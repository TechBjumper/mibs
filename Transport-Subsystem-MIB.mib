-- extracted from draft-ietf-isms-tmsm-04.txt
-- at Thu Oct 12 06:07:13 2006

  Transport-Subsystem-MIB DEFINITIONS ::= BEGIN

  IMPORTS
      MODULE-IDENTITY, OBJECT-TYPE,
      mib-2, Integer32, Unsigned32, Gauge32
        FROM SNMPv2-SMI
      TestAndIncr, StorageType, RowStatus
        FROM SNMPv2-TC
      MODULE-COMPLIANCE, OBJECT-GROUP
        FROM SNMPv2-CONF
      SnmpSecurityModel,
      SnmpAdminString,  SnmpSecurityLevel, SnmpEngineID
         FROM SNMP-FRAMEWORK-MIB
      TransportAddress, TransportAddressType
        FROM TRANSPORT-ADDRESS-MIB
      ;

  tmsMIB MODULE-IDENTITY
      LAST-UPDATED "200610060000Z"
      ORGANIZATION "ISMS Working Group"
      CONTACT-INFO "WG-EMail:   isms@lists.ietf.org
                    Subscribe:  isms-request@lists.ietf.org

                 Chairs:
                   Juergen Quittek
                   NEC Europe Ltd.
                   Network Laboratories
                   Kurfuersten-Anlage 36
                   69115 Heidelberg
                   Germany
                   +49 6221 90511-15
                    quittek@netlab.nec.de

                    Juergen Schoenwaelder
                    International University Bremen
                    Campus Ring 1
                    28725 Bremen
                    Germany
                    +49 421 200-3587
                    j.schoenwaelder@iu-bremen.de

                 Editor:
                    David Harrington
                    FutureWei Technologies
                    1700 Alma Drive, Suite 100
                    Plano, Texas 75075
                    USA
                    +1 603-436-8634
                    dharrington@huawei.com
                      "
         DESCRIPTION  "The Transport Subsystem MIB Module

                       Copyright (C) The Internet Society (2006). This
                       version of this MIB module is part of RFC XXXX;
                       see the RFC itself for full legal notices.

  -- NOTE to RFC editor: replace XXXX with actual RFC number
  --                     for this document and remove this note
                      "

         REVISION     "200610060000Z"         -- 20 April 2006
         DESCRIPTION  "The initial version, published in RFC XXXX.
  -- NOTE to RFC editor: replace XXXX with actual RFC number
  --                     for this document and remove this note
                      "

      ::= { mib-2 1 }
  -- RFC Ed.: replace xxxx with IANA-assigned number and
  --          remove this note

  -- ---------------------------------------------------------- --
  -- subtrees in the Transport-Subsystem-MIB
  -- ---------------------------------------------------------- --

  tmsNotifications OBJECT IDENTIFIER ::= { tmsMIB 0 }
  tmsObjects       OBJECT IDENTIFIER ::= { tmsMIB 1 }
  tmsConformance   OBJECT IDENTIFIER ::= { tmsMIB 2 }

  -- -------------------------------------------------------------
  -- Objects
  -- -------------------------------------------------------------

  -- Textual Conventions

  SnmpTransportModel ::= TEXTUAL-CONVENTION
      STATUS       current
      DESCRIPTION "An identifier that uniquely identifies a
                   Transport Model of the Transport Subsystem within
                   the SNMP Management Architecture.

                   The values for transportModel are allocated as
                   follows:

                   - The zero value does not identify any particular
                     transport model.

                   - Values between 1 and 255, inclusive, are reserved
                     for standards-track Transport Models and are
                     managed by the Internet Assigned Numbers Authority
                     (IANA).
                   - Values greater than 255 are allocated to
                     enterprise-specific Transport Models.  An
                     enterprise-specific transportModel value is defined
                     to be:
                     enterpriseID * 256 + transport model within
                     enterprise

                     For example, the fourth Transport Model defined by
                     the enterprise whose enterpriseID is 1 would be
                     260.

                   This scheme for allocation of transportModel
                   values allows for a maximum of 255 standards-
                   based Transport Models, and for a maximum of
                   256 Transport Models per enterprise.

                   It is believed that the assignment of new
                   transportModel values will be rare in practice
                   because the larger the number of simultaneously
                   utilized Transport Models, the larger the
                   chance that interoperability will suffer.
                   Consequently, it is believed that such a range
                   will be sufficient.  In the unlikely event that
                   the standards committee finds this number to be
                   insufficient over time, an enterprise number
                   can be allocated to obtain an additional 256
                   possible values.

                   Note that the most significant bit must be zero;
                   hence, there are 23 bits allocated for various
                   organizations to design and define non-standard
                   transportModels.  This limits the ability to
                   define new proprietary implementations of Transport
                   Models to the first 8,388,608 enterprises.

                   It is worthwhile to note that, in its encoded
                   form, the transportModel value will normally
                   require only a single byte since, in practice,
                   the leftmost bits will be zero for most messages
                   and sign extension is suppressed by the encoding
                   rules.

                   As of this writing, there are several values
                   of transportModel defined for use with SNMP or
                   reserved for use with supporting MIB objects.
                   They are as follows:

                       0  reserved for 'any'
                       1  reserved for UDP
                       2  reserved for TCP
                       3  SSH Transport Model
                  "

      SYNTAX       INTEGER(0 .. 2147483647)

  -- Notifications for the Transport Subsystem

  -- Statistics for the Transport Subsystem


  tmsStats         OBJECT IDENTIFIER ::= { tmsObjects 1 }


  -- -------------------------------------------------------------
  -- Conformance Information
  -- -------------------------------------------------------------

  tmsGroups OBJECT IDENTIFIER ::= { tmsConformance 1 }

  tmsCompliances OBJECT IDENTIFIER ::= { tmsConformance 2 }

  -- -------------------------------------------------------------
  -- Units of conformance
  -- -------------------------------------------------------------
  tmsGroup OBJECT-GROUP
--      OBJECTS {
--
--      }
      STATUS      current
      DESCRIPTION "A collection of objects for maintaining session
                   information of an SNMP engine which implements the
                   Transport subsystem.
                  "

      ::= { tmsGroups 2 }

  -- -------------------------------------------------------------
  -- Compliance statements
  -- -------------------------------------------------------------

  tmsCompliance MODULE-COMPLIANCE
      STATUS      current
      DESCRIPTION
          "The compliance statement for SNMP engines that support the
          Transport-Subsystem-MIB"
      MODULE
          MANDATORY-GROUPS { tmsGroup }
      ::= { tmsCompliances 1 }

  END

-- 
--    Copyright (C) The Internet Society (2006).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
