----------------------------------------------
-- NOVELSAT-DEMODULATOR.mib             --
-- MIB generated by naamab, Novelsat        --
-- Sunday, September 12, 2010 at 15:46:00   --
----------------------------------------------


NOVELSAT-DEMODULATOR-MIB DEFINITIONS ::= BEGIN

IMPORTS
        OBJECT-TYPE, Integer32, Counter32, OBJECT-IDENTITY, MODULE-IDENTITY, Unsigned32, IpAddress, Counter64
                FROM SNMPv2-SMI
        DisplayString, DateAndTime, RowStatus
                FROM SNMPv2-TC
        ifIndex
                FROM IF-MIB
        nsRoot
                FROM NOVELSAT-ROOT-MIB;

-- ===================================================

nsDemodulator MODULE-IDENTITY
        LAST-UPDATED "201009121500Z"
        ORGANIZATION
                "Novelsat"
        CONTACT-INFO
                "21 Ha'taasiya St.,
                Ra'anana 43654,Israel
                --------------------------
                Tel: +972-9-7889730
                Fax: +972-9-
                e-mail: info@novelsat.com, support@novelsat.com
                http://www.novelsat.com
                --------------------------
                "
        DESCRIPTION
                "Novelsat MIB branch for DeModulator products"

        REVISION "201009121500Z"
        DESCRIPTION
                "Version 1.0.0.X"
::= { nsRoot 4 }

-- ===================================================
nsDemodConfig  OBJECT-IDENTITY
        STATUS current
        DESCRIPTION
              "Demodulator MIB branch that holds all Demodulator configuration parameters."
        ::= { nsDemodulator 1 }

-- ===================================================
nsDemodConfigLine  OBJECT-IDENTITY
        STATUS current
        DESCRIPTION
              "Demodulator MIB branch that holds all Demodulator line parameters."
        ::= { nsDemodConfig 1 }

nsDemodConfigLineMode  OBJECT-TYPE
        SYNTAX  INTEGER {
            dvbs (0),
            dsng (1),
            dvbs2 (2),
            ns3 (3),
            notApplicable (255)
        }
        MAX-ACCESS  read-write
        STATUS  current
        DESCRIPTION
                "This parameter holds Line mode."
        ::= { nsDemodConfigLine  1 }
        
nsDemodConfigLineRFFreq  OBJECT-TYPE
        SYNTAX  Unsigned32 
        MAX-ACCESS  read-write
        STATUS  current
        DESCRIPTION
                "This parameter holds Line RF frequency in 10Hrz."
        ::= { nsDemodConfigLine  2 }

nsDemodConfigLineRollOff  OBJECT-TYPE
        SYNTAX  INTEGER {
            rollOff005 (0),
            rollOff010 (1),
            rollOff015 (2),
            rollOff020 (3),
            rollOff025 (4),
            rollOff035 (5),
            notApplicable (255)
        }
        MAX-ACCESS  read-write
        STATUS  current
        DESCRIPTION
                "This parameter holds Line roll off.
                rollOff005 = 0.05
                rollOff010 = 0.10
                rollOff015 = 0.15
                rollOff020 = 0.20
                rollOff025 = 0.25
                rollOff035 = 0.35
                "
        ::= { nsDemodConfigLine  3 } 
 
nsDemodConfigLineSymbolRate  OBJECT-TYPE
        SYNTAX  Integer32 (50000..72000000)
        MAX-ACCESS  read-write
        STATUS  current
        DESCRIPTION
                "This parameter holds Line symbol rate in SPS."
        ::= { nsDemodConfigLine  4 }      

nsDemodConfigLineLNBControl  OBJECT-TYPE
        SYNTAX  INTEGER {
            lnbOff (0),
            lnb13v0khz (1),
            lnb13v22khz (2),
            lnb18v0khz (3),
            lnb18v22khz (4),
            notApplicable (255)
        }
        MAX-ACCESS  read-write
        STATUS  current
        DESCRIPTION
                "This parameter holds Line LNB control."
        ::= { nsDemodConfigLine  5 }

nsDemodConfigLineDualChState  OBJECT-TYPE
        SYNTAX  INTEGER {
			dual (0),
			single (1),
            notApplicable (255)
        }
        MAX-ACCESS  read-write
        STATUS  current
        DESCRIPTION
                "This parameter holds Line dual channel status: dual/single channel."
        ::= { nsDemodConfigLine  6 }

nsDemodConfigLineNoneLinearMode  OBJECT-TYPE
        SYNTAX  INTEGER {
			off (0),
			on (1),
            notApplicable (255)
        }
        MAX-ACCESS  read-write
        STATUS  current
        DESCRIPTION
                "This parameter holds Line none linear mode: off/on."
        ::= { nsDemodConfigLine  7 }
 
nsDemodConfigLineAcmMode  OBJECT-TYPE
        SYNTAX  INTEGER {
			disable (0),
            enableCh1 (1),
            enableCh2 (2),
            enableCh1Ch2 (3),
            notApplicable (255)
        }
        MAX-ACCESS  read-write
        STATUS  current
        DESCRIPTION
                "This parameter holds Line ACM mode: enable/disable."
        ::= { nsDemodConfigLine  8 }

nsDemodConfigLineAcmServerAddress  OBJECT-TYPE
		SYNTAX   IpAddress
        MAX-ACCESS  read-write
        STATUS  current
        DESCRIPTION
                "This parameter holds Line ACM server address."
        ::= { nsDemodConfigLine  9 }
        
nsDemodConfigLineAcmMargin  OBJECT-TYPE
        SYNTAX  Integer32 (0..25500)
        MAX-ACCESS  read-write
        STATUS  current
        DESCRIPTION
                "This parameter is no longer supported" 
        ::= { nsDemodConfigLine  10 }
                 
nsDemodConfigLineGoldSeq  OBJECT-TYPE
        SYNTAX  Integer32 (0..262141)
        MAX-ACCESS  read-write
        STATUS  current
        DESCRIPTION
                "This parameter holds Line golden sequence."
        ::= { nsDemodConfigLine  11 } 

nsDemodConfigLineAutoCcmMode  OBJECT-TYPE
        SYNTAX  INTEGER {
            disable (0),
            enable (1),
            notApplicable (255)
        }
        MAX-ACCESS  read-write
        STATUS  current
        DESCRIPTION
                "This parameter holds Line Auto CCM mode: enable/disable."
        ::= { nsDemodConfigLine  12 }

nsDemodConfigLineLOFreq  OBJECT-TYPE
        SYNTAX  Unsigned32 (0..4000000000)
        MAX-ACCESS  read-write
        STATUS  current
        DESCRIPTION
                "This parameter holds Line LO frequency in 10Hrz."
        ::= { nsDemodConfigLine  13 }
	 
nsDemodConfigLineInputLevelMode  OBJECT-TYPE
        SYNTAX  INTEGER {
            constantPower (0),
            constantEnvelope (1),
            notApplicable (255)
        }
        MAX-ACCESS  read-write
        STATUS  current
        DESCRIPTION
                "This parameter holds Line input level mode: constant power/constant envelope."
        ::= { nsDemodConfigLine  14 }

nsDemodConfigLineAcmUseManagementIp  OBJECT-TYPE 
        SYNTAX  INTEGER {
            disable (0),
            enable (1),
            notApplicable (255)
        }
        MAX-ACCESS  read-write
        STATUS  current
        DESCRIPTION
                "This parameter is no longer supported"
        ::= { nsDemodConfigLine  15 } 
                
nsDemodConfigLineAcmIpAddress  OBJECT-TYPE 
        SYNTAX  IpAddress
        MAX-ACCESS  read-write
        STATUS  current
        DESCRIPTION
                "This parameter is no longer supported"
        ::= { nsDemodConfigLine  16 } 
        
nsDemodConfigLineAcmIpNetmask  OBJECT-TYPE 
        SYNTAX  IpAddress
        MAX-ACCESS  read-write
        STATUS  current
        DESCRIPTION
                "This parameter is no longer supported"
        ::= { nsDemodConfigLine  17 } 
        
nsDemodConfigLineAcmIpNextHopIp  OBJECT-TYPE 
        SYNTAX  IpAddress
        MAX-ACCESS  read-write
        STATUS  current
        DESCRIPTION
                "This parameter is no longer supported"
        ::= { nsDemodConfigLine  18 }         

nsDemodConfigLineAcmMarginCh1  OBJECT-TYPE
        SYNTAX  Integer32 (0..25500)
        MAX-ACCESS  read-write
        STATUS  current
        DESCRIPTION
                "This parameter holds Line ACM margin for channel 2 in hundreds of dB."
        ::= { nsDemodConfigLine  19 }
                 
nsDemodConfigLineAcmMarginCh2  OBJECT-TYPE
        SYNTAX  Integer32 (0..25500)
        MAX-ACCESS  read-write
        STATUS  current
        DESCRIPTION
                "This parameter holds Line ACM margin for channel 2 in hundreds of dB."
        ::= { nsDemodConfigLine  20 }
                 

nsDemodConfigLineEchoCancellationMode  OBJECT-TYPE
        SYNTAX  INTEGER {
            disable (0),
            enable (1),
            tx-hub-enable (2),
            rx-hub-enable (3),
            notApplicable (255)
        }
        MAX-ACCESS  read-write
        STATUS  current
        DESCRIPTION
                "This parameter holds Line echo cancellation mode."
        ::= { nsDemodConfigLine  21 }
 
nsDemodConfigLineEchoCancellationMinDelay  OBJECT-TYPE
        SYNTAX  Unsigned32 (0..650)
        MAX-ACCESS  read-write
        STATUS  current
        DESCRIPTION
                "This parameter holds Line echo cancellation min delay in mSec."
        ::= { nsDemodConfigLine  22 }

nsDemodConfigLineEchoCancellationMaxDelay  OBJECT-TYPE
        SYNTAX  Unsigned32 (1..650)
        MAX-ACCESS  read-write
        STATUS  current
        DESCRIPTION
                "This parameter holds Line echo cancellation max delay in mSec."
        ::= { nsDemodConfigLine  23 }

nsDemodConfigLineEchoCancellationTxFreqOffset  OBJECT-TYPE
        SYNTAX  Integer32 (-36000000..36000000)
        MAX-ACCESS  read-write
        STATUS  current
        DESCRIPTION
                "This parameter holds Line echo cancellation TX frequency offset in Hz."
        ::= { nsDemodConfigLine  24 }

nsDemodConfigLineAdvancedAcmMode  OBJECT-TYPE
        SYNTAX  INTEGER {
            disable (0),
            enable (1),
            notApplicable (255)
        }
        MAX-ACCESS  read-write
        STATUS  current
        DESCRIPTION
                "This parameter holds Line Advanced ACM: enable/disable."
        ::= { nsDemodConfigLine  25 }
-- ===================================================
nsDemodConfigChannel  OBJECT-IDENTITY
        STATUS current
        DESCRIPTION
              "Demodulator MIB branch that holds all Demodulator channel parameters."
        ::= { nsDemodConfig 2 }

nsDemodConfigChannelTable OBJECT-TYPE
    SYNTAX SEQUENCE OF DemodConfigChannelEntry
    MAX-ACCESS not-accessible
    STATUS current
    DESCRIPTION
        "A list of Channel parameters"
    ::= { nsDemodConfigChannel 1 } 

nsDemodConfigChannelEntry OBJECT-TYPE
    SYNTAX      DemodConfigChannelEntry
    MAX-ACCESS  not-accessible
    STATUS      current
    DESCRIPTION "Conceptual row in table for each channel."
    INDEX   { ifIndex }
    ::= { nsDemodConfigChannelTable 1 }
        
DemodConfigChannelEntry ::=
    SEQUENCE {
        nsDemodConfigChIsiFrom      INTEGER,
        nsDemodConfigChIsiTo        INTEGER
    } 
    
nsDemodConfigChIsiFrom  OBJECT-TYPE
        SYNTAX  Integer32 
        MAX-ACCESS  read-write
        STATUS  current
        DESCRIPTION
                "This parameter holds channel ISI start range."
        ::= { nsDemodConfigChannelEntry  1 }

nsDemodConfigChIsiTo  OBJECT-TYPE
        SYNTAX  Integer32 
        MAX-ACCESS  read-write
        STATUS  current
        DESCRIPTION
                "This parameter holds channel ISI end range."
        ::= { nsDemodConfigChannelEntry  2 }

-- ===================================================
nsDemodConfigInterface  OBJECT-IDENTITY
        STATUS current
        DESCRIPTION
              "Demodulator MIB branch that holds all Demodulator Interface parameters."
        ::= { nsDemodConfig 3 }


nsDemodConfigInterfaceTestTable  OBJECT-TYPE
    SYNTAX SEQUENCE OF DemodConfigInterfaceTestEntry
    MAX-ACCESS not-accessible
    STATUS current
    DESCRIPTION
        "A list of Test interfaces"
    ::= { nsDemodConfigInterface 1 } 

nsDemodConfigInterfaceTestEntry OBJECT-TYPE
    SYNTAX      DemodConfigInterfaceTestEntry
    MAX-ACCESS  not-accessible
    STATUS      current
    DESCRIPTION "Conceptual row in table for each test interface."
    INDEX   { ifIndex }
    ::= { nsDemodConfigInterfaceTestTable 1 }
                
DemodConfigInterfaceTestEntry ::=
    SEQUENCE {
        nsDemodConfigInterfaceTestSource          INTEGER,
        nsDemodConfigInterfaceTestPattern         INTEGER,
        nsDemodConfigInterfaceTestInvert          INTEGER,
        nsDemodConfigInterfaceTestIgnoreBytes     INTEGER
    } 

nsDemodConfigInterfaceTestSource  OBJECT-TYPE
        SYNTAX  INTEGER {
            disable (0),
            channel1 (1),
            channel2 (2),
            notApplicable (255)
        }
        MAX-ACCESS  read-write
        STATUS  current
        DESCRIPTION
                "This parameter holds Test interface source."
        ::= { nsDemodConfigInterfaceTestEntry  1 }     

nsDemodConfigInterfaceTestPattern  OBJECT-TYPE
        SYNTAX  INTEGER {
            pattern2Pwr7Neg1 (0),
            pattern2Pwr9Neg1 (1),
            pattern2Pwr11Neg1 (2),
            pattern2Pwr15Neg1 (3),
            pattern2Pwr20Neg1 (4),
            pattern2Pwr23Neg1 (5),
            pattern2Pwr29Neg1 (6),
            pattern2Pwr31Neg1 (7),
            patternAllZeros (8),
            patternAllOnes (9),
            patternBitAlternate (10),
            pattern2BitAlternate (11),
            pattern7Ones (12),
            pattern7Zeros (13),
            pattern6Ones (14),
            pattern6Zeros (15),
            pattern55AA (16),
            pattern6699 (17),
            patternC33C (18),
            pattern00FF (19),
            patternSAWTOOTH (20),
            notApplicable (255)
        }
        MAX-ACCESS  read-write
        STATUS  current
        DESCRIPTION
                "This parameter holds Test interface pattern.
                    pattern2Pwr07Neg1 = 2^07-1
                    pattern2Pwr09Neg1 = 2^09-1
		            pattern2Pwr11Neg1 = 2^11-1
		            pattern2Pwr15Neg1 = 2^15-1
		            pattern2Pwr20Neg1 = 2^20-1
		            pattern2Pwr23Neg1 = 2^23-1
		            pattern2Pwr29Neg1 = 2^29-1
		            pattern2Pwr31Neg1 = 2^31-1
		            patternAllZeros   = all zeros
		            patternAllOnes    = all ones
		            patternBitAlternate = bit alternate
		            pattern2BitAlternate= 2 bit alternate
		            pattern7Ones      = 1111111 (7 ones)
		            pattern7Zeros     = 0000000 (7 zeros)
		            pattern6Ones      = 111111 (6 ones)
		            pattern6Zeros     = 000000 (6 zeros)
		            pattern55AA       = 0x55AA
		            pattern6699       = 0x6699
		            patternC33C       = 0xC33C
		            pattern00FF       = 0x00FF
		            patternSAWTOOTH   = SAWTOOTH
                "
        ::= { nsDemodConfigInterfaceTestEntry  2 }                

nsDemodConfigInterfaceTestInvert  OBJECT-TYPE
        SYNTAX  INTEGER {
            no (0),
            yes (1),
            notApplicable (255)
        }
        MAX-ACCESS  read-write
        STATUS  current
        DESCRIPTION
                "This parameter holds Test interface invert."
        ::= { nsDemodConfigInterfaceTestEntry  3 }   
                
nsDemodConfigInterfaceTestIgnoreBytes  OBJECT-TYPE
        SYNTAX  Integer32 (0..262142)
        MAX-ACCESS  read-write
        STATUS  current
        DESCRIPTION
                "This parameter holds Test interface ignore bytes."
        ::= { nsDemodConfigInterfaceTestEntry  4 }                 
                
                
                
nsDemodConfigInterfaceASITable  OBJECT-TYPE
    SYNTAX SEQUENCE OF DemodConfigInterfaceASIEntry
    MAX-ACCESS not-accessible
    STATUS current
    DESCRIPTION
        "A list of ASI interfaces"
    ::= { nsDemodConfigInterface  2 }

nsDemodConfigInterfaceASIEntry OBJECT-TYPE
    SYNTAX      DemodConfigInterfaceASIEntry
    MAX-ACCESS  not-accessible
    STATUS      current
    DESCRIPTION "Conceptual row in table for each ASI interface."
    INDEX   { ifIndex }
    ::= { nsDemodConfigInterfaceASITable 1 }
            
DemodConfigInterfaceASIEntry ::=
    SEQUENCE {
        nsDemodConfigInterfaceASISource             INTEGER,
        nsDemodConfigInterfaceASIDataInvert         INTEGER,
        nsDemodConfigInterfaceASIDataRateMode       INTEGER,
        nsDemodConfigInterfaceASIDataRate           Integer32,
        nsDemodConfigInterfaceASIDataRateAccuracy   Integer32
    } 
                
nsDemodConfigInterfaceASISource  OBJECT-TYPE
        SYNTAX  INTEGER {
            disable (0),
            channel1 (1),
            channel2 (2),
            notApplicable (255)
        }
        MAX-ACCESS  read-write
        STATUS  current
        DESCRIPTION
                "This parameter holds ASI interface source."
        ::= { nsDemodConfigInterfaceASIEntry  1 }                

nsDemodConfigInterfaceASIDataInvert  OBJECT-TYPE
        SYNTAX  INTEGER {
            no (0),
            yes (1),
            notApplicable (255)
        }
        MAX-ACCESS  read-write
        STATUS  current
        DESCRIPTION
                "This parameter holds ASI interface data invert."
        ::= { nsDemodConfigInterfaceASIEntry  2 }   
        
nsDemodConfigInterfaceASIDataRateMode  OBJECT-TYPE
        SYNTAX  INTEGER {
            auto (0),
            manual (1),
            notApplicable (255)
        }
        MAX-ACCESS  read-write
        STATUS  current
        DESCRIPTION
                "This parameter holds ASI interface data rate mode: automatic/manual."
        ::= { nsDemodConfigInterfaceASIEntry  3 }         
        
nsDemodConfigInterfaceASIDataRate  OBJECT-TYPE
        SYNTAX  Integer32
        MAX-ACCESS  read-write
        STATUS  current
        DESCRIPTION
                "This parameter holds ASI interface data rate in bPS."
        ::= { nsDemodConfigInterfaceASIEntry  4 }
        
nsDemodConfigInterfaceASIDataRateAccuracy  OBJECT-TYPE
        SYNTAX  Integer32
        MAX-ACCESS  read-write
        STATUS  current
        DESCRIPTION
                "This parameter holds ASI interface data rate accuracy in hundreds of ppm."
        ::= { nsDemodConfigInterfaceASIEntry  5 }                  

nsDemodConfigInterfaceEthernetTable  OBJECT-TYPE
	SYNTAX SEQUENCE OF ModConfigInterfaceEthernetEntry
	MAX-ACCESS not-accessible
	STATUS current
	DESCRIPTION
		"A list of Ethernet interfaces"
    ::= { nsDemodConfigInterface  4 }
          
nsDemodConfigInterfaceEthernetEntry OBJECT-TYPE
    SYNTAX      ModConfigInterfaceEthernetEntry
    MAX-ACCESS  not-accessible
    STATUS      current
    DESCRIPTION "Conceptual row in table for each Ethernet interface."
    INDEX   { ifIndex }
    ::= { nsDemodConfigInterfaceEthernetTable 1 }
            
ModConfigInterfaceEthernetEntry ::=
    SEQUENCE {
        nsDemodConfigInterfaceEthernetSource    		 INTEGER,
        nsDemodConfigInterfaceEthernetAutoNegotiation    INTEGER,
        nsDemodConfigInterfaceEthernetSpeed              INTEGER,
        nsDemodConfigInterfaceEthernetDuplex             INTEGER,
        nsDemodConfigInterfaceEthernetEncapsulation      INTEGER,
        nsDemodConfigInterfaceEthernetPid                Integer32
    } 
                

nsDemodConfigInterfaceEthernetSource  OBJECT-TYPE
        SYNTAX  INTEGER {
            disable (0),
            channel-1 (1),
            channel-2 (2),
            notApplicable (255)
        }
        MAX-ACCESS  read-write
        STATUS  current
        DESCRIPTION
                "This parameter holds Ethernet interface source"
        ::= { nsDemodConfigInterfaceEthernetEntry  1 }
        
nsDemodConfigInterfaceEthernetAutoNegotiation  OBJECT-TYPE
        SYNTAX  INTEGER {
            disable (0),
            enable (1),
            notApplicable (255)
        }
        MAX-ACCESS  read-write
        STATUS  current
        DESCRIPTION
                "This parameter holds Ethernet interface auto-negotiation status"
        ::= { nsDemodConfigInterfaceEthernetEntry  2 }
        
nsDemodConfigInterfaceEthernetSpeed  OBJECT-TYPE
        SYNTAX  INTEGER {
            speed10 (0),
            speed100 (1),
            notApplicable (255)
        }
        MAX-ACCESS  read-write
        STATUS  current
        DESCRIPTION
                "This parameter holds Ethernet interface speed"
        ::= { nsDemodConfigInterfaceEthernetEntry  3 }        
        
nsDemodConfigInterfaceEthernetDuplex  OBJECT-TYPE
        SYNTAX  INTEGER {
            half (0),
            full (1),
            notApplicable (255)
        }
        MAX-ACCESS  read-write
        STATUS  current
        DESCRIPTION
                "This parameter holds Ethernet interface Duplex"
        ::= { nsDemodConfigInterfaceEthernetEntry  4 }                           

nsDemodConfigInterfaceEthernetEncapsulation  OBJECT-TYPE
        SYNTAX  INTEGER {
            raw (0),
            nspe (1),
            gse  (2),
            ule  (3),
            notApplicable (255)
        }
        MAX-ACCESS  read-write
        STATUS  current
        DESCRIPTION
                "This parameter holds Ethernet interface Encapsulation"
        ::= { nsDemodConfigInterfaceEthernetEntry  5 }                           

nsDemodConfigInterfaceEthernetPid  OBJECT-TYPE
        SYNTAX  Integer32 (32..8191)
        MAX-ACCESS  read-write
        STATUS  current
        DESCRIPTION
                "This parameter holds Ethernet interface PID value"
        ::= { nsDemodConfigInterfaceEthernetEntry  6 }                 
                              
                              
        
nsDemodConfigInterfaceGigETable  OBJECT-TYPE
    SYNTAX SEQUENCE OF ModConfigInterfaceGigEEntry
    MAX-ACCESS not-accessible
    STATUS current
    DESCRIPTION
        "A list of GigE interfaces"
    ::= { nsDemodConfigInterface  5 }
          
nsDemodConfigInterfaceGigEEntry OBJECT-TYPE
    SYNTAX      ModConfigInterfaceGigEEntry
    MAX-ACCESS  not-accessible
    STATUS      current
    DESCRIPTION "Conceptual row in table for each gigE interface."
    INDEX   { ifIndex }
    ::= { nsDemodConfigInterfaceGigETable 1 }
            
ModConfigInterfaceGigEEntry ::=
    SEQUENCE {
        nsDemodConfigInterfaceGigEAutoNegotiation    INTEGER,
        nsDemodConfigInterfaceGigESpeed              INTEGER,
        nsDemodConfigInterfaceGigEDuplex             INTEGER,
        nsDemodConfigInterfaceGigEPortType           INTEGER
    } 
                

nsDemodConfigInterfaceGigEAutoNegotiation  OBJECT-TYPE
        SYNTAX  INTEGER {
            disable (0),
            enable (1),
            notApplicable (255)
        }
        MAX-ACCESS  read-write
        STATUS  current
        DESCRIPTION
                "This parameter holds GigE interface auto-negotiation status"
        ::= { nsDemodConfigInterfaceGigEEntry  1 }
        
nsDemodConfigInterfaceGigESpeed  OBJECT-TYPE
        SYNTAX  INTEGER {
            speed10 (0),
            speed100 (1),
            notApplicable (255)
        }
        MAX-ACCESS  read-write
        STATUS  current
        DESCRIPTION
                "This parameter holds GigE interface speed"
        ::= { nsDemodConfigInterfaceGigEEntry  2 }          
        
nsDemodConfigInterfaceGigEDuplex  OBJECT-TYPE
        SYNTAX  INTEGER {
            half (0),
            full (1),
            notApplicable (255)
        }
        MAX-ACCESS  read-write
        STATUS  current
        DESCRIPTION
                "This parameter holds GigE interface Duplex"
        ::= { nsDemodConfigInterfaceGigEEntry  3 }     

nsDemodConfigInterfaceGigEPortType  OBJECT-TYPE
        SYNTAX  INTEGER {
            rj45 (0),
            sfp (1),
            notApplicable (255)
        }
        MAX-ACCESS  read-write
        STATUS  current
        DESCRIPTION
                "This parameter holds GigE interface port type value"
        ::= { nsDemodConfigInterfaceGigEEntry  5 }                               
                              
 
-- ===================================================
nsDemodConfigDiseqc  OBJECT-IDENTITY
        STATUS current
        DESCRIPTION
              "Demodulator MIB branch that holds all Demodulator DiSEqC parameters."
        ::= { nsDemodConfig 4 }

nsDemodConfigDiseqcTable OBJECT-TYPE
    SYNTAX SEQUENCE OF DemodConfigDiseqcEntry
    MAX-ACCESS not-accessible
    STATUS current
    DESCRIPTION
        "A list of Diseqc parameters"
    ::= { nsDemodConfigDiseqc 1 } 

nsDemodConfigDiseqcEntry OBJECT-TYPE
    SYNTAX      DemodConfigDiseqcEntry
    MAX-ACCESS  not-accessible
    STATUS      current
    DESCRIPTION "Conceptual row in table for each DiSEqC."
    INDEX   { nsDemodConfigDiseqcName }
    ::= { nsDemodConfigDiseqcTable 1 }
        
DemodConfigDiseqcEntry ::=
    SEQUENCE {
        nsDemodConfigDiseqcName             DisplayString,
        nsDemodConfigDiseqcHeaderBytes      Counter64,
        nsDemodConfigDiseqcNumDataBytes     Unsigned32,
        nsDemodConfigDiseqcToneBurstMode    INTEGER,
        nsDemodConfigDiseqcNotifyRowStatus  RowStatus
    } 
    
nsDemodConfigDiseqcName  OBJECT-TYPE
        SYNTAX  DisplayString 
        MAX-ACCESS  not-accessible
        STATUS  current
        DESCRIPTION
                "This parameter holds DiSEqC command's name."
        ::= { nsDemodConfigDiseqcEntry  1 }

nsDemodConfigDiseqcHeaderBytes  OBJECT-TYPE
        SYNTAX  Counter64 
        MAX-ACCESS  read-create
        STATUS  current
        DESCRIPTION
                "This parameter holds DiSEqC command's header bytes."
        ::= { nsDemodConfigDiseqcEntry  2 }

nsDemodConfigDiseqcNumDataBytes  OBJECT-TYPE
        SYNTAX  Unsigned32 
        MAX-ACCESS  read-create
        STATUS  current
        DESCRIPTION
                "This parameter holds DiSEqC command's number of data bytes."
        ::= { nsDemodConfigDiseqcEntry  3 }
        
nsDemodConfigDiseqcToneBurstMode  OBJECT-TYPE
        SYNTAX  INTEGER {
            auto (0),
            unmodulated (1),
            modulated (2),
            none (3),
            notApplicable (255)
        }
        MAX-ACCESS  read-create
        STATUS  current
        DESCRIPTION
                "This parameter holds DiSEqC command's tone burst mode."
        ::= { nsDemodConfigDiseqcEntry  4 } 
               
nsDemodConfigDiseqcNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsDemodConfigDiseqcEntry 5 }
        
-- ==  run command
nsDemodConfigDiseqcExecuteCmd  OBJECT-IDENTITY
        STATUS current
        DESCRIPTION
              "Demodulator MIB branch that holds parameters to execute DiSEqC command."
        ::= { nsDemodConfigDiseqc 2 }

nsDemodConfigDiseqcExecuteCmdName  OBJECT-TYPE
        SYNTAX  DisplayString 
        MAX-ACCESS  read-write
        STATUS  current
        DESCRIPTION
              "This parameter holds DiSEqC command's name to execute."
        ::= { nsDemodConfigDiseqcExecuteCmd 1 }

nsDemodConfigDiseqcExecuteCmdData  OBJECT-TYPE
        SYNTAX  Unsigned32 
        MAX-ACCESS  read-write
        STATUS  current
        DESCRIPTION
              "This parameter holds DiSEqC command's data for execution."
        ::= { nsDemodConfigDiseqcExecuteCmd 2 }
                     
nsDemodConfigDiseqcExecuteCmdExecute  OBJECT-TYPE
        SYNTAX  INTEGER {
            none (0),
            run (1),
            notApplicable (255)
        }
        MAX-ACCESS  read-write
        STATUS  current
        DESCRIPTION
              "This parameter holds allow to start DiSEqC command execution."
        ::= { nsDemodConfigDiseqcExecuteCmd 3 }
                     
                                   
-- ===================================================
nsDemodMonitor  OBJECT-IDENTITY
        STATUS current
        DESCRIPTION
              "Demodulator MIB branch that holds all Demodulator status and alarms."
        ::= { nsDemodulator 2 }

nsDemodMonitorLine  OBJECT-IDENTITY
        STATUS current
        DESCRIPTION
              "Demodulator MIB branch that holds all Demodulator line statuses."
        ::= { nsDemodMonitor 1 }

nsDemodMonitorLineMode  OBJECT-TYPE
        SYNTAX  INTEGER {
            dvbs (0),
            dsng (1),
            dvbs2 (2),
            ns3 (3),
            notApplicable (255)
        }
        MAX-ACCESS  read-only
        STATUS  current
        DESCRIPTION
                "This parameter holds Line mode status."
        ::= { nsDemodMonitorLine  1 }

nsDemodMonitorLineState  OBJECT-TYPE
        SYNTAX  INTEGER {
            no-sync (0),
            sync (1),
            notApplicable (255)
        }
        MAX-ACCESS  read-only
        STATUS  current
        DESCRIPTION
                "This parameter holds Line state status."
        ::= { nsDemodMonitorLine  2 }

nsDemodMonitorLineSNR  OBJECT-TYPE
        SYNTAX  Integer32 
        MAX-ACCESS  read-only
        STATUS  current
        DESCRIPTION
                "This parameter holds Line Pilot SNR status in hundreds of dB."
        ::= { nsDemodMonitorLine  3 }
        
nsDemodMonitorLineCompositePower  OBJECT-TYPE
        SYNTAX  Integer32 
        MAX-ACCESS  read-only
        STATUS  current
        DESCRIPTION
                "This parameter holds Line Composite power status in hundreds of dBm."
        ::= { nsDemodMonitorLine  4 }

nsDemodMonitorLineSymbolRate  OBJECT-TYPE
        SYNTAX  Integer32 
        MAX-ACCESS  read-only
        STATUS  current
        DESCRIPTION
                "This parameter holds Symbol rate status in SPS."
        ::= { nsDemodMonitorLine  5 }

nsDemodMonitorLineRollOff  OBJECT-TYPE
        SYNTAX  INTEGER {
            rollOff005 (0),
            rollOff010 (1),
            rollOff015 (2),
            rollOff020 (3),
            rollOff025 (4),
            rollOff035 (5),
            notApplicable (255)
        }
        MAX-ACCESS  read-only
        STATUS  current
        DESCRIPTION
                "This parameter holds Line roll off.
                rollOff005 = 0.05
                rollOff010 = 0.10
                rollOff015 = 0.15
                rollOff020 = 0.20
                rollOff025 = 0.25
                rollOff035 = 0.35
                "
        ::= { nsDemodMonitorLine  6 }

nsDemodMonitorLineRFFreq  OBJECT-TYPE
        SYNTAX  Unsigned32 
        MAX-ACCESS  read-only
        STATUS  current
        DESCRIPTION
                "This parameter holds Line RF frequency status in 10Hz."
        ::= { nsDemodMonitorLine  7 }

nsDemodMonitorLineDataRateCh1  OBJECT-TYPE
        SYNTAX  Integer32 
        MAX-ACCESS  read-only
        STATUS  current
        DESCRIPTION
                "This parameter holds Line Data rate channel 1 status in bit/sec."
        ::= { nsDemodMonitorLine  8 }

nsDemodMonitorLineDataRateCh2  OBJECT-TYPE
        SYNTAX  Integer32 
        MAX-ACCESS  read-only
        STATUS  current
        DESCRIPTION
                "This parameter holds Line Data rate channel 2 status in bit/sec."
        ::= { nsDemodMonitorLine  9 }

nsDemodMonitorLinePrbsDataBytes  OBJECT-TYPE
        SYNTAX  Integer32 
        MAX-ACCESS  read-only
        STATUS  current
        DESCRIPTION
                "This parameter holds PRBS Data Rate."
        ::= { nsDemodMonitorLine  10 }
        
nsDemodMonitorLinePrbsErrorBits  OBJECT-TYPE
        SYNTAX  Integer32 
        MAX-ACCESS  read-only
        STATUS  current
        DESCRIPTION
                "This parameter holds PRBS Error bits."
        ::= { nsDemodMonitorLine  11 }
        
nsDemodMonitorLinePrbsErrorBitsRate  OBJECT-TYPE
        SYNTAX  DisplayString (SIZE(0..255))
        MAX-ACCESS  read-only
        STATUS  current
        DESCRIPTION
                "This parameter holds PRBS Error bits rate."
        ::= { nsDemodMonitorLine  12 }        

nsDemodMonitorLineFERFrames  OBJECT-TYPE
        SYNTAX  Integer32 
        MAX-ACCESS  read-only
        STATUS  current
        DESCRIPTION
                "This parameter holds FER frames."
        ::= { nsDemodMonitorLine  13 }

nsDemodMonitorLineFERErrorFrames  OBJECT-TYPE
        SYNTAX  Integer32 
        MAX-ACCESS  read-only
        STATUS  current
        DESCRIPTION
                "This parameter holds FER error frames."
        ::= { nsDemodMonitorLine  14 }

nsDemodMonitorLineFERErrorFramesRate  OBJECT-TYPE
        SYNTAX  DisplayString (SIZE(0..255))
        MAX-ACCESS  read-only
        STATUS  current
        DESCRIPTION
                "This parameter holds FER error frames rate."
        ::= { nsDemodMonitorLine  15 }


nsDemodMonitorModeCodeTable OBJECT-TYPE
        SYNTAX SEQUENCE OF DemodModeCodeEntry
        MAX-ACCESS not-accessible
        STATUS current
        DESCRIPTION
            "A list of Mode code status fields"
        ::= { nsDemodMonitorLine 16 } 

nsDemodMonitorModeCodeEntry OBJECT-TYPE
        SYNTAX      DemodModeCodeEntry
        MAX-ACCESS  not-accessible
        STATUS      current
        DESCRIPTION "Conceptual row in table for each mode code option."
        INDEX   { nsDemodMonitorModeCodeModulation,  nsDemodMonitorModeCodeFEC, nsDemodMonitorModeCodePilot , nsDemodMonitorModeCodeFrameSize}
        ::= { nsDemodMonitorModeCodeTable 1 }
        
DemodModeCodeEntry ::=
    SEQUENCE {
        nsDemodMonitorModeCodeModulation    INTEGER,
        nsDemodMonitorModeCodeFEC           INTEGER,
        nsDemodMonitorModeCodePilot         INTEGER,
        nsDemodMonitorModeCodeFrameSize     INTEGER,
        nsDemodMonitorModeCodeFrames        INTEGER,
        nsDemodMonitorModeCodeFramesErr     INTEGER,
        nsDemodMonitorModeCodeFramesErrRate    DisplayString,
        nsDemodMonitorModeCodeFramesLinkMargin DisplayString,
        nsDemodMonitorModeCodeFramesSnr        DisplayString,
        nsDemodMonitorModeCodeFramesDesignatedToUnit DisplayString
    } 
    
nsDemodMonitorModeCodeModulation  OBJECT-TYPE
        SYNTAX  INTEGER {
            modulationBpsk   (0),
            modulationQpsk   (1),
            modulation8Psk   (2),
            modulation16Qam  (3),
            modulation16Apsk (4),
            modulation32Apsk (5),
            modulation64Apsk (6),
            notApplicable (255)
        }
        MAX-ACCESS  not-accessible 
        STATUS  current
        DESCRIPTION
                "This parameter holds mode code modulation."
        ::= { nsDemodMonitorModeCodeEntry  1 }

nsDemodMonitorModeCodeFEC  OBJECT-TYPE
        SYNTAX  INTEGER {
            fec1Div5      (0),
            fec1Div4      (1),
            fec1Div4Short (2),
            fec1Div3      (3),
            fec2Div5      (4),
            fec13Div30    (5),
            fec4Div9      (6),
            fec7Div15     (7),
            fec22Div45    (8),
            fec1Div2      (9),
            fec1Div2Short (10),
            fec8Div15     (11),
            fec5Div9      (12),
            fec17Div30    (13),
            fec3Div5      (14),
            fec28Div45    (15),
            fec19Div30    (16),
            fec2Div3      (17),
            fec32Div45    (18),
            fec11Div15    (19),
            fec3Div4      (20),
            fec3Div4Short (21),
            fec7Div9      (22),
            fec4Div5      (23),
            fec4Div5Short (24),
            fec37Div45    (25),
            fec5Div6      (26),
            fec5Div6Short (27),
            fec7Div8      (28),
            fec8Div9      (29),
            fec9Div10     (30),
            notApplicable (255)
        }
        MAX-ACCESS  not-accessible 
        STATUS  current
        DESCRIPTION
                "This parameter holds channel FEC rate.
                    fec1Div5      = 1/5  
                    fec1Div4      = 1/4  
                    fec1Div4Short = 1/4 DVBS2 SHORT FRAME  
                    fec1Div3      = 1/3  
                    fec2Div5      = 2/5  
                    fec13Div30    = 13/30
                    fec4Div9      = 4/9  
                    fec7Div15     = 7/15 
                    fec22Div45    = 22/45
                    fec1Div2      = 1/2  
                    fec1Div2Short = 1/2 DVBS2 SHORT FRAME 
                    fec8Div15     = 8/15 
                    fec5Div9      = 5/9  
                    fec17Div30    = 17/30
                    fec3Div5      = 3/5  
                    fec28Div45    = 28/45
                    fec19Div30    = 19/30
                    fec2Div3      = 2/3  
                    fec32Div45    = 32/45
                    fec11Div15    = 11/15
                    fec3Div4      = 3/4  
                    fec3Div4Short = 3/4 DVBS2 SHORT FRAME  
                    fec7Div9      = 7/9  
                    fec4Div5      = 4/5  
                    fec4Div5Short = 4/5 DVBS2 SHORT FRAME 
                    fec37Div45    = 37/45
                    fec5Div6      = 5/6  
                    fec5Div6Short = 5/6 DVBS2 SHORT FRAME 
                    fec7Div8      = 7/8  
                    fec8Div9      = 8/9  
                    fec9Div10     = 9/10 
                "
        ::= { nsDemodMonitorModeCodeEntry  2 }

nsDemodMonitorModeCodePilot  OBJECT-TYPE
        SYNTAX  INTEGER {
          pilotNo       (0),
          pilot16Slots  (1),
          pilot8Slots   (2),
            notApplicable (255)
        }
        MAX-ACCESS  not-accessible 
        STATUS  current
        DESCRIPTION
                "This parameter holds mode code pilot."
        ::= { nsDemodMonitorModeCodeEntry  3 }
        
nsDemodMonitorModeCodeFrameSize  OBJECT-TYPE
        SYNTAX  INTEGER {
            normal (0),
            short (1),
            notApplicable (255)
        }
        MAX-ACCESS  not-accessible 
        STATUS  current
        DESCRIPTION
                "This parameter holds mode code pilot."
        ::= { nsDemodMonitorModeCodeEntry  4 }

nsDemodMonitorModeCodeFrames  OBJECT-TYPE
        SYNTAX  Integer32 
        MAX-ACCESS  read-only
        STATUS  current
        DESCRIPTION
                "This parameter holds mode code pilot."
        ::= { nsDemodMonitorModeCodeEntry  5 }
        
nsDemodMonitorModeCodeFramesErr  OBJECT-TYPE
        SYNTAX  Integer32 
        MAX-ACCESS  read-only
        STATUS  current
        DESCRIPTION
                "This parameter holds mode code pilot."
        ::= { nsDemodMonitorModeCodeEntry  6 }

nsDemodMonitorModeCodeFramesErrRate  OBJECT-TYPE
        SYNTAX  DisplayString (SIZE(0..255))
        MAX-ACCESS  read-only
        STATUS  current
        DESCRIPTION
                "This parameter holds mode code FER."
        ::= { nsDemodMonitorModeCodeEntry  7 }

nsDemodMonitorModeCodeFramesLinkMargin  OBJECT-TYPE
        SYNTAX  DisplayString (SIZE(0..255))
        MAX-ACCESS  read-only
        STATUS  current
        DESCRIPTION
                "This parameter holds mode code Link Margin."
        ::= { nsDemodMonitorModeCodeEntry  8 }
        
nsDemodMonitorModeCodeFramesSnr  OBJECT-TYPE
		SYNTAX  DisplayString (SIZE(0..255))
        MAX-ACCESS  read-only
        STATUS  current
        DESCRIPTION
                "This parameter holds mode code Snr."
        ::= { nsDemodMonitorModeCodeEntry  9 }

nsDemodMonitorModeCodeFramesDesignatedToUnit  OBJECT-TYPE
		SYNTAX  DisplayString (SIZE(0..255))
        MAX-ACCESS  read-only
        STATUS  current
        DESCRIPTION
                 "This parameter holds the information whether the mode code was sent to this remote or not"
        ::= { nsDemodMonitorModeCodeEntry  10 }

nsDemodMonitorLineLinkMargin  OBJECT-TYPE
        SYNTAX  Integer32 
        MAX-ACCESS  read-only
        STATUS  current
        DESCRIPTION
                "This parameter holds Line Link Margin in hundreds of dB."
        ::= { nsDemodMonitorLine  17 }       

nsDemodMonitorLineSymbolRateOffset  OBJECT-TYPE
        SYNTAX  Integer32 
        MAX-ACCESS  read-only
        STATUS  current
        DESCRIPTION
                "This parameter holds Line Symbol-rate offset status in thousands of PPM." 
        ::= { nsDemodMonitorLine  18 }
        
nsDemodMonitorLineFrequencyOffset  OBJECT-TYPE
        SYNTAX  Integer32 
        MAX-ACCESS  read-only
        STATUS  current
        DESCRIPTION
                "This parameter holds Line frequency offset status in Hz."
        ::= { nsDemodMonitorLine  19 }

nsDemodMonitorLinePrbsSource  OBJECT-TYPE
        SYNTAX  INTEGER {
            disable (0),
            channel1 (1),
            channel2 (2),
            notApplicable (255)
        }
        MAX-ACCESS  read-only
        STATUS  current
        DESCRIPTION
                "This parameter holds PRBS source."
        ::= { nsDemodMonitorLine  20 }       

nsDemodMonitorLineChannelTable OBJECT-TYPE
        SYNTAX SEQUENCE OF DemodLineStatusChannelEntry
        MAX-ACCESS not-accessible
        STATUS current
        DESCRIPTION
            "A list of Channel specific status fields"
        ::= { nsDemodMonitorLine 21 } 

nsDemodMonitorChannelEntry OBJECT-TYPE
        SYNTAX      DemodLineStatusChannelEntry
        MAX-ACCESS  not-accessible
        STATUS      current
        DESCRIPTION "Conceptual row in table for each channel option."
        INDEX   { ifIndex}
        ::= { nsDemodMonitorLineChannelTable 1 }
        
DemodLineStatusChannelEntry ::=
    SEQUENCE {
        nsDemodMonitorLineChannelDataRate      INTEGER,
        nsDemodMonitorLineChannelLinkMargin    INTEGER,
        nsDemodMonitorLineChannelLockStatus    INTEGER,
        nsDemodMonitorLineChannelSNR           INTEGER,
        nsDemodMonitorLineChannelModulation    INTEGER,
        nsDemodMonitorLineChannelFEC           INTEGER,
        nsDemodMonitorLineChannelPilot         INTEGER,
        nsDemodMonitorLineChannelFrameSize     INTEGER,
        nsDemodMonitorLineChannelFrames        INTEGER,
        nsDemodMonitorLineChannelFramesErr     INTEGER,
        nsDemodMonitorLineChannelFramesErrRate DisplayString
    } 
    
nsDemodMonitorLineChannelDataRate  OBJECT-TYPE
        SYNTAX  Integer32 
        MAX-ACCESS  read-only
        STATUS  current
        DESCRIPTION
                "This parameter holds Channel Data rate status in bit/sec."
        ::= { nsDemodMonitorChannelEntry  1 }

nsDemodMonitorLineChannelLinkMargin  OBJECT-TYPE
        SYNTAX  Integer32 
        MAX-ACCESS  read-only
        STATUS  current
        DESCRIPTION
                "This parameter holds Line Link Margin in hundreds of dB."
        ::= { nsDemodMonitorChannelEntry  2 }       

nsDemodMonitorLineChannelLockStatus  OBJECT-TYPE
        SYNTAX  INTEGER {
            unlocked (0),
            locked (1),
            notApplicable (255)
        }
        MAX-ACCESS  read-only
        STATUS  current
        DESCRIPTION
                "This parameter holds Channel lock status."
        ::= { nsDemodMonitorChannelEntry  3 }

nsDemodMonitorLineChannelSNR  OBJECT-TYPE
        SYNTAX  Integer32 
        MAX-ACCESS  read-only
        STATUS  current
        DESCRIPTION
                "This parameter holds Line Data SNR status in hundreds of dB."
        ::= { nsDemodMonitorChannelEntry  4 }

nsDemodMonitorLineChannelModulation  OBJECT-TYPE
        SYNTAX  INTEGER {
            modulationBpsk   (0),
            modulationQpsk   (1),
            modulation8Psk   (2),
            modulation16Qam  (3),
            modulation16Apsk (4),
            modulation32Apsk (5),
            modulation64Apsk (6),
            notApplicable (255)
        }
        MAX-ACCESS  read-only 
        STATUS  current
        DESCRIPTION
                "This parameter holds mode code modulation."
        ::= { nsDemodMonitorChannelEntry  5 }

nsDemodMonitorLineChannelFEC  OBJECT-TYPE
        SYNTAX  INTEGER {
            fec1Div5   (0),
            fec1Div4   (1),
            fec1Div3   (2),
            fec2Div5   (3),
            fec13Div30 (4),
            fec4Div9   (5),
            fec7Div15  (6),
            fec22Div45 (7),
            fec1Div2   (8),
            fec8Div15  (9),
            fec5Div9   (10),
            fec17Div30 (11),
            fec3Div5   (12),
            fec28Div45 (13),
            fec19Div30 (14),
            fec2Div3   (15),
            fec32Div45 (16),
            fec11Div15 (17),
            fec3Div4   (18),
            fec7Div9   (19),
            fec4Div5   (20),
            fec37Div45 (21),
            fec5Div6   (22),
            fec7Div8   (23),
            fec8Div9   (24),
            fec9Div10  (25),
            notApplicable (255)
        }
        MAX-ACCESS  read-only 
        STATUS  current
        DESCRIPTION
                "This parameter holds channel FEC rate.
                    fec1Div5   = 1/5
                    fec1Div4   = 1/4
                    fec1Div3   = 1/3
                    fec2Div5   = 2/5
                    fec13Div30 = 13/30
                    fec4Div9   = 4/9
                    fec7Div15  = 7/15
                    fec22Div45 = 22/45
                    fec1Div2   = 1/2
                    fec8Div15  = 8/15
                    fec5Div9   = 5/9
                    fec17Div30 = 17/30
                    fec3Div5   = 3/5
                    fec28Div45 = 28/45
                    fec19Div30 = 19/30
                    fec2Div3   = 2/3
                    fec32Div45 = 32/45
                    fec11Div15 = 11/15
                    fec3Div4   = 3/4
                    fec7Div9   = 7/9
                    fec4Div5   = 4/5
                    fec37Div45 = 37/45
                    fec5Div6   = 5/6
                    fec7Div8   = 7/8
                    fec8Div9   = 8/9
                    fec9Div10  = 9/10  
                "
        ::= { nsDemodMonitorChannelEntry  6 }

nsDemodMonitorLineChannelPilot  OBJECT-TYPE
        SYNTAX  INTEGER {
          pilotNo       (0),
          pilot16Slots  (1),
          pilot8Slots   (2),
            notApplicable (255)
        }
        MAX-ACCESS  read-only 
        STATUS  current
        DESCRIPTION
                "This parameter holds mode code pilot."
        ::= { nsDemodMonitorChannelEntry  7 }
        
nsDemodMonitorLineChannelFrameSize  OBJECT-TYPE
        SYNTAX  INTEGER {
            normal (0),
            short (1),
            notApplicable (255)
        }
        MAX-ACCESS  read-only 
        STATUS  current
        DESCRIPTION
                "This parameter holds mode code pilot."
        ::= { nsDemodMonitorChannelEntry  8 }

nsDemodMonitorLineChannelFrames  OBJECT-TYPE
        SYNTAX  Integer32 
        MAX-ACCESS  read-only
        STATUS  current
        DESCRIPTION
                "This parameter holds mode code pilot."
        ::= { nsDemodMonitorChannelEntry  9 }
        
nsDemodMonitorLineChannelFramesErr  OBJECT-TYPE
        SYNTAX  Integer32 
        MAX-ACCESS  read-only
        STATUS  current
        DESCRIPTION
                "This parameter holds mode code pilot."
        ::= { nsDemodMonitorChannelEntry  10 }

nsDemodMonitorLineChannelFramesErrRate  OBJECT-TYPE
        SYNTAX  DisplayString (SIZE(0..255))
        MAX-ACCESS  read-only
        STATUS  current
        DESCRIPTION
                "This parameter holds mode code FER."
        ::= { nsDemodMonitorChannelEntry  11 }

nsDemodMonitorLineSignalPower  OBJECT-TYPE
        SYNTAX  Integer32 
        MAX-ACCESS  read-only
        STATUS  current
        DESCRIPTION
                "This parameter holds Line Signal Power status in hundreds of dBm."
        ::= { nsDemodMonitorLine  22 }

nsDemodMonitorLineCntrClrCmd  OBJECT-TYPE
        SYNTAX  INTEGER {
            none (0),
            execute (1),
            notApplicable (255)
        }
        MAX-ACCESS  read-write
        STATUS  current
        DESCRIPTION
                "Clear Line counters command" 
        ::= { nsDemodMonitorLine  23 }

nsDemodMonitorLineEcState  OBJECT-TYPE
        SYNTAX  INTEGER {
            unlock (0),
            lock (1)
        }
        MAX-ACCESS  read-only
        STATUS  current
        DESCRIPTION
                "This parameter holds Echo Cancellation State."
        ::= { nsDemodMonitorLine  24 }

nsDemodMonitorLineEcSatDelay  OBJECT-TYPE
        SYNTAX  Unsigned32 (0..500)
        MAX-ACCESS  read-only
        STATUS  current
        DESCRIPTION
                "This parameter holds Echo Cancellation satellite delay in ms."
        ::= { nsDemodMonitorLine  25 }

nsDemodMonitorLineEcTxFreqOffset  OBJECT-TYPE
        SYNTAX  Integer32 (-36000000..36000000)
        MAX-ACCESS  read-only
        STATUS  current
        DESCRIPTION
                "This parameter holds Echo Cancellation TX frequency offset in Hz."
        ::= { nsDemodMonitorLine  26 }

nsDemodMonitorLineEcGainDiff  OBJECT-TYPE
        SYNTAX  Integer32 
        MAX-ACCESS  read-only
        STATUS  current
        DESCRIPTION
                "This parameter holds Echo Cancellation Gain Difference in hundreds of dBm."
        ::= { nsDemodMonitorLine  27 }

        
-- ===================================================

nsDemodMonitorInterface  OBJECT-IDENTITY
        STATUS current
        DESCRIPTION
              "Demodulator MIB branch that holds all Demodulator interface statuses."
        ::= { nsDemodMonitor 2 }

nsDemodMonitorInterfaceTable OBJECT-TYPE
    SYNTAX SEQUENCE OF DemodMonitorInterfaceEntry
    MAX-ACCESS not-accessible
    STATUS current
    DESCRIPTION
        "A list of interface statuses"
    ::= { nsDemodMonitorInterface 1 } 
    
nsDemodMonitorInterfaceEntry OBJECT-TYPE
    SYNTAX      DemodMonitorInterfaceEntry
    MAX-ACCESS  not-accessible
    STATUS      current
    DESCRIPTION "Conceptual row in table for each interface."
    INDEX   { ifIndex }
    ::= { nsDemodMonitorInterfaceTable 1 }   
        
DemodMonitorInterfaceEntry ::=
    SEQUENCE {
        nsDemodMonitorInterfaceName              DisplayString,
        nsDemodMonitorInterfaceSource            DisplayString,
        nsDemodMonitorInterfaceRate			     DisplayString
    }   

nsDemodMonitorInterfaceName  OBJECT-TYPE
        SYNTAX  DisplayString (SIZE(0..255))
        MAX-ACCESS  read-only
        STATUS  current
        DESCRIPTION
                "Name of interface"
        ::= { nsDemodMonitorInterfaceEntry  1 }
            
nsDemodMonitorInterfaceSource  OBJECT-TYPE
        SYNTAX  DisplayString (SIZE(0..255))
        MAX-ACCESS  read-only
        STATUS  current
        DESCRIPTION
                "Source of interface"
        ::= { nsDemodMonitorInterfaceEntry  2 }
        
nsDemodMonitorInterfaceRate  OBJECT-TYPE
        SYNTAX  DisplayString (SIZE(0..255))
        MAX-ACCESS  read-only
        STATUS  current
        DESCRIPTION
                "This parameter holds interface source rate."
        ::= { nsDemodMonitorInterfaceEntry  3 }

-- ===================================================

nsDemodMonitorSystem  OBJECT-IDENTITY
        STATUS current
        DESCRIPTION
              "Demodulator MIB branch that holds all Demodulator system statuses."
        ::= { nsDemodMonitor 3 }

nsDemodMonitorSystemFPGATmp  OBJECT-TYPE
        SYNTAX  Integer32 
        MAX-ACCESS  read-only
        STATUS  current
        DESCRIPTION
                "This parameter holds system FPGA temperature status in hundreds of Celsius degrees."
        ::= { nsDemodMonitorSystem  1 }
        
nsDemodMonitorSystemBoardTmp  OBJECT-TYPE
        SYNTAX  Integer32 
        MAX-ACCESS  read-only
        STATUS  current
        DESCRIPTION
                "This parameter holds system board temperature status in hundreds of Celsius degrees."
        ::= { nsDemodMonitorSystem  2 }

nsDemodMonitorSystem10MHrzClkSource  OBJECT-TYPE
        SYNTAX  INTEGER {
            internal (0),
            external (1)
        }
        MAX-ACCESS  read-only
        STATUS  current
        DESCRIPTION
                "This parameter holds system 10MHrz clock source."
        ::= { nsDemodMonitorSystem  3 }
        
nsDemodMonitorSystemRefClkOut  OBJECT-TYPE
        SYNTAX  INTEGER {
            off (0),
            on (1),
            notApplicable (255)
        }
        MAX-ACCESS  read-only
        STATUS  current
        DESCRIPTION
                "This parameter holds system ref clock out."
        ::= { nsDemodMonitorSystem  4 }

nsDemodMonitorSystemLnbRefClk  OBJECT-TYPE
        SYNTAX  INTEGER {
            off (0),
            on (1),
            notApplicable (255)
        }
        MAX-ACCESS  read-only
        STATUS  current
        DESCRIPTION
                "This parameter holds system LNB ref clock."
        ::= { nsDemodMonitorSystem  5 }        


-- ===================================================

nsDemodMonitorEthernet  OBJECT-IDENTITY
         STATUS current
        DESCRIPTION
              "Common MIB branch that holds all Ethernet statistics."
        ::= { nsDemodMonitor 4 }
 
nsDemodMonitorEthernetTable OBJECT-TYPE
	SYNTAX SEQUENCE OF DemodEthernetStatisticsEntry
	MAX-ACCESS not-accessible
	STATUS current
	DESCRIPTION
		"List of Ethernet Statistics"
	::= { nsDemodMonitorEthernet 1 } 

nsDemodMonitorEthernetEntry OBJECT-TYPE
    SYNTAX      DemodEthernetStatisticsEntry
    MAX-ACCESS  not-accessible
    STATUS      current
    DESCRIPTION "Conceptual row in table for each event."
    INDEX   { nsDemodMonitorEthernetStatisticsNumber }
    ::= { nsDemodMonitorEthernetTable 1 }
        
DemodEthernetStatisticsEntry ::=
	SEQUENCE {
		nsDemodMonitorEthernetStatisticsNumber	Counter32,
		nsDemodMonitorEthernetStatisticsName	DisplayString,
		nsDemodMonitorEthernetStatisticsValueA	Integer32,
		nsDemodMonitorEthernetStatisticsValueB	Integer32
	} 
    
nsDemodMonitorEthernetStatisticsNumber  OBJECT-TYPE
        SYNTAX  Counter32
        MAX-ACCESS  not-accessible
        STATUS  current
        DESCRIPTION
                "Ethernet Statistics Number"
        ::= { nsDemodMonitorEthernetEntry  1 }        
 
nsDemodMonitorEthernetStatisticsName  OBJECT-TYPE
        SYNTAX  DisplayString (SIZE(0..255))
        MAX-ACCESS  read-only
        STATUS  current
        DESCRIPTION
                "Name of Ethernet Statistics"
        ::= { nsDemodMonitorEthernetEntry  2 }  
 
nsDemodMonitorEthernetStatisticsValueA  OBJECT-TYPE
        SYNTAX  Integer32
        MAX-ACCESS  read-only
        STATUS  current
        DESCRIPTION
                "Value of Ethernet Statistics"
        ::= { nsDemodMonitorEthernetEntry  3 }   
        
nsDemodMonitorEthernetStatisticsValueB  OBJECT-TYPE
        SYNTAX  Integer32
        MAX-ACCESS  read-only
        STATUS  current
        DESCRIPTION
                "Value of Ethernet Statistics"
        ::= { nsDemodMonitorEthernetEntry  4 }        
        
-- ===================================================


END

----------------------------------------------
-- NOVELSAT-DEMODULATOR.mib               --
----------------------------------------------
