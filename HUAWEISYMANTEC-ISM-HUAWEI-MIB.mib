--
-- HUAWEISYMANTEC-ISM-HUAWEI-MIB.my
-- MIB generated by MG-SOFT Visual MIB Builder Version 4.0 Build 347
-- Friday, February 17, 2012 at 14:01:17
--

	HUAWEISYMANTEC-ISM-HUAWEI-MIB DEFINITIONS ::= BEGIN
 
		IMPORTS
			enterprises, IpAddress, Integer32, Gauge32, Counter64, 
			OBJECT-TYPE, MODULE-IDENTITY, OBJECT-IDENTITY, NOTIFICATION-TYPE			
				FROM SNMPv2-SMI			
			DateAndTime, DisplayString			
				FROM SNMPv2-TC;
	
	
		-- 1.3.6.1.4.1.2011.2.91
		hwISMCommon MODULE-IDENTITY 
			LAST-UPDATED "200809171628Z"		-- September 17, 2008 at 16:28 GMT
			ORGANIZATION 
				"HUAWEI-Symantec"
			CONTACT-INFO 
				"Contact-info."
			DESCRIPTION 
				"Description."
			::= { products 91 }

		
	
--
-- Type definitions
--
	
--  Type definitions
-- 
-- 
-- 
		NodeCodeString ::= OCTET STRING (SIZE (15..17))

		RowStatus ::= INTEGER
			{
			active(1),
			notInService(2),
			notReady(3),
			createAndGo(4),
			createAndWait(5),
			destroy(6)
			}

	
	
--
-- Node definitions
--
	
--  1.3.6.1.4.1.2011
		-- 1.3.6.1.4.1.2011
		huawei OBJECT IDENTIFIER ::= { enterprises 2011 }

		
--  1.3.6.1.4.1.2011.2
		-- 1.3.6.1.4.1.2011.2
		products OBJECT IDENTIFIER ::= { huawei 2 }

		
		-- 1.3.6.1.4.1.2011.2.91.9
		hwIsmTopo OBJECT IDENTIFIER ::= { hwISMCommon 9 }

		
		-- 1.3.6.1.4.1.2011.2.91.9.1
		hwIsmAccessNodeInfo OBJECT IDENTIFIER ::= { hwIsmTopo 1 }

		
		-- 1.3.6.1.4.1.2011.2.91.9.1.1
		hwIsmAccessNodeTable OBJECT-TYPE
			SYNTAX SEQUENCE OF HwIsmAccessNodeEntry
			MAX-ACCESS not-accessible
			STATUS current
			DESCRIPTION
				"Access Node Information Table
				"
			::= { hwIsmAccessNodeInfo 1 }

		
		-- 1.3.6.1.4.1.2011.2.91.9.1.1.1
		hwIsmAccessNodeEntry OBJECT-TYPE
			SYNTAX HwIsmAccessNodeEntry
			MAX-ACCESS not-accessible
			STATUS current
			DESCRIPTION
				"Entry of Access Node Information Table
				"
			INDEX { hwIsmNENodeCode }
			::= { hwIsmAccessNodeTable 1 }

		
		HwIsmAccessNodeEntry ::=
			SEQUENCE { 
				hwIsmNENodeCode
					NodeCodeString,
				hwIsmNENodeType
					Integer32,
				hwIsmNENodeWorkingMode
					INTEGER,
				hwIsmNENodeIPAddress
					IpAddress,
				hwIsmNENodeContextName
					DisplayString,
				hwIsmNENodeContextEngineID
					DisplayString,
				hwIsmNENodeClusterName
					DisplayString,
				hwIsmNENodeRunningStatus
					INTEGER
			 }

		-- 1.3.6.1.4.1.2011.2.91.9.1.1.1.1
		hwIsmNENodeCode OBJECT-TYPE
			SYNTAX NodeCodeString
			MAX-ACCESS read-only
			STATUS current
			DESCRIPTION
				"NE Node Code
				
				"
			::= { hwIsmAccessNodeEntry 1 }

		
		-- 1.3.6.1.4.1.2011.2.91.9.1.1.1.2
		hwIsmNENodeType OBJECT-TYPE
			SYNTAX Integer32
			MAX-ACCESS read-only
			STATUS current
			DESCRIPTION
				"NE Node Type
				"
			::= { hwIsmAccessNodeEntry 2 }

		
		-- 1.3.6.1.4.1.2011.2.91.9.1.1.1.3
		hwIsmNENodeWorkingMode OBJECT-TYPE
			SYNTAX INTEGER
				{
				mode1(1),
				mode2(2),
				mode3(3),
				mode4(4)
				}
			MAX-ACCESS read-only
			STATUS current
			DESCRIPTION
				"NE Working Mode
				"
			::= { hwIsmAccessNodeEntry 3 }

		
		-- 1.3.6.1.4.1.2011.2.91.9.1.1.1.4
		hwIsmNENodeIPAddress OBJECT-TYPE
			SYNTAX IpAddress
			MAX-ACCESS read-only
			STATUS current
			DESCRIPTION
				"NE Node IP Address
				"
			::= { hwIsmAccessNodeEntry 4 }

		
		-- 1.3.6.1.4.1.2011.2.91.9.1.1.1.5
		hwIsmNENodeContextName OBJECT-TYPE
			SYNTAX DisplayString
			MAX-ACCESS read-only
			STATUS current
			DESCRIPTION
				"NE Node Context Name
				"
			::= { hwIsmAccessNodeEntry 5 }

		
		-- 1.3.6.1.4.1.2011.2.91.9.1.1.1.6
		hwIsmNENodeContextEngineID OBJECT-TYPE
			SYNTAX DisplayString
			MAX-ACCESS read-only
			STATUS current
			DESCRIPTION
				"NE Node Context EngineID
				"
			::= { hwIsmAccessNodeEntry 6 }

		
		-- 1.3.6.1.4.1.2011.2.91.9.1.1.1.7
		hwIsmNENodeClusterName OBJECT-TYPE
			SYNTAX DisplayString
			MAX-ACCESS read-only
			STATUS current
			DESCRIPTION
				"NE Cluster Name
				"
			::= { hwIsmAccessNodeEntry 7 }

		
		-- 1.3.6.1.4.1.2011.2.91.9.1.1.1.8
		hwIsmNENodeRunningStatus OBJECT-TYPE
			SYNTAX INTEGER
				{
				admin(1),
				freedom(2)
				}
			MAX-ACCESS read-only
			STATUS current
			DESCRIPTION
				"NE Running Status
				
				admin(1)
				freedom(2)"
			::= { hwIsmAccessNodeEntry 8 }

		
		-- 1.3.6.1.4.1.2011.2.91.10
		hwIsmNotification OBJECT IDENTIFIER ::= { hwISMCommon 10 }

		
		-- 1.3.6.1.4.1.2011.2.91.10.1
		hwIsmActiveAlarmInfo OBJECT IDENTIFIER ::= { hwIsmNotification 1 }

		
		-- 1.3.6.1.4.1.2011.2.91.10.1.1
		hwIsmActiveAlarmInfoTable OBJECT-TYPE
			SYNTAX SEQUENCE OF HwIsmActiveAlarmInfoEntry
			MAX-ACCESS not-accessible
			STATUS current
			DESCRIPTION
				"ActiveAlarm Information Table
				"
			::= { hwIsmActiveAlarmInfo 1 }

		
		-- 1.3.6.1.4.1.2011.2.91.10.1.1.1
		hwIsmActiveAlarmInfoEntry OBJECT-TYPE
			SYNTAX HwIsmActiveAlarmInfoEntry
			MAX-ACCESS not-accessible
			STATUS current
			DESCRIPTION
				"Entry of Active Alarm Information Table"
			INDEX { hwIsmActiveAlarmInfoNodeCode, hwIsmActiveAlarmInfoSerialNo }
			::= { hwIsmActiveAlarmInfoTable 1 }

		
		HwIsmActiveAlarmInfoEntry ::=
			SEQUENCE { 
				hwIsmActiveAlarmInfoNodeCode
					NodeCodeString,
				hwIsmActiveAlarmInfoLocationInfo
					DisplayString,
				hwIsmActiveAlarmInfoRestoreAdvice
					DisplayString,
				hwIsmActiveAlarmInfoTitle
					DisplayString,
				hwIsmActiveAlarmInfoType
					INTEGER,
				hwIsmActiveAlarmInfoLevel
					INTEGER,
				hwIsmActiveAlarmInfoAlarmID
					Gauge32,
				hwIsmActiveAlarmInfoOccurTime
					DateAndTime,
				hwIsmActiveAlarmInfoSerialNo
					Gauge32,
				hwIsmActiveAlarmInfoAddtionInfo
					OCTET STRING,
				hwIsmActiveAlarmInfoCategory
					INTEGER
			 }

		-- 1.3.6.1.4.1.2011.2.91.10.1.1.1.1
		hwIsmActiveAlarmInfoNodeCode OBJECT-TYPE
			SYNTAX NodeCodeString
			MAX-ACCESS read-only
			STATUS current
			DESCRIPTION
				"Active Alarm NodeCode"
			::= { hwIsmActiveAlarmInfoEntry 1 }

		
		-- 1.3.6.1.4.1.2011.2.91.10.1.1.1.2
		hwIsmActiveAlarmInfoLocationInfo OBJECT-TYPE
			SYNTAX DisplayString
			MAX-ACCESS read-only
			STATUS current
			DESCRIPTION
				"Active Alarm Location Information"
			::= { hwIsmActiveAlarmInfoEntry 2 }

		
		-- 1.3.6.1.4.1.2011.2.91.10.1.1.1.3
		hwIsmActiveAlarmInfoRestoreAdvice OBJECT-TYPE
			SYNTAX DisplayString
			MAX-ACCESS read-only
			STATUS current
			DESCRIPTION
				"Active Alarm Restore Advice"
			::= { hwIsmActiveAlarmInfoEntry 3 }

		
		-- 1.3.6.1.4.1.2011.2.91.10.1.1.1.4
		hwIsmActiveAlarmInfoTitle OBJECT-TYPE
			SYNTAX DisplayString
			MAX-ACCESS read-only
			STATUS current
			DESCRIPTION
				"Active Alarm Title"
			::= { hwIsmActiveAlarmInfoEntry 4 }

		
		-- 1.3.6.1.4.1.2011.2.91.10.1.1.1.5
		hwIsmActiveAlarmInfoType OBJECT-TYPE
			SYNTAX INTEGER
				{
				communicationQuality(1),
				equipmentFault(2),
				processError(3),
				serviceQuality(4),
				environmentFault(5),
				performanceLimit(6)
				}
			MAX-ACCESS read-only
			STATUS current
			DESCRIPTION
				"Active Alarm Type
				
				1-communicationQuality
				2-serviceQuality
				3-processError
				4-equipmentFault
				5-environmentFault
				6-performanceLimit
				"
			::= { hwIsmActiveAlarmInfoEntry 5 }

		
--  1.3.6.1.4.1.2011.2.40.100.9.2.2.1.1.6
		-- 1.3.6.1.4.1.2011.2.91.10.1.1.1.6
		hwIsmActiveAlarmInfoLevel OBJECT-TYPE
			SYNTAX INTEGER
				{
				criticalAlarm(1),
				majorAlarm(2),
				minorAlarm(3),
				warningAlarm(4)
				}
			MAX-ACCESS read-only
			STATUS current
			DESCRIPTION
				"Active Alarm Level
				
				1-criticalAlarm
				2-majorAlarm
				3-minorAlarm
				4-warningAlarm
				
				"
			::= { hwIsmActiveAlarmInfoEntry 6 }

		
		-- 1.3.6.1.4.1.2011.2.91.10.1.1.1.7
		hwIsmActiveAlarmInfoAlarmID OBJECT-TYPE
			SYNTAX Gauge32
			MAX-ACCESS read-only
			STATUS current
			DESCRIPTION
				"Active Alarm ID"
			::= { hwIsmActiveAlarmInfoEntry 7 }

		
		-- 1.3.6.1.4.1.2011.2.91.10.1.1.1.8
		hwIsmActiveAlarmInfoOccurTime OBJECT-TYPE
			SYNTAX DateAndTime
			MAX-ACCESS read-only
			STATUS current
			DESCRIPTION
				"Occurrence Time of Alarm"
			::= { hwIsmActiveAlarmInfoEntry 8 }

		
		-- 1.3.6.1.4.1.2011.2.91.10.1.1.1.9
		hwIsmActiveAlarmInfoSerialNo OBJECT-TYPE
			SYNTAX Gauge32
			MAX-ACCESS read-only
			STATUS current
			DESCRIPTION
				"Active Alarm Serial No"
			::= { hwIsmActiveAlarmInfoEntry 9 }

		
		-- 1.3.6.1.4.1.2011.2.91.10.1.1.1.10
		hwIsmActiveAlarmInfoAddtionInfo OBJECT-TYPE
			SYNTAX OCTET STRING
			MAX-ACCESS read-only
			STATUS current
			DESCRIPTION
				"Active Alarm Addtion Information"
			::= { hwIsmActiveAlarmInfoEntry 10 }

		
		-- 1.3.6.1.4.1.2011.2.91.10.1.1.1.11
		hwIsmActiveAlarmInfoCategory OBJECT-TYPE
			SYNTAX INTEGER
				{
				faultAlarm(1),
				resumeAlarm(2),
				eventAlarm(3)
				}
			MAX-ACCESS read-only
			STATUS current
			DESCRIPTION
				"Active Alarm Category
				
				1 faultAlarm
				2 resumeAlarm
				3 eventAlarm"
			::= { hwIsmActiveAlarmInfoEntry 11 }

		
		-- 1.3.6.1.4.1.2011.2.91.10.1.2
		hwIsmClearedAlarmConfirm OBJECT-TYPE
			SYNTAX Gauge32
			MAX-ACCESS read-write
			STATUS current
			DESCRIPTION
				"Confirm active alarm's status
				
				Set: to clear alarm
				"
			::= { hwIsmActiveAlarmInfo 2 }

		
		-- 1.3.6.1.4.1.2011.2.91.10.2
		hwIsmNotificationType OBJECT IDENTIFIER ::= { hwIsmNotification 2 }

		
		-- 1.3.6.1.4.1.2011.2.91.10.2.1
		hwinfoFaultNotificationType OBJECT IDENTIFIER ::= { hwIsmNotificationType 1 }

		
		-- 1.3.6.1.4.1.2011.2.91.10.2.1.0
		hwIsmFaultNotificationTypeV2 OBJECT-IDENTITY
			STATUS current
			DESCRIPTION 
				"Root node for the converted TRAP-TYPEs."
			::= { hwinfoFaultNotificationType 0 }

		
		-- 1.3.6.1.4.1.2011.2.91.10.2.1.0.1
		hwIsmAlarmReporting NOTIFICATION-TYPE
			OBJECTS { hwIsmReportingAlarmNodeCode, hwIsmReportingAlarmLocationInfo, hwIsmReportingAlarmRestoreAdvice, hwIsmReportingAlarmFaultTitle, hwIsmReportingAlarmFaultType, 
				hwIsmReportingAlarmFaultLevel, hwIsmReportingAlarmAlarmID, hwIsmReportingAlarmFaultTime, hwIsmReportingAlarmSerialNo, hwIsmReportingAlarmLocationAlarmID, 
				hwIsmReportingAlarmFaultCategory, hwIsmReportingAlarmAdditionInfo }
			STATUS current
			DESCRIPTION 
				"Alarm Reporting"
			::= { hwIsmFaultNotificationTypeV2 1 }

		
		-- 1.3.6.1.4.1.2011.2.91.10.2.2
		hwIsmEventNotificationType OBJECT IDENTIFIER ::= { hwIsmNotificationType 2 }

		
		-- 1.3.6.1.4.1.2011.2.91.10.2.2.0
		hwIsmEventNotificationTypeV2 OBJECT-IDENTITY
			STATUS current
			DESCRIPTION 
				"Root node for the converted TRAP-TYPEs."
			::= { hwIsmEventNotificationType 0 }

		
		-- 1.3.6.1.4.1.2011.2.91.10.2.2.0.1
		hwIsmEvent NOTIFICATION-TYPE
			OBJECTS { hwIsmEventNotiNodeCode, hwIsmEventNotiLocationInfo, hwIsmEventNotiFaultTitle, hwIsmEventNotiFaultType, hwIsmEventNotiFaultTime, 
				hwIsmEventNotiSerialNo, hwIsmEventNotiAlarmID, hwIsmEventNotiAddition }
			STATUS current
			DESCRIPTION 
				"Refresh Top Reporting
				traptype = 7"
			::= { hwIsmEventNotificationTypeV2 1 }

		
		-- 1.3.6.1.4.1.2011.2.91.10.3
		hwIsmTrapNotification OBJECT IDENTIFIER ::= { hwIsmNotification 3 }

		
		-- 1.3.6.1.4.1.2011.2.91.10.3.1
		hwIsmFaultNotification OBJECT IDENTIFIER ::= { hwIsmTrapNotification 1 }

		
		-- 1.3.6.1.4.1.2011.2.91.10.3.1.1
		hwIsmReportingAlarm OBJECT IDENTIFIER ::= { hwIsmFaultNotification 1 }

		
		-- 1.3.6.1.4.1.2011.2.91.10.3.1.1.1
		hwIsmReportingAlarmNodeCode OBJECT-TYPE
			SYNTAX NodeCodeString
			MAX-ACCESS accessible-for-notify
			STATUS current
			DESCRIPTION
				"Alarm Node Code"
			REFERENCE
				"Location info of  Fault Alarm"
			::= { hwIsmReportingAlarm 1 }

		
		-- 1.3.6.1.4.1.2011.2.91.10.3.1.1.2
		hwIsmReportingAlarmLocationInfo OBJECT-TYPE
			SYNTAX DisplayString
			MAX-ACCESS accessible-for-notify
			STATUS current
			DESCRIPTION
				"Reporting Alarm Location Information"
			::= { hwIsmReportingAlarm 2 }

		
		-- 1.3.6.1.4.1.2011.2.91.10.3.1.1.3
		hwIsmReportingAlarmRestoreAdvice OBJECT-TYPE
			SYNTAX OCTET STRING (SIZE (0..256))
			MAX-ACCESS accessible-for-notify
			STATUS current
			DESCRIPTION
				"Advice of Restore Reporting Alarm"
			::= { hwIsmReportingAlarm 3 }

		
		-- 1.3.6.1.4.1.2011.2.91.10.3.1.1.4
		hwIsmReportingAlarmFaultTitle OBJECT-TYPE
			SYNTAX OCTET STRING (SIZE (0..256))
			MAX-ACCESS accessible-for-notify
			STATUS current
			DESCRIPTION
				"Fault Alarm Title"
			::= { hwIsmReportingAlarm 4 }

		
		-- 1.3.6.1.4.1.2011.2.91.10.3.1.1.5
		hwIsmReportingAlarmFaultType OBJECT-TYPE
			SYNTAX INTEGER
				{
				communicationQuality(1),
				equipmentFault(2),
				processError(3),
				serviceQuality(4),
				environmentFault(5),
				performanceLimit(6)
				}
			MAX-ACCESS accessible-for-notify
			STATUS current
			DESCRIPTION
				"Fault Alarm  Type
				
				communicationQuality(1)
				equipmentFault(2)
				processError(3)
				serviceQuality(4)
				environmentFault(5)
				performanceLimit(6)
				"
			::= { hwIsmReportingAlarm 5 }

		
		-- 1.3.6.1.4.1.2011.2.91.10.3.1.1.6
		hwIsmReportingAlarmFaultLevel OBJECT-TYPE
			SYNTAX INTEGER
				{
				criticalAlarm(1),
				majorAlarm(2),
				minorAlarm(3),
				warningAlarm(4)
				}
			MAX-ACCESS accessible-for-notify
			STATUS current
			DESCRIPTION
				"Level of Fault Alarm
				
				CriticalAlarm(1)
				MajorAlarm(2)
				MinorAlarm(3)
				WarningAlarm(4)
				"
			::= { hwIsmReportingAlarm 6 }

		
		-- 1.3.6.1.4.1.2011.2.91.10.3.1.1.7
		hwIsmReportingAlarmAlarmID OBJECT-TYPE
			SYNTAX Gauge32
			MAX-ACCESS accessible-for-notify
			STATUS current
			DESCRIPTION
				"Fault Alarm ID"
			::= { hwIsmReportingAlarm 7 }

		
		-- 1.3.6.1.4.1.2011.2.91.10.3.1.1.8
		hwIsmReportingAlarmFaultTime OBJECT-TYPE
			SYNTAX DateAndTime
			MAX-ACCESS accessible-for-notify
			STATUS current
			DESCRIPTION
				"Occurrence Time of Fault Alarm"
			::= { hwIsmReportingAlarm 8 }

		
		-- 1.3.6.1.4.1.2011.2.91.10.3.1.1.9
		hwIsmReportingAlarmSerialNo OBJECT-TYPE
			SYNTAX Gauge32
			MAX-ACCESS accessible-for-notify
			STATUS current
			DESCRIPTION
				"Fault Alarm Serial No"
			::= { hwIsmReportingAlarm 9 }

		
		-- 1.3.6.1.4.1.2011.2.91.10.3.1.1.10
		hwIsmReportingAlarmAdditionInfo OBJECT-TYPE
			SYNTAX DisplayString
			MAX-ACCESS accessible-for-notify
			STATUS current
			DESCRIPTION
				"Addition Info of Fault Alarm"
			::= { hwIsmReportingAlarm 10 }

		
		-- 1.3.6.1.4.1.2011.2.91.10.3.1.1.11
		hwIsmReportingAlarmFaultCategory OBJECT-TYPE
			SYNTAX INTEGER
				{
				faultAlarm(1),
				resumeAlarm(2),
				eventAlarm(3)
				}
			MAX-ACCESS accessible-for-notify
			STATUS current
			DESCRIPTION
				"Category of Fault Alarm
				
				faultAlarm (1)
				resumeAlarm(2)
				eventAlarm (3)
				"
			::= { hwIsmReportingAlarm 11 }

		
		-- 1.3.6.1.4.1.2011.2.91.10.3.1.1.12
		hwIsmReportingAlarmLocationAlarmID OBJECT-TYPE
			SYNTAX Counter64
			MAX-ACCESS accessible-for-notify
			STATUS current
			DESCRIPTION
				"Description."
			::= { hwIsmReportingAlarm 12 }

		
		-- 1.3.6.1.4.1.2011.2.91.10.3.2
		hwIsmEventNotification OBJECT IDENTIFIER ::= { hwIsmTrapNotification 2 }

		
		-- 1.3.6.1.4.1.2011.2.91.10.3.2.1
		hwIsmEventNotiNodeCode OBJECT-TYPE
			SYNTAX NodeCodeString
			MAX-ACCESS accessible-for-notify
			STATUS current
			DESCRIPTION
				"Event Notification Code"
			::= { hwIsmEventNotification 1 }

		
		-- 1.3.6.1.4.1.2011.2.91.10.3.2.2
		hwIsmEventNotiLocationInfo OBJECT-TYPE
			SYNTAX DisplayString
			MAX-ACCESS accessible-for-notify
			STATUS current
			DESCRIPTION
				"Event Notification Location Info"
			::= { hwIsmEventNotification 2 }

		
		-- 1.3.6.1.4.1.2011.2.91.10.3.2.3
		hwIsmEventNotiFaultTitle OBJECT-TYPE
			SYNTAX OCTET STRING (SIZE (0..256))
			MAX-ACCESS accessible-for-notify
			STATUS current
			DESCRIPTION
				"Event Notification Title"
			::= { hwIsmEventNotification 3 }

		
		-- 1.3.6.1.4.1.2011.2.91.10.3.2.4
		hwIsmEventNotiFaultType OBJECT-TYPE
			SYNTAX INTEGER
				{
				objectcreation(1),
				objectdeletion(2),
				statechanged(3)
				}
			MAX-ACCESS accessible-for-notify
			STATUS current
			DESCRIPTION
				"Event Notification Type
				
				communicationQuality(1)
				equipmentFault(2)
				processError(3)
				serviceQuality(4)
				environmentFault(5)
				"
			::= { hwIsmEventNotification 4 }

		
		-- 1.3.6.1.4.1.2011.2.91.10.3.2.5
		hwIsmEventNotiAddition OBJECT-TYPE
			SYNTAX DisplayString
			MAX-ACCESS accessible-for-notify
			STATUS current
			DESCRIPTION
				"Event Notification Addition Information"
			::= { hwIsmEventNotification 5 }

		
		-- 1.3.6.1.4.1.2011.2.91.10.3.2.6
		hwIsmEventNotiAlarmID OBJECT-TYPE
			SYNTAX Gauge32
			MAX-ACCESS accessible-for-notify
			STATUS current
			DESCRIPTION
				"Event Notification Alarm ID
				"
			::= { hwIsmEventNotification 6 }

		
		-- 1.3.6.1.4.1.2011.2.91.10.3.2.7
		hwIsmEventNotiFaultTime OBJECT-TYPE
			SYNTAX DateAndTime
			MAX-ACCESS accessible-for-notify
			STATUS current
			DESCRIPTION
				"Occurence Time of Event Notification
				"
			::= { hwIsmEventNotification 7 }

		
		-- 1.3.6.1.4.1.2011.2.91.10.3.2.8
		hwIsmEventNotiSerialNo OBJECT-TYPE
			SYNTAX Gauge32
			MAX-ACCESS accessible-for-notify
			STATUS current
			DESCRIPTION
				"Serial No. of Event Notification
				"
			::= { hwIsmEventNotification 8 }

		
		-- 1.3.6.1.4.1.2011.2.91.10.4
		hwIsmTrapForwardControl OBJECT IDENTIFIER ::= { hwIsmNotification 4 }

		
		-- 1.3.6.1.4.1.2011.2.91.10.4.1
		hwIsmTrapTargetAddrTable OBJECT-TYPE
			SYNTAX SEQUENCE OF HwIsmTrapTargetAddrEntry
			MAX-ACCESS not-accessible
			STATUS current
			DESCRIPTION
				"Description."
			::= { hwIsmTrapForwardControl 1 }

		
		-- 1.3.6.1.4.1.2011.2.91.10.4.1.1
		hwIsmTrapTargetAddrEntry OBJECT-TYPE
			SYNTAX HwIsmTrapTargetAddrEntry
			MAX-ACCESS not-accessible
			STATUS current
			DESCRIPTION
				"Description."
			INDEX { hwIsmTrapTargetAddrIPAddr }
			::= { hwIsmTrapTargetAddrTable 1 }

		
		HwIsmTrapTargetAddrEntry ::=
			SEQUENCE { 
				hwIsmTrapTargetAddrIPAddr
					IpAddress,
				hwIsmTrapTargetAddrPort
					INTEGER,
				hwIsmTrapTargetAddrRowStatus
					RowStatus
			 }

		-- 1.3.6.1.4.1.2011.2.91.10.4.1.1.1
		hwIsmTrapTargetAddrIPAddr OBJECT-TYPE
			SYNTAX IpAddress
			MAX-ACCESS read-create
			STATUS current
			DESCRIPTION
				"IP Address of Trap Target
				"
			::= { hwIsmTrapTargetAddrEntry 1 }

		
		-- 1.3.6.1.4.1.2011.2.91.10.4.1.1.2
		hwIsmTrapTargetAddrPort OBJECT-TYPE
			SYNTAX INTEGER
			MAX-ACCESS read-create
			STATUS current
			DESCRIPTION
				"Port of Trap Target"
			::= { hwIsmTrapTargetAddrEntry 2 }

		
		-- 1.3.6.1.4.1.2011.2.91.10.4.1.1.3
		hwIsmTrapTargetAddrRowStatus OBJECT-TYPE
			SYNTAX RowStatus
			MAX-ACCESS read-create
			STATUS current
			DESCRIPTION
				"RowStatus
				"
			::= { hwIsmTrapTargetAddrEntry 3 }

		
	
	END

--
-- HUAWEISYMANTEC-ISM-HUAWEI-MIB.my
--
