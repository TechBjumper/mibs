--  ********************************************************
--  $Id: ZXR10-L2PT-MIB.mib 2010-03-01 01:34:21Z $
--
--  ZXR10-L2PT-MIB.mib: ZXR10 L2PT MIB file
--
--  Copyright(c) 2010 by ZTE Corporation
--  All rights reserved
--
--  ********************************************************

ZXR10-L2PT-MIB DEFINITIONS ::= BEGIN

IMPORTS
    MODULE-IDENTITY,
    OBJECT-TYPE,
    Integer32
        FROM SNMPv2-SMI

    TEXTUAL-CONVENTION
        FROM SNMPv2-TC

    zxr10,
    zxr10RosngMIB
        FROM ZXR10-SMI
    ;
   

    zxrosngL2PTModules MODULE-IDENTITY

        LAST-UPDATED "201708010000Z"  -- 12/18/2012 00:00GMT

        ORGANIZATION "ZTE Corporation"

        CONTACT-INFO
            "ZTE Corporation

             Nanjing Institute of ZTE Corporation

             No.68 ZiJinghua Rd. YuHuatai District, Nanjing, China

             Tel: +86-25-52870000"

        DESCRIPTION
            "ZXROSNG 11R1 L2PT MIB create"

        REVISION "201708010000Z" -- 01/08/2017 00:00GMT
        DESCRIPTION
            "Modify syntax of zxL2ptPortDMacRewriteType:
            add efm(11),pvstPlus(12) value."

        REVISION "201212180000Z" -- 12/18/2012 00:00GMT
        DESCRIPTION
            "ZXROSNG 30R2 L2PT MIB modify access"

        REVISION "201001240000Z" -- 01/24/2010 00:00GMT
        DESCRIPTION
            "ZXROSNG 30R2 L2PT MIB modify access"

        ::= { zxr10RosngMIB 2001 }


    zxL2PTMIBObjects  OBJECT IDENTIFIER ::= { zxrosngL2PTModules  1 }


--TEXTUAL-CONVENTION


    --Char ::=
    --     OCTET STRING
    -- This data type is used to model textual information taken
    -- from the NVT ASCII character set.  By convention, objects
    -- with this syntax are declared as having 0-65535 characters.

    L2ptGlobalRewriteEnable ::= TEXTUAL-CONVENTION
        STATUS          current
        DESCRIPTION     "Whether rewrite mac enabled in Switch"
        SYNTAX          INTEGER
                        {
                            globalDisabled(0),
                            globalEnabled(1)
                        }

    L2ptPortRewriteEnable ::= TEXTUAL-CONVENTION
        STATUS          current
        DESCRIPTION     "Whether rewrite mac enabled on the switch-port"
        SYNTAX          INTEGER
                        {
                            portRewriteDisabled(0),
                            portRewriteEnabled(1)
                        }

    L2ptPortBpduProtectEnable::= TEXTUAL-CONVENTION
        STATUS          current
        DESCRIPTION     "Whether bpdu-protect enabled on the switch-port"
        SYNTAX          INTEGER
                        {
                            bpduProtectDisabled(0),
                            bpduProtectEnabled(1)
                        }

-- groups in zxL2PTMIBObjects

    zxL2ptGlobalConfig    OBJECT IDENTIFIER ::= { zxL2PTMIBObjects  1 }

--zxL2ptGlobalConfig
    zxL2ptGlobalDMacRewriteEnable   OBJECT-TYPE
        SYNTAX          L2ptGlobalRewriteEnable
        MAX-ACCESS      read-only
        STATUS          current
        DESCRIPTION     "Configure Global Write Enable."
        ::=  { zxL2ptGlobalConfig  1 }

    zxL2ptGlobalSubstituteDmacStp   OBJECT-TYPE
        SYNTAX          OCTET STRING
        MAX-ACCESS      read-only
        STATUS          current
        DESCRIPTION     "Configure STP Rewrite MAC."
       ::=  { zxL2ptGlobalConfig  2 }

    zxL2ptGlobalSubstituteDmacDot1x   OBJECT-TYPE
        SYNTAX          OCTET STRING
        MAX-ACCESS      read-only
        STATUS          current
        DESCRIPTION     "Configure Dot1x Rewrite MAC."
        ::=  { zxL2ptGlobalConfig  3 }

    zxL2ptGlobalSubstituteDmacDot3x   OBJECT-TYPE
        SYNTAX          OCTET STRING
        MAX-ACCESS      read-only
        STATUS          current
        DESCRIPTION     "Configure Dot3x Rewrite MAC."
        ::=  { zxL2ptGlobalConfig  4 }

    zxL2ptGlobalSubstituteDmacGvrp   OBJECT-TYPE
        SYNTAX          OCTET STRING
        MAX-ACCESS      read-only
        STATUS          current
        DESCRIPTION     "Configure GVRP Rewrite MAC."
        ::=  { zxL2ptGlobalConfig  5 }

    zxL2ptGlobalSubstituteDmacLacp   OBJECT-TYPE
        SYNTAX          OCTET STRING
        MAX-ACCESS      read-only
        STATUS          current
        DESCRIPTION     "Configure LACP Rewrite MAC."
        ::=  { zxL2ptGlobalConfig  6 }

    zxL2ptGlobalSubstituteDmacLldp   OBJECT-TYPE
        SYNTAX          OCTET STRING
        MAX-ACCESS      read-only
        STATUS          current
        DESCRIPTION     "Configure LLDP Rewrite MAC."
        ::=  { zxL2ptGlobalConfig  7 }

    zxL2ptGlobalSubstituteDmacZdpZtp   OBJECT-TYPE
        SYNTAX          OCTET STRING
        MAX-ACCESS      read-only
        STATUS          current
        DESCRIPTION     "Configure ZDP/ZTP Rewrite MAC."
        ::=  { zxL2ptGlobalConfig  8 }

    zxL2ptGlobalSubstituteDmacVtp   OBJECT-TYPE
        SYNTAX          OCTET STRING
        MAX-ACCESS      read-only
        STATUS          current
        DESCRIPTION     "Configure VTP Rewrite MAC."
        ::=  { zxL2ptGlobalConfig  9 }

    zxL2ptGlobalSubstituteDmacCdp   OBJECT-TYPE
        SYNTAX          OCTET STRING
        MAX-ACCESS      read-only
        STATUS          current
        DESCRIPTION     "Configure CDP Rewrite MAC."
        ::=  { zxL2ptGlobalConfig  10 }

    zxL2ptGlobalSubstituteDmacUdld   OBJECT-TYPE
        SYNTAX          OCTET STRING
        MAX-ACCESS      read-only
        STATUS          current
        DESCRIPTION     "Configure UDLD Rewrite MAC."
        ::=  { zxL2ptGlobalConfig  11 }

---zxL2ptPortTable
    zxL2ptPortTable OBJECT-TYPE
        SYNTAX          SEQUENCE OF ZxL2ptPortEntry
        MAX-ACCESS      not-accessible
        STATUS          current
        DESCRIPTION     "Configure L2PT Port parameters."
        ::=  { zxL2PTMIBObjects  2 }

    zxL2ptPortEntry OBJECT-TYPE
        SYNTAX          ZxL2ptPortEntry
        MAX-ACCESS      not-accessible
        STATUS          current
        DESCRIPTION     "Each row index by zxL2ptPortIndex And contain l2pt imformation of Port."
        INDEX           {  zxL2ptPortIndex  }
        ::=  { zxL2ptPortTable 1 }

    ZxL2ptPortEntry ::=  SEQUENCE
        {
            zxL2ptPortIndex                    Integer32,
            zxL2ptPortName                     OCTET STRING,
            zxL2ptPortDMacRewriteEnable        L2ptPortRewriteEnable,
            zxL2ptPortDMacRewriteType          BITS,
            zxL2ptPortBpduProtectEnable        L2ptPortBpduProtectEnable,
            zxL2ptPortBpduProtectPPS           Integer32
        }

    zxL2ptPortIndex   OBJECT-TYPE
        SYNTAX          Integer32
        MAX-ACCESS      read-only
        STATUS          current
        DESCRIPTION     "Interface Index."
        ::=  { zxL2ptPortEntry  1 }

    zxL2ptPortName   OBJECT-TYPE
        SYNTAX          OCTET STRING
        MAX-ACCESS      read-only
        STATUS          current
        DESCRIPTION     "Interface Name."
        ::=  { zxL2ptPortEntry  2 }

    zxL2ptPortDMacRewriteEnable   OBJECT-TYPE
        SYNTAX          L2ptPortRewriteEnable
        MAX-ACCESS      read-only
        STATUS          current
        DESCRIPTION     "Config Rewrite Enable."
        ::=  { zxL2ptPortEntry  3 }

    zxL2ptPortDMacRewriteType OBJECT-TYPE
        SYNTAX BITS {   none(0),
                        stp(1),
                        dot1x(2),
                        dot3x(3),
                        gvrp(4),
                        lacp(5),
                        lldp(6),
                        zdpZtp(7),
                        vtp(8),
                        cdp(9),
                        udld(10),
                        efm(11),
                        pvstPlus(12)
                    }
        MAX-ACCESS      read-only
        STATUS          current
        DESCRIPTION     "Interface BPDU rewrite type."
        ::= { zxL2ptPortEntry 4 }

    zxL2ptPortBpduProtectEnable   OBJECT-TYPE
        SYNTAX          L2ptPortBpduProtectEnable
        MAX-ACCESS      read-only
        STATUS          current
        DESCRIPTION     "Config BPDU Protect Enable."
        ::=  { zxL2ptPortEntry  5 }

    zxL2ptPortBpduProtectPPS   OBJECT-TYPE
        SYNTAX          Integer32
        MAX-ACCESS      read-only
        STATUS          current
        DESCRIPTION     "Config BPDU Protect Limit."
        ::=  { zxL2ptPortEntry  6 }

END
