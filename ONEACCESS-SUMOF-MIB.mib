--          *****************************
--          *                           *
--          *         ONEOS MIB         *
--          *                           *
--          *****************************
--
--          ONEOS_MIB_STD_V05.1.R005_E001
--
--          Creation date : 06/07/2008
--
     ONEACCESS-SUMOF-MIB DEFINITIONS ::= BEGIN

     IMPORTS
		MODULE-IDENTITY, OBJECT-TYPE,Counter32,Counter64
			FROM SNMPv2-SMI
--		MODULE-COMPLIANCE, OBJECT-GROUP
--			FROM SNMPv2-CONF
		ifIndex
			FROM IF-MIB
		oacExpIMManagement
			FROM ONEACCESS-GLOBAL-REG;

     oacSumOfMIBModule MODULE-IDENTITY
        LAST-UPDATED "201110270000Z"
        ORGANIZATION  " OneAccess "
         CONTACT-INFO
           "Pascal KESTELOOT
            Postal: ONE ACCESS
                    381 Avenue du General de Gaulle
                    92140 Clamart, France
		    FRANCE

            Tel: (+33) 01 41 87 70 00
            Fax: (+33) 01 41 87 74 00

            E-mail: pascal.kesteloot@oneaccess-net.com"

         DESCRIPTION
                    	"Contact updated"
    	REVISION        "201110270000Z"

		DESCRIPTION
			"Fixed Minor correction added last revision."
		REVISION	"201007080001Z"

         DESCRIPTION
              "This MIB module describes ... something."

	::= { oacExpIMManagement 7 }

oacSumOfObjects OBJECT IDENTIFIER ::= { oacSumOfMIBModule 1 }

oacSumOfIfTable OBJECT-TYPE
	SYNTAX SEQUENCE OF OacSumOfIfEntry
		MAX-ACCESS not-accessible
		STATUS current
		DESCRIPTION
			"The table representing the oacSumOfIfTable"
	 ::= { oacSumOfObjects 1 }

oacSumOfIfEntry OBJECT-TYPE
    SYNTAX      OacSumOfIfEntry
    MAX-ACCESS  not-accessible
    STATUS      current
    DESCRIPTION
        "Defines an entry in the oacSumOfIfTable."
    INDEX {ifIndex}
    ::= { oacSumOfIfTable 1 }

 OacSumOfIfEntry ::=
    SEQUENCE {
           sumOfIfInOctets              Counter32,
           sumOfIfInUcastPkts           Counter32,
           sumOfIfInNUcastPkts          Counter32,
           sumOfIfInDiscards            Counter32,
           sumOfIfInErrors              Counter32,
           sumOfIfInUnknownProtos       Counter32,
           sumOfIfOutOctets             Counter32,
           sumOfIfOutUcastPkts          Counter32,
           sumOfIfOutNUcastPkts         Counter32,
           sumOfIfOutDiscards           Counter32,
           sumOfIfOutErrors             Counter32
     }

   sumOfIfInOctets OBJECT-TYPE
       SYNTAX      Counter32
       MAX-ACCESS  read-only
       STATUS      current
       DESCRIPTION
               "The sum of ifInOctets for the subinterfaces of this interface."
       ::= { oacSumOfIfEntry 1 }

   sumOfIfInUcastPkts OBJECT-TYPE
       SYNTAX      Counter32
       MAX-ACCESS  read-only
       STATUS      current
       DESCRIPTION
               "The sum of ifInUcastPkts for the subinterfaces of this interface."
       ::= { oacSumOfIfEntry 2 }


   sumOfIfInNUcastPkts OBJECT-TYPE
       SYNTAX      Counter32
       MAX-ACCESS  read-only
       STATUS      current
       DESCRIPTION
               "The sum of ifInNUcastPkts for the subinterfaces of this interface."
       ::= { oacSumOfIfEntry 3 }

   sumOfIfInDiscards OBJECT-TYPE
       SYNTAX      Counter32
       MAX-ACCESS  read-only
       STATUS      current
       DESCRIPTION
               "The sum of ifInDiscards for the subinterfaces of this interface."
       ::= { oacSumOfIfEntry 4 }

   sumOfIfInErrors OBJECT-TYPE
       SYNTAX      Counter32
       MAX-ACCESS  read-only
       STATUS      current
       DESCRIPTION
               "The sum of ifInErrors for the subinterfaces of this interface."
       ::= { oacSumOfIfEntry 5 }

   sumOfIfInUnknownProtos OBJECT-TYPE
       SYNTAX      Counter32
       MAX-ACCESS  read-only
       STATUS      current
       DESCRIPTION
               "The sum of ifInUnknownProtos for the subinterfaces of this interface."
       ::= { oacSumOfIfEntry 6 }

   sumOfIfOutOctets OBJECT-TYPE
       SYNTAX      Counter32
       MAX-ACCESS  read-only
       STATUS      current
       DESCRIPTION
               "The sum of ifOutOctets for the subinterfaces of this interface."
       ::= { oacSumOfIfEntry 7 }

   sumOfIfOutUcastPkts OBJECT-TYPE
       SYNTAX      Counter32
       MAX-ACCESS  read-only
       STATUS      current
       DESCRIPTION
               "The sum of ifOutUcastPkts for the subinterfaces of this interface."
       ::= { oacSumOfIfEntry 8 }

   sumOfIfOutNUcastPkts OBJECT-TYPE
       SYNTAX      Counter32
       MAX-ACCESS  read-only
       STATUS      current
       DESCRIPTION
               "The sum of ifOutNUcastPkts for the subinterfaces of this interface."
       ::= { oacSumOfIfEntry 9 }

   sumOfIfOutDiscards OBJECT-TYPE
       SYNTAX      Counter32
       MAX-ACCESS  read-only
       STATUS      current
       DESCRIPTION
               "The sum of ifOutDiscards for the subinterfaces of this interface."
       ::= { oacSumOfIfEntry 10 }

   sumOfIfOutErrors OBJECT-TYPE
       SYNTAX      Counter32
       MAX-ACCESS  read-only
       STATUS      current
       DESCRIPTION
               "The sum of ifOutErrors for the subinterfaces of this interface."
       ::= { oacSumOfIfEntry 11 }


oacSumOfIfXTable OBJECT-TYPE
	SYNTAX SEQUENCE OF OacSumOfIfXEntry
		MAX-ACCESS not-accessible
		STATUS current
		DESCRIPTION
			"The table representing the entriese of oacSumOfIfXTable"
	 ::= { oacSumOfObjects 2 }

oacSumOfIfXEntry OBJECT-TYPE
    SYNTAX      OacSumOfIfXEntry
    MAX-ACCESS  not-accessible
    STATUS      current
    DESCRIPTION
        "Defines an entry in the oacSumOfIfXTable."
    INDEX {ifIndex}
    ::= { oacSumOfIfXTable 1 }

 OacSumOfIfXEntry ::=
    SEQUENCE {
    	   sumOfIfInMulticastPkts       Counter32,
           sumOfIfInBroadcastPkts       Counter32,
           sumOfIfOutMulticastPkts      Counter32,
           sumOfIfOutBroadcastPkts      Counter32,
           sumOfIfHCInOctets            Counter64,
           sumOfIfHCInUcastPkts         Counter64,
           sumOfIfHCInMulticastPkts     Counter64,
           sumOfIfHCInBroadcastPkts     Counter64,
           sumOfIfHCOutOctets           Counter64,
           sumOfIfHCOutUcastPkts        Counter64,
           sumOfIfHCOutMulticastPkts    Counter64,
           sumOfIfHCOutBroadcastPkts    Counter64
        }

   sumOfIfInMulticastPkts OBJECT-TYPE
       SYNTAX      Counter32
       MAX-ACCESS  read-only
       STATUS      current
       DESCRIPTION
               "The sum of ifInMulticastPkts for the subinterfaces of this interface."
       ::= { oacSumOfIfXEntry 1 }

   sumOfIfInBroadcastPkts OBJECT-TYPE
       SYNTAX      Counter32
       MAX-ACCESS  read-only
       STATUS      current
       DESCRIPTION
               "The sum ifInBroadcastPkts for the subinterfaces of this interface."
       ::= { oacSumOfIfXEntry 2 }

   sumOfIfOutMulticastPkts OBJECT-TYPE
       SYNTAX      Counter32
       MAX-ACCESS  read-only
       STATUS      current
       DESCRIPTION
               "The sum of ifOutMulticastPkts for the subinterfaces of this interface."
       ::= { oacSumOfIfXEntry 3 }

   sumOfIfOutBroadcastPkts OBJECT-TYPE
       SYNTAX      Counter32
       MAX-ACCESS  read-only
       STATUS      current
       DESCRIPTION
               "The sum of ifOutBroadcastPkts for the subinterfaces of this interface."
       ::= { oacSumOfIfXEntry 4 }

   sumOfIfHCInOctets OBJECT-TYPE
       SYNTAX      Counter64
       MAX-ACCESS  read-only
       STATUS      current
       DESCRIPTION
               "The sum of ifHCInOctets for the subinterfaces of this interface."
       ::= { oacSumOfIfXEntry 5 }

   sumOfIfHCInUcastPkts OBJECT-TYPE
       SYNTAX      Counter64
       MAX-ACCESS  read-only
       STATUS      current
       DESCRIPTION
               "The sum of ifHCInUcastPkts for the subinterfaces of this interface."
       ::= { oacSumOfIfXEntry 6 }

   sumOfIfHCInMulticastPkts OBJECT-TYPE
       SYNTAX      Counter64
       MAX-ACCESS  read-only
       STATUS      current
       DESCRIPTION
               "The sum of ifHCInMulticastPkts for the subinterfaces of this interface."
       ::= { oacSumOfIfXEntry 7 }

   sumOfIfHCInBroadcastPkts OBJECT-TYPE
       SYNTAX      Counter64
       MAX-ACCESS  read-only
       STATUS      current
       DESCRIPTION
               "The sum of ifHCInBroadcastPkts for the subinterfaces of this interface."
       ::= { oacSumOfIfXEntry 8 }

   sumOfIfHCOutOctets OBJECT-TYPE
       SYNTAX      Counter64
       MAX-ACCESS  read-only
       STATUS      current
       DESCRIPTION
               "The sum of ifHCOutOctets for the subinterfaces of this interface."
       ::= { oacSumOfIfXEntry 9 }

   sumOfIfHCOutUcastPkts OBJECT-TYPE
       SYNTAX      Counter64
       MAX-ACCESS  read-only
       STATUS      current
       DESCRIPTION
               "The sum of ifHCOutUcastPkts for the subinterfaces of this interface."
       ::= { oacSumOfIfXEntry 10 }

   sumOfIfHCOutMulticastPkts OBJECT-TYPE
       SYNTAX      Counter64
       MAX-ACCESS  read-only
       STATUS      current
       DESCRIPTION
               "The sum of ifHCOutMulticastPkts for the subinterfaces of this interface."
       ::= { oacSumOfIfXEntry 11 }

   sumOfIfHCOutBroadcastPkts OBJECT-TYPE
       SYNTAX      Counter64
       MAX-ACCESS  read-only
       STATUS      current
       DESCRIPTION
               "The sum of ifHCOutBroadcastPkts for the subinterfaces of this interface."
       ::= { oacSumOfIfXEntry 12 }

END
--
