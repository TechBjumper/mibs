-- file automatically created


TELDAT-TRAP-BR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


brTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BR event subsystem."
    REVISION "201401200930Z"
    DESCRIPTION "Initial implementation"
        ::= { telEventTraps 74 }


brEventsGroup	OBJECT IDENTIFIER	::= { brTrapsMIB 1 }

brNotifications	OBJECT IDENTIFIER	::= { brTrapsMIB 2 }
brNotificationsPrefix	OBJECT IDENTIFIER	::= { brNotifications 0 }

brEventObjects1 OBJECT-IDENTITY
    STATUS current
    DESCRIPTION
        "Event BR.1
        A MAC frame has been received by the hardware, but is being dropped
        because the port it was received on is in the 'blocking' or 'listening'
        state. Frames are only processed when the port is in the 'learning' or
        'forwarding' state."
    ::= { brEventsGroup 1 }

br1-source-mac OBJECT-TYPE
    SYNTAX DisplayString
    MAX-ACCESS accessible-for-notify
    STATUS current
    DESCRIPTION
        "Parameter 'source-mac' in event BR.1"
    ::= { brEventObjects1 1 }

br1-dest-mac OBJECT-TYPE
    SYNTAX DisplayString
    MAX-ACCESS accessible-for-notify
    STATUS current
    DESCRIPTION
        "Parameter 'dest-mac' in event BR.1"
    ::= { brEventObjects1 2 }

br1-interface OBJECT-TYPE
    SYNTAX DisplayString
    MAX-ACCESS accessible-for-notify
    STATUS current
    DESCRIPTION
        "Parameter 'interface' in event BR.1"
    ::= { brEventObjects1 3 }

brEventObjects2 OBJECT-IDENTITY
    STATUS current
    DESCRIPTION
        "Event BR.2
        A MAC frame has been received whose destination address is known to be
        on the same side of the bridge as the packet came from. It is dropped
        by the filtering logic since it does not need to be bridged. Note that
        this event is not counted by ELS for performance reasons. A counter
        is kept in ASRT, it is the 'Dropped, dest addr filtering' entry in
        the ASRT>LIST SOURCE-ROUTE COUNTERS and ASRT>LIST TRANSPARENT COUNTERS
        commands."
    ::= { brEventsGroup 2 }

br2-source-mac OBJECT-TYPE
    SYNTAX DisplayString
    MAX-ACCESS accessible-for-notify
    STATUS current
    DESCRIPTION
        "Parameter 'source-mac' in event BR.2"
    ::= { brEventObjects2 1 }

br2-dest-mac OBJECT-TYPE
    SYNTAX DisplayString
    MAX-ACCESS accessible-for-notify
    STATUS current
    DESCRIPTION
        "Parameter 'dest-mac' in event BR.2"
    ::= { brEventObjects2 2 }

br2-interface OBJECT-TYPE
    SYNTAX DisplayString
    MAX-ACCESS accessible-for-notify
    STATUS current
    DESCRIPTION
        "Parameter 'interface' in event BR.2"
    ::= { brEventObjects2 3 }

brEventObjects3 OBJECT-IDENTITY
    STATUS current
    DESCRIPTION
        "Event BR.3
        A frame has been received over a WAN interface in the Ethernet bridge
        encapsulation, but the IPX protocol (in 802.3 encapsulation) is routed
        by this node."
    ::= { brEventsGroup 3 }

br3-source-mac OBJECT-TYPE
    SYNTAX DisplayString
    MAX-ACCESS accessible-for-notify
    STATUS current
    DESCRIPTION
        "Parameter 'source-mac' in event BR.3"
    ::= { brEventObjects3 1 }

br3-dest-mac OBJECT-TYPE
    SYNTAX DisplayString
    MAX-ACCESS accessible-for-notify
    STATUS current
    DESCRIPTION
        "Parameter 'dest-mac' in event BR.3"
    ::= { brEventObjects3 2 }

br3-interface OBJECT-TYPE
    SYNTAX DisplayString
    MAX-ACCESS accessible-for-notify
    STATUS current
    DESCRIPTION
        "Parameter 'interface' in event BR.3"
    ::= { brEventObjects3 3 }

brEventObjects4 OBJECT-IDENTITY
    STATUS current
    DESCRIPTION
        "Event BR.4
        A frame has been received for the IPX protocol (in 802.3 encapsulation),
        but the IPX protocol is being administratively filtered by the bridge.
        The frame will be dropped."
    ::= { brEventsGroup 4 }

br4-source-mac OBJECT-TYPE
    SYNTAX DisplayString
    MAX-ACCESS accessible-for-notify
    STATUS current
    DESCRIPTION
        "Parameter 'source-mac' in event BR.4"
    ::= { brEventObjects4 1 }

br4-dest-mac OBJECT-TYPE
    SYNTAX DisplayString
    MAX-ACCESS accessible-for-notify
    STATUS current
    DESCRIPTION
        "Parameter 'dest-mac' in event BR.4"
    ::= { brEventObjects4 2 }

br4-interface OBJECT-TYPE
    SYNTAX DisplayString
    MAX-ACCESS accessible-for-notify
    STATUS current
    DESCRIPTION
        "Parameter 'interface' in event BR.4"
    ::= { brEventObjects4 3 }

brEventObjects5 OBJECT-IDENTITY
    STATUS current
    DESCRIPTION
        "Event BR.5
        A frame has been received for the specified IEEE 802 Subnetwork Access
        Protocol (SNAP) Protocol Identifier (PID), but this PID is being
        administratively filtered by the bridge. The frame will be dropped."
    ::= { brEventsGroup 5 }

br5-source-mac OBJECT-TYPE
    SYNTAX DisplayString
    MAX-ACCESS accessible-for-notify
    STATUS current
    DESCRIPTION
        "Parameter 'source-mac' in event BR.5"
    ::= { brEventObjects5 1 }

br5-dest-mac OBJECT-TYPE
    SYNTAX DisplayString
    MAX-ACCESS accessible-for-notify
    STATUS current
    DESCRIPTION
        "Parameter 'dest-mac' in event BR.5"
    ::= { brEventObjects5 2 }

br5-protocol-identifier OBJECT-TYPE
    SYNTAX Integer32
    MAX-ACCESS accessible-for-notify
    STATUS current
    DESCRIPTION
        "Parameter 'protocol-identifier' in event BR.5"
    ::= { brEventObjects5 3 }

br5-interface OBJECT-TYPE
    SYNTAX DisplayString
    MAX-ACCESS accessible-for-notify
    STATUS current
    DESCRIPTION
        "Parameter 'interface' in event BR.5"
    ::= { brEventObjects5 4 }

brEventObjects6 OBJECT-IDENTITY
    STATUS current
    DESCRIPTION
        "Event BR.6
        A frame has been received for the IEEE 802 Subnetwork Access Protocol
        (SNAP) Protocol Identifier (PID) which corresponds with an enabled
        protocol, but the destination MAC address is not registered
        in the bridge. The frame will be dropped."
    ::= { brEventsGroup 6 }

br6-source-mac OBJECT-TYPE
    SYNTAX DisplayString
    MAX-ACCESS accessible-for-notify
    STATUS current
    DESCRIPTION
        "Parameter 'source-mac' in event BR.6"
    ::= { brEventObjects6 1 }

br6-dest-mac OBJECT-TYPE
    SYNTAX DisplayString
    MAX-ACCESS accessible-for-notify
    STATUS current
    DESCRIPTION
        "Parameter 'dest-mac' in event BR.6"
    ::= { brEventObjects6 2 }

br6-protocol-identifier OBJECT-TYPE
    SYNTAX Integer32
    MAX-ACCESS accessible-for-notify
    STATUS current
    DESCRIPTION
        "Parameter 'protocol-identifier' in event BR.6"
    ::= { brEventObjects6 3 }

br6-interface OBJECT-TYPE
    SYNTAX DisplayString
    MAX-ACCESS accessible-for-notify
    STATUS current
    DESCRIPTION
        "Parameter 'interface' in event BR.6"
    ::= { brEventObjects6 4 }

brEventObjects7 OBJECT-IDENTITY
    STATUS current
    DESCRIPTION
        "Event BR.7
        A multicast frame has been received for the IEEE 802 Subnetwork Access
        Protocol (SNAP) Protocol Identifier (PID) which corresponds with
        an endnode protocol. The frame will be both bridged and
        locally processed by the endnode protocol."
    ::= { brEventsGroup 7 }

br7-source-mac OBJECT-TYPE
    SYNTAX DisplayString
    MAX-ACCESS accessible-for-notify
    STATUS current
    DESCRIPTION
        "Parameter 'source-mac' in event BR.7"
    ::= { brEventObjects7 1 }

br7-dest-mac OBJECT-TYPE
    SYNTAX DisplayString
    MAX-ACCESS accessible-for-notify
    STATUS current
    DESCRIPTION
        "Parameter 'dest-mac' in event BR.7"
    ::= { brEventObjects7 2 }

br7-protocol-identifier OBJECT-TYPE
    SYNTAX Integer32
    MAX-ACCESS accessible-for-notify
    STATUS current
    DESCRIPTION
        "Parameter 'protocol-identifier' in event BR.7"
    ::= { brEventObjects7 3 }

br7-interface OBJECT-TYPE
    SYNTAX DisplayString
    MAX-ACCESS accessible-for-notify
    STATUS current
    DESCRIPTION
        "Parameter 'interface' in event BR.7"
    ::= { brEventObjects7 4 }

brEventObjects8 OBJECT-IDENTITY
    STATUS current
    DESCRIPTION
        "Event BR.8
        An IEEE 802.2 frame has been received over a WAN interface in a bridge
        encapsulation, but its IEEE 802 Subnetwork Access Protocol (SNAP)
        Protocol Identifier (PID) is one that is being routed by this node.
        The frame will be dropped."
    ::= { brEventsGroup 8 }

br8-source-mac OBJECT-TYPE
    SYNTAX DisplayString
    MAX-ACCESS accessible-for-notify
    STATUS current
    DESCRIPTION
        "Parameter 'source-mac' in event BR.8"
    ::= { brEventObjects8 1 }

br8-dest-mac OBJECT-TYPE
    SYNTAX DisplayString
    MAX-ACCESS accessible-for-notify
    STATUS current
    DESCRIPTION
        "Parameter 'dest-mac' in event BR.8"
    ::= { brEventObjects8 2 }

br8-protocol-identifier OBJECT-TYPE
    SYNTAX Integer32
    MAX-ACCESS accessible-for-notify
    STATUS current
    DESCRIPTION
        "Parameter 'protocol-identifier' in event BR.8"
    ::= { brEventObjects8 3 }

br8-interface OBJECT-TYPE
    SYNTAX DisplayString
    MAX-ACCESS accessible-for-notify
    STATUS current
    DESCRIPTION
        "Parameter 'interface' in event BR.8"
    ::= { brEventObjects8 4 }

brEventObjects9 OBJECT-IDENTITY
    STATUS current
    DESCRIPTION
        "Event BR.9
        An IEEE 802.1D Bridge Protocol Data Unit (BPDU) was received at
        the wrong destination address. It is supposed to be addressed to
        a particular multicast address. The BPDU will be dropped."
    ::= { brEventsGroup 9 }

br9-source-mac OBJECT-TYPE
    SYNTAX DisplayString
    MAX-ACCESS accessible-for-notify
    STATUS current
    DESCRIPTION
        "Parameter 'source-mac' in event BR.9"
    ::= { brEventObjects9 1 }

br9-dest-mac OBJECT-TYPE
    SYNTAX DisplayString
    MAX-ACCESS accessible-for-notify
    STATUS current
    DESCRIPTION
        "Parameter 'dest-mac' in event BR.9"
    ::= { brEventObjects9 2 }

br9-interface OBJECT-TYPE
    SYNTAX DisplayString
    MAX-ACCESS accessible-for-notify
    STATUS current
    DESCRIPTION
        "Parameter 'interface' in event BR.9"
    ::= { brEventObjects9 3 }

brEventObjects10 OBJECT-IDENTITY
    STATUS current
    DESCRIPTION
        "Event BR.10
        A frame has been received for the specified IEEE 802.2 Destination
        Service Access Point (DSAP), but this DSAP is being administratively
        filtered by the bridge. The frame will be dropped."
    ::= { brEventsGroup 10 }

br10-source-mac OBJECT-TYPE
    SYNTAX DisplayString
    MAX-ACCESS accessible-for-notify
    STATUS current
    DESCRIPTION
        "Parameter 'source-mac' in event BR.10"
    ::= { brEventObjects10 1 }

br10-dest-mac OBJECT-TYPE
    SYNTAX DisplayString
    MAX-ACCESS accessible-for-notify
    STATUS current
    DESCRIPTION
        "Parameter 'dest-mac' in event BR.10"
    ::= { brEventObjects10 2 }

br10-destination-service-access-point OBJECT-TYPE
    SYNTAX Integer32
    MAX-ACCESS accessible-for-notify
    STATUS current
    DESCRIPTION
        "Parameter 'destination-service-access-point' in event BR.10"
    ::= { brEventObjects10 3 }

br10-interface OBJECT-TYPE
    SYNTAX DisplayString
    MAX-ACCESS accessible-for-notify
    STATUS current
    DESCRIPTION
        "Parameter 'interface' in event BR.10"
    ::= { brEventObjects10 4 }

brEventObjects11 OBJECT-IDENTITY
    STATUS current
    DESCRIPTION
        "Event BR.11
        A frame has been received for the IEEE 802.2 Destination Service Access
        Point (DSAP) which corresponds with an enabled protocol, but
        the destination MAC address is not registered in the bridge.
        The frame will be dropped."
    ::= { brEventsGroup 11 }

br11-source-mac OBJECT-TYPE
    SYNTAX DisplayString
    MAX-ACCESS accessible-for-notify
    STATUS current
    DESCRIPTION
        "Parameter 'source-mac' in event BR.11"
    ::= { brEventObjects11 1 }

br11-dest-mac OBJECT-TYPE
    SYNTAX DisplayString
    MAX-ACCESS accessible-for-notify
    STATUS current
    DESCRIPTION
        "Parameter 'dest-mac' in event BR.11"
    ::= { brEventObjects11 2 }

br11-destination-service-access-point OBJECT-TYPE
    SYNTAX Integer32
    MAX-ACCESS accessible-for-notify
    STATUS current
    DESCRIPTION
        "Parameter 'destination-service-access-point' in event BR.11"
    ::= { brEventObjects11 3 }

br11-interface OBJECT-TYPE
    SYNTAX DisplayString
    MAX-ACCESS accessible-for-notify
    STATUS current
    DESCRIPTION
        "Parameter 'interface' in event BR.11"
    ::= { brEventObjects11 4 }

brEventObjects12 OBJECT-IDENTITY
    STATUS current
    DESCRIPTION
        "Event BR.12
        A multicast frame has been received for the IEEE 802.2 Destination
        Service Access Point (DSAP) which corresponds with an endnode protocol.
        The frame will be both bridged and locally processed by
        the endnode protocol."
    ::= { brEventsGroup 12 }

br12-source-mac OBJECT-TYPE
    SYNTAX DisplayString
    MAX-ACCESS accessible-for-notify
    STATUS current
    DESCRIPTION
        "Parameter 'source-mac' in event BR.12"
    ::= { brEventObjects12 1 }

br12-dest-mac OBJECT-TYPE
    SYNTAX DisplayString
    MAX-ACCESS accessible-for-notify
    STATUS current
    DESCRIPTION
        "Parameter 'dest-mac' in event BR.12"
    ::= { brEventObjects12 2 }

br12-destination-service-access-point OBJECT-TYPE
    SYNTAX Integer32
    MAX-ACCESS accessible-for-notify
    STATUS current
    DESCRIPTION
        "Parameter 'destination-service-access-point' in event BR.12"
    ::= { brEventObjects12 3 }

br12-interface OBJECT-TYPE
    SYNTAX DisplayString
    MAX-ACCESS accessible-for-notify
    STATUS current
    DESCRIPTION
        "Parameter 'interface' in event BR.12"
    ::= { brEventObjects12 4 }

brEventObjects13 OBJECT-IDENTITY
    STATUS current
    DESCRIPTION
        "Event BR.13
        An IEEE 802.2 frame has been received over a WAN interface in a bridge
        encapsulation, but its IEEE 802.2 Destination Service Access Point
        (DSAP) is one that is being routed by this node. The frame will be
        dropped."
    ::= { brEventsGroup 13 }

br13-source-mac OBJECT-TYPE
    SYNTAX DisplayString
    MAX-ACCESS accessible-for-notify
    STATUS current
    DESCRIPTION
        "Parameter 'source-mac' in event BR.13"
    ::= { brEventObjects13 1 }

br13-dest-mac OBJECT-TYPE
    SYNTAX DisplayString
    MAX-ACCESS accessible-for-notify
    STATUS current
    DESCRIPTION
        "Parameter 'dest-mac' in event BR.13"
    ::= { brEventObjects13 2 }

br13-destination-service-access-point OBJECT-TYPE
    SYNTAX Integer32
    MAX-ACCESS accessible-for-notify
    STATUS current
    DESCRIPTION
        "Parameter 'destination-service-access-point' in event BR.13"
    ::= { brEventObjects13 3 }

br13-interface OBJECT-TYPE
    SYNTAX DisplayString
    MAX-ACCESS accessible-for-notify
    STATUS current
    DESCRIPTION
        "Parameter 'interface' in event BR.13"
    ::= { brEventObjects13 4 }

brEventObjects14 OBJECT-IDENTITY
    STATUS current
    DESCRIPTION
        "Event BR.14
        A frame has been received for the specified Ethernet type, but this type
        is being administratively filtered by the bridge. The frame will be
        dropped."
    ::= { brEventsGroup 14 }

br14-source-mac OBJECT-TYPE
    SYNTAX DisplayString
    MAX-ACCESS accessible-for-notify
    STATUS current
    DESCRIPTION
        "Parameter 'source-mac' in event BR.14"
    ::= { brEventObjects14 1 }

br14-dest-mac OBJECT-TYPE
    SYNTAX DisplayString
    MAX-ACCESS accessible-for-notify
    STATUS current
    DESCRIPTION
        "Parameter 'dest-mac' in event BR.14"
    ::= { brEventObjects14 2 }

br14-Ethernet-type OBJECT-TYPE
    SYNTAX Integer32
    MAX-ACCESS accessible-for-notify
    STATUS current
    DESCRIPTION
        "Parameter 'Ethernet-type' in event BR.14"
    ::= { brEventObjects14 3 }

br14-interface OBJECT-TYPE
    SYNTAX DisplayString
    MAX-ACCESS accessible-for-notify
    STATUS current
    DESCRIPTION
        "Parameter 'interface' in event BR.14"
    ::= { brEventObjects14 4 }

brEventObjects15 OBJECT-IDENTITY
    STATUS current
    DESCRIPTION
        "Event BR.15
        A frame has been received for the Ethernet type which corresponds with
        an enabled protocol, but the destination MAC address is not registered
        in the bridge. The frame will be dropped."
    ::= { brEventsGroup 15 }

br15-source-mac OBJECT-TYPE
    SYNTAX DisplayString
    MAX-ACCESS accessible-for-notify
    STATUS current
    DESCRIPTION
        "Parameter 'source-mac' in event BR.15"
    ::= { brEventObjects15 1 }

br15-dest-mac OBJECT-TYPE
    SYNTAX DisplayString
    MAX-ACCESS accessible-for-notify
    STATUS current
    DESCRIPTION
        "Parameter 'dest-mac' in event BR.15"
    ::= { brEventObjects15 2 }

br15-Ethernet-type OBJECT-TYPE
    SYNTAX Integer32
    MAX-ACCESS accessible-for-notify
    STATUS current
    DESCRIPTION
        "Parameter 'Ethernet-type' in event BR.15"
    ::= { brEventObjects15 3 }

br15-interface OBJECT-TYPE
    SYNTAX DisplayString
    MAX-ACCESS accessible-for-notify
    STATUS current
    DESCRIPTION
        "Parameter 'interface' in event BR.15"
    ::= { brEventObjects15 4 }

brEventObjects16 OBJECT-IDENTITY
    STATUS current
    DESCRIPTION
        "Event BR.16
        A multicast frame has been received for the Ethernet type which
        corresponds with an endnode protocol. The frame will be both bridged
        and locally processed by the endnode protocol."
    ::= { brEventsGroup 16 }

br16-source-mac OBJECT-TYPE
    SYNTAX DisplayString
    MAX-ACCESS accessible-for-notify
    STATUS current
    DESCRIPTION
        "Parameter 'source-mac' in event BR.16"
    ::= { brEventObjects16 1 }

br16-dest-mac OBJECT-TYPE
    SYNTAX DisplayString
    MAX-ACCESS accessible-for-notify
    STATUS current
    DESCRIPTION
        "Parameter 'dest-mac' in event BR.16"
    ::= { brEventObjects16 2 }

br16-Ethernet-type OBJECT-TYPE
    SYNTAX Integer32
    MAX-ACCESS accessible-for-notify
    STATUS current
    DESCRIPTION
        "Parameter 'Ethernet-type' in event BR.16"
    ::= { brEventObjects16 3 }

br16-interface OBJECT-TYPE
    SYNTAX DisplayString
    MAX-ACCESS accessible-for-notify
    STATUS current
    DESCRIPTION
        "Parameter 'interface' in event BR.16"
    ::= { brEventObjects16 4 }

brEventObjects17 OBJECT-IDENTITY
    STATUS current
    DESCRIPTION
        "Event BR.17
        An Ethernet frame has been received over a WAN interface in the Ethernet
        bridge encapsulation, but its Ethernet type is one that is being routed
        by this node. The frame will be dropped."
    ::= { brEventsGroup 17 }

br17-source-mac OBJECT-TYPE
    SYNTAX DisplayString
    MAX-ACCESS accessible-for-notify
    STATUS current
    DESCRIPTION
        "Parameter 'source-mac' in event BR.17"
    ::= { brEventObjects17 1 }

br17-dest-mac OBJECT-TYPE
    SYNTAX DisplayString
    MAX-ACCESS accessible-for-notify
    STATUS current
    DESCRIPTION
        "Parameter 'dest-mac' in event BR.17"
    ::= { brEventObjects17 2 }

br17-Ethernet-type OBJECT-TYPE
    SYNTAX Integer32
    MAX-ACCESS accessible-for-notify
    STATUS current
    DESCRIPTION
        "Parameter 'Ethernet-type' in event BR.17"
    ::= { brEventObjects17 3 }

br17-interface OBJECT-TYPE
    SYNTAX DisplayString
    MAX-ACCESS accessible-for-notify
    STATUS current
    DESCRIPTION
        "Parameter 'interface' in event BR.17"
    ::= { brEventObjects17 4 }

brEventObjects18 OBJECT-IDENTITY
    STATUS current
    DESCRIPTION
        "Event BR.18
        A source-routed frame has been received for the specified IEEE 802.2
        Destination Service Access Point (DSAP), but this DSAP is being
        administratively filtered by the bridge. The frame will be dropped."
    ::= { brEventsGroup 18 }

br18-source-mac OBJECT-TYPE
    SYNTAX DisplayString
    MAX-ACCESS accessible-for-notify
    STATUS current
    DESCRIPTION
        "Parameter 'source-mac' in event BR.18"
    ::= { brEventObjects18 1 }

br18-dest-mac OBJECT-TYPE
    SYNTAX DisplayString
    MAX-ACCESS accessible-for-notify
    STATUS current
    DESCRIPTION
        "Parameter 'dest-mac' in event BR.18"
    ::= { brEventObjects18 2 }

br18-destination-service-access-point OBJECT-TYPE
    SYNTAX Integer32
    MAX-ACCESS accessible-for-notify
    STATUS current
    DESCRIPTION
        "Parameter 'destination-service-access-point' in event BR.18"
    ::= { brEventObjects18 3 }

br18-interface OBJECT-TYPE
    SYNTAX DisplayString
    MAX-ACCESS accessible-for-notify
    STATUS current
    DESCRIPTION
        "Parameter 'interface' in event BR.18"
    ::= { brEventObjects18 4 }

brEventObjects19 OBJECT-IDENTITY
    STATUS current
    DESCRIPTION
        "Event BR.19
        A source-routed frame has been received for the IEEE 802.2 Destination
        Service Access Point (DSAP) which corresponds with an enabled protocol,
        but the destination MAC address is not registered in the bridge.
        The frame will be dropped."
    ::= { brEventsGroup 19 }

br19-source-mac OBJECT-TYPE
    SYNTAX DisplayString
    MAX-ACCESS accessible-for-notify
    STATUS current
    DESCRIPTION
        "Parameter 'source-mac' in event BR.19"
    ::= { brEventObjects19 1 }

br19-dest-mac OBJECT-TYPE
    SYNTAX DisplayString
    MAX-ACCESS accessible-for-notify
    STATUS current
    DESCRIPTION
        "Parameter 'dest-mac' in event BR.19"
    ::= { brEventObjects19 2 }

br19-destination-service-access-point OBJECT-TYPE
    SYNTAX Integer32
    MAX-ACCESS accessible-for-notify
    STATUS current
    DESCRIPTION
        "Parameter 'destination-service-access-point' in event BR.19"
    ::= { brEventObjects19 3 }

br19-interface OBJECT-TYPE
    SYNTAX DisplayString
    MAX-ACCESS accessible-for-notify
    STATUS current
    DESCRIPTION
        "Parameter 'interface' in event BR.19"
    ::= { brEventObjects19 4 }

brEventObjects20 OBJECT-IDENTITY
    STATUS current
    DESCRIPTION
        "Event BR.20
        A multicast source-routed frame has been received for the IEEE 802.2
        Destination Service Access Point (DSAP) which corresponds with
        an endnode protocol. The frame will be both bridged and
        locally processed by the endnode protocol."
    ::= { brEventsGroup 20 }

br20-source-mac OBJECT-TYPE
    SYNTAX DisplayString
    MAX-ACCESS accessible-for-notify
    STATUS current
    DESCRIPTION
        "Parameter 'source-mac' in event BR.20"
    ::= { brEventObjects20 1 }

br20-dest-mac OBJECT-TYPE
    SYNTAX DisplayString
    MAX-ACCESS accessible-for-notify
    STATUS current
    DESCRIPTION
        "Parameter 'dest-mac' in event BR.20"
    ::= { brEventObjects20 2 }

br20-destination-service-access-point OBJECT-TYPE
    SYNTAX Integer32
    MAX-ACCESS accessible-for-notify
    STATUS current
    DESCRIPTION
        "Parameter 'destination-service-access-point' in event BR.20"
    ::= { brEventObjects20 3 }

br20-interface OBJECT-TYPE
    SYNTAX DisplayString
    MAX-ACCESS accessible-for-notify
    STATUS current
    DESCRIPTION
        "Parameter 'interface' in event BR.20"
    ::= { brEventObjects20 4 }

brEventObjects21 OBJECT-IDENTITY
    STATUS current
    DESCRIPTION
        "Event BR.21
        A source-routed frame has been received for the specified IEEE 802
        Subnetwork Access Protocol (SNAP) Protocol Identifier (PID), but
        this PID is being administratively filtered by the bridge. The frame
        will be dropped."
    ::= { brEventsGroup 21 }

br21-source-mac OBJECT-TYPE
    SYNTAX DisplayString
    MAX-ACCESS accessible-for-notify
    STATUS current
    DESCRIPTION
        "Parameter 'source-mac' in event BR.21"
    ::= { brEventObjects21 1 }

br21-dest-mac OBJECT-TYPE
    SYNTAX DisplayString
    MAX-ACCESS accessible-for-notify
    STATUS current
    DESCRIPTION
        "Parameter 'dest-mac' in event BR.21"
    ::= { brEventObjects21 2 }

br21-protocol-identifier OBJECT-TYPE
    SYNTAX Integer32
    MAX-ACCESS accessible-for-notify
    STATUS current
    DESCRIPTION
        "Parameter 'protocol-identifier' in event BR.21"
    ::= { brEventObjects21 3 }

br21-interface OBJECT-TYPE
    SYNTAX DisplayString
    MAX-ACCESS accessible-for-notify
    STATUS current
    DESCRIPTION
        "Parameter 'interface' in event BR.21"
    ::= { brEventObjects21 4 }

brEventObjects22 OBJECT-IDENTITY
    STATUS current
    DESCRIPTION
        "Event BR.22
        A source-routed frame has been received for the IEEE 802 Subnetwork
        Access Protocol (SNAP) Protocol Identifier (PID) which corresponds with
        an enabled protocol, but the destination MAC address is not registered
        in the bridge. The frame will be dropped."
    ::= { brEventsGroup 22 }

br22-source-mac OBJECT-TYPE
    SYNTAX DisplayString
    MAX-ACCESS accessible-for-notify
    STATUS current
    DESCRIPTION
        "Parameter 'source-mac' in event BR.22"
    ::= { brEventObjects22 1 }

br22-dest-mac OBJECT-TYPE
    SYNTAX DisplayString
    MAX-ACCESS accessible-for-notify
    STATUS current
    DESCRIPTION
        "Parameter 'dest-mac' in event BR.22"
    ::= { brEventObjects22 2 }

br22-protocol-identifier OBJECT-TYPE
    SYNTAX Integer32
    MAX-ACCESS accessible-for-notify
    STATUS current
    DESCRIPTION
        "Parameter 'protocol-identifier' in event BR.22"
    ::= { brEventObjects22 3 }

br22-interface OBJECT-TYPE
    SYNTAX DisplayString
    MAX-ACCESS accessible-for-notify
    STATUS current
    DESCRIPTION
        "Parameter 'interface' in event BR.22"
    ::= { brEventObjects22 4 }

brEventObjects23 OBJECT-IDENTITY
    STATUS current
    DESCRIPTION
        "Event BR.23
        SA source-routed multicast frame has been received for the IEEE 802
        Subnetwork Access Protocol (SNAP) Protocol Identifier (PID) which
        corresponds with an endnode protocol. The frame will be both bridged
        and locally processed by the endnode protocol."
    ::= { brEventsGroup 23 }

br23-source-mac OBJECT-TYPE
    SYNTAX DisplayString
    MAX-ACCESS accessible-for-notify
    STATUS current
    DESCRIPTION
        "Parameter 'source-mac' in event BR.23"
    ::= { brEventObjects23 1 }

br23-dest-mac OBJECT-TYPE
    SYNTAX DisplayString
    MAX-ACCESS accessible-for-notify
    STATUS current
    DESCRIPTION
        "Parameter 'dest-mac' in event BR.23"
    ::= { brEventObjects23 2 }

br23-protocol-identifier OBJECT-TYPE
    SYNTAX Integer32
    MAX-ACCESS accessible-for-notify
    STATUS current
    DESCRIPTION
        "Parameter 'protocol-identifier' in event BR.23"
    ::= { brEventObjects23 3 }

br23-interface OBJECT-TYPE
    SYNTAX DisplayString
    MAX-ACCESS accessible-for-notify
    STATUS current
    DESCRIPTION
        "Parameter 'interface' in event BR.23"
    ::= { brEventObjects23 4 }

brEventObjects24 OBJECT-IDENTITY
    STATUS current
    DESCRIPTION
        "Event BR.24
        A vlan frame has been received whose virtual lan id is not supported.
        Frame is dropped."
    ::= { brEventsGroup 24 }

br24-vlan-id OBJECT-TYPE
    SYNTAX Integer32
    MAX-ACCESS accessible-for-notify
    STATUS current
    DESCRIPTION
        "Parameter 'vlan-id' in event BR.24"
    ::= { brEventObjects24 1 }

br24-interface OBJECT-TYPE
    SYNTAX DisplayString
    MAX-ACCESS accessible-for-notify
    STATUS current
    DESCRIPTION
        "Parameter 'interface' in event BR.24"
    ::= { brEventObjects24 2 }

brEventObjects26 OBJECT-IDENTITY
    STATUS current
    DESCRIPTION
        "Event BR.26
        A source-routed MAC frame has been received by the hardware, but
        is being dropped because the destination MAC address is being
        administratively filtered by the bridge. The frame will be dropped."
    ::= { brEventsGroup 26 }

br26-source-mac OBJECT-TYPE
    SYNTAX DisplayString
    MAX-ACCESS accessible-for-notify
    STATUS current
    DESCRIPTION
        "Parameter 'source-mac' in event BR.26"
    ::= { brEventObjects26 1 }

br26-dest-mac OBJECT-TYPE
    SYNTAX DisplayString
    MAX-ACCESS accessible-for-notify
    STATUS current
    DESCRIPTION
        "Parameter 'dest-mac' in event BR.26"
    ::= { brEventObjects26 2 }

br26-interface OBJECT-TYPE
    SYNTAX DisplayString
    MAX-ACCESS accessible-for-notify
    STATUS current
    DESCRIPTION
        "Parameter 'interface' in event BR.26"
    ::= { brEventObjects26 3 }

brEventObjects27 OBJECT-IDENTITY
    STATUS current
    DESCRIPTION
        "Event BR.27
        A source-routed MAC frame has been received by the hardware, but
        is being dropped because the source MAC address is being
        administratively filtered by the bridge. The frame will be dropped."
    ::= { brEventsGroup 27 }

br27-source-mac OBJECT-TYPE
    SYNTAX DisplayString
    MAX-ACCESS accessible-for-notify
    STATUS current
    DESCRIPTION
        "Parameter 'source-mac' in event BR.27"
    ::= { brEventObjects27 1 }

br27-dest-mac OBJECT-TYPE
    SYNTAX DisplayString
    MAX-ACCESS accessible-for-notify
    STATUS current
    DESCRIPTION
        "Parameter 'dest-mac' in event BR.27"
    ::= { brEventObjects27 2 }

br27-interface OBJECT-TYPE
    SYNTAX DisplayString
    MAX-ACCESS accessible-for-notify
    STATUS current
    DESCRIPTION
        "Parameter 'interface' in event BR.27"
    ::= { brEventObjects27 3 }

brEventObjects28 OBJECT-IDENTITY
    STATUS current
    DESCRIPTION
        "Event BR.28
        A multicast frame has been received for an endnode protocol that is
        both bridged and locally processed. There was no buffer to make
        two copies of the frame for both types of processing, so it will not be
        bridged, only locally processed."
    ::= { brEventsGroup 28 }

br28-source-mac OBJECT-TYPE
    SYNTAX DisplayString
    MAX-ACCESS accessible-for-notify
    STATUS current
    DESCRIPTION
        "Parameter 'source-mac' in event BR.28"
    ::= { brEventObjects28 1 }

br28-dest-mac OBJECT-TYPE
    SYNTAX DisplayString
    MAX-ACCESS accessible-for-notify
    STATUS current
    DESCRIPTION
        "Parameter 'dest-mac' in event BR.28"
    ::= { brEventObjects28 2 }

br28-interface OBJECT-TYPE
    SYNTAX DisplayString
    MAX-ACCESS accessible-for-notify
    STATUS current
    DESCRIPTION
        "Parameter 'interface' in event BR.28"
    ::= { brEventObjects28 3 }

brEventObjects29 OBJECT-IDENTITY
    STATUS current
    DESCRIPTION
        "Event BR.29
        A NETBIOS packet has matched the criteria specified in a NETBIOS Filter
        configuration record. The packet is dropped."
    ::= { brEventsGroup 29 }

br29-source-mac OBJECT-TYPE
    SYNTAX DisplayString
    MAX-ACCESS accessible-for-notify
    STATUS current
    DESCRIPTION
        "Parameter 'source-mac' in event BR.29"
    ::= { brEventObjects29 1 }

br29-dest-mac OBJECT-TYPE
    SYNTAX DisplayString
    MAX-ACCESS accessible-for-notify
    STATUS current
    DESCRIPTION
        "Parameter 'dest-mac' in event BR.29"
    ::= { brEventObjects29 2 }

br29-port OBJECT-TYPE
    SYNTAX Integer32
    MAX-ACCESS accessible-for-notify
    STATUS current
    DESCRIPTION
        "Parameter 'port' in event BR.29"
    ::= { brEventObjects29 3 }

br29-interface OBJECT-TYPE
    SYNTAX DisplayString
    MAX-ACCESS accessible-for-notify
    STATUS current
    DESCRIPTION
        "Parameter 'interface' in event BR.29"
    ::= { brEventObjects29 4 }

brEventObjects30 OBJECT-IDENTITY
    STATUS current
    DESCRIPTION
        "Event BR.30
        The MAC address of a BVI interface has been updated"
    ::= { brEventsGroup 30 }

br30-interface OBJECT-TYPE
    SYNTAX DisplayString
    MAX-ACCESS accessible-for-notify
    STATUS current
    DESCRIPTION
        "Parameter 'interface' in event BR.30"
    ::= { brEventObjects30 1 }

br30-new-mac OBJECT-TYPE
    SYNTAX DisplayString
    MAX-ACCESS accessible-for-notify
    STATUS current
    DESCRIPTION
        "Parameter 'new-mac' in event BR.30"
    ::= { brEventObjects30 2 }

brEventObjects31 OBJECT-IDENTITY
    STATUS current
    DESCRIPTION
        "Event BR.31
        A frame is going to be output to the bridge through a BVI interface."
    ::= { brEventsGroup 31 }

br31-interface OBJECT-TYPE
    SYNTAX DisplayString
    MAX-ACCESS accessible-for-notify
    STATUS current
    DESCRIPTION
        "Parameter 'interface' in event BR.31"
    ::= { brEventObjects31 1 }

br31-source-mac OBJECT-TYPE
    SYNTAX DisplayString
    MAX-ACCESS accessible-for-notify
    STATUS current
    DESCRIPTION
        "Parameter 'source-mac' in event BR.31"
    ::= { brEventObjects31 2 }

br31-dest-mac OBJECT-TYPE
    SYNTAX DisplayString
    MAX-ACCESS accessible-for-notify
    STATUS current
    DESCRIPTION
        "Parameter 'dest-mac' in event BR.31"
    ::= { brEventObjects31 3 }

br31-protocol OBJECT-TYPE
    SYNTAX Integer32
    MAX-ACCESS accessible-for-notify
    STATUS current
    DESCRIPTION
        "Parameter 'protocol' in event BR.31"
    ::= { brEventObjects31 4 }

brEventObjects32 OBJECT-IDENTITY
    STATUS current
    DESCRIPTION
        "Event BR.32
        A frame has been received in a BVI interface."
    ::= { brEventsGroup 32 }

br32-interface OBJECT-TYPE
    SYNTAX DisplayString
    MAX-ACCESS accessible-for-notify
    STATUS current
    DESCRIPTION
        "Parameter 'interface' in event BR.32"
    ::= { brEventObjects32 1 }

br32-source-mac OBJECT-TYPE
    SYNTAX DisplayString
    MAX-ACCESS accessible-for-notify
    STATUS current
    DESCRIPTION
        "Parameter 'source-mac' in event BR.32"
    ::= { brEventObjects32 2 }

br32-dest-mac OBJECT-TYPE
    SYNTAX DisplayString
    MAX-ACCESS accessible-for-notify
    STATUS current
    DESCRIPTION
        "Parameter 'dest-mac' in event BR.32"
    ::= { brEventObjects32 3 }

br32-protocol OBJECT-TYPE
    SYNTAX Integer32
    MAX-ACCESS accessible-for-notify
    STATUS current
    DESCRIPTION
        "Parameter 'protocol' in event BR.32"
    ::= { brEventObjects32 4 }

brEventObjects33 OBJECT-IDENTITY
    STATUS current
    DESCRIPTION
        "Event BR.33
        A frame is droped because BVI interface is down"
    ::= { brEventsGroup 33 }

br33-interface OBJECT-TYPE
    SYNTAX DisplayString
    MAX-ACCESS accessible-for-notify
    STATUS current
    DESCRIPTION
        "Parameter 'interface' in event BR.33"
    ::= { brEventObjects33 1 }

brEventObjects34 OBJECT-IDENTITY
    STATUS current
    DESCRIPTION
        "Event BR.34
        A frame is dropped because destination IP has no registered MAC address."
    ::= { brEventsGroup 34 }

br34-interface OBJECT-TYPE
    SYNTAX DisplayString
    MAX-ACCESS accessible-for-notify
    STATUS current
    DESCRIPTION
        "Parameter 'interface' in event BR.34"
    ::= { brEventObjects34 1 }

br34-source-mac OBJECT-TYPE
    SYNTAX DisplayString
    MAX-ACCESS accessible-for-notify
    STATUS current
    DESCRIPTION
        "Parameter 'source-mac' in event BR.34"
    ::= { brEventObjects34 2 }

br34-dest-IP-address OBJECT-TYPE
    SYNTAX IpAddress
    MAX-ACCESS accessible-for-notify
    STATUS current
    DESCRIPTION
        "Parameter 'dest-IP-address' in event BR.34"
    ::= { brEventObjects34 3 }

brEventObjects35 OBJECT-IDENTITY
    STATUS current
    DESCRIPTION
        "Event BR.35
        A frame is droped because BVI interface has no protocol handler"
    ::= { brEventsGroup 35 }

br35-interface OBJECT-TYPE
    SYNTAX DisplayString
    MAX-ACCESS accessible-for-notify
    STATUS current
    DESCRIPTION
        "Parameter 'interface' in event BR.35"
    ::= { brEventObjects35 1 }

br35-protocol OBJECT-TYPE
    SYNTAX Integer32
    MAX-ACCESS accessible-for-notify
    STATUS current
    DESCRIPTION
        "Parameter 'protocol' in event BR.35"
    ::= { brEventObjects35 2 }

brEventObjects36 OBJECT-IDENTITY
    STATUS current
    DESCRIPTION
        "Event BR.36
        A frame has been received for the specified IEEE 802 Subnetwork Access
        Protocol (SNAP) Protocol Identifier (PID), but this PID has no
        forwarder or endnode support. The frame will be dropped."
    ::= { brEventsGroup 36 }

br36-source-mac OBJECT-TYPE
    SYNTAX DisplayString
    MAX-ACCESS accessible-for-notify
    STATUS current
    DESCRIPTION
        "Parameter 'source-mac' in event BR.36"
    ::= { brEventObjects36 1 }

br36-dest-mac OBJECT-TYPE
    SYNTAX DisplayString
    MAX-ACCESS accessible-for-notify
    STATUS current
    DESCRIPTION
        "Parameter 'dest-mac' in event BR.36"
    ::= { brEventObjects36 2 }

br36-protocol-identifier OBJECT-TYPE
    SYNTAX Integer32
    MAX-ACCESS accessible-for-notify
    STATUS current
    DESCRIPTION
        "Parameter 'protocol-identifier' in event BR.36"
    ::= { brEventObjects36 3 }

br36-interface OBJECT-TYPE
    SYNTAX DisplayString
    MAX-ACCESS accessible-for-notify
    STATUS current
    DESCRIPTION
        "Parameter 'interface' in event BR.36"
    ::= { brEventObjects36 4 }

brEventObjects37 OBJECT-IDENTITY
    STATUS current
    DESCRIPTION
        "Event BR.37
        A frame has been received for the specified IEEE 802 Subnetwork Access
        Protocol (SNAP) Protocol Identifier (PID), but this PID has no
        enabled bridging nor routing. The frame will be dropped."
    ::= { brEventsGroup 37 }

br37-source-mac OBJECT-TYPE
    SYNTAX DisplayString
    MAX-ACCESS accessible-for-notify
    STATUS current
    DESCRIPTION
        "Parameter 'source-mac' in event BR.37"
    ::= { brEventObjects37 1 }

br37-dest-mac OBJECT-TYPE
    SYNTAX DisplayString
    MAX-ACCESS accessible-for-notify
    STATUS current
    DESCRIPTION
        "Parameter 'dest-mac' in event BR.37"
    ::= { brEventObjects37 2 }

br37-protocol-identifier OBJECT-TYPE
    SYNTAX Integer32
    MAX-ACCESS accessible-for-notify
    STATUS current
    DESCRIPTION
        "Parameter 'protocol-identifier' in event BR.37"
    ::= { brEventObjects37 3 }

br37-interface OBJECT-TYPE
    SYNTAX DisplayString
    MAX-ACCESS accessible-for-notify
    STATUS current
    DESCRIPTION
        "Parameter 'interface' in event BR.37"
    ::= { brEventObjects37 4 }

brEventObjects38 OBJECT-IDENTITY
    STATUS current
    DESCRIPTION
        "Event BR.38
        A frame has been received for the specified IEEE 802.2 Destination
        Service Access Point (DSAP), but this DSAP has no forwarder or
        endnode support. The frame will be dropped."
    ::= { brEventsGroup 38 }

br38-source-mac OBJECT-TYPE
    SYNTAX DisplayString
    MAX-ACCESS accessible-for-notify
    STATUS current
    DESCRIPTION
        "Parameter 'source-mac' in event BR.38"
    ::= { brEventObjects38 1 }

br38-dest-mac OBJECT-TYPE
    SYNTAX DisplayString
    MAX-ACCESS accessible-for-notify
    STATUS current
    DESCRIPTION
        "Parameter 'dest-mac' in event BR.38"
    ::= { brEventObjects38 2 }

br38-destination-service-access-point OBJECT-TYPE
    SYNTAX Integer32
    MAX-ACCESS accessible-for-notify
    STATUS current
    DESCRIPTION
        "Parameter 'destination-service-access-point' in event BR.38"
    ::= { brEventObjects38 3 }

br38-interface OBJECT-TYPE
    SYNTAX DisplayString
    MAX-ACCESS accessible-for-notify
    STATUS current
    DESCRIPTION
        "Parameter 'interface' in event BR.38"
    ::= { brEventObjects38 4 }

brEventObjects39 OBJECT-IDENTITY
    STATUS current
    DESCRIPTION
        "Event BR.39
        A frame has been received for the specified IEEE 802.2 Destination
        Service Access Point (DSAP), but this DSAP has no enabled
        bridging nor routing. The frame will be dropped."
    ::= { brEventsGroup 39 }

br39-source-mac OBJECT-TYPE
    SYNTAX DisplayString
    MAX-ACCESS accessible-for-notify
    STATUS current
    DESCRIPTION
        "Parameter 'source-mac' in event BR.39"
    ::= { brEventObjects39 1 }

br39-dest-mac OBJECT-TYPE
    SYNTAX DisplayString
    MAX-ACCESS accessible-for-notify
    STATUS current
    DESCRIPTION
        "Parameter 'dest-mac' in event BR.39"
    ::= { brEventObjects39 2 }

br39-destination-service-access-point OBJECT-TYPE
    SYNTAX Integer32
    MAX-ACCESS accessible-for-notify
    STATUS current
    DESCRIPTION
        "Parameter 'destination-service-access-point' in event BR.39"
    ::= { brEventObjects39 3 }

br39-interface OBJECT-TYPE
    SYNTAX DisplayString
    MAX-ACCESS accessible-for-notify
    STATUS current
    DESCRIPTION
        "Parameter 'interface' in event BR.39"
    ::= { brEventObjects39 4 }

brEventObjects40 OBJECT-IDENTITY
    STATUS current
    DESCRIPTION
        "Event BR.40
        A frame has been received for the specified Ethernet type, but this type
        has no forwarder or endnode support. The frame will be
        dropped."
    ::= { brEventsGroup 40 }

br40-source-mac OBJECT-TYPE
    SYNTAX DisplayString
    MAX-ACCESS accessible-for-notify
    STATUS current
    DESCRIPTION
        "Parameter 'source-mac' in event BR.40"
    ::= { brEventObjects40 1 }

br40-dest-mac OBJECT-TYPE
    SYNTAX DisplayString
    MAX-ACCESS accessible-for-notify
    STATUS current
    DESCRIPTION
        "Parameter 'dest-mac' in event BR.40"
    ::= { brEventObjects40 2 }

br40-Ethernet-type OBJECT-TYPE
    SYNTAX Integer32
    MAX-ACCESS accessible-for-notify
    STATUS current
    DESCRIPTION
        "Parameter 'Ethernet-type' in event BR.40"
    ::= { brEventObjects40 3 }

br40-interface OBJECT-TYPE
    SYNTAX DisplayString
    MAX-ACCESS accessible-for-notify
    STATUS current
    DESCRIPTION
        "Parameter 'interface' in event BR.40"
    ::= { brEventObjects40 4 }

brEventObjects41 OBJECT-IDENTITY
    STATUS current
    DESCRIPTION
        "Event BR.41
        A frame has been received for the specified Ethernet type, but this type
        has no enabled bridging nor routing. The frame will be
        dropped."
    ::= { brEventsGroup 41 }

br41-source-mac OBJECT-TYPE
    SYNTAX DisplayString
    MAX-ACCESS accessible-for-notify
    STATUS current
    DESCRIPTION
        "Parameter 'source-mac' in event BR.41"
    ::= { brEventObjects41 1 }

br41-dest-mac OBJECT-TYPE
    SYNTAX DisplayString
    MAX-ACCESS accessible-for-notify
    STATUS current
    DESCRIPTION
        "Parameter 'dest-mac' in event BR.41"
    ::= { brEventObjects41 2 }

br41-Ethernet-type OBJECT-TYPE
    SYNTAX Integer32
    MAX-ACCESS accessible-for-notify
    STATUS current
    DESCRIPTION
        "Parameter 'Ethernet-type' in event BR.41"
    ::= { brEventObjects41 3 }

br41-interface OBJECT-TYPE
    SYNTAX DisplayString
    MAX-ACCESS accessible-for-notify
    STATUS current
    DESCRIPTION
        "Parameter 'interface' in event BR.41"
    ::= { brEventObjects41 4 }

brEventObjects42 OBJECT-IDENTITY
    STATUS current
    DESCRIPTION
        "Event BR.42
        A source-routed frame has been received for the specified IEEE 802.2
        Destination Service Access Point (DSAP), but this DSAP has no enabled
        bridging nor routing. The frame will be dropped."
    ::= { brEventsGroup 42 }

br42-source-mac OBJECT-TYPE
    SYNTAX DisplayString
    MAX-ACCESS accessible-for-notify
    STATUS current
    DESCRIPTION
        "Parameter 'source-mac' in event BR.42"
    ::= { brEventObjects42 1 }

br42-dest-mac OBJECT-TYPE
    SYNTAX DisplayString
    MAX-ACCESS accessible-for-notify
    STATUS current
    DESCRIPTION
        "Parameter 'dest-mac' in event BR.42"
    ::= { brEventObjects42 2 }

br42-destination-service-access-point OBJECT-TYPE
    SYNTAX Integer32
    MAX-ACCESS accessible-for-notify
    STATUS current
    DESCRIPTION
        "Parameter 'destination-service-access-point' in event BR.42"
    ::= { brEventObjects42 3 }

br42-interface OBJECT-TYPE
    SYNTAX DisplayString
    MAX-ACCESS accessible-for-notify
    STATUS current
    DESCRIPTION
        "Parameter 'interface' in event BR.42"
    ::= { brEventObjects42 4 }

brEventObjects43 OBJECT-IDENTITY
    STATUS current
    DESCRIPTION
        "Event BR.43
        A source-routed frame has been received for the specified IEEE 802
        Subnetwork Access Protocol (SNAP) Protocol Identifier (PID), but
        this PID has no enabled bridging nor routing. The frame
        will be dropped."
    ::= { brEventsGroup 43 }

br43-source-mac OBJECT-TYPE
    SYNTAX DisplayString
    MAX-ACCESS accessible-for-notify
    STATUS current
    DESCRIPTION
        "Parameter 'source-mac' in event BR.43"
    ::= { brEventObjects43 1 }

br43-dest-mac OBJECT-TYPE
    SYNTAX DisplayString
    MAX-ACCESS accessible-for-notify
    STATUS current
    DESCRIPTION
        "Parameter 'dest-mac' in event BR.43"
    ::= { brEventObjects43 2 }

br43-protocol-identifier OBJECT-TYPE
    SYNTAX Integer32
    MAX-ACCESS accessible-for-notify
    STATUS current
    DESCRIPTION
        "Parameter 'protocol-identifier' in event BR.43"
    ::= { brEventObjects43 3 }

br43-interface OBJECT-TYPE
    SYNTAX DisplayString
    MAX-ACCESS accessible-for-notify
    STATUS current
    DESCRIPTION
        "Parameter 'interface' in event BR.43"
    ::= { brEventObjects43 4 }

brEventObjects44 OBJECT-IDENTITY
    STATUS current
    DESCRIPTION
        "Event BR.44
        A frame has been received with vlan identifier FFF. This
        frame will be dropped."
    ::= { brEventsGroup 44 }

br44-source-mac OBJECT-TYPE
    SYNTAX DisplayString
    MAX-ACCESS accessible-for-notify
    STATUS current
    DESCRIPTION
        "Parameter 'source-mac' in event BR.44"
    ::= { brEventObjects44 1 }

br44-dest-mac OBJECT-TYPE
    SYNTAX DisplayString
    MAX-ACCESS accessible-for-notify
    STATUS current
    DESCRIPTION
        "Parameter 'dest-mac' in event BR.44"
    ::= { brEventObjects44 2 }

br44-interface OBJECT-TYPE
    SYNTAX DisplayString
    MAX-ACCESS accessible-for-notify
    STATUS current
    DESCRIPTION
        "Parameter 'interface' in event BR.44"
    ::= { brEventObjects44 3 }

brEventObjects45 OBJECT-IDENTITY
    STATUS current
    DESCRIPTION
        "Event BR.45
        A frame has been received with no vlan tag and port
        is configured to accept only tagged frames. This frame will be dropped."
    ::= { brEventsGroup 45 }

br45-source-mac OBJECT-TYPE
    SYNTAX DisplayString
    MAX-ACCESS accessible-for-notify
    STATUS current
    DESCRIPTION
        "Parameter 'source-mac' in event BR.45"
    ::= { brEventObjects45 1 }

br45-dest-mac OBJECT-TYPE
    SYNTAX DisplayString
    MAX-ACCESS accessible-for-notify
    STATUS current
    DESCRIPTION
        "Parameter 'dest-mac' in event BR.45"
    ::= { brEventObjects45 2 }

br45-interface OBJECT-TYPE
    SYNTAX DisplayString
    MAX-ACCESS accessible-for-notify
    STATUS current
    DESCRIPTION
        "Parameter 'interface' in event BR.45"
    ::= { brEventObjects45 3 }

brEventObjects46 OBJECT-IDENTITY
    STATUS current
    DESCRIPTION
        "Event BR.46
        A frame has been received, but its VLAN ID is not ingress enabled in the
        the port bridge. The frame will be dropped."
    ::= { brEventsGroup 46 }

br46-source-mac OBJECT-TYPE
    SYNTAX DisplayString
    MAX-ACCESS accessible-for-notify
    STATUS current
    DESCRIPTION
        "Parameter 'source-mac' in event BR.46"
    ::= { brEventObjects46 1 }

br46-dest-mac OBJECT-TYPE
    SYNTAX DisplayString
    MAX-ACCESS accessible-for-notify
    STATUS current
    DESCRIPTION
        "Parameter 'dest-mac' in event BR.46"
    ::= { brEventObjects46 2 }

br46-vlan-id OBJECT-TYPE
    SYNTAX Integer32
    MAX-ACCESS accessible-for-notify
    STATUS current
    DESCRIPTION
        "Parameter 'vlan-id' in event BR.46"
    ::= { brEventObjects46 3 }

br46-interface OBJECT-TYPE
    SYNTAX DisplayString
    MAX-ACCESS accessible-for-notify
    STATUS current
    DESCRIPTION
        "Parameter 'interface' in event BR.46"
    ::= { brEventObjects46 4 }

brEventObjects47 OBJECT-IDENTITY
    STATUS current
    DESCRIPTION
        "Event BR.47
        A frame has been received, but its VLAN ID is not egress enabled in the
        the port bridge. The frame will be dropped."
    ::= { brEventsGroup 47 }

br47-source-mac OBJECT-TYPE
    SYNTAX DisplayString
    MAX-ACCESS accessible-for-notify
    STATUS current
    DESCRIPTION
        "Parameter 'source-mac' in event BR.47"
    ::= { brEventObjects47 1 }

br47-dest-mac OBJECT-TYPE
    SYNTAX DisplayString
    MAX-ACCESS accessible-for-notify
    STATUS current
    DESCRIPTION
        "Parameter 'dest-mac' in event BR.47"
    ::= { brEventObjects47 2 }

br47-vlan-id OBJECT-TYPE
    SYNTAX Integer32
    MAX-ACCESS accessible-for-notify
    STATUS current
    DESCRIPTION
        "Parameter 'vlan-id' in event BR.47"
    ::= { brEventObjects47 3 }

br47-interface OBJECT-TYPE
    SYNTAX DisplayString
    MAX-ACCESS accessible-for-notify
    STATUS current
    DESCRIPTION
        "Parameter 'interface' in event BR.47"
    ::= { brEventObjects47 4 }

brEventObjects48 OBJECT-IDENTITY
    STATUS current
    DESCRIPTION
        "Event BR.48
        A frame has been received, but its VLAN ID is not active in the
        this port bridge. The frame will be dropped."
    ::= { brEventsGroup 48 }

br48-source-mac OBJECT-TYPE
    SYNTAX DisplayString
    MAX-ACCESS accessible-for-notify
    STATUS current
    DESCRIPTION
        "Parameter 'source-mac' in event BR.48"
    ::= { brEventObjects48 1 }

br48-dest-mac OBJECT-TYPE
    SYNTAX DisplayString
    MAX-ACCESS accessible-for-notify
    STATUS current
    DESCRIPTION
        "Parameter 'dest-mac' in event BR.48"
    ::= { brEventObjects48 2 }

br48-vlan-id OBJECT-TYPE
    SYNTAX Integer32
    MAX-ACCESS accessible-for-notify
    STATUS current
    DESCRIPTION
        "Parameter 'vlan-id' in event BR.48"
    ::= { brEventObjects48 3 }

br48-interface OBJECT-TYPE
    SYNTAX DisplayString
    MAX-ACCESS accessible-for-notify
    STATUS current
    DESCRIPTION
        "Parameter 'interface' in event BR.48"
    ::= { brEventObjects48 4 }


brNotification1 NOTIFICATION-TYPE
    OBJECTS { 
              br1-source-mac, 
              br1-dest-mac,
              br1-interface 
            }
    STATUS current
    DESCRIPTION
        "Notification of Event BR.1

        Message: 'Frame from $1 to $2 dropped, received on blocked or listening port, interface $3'

        Parameters list:
              $1: br1-source-mac
              $2: br1-dest-mac
              $3: br1-interface

        A MAC frame has been received by the hardware, but is being dropped
        because the port it was received on is in the 'blocking' or 'listening'
        state. Frames are only processed when the port is in the 'learning' or
        'forwarding' state."
    ::= { brNotificationsPrefix 1 }

brNotification2 NOTIFICATION-TYPE
    OBJECTS { 
              br2-source-mac, 
              br2-dest-mac,
              br2-interface 
            }
    STATUS current
    DESCRIPTION
        "Notification of Event BR.2

        Message: 'Frame from $1 to $2 dropped, destination on same LAN, interface $3'

        Parameters list:
              $1: br2-source-mac
              $2: br2-dest-mac
              $3: br2-interface

        A MAC frame has been received whose destination address is known to be
        on the same side of the bridge as the packet came from. It is dropped
        by the filtering logic since it does not need to be bridged. Note that
        this event is not counted by ELS for performance reasons. A counter
        is kept in ASRT, it is the 'Dropped, dest addr filtering' entry in
        the ASRT>LIST SOURCE-ROUTE COUNTERS and ASRT>LIST TRANSPARENT COUNTERS
        commands."
    ::= { brNotificationsPrefix 2 }

brNotification3 NOTIFICATION-TYPE
    OBJECTS { 
              br3-source-mac, 
              br3-dest-mac,
              br3-interface 
            }
    STATUS current
    DESCRIPTION
        "Notification of Event BR.3

        Message: 'Frame from $1 a $2, WAN bridge encapsulation for routed protocol IPX (802.3), dropped, interface $3'

        Parameters list:
              $1: br3-source-mac
              $2: br3-dest-mac
              $3: br3-interface

        A frame has been received over a WAN interface in the Ethernet bridge
        encapsulation, but the IPX protocol (in 802.3 encapsulation) is routed
        by this node."
    ::= { brNotificationsPrefix 3 }

brNotification4 NOTIFICATION-TYPE
    OBJECTS { 
              br4-source-mac, 
              br4-dest-mac,
              br4-interface 
            }
    STATUS current
    DESCRIPTION
        "Notification of Event BR.4

        Message: 'Frame from $1 to $2, protocol IPX (802.3) filtered, dropped, interface $3'

        Parameters list:
              $1: br4-source-mac
              $2: br4-dest-mac
              $3: br4-interface

        A frame has been received for the IPX protocol (in 802.3 encapsulation),
        but the IPX protocol is being administratively filtered by the bridge.
        The frame will be dropped."
    ::= { brNotificationsPrefix 4 }

brNotification5 NOTIFICATION-TYPE
    OBJECTS { 
              br5-source-mac, 
              br5-dest-mac,
              br5-protocol-identifier,
              br5-protocol-identifier,
              br5-protocol-identifier,
              br5-protocol-identifier,
              br5-protocol-identifier,
              br5-interface 
            }
    STATUS current
    DESCRIPTION
        "Notification of Event BR.5

        Message: 'Frame from $1 to $2, IEEE 802 SNAP Protocol Identifier $3-$4-$5-$6-$7 filtered, dropped, interface $8'

        Parameters list:
              $1: br5-source-mac
              $2: br5-dest-mac
              $3: br5-protocol-identifier
              $4: br5-protocol-identifier
              $5: br5-protocol-identifier
              $6: br5-protocol-identifier
              $7: br5-protocol-identifier
              $8: br5-interface

        A frame has been received for the specified IEEE 802 Subnetwork Access
        Protocol (SNAP) Protocol Identifier (PID), but this PID is being
        administratively filtered by the bridge. The frame will be dropped."
    ::= { brNotificationsPrefix 5 }

brNotification6 NOTIFICATION-TYPE
    OBJECTS { 
              br6-source-mac, 
              br6-dest-mac,
              br6-protocol-identifier,
              br6-protocol-identifier,
              br6-protocol-identifier,
              br6-protocol-identifier,
              br6-protocol-identifier,
              br6-interface 
            }
    STATUS current
    DESCRIPTION
        "Notification of Event BR.6

        Message: 'Frame from $1 to unregistered destination MAC address $2, IEEE 802 SNAP Protocol Identifier $3-$4-$5-$6-$7, dropped, interface $8'

        Parameters list:
              $1: br6-source-mac
              $2: br6-dest-mac
              $3: br6-protocol-identifier
              $4: br6-protocol-identifier
              $5: br6-protocol-identifier
              $6: br6-protocol-identifier
              $7: br6-protocol-identifier
              $8: br6-interface

        A frame has been received for the IEEE 802 Subnetwork Access Protocol
        (SNAP) Protocol Identifier (PID) which corresponds with an enabled
        protocol, but the destination MAC address is not registered
        in the bridge. The frame will be dropped."
    ::= { brNotificationsPrefix 6 }

brNotification7 NOTIFICATION-TYPE
    OBJECTS { 
              br7-source-mac, 
              br7-dest-mac,
              br7-protocol-identifier,
              br7-protocol-identifier,
              br7-protocol-identifier,
              br7-protocol-identifier,
              br7-protocol-identifier,
              br7-interface 
            }
    STATUS current
    DESCRIPTION
        "Notification of Event BR.7

        Message: 'Frame from $1 to $2, IEEE 802 SNAP Protocol Identifier $3-$4-$5-$6-$7 for endnode protocol, interface $8'

        Parameters list:
              $1: br7-source-mac
              $2: br7-dest-mac
              $3: br7-protocol-identifier
              $4: br7-protocol-identifier
              $5: br7-protocol-identifier
              $6: br7-protocol-identifier
              $7: br7-protocol-identifier
              $8: br7-interface

        A multicast frame has been received for the IEEE 802 Subnetwork Access
        Protocol (SNAP) Protocol Identifier (PID) which corresponds with
        an endnode protocol. The frame will be both bridged and
        locally processed by the endnode protocol."
    ::= { brNotificationsPrefix 7 }

brNotification8 NOTIFICATION-TYPE
    OBJECTS { 
              br8-source-mac, 
              br8-dest-mac,
              br8-protocol-identifier,
              br8-protocol-identifier,
              br8-protocol-identifier,
              br8-protocol-identifier,
              br8-protocol-identifier,
              br8-interface 
            }
    STATUS current
    DESCRIPTION
        "Notification of Event BR.8

        Message: 'Frame from $1 to $2, WAN bridge encapsulation for routed IEEE 802 SNAP Protocol Identifier $3-$4-$5-$6-$7, dropped, interface $8'

        Parameters list:
              $1: br8-source-mac
              $2: br8-dest-mac
              $3: br8-protocol-identifier
              $4: br8-protocol-identifier
              $5: br8-protocol-identifier
              $6: br8-protocol-identifier
              $7: br8-protocol-identifier
              $8: br8-interface

        An IEEE 802.2 frame has been received over a WAN interface in a bridge
        encapsulation, but its IEEE 802 Subnetwork Access Protocol (SNAP)
        Protocol Identifier (PID) is one that is being routed by this node.
        The frame will be dropped."
    ::= { brNotificationsPrefix 8 }

brNotification9 NOTIFICATION-TYPE
    OBJECTS { 
              br9-source-mac, 
              br9-dest-mac,
              br9-interface 
            }
    STATUS current
    DESCRIPTION
        "Notification of Event BR.9

        Message: 'IEEE 802.1D BPDU $1 to $2, wrong destination, dropped, interface $3'

        Parameters list:
              $1: br9-source-mac
              $2: br9-dest-mac
              $3: br9-interface

        An IEEE 802.1D Bridge Protocol Data Unit (BPDU) was received at
        the wrong destination address. It is supposed to be addressed to
        a particular multicast address. The BPDU will be dropped."
    ::= { brNotificationsPrefix 9 }

brNotification10 NOTIFICATION-TYPE
    OBJECTS { 
              br10-source-mac, 
              br10-dest-mac,
              br10-destination-service-access-point,
              br10-interface 
            }
    STATUS current
    DESCRIPTION
        "Notification of Event BR.10

        Message: 'Frame from $1 to $2, IEEE 802.2 DSAP $3 filtered, dropped, interface $4'

        Parameters list:
              $1: br10-source-mac
              $2: br10-dest-mac
              $3: br10-destination-service-access-point
              $4: br10-interface

        A frame has been received for the specified IEEE 802.2 Destination
        Service Access Point (DSAP), but this DSAP is being administratively
        filtered by the bridge. The frame will be dropped."
    ::= { brNotificationsPrefix 10 }

brNotification11 NOTIFICATION-TYPE
    OBJECTS { 
              br11-source-mac, 
              br11-dest-mac,
              br11-destination-service-access-point,
              br11-interface 
            }
    STATUS current
    DESCRIPTION
        "Notification of Event BR.11

        Message: 'Frame from $1 to unregistered destination MAC address $2, IEEE 802.2 DSAP $3, dropped, interface $4'

        Parameters list:
              $1: br11-source-mac
              $2: br11-dest-mac
              $3: br11-destination-service-access-point
              $4: br11-interface

        A frame has been received for the IEEE 802.2 Destination Service Access
        Point (DSAP) which corresponds with an enabled protocol, but
        the destination MAC address is not registered in the bridge.
        The frame will be dropped."
    ::= { brNotificationsPrefix 11 }

brNotification12 NOTIFICATION-TYPE
    OBJECTS { 
              br12-source-mac, 
              br12-dest-mac,
              br12-destination-service-access-point,
              br12-interface 
            }
    STATUS current
    DESCRIPTION
        "Notification of Event BR.12

        Message: 'Frame from $1 to $2, IEEE 802.2 DSAP $3 for endnode protocol, interface $4'

        Parameters list:
              $1: br12-source-mac
              $2: br12-dest-mac
              $3: br12-destination-service-access-point
              $4: br12-interface

        A multicast frame has been received for the IEEE 802.2 Destination
        Service Access Point (DSAP) which corresponds with an endnode protocol.
        The frame will be both bridged and locally processed by
        the endnode protocol."
    ::= { brNotificationsPrefix 12 }

brNotification13 NOTIFICATION-TYPE
    OBJECTS { 
              br13-source-mac, 
              br13-dest-mac,
              br13-destination-service-access-point,
              br13-interface 
            }
    STATUS current
    DESCRIPTION
        "Notification of Event BR.13

        Message: 'Frame from $1 to $2, WAN bridge encapsulation for routed IEEE 802.2 DSAP $3, dropped, interface $4'

        Parameters list:
              $1: br13-source-mac
              $2: br13-dest-mac
              $3: br13-destination-service-access-point
              $4: br13-interface

        An IEEE 802.2 frame has been received over a WAN interface in a bridge
        encapsulation, but its IEEE 802.2 Destination Service Access Point
        (DSAP) is one that is being routed by this node. The frame will be
        dropped."
    ::= { brNotificationsPrefix 13 }

brNotification14 NOTIFICATION-TYPE
    OBJECTS { 
              br14-source-mac, 
              br14-dest-mac,
              br14-Ethernet-type,
              br14-interface 
            }
    STATUS current
    DESCRIPTION
        "Notification of Event BR.14

        Message: 'Frame from $1 to $2, Ethernet type $3 filtered, dropped, interface $4'

        Parameters list:
              $1: br14-source-mac
              $2: br14-dest-mac
              $3: br14-Ethernet-type
              $4: br14-interface

        A frame has been received for the specified Ethernet type, but this type
        is being administratively filtered by the bridge. The frame will be
        dropped."
    ::= { brNotificationsPrefix 14 }

brNotification15 NOTIFICATION-TYPE
    OBJECTS { 
              br15-source-mac, 
              br15-dest-mac,
              br15-Ethernet-type,
              br15-interface 
            }
    STATUS current
    DESCRIPTION
        "Notification of Event BR.15

        Message: 'Frame from $1 to unregistered destination MAC address $2, Ethernet type $3, dropped, interface $4'

        Parameters list:
              $1: br15-source-mac
              $2: br15-dest-mac
              $3: br15-Ethernet-type
              $4: br15-interface

        A frame has been received for the Ethernet type which corresponds with
        an enabled protocol, but the destination MAC address is not registered
        in the bridge. The frame will be dropped."
    ::= { brNotificationsPrefix 15 }

brNotification16 NOTIFICATION-TYPE
    OBJECTS { 
              br16-source-mac, 
              br16-dest-mac,
              br16-Ethernet-type,
              br16-interface 
            }
    STATUS current
    DESCRIPTION
        "Notification of Event BR.16

        Message: 'Frame from $1 to $2, Ethernet type $3 for endnode protocol, interface $4'

        Parameters list:
              $1: br16-source-mac
              $2: br16-dest-mac
              $3: br16-Ethernet-type
              $4: br16-interface

        A multicast frame has been received for the Ethernet type which
        corresponds with an endnode protocol. The frame will be both bridged
        and locally processed by the endnode protocol."
    ::= { brNotificationsPrefix 16 }

brNotification17 NOTIFICATION-TYPE
    OBJECTS { 
              br17-source-mac, 
              br17-dest-mac,
              br17-Ethernet-type,
              br17-interface 
            }
    STATUS current
    DESCRIPTION
        "Notification of Event BR.17

        Message: 'Frame from $1 to $2, WAN bridge encapsulation for routed Ethernet type $3, dropped, interface $4'

        Parameters list:
              $1: br17-source-mac
              $2: br17-dest-mac
              $3: br17-Ethernet-type
              $4: br17-interface

        An Ethernet frame has been received over a WAN interface in the Ethernet
        bridge encapsulation, but its Ethernet type is one that is being routed
        by this node. The frame will be dropped."
    ::= { brNotificationsPrefix 17 }

brNotification18 NOTIFICATION-TYPE
    OBJECTS { 
              br18-source-mac, 
              br18-dest-mac,
              br18-destination-service-access-point,
              br18-interface 
            }
    STATUS current
    DESCRIPTION
        "Notification of Event BR.18

        Message: 'Source-routed frame from $1 to $2, IEEE 802.2 DSAP $3 filtered, dropped, interface $4'

        Parameters list:
              $1: br18-source-mac
              $2: br18-dest-mac
              $3: br18-destination-service-access-point
              $4: br18-interface

        A source-routed frame has been received for the specified IEEE 802.2
        Destination Service Access Point (DSAP), but this DSAP is being
        administratively filtered by the bridge. The frame will be dropped."
    ::= { brNotificationsPrefix 18 }

brNotification19 NOTIFICATION-TYPE
    OBJECTS { 
              br19-source-mac, 
              br19-dest-mac,
              br19-destination-service-access-point,
              br19-interface 
            }
    STATUS current
    DESCRIPTION
        "Notification of Event BR.19

        Message: 'Source-routed frame from $1 to unregistered destination MAC address $2, IEEE 802.2 DSAP $3, dropped, interface $4'

        Parameters list:
              $1: br19-source-mac
              $2: br19-dest-mac
              $3: br19-destination-service-access-point
              $4: br19-interface

        A source-routed frame has been received for the IEEE 802.2 Destination
        Service Access Point (DSAP) which corresponds with an enabled protocol,
        but the destination MAC address is not registered in the bridge.
        The frame will be dropped."
    ::= { brNotificationsPrefix 19 }

brNotification20 NOTIFICATION-TYPE
    OBJECTS { 
              br20-source-mac, 
              br20-dest-mac,
              br20-destination-service-access-point,
              br20-interface 
            }
    STATUS current
    DESCRIPTION
        "Notification of Event BR.20

        Message: 'Source-routed frame from $1 to $2, IEEE 802.2 DSAP $3 for endnode protocol, interface $4'

        Parameters list:
              $1: br20-source-mac
              $2: br20-dest-mac
              $3: br20-destination-service-access-point
              $4: br20-interface

        A multicast source-routed frame has been received for the IEEE 802.2
        Destination Service Access Point (DSAP) which corresponds with
        an endnode protocol. The frame will be both bridged and
        locally processed by the endnode protocol."
    ::= { brNotificationsPrefix 20 }

brNotification21 NOTIFICATION-TYPE
    OBJECTS { 
              br21-source-mac, 
              br21-dest-mac,
              br21-protocol-identifier,
              br21-protocol-identifier,
              br21-protocol-identifier,
              br21-protocol-identifier,
              br21-protocol-identifier,
              br21-interface 
            }
    STATUS current
    DESCRIPTION
        "Notification of Event BR.21

        Message: 'Source-routed frame from $1 to $2, IEEE 802 SNAP Protocol Identifier $3-$4-$5-$6-$7 filtered, dropped, interface $8'

        Parameters list:
              $1: br21-source-mac
              $2: br21-dest-mac
              $3: br21-protocol-identifier
              $4: br21-protocol-identifier
              $5: br21-protocol-identifier
              $6: br21-protocol-identifier
              $7: br21-protocol-identifier
              $8: br21-interface

        A source-routed frame has been received for the specified IEEE 802
        Subnetwork Access Protocol (SNAP) Protocol Identifier (PID), but
        this PID is being administratively filtered by the bridge. The frame
        will be dropped."
    ::= { brNotificationsPrefix 21 }

brNotification22 NOTIFICATION-TYPE
    OBJECTS { 
              br22-source-mac, 
              br22-dest-mac,
              br22-protocol-identifier,
              br22-protocol-identifier,
              br22-protocol-identifier,
              br22-protocol-identifier,
              br22-protocol-identifier,
              br22-interface 
            }
    STATUS current
    DESCRIPTION
        "Notification of Event BR.22

        Message: 'Source-routed frame from $1 to unregistered destination MAC address $2, IEEE 802 SNAP Protocol Identifier $3-$4-$5-$6-$7, dropped, interface $8'

        Parameters list:
              $1: br22-source-mac
              $2: br22-dest-mac
              $3: br22-protocol-identifier
              $4: br22-protocol-identifier
              $5: br22-protocol-identifier
              $6: br22-protocol-identifier
              $7: br22-protocol-identifier
              $8: br22-interface

        A source-routed frame has been received for the IEEE 802 Subnetwork
        Access Protocol (SNAP) Protocol Identifier (PID) which corresponds with
        an enabled protocol, but the destination MAC address is not registered
        in the bridge. The frame will be dropped."
    ::= { brNotificationsPrefix 22 }

brNotification23 NOTIFICATION-TYPE
    OBJECTS { 
              br23-source-mac, 
              br23-dest-mac,
              br23-protocol-identifier,
              br23-protocol-identifier,
              br23-protocol-identifier,
              br23-protocol-identifier,
              br23-protocol-identifier,
              br23-interface 
            }
    STATUS current
    DESCRIPTION
        "Notification of Event BR.23

        Message: 'Source-routed frame from $1 to $2 IEEE 802 SNAP Protocol Identifier $3-$4-$5-$6-$7 for endnode protocol, interface $8'

        Parameters list:
              $1: br23-source-mac
              $2: br23-dest-mac
              $3: br23-protocol-identifier
              $4: br23-protocol-identifier
              $5: br23-protocol-identifier
              $6: br23-protocol-identifier
              $7: br23-protocol-identifier
              $8: br23-interface

        SA source-routed multicast frame has been received for the IEEE 802
        Subnetwork Access Protocol (SNAP) Protocol Identifier (PID) which
        corresponds with an endnode protocol. The frame will be both bridged
        and locally processed by the endnode protocol."
    ::= { brNotificationsPrefix 23 }

brNotification24 NOTIFICATION-TYPE
    OBJECTS { 
              br24-vlan-id, 
              br24-interface 
            }
    STATUS current
    DESCRIPTION
        "Notification of Event BR.24

        Message: 'VLAN vid $1 not supported. Frame discarded, interface $2'

        Parameters list:
              $1: br24-vlan-id
              $2: br24-interface

        A vlan frame has been received whose virtual lan id is not supported.
        Frame is dropped."
    ::= { brNotificationsPrefix 24 }

brNotification25 NOTIFICATION-TYPE
    STATUS current
    DESCRIPTION
        "Notification of Event BR.25

        Message: '---'

        Reserved for possible future use."
    ::= { brNotificationsPrefix 25 }

brNotification26 NOTIFICATION-TYPE
    OBJECTS { 
              br26-source-mac, 
              br26-dest-mac,
              br26-interface 
            }
    STATUS current
    DESCRIPTION
        "Notification of Event BR.26

        Message: 'Frame from $1 to $2 dropped, destination address filtered, interface $3'

        Parameters list:
              $1: br26-source-mac
              $2: br26-dest-mac
              $3: br26-interface

        A source-routed MAC frame has been received by the hardware, but
        is being dropped because the destination MAC address is being
        administratively filtered by the bridge. The frame will be dropped."
    ::= { brNotificationsPrefix 26 }

brNotification27 NOTIFICATION-TYPE
    OBJECTS { 
              br27-source-mac, 
              br27-dest-mac,
              br27-interface 
            }
    STATUS current
    DESCRIPTION
        "Notification of Event BR.27

        Message: 'Frame from $1 to $2 dropped, source address filtered, interface $3'

        Parameters list:
              $1: br27-source-mac
              $2: br27-dest-mac
              $3: br27-interface

        A source-routed MAC frame has been received by the hardware, but
        is being dropped because the source MAC address is being
        administratively filtered by the bridge. The frame will be dropped."
    ::= { brNotificationsPrefix 27 }

brNotification28 NOTIFICATION-TYPE
    OBJECTS { 
              br28-source-mac, 
              br28-dest-mac,
              br28-interface 
            }
    STATUS current
    DESCRIPTION
        "Notification of Event BR.28

        Message: 'No buffer to copy packet for endnode bridge and process, from $1 to $2, interface $3 not bridged'

        Parameters list:
              $1: br28-source-mac
              $2: br28-dest-mac
              $3: br28-interface

        A multicast frame has been received for an endnode protocol that is
        both bridged and locally processed. There was no buffer to make
        two copies of the frame for both types of processing, so it will not be
        bridged, only locally processed."
    ::= { brNotificationsPrefix 28 }

brNotification29 NOTIFICATION-TYPE
    OBJECTS { 
              br29-source-mac, 
              br29-dest-mac,
              br29-port,
              br29-interface 
            }
    STATUS current
    DESCRIPTION
        "Notification of Event BR.29

        Message: 'NETBIOS Input Packet Filtered - $1->$2, port $3, interface $4'

        Parameters list:
              $1: br29-source-mac
              $2: br29-dest-mac
              $3: br29-port
              $4: br29-interface

        A NETBIOS packet has matched the criteria specified in a NETBIOS Filter
        configuration record. The packet is dropped."
    ::= { brNotificationsPrefix 29 }

brNotification30 NOTIFICATION-TYPE
    OBJECTS { 
              br30-interface, 
              br30-new-mac 
            }
    STATUS current
    DESCRIPTION
        "Notification of Event BR.30

        Message: 'Updated MAC address for interface $1: $2'

        Parameters list:
              $1: br30-interface
              $2: br30-new-mac

        The MAC address of a BVI interface has been updated"
    ::= { brNotificationsPrefix 30 }

brNotification31 NOTIFICATION-TYPE
    OBJECTS { 
              br31-interface, 
              br31-source-mac,
              br31-dest-mac,
              br31-protocol 
            }
    STATUS current
    DESCRIPTION
        "Notification of Event BR.31

        Message: 'Interface $1 sends a frame from $2 to $3, protocol $4'

        Parameters list:
              $1: br31-interface
              $2: br31-source-mac
              $3: br31-dest-mac
              $4: br31-protocol

        A frame is going to be output to the bridge through a BVI interface."
    ::= { brNotificationsPrefix 31 }

brNotification32 NOTIFICATION-TYPE
    OBJECTS { 
              br32-interface, 
              br32-source-mac,
              br32-dest-mac,
              br32-protocol 
            }
    STATUS current
    DESCRIPTION
        "Notification of Event BR.32

        Message: 'Interface $1 has received a frame from $2 to $3, protocol $4'

        Parameters list:
              $1: br32-interface
              $2: br32-source-mac
              $3: br32-dest-mac
              $4: br32-protocol

        A frame has been received in a BVI interface."
    ::= { brNotificationsPrefix 32 }

brNotification33 NOTIFICATION-TYPE
    OBJECTS { 
              br33-interface 
            }
    STATUS current
    DESCRIPTION
        "Notification of Event BR.33

        Message: 'Interface $1 drops frame because interface is down'

        Parameters list:
              $1: br33-interface

        A frame is droped because BVI interface is down"
    ::= { brNotificationsPrefix 33 }

brNotification34 NOTIFICATION-TYPE
    OBJECTS { 
              br34-interface, 
              br34-source-mac,
              br34-dest-IP-address 
            }
    STATUS current
    DESCRIPTION
        "Notification of Event BR.34

        Message: 'Interface $1 sends a frame from $2 to $3, protocol IP'

        Parameters list:
              $1: br34-interface
              $2: br34-source-mac
              $3: br34-dest-IP-address

        A frame is dropped because destination IP has no registered MAC address."
    ::= { brNotificationsPrefix 34 }

brNotification35 NOTIFICATION-TYPE
    OBJECTS { 
              br35-interface, 
              br35-protocol 
            }
    STATUS current
    DESCRIPTION
        "Notification of Event BR.35

        Message: 'Interface $1 drops frame because protocol $2 is unhandled'

        Parameters list:
              $1: br35-interface
              $2: br35-protocol

        A frame is droped because BVI interface has no protocol handler"
    ::= { brNotificationsPrefix 35 }

brNotification36 NOTIFICATION-TYPE
    OBJECTS { 
              br36-source-mac, 
              br36-dest-mac,
              br36-protocol-identifier,
              br36-protocol-identifier,
              br36-protocol-identifier,
              br36-protocol-identifier,
              br36-protocol-identifier,
              br36-interface 
            }
    STATUS current
    DESCRIPTION
        "Notification of Event BR.36

        Message: 'Frame from $1 to $2, IEEE 802 SNAP Protocol Identifier $3-$4-$5-$6-$7 not handled, dropped, interface $8'

        Parameters list:
              $1: br36-source-mac
              $2: br36-dest-mac
              $3: br36-protocol-identifier
              $4: br36-protocol-identifier
              $5: br36-protocol-identifier
              $6: br36-protocol-identifier
              $7: br36-protocol-identifier
              $8: br36-interface

        A frame has been received for the specified IEEE 802 Subnetwork Access
        Protocol (SNAP) Protocol Identifier (PID), but this PID has no
        forwarder or endnode support. The frame will be dropped."
    ::= { brNotificationsPrefix 36 }

brNotification37 NOTIFICATION-TYPE
    OBJECTS { 
              br37-source-mac, 
              br37-dest-mac,
              br37-protocol-identifier,
              br37-protocol-identifier,
              br37-protocol-identifier,
              br37-protocol-identifier,
              br37-protocol-identifier,
              br37-interface 
            }
    STATUS current
    DESCRIPTION
        "Notification of Event BR.37

        Message: 'Frame from $1 to $2, IEEE 802 SNAP Protocol Identifier $3-$4-$5-$6-$7 dropped, interface $8'

        Parameters list:
              $1: br37-source-mac
              $2: br37-dest-mac
              $3: br37-protocol-identifier
              $4: br37-protocol-identifier
              $5: br37-protocol-identifier
              $6: br37-protocol-identifier
              $7: br37-protocol-identifier
              $8: br37-interface

        A frame has been received for the specified IEEE 802 Subnetwork Access
        Protocol (SNAP) Protocol Identifier (PID), but this PID has no
        enabled bridging nor routing. The frame will be dropped."
    ::= { brNotificationsPrefix 37 }

brNotification38 NOTIFICATION-TYPE
    OBJECTS { 
              br38-source-mac, 
              br38-dest-mac,
              br38-destination-service-access-point,
              br38-interface 
            }
    STATUS current
    DESCRIPTION
        "Notification of Event BR.38

        Message: 'Frame from $1 to $2, IEEE 802.2 DSAP $3 not handled, dropped, interface $4'

        Parameters list:
              $1: br38-source-mac
              $2: br38-dest-mac
              $3: br38-destination-service-access-point
              $4: br38-interface

        A frame has been received for the specified IEEE 802.2 Destination
        Service Access Point (DSAP), but this DSAP has no forwarder or
        endnode support. The frame will be dropped."
    ::= { brNotificationsPrefix 38 }

brNotification39 NOTIFICATION-TYPE
    OBJECTS { 
              br39-source-mac, 
              br39-dest-mac,
              br39-destination-service-access-point,
              br39-interface 
            }
    STATUS current
    DESCRIPTION
        "Notification of Event BR.39

        Message: 'Frame from $1 to $2, IEEE 802.2 DSAP $3, dropped, interface $4'

        Parameters list:
              $1: br39-source-mac
              $2: br39-dest-mac
              $3: br39-destination-service-access-point
              $4: br39-interface

        A frame has been received for the specified IEEE 802.2 Destination
        Service Access Point (DSAP), but this DSAP has no enabled
        bridging nor routing. The frame will be dropped."
    ::= { brNotificationsPrefix 39 }

brNotification40 NOTIFICATION-TYPE
    OBJECTS { 
              br40-source-mac, 
              br40-dest-mac,
              br40-Ethernet-type,
              br40-interface 
            }
    STATUS current
    DESCRIPTION
        "Notification of Event BR.40

        Message: 'Frame from $1 to $2, Ethernet type $3 not handled, dropped, interface $4'

        Parameters list:
              $1: br40-source-mac
              $2: br40-dest-mac
              $3: br40-Ethernet-type
              $4: br40-interface

        A frame has been received for the specified Ethernet type, but this type
        has no forwarder or endnode support. The frame will be
        dropped."
    ::= { brNotificationsPrefix 40 }

brNotification41 NOTIFICATION-TYPE
    OBJECTS { 
              br41-source-mac, 
              br41-dest-mac,
              br41-Ethernet-type,
              br41-interface 
            }
    STATUS current
    DESCRIPTION
        "Notification of Event BR.41

        Message: 'Frame from $1 to $2, Ethernet type $3 dropped, interface $4'

        Parameters list:
              $1: br41-source-mac
              $2: br41-dest-mac
              $3: br41-Ethernet-type
              $4: br41-interface

        A frame has been received for the specified Ethernet type, but this type
        has no enabled bridging nor routing. The frame will be
        dropped."
    ::= { brNotificationsPrefix 41 }

brNotification42 NOTIFICATION-TYPE
    OBJECTS { 
              br42-source-mac, 
              br42-dest-mac,
              br42-destination-service-access-point,
              br42-interface 
            }
    STATUS current
    DESCRIPTION
        "Notification of Event BR.42

        Message: 'Source-routed frame from $1 to $2, IEEE 802.2 DSAP $3 dropped, interface $4'

        Parameters list:
              $1: br42-source-mac
              $2: br42-dest-mac
              $3: br42-destination-service-access-point
              $4: br42-interface

        A source-routed frame has been received for the specified IEEE 802.2
        Destination Service Access Point (DSAP), but this DSAP has no enabled
        bridging nor routing. The frame will be dropped."
    ::= { brNotificationsPrefix 42 }

brNotification43 NOTIFICATION-TYPE
    OBJECTS { 
              br43-source-mac, 
              br43-dest-mac,
              br43-protocol-identifier,
              br43-protocol-identifier,
              br43-protocol-identifier,
              br43-protocol-identifier,
              br43-protocol-identifier,
              br43-interface 
            }
    STATUS current
    DESCRIPTION
        "Notification of Event BR.43

        Message: 'Source-routed frame from $1 to $2, IEEE 802 SNAP Protocol Identifier $3-$4-$5-$6-$7 dropped, interface $8'

        Parameters list:
              $1: br43-source-mac
              $2: br43-dest-mac
              $3: br43-protocol-identifier
              $4: br43-protocol-identifier
              $5: br43-protocol-identifier
              $6: br43-protocol-identifier
              $7: br43-protocol-identifier
              $8: br43-interface

        A source-routed frame has been received for the specified IEEE 802
        Subnetwork Access Protocol (SNAP) Protocol Identifier (PID), but
        this PID has no enabled bridging nor routing. The frame
        will be dropped."
    ::= { brNotificationsPrefix 43 }

brNotification44 NOTIFICATION-TYPE
    OBJECTS { 
              br44-source-mac, 
              br44-dest-mac,
              br44-interface 
            }
    STATUS current
    DESCRIPTION
        "Notification of Event BR.44

        Message: 'Frame from $1 to $2, with VID FFF dropped, interface $3'

        Parameters list:
              $1: br44-source-mac
              $2: br44-dest-mac
              $3: br44-interface

        A frame has been received with vlan identifier FFF. This
        frame will be dropped."
    ::= { brNotificationsPrefix 44 }

brNotification45 NOTIFICATION-TYPE
    OBJECTS { 
              br45-source-mac, 
              br45-dest-mac,
              br45-interface 
            }
    STATUS current
    DESCRIPTION
        "Notification of Event BR.45

        Message: 'Frame without vlan tag from $1 to $2, dropped, interface $3'

        Parameters list:
              $1: br45-source-mac
              $2: br45-dest-mac
              $3: br45-interface

        A frame has been received with no vlan tag and port
        is configured to accept only tagged frames. This frame will be dropped."
    ::= { brNotificationsPrefix 45 }

brNotification46 NOTIFICATION-TYPE
    OBJECTS { 
              br46-source-mac, 
              br46-dest-mac,
              br46-vlan-id,
              br46-interface 
            }
    STATUS current
    DESCRIPTION
        "Notification of Event BR.46

        Message: 'Frame dropped from $1 to $2, vlan ID $3, ingress not enabled on interface $4'

        Parameters list:
              $1: br46-source-mac
              $2: br46-dest-mac
              $3: br46-vlan-id
              $4: br46-interface

        A frame has been received, but its VLAN ID is not ingress enabled in the
        the port bridge. The frame will be dropped."
    ::= { brNotificationsPrefix 46 }

brNotification47 NOTIFICATION-TYPE
    OBJECTS { 
              br47-source-mac, 
              br47-dest-mac,
              br47-vlan-id,
              br47-interface 
            }
    STATUS current
    DESCRIPTION
        "Notification of Event BR.47

        Message: 'Frame dropped from $1 to $2, vlan ID $3 egress not enabled on interface $4'

        Parameters list:
              $1: br47-source-mac
              $2: br47-dest-mac
              $3: br47-vlan-id
              $4: br47-interface

        A frame has been received, but its VLAN ID is not egress enabled in the
        the port bridge. The frame will be dropped."
    ::= { brNotificationsPrefix 47 }

brNotification48 NOTIFICATION-TYPE
    OBJECTS { 
              br48-source-mac, 
              br48-dest-mac,
              br48-vlan-id,
              br48-interface 
            }
    STATUS current
    DESCRIPTION
        "Notification of Event BR.48

        Message: 'Frame dropped from $1 to $2, vlan ID $3 egress filt, not active on interface $4'

        Parameters list:
              $1: br48-source-mac
              $2: br48-dest-mac
              $3: br48-vlan-id
              $4: br48-interface

        A frame has been received, but its VLAN ID is not active in the
        this port bridge. The frame will be dropped."
    ::= { brNotificationsPrefix 48 }


END
