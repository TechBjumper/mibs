-- file automatically created


TELDAT-TRAP-VOIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


voipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the VOIP event subsystem."
    REVISION "201401200930Z"
    DESCRIPTION "Initial implementation"
        ::= { telEventTraps 174 }


voipEventsGroup	OBJECT IDENTIFIER	::= { voipTrapsMIB 1 }

voipNotifications	OBJECT IDENTIFIER	::= { voipTrapsMIB 2 }
voipNotificationsPrefix	OBJECT IDENTIFIER	::= { voipNotifications 0 }

voipEventObjects1 OBJECT-IDENTITY
    STATUS current
    DESCRIPTION
        "Event VOIP.1
        Report actions, status and error related to VoIP initialization process."
    ::= { voipEventsGroup 1 }

voip1-text OBJECT-TYPE
    SYNTAX DisplayString
    MAX-ACCESS accessible-for-notify
    STATUS current
    DESCRIPTION
        "Parameter 'text' in event VOIP.1"
    ::= { voipEventObjects1 1 }

voipEventObjects2 OBJECT-IDENTITY
    STATUS current
    DESCRIPTION
        "Event VOIP.2
        Report actions, status and error related to a VoIP card placed in interface."
    ::= { voipEventsGroup 2 }

voip2-text OBJECT-TYPE
    SYNTAX DisplayString
    MAX-ACCESS accessible-for-notify
    STATUS current
    DESCRIPTION
        "Parameter 'text' in event VOIP.2"
    ::= { voipEventObjects2 1 }

voip2-interface OBJECT-TYPE
    SYNTAX DisplayString
    MAX-ACCESS accessible-for-notify
    STATUS current
    DESCRIPTION
        "Parameter 'interface' in event VOIP.2"
    ::= { voipEventObjects2 2 }

voipEventObjects3 OBJECT-IDENTITY
    STATUS current
    DESCRIPTION
        "Event VOIP.3
        An event has been received on indicated interface and line."
    ::= { voipEventsGroup 3 }

voip3-Event OBJECT-TYPE
    SYNTAX DisplayString
    MAX-ACCESS accessible-for-notify
    STATUS current
    DESCRIPTION
        "Parameter 'Event' in event VOIP.3"
    ::= { voipEventObjects3 1 }

voip3-parameter OBJECT-TYPE
    SYNTAX DisplayString
    MAX-ACCESS accessible-for-notify
    STATUS current
    DESCRIPTION
        "Parameter 'parameter' in event VOIP.3"
    ::= { voipEventObjects3 2 }

voip3-interface OBJECT-TYPE
    SYNTAX DisplayString
    MAX-ACCESS accessible-for-notify
    STATUS current
    DESCRIPTION
        "Parameter 'interface' in event VOIP.3"
    ::= { voipEventObjects3 3 }

voip3-line OBJECT-TYPE
    SYNTAX Integer32
    MAX-ACCESS accessible-for-notify
    STATUS current
    DESCRIPTION
        "Parameter 'line' in event VOIP.3"
    ::= { voipEventObjects3 4 }

voipEventObjects4 OBJECT-IDENTITY
    STATUS current
    DESCRIPTION
        "Event VOIP.4
        Line state has changed."
    ::= { voipEventsGroup 4 }

voip4-Event OBJECT-TYPE
    SYNTAX DisplayString
    MAX-ACCESS accessible-for-notify
    STATUS current
    DESCRIPTION
        "Parameter 'Event' in event VOIP.4"
    ::= { voipEventObjects4 1 }

voip4-interface OBJECT-TYPE
    SYNTAX DisplayString
    MAX-ACCESS accessible-for-notify
    STATUS current
    DESCRIPTION
        "Parameter 'interface' in event VOIP.4"
    ::= { voipEventObjects4 2 }

voip4-line OBJECT-TYPE
    SYNTAX Integer32
    MAX-ACCESS accessible-for-notify
    STATUS current
    DESCRIPTION
        "Parameter 'line' in event VOIP.4"
    ::= { voipEventObjects4 3 }

voipEventObjects5 OBJECT-IDENTITY
    STATUS current
    DESCRIPTION
        "Event VOIP.5
        Frequently Time Out Events."
    ::= { voipEventsGroup 5 }

voip5-Type OBJECT-TYPE
    SYNTAX DisplayString
    MAX-ACCESS accessible-for-notify
    STATUS current
    DESCRIPTION
        "Parameter 'Type' in event VOIP.5"
    ::= { voipEventObjects5 1 }

voip5-Reason OBJECT-TYPE
    SYNTAX DisplayString
    MAX-ACCESS accessible-for-notify
    STATUS current
    DESCRIPTION
        "Parameter 'Reason' in event VOIP.5"
    ::= { voipEventObjects5 2 }

voip5-interface OBJECT-TYPE
    SYNTAX DisplayString
    MAX-ACCESS accessible-for-notify
    STATUS current
    DESCRIPTION
        "Parameter 'interface' in event VOIP.5"
    ::= { voipEventObjects5 3 }

voip5-line OBJECT-TYPE
    SYNTAX Integer32
    MAX-ACCESS accessible-for-notify
    STATUS current
    DESCRIPTION
        "Parameter 'line' in event VOIP.5"
    ::= { voipEventObjects5 4 }

voipEventObjects6 OBJECT-IDENTITY
    STATUS current
    DESCRIPTION
        "Event VOIP.6
        Unfrequently Time Out Events."
    ::= { voipEventsGroup 6 }

voip6-Type OBJECT-TYPE
    SYNTAX DisplayString
    MAX-ACCESS accessible-for-notify
    STATUS current
    DESCRIPTION
        "Parameter 'Type' in event VOIP.6"
    ::= { voipEventObjects6 1 }

voip6-Reason OBJECT-TYPE
    SYNTAX DisplayString
    MAX-ACCESS accessible-for-notify
    STATUS current
    DESCRIPTION
        "Parameter 'Reason' in event VOIP.6"
    ::= { voipEventObjects6 2 }

voip6-interface OBJECT-TYPE
    SYNTAX DisplayString
    MAX-ACCESS accessible-for-notify
    STATUS current
    DESCRIPTION
        "Parameter 'interface' in event VOIP.6"
    ::= { voipEventObjects6 3 }

voip6-line OBJECT-TYPE
    SYNTAX Integer32
    MAX-ACCESS accessible-for-notify
    STATUS current
    DESCRIPTION
        "Parameter 'line' in event VOIP.6"
    ::= { voipEventObjects6 4 }

voipEventObjects7 OBJECT-IDENTITY
    STATUS current
    DESCRIPTION
        "Event VOIP.7
        Report E&M actions, status and error."
    ::= { voipEventsGroup 7 }

voip7-text OBJECT-TYPE
    SYNTAX DisplayString
    MAX-ACCESS accessible-for-notify
    STATUS current
    DESCRIPTION
        "Parameter 'text' in event VOIP.7"
    ::= { voipEventObjects7 1 }

voip7-interface OBJECT-TYPE
    SYNTAX DisplayString
    MAX-ACCESS accessible-for-notify
    STATUS current
    DESCRIPTION
        "Parameter 'interface' in event VOIP.7"
    ::= { voipEventObjects7 2 }

voip7-line OBJECT-TYPE
    SYNTAX Integer32
    MAX-ACCESS accessible-for-notify
    STATUS current
    DESCRIPTION
        "Parameter 'line' in event VOIP.7"
    ::= { voipEventObjects7 3 }

voipEventObjects8 OBJECT-IDENTITY
    STATUS current
    DESCRIPTION
        "Event VOIP.8
        Report PBX service related events, status and error."
    ::= { voipEventsGroup 8 }

voip8-description OBJECT-TYPE
    SYNTAX DisplayString
    MAX-ACCESS accessible-for-notify
    STATUS current
    DESCRIPTION
        "Parameter 'description' in event VOIP.8"
    ::= { voipEventObjects8 1 }

voip8-number OBJECT-TYPE
    SYNTAX DisplayString
    MAX-ACCESS accessible-for-notify
    STATUS current
    DESCRIPTION
        "Parameter 'number' in event VOIP.8"
    ::= { voipEventObjects8 2 }

voip8-interface OBJECT-TYPE
    SYNTAX DisplayString
    MAX-ACCESS accessible-for-notify
    STATUS current
    DESCRIPTION
        "Parameter 'interface' in event VOIP.8"
    ::= { voipEventObjects8 3 }

voip8-line OBJECT-TYPE
    SYNTAX Integer32
    MAX-ACCESS accessible-for-notify
    STATUS current
    DESCRIPTION
        "Parameter 'line' in event VOIP.8"
    ::= { voipEventObjects8 4 }

voipEventObjects9 OBJECT-IDENTITY
    STATUS current
    DESCRIPTION
        "Event VOIP.9
        Report NSLA related events, status and error."
    ::= { voipEventsGroup 9 }

voip9-description OBJECT-TYPE
    SYNTAX DisplayString
    MAX-ACCESS accessible-for-notify
    STATUS current
    DESCRIPTION
        "Parameter 'description' in event VOIP.9"
    ::= { voipEventObjects9 1 }

voip9-item OBJECT-TYPE
    SYNTAX DisplayString
    MAX-ACCESS accessible-for-notify
    STATUS current
    DESCRIPTION
        "Parameter 'item' in event VOIP.9"
    ::= { voipEventObjects9 2 }

voip9-active OBJECT-TYPE
    SYNTAX DisplayString
    MAX-ACCESS accessible-for-notify
    STATUS current
    DESCRIPTION
        "Parameter 'active' in event VOIP.9"
    ::= { voipEventObjects9 3 }

voipEventObjects10 OBJECT-IDENTITY
    STATUS current
    DESCRIPTION
        "Event VOIP.10
        Report ISDN/cellular command"
    ::= { voipEventsGroup 10 }

voip10-command OBJECT-TYPE
    SYNTAX DisplayString
    MAX-ACCESS accessible-for-notify
    STATUS current
    DESCRIPTION
        "Parameter 'command' in event VOIP.10"
    ::= { voipEventObjects10 1 }

voip10-interface OBJECT-TYPE
    SYNTAX DisplayString
    MAX-ACCESS accessible-for-notify
    STATUS current
    DESCRIPTION
        "Parameter 'interface' in event VOIP.10"
    ::= { voipEventObjects10 2 }

voip10-line OBJECT-TYPE
    SYNTAX Integer32
    MAX-ACCESS accessible-for-notify
    STATUS current
    DESCRIPTION
        "Parameter 'line' in event VOIP.10"
    ::= { voipEventObjects10 3 }

voipEventObjects11 OBJECT-IDENTITY
    STATUS current
    DESCRIPTION
        "Event VOIP.11
        Report ISDN/cellular events"
    ::= { voipEventsGroup 11 }

voip11-event OBJECT-TYPE
    SYNTAX DisplayString
    MAX-ACCESS accessible-for-notify
    STATUS current
    DESCRIPTION
        "Parameter 'event' in event VOIP.11"
    ::= { voipEventObjects11 1 }

voip11-interface OBJECT-TYPE
    SYNTAX DisplayString
    MAX-ACCESS accessible-for-notify
    STATUS current
    DESCRIPTION
        "Parameter 'interface' in event VOIP.11"
    ::= { voipEventObjects11 2 }

voip11-line OBJECT-TYPE
    SYNTAX Integer32
    MAX-ACCESS accessible-for-notify
    STATUS current
    DESCRIPTION
        "Parameter 'line' in event VOIP.11"
    ::= { voipEventObjects11 3 }

voipEventObjects12 OBJECT-IDENTITY
    STATUS current
    DESCRIPTION
        "Event VOIP.12
        Report ISDN/cellular status and error"
    ::= { voipEventsGroup 12 }

voip12-str OBJECT-TYPE
    SYNTAX DisplayString
    MAX-ACCESS accessible-for-notify
    STATUS current
    DESCRIPTION
        "Parameter 'str' in event VOIP.12"
    ::= { voipEventObjects12 1 }

voip12-interface OBJECT-TYPE
    SYNTAX DisplayString
    MAX-ACCESS accessible-for-notify
    STATUS current
    DESCRIPTION
        "Parameter 'interface' in event VOIP.12"
    ::= { voipEventObjects12 2 }

voip12-line OBJECT-TYPE
    SYNTAX Integer32
    MAX-ACCESS accessible-for-notify
    STATUS current
    DESCRIPTION
        "Parameter 'line' in event VOIP.12"
    ::= { voipEventObjects12 3 }

voipEventObjects13 OBJECT-IDENTITY
    STATUS current
    DESCRIPTION
        "Event VOIP.13
        Report voip errors"
    ::= { voipEventsGroup 13 }

voip13-str OBJECT-TYPE
    SYNTAX DisplayString
    MAX-ACCESS accessible-for-notify
    STATUS current
    DESCRIPTION
        "Parameter 'str' in event VOIP.13"
    ::= { voipEventObjects13 1 }

voip13-interface OBJECT-TYPE
    SYNTAX DisplayString
    MAX-ACCESS accessible-for-notify
    STATUS current
    DESCRIPTION
        "Parameter 'interface' in event VOIP.13"
    ::= { voipEventObjects13 2 }

voip13-line OBJECT-TYPE
    SYNTAX Integer32
    MAX-ACCESS accessible-for-notify
    STATUS current
    DESCRIPTION
        "Parameter 'line' in event VOIP.13"
    ::= { voipEventObjects13 3 }

voipEventObjects14 OBJECT-IDENTITY
    STATUS current
    DESCRIPTION
        "Event VOIP.14
        Report events related to voice messages"
    ::= { voipEventsGroup 14 }

voip14-loc-index OBJECT-TYPE
    SYNTAX Integer32
    MAX-ACCESS accessible-for-notify
    STATUS current
    DESCRIPTION
        "Parameter 'loc-index' in event VOIP.14"
    ::= { voipEventObjects14 1 }

voip14-event OBJECT-TYPE
    SYNTAX DisplayString
    MAX-ACCESS accessible-for-notify
    STATUS current
    DESCRIPTION
        "Parameter 'event' in event VOIP.14"
    ::= { voipEventObjects14 2 }


voipNotification1 NOTIFICATION-TYPE
    OBJECTS { 
              voip1-text 
            }
    STATUS current
    DESCRIPTION
        "Notification of Event VOIP.1

        Message: 'Report $1'

        Parameters list:
              $1: voip1-text

        Report actions, status and error related to VoIP initialization process."
    ::= { voipNotificationsPrefix 1 }

voipNotification2 NOTIFICATION-TYPE
    OBJECTS { 
              voip2-text, 
              voip2-interface 
            }
    STATUS current
    DESCRIPTION
        "Notification of Event VOIP.2

        Message: 'Error $1 ifc $2'

        Parameters list:
              $1: voip2-text
              $2: voip2-interface

        Report actions, status and error related to a VoIP card placed in interface."
    ::= { voipNotificationsPrefix 2 }

voipNotification3 NOTIFICATION-TYPE
    OBJECTS { 
              voip3-Event, 
              voip3-parameter,
              voip3-interface,
              voip3-line 
            }
    STATUS current
    DESCRIPTION
        "Notification of Event VOIP.3

        Message: 'Event: $1 $2 line $3-$4'

        Parameters list:
              $1: voip3-Event
              $2: voip3-parameter
              $3: voip3-interface
              $4: voip3-line

        An event has been received on indicated interface and line."
    ::= { voipNotificationsPrefix 3 }

voipNotification4 NOTIFICATION-TYPE
    OBJECTS { 
              voip4-Event, 
              voip4-interface,
              voip4-line 
            }
    STATUS current
    DESCRIPTION
        "Notification of Event VOIP.4

        Message: 'State terminal changed to $1 line $2-$3'

        Parameters list:
              $1: voip4-Event
              $2: voip4-interface
              $3: voip4-line

        Line state has changed."
    ::= { voipNotificationsPrefix 4 }

voipNotification5 NOTIFICATION-TYPE
    OBJECTS { 
              voip5-Type, 
              voip5-Reason,
              voip5-interface,
              voip5-line 
            }
    STATUS current
    DESCRIPTION
        "Notification of Event VOIP.5

        Message: 'Time Out (type: $1 by $2) ln $3-$4'

        Parameters list:
              $1: voip5-Type
              $2: voip5-Reason
              $3: voip5-interface
              $4: voip5-line

        Frequently Time Out Events."
    ::= { voipNotificationsPrefix 5 }

voipNotification6 NOTIFICATION-TYPE
    OBJECTS { 
              voip6-Type, 
              voip6-Reason,
              voip6-interface,
              voip6-line 
            }
    STATUS current
    DESCRIPTION
        "Notification of Event VOIP.6

        Message: 'Time Out (typ: $1 by $2) line $3-$4'

        Parameters list:
              $1: voip6-Type
              $2: voip6-Reason
              $3: voip6-interface
              $4: voip6-line

        Unfrequently Time Out Events."
    ::= { voipNotificationsPrefix 6 }

voipNotification7 NOTIFICATION-TYPE
    OBJECTS { 
              voip7-text, 
              voip7-interface,
              voip7-line 
            }
    STATUS current
    DESCRIPTION
        "Notification of Event VOIP.7

        Message: 'E&M: $1 line $2-$3'

        Parameters list:
              $1: voip7-text
              $2: voip7-interface
              $3: voip7-line

        Report E&M actions, status and error."
    ::= { voipNotificationsPrefix 7 }

voipNotification8 NOTIFICATION-TYPE
    OBJECTS { 
              voip8-description, 
              voip8-number,
              voip8-interface,
              voip8-line 
            }
    STATUS current
    DESCRIPTION
        "Notification of Event VOIP.8

        Message: 'PBX: $1 $2 line $3-$4'

        Parameters list:
              $1: voip8-description
              $2: voip8-number
              $3: voip8-interface
              $4: voip8-line

        Report PBX service related events, status and error."
    ::= { voipNotificationsPrefix 8 }

voipNotification9 NOTIFICATION-TYPE
    OBJECTS { 
              voip9-description, 
              voip9-item,
              voip9-active 
            }
    STATUS current
    DESCRIPTION
        "Notification of Event VOIP.9

        Message: 'NSLA: $1 $2 $3'

        Parameters list:
              $1: voip9-description
              $2: voip9-item
              $3: voip9-active

        Report NSLA related events, status and error."
    ::= { voipNotificationsPrefix 9 }

voipNotification10 NOTIFICATION-TYPE
    OBJECTS { 
              voip10-command, 
              voip10-interface,
              voip10-line 
            }
    STATUS current
    DESCRIPTION
        "Notification of Event VOIP.10

        Message: 'DIAL: command $1 line $2-$3'

        Parameters list:
              $1: voip10-command
              $2: voip10-interface
              $3: voip10-line

        Report ISDN/cellular command"
    ::= { voipNotificationsPrefix 10 }

voipNotification11 NOTIFICATION-TYPE
    OBJECTS { 
              voip11-event, 
              voip11-interface,
              voip11-line 
            }
    STATUS current
    DESCRIPTION
        "Notification of Event VOIP.11

        Message: 'DIAL: event $1 line $2-$3'

        Parameters list:
              $1: voip11-event
              $2: voip11-interface
              $3: voip11-line

        Report ISDN/cellular events"
    ::= { voipNotificationsPrefix 11 }

voipNotification12 NOTIFICATION-TYPE
    OBJECTS { 
              voip12-str, 
              voip12-interface,
              voip12-line 
            }
    STATUS current
    DESCRIPTION
        "Notification of Event VOIP.12

        Message: 'DIAL: $1 line $2-$3'

        Parameters list:
              $1: voip12-str
              $2: voip12-interface
              $3: voip12-line

        Report ISDN/cellular status and error"
    ::= { voipNotificationsPrefix 12 }

voipNotification13 NOTIFICATION-TYPE
    OBJECTS { 
              voip13-str, 
              voip13-interface,
              voip13-line 
            }
    STATUS current
    DESCRIPTION
        "Notification of Event VOIP.13

        Message: 'Error: $1 line $2-$3'

        Parameters list:
              $1: voip13-str
              $2: voip13-interface
              $3: voip13-line

        Report voip errors"
    ::= { voipNotificationsPrefix 13 }

voipNotification14 NOTIFICATION-TYPE
    OBJECTS { 
              voip14-loc-index, 
              voip14-event 
            }
    STATUS current
    DESCRIPTION
        "Notification of Event VOIP.14

        Message: 'Voice message $1: $2'

        Parameters list:
              $1: voip14-loc-index
              $2: voip14-event

        Report events related to voice messages"
    ::= { voipNotificationsPrefix 14 }


END
