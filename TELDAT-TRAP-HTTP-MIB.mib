-- file automatically created


TELDAT-TRAP-HTTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


httpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the HTTP event subsystem."
    REVISION "201401200930Z"
    DESCRIPTION "Initial implementation"
        ::= { telEventTraps 142 }


httpEventsGroup	OBJECT IDENTIFIER	::= { httpTrapsMIB 1 }

httpNotifications	OBJECT IDENTIFIER	::= { httpTrapsMIB 2 }
httpNotificationsPrefix	OBJECT IDENTIFIER	::= { httpNotifications 0 }

httpEventObjects1 OBJECT-IDENTITY
    STATUS current
    DESCRIPTION
        "Event HTTP.1
        The Web probe could not be started because of memory limitations."
    ::= { httpEventsGroup 1 }

http1-probe-identifier OBJECT-TYPE
    SYNTAX Integer32
    MAX-ACCESS accessible-for-notify
    STATUS current
    DESCRIPTION
        "Parameter 'probe-identifier' in event HTTP.1"
    ::= { httpEventObjects1 1 }

httpEventObjects2 OBJECT-IDENTITY
    STATUS current
    DESCRIPTION
        "Event HTTP.2
        The router was unable to read the data configured for a Web probe."
    ::= { httpEventsGroup 2 }

http2-probe-identifier OBJECT-TYPE
    SYNTAX Integer32
    MAX-ACCESS accessible-for-notify
    STATUS current
    DESCRIPTION
        "Parameter 'probe-identifier' in event HTTP.2"
    ::= { httpEventObjects2 1 }

httpEventObjects3 OBJECT-IDENTITY
    STATUS current
    DESCRIPTION
        "Event HTTP.3
        The router was unable to open a TCP session for a Web probe."
    ::= { httpEventsGroup 3 }

http3-host OBJECT-TYPE
    SYNTAX IpAddress
    MAX-ACCESS accessible-for-notify
    STATUS current
    DESCRIPTION
        "Parameter 'host' in event HTTP.3"
    ::= { httpEventObjects3 1 }

http3-url OBJECT-TYPE
    SYNTAX DisplayString
    MAX-ACCESS accessible-for-notify
    STATUS current
    DESCRIPTION
        "Parameter 'url' in event HTTP.3"
    ::= { httpEventObjects3 2 }

httpEventObjects4 OBJECT-IDENTITY
    STATUS current
    DESCRIPTION
        "Event HTTP.4
        The probe, for a generic page, finished before being successfully
        completed."
    ::= { httpEventsGroup 4 }

http4-bytes OBJECT-TYPE
    SYNTAX Integer32
    MAX-ACCESS accessible-for-notify
    STATUS current
    DESCRIPTION
        "Parameter 'bytes' in event HTTP.4"
    ::= { httpEventObjects4 1 }

http4-time OBJECT-TYPE
    SYNTAX Integer32
    MAX-ACCESS accessible-for-notify
    STATUS current
    DESCRIPTION
        "Parameter 'time' in event HTTP.4"
    ::= { httpEventObjects4 2 }

http4-bps OBJECT-TYPE
    SYNTAX Integer32
    MAX-ACCESS accessible-for-notify
    STATUS current
    DESCRIPTION
        "Parameter 'bps' in event HTTP.4"
    ::= { httpEventObjects4 3 }

http4-host OBJECT-TYPE
    SYNTAX IpAddress
    MAX-ACCESS accessible-for-notify
    STATUS current
    DESCRIPTION
        "Parameter 'host' in event HTTP.4"
    ::= { httpEventObjects4 4 }

http4-url OBJECT-TYPE
    SYNTAX DisplayString
    MAX-ACCESS accessible-for-notify
    STATUS current
    DESCRIPTION
        "Parameter 'url' in event HTTP.4"
    ::= { httpEventObjects4 5 }

http4-time-dns OBJECT-TYPE
    SYNTAX Integer32
    MAX-ACCESS accessible-for-notify
    STATUS current
    DESCRIPTION
        "Parameter 'time-dns' in event HTTP.4"
    ::= { httpEventObjects4 6 }

http4-time-tcp OBJECT-TYPE
    SYNTAX Integer32
    MAX-ACCESS accessible-for-notify
    STATUS current
    DESCRIPTION
        "Parameter 'time-tcp' in event HTTP.4"
    ::= { httpEventObjects4 7 }

http4-device-status OBJECT-TYPE
    SYNTAX Integer32
    MAX-ACCESS accessible-for-notify
    STATUS current
    DESCRIPTION
        "Parameter 'device-status' in event HTTP.4"
    ::= { httpEventObjects4 8 }

http4-time-server-response OBJECT-TYPE
    SYNTAX Integer32
    MAX-ACCESS accessible-for-notify
    STATUS current
    DESCRIPTION
        "Parameter 'time-server-response' in event HTTP.4"
    ::= { httpEventObjects4 9 }

http4-transmit-speed OBJECT-TYPE
    SYNTAX Integer32
    MAX-ACCESS accessible-for-notify
    STATUS current
    DESCRIPTION
        "Parameter 'transmit-speed' in event HTTP.4"
    ::= { httpEventObjects4 10 }

http4-receive-speed OBJECT-TYPE
    SYNTAX Integer32
    MAX-ACCESS accessible-for-notify
    STATUS current
    DESCRIPTION
        "Parameter 'receive-speed' in event HTTP.4"
    ::= { httpEventObjects4 11 }

httpEventObjects5 OBJECT-IDENTITY
    STATUS current
    DESCRIPTION
        "Event HTTP.5
        The HTTP header received is not the expected."
    ::= { httpEventsGroup 5 }

http5-level OBJECT-TYPE
    SYNTAX Integer32
    MAX-ACCESS accessible-for-notify
    STATUS current
    DESCRIPTION
        "Parameter 'level' in event HTTP.5"
    ::= { httpEventObjects5 1 }

http5-sublevel OBJECT-TYPE
    SYNTAX Integer32
    MAX-ACCESS accessible-for-notify
    STATUS current
    DESCRIPTION
        "Parameter 'sublevel' in event HTTP.5"
    ::= { httpEventObjects5 2 }

http5-status-code OBJECT-TYPE
    SYNTAX Integer32
    MAX-ACCESS accessible-for-notify
    STATUS current
    DESCRIPTION
        "Parameter 'status-code' in event HTTP.5"
    ::= { httpEventObjects5 3 }

http5-reason OBJECT-TYPE
    SYNTAX DisplayString
    MAX-ACCESS accessible-for-notify
    STATUS current
    DESCRIPTION
        "Parameter 'reason' in event HTTP.5"
    ::= { httpEventObjects5 4 }

httpEventObjects6 OBJECT-IDENTITY
    STATUS current
    DESCRIPTION
        "Event HTTP.6
        The probe, for a generic page, was successfully completed."
    ::= { httpEventsGroup 6 }

http6-bytes OBJECT-TYPE
    SYNTAX Integer32
    MAX-ACCESS accessible-for-notify
    STATUS current
    DESCRIPTION
        "Parameter 'bytes' in event HTTP.6"
    ::= { httpEventObjects6 1 }

http6-time OBJECT-TYPE
    SYNTAX Integer32
    MAX-ACCESS accessible-for-notify
    STATUS current
    DESCRIPTION
        "Parameter 'time' in event HTTP.6"
    ::= { httpEventObjects6 2 }

http6-bps OBJECT-TYPE
    SYNTAX Integer32
    MAX-ACCESS accessible-for-notify
    STATUS current
    DESCRIPTION
        "Parameter 'bps' in event HTTP.6"
    ::= { httpEventObjects6 3 }

http6-host OBJECT-TYPE
    SYNTAX IpAddress
    MAX-ACCESS accessible-for-notify
    STATUS current
    DESCRIPTION
        "Parameter 'host' in event HTTP.6"
    ::= { httpEventObjects6 4 }

http6-url OBJECT-TYPE
    SYNTAX DisplayString
    MAX-ACCESS accessible-for-notify
    STATUS current
    DESCRIPTION
        "Parameter 'url' in event HTTP.6"
    ::= { httpEventObjects6 5 }

http6-time-dns OBJECT-TYPE
    SYNTAX Integer32
    MAX-ACCESS accessible-for-notify
    STATUS current
    DESCRIPTION
        "Parameter 'time-dns' in event HTTP.6"
    ::= { httpEventObjects6 6 }

http6-time-tcp OBJECT-TYPE
    SYNTAX Integer32
    MAX-ACCESS accessible-for-notify
    STATUS current
    DESCRIPTION
        "Parameter 'time-tcp' in event HTTP.6"
    ::= { httpEventObjects6 7 }

http6-device-status OBJECT-TYPE
    SYNTAX Integer32
    MAX-ACCESS accessible-for-notify
    STATUS current
    DESCRIPTION
        "Parameter 'device-status' in event HTTP.6"
    ::= { httpEventObjects6 8 }

http6-time-server-response OBJECT-TYPE
    SYNTAX Integer32
    MAX-ACCESS accessible-for-notify
    STATUS current
    DESCRIPTION
        "Parameter 'time-server-response' in event HTTP.6"
    ::= { httpEventObjects6 9 }

http6-transmit-speed OBJECT-TYPE
    SYNTAX Integer32
    MAX-ACCESS accessible-for-notify
    STATUS current
    DESCRIPTION
        "Parameter 'transmit-speed' in event HTTP.6"
    ::= { httpEventObjects6 10 }

http6-receive-speed OBJECT-TYPE
    SYNTAX Integer32
    MAX-ACCESS accessible-for-notify
    STATUS current
    DESCRIPTION
        "Parameter 'receive-speed' in event HTTP.6"
    ::= { httpEventObjects6 11 }

httpEventObjects7 OBJECT-IDENTITY
    STATUS current
    DESCRIPTION
        "Event HTTP.7
        The probe has been started."
    ::= { httpEventsGroup 7 }

http7-url OBJECT-TYPE
    SYNTAX DisplayString
    MAX-ACCESS accessible-for-notify
    STATUS current
    DESCRIPTION
        "Parameter 'url' in event HTTP.7"
    ::= { httpEventObjects7 1 }

httpEventObjects8 OBJECT-IDENTITY
    STATUS current
    DESCRIPTION
        "Event HTTP.8
        An error occurred while reading a chunk."
    ::= { httpEventsGroup 8 }

http8-host OBJECT-TYPE
    SYNTAX IpAddress
    MAX-ACCESS accessible-for-notify
    STATUS current
    DESCRIPTION
        "Parameter 'host' in event HTTP.8"
    ::= { httpEventObjects8 1 }

http8-url OBJECT-TYPE
    SYNTAX DisplayString
    MAX-ACCESS accessible-for-notify
    STATUS current
    DESCRIPTION
        "Parameter 'url' in event HTTP.8"
    ::= { httpEventObjects8 2 }

httpEventObjects9 OBJECT-IDENTITY
    STATUS current
    DESCRIPTION
        "Event HTTP.9
        An error occurred while reading a JavaScript."
    ::= { httpEventsGroup 9 }

http9-host OBJECT-TYPE
    SYNTAX IpAddress
    MAX-ACCESS accessible-for-notify
    STATUS current
    DESCRIPTION
        "Parameter 'host' in event HTTP.9"
    ::= { httpEventObjects9 1 }

http9-url OBJECT-TYPE
    SYNTAX DisplayString
    MAX-ACCESS accessible-for-notify
    STATUS current
    DESCRIPTION
        "Parameter 'url' in event HTTP.9"
    ::= { httpEventObjects9 2 }

http9-JavaScript-number OBJECT-TYPE
    SYNTAX Integer32
    MAX-ACCESS accessible-for-notify
    STATUS current
    DESCRIPTION
        "Parameter 'JavaScript-number' in event HTTP.9"
    ::= { httpEventObjects9 3 }

httpEventObjects10 OBJECT-IDENTITY
    STATUS current
    DESCRIPTION
        "Event HTTP.10
        The speed calculated probing the url specified was below the threshold
        configured in n consecutive probes."
    ::= { httpEventsGroup 10 }

http10-host OBJECT-TYPE
    SYNTAX IpAddress
    MAX-ACCESS accessible-for-notify
    STATUS current
    DESCRIPTION
        "Parameter 'host' in event HTTP.10"
    ::= { httpEventObjects10 1 }

http10-url OBJECT-TYPE
    SYNTAX DisplayString
    MAX-ACCESS accessible-for-notify
    STATUS current
    DESCRIPTION
        "Parameter 'url' in event HTTP.10"
    ::= { httpEventObjects10 2 }

http10-threshold OBJECT-TYPE
    SYNTAX Integer32
    MAX-ACCESS accessible-for-notify
    STATUS current
    DESCRIPTION
        "Parameter 'threshold' in event HTTP.10"
    ::= { httpEventObjects10 3 }

http10-n-failures OBJECT-TYPE
    SYNTAX Integer32
    MAX-ACCESS accessible-for-notify
    STATUS current
    DESCRIPTION
        "Parameter 'n-failures' in event HTTP.10"
    ::= { httpEventObjects10 4 }

httpEventObjects11 OBJECT-IDENTITY
    STATUS current
    DESCRIPTION
        "Event HTTP.11
        An http 'get' has been made for the url shown."
    ::= { httpEventsGroup 11 }

http11-url OBJECT-TYPE
    SYNTAX DisplayString
    MAX-ACCESS accessible-for-notify
    STATUS current
    DESCRIPTION
        "Parameter 'url' in event HTTP.11"
    ::= { httpEventObjects11 1 }

httpEventObjects12 OBJECT-IDENTITY
    STATUS current
    DESCRIPTION
        "Event HTTP.12
        A HTTP packet has been received."
    ::= { httpEventsGroup 12 }

http12-host OBJECT-TYPE
    SYNTAX IpAddress
    MAX-ACCESS accessible-for-notify
    STATUS current
    DESCRIPTION
        "Parameter 'host' in event HTTP.12"
    ::= { httpEventObjects12 1 }

http12-url OBJECT-TYPE
    SYNTAX DisplayString
    MAX-ACCESS accessible-for-notify
    STATUS current
    DESCRIPTION
        "Parameter 'url' in event HTTP.12"
    ::= { httpEventObjects12 2 }

http12-size OBJECT-TYPE
    SYNTAX Integer32
    MAX-ACCESS accessible-for-notify
    STATUS current
    DESCRIPTION
        "Parameter 'size' in event HTTP.12"
    ::= { httpEventObjects12 3 }

httpEventObjects14 OBJECT-IDENTITY
    STATUS current
    DESCRIPTION
        "Event HTTP.14
        The Web probe could not be started because of memory limitations."
    ::= { httpEventsGroup 14 }

http14-host OBJECT-TYPE
    SYNTAX IpAddress
    MAX-ACCESS accessible-for-notify
    STATUS current
    DESCRIPTION
        "Parameter 'host' in event HTTP.14"
    ::= { httpEventObjects14 1 }

http14-url OBJECT-TYPE
    SYNTAX DisplayString
    MAX-ACCESS accessible-for-notify
    STATUS current
    DESCRIPTION
        "Parameter 'url' in event HTTP.14"
    ::= { httpEventObjects14 2 }

httpEventObjects15 OBJECT-IDENTITY
    STATUS current
    DESCRIPTION
        "Event HTTP.15
        The probe timed out before being successfully completed."
    ::= { httpEventsGroup 15 }

http15-host OBJECT-TYPE
    SYNTAX IpAddress
    MAX-ACCESS accessible-for-notify
    STATUS current
    DESCRIPTION
        "Parameter 'host' in event HTTP.15"
    ::= { httpEventObjects15 1 }

http15-url OBJECT-TYPE
    SYNTAX DisplayString
    MAX-ACCESS accessible-for-notify
    STATUS current
    DESCRIPTION
        "Parameter 'url' in event HTTP.15"
    ::= { httpEventObjects15 2 }

httpEventObjects16 OBJECT-IDENTITY
    STATUS current
    DESCRIPTION
        "Event HTTP.16
        An HTTP response was received with the status-code shown."
    ::= { httpEventsGroup 16 }

http16-status-code OBJECT-TYPE
    SYNTAX Integer32
    MAX-ACCESS accessible-for-notify
    STATUS current
    DESCRIPTION
        "Parameter 'status-code' in event HTTP.16"
    ::= { httpEventObjects16 1 }

http16-reason OBJECT-TYPE
    SYNTAX DisplayString
    MAX-ACCESS accessible-for-notify
    STATUS current
    DESCRIPTION
        "Parameter 'reason' in event HTTP.16"
    ::= { httpEventObjects16 2 }

httpEventObjects17 OBJECT-IDENTITY
    STATUS current
    DESCRIPTION
        "Event HTTP.17
        An HTTP response was received with status-code 3xx (redirection). The
        location requested is shown for informational purposes."
    ::= { httpEventsGroup 17 }

http17-location OBJECT-TYPE
    SYNTAX DisplayString
    MAX-ACCESS accessible-for-notify
    STATUS current
    DESCRIPTION
        "Parameter 'location' in event HTTP.17"
    ::= { httpEventObjects17 1 }

httpEventObjects18 OBJECT-IDENTITY
    STATUS current
    DESCRIPTION
        "Event HTTP.18
        When parsing a HTTP response, the temporal buffer was not big enough
        to store the bytes needed. The response parsed could be inexact."
    ::= { httpEventsGroup 18 }

http18-bytes-stored OBJECT-TYPE
    SYNTAX Integer32
    MAX-ACCESS accessible-for-notify
    STATUS current
    DESCRIPTION
        "Parameter 'bytes-stored' in event HTTP.18"
    ::= { httpEventObjects18 1 }

http18-bytes-to-store OBJECT-TYPE
    SYNTAX Integer32
    MAX-ACCESS accessible-for-notify
    STATUS current
    DESCRIPTION
        "Parameter 'bytes-to-store' in event HTTP.18"
    ::= { httpEventObjects18 2 }

httpEventObjects19 OBJECT-IDENTITY
    STATUS current
    DESCRIPTION
        "Event HTTP.19
        The probe, for an specific page, was successfully completed."
    ::= { httpEventsGroup 19 }

http19-bytes OBJECT-TYPE
    SYNTAX Integer32
    MAX-ACCESS accessible-for-notify
    STATUS current
    DESCRIPTION
        "Parameter 'bytes' in event HTTP.19"
    ::= { httpEventObjects19 1 }

http19-time OBJECT-TYPE
    SYNTAX Integer32
    MAX-ACCESS accessible-for-notify
    STATUS current
    DESCRIPTION
        "Parameter 'time' in event HTTP.19"
    ::= { httpEventObjects19 2 }

http19-bps OBJECT-TYPE
    SYNTAX Integer32
    MAX-ACCESS accessible-for-notify
    STATUS current
    DESCRIPTION
        "Parameter 'bps' in event HTTP.19"
    ::= { httpEventObjects19 3 }

http19-host OBJECT-TYPE
    SYNTAX IpAddress
    MAX-ACCESS accessible-for-notify
    STATUS current
    DESCRIPTION
        "Parameter 'host' in event HTTP.19"
    ::= { httpEventObjects19 4 }

http19-url OBJECT-TYPE
    SYNTAX DisplayString
    MAX-ACCESS accessible-for-notify
    STATUS current
    DESCRIPTION
        "Parameter 'url' in event HTTP.19"
    ::= { httpEventObjects19 5 }

http19-time-dns OBJECT-TYPE
    SYNTAX Integer32
    MAX-ACCESS accessible-for-notify
    STATUS current
    DESCRIPTION
        "Parameter 'time-dns' in event HTTP.19"
    ::= { httpEventObjects19 6 }

http19-time-tcp OBJECT-TYPE
    SYNTAX Integer32
    MAX-ACCESS accessible-for-notify
    STATUS current
    DESCRIPTION
        "Parameter 'time-tcp' in event HTTP.19"
    ::= { httpEventObjects19 7 }

http19-device-status OBJECT-TYPE
    SYNTAX Integer32
    MAX-ACCESS accessible-for-notify
    STATUS current
    DESCRIPTION
        "Parameter 'device-status' in event HTTP.19"
    ::= { httpEventObjects19 8 }

http19-time-server-response OBJECT-TYPE
    SYNTAX Integer32
    MAX-ACCESS accessible-for-notify
    STATUS current
    DESCRIPTION
        "Parameter 'time-server-response' in event HTTP.19"
    ::= { httpEventObjects19 9 }

http19-transmit-speed OBJECT-TYPE
    SYNTAX Integer32
    MAX-ACCESS accessible-for-notify
    STATUS current
    DESCRIPTION
        "Parameter 'transmit-speed' in event HTTP.19"
    ::= { httpEventObjects19 10 }

http19-receive-speed OBJECT-TYPE
    SYNTAX Integer32
    MAX-ACCESS accessible-for-notify
    STATUS current
    DESCRIPTION
        "Parameter 'receive-speed' in event HTTP.19"
    ::= { httpEventObjects19 11 }

httpEventObjects20 OBJECT-IDENTITY
    STATUS current
    DESCRIPTION
        "Event HTTP.20
        The probe, for an specific page, finished before being successfully
        completed."
    ::= { httpEventsGroup 20 }

http20-bytes OBJECT-TYPE
    SYNTAX Integer32
    MAX-ACCESS accessible-for-notify
    STATUS current
    DESCRIPTION
        "Parameter 'bytes' in event HTTP.20"
    ::= { httpEventObjects20 1 }

http20-time OBJECT-TYPE
    SYNTAX Integer32
    MAX-ACCESS accessible-for-notify
    STATUS current
    DESCRIPTION
        "Parameter 'time' in event HTTP.20"
    ::= { httpEventObjects20 2 }

http20-bps OBJECT-TYPE
    SYNTAX Integer32
    MAX-ACCESS accessible-for-notify
    STATUS current
    DESCRIPTION
        "Parameter 'bps' in event HTTP.20"
    ::= { httpEventObjects20 3 }

http20-host OBJECT-TYPE
    SYNTAX IpAddress
    MAX-ACCESS accessible-for-notify
    STATUS current
    DESCRIPTION
        "Parameter 'host' in event HTTP.20"
    ::= { httpEventObjects20 4 }

http20-url OBJECT-TYPE
    SYNTAX DisplayString
    MAX-ACCESS accessible-for-notify
    STATUS current
    DESCRIPTION
        "Parameter 'url' in event HTTP.20"
    ::= { httpEventObjects20 5 }

http20-time-dns OBJECT-TYPE
    SYNTAX Integer32
    MAX-ACCESS accessible-for-notify
    STATUS current
    DESCRIPTION
        "Parameter 'time-dns' in event HTTP.20"
    ::= { httpEventObjects20 6 }

http20-time-tcp OBJECT-TYPE
    SYNTAX Integer32
    MAX-ACCESS accessible-for-notify
    STATUS current
    DESCRIPTION
        "Parameter 'time-tcp' in event HTTP.20"
    ::= { httpEventObjects20 7 }

http20-device-status OBJECT-TYPE
    SYNTAX Integer32
    MAX-ACCESS accessible-for-notify
    STATUS current
    DESCRIPTION
        "Parameter 'device-status' in event HTTP.20"
    ::= { httpEventObjects20 8 }

http20-time-server-response OBJECT-TYPE
    SYNTAX Integer32
    MAX-ACCESS accessible-for-notify
    STATUS current
    DESCRIPTION
        "Parameter 'time-server-response' in event HTTP.20"
    ::= { httpEventObjects20 9 }

http20-transmit-speed OBJECT-TYPE
    SYNTAX Integer32
    MAX-ACCESS accessible-for-notify
    STATUS current
    DESCRIPTION
        "Parameter 'transmit-speed' in event HTTP.20"
    ::= { httpEventObjects20 10 }

http20-receive-speed OBJECT-TYPE
    SYNTAX Integer32
    MAX-ACCESS accessible-for-notify
    STATUS current
    DESCRIPTION
        "Parameter 'receive-speed' in event HTTP.20"
    ::= { httpEventObjects20 11 }

httpEventObjects21 OBJECT-IDENTITY
    STATUS current
    DESCRIPTION
        "Event HTTP.21
        There was some error when querying for the IP address associated with
        the host."
    ::= { httpEventsGroup 21 }

http21-url OBJECT-TYPE
    SYNTAX DisplayString
    MAX-ACCESS accessible-for-notify
    STATUS current
    DESCRIPTION
        "Parameter 'url' in event HTTP.21"
    ::= { httpEventObjects21 1 }

httpEventObjects22 OBJECT-IDENTITY
    STATUS current
    DESCRIPTION
        "Event HTTP.22
        Generic informational event from HTTP server."
    ::= { httpEventsGroup 22 }

http22-string OBJECT-TYPE
    SYNTAX DisplayString
    MAX-ACCESS accessible-for-notify
    STATUS current
    DESCRIPTION
        "Parameter 'string' in event HTTP.22"
    ::= { httpEventObjects22 1 }

httpEventObjects23 OBJECT-IDENTITY
    STATUS current
    DESCRIPTION
        "Event HTTP.23
        The configured maximum number of redirections allowed has been reached.
        The next redirection required is not followed."
    ::= { httpEventsGroup 23 }

http23-url OBJECT-TYPE
    SYNTAX DisplayString
    MAX-ACCESS accessible-for-notify
    STATUS current
    DESCRIPTION
        "Parameter 'url' in event HTTP.23"
    ::= { httpEventObjects23 1 }

httpEventObjects24 OBJECT-IDENTITY
    STATUS current
    DESCRIPTION
        "Event HTTP.24
        A HTTP chunk has been received."
    ::= { httpEventsGroup 24 }

http24-host OBJECT-TYPE
    SYNTAX IpAddress
    MAX-ACCESS accessible-for-notify
    STATUS current
    DESCRIPTION
        "Parameter 'host' in event HTTP.24"
    ::= { httpEventObjects24 1 }

http24-url OBJECT-TYPE
    SYNTAX DisplayString
    MAX-ACCESS accessible-for-notify
    STATUS current
    DESCRIPTION
        "Parameter 'url' in event HTTP.24"
    ::= { httpEventObjects24 2 }

http24-size OBJECT-TYPE
    SYNTAX Integer32
    MAX-ACCESS accessible-for-notify
    STATUS current
    DESCRIPTION
        "Parameter 'size' in event HTTP.24"
    ::= { httpEventObjects24 3 }

httpEventObjects25 OBJECT-IDENTITY
    STATUS current
    DESCRIPTION
        "Event HTTP.25
        A HTTP packet has been passed to the web probe."
    ::= { httpEventsGroup 25 }

http25-host OBJECT-TYPE
    SYNTAX IpAddress
    MAX-ACCESS accessible-for-notify
    STATUS current
    DESCRIPTION
        "Parameter 'host' in event HTTP.25"
    ::= { httpEventObjects25 1 }

http25-url OBJECT-TYPE
    SYNTAX DisplayString
    MAX-ACCESS accessible-for-notify
    STATUS current
    DESCRIPTION
        "Parameter 'url' in event HTTP.25"
    ::= { httpEventObjects25 2 }

http25-size OBJECT-TYPE
    SYNTAX Integer32
    MAX-ACCESS accessible-for-notify
    STATUS current
    DESCRIPTION
        "Parameter 'size' in event HTTP.25"
    ::= { httpEventObjects25 3 }

http25-total-size OBJECT-TYPE
    SYNTAX Integer32
    MAX-ACCESS accessible-for-notify
    STATUS current
    DESCRIPTION
        "Parameter 'total-size' in event HTTP.25"
    ::= { httpEventObjects25 4 }


httpNotification1 NOTIFICATION-TYPE
    OBJECTS { 
              http1-probe-identifier 
            }
    STATUS current
    DESCRIPTION
        "Notification of Event HTTP.1

        Message: 'no memory to start probe, identifier=$1'

        Parameters list:
              $1: http1-probe-identifier

        The Web probe could not be started because of memory limitations."
    ::= { httpNotificationsPrefix 1 }

httpNotification2 NOTIFICATION-TYPE
    OBJECTS { 
              http2-probe-identifier 
            }
    STATUS current
    DESCRIPTION
        "Notification of Event HTTP.2

        Message: 'no data for probe identifier=$1'

        Parameters list:
              $1: http2-probe-identifier

        The router was unable to read the data configured for a Web probe."
    ::= { httpNotificationsPrefix 2 }

httpNotification3 NOTIFICATION-TYPE
    OBJECTS { 
              http3-host, 
              http3-url 
            }
    STATUS current
    DESCRIPTION
        "Notification of Event HTTP.3

        Message: 'cannot open TCP session with destination IP addr=$1 url=$2'

        Parameters list:
              $1: http3-host
              $2: http3-url

        The router was unable to open a TCP session for a Web probe."
    ::= { httpNotificationsPrefix 3 }

httpNotification4 NOTIFICATION-TYPE
    OBJECTS { 
              http4-bytes, 
              http4-time,
              http4-bps,
              http4-host,
              http4-url,
              http4-time-dns,
              http4-time-tcp,
              http4-device-status,
              http4-time-server-response,
              http4-transmit-speed,
              http4-receive-speed 
            }
    STATUS current
    DESCRIPTION
        "Notification of Event HTTP.4

        Message: 'probe failed, bytes=$1 time=$2 bps=$3 IP addr=$4 url=$5 time-dns=$6 time-tcp=$7 device-status=$8 time-server-response=$9 transmit-speed=$10 receive-speed=$11'

        Parameters list:
              $1: http4-bytes
              $2: http4-time
              $3: http4-bps
              $4: http4-host
              $5: http4-url
              $6: http4-time-dns
              $7: http4-time-tcp
              $8: http4-device-status
              $9: http4-time-server-response
              $10: http4-transmit-speed
              $11: http4-receive-speed

        The probe, for a generic page, finished before being successfully
        completed."
    ::= { httpNotificationsPrefix 4 }

httpNotification5 NOTIFICATION-TYPE
    OBJECTS { 
              http5-level, 
              http5-sublevel,
              http5-status-code,
              http5-reason 
            }
    STATUS current
    DESCRIPTION
        "Notification of Event HTTP.5

        Message: 'header error, HTTP version: $1.$2 status-code=$3 (cause: $4)'

        Parameters list:
              $1: http5-level
              $2: http5-sublevel
              $3: http5-status-code
              $4: http5-reason

        The HTTP header received is not the expected."
    ::= { httpNotificationsPrefix 5 }

httpNotification6 NOTIFICATION-TYPE
    OBJECTS { 
              http6-bytes, 
              http6-time,
              http6-bps,
              http6-host,
              http6-url,
              http6-time-dns,
              http6-time-tcp,
              http6-device-status,
              http6-time-server-response,
              http6-transmit-speed,
              http6-receive-speed 
            }
    STATUS current
    DESCRIPTION
        "Notification of Event HTTP.6

        Message: 'probe completed, bytes=$1 time=$2 bps=$3 IP addr=$4 url=$5 time-dns=$6 time-tcp=$7 device-status=$8 time-server-response=$9 transmit-speed=$10 receive-speed=$11'

        Parameters list:
              $1: http6-bytes
              $2: http6-time
              $3: http6-bps
              $4: http6-host
              $5: http6-url
              $6: http6-time-dns
              $7: http6-time-tcp
              $8: http6-device-status
              $9: http6-time-server-response
              $10: http6-transmit-speed
              $11: http6-receive-speed

        The probe, for a generic page, was successfully completed."
    ::= { httpNotificationsPrefix 6 }

httpNotification7 NOTIFICATION-TYPE
    OBJECTS { 
              http7-url 
            }
    STATUS current
    DESCRIPTION
        "Notification of Event HTTP.7

        Message: 'probe started, url=$1'

        Parameters list:
              $1: http7-url

        The probe has been started."
    ::= { httpNotificationsPrefix 7 }

httpNotification8 NOTIFICATION-TYPE
    OBJECTS { 
              http8-host, 
              http8-url 
            }
    STATUS current
    DESCRIPTION
        "Notification of Event HTTP.8

        Message: 'chunk error, IP addr=$1 url=$2'

        Parameters list:
              $1: http8-host
              $2: http8-url

        An error occurred while reading a chunk."
    ::= { httpNotificationsPrefix 8 }

httpNotification9 NOTIFICATION-TYPE
    OBJECTS { 
              http9-host, 
              http9-url,
              http9-JavaScript-number 
            }
    STATUS current
    DESCRIPTION
        "Notification of Event HTTP.9

        Message: 'JavaScript error, IP addr=$1 url=$2, JavaScript number=$3'

        Parameters list:
              $1: http9-host
              $2: http9-url
              $3: http9-JavaScript-number

        An error occurred while reading a JavaScript."
    ::= { httpNotificationsPrefix 9 }

httpNotification10 NOTIFICATION-TYPE
    OBJECTS { 
              http10-host, 
              http10-url,
              http10-threshold,
              http10-n-failures 
            }
    STATUS current
    DESCRIPTION
        "Notification of Event HTTP.10

        Message: 'Probe error, IP addr=$1 url=$2, threshold=$3, number of failures=$4'

        Parameters list:
              $1: http10-host
              $2: http10-url
              $3: http10-threshold
              $4: http10-n-failures

        The speed calculated probing the url specified was below the threshold
        configured in n consecutive probes."
    ::= { httpNotificationsPrefix 10 }

httpNotification11 NOTIFICATION-TYPE
    OBJECTS { 
              http11-url 
            }
    STATUS current
    DESCRIPTION
        "Notification of Event HTTP.11

        Message: 'get url=/$1'

        Parameters list:
              $1: http11-url

        An http 'get' has been made for the url shown."
    ::= { httpNotificationsPrefix 11 }

httpNotification12 NOTIFICATION-TYPE
    OBJECTS { 
              http12-host, 
              http12-url,
              http12-size 
            }
    STATUS current
    DESCRIPTION
        "Notification of Event HTTP.12

        Message: 'received packet IP addr=$1 url=$2 size=$3'

        Parameters list:
              $1: http12-host
              $2: http12-url
              $3: http12-size

        A HTTP packet has been received."
    ::= { httpNotificationsPrefix 12 }

httpNotification13 NOTIFICATION-TYPE
    STATUS current
    DESCRIPTION
        "Notification of Event HTTP.13

        Message: 'no memory to start probe process'

        The Web probe process could not be started because of memory limitations."
    ::= { httpNotificationsPrefix 13 }

httpNotification14 NOTIFICATION-TYPE
    OBJECTS { 
              http14-host, 
              http14-url 
            }
    STATUS current
    DESCRIPTION
        "Notification of Event HTTP.14

        Message: 'no memory to start probe, IP addr=$1 url=$2'

        Parameters list:
              $1: http14-host
              $2: http14-url

        The Web probe could not be started because of memory limitations."
    ::= { httpNotificationsPrefix 14 }

httpNotification15 NOTIFICATION-TYPE
    OBJECTS { 
              http15-host, 
              http15-url 
            }
    STATUS current
    DESCRIPTION
        "Notification of Event HTTP.15

        Message: 'probe time out, closing TCP session, IP addr=$1 url=$2'

        Parameters list:
              $1: http15-host
              $2: http15-url

        The probe timed out before being successfully completed."
    ::= { httpNotificationsPrefix 15 }

httpNotification16 NOTIFICATION-TYPE
    OBJECTS { 
              http16-status-code, 
              http16-reason 
            }
    STATUS current
    DESCRIPTION
        "Notification of Event HTTP.16

        Message: 'received response with status-code=$1 (cause: $2)'

        Parameters list:
              $1: http16-status-code
              $2: http16-reason

        An HTTP response was received with the status-code shown."
    ::= { httpNotificationsPrefix 16 }

httpNotification17 NOTIFICATION-TYPE
    OBJECTS { 
              http17-location 
            }
    STATUS current
    DESCRIPTION
        "Notification of Event HTTP.17

        Message: 'Redirection requested, location:$1'

        Parameters list:
              $1: http17-location

        An HTTP response was received with status-code 3xx (redirection). The
        location requested is shown for informational purposes."
    ::= { httpNotificationsPrefix 17 }

httpNotification18 NOTIFICATION-TYPE
    OBJECTS { 
              http18-bytes-stored, 
              http18-bytes-to-store 
            }
    STATUS current
    DESCRIPTION
        "Notification of Event HTTP.18

        Message: 'no memory to store in temporal buffer, bytes stored=$1, bytes to store=$2'

        Parameters list:
              $1: http18-bytes-stored
              $2: http18-bytes-to-store

        When parsing a HTTP response, the temporal buffer was not big enough
        to store the bytes needed. The response parsed could be inexact."
    ::= { httpNotificationsPrefix 18 }

httpNotification19 NOTIFICATION-TYPE
    OBJECTS { 
              http19-bytes, 
              http19-time,
              http19-bps,
              http19-host,
              http19-url,
              http19-time-dns,
              http19-time-tcp,
              http19-device-status,
              http19-time-server-response,
              http19-transmit-speed,
              http19-receive-speed 
            }
    STATUS current
    DESCRIPTION
        "Notification of Event HTTP.19

        Message: 'probe completed, bytes=$1 time=$2 bps=$3 IP addr=$4 url=$5 time-dns=$6 time-tcp=$7 device-status=$8 time-server-response=$9 transmit-speed=$10 receive-speed=$11'

        Parameters list:
              $1: http19-bytes
              $2: http19-time
              $3: http19-bps
              $4: http19-host
              $5: http19-url
              $6: http19-time-dns
              $7: http19-time-tcp
              $8: http19-device-status
              $9: http19-time-server-response
              $10: http19-transmit-speed
              $11: http19-receive-speed

        The probe, for an specific page, was successfully completed."
    ::= { httpNotificationsPrefix 19 }

httpNotification20 NOTIFICATION-TYPE
    OBJECTS { 
              http20-bytes, 
              http20-time,
              http20-bps,
              http20-host,
              http20-url,
              http20-time-dns,
              http20-time-tcp,
              http20-device-status,
              http20-time-server-response,
              http20-transmit-speed,
              http20-receive-speed 
            }
    STATUS current
    DESCRIPTION
        "Notification of Event HTTP.20

        Message: 'probe failed, bytes=$1 time=$2 bps=$3 IP addr=$4 url=$5 time-dns=$6 time-tcp=$7 device-status=$8 time-server-response=$9 transmit-speed=$10 receive-speed=$11'

        Parameters list:
              $1: http20-bytes
              $2: http20-time
              $3: http20-bps
              $4: http20-host
              $5: http20-url
              $6: http20-time-dns
              $7: http20-time-tcp
              $8: http20-device-status
              $9: http20-time-server-response
              $10: http20-transmit-speed
              $11: http20-receive-speed

        The probe, for an specific page, finished before being successfully
        completed."
    ::= { httpNotificationsPrefix 20 }

httpNotification21 NOTIFICATION-TYPE
    OBJECTS { 
              http21-url 
            }
    STATUS current
    DESCRIPTION
        "Notification of Event HTTP.21

        Message: 'cannot resolve DNS url=$1'

        Parameters list:
              $1: http21-url

        There was some error when querying for the IP address associated with
        the host."
    ::= { httpNotificationsPrefix 21 }

httpNotification22 NOTIFICATION-TYPE
    OBJECTS { 
              http22-string 
            }
    STATUS current
    DESCRIPTION
        "Notification of Event HTTP.22

        Message: '$1'

        Parameters list:
              $1: http22-string

        Generic informational event from HTTP server."
    ::= { httpNotificationsPrefix 22 }

httpNotification23 NOTIFICATION-TYPE
    OBJECTS { 
              http23-url 
            }
    STATUS current
    DESCRIPTION
        "Notification of Event HTTP.23

        Message: 'max redirections reached url=$1'

        Parameters list:
              $1: http23-url

        The configured maximum number of redirections allowed has been reached.
        The next redirection required is not followed."
    ::= { httpNotificationsPrefix 23 }

httpNotification24 NOTIFICATION-TYPE
    OBJECTS { 
              http24-host, 
              http24-url,
              http24-size 
            }
    STATUS current
    DESCRIPTION
        "Notification of Event HTTP.24

        Message: 'received chunk IP addr=$1 url=$2 size=$3'

        Parameters list:
              $1: http24-host
              $2: http24-url
              $3: http24-size

        A HTTP chunk has been received."
    ::= { httpNotificationsPrefix 24 }

httpNotification25 NOTIFICATION-TYPE
    OBJECTS { 
              http25-host, 
              http25-url,
              http25-size,
              http25-total-size 
            }
    STATUS current
    DESCRIPTION
        "Notification of Event HTTP.25

        Message: 'received data IP addr=$1 url=$2 size=$3, total-size=$4'

        Parameters list:
              $1: http25-host
              $2: http25-url
              $3: http25-size
              $4: http25-total-size

        A HTTP packet has been passed to the web probe."
    ::= { httpNotificationsPrefix 25 }


END
