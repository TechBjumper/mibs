--------------------------------------------------------------
-- Note: This mib was auto generated from the mib file:
--       f:/3.2/buildstage/stage//cs.ear/doc/HPOVSam.mib
-- Wed Jun 02 09:59:57 PDT 2004
--------------------------------------------------------------

--------------------------------------------------------------
--
-- The information in this MIB is subject to change without
-- notice and should not be construed as a commitment by 
-- Hewlett Packard.  Hewlett Packard assumes no responsibility
-- for the use or reliability of this software.
--
--------------------------------------------------------------
--
-- HP OpenView Storarge Areas Manager
-- Management Information Base description
-- SMI format
--
--------------------------------------------------------------
--
-- Author
-- Evan H. Burns
-- Modified by Paulene M. Purdy
-- Modified by Greg Stephens & Dave Kasberg
-- Modified by Eddie Houston
--------------------------------------------------------------
--
-- 01-13-98 Created Original Module
-- 08/11/2000 Modified  
-- 08/15/2000 Modified modification :)
-- 09/24/2002 Added NNM event config fields
-- 06/11/2003 Converted to SMIv1 -EDH
-- 07/18/2003 Renamed from HPOvSam-MIB-V1.mib to 
--            HPOVSam_smiV1.mib -EDH
-- 07/21/2003 Changed the trap-types that we send 
--            to now include the category as the 
--            Enterprise OID and severity as the 
--            trap type.  -EDH
-- 09/05/2003 Renamed from HPOvSam_smiV1.mib to 
--            HPOVSam.mib -EDH
--
--------------------------------------------------------------

    HPOVSam-IM DEFINITIONS ::= BEGIN

        IMPORTS
            OBJECT-TYPE
                FROM RFC-1212
            TRAP-TYPE
                FROM RFC-1215
            enterprises
                FROM RFC1155-SMI
            DisplayString
                FROM RFC1213-MIB;


--
-- Node definitions
    
        -- 1.3.6.1.4.1.11
        hp OBJECT IDENTIFIER ::= { enterprises 11 }

        -- 1.3.6.1.4.1.11.2
        nm OBJECT IDENTIFIER ::= { hp 2 }

        -- 1.3.6.1.4.1.11.2.27
        hpStorageAssistant OBJECT IDENTIFIER ::= { nm 27 }

        -- 1.3.6.1.4.1.11.2.27.3
        hpSanManager OBJECT IDENTIFIER ::= { hpStorageAssistant 3 }

        -- 1.3.6.1.4.1.11.2.27.3.0
        hpSanManagerTraps OBJECT IDENTIFIER ::= { hpSanManager 0 }

        -- 1.3.6.1.4.1.11.2.27.3.1
        hpSanManagerModules OBJECT IDENTIFIER ::= { hpSanManager 1 }

        -- 1.3.6.1.4.1.11.2.27.3.1.1
        hpSanManagerMibModule OBJECT IDENTIFIER ::= { hpSanManagerModules 1 }

        -- 1.3.6.1.4.1.11.2.27.3.1.1.1
        mibModuleEventVars OBJECT IDENTIFIER ::= { hpSanManagerMibModule 1 }

        -- 1.3.6.1.4.1.11.2.27.3.3
        hpovsamGenericTrap OBJECT IDENTIFIER ::= { hpSanManager 3 }

        -- 1.3.6.1.4.1.11.2.27.3.4
        hpovsamDeviceTrap OBJECT IDENTIFIER ::= { hpSanManager 4 }

        -- 1.3.6.1.4.1.11.2.27.3.5
        hpovsamAccountantTrap OBJECT IDENTIFIER ::= { hpSanManager 5 }

        -- 1.3.6.1.4.1.11.2.27.3.6
        hpovsamAllocaterTrap OBJECT IDENTIFIER ::= { hpSanManager 6 }

        -- 1.3.6.1.4.1.11.2.27.3.7
        hpovsamBuilderTrap OBJECT IDENTIFIER ::= { hpSanManager 7 }

        -- 1.3.6.1.4.1.11.2.27.3.8
        hpovsamOptimizerTrap OBJECT IDENTIFIER ::= { hpSanManager 8 }


-- Trap-only variable
        -- 1.3.6.1.4.1.11.2.27.3.1.1.1.1
        severityLevel OBJECT-TYPE
            SYNTAX INTEGER
                {
                informational(1),
                warning(2),
                minor(3),
                major(4),
                critical(5)
                }
            ACCESS read-only
            STATUS mandatory
            DESCRIPTION
                "Severity level of the event being reported"
            ::= { mibModuleEventVars 1 }


-- Trap-only variable
        -- 1.3.6.1.4.1.11.2.27.3.1.1.1.2
        category OBJECT-TYPE
            SYNTAX DisplayString
            ACCESS read-only
            STATUS mandatory
            DESCRIPTION
                "Category of the event being reported"
            ::= { mibModuleEventVars 2 }


-- Trap-only variable
        -- 1.3.6.1.4.1.11.2.27.3.1.1.1.3
        id OBJECT-TYPE
            SYNTAX INTEGER 
            ACCESS read-only
            STATUS mandatory
            DESCRIPTION
                "ID number of the event within the given category"
            ::= { mibModuleEventVars 3 }

-- Trap-only variable
        -- 1.3.6.1.4.1.11.2.27.3.1.1.1.4
        msgString OBJECT-TYPE
            SYNTAX DisplayString
            ACCESS read-only
            STATUS mandatory
            DESCRIPTION
                "Message string associated with the event being reported."
            ::= { mibModuleEventVars 4 }


-- Trap-only variable
        -- 1.3.6.1.4.1.11.2.27.3.1.1.1.5
        contactName OBJECT-TYPE
            SYNTAX DisplayString
            ACCESS read-only
            STATUS mandatory
            DESCRIPTION
                "Name of the person to be notified of the
                 occurence of the event being reported."
            ::= { mibModuleEventVars 5 }

-- Trap-only variable
        -- 1.3.6.1.4.1.11.2.27.3.1.1.1.6
        contactEmail	OBJECT-TYPE
            SYNTAX DisplayString
            ACCESS read-only
            STATUS mandatory
            DESCRIPTION
                "Email address of the individual referenced by 
                 an instance of the contactName variable."
            ::= { mibModuleEventVars 6 }

-- Trap-only variable
        -- 1.3.6.1.4.1.11.2.27.3.1.1.1.7
        contactHomePhone OBJECT-TYPE
            SYNTAX DisplayString
            ACCESS read-only
            STATUS mandatory
            DESCRIPTION
                "Home telephone number of the individual
                 referenced by an instance of the contactName
                 variable."
            ::= { mibModuleEventVars 7 }

-- Trap-only variable
        -- 1.3.6.1.4.1.11.2.27.3.1.1.1.8
        contactWorkPhone OBJECT-TYPE
            SYNTAX DisplayString
            ACCESS read-only
            STATUS mandatory
            DESCRIPTION
                "Work telephone number of the individual
                 referenced by an instance of the contactName
                 variable."
            ::= { mibModuleEventVars 8 }

-- Trap-only variable
        -- 1.3.6.1.4.1.11.2.27.3.1.1.1.9
        contactPager OBJECT-TYPE
            SYNTAX DisplayString
            ACCESS read-only
            STATUS mandatory
            DESCRIPTION
                "Pager telephone number of the individual
                 referenced by an instance of the contactName
                 variable."
            ::= { mibModuleEventVars 9 }

-- Trap-only variable
        -- 1.3.6.1.4.1.11.2.27.3.1.1.1.10
        contactFax OBJECT-TYPE
            SYNTAX DisplayString
            ACCESS read-only
            STATUS mandatory
            DESCRIPTION
                "Fax telephone number of the individual
                 referenced by an instance of the contactName
                 variable."
            ::= { mibModuleEventVars 10 }

-- Trap-only variable
        -- 1.3.6.1.4.1.11.2.27.3.1.1.1.11
        sourceName OBJECT-TYPE
            SYNTAX DisplayString
            ACCESS read-only
            STATUS mandatory
            DESCRIPTION
                "Event source 'friendly' name"
            ::= { mibModuleEventVars 11 }

-- Trap-only variable
        -- 1.3.6.1.4.1.11.2.27.3.1.1.1.12
        uniqueId OBJECT-TYPE
            SYNTAX DisplayString
            ACCESS read-only
            STATUS mandatory
            DESCRIPTION
                "Unique identifier of device that is source of event"
            ::= { mibModuleEventVars 12 }

-- Trap-only variable
        -- 1.3.6.1.4.1.11.2.27.3.1.1.1.12
        vendorId OBJECT-TYPE
            SYNTAX DisplayString
            ACCESS read-only
            STATUS mandatory
            DESCRIPTION
                "Vendor identifier of device that is source of event"
            ::= { mibModuleEventVars 13 }

-- Trap-only variable
        -- 1.3.6.1.4.1.11.2.27.3.1.1.1.14
        prodId OBJECT-TYPE
            SYNTAX DisplayString
            ACCESS read-only
            STATUS mandatory
            DESCRIPTION
                "Product identifier of device that is source of event"
            ::= { mibModuleEventVars 14 }

-- Trap-only variable
        -- 1.3.6.1.4.1.11.2.27.3.1.1.1.15
        prodRev OBJECT-TYPE
            SYNTAX DisplayString
            ACCESS read-only
            STATUS mandatory
            DESCRIPTION
                "Product revision of device that is source of event"
            ::= { mibModuleEventVars 15 }

-- Trap-only variable
        -- 1.3.6.1.4.1.11.2.27.3.1.1.1.16
        serialNo OBJECT-TYPE
            SYNTAX DisplayString
            ACCESS read-only
            STATUS mandatory
            DESCRIPTION
                "Serial number of device that is source of event"
            ::= { mibModuleEventVars 16 }

-- Trap-only variable
        -- 1.3.6.1.4.1.11.2.27.3.1.1.1.17
        storageDmn OBJECT-TYPE
            SYNTAX DisplayString
            ACCESS read-only
            STATUS mandatory
            DESCRIPTION
                "Storage domain in which the device is located."
            ::= { mibModuleEventVars 17 }

    --------------------------------------------------------------------------------
    --
    -- The following are all trap-type definitions for the differing categories and
    -- severities of events that we send out.
    -- 
    -- NOTE: The pragmas here are defaulted to work with Network Node Manager(NNM).
    --       There are commented out pragmas that show what the differences are
    --       between what the NNM defaults are and what is required to be compatible
    --       With Insight Manager (CIM).
    --
    --       To make this mib work with CIM you should remove the dashes and CIM 
    --       from the beginning of the few pragmas that have them and delete the 
    --       default one.  The main differences are: 
    --         1) We use CATEGORY of "Application Alert Events" for NNM 
    --            instead of "STORAGE" for CIM.
    --         2) SEVERITY WARNING events need to be mapped to MINOR for CIM. 
    --
    --------------------------------------------------------------------------------

--
-- Traps of type hpovsamGenericTrap

    genericSanEventInformational TRAP-TYPE
        ENTERPRISE hpovsamGenericTrap
        VARIABLES  { severityLevel, category, id,
                     msgString, contactName, contactEmail,
                     contactWorkPhone, contactHomePhone, 
                     contactPager, contactFax }
        DESCRIPTION
                        "A generic Storage Area Manager SAN event of Informational severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM SAN Event"
     --#SUMMARY "OV SAM SAN Event, Category/Id: %d/%d, Msg: %d  Severity: %d  Contact: %d"
     --#ARGUMENTS {1,2,3,0,4}
     --#SEVERITY INFORMATIONAL
     --#GENERIC 6
     --#CATEGORY "STORAGE"
     -- CIM
	  --#CATEGORY "STORAGE"
     --#SOURCE_ID "T"
        ::= 1

    genericSanEventWarning TRAP-TYPE
        ENTERPRISE hpovsamGenericTrap
        VARIABLES  { severityLevel, category, id,
                     msgString, contactName, contactEmail,
                     contactWorkPhone, contactHomePhone, 
                     contactPager, contactFax }
        DESCRIPTION
                        "A generic Storage Area Manager SAN event of Warning severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM SAN Event"
     --#SUMMARY "OV SAM SAN Event, Category/Id: %d/%d, Msg: %d  Severity: %d  Contact: %d"
     --#ARGUMENTS {1,2,3,0,4}
     --#SEVERITY MINOR
     -- CIM
	  --#SEVERITY MINOR
     --#GENERIC 6
     --#CATEGORY "STORAGE"
     -- CIM
	  --#CATEGORY "STORAGE"
     --#SOURCE_ID "T"
        ::= 2

    genericSanEventMinor TRAP-TYPE
        ENTERPRISE hpovsamGenericTrap
        VARIABLES  { severityLevel, category, id,
                     msgString, contactName, contactEmail,
                     contactWorkPhone, contactHomePhone, 
                     contactPager, contactFax }
        DESCRIPTION
                        "A generic Storage Area Manager SAN event of Minor severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM SAN Event"
     --#SUMMARY "OV SAM SAN Event, Category/Id: %d/%d, Msg: %d  Severity: %d  Contact: %d"
     --#ARGUMENTS {1,2,3,0,4}
     --#SEVERITY MINOR
     --#GENERIC 6
     -- CIM
	  --#CATEGORY "STORAGE"
     --#CATEGORY "STORAGE"
     --#SOURCE_ID "T"
        ::= 3

    genericSanEventMajor TRAP-TYPE
        ENTERPRISE hpovsamGenericTrap
        VARIABLES  { severityLevel, category, id,
                     msgString, contactName, contactEmail,
                     contactWorkPhone, contactHomePhone, 
                     contactPager, contactFax }
        DESCRIPTION
                        "A generic Storage Area Manager SAN event of Major severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM SAN Event"
     --#SUMMARY "OV SAM SAN Event, Category/Id: %d/%d, Msg: %d  Severity: %d  Contact: %d"
     --#ARGUMENTS {1,2,3,0,4}
     --#SEVERITY MAJOR
     --#GENERIC 6
     --#CATEGORY "STORAGE"
     -- CIM
	  --#CATEGORY "STORAGE"
     --#SOURCE_ID "T"
        ::= 4

    genericSanEventCritical TRAP-TYPE
        ENTERPRISE hpovsamGenericTrap
        VARIABLES  { severityLevel, category, id,
                     msgString, contactName, contactEmail,
                     contactWorkPhone, contactHomePhone, 
                     contactPager, contactFax }
        DESCRIPTION
                        "A generic Storage Area Manager SAN event of Critical severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM SAN Event"
     --#SUMMARY "OV SAM SAN Event, Category/Id: %d/%d, Msg: %d  Severity: %d  Contact: %d"
     --#ARGUMENTS {1,2,3,0,4}
     --#SEVERITY CRITICAL
     --#GENERIC 6
     --#CATEGORY "STORAGE"
     -- CIM
	  --#CATEGORY "STORAGE"
     --#SOURCE_ID "T"
        ::= 5

--
-- Traps of type hpovsamDeviceTrap

    sanDeviceEventInformational TRAP-TYPE
        ENTERPRISE hpovsamDeviceTrap
        VARIABLES  { severityLevel, category, id,
                     msgString, contactName, contactEmail,
                     contactWorkPhone, contactHomePhone,
                     contactPager, contactFax, sourceName, 
                     uniqueId, vendorId, prodId, prodRev, 
                     serialNo, storageDmn}
        DESCRIPTION
                        "A SAN Device Event of Informational severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName;
                            sourceName - Event source 'friendly' name;
                            uniqueId - Unique identifier of device that 
                                is source of event;
                            vendorId - Vendor identifier of device that 
                                is source of event;
                            prodId - Product identifier of device that 
                                is source of event;
                            prodRev - Product revision of device that is 
                                source of event;
                            serialNo - Serial number of device that is
                                source of event
                            storageDom - Storage domain in which the device
                                is located"
     -- The following are attributes used by xnmloadmib for improved formatting
     --#TYPE "OV SAM Device Event"
     --#SUMMARY "OV SAM Device Event, Id: %d, Msg: %d  Severity: %d  Source: %d, %d, %d, %d  StorageDomain: %d Contact: %d"
     --#ARGUMENTS {2,3,0,10,11,12,13,16,4}
     --#SEVERITY INFORMATIONAL
     --#GENERIC 6
     --#CATEGORY "STORAGE"
     -- CIM
	  --#CATEGORY "STORAGE"
     --#SOURCE_ID "T"
        ::= 1

    sanDeviceEventWarning TRAP-TYPE
        ENTERPRISE hpovsamDeviceTrap
        VARIABLES  { severityLevel, category, id,
                     msgString, contactName, contactEmail,
                     contactWorkPhone, contactHomePhone,
                     contactPager, contactFax, sourceName, 
                     uniqueId, vendorId, prodId, prodRev, 
                     serialNo, storageDmn}
        DESCRIPTION
                        "A SAN Device Event of Warning severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName;
                            sourceName - Event source 'friendly' name;
                            uniqueId - Unique identifier of device that 
                                is source of event;
                            vendorId - Vendor identifier of device that 
                                is source of event;
                            prodId - Product identifier of device that 
                                is source of event;
                            prodRev - Product revision of device that is 
                                source of event;
                            serialNo - Serial number of device that is
                                source of event
                            storageDom - Storage domain in which the device
                                is located"
     -- The following are attributes used by xnmloadmib for improved formatting
     --#TYPE "OV SAM Device Event"
     --#SUMMARY "OV SAM Device Event, Id: %d, Msg: %d  Severity: %d  Source: %d, %d, %d, %d  StorageDomain: %d Contact: %d"
     --#ARGUMENTS {2,3,0,10,11,12,13,16,4}
     --#SEVERITY MINOR
     -- CIM
	  --#SEVERITY MINOR
     --#GENERIC 6
     --#CATEGORY "STORAGE"
     -- CIM
	  --#CATEGORY "STORAGE"
     --#SOURCE_ID "T"
        ::= 2

    sanDeviceEventMinor TRAP-TYPE
        ENTERPRISE hpovsamDeviceTrap
        VARIABLES  { severityLevel, category, id,
                     msgString, contactName, contactEmail,
                     contactWorkPhone, contactHomePhone,
                     contactPager, contactFax, sourceName, 
                     uniqueId, vendorId, prodId, prodRev, 
                     serialNo, storageDmn}
        DESCRIPTION
                        "A SAN Device Event of Minor severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName;
                            sourceName - Event source 'friendly' name;
                            uniqueId - Unique identifier of device that 
                                is source of event;
                            vendorId - Vendor identifier of device that 
                                is source of event;
                            prodId - Product identifier of device that 
                                is source of event;
                            prodRev - Product revision of device that is 
                                source of event;
                            serialNo - Serial number of device that is
                                source of event
                            storageDom - Storage domain in which the device
                                is located"
     -- The following are attributes used by xnmloadmib for improved formatting
     --#TYPE "OV SAM Device Event"
     --#SUMMARY "OV SAM Device Event, Id: %d, Msg: %d  Severity: %d  Source: %d, %d, %d, %d  StorageDomain: %d Contact: %d"
     --#ARGUMENTS {2,3,0,10,11,12,13,16,4}
     --#SEVERITY MINOR
     --#GENERIC 6
     --#CATEGORY "STORAGE"
     -- CIM
	  --#CATEGORY "STORAGE"
     --#SOURCE_ID "T"
        ::= 3

    sanDeviceEventMajor TRAP-TYPE
        ENTERPRISE hpovsamDeviceTrap
        VARIABLES  { severityLevel, category, id,
                     msgString, contactName, contactEmail,
                     contactWorkPhone, contactHomePhone,
                     contactPager, contactFax, sourceName, 
                     uniqueId, vendorId, prodId, prodRev, 
                     serialNo, storageDmn}
        DESCRIPTION
                        "A SAN Device Event of Major severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName;
                            sourceName - Event source 'friendly' name;
                            uniqueId - Unique identifier of device that 
                                is source of event;
                            vendorId - Vendor identifier of device that 
                                is source of event;
                            prodId - Product identifier of device that 
                                is source of event;
                            prodRev - Product revision of device that is 
                                source of event;
                            serialNo - Serial number of device that is
                                source of event
                            storageDom - Storage domain in which the device
                                is located"
     -- The following are attributes used by xnmloadmib for improved formatting
     --#TYPE "OV SAM Device Event"
     --#SUMMARY "OV SAM Device Event, Id: %d, Msg: %d  Severity: %d  Source: %d, %d, %d, %d  StorageDomain: %d Contact: %d"
     --#ARGUMENTS {2,3,0,10,11,12,13,16,4}
     --#SEVERITY MAJOR
     --#GENERIC 6
     --#CATEGORY "STORAGE"
     -- CIM
	  --#CATEGORY "STORAGE"
     --#SOURCE_ID "T"
        ::= 4

    sanDeviceEventCritical TRAP-TYPE
        ENTERPRISE hpovsamDeviceTrap
        VARIABLES  { severityLevel, category, id,
                     msgString, contactName, contactEmail,
                     contactWorkPhone, contactHomePhone,
                     contactPager, contactFax, sourceName, 
                     uniqueId, vendorId, prodId, prodRev, 
                     serialNo, storageDmn}
        DESCRIPTION
                        "A SAN Device Event of Critical severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName;
                            sourceName - Event source 'friendly' name;
                            uniqueId - Unique identifier of device that 
                                is source of event;
                            vendorId - Vendor identifier of device that 
                                is source of event;
                            prodId - Product identifier of device that 
                                is source of event;
                            prodRev - Product revision of device that is 
                                source of event;
                            serialNo - Serial number of device that is
                                source of event
                            storageDom - Storage domain in which the device
                                is located"
     -- The following are attributes used by xnmloadmib for improved formatting
     --#TYPE "OV SAM Device Event"
     --#SUMMARY "OV SAM Device Event, Id: %d, Msg: %d  Severity: %d  Source: %d, %d, %d, %d  StorageDomain: %d Contact: %d"
     --#ARGUMENTS {2,3,0,10,11,12,13,16,4}
     --#SEVERITY CRITICAL
     --#GENERIC 6
     --#CATEGORY "STORAGE"
     -- CIM
	  --#CATEGORY "STORAGE"
     --#SOURCE_ID "T"
        ::= 5

--
-- Traps of type hpovsamAccountantTrap

    sanAccountantEventInformational TRAP-TYPE
        ENTERPRISE hpovsamAccountantTrap
        VARIABLES  { severityLevel, category, id,
                     msgString, contactName, contactEmail,
                     contactWorkPhone, contactHomePhone, 
                     contactPager, contactFax }
        DESCRIPTION
                        "A Storage Area Manager Accountant SAN event of Informational severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Accountant Event"
     --#SUMMARY "OV SAM Accountant Event, Category/Id: %d/%d, Msg: %d  Severity: %d  Contact: %d"
     --#ARGUMENTS {1,2,3,0,4}
     --#SEVERITY INFORMATIONAL
     --#GENERIC 6
     --#CATEGORY "STORAGE"
     -- CIM
	  --#CATEGORY "STORAGE"
     --#SOURCE_ID "T"
        ::= 1

    sanAccountantEventWarning TRAP-TYPE
        ENTERPRISE hpovsamAccountantTrap
        VARIABLES  { severityLevel, category, id,
                     msgString, contactName, contactEmail,
                     contactWorkPhone, contactHomePhone, 
                     contactPager, contactFax }
        DESCRIPTION
                        "A Storage Area Manager Accountant SAN event of Warning severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Accountant Event"
     --#SUMMARY "OV SAM Accountant Event, Category/Id: %d/%d, Msg: %d  Severity: %d  Contact: %d"
     --#ARGUMENTS {1,2,3,0,4}
     --#SEVERITY MINOR
     -- CIM
	  --#SEVERITY MINOR
     --#GENERIC 6
     --#CATEGORY "STORAGE"
     -- CIM
	  --#CATEGORY "STORAGE"
     --#SOURCE_ID "T"
        ::= 2

    sanAccountantEventMinor TRAP-TYPE
        ENTERPRISE hpovsamAccountantTrap
        VARIABLES  { severityLevel, category, id,
                     msgString, contactName, contactEmail,
                     contactWorkPhone, contactHomePhone, 
                     contactPager, contactFax }
        DESCRIPTION
                        "A Storage Area Manager Accountant SAN event of Minor severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Accountant Event"
     --#SUMMARY "OV SAM Accountant Event, Category/Id: %d/%d, Msg: %d  Severity: %d  Contact: %d"
     --#ARGUMENTS {1,2,3,0,4}
     --#SEVERITY MINOR
     --#GENERIC 6
     --#CATEGORY "STORAGE"
     -- CIM
	  --#CATEGORY "STORAGE"
     --#SOURCE_ID "T"
        ::= 3

    sanAccountantEventMajor TRAP-TYPE
        ENTERPRISE hpovsamAccountantTrap
        VARIABLES  { severityLevel, category, id,
                     msgString, contactName, contactEmail,
                     contactWorkPhone, contactHomePhone, 
                     contactPager, contactFax }
        DESCRIPTION
                        "A Storage Area Manager Accountant SAN event of Major severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Accountant Event"
     --#SUMMARY "OV SAM Accountant Event, Category/Id: %d/%d, Msg: %d  Severity: %d  Contact: %d"
     --#ARGUMENTS {1,2,3,0,4}
     --#SEVERITY MAJOR
     --#GENERIC 6
     --#CATEGORY "STORAGE"
     -- CIM
	  --#CATEGORY "STORAGE"
     --#SOURCE_ID "T"
        ::= 4

    sanAccountantEventCritical TRAP-TYPE
        ENTERPRISE hpovsamAccountantTrap
        VARIABLES  { severityLevel, category, id,
                     msgString, contactName, contactEmail,
                     contactWorkPhone, contactHomePhone, 
                     contactPager, contactFax }
        DESCRIPTION
                        "A Storage Area Manager Accountant SAN event of Critical severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Accountant Event"
     --#SUMMARY "OV SAM Accountant Event, Category/Id: %d/%d, Msg: %d  Severity: %d  Contact: %d"
     --#ARGUMENTS {1,2,3,0,4}
     --#SEVERITY CRITICAL
     --#GENERIC 6
     --#CATEGORY "STORAGE"
     -- CIM
	  --#CATEGORY "STORAGE"
     --#SOURCE_ID "T"
        ::= 5

--
-- Traps of type hpovsamAllocaterTrap

    sanAllocaterEventInformational TRAP-TYPE
        ENTERPRISE hpovsamAllocaterTrap
        VARIABLES  { severityLevel, category, id,
                     msgString, contactName, contactEmail,
                     contactWorkPhone, contactHomePhone, 
                     contactPager, contactFax }
        DESCRIPTION
                        "A Storage Area Manager Allocater SAN event of Informational severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Allocater Event"
     --#SUMMARY "OV SAM Allocater Event, Category/Id: %d/%d, Msg: %d  Severity: %d  Contact: %d"
     --#ARGUMENTS {1,2,3,0,4}
     --#SEVERITY INFORMATIONAL
     --#GENERIC 6
     --#CATEGORY "STORAGE"
     -- CIM
	  --#CATEGORY "STORAGE"
     --#SOURCE_ID "T"
        ::= 1

    sanAllocaterEventWarning TRAP-TYPE
        ENTERPRISE hpovsamAllocaterTrap
        VARIABLES  { severityLevel, category, id,
                     msgString, contactName, contactEmail,
                     contactWorkPhone, contactHomePhone, 
                     contactPager, contactFax }
        DESCRIPTION
                        "A Storage Area Manager Allocater SAN event of Warning severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Allocater Event"
     --#SUMMARY "OV SAM Allocater Event, Category/Id: %d/%d, Msg: %d  Severity: %d  Contact: %d"
     --#ARGUMENTS {1,2,3,0,4}
     --#SEVERITY MINOR
     -- CIM
	  --#SEVERITY MINOR
     --#GENERIC 6
     --#CATEGORY "STORAGE"
     -- CIM
	  --#CATEGORY "STORAGE"
     --#SOURCE_ID "T"
        ::= 2

    sanAllocaterEventMinor TRAP-TYPE
        ENTERPRISE hpovsamAllocaterTrap
        VARIABLES  { severityLevel, category, id,
                     msgString, contactName, contactEmail,
                     contactWorkPhone, contactHomePhone, 
                     contactPager, contactFax }
        DESCRIPTION
                        "A Storage Area Manager Allocater SAN event of Minor severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Allocater Event"
     --#SUMMARY "OV SAM Allocater Event, Category/Id: %d/%d, Msg: %d  Severity: %d  Contact: %d"
     --#ARGUMENTS {1,2,3,0,4}
     --#SEVERITY MINOR
     --#GENERIC 6
     --#CATEGORY "STORAGE"
     -- CIM
	  --#CATEGORY "STORAGE"
     --#SOURCE_ID "T"
        ::= 3

    sanAllocaterEventMajor TRAP-TYPE
        ENTERPRISE hpovsamAllocaterTrap
        VARIABLES  { severityLevel, category, id,
                     msgString, contactName, contactEmail,
                     contactWorkPhone, contactHomePhone, 
                     contactPager, contactFax }
        DESCRIPTION
                        "A Storage Area Manager Allocater SAN event of Major severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Allocater Event"
     --#SUMMARY "OV SAM Allocater Event, Category/Id: %d/%d, Msg: %d  Severity: %d  Contact: %d"
     --#ARGUMENTS {1,2,3,0,4}
     --#SEVERITY MAJOR
     --#GENERIC 6
     --#CATEGORY "STORAGE"
     -- CIM
	  --#CATEGORY "STORAGE"
     --#SOURCE_ID "T"
        ::= 4

    sanAllocaterEventCritical TRAP-TYPE
        ENTERPRISE hpovsamAllocaterTrap
        VARIABLES  { severityLevel, category, id,
                     msgString, contactName, contactEmail,
                     contactWorkPhone, contactHomePhone, 
                     contactPager, contactFax }
        DESCRIPTION
                        "A Storage Area Manager Allocater SAN event of Critical severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Allocater Event"
     --#SUMMARY "OV SAM Allocater Event, Category/Id: %d/%d, Msg: %d  Severity: %d  Contact: %d"
     --#ARGUMENTS {1,2,3,0,4}
     --#SEVERITY CRITICAL
     --#GENERIC 6
     --#CATEGORY "STORAGE"
     -- CIM
	  --#CATEGORY "STORAGE"
     --#SOURCE_ID "T"
        ::= 5

--
-- Traps of type hpovsamBuilderTrap

    sanBuilderEventInformational TRAP-TYPE
        ENTERPRISE hpovsamBuilderTrap
        VARIABLES  { severityLevel, category, id,
                     msgString, contactName, contactEmail,
                     contactWorkPhone, contactHomePhone, 
                     contactPager, contactFax }
        DESCRIPTION
                        "A Storage Area Manager Builder SAN event of Informational severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Builder Event"
     --#SUMMARY "OV SAM Builder Event, Category/Id: %d/%d, Msg: %d  Severity: %d  Contact: %d"
     --#ARGUMENTS {1,2,3,0,4}
     --#SEVERITY INFORMATIONAL
     --#GENERIC 6
     --#CATEGORY "STORAGE"
     -- CIM
	  --#CATEGORY "STORAGE"
     --#SOURCE_ID "T"
        ::= 1

    sanBuilderEventWarning TRAP-TYPE
        ENTERPRISE hpovsamBuilderTrap
        VARIABLES  { severityLevel, category, id,
                     msgString, contactName, contactEmail,
                     contactWorkPhone, contactHomePhone, 
                     contactPager, contactFax }
        DESCRIPTION
                        "A Storage Area Manager Builder SAN event of Warning severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Builder Event"
     --#SUMMARY "OV SAM Builder Event, Category/Id: %d/%d, Msg: %d  Severity: %d  Contact: %d"
     --#ARGUMENTS {1,2,3,0,4}
     --#SEVERITY MINOR
     -- CIM
	  --#SEVERITY MINOR
     --#GENERIC 6
     --#CATEGORY "STORAGE"
     -- CIM
	  --#CATEGORY "STORAGE"
     --#SOURCE_ID "T"
        ::= 2

    sanBuilderEventMinor TRAP-TYPE
        ENTERPRISE hpovsamBuilderTrap
        VARIABLES  { severityLevel, category, id,
                     msgString, contactName, contactEmail,
                     contactWorkPhone, contactHomePhone, 
                     contactPager, contactFax }
        DESCRIPTION
                        "A Storage Area Manager Builder SAN event of Minor severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Builder Event"
     --#SUMMARY "OV SAM Builder Event, Category/Id: %d/%d, Msg: %d  Severity: %d  Contact: %d"
     --#ARGUMENTS {1,2,3,0,4}
     --#SEVERITY MINOR
     --#GENERIC 6
     --#CATEGORY "STORAGE"
     -- CIM
	  --#CATEGORY "STORAGE"
     --#SOURCE_ID "T"
        ::= 3

    sanBuilderEventMajor TRAP-TYPE
        ENTERPRISE hpovsamBuilderTrap
        VARIABLES  { severityLevel, category, id,
                     msgString, contactName, contactEmail,
                     contactWorkPhone, contactHomePhone, 
                     contactPager, contactFax }
        DESCRIPTION
                        "A Storage Area Manager Builder SAN event of Major severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Builder Event"
     --#SUMMARY "OV SAM Builder Event, Category/Id: %d/%d, Msg: %d  Severity: %d  Contact: %d"
     --#ARGUMENTS {1,2,3,0,4}
     --#SEVERITY MAJOR
     --#GENERIC 6
     --#CATEGORY "STORAGE"
     -- CIM
	  --#CATEGORY "STORAGE"
     --#SOURCE_ID "T"
        ::= 4

    sanBuilderEventCritical TRAP-TYPE
        ENTERPRISE hpovsamBuilderTrap
        VARIABLES  { severityLevel, category, id,
                     msgString, contactName, contactEmail,
                     contactWorkPhone, contactHomePhone, 
                     contactPager, contactFax }
        DESCRIPTION
                        "A Storage Area Manager Builder SAN event of Critical severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Builder Event"
     --#SUMMARY "OV SAM Builder Event, Category/Id: %d/%d, Msg: %d  Severity: %d  Contact: %d"
     --#ARGUMENTS {1,2,3,0,4}
     --#SEVERITY CRITICAL
     --#GENERIC 6
     --#CATEGORY "STORAGE"
     -- CIM
	  --#CATEGORY "STORAGE"
     --#SOURCE_ID "T"
        ::= 5
--
-- Traps of type hpovsamOptimizerTrap

    sanOptimizerEventInformational TRAP-TYPE
        ENTERPRISE hpovsamOptimizerTrap
        VARIABLES  { severityLevel, category, id,
                     msgString, contactName, contactEmail,
                     contactWorkPhone, contactHomePhone, 
                     contactPager, contactFax }
        DESCRIPTION
                        "A Storage Area Manager Optimizer SAN event of Informational severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Optimizer Event"
     --#SUMMARY "OV SAM Optimizer Event, Category/Id: %d/%d, Msg: %d  Severity: %d  Contact: %d"
     --#ARGUMENTS {1,2,3,0,4}
     --#SEVERITY INFORMATIONAL
     --#GENERIC 6
     --#CATEGORY "STORAGE"
     -- CIM
	  --#CATEGORY "STORAGE"
     --#SOURCE_ID "T"
        ::= 1

    sanOptimizerEventWarning TRAP-TYPE
        ENTERPRISE hpovsamOptimizerTrap
        VARIABLES  { severityLevel, category, id,
                     msgString, contactName, contactEmail,
                     contactWorkPhone, contactHomePhone, 
                     contactPager, contactFax }
        DESCRIPTION
                        "A Storage Area Manager Optimizer SAN event of Warning severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Optimizer Event"
     --#SUMMARY "OV SAM Optimizer Event, Category/Id: %d/%d, Msg: %d  Severity: %d  Contact: %d"
     --#ARGUMENTS {1,2,3,0,4}
     --#SEVERITY MINOR
     -- CIM
	  --#SEVERITY MINOR
     --#GENERIC 6
     --#CATEGORY "STORAGE"
     -- CIM
	  --#CATEGORY "STORAGE"
     --#SOURCE_ID "T"
        ::= 2

    sanOptimizerEventMinor TRAP-TYPE
        ENTERPRISE hpovsamOptimizerTrap
        VARIABLES  { severityLevel, category, id,
                     msgString, contactName, contactEmail,
                     contactWorkPhone, contactHomePhone, 
                     contactPager, contactFax }
        DESCRIPTION
                        "A Storage Area Manager Optimizer SAN event of Minor severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Optimizer Event"
     --#SUMMARY "OV SAM Optimizer Event, Category/Id: %d/%d, Msg: %d  Severity: %d  Contact: %d"
     --#ARGUMENTS {1,2,3,0,4}
     --#SEVERITY MINOR
     --#GENERIC 6
     --#CATEGORY "STORAGE"
     -- CIM
	  --#CATEGORY "STORAGE"
     --#SOURCE_ID "T"
        ::= 3

    sanOptimizerEventMajor TRAP-TYPE
        ENTERPRISE hpovsamOptimizerTrap
        VARIABLES  { severityLevel, category, id,
                     msgString, contactName, contactEmail,
                     contactWorkPhone, contactHomePhone, 
                     contactPager, contactFax }
        DESCRIPTION
                        "A Storage Area Manager Optimizer SAN event of Major severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Optimizer Event"
     --#SUMMARY "OV SAM Optimizer Event, Category/Id: %d/%d, Msg: %d  Severity: %d  Contact: %d"
     --#ARGUMENTS {1,2,3,0,4}
     --#SEVERITY MAJOR
     --#GENERIC 6
     --#CATEGORY "STORAGE"
     -- CIM
	  --#CATEGORY "STORAGE"
     --#SOURCE_ID "T"
        ::= 4

    sanOptimizerEventCritical TRAP-TYPE
        ENTERPRISE hpovsamOptimizerTrap
        VARIABLES  { severityLevel, category, id,
                     msgString, contactName, contactEmail,
                     contactWorkPhone, contactHomePhone, 
                     contactPager, contactFax }
        DESCRIPTION
                        "A Storage Area Manager Optimizer SAN event of Critical severity has occurred.  
                         The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM Optimizer Event"
     --#SUMMARY "OV SAM Optimizer Event, Category/Id: %d/%d, Msg: %d  Severity: %d  Contact: %d"
     --#ARGUMENTS {1,2,3,0,4}
     --#SEVERITY CRITICAL
     --#GENERIC 6
     --#CATEGORY "STORAGE"
     -- CIM
	  --#CATEGORY "STORAGE"
     --#SOURCE_ID "T"
        ::= 5

END
