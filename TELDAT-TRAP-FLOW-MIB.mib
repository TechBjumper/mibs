-- file automatically created


TELDAT-TRAP-FLOW-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


flowTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FLOW event subsystem."
    REVISION "201401200930Z"
    DESCRIPTION "Initial implementation"
        ::= { telEventTraps 218 }


flowEventsGroup	OBJECT IDENTIFIER	::= { flowTrapsMIB 1 }

flowNotifications	OBJECT IDENTIFIER	::= { flowTrapsMIB 2 }
flowNotificationsPrefix	OBJECT IDENTIFIER	::= { flowNotifications 0 }

flowEventObjects1 OBJECT-IDENTITY
    STATUS current
    DESCRIPTION
        "Event FLOW.1
        client state changed"
    ::= { flowEventsGroup 1 }

flow1-state OBJECT-TYPE
    SYNTAX DisplayString
    MAX-ACCESS accessible-for-notify
    STATUS current
    DESCRIPTION
        "Parameter 'state' in event FLOW.1"
    ::= { flowEventObjects1 1 }

flowEventObjects2 OBJECT-IDENTITY
    STATUS current
    DESCRIPTION
        "Event FLOW.2
        new flow created"
    ::= { flowEventsGroup 2 }

flow2-source-ip OBJECT-TYPE
    SYNTAX IpAddress
    MAX-ACCESS accessible-for-notify
    STATUS current
    DESCRIPTION
        "Parameter 'source-ip' in event FLOW.2"
    ::= { flowEventObjects2 1 }

flow2-destination-ip OBJECT-TYPE
    SYNTAX IpAddress
    MAX-ACCESS accessible-for-notify
    STATUS current
    DESCRIPTION
        "Parameter 'destination-ip' in event FLOW.2"
    ::= { flowEventObjects2 2 }

flow2-protocol OBJECT-TYPE
    SYNTAX DisplayString
    MAX-ACCESS accessible-for-notify
    STATUS current
    DESCRIPTION
        "Parameter 'protocol' in event FLOW.2"
    ::= { flowEventObjects2 3 }

flow2-expiry OBJECT-TYPE
    SYNTAX Integer32
    MAX-ACCESS accessible-for-notify
    STATUS current
    DESCRIPTION
        "Parameter 'expiry' in event FLOW.2"
    ::= { flowEventObjects2 4 }

flowEventObjects3 OBJECT-IDENTITY
    STATUS current
    DESCRIPTION
        "Event FLOW.3
        flow matched"
    ::= { flowEventsGroup 3 }

flow3-source-ip OBJECT-TYPE
    SYNTAX IpAddress
    MAX-ACCESS accessible-for-notify
    STATUS current
    DESCRIPTION
        "Parameter 'source-ip' in event FLOW.3"
    ::= { flowEventObjects3 1 }

flow3-destination-ip OBJECT-TYPE
    SYNTAX IpAddress
    MAX-ACCESS accessible-for-notify
    STATUS current
    DESCRIPTION
        "Parameter 'destination-ip' in event FLOW.3"
    ::= { flowEventObjects3 2 }

flow3-protocol OBJECT-TYPE
    SYNTAX DisplayString
    MAX-ACCESS accessible-for-notify
    STATUS current
    DESCRIPTION
        "Parameter 'protocol' in event FLOW.3"
    ::= { flowEventObjects3 3 }

flow3-expiry OBJECT-TYPE
    SYNTAX Integer32
    MAX-ACCESS accessible-for-notify
    STATUS current
    DESCRIPTION
        "Parameter 'expiry' in event FLOW.3"
    ::= { flowEventObjects3 4 }

flowEventObjects4 OBJECT-IDENTITY
    STATUS current
    DESCRIPTION
        "Event FLOW.4
        netflow v9 packet sent"
    ::= { flowEventsGroup 4 }

flow4-srvr-ip OBJECT-TYPE
    SYNTAX IpAddress
    MAX-ACCESS accessible-for-notify
    STATUS current
    DESCRIPTION
        "Parameter 'srvr-ip' in event FLOW.4"
    ::= { flowEventObjects4 1 }

flow4-srvr-port OBJECT-TYPE
    SYNTAX Integer32
    MAX-ACCESS accessible-for-notify
    STATUS current
    DESCRIPTION
        "Parameter 'srvr-port' in event FLOW.4"
    ::= { flowEventObjects4 2 }

flow4-length OBJECT-TYPE
    SYNTAX Integer32
    MAX-ACCESS accessible-for-notify
    STATUS current
    DESCRIPTION
        "Parameter 'length' in event FLOW.4"
    ::= { flowEventObjects4 3 }

flow4-flows OBJECT-TYPE
    SYNTAX Integer32
    MAX-ACCESS accessible-for-notify
    STATUS current
    DESCRIPTION
        "Parameter 'flows' in event FLOW.4"
    ::= { flowEventObjects4 4 }

flow4-template OBJECT-TYPE
    SYNTAX DisplayString
    MAX-ACCESS accessible-for-notify
    STATUS current
    DESCRIPTION
        "Parameter 'template' in event FLOW.4"
    ::= { flowEventObjects4 5 }

flowEventObjects5 OBJECT-IDENTITY
    STATUS current
    DESCRIPTION
        "Event FLOW.5
        netflow v5 packet sent"
    ::= { flowEventsGroup 5 }

flow5-srvr-ip OBJECT-TYPE
    SYNTAX IpAddress
    MAX-ACCESS accessible-for-notify
    STATUS current
    DESCRIPTION
        "Parameter 'srvr-ip' in event FLOW.5"
    ::= { flowEventObjects5 1 }

flow5-srvr-port OBJECT-TYPE
    SYNTAX Integer32
    MAX-ACCESS accessible-for-notify
    STATUS current
    DESCRIPTION
        "Parameter 'srvr-port' in event FLOW.5"
    ::= { flowEventObjects5 2 }

flow5-length OBJECT-TYPE
    SYNTAX Integer32
    MAX-ACCESS accessible-for-notify
    STATUS current
    DESCRIPTION
        "Parameter 'length' in event FLOW.5"
    ::= { flowEventObjects5 3 }

flow5-flows OBJECT-TYPE
    SYNTAX Integer32
    MAX-ACCESS accessible-for-notify
    STATUS current
    DESCRIPTION
        "Parameter 'flows' in event FLOW.5"
    ::= { flowEventObjects5 4 }

flowEventObjects6 OBJECT-IDENTITY
    STATUS current
    DESCRIPTION
        "Event FLOW.6
        flow deleted"
    ::= { flowEventsGroup 6 }

flow6-source-ip OBJECT-TYPE
    SYNTAX IpAddress
    MAX-ACCESS accessible-for-notify
    STATUS current
    DESCRIPTION
        "Parameter 'source-ip' in event FLOW.6"
    ::= { flowEventObjects6 1 }

flow6-destination-ip OBJECT-TYPE
    SYNTAX IpAddress
    MAX-ACCESS accessible-for-notify
    STATUS current
    DESCRIPTION
        "Parameter 'destination-ip' in event FLOW.6"
    ::= { flowEventObjects6 2 }

flow6-protocol OBJECT-TYPE
    SYNTAX DisplayString
    MAX-ACCESS accessible-for-notify
    STATUS current
    DESCRIPTION
        "Parameter 'protocol' in event FLOW.6"
    ::= { flowEventObjects6 3 }

flowEventObjects7 OBJECT-IDENTITY
    STATUS current
    DESCRIPTION
        "Event FLOW.7
        an ip fragment has been ignored"
    ::= { flowEventsGroup 7 }

flow7-source-ip OBJECT-TYPE
    SYNTAX IpAddress
    MAX-ACCESS accessible-for-notify
    STATUS current
    DESCRIPTION
        "Parameter 'source-ip' in event FLOW.7"
    ::= { flowEventObjects7 1 }

flow7-destination-ip OBJECT-TYPE
    SYNTAX IpAddress
    MAX-ACCESS accessible-for-notify
    STATUS current
    DESCRIPTION
        "Parameter 'destination-ip' in event FLOW.7"
    ::= { flowEventObjects7 2 }

flow7-protocol OBJECT-TYPE
    SYNTAX DisplayString
    MAX-ACCESS accessible-for-notify
    STATUS current
    DESCRIPTION
        "Parameter 'protocol' in event FLOW.7"
    ::= { flowEventObjects7 3 }

flowEventObjects8 OBJECT-IDENTITY
    STATUS current
    DESCRIPTION
        "Event FLOW.8
        an ipsec packet has been ignored"
    ::= { flowEventsGroup 8 }

flow8-source-ip OBJECT-TYPE
    SYNTAX IpAddress
    MAX-ACCESS accessible-for-notify
    STATUS current
    DESCRIPTION
        "Parameter 'source-ip' in event FLOW.8"
    ::= { flowEventObjects8 1 }

flow8-destination-ip OBJECT-TYPE
    SYNTAX IpAddress
    MAX-ACCESS accessible-for-notify
    STATUS current
    DESCRIPTION
        "Parameter 'destination-ip' in event FLOW.8"
    ::= { flowEventObjects8 2 }

flow8-protocol OBJECT-TYPE
    SYNTAX DisplayString
    MAX-ACCESS accessible-for-notify
    STATUS current
    DESCRIPTION
        "Parameter 'protocol' in event FLOW.8"
    ::= { flowEventObjects8 3 }

flowEventObjects9 OBJECT-IDENTITY
    STATUS current
    DESCRIPTION
        "Event FLOW.9
        ip packtet ignored due to sampling"
    ::= { flowEventsGroup 9 }

flow9-source-ip OBJECT-TYPE
    SYNTAX IpAddress
    MAX-ACCESS accessible-for-notify
    STATUS current
    DESCRIPTION
        "Parameter 'source-ip' in event FLOW.9"
    ::= { flowEventObjects9 1 }

flow9-destination-ip OBJECT-TYPE
    SYNTAX IpAddress
    MAX-ACCESS accessible-for-notify
    STATUS current
    DESCRIPTION
        "Parameter 'destination-ip' in event FLOW.9"
    ::= { flowEventObjects9 2 }

flow9-protocol OBJECT-TYPE
    SYNTAX DisplayString
    MAX-ACCESS accessible-for-notify
    STATUS current
    DESCRIPTION
        "Parameter 'protocol' in event FLOW.9"
    ::= { flowEventObjects9 3 }

flow9-sampling-factor OBJECT-TYPE
    SYNTAX Integer32
    MAX-ACCESS accessible-for-notify
    STATUS current
    DESCRIPTION
        "Parameter 'sampling-factor' in event FLOW.9"
    ::= { flowEventObjects9 4 }


flowNotification1 NOTIFICATION-TYPE
    OBJECTS { 
              flow1-state 
            }
    STATUS current
    DESCRIPTION
        "Notification of Event FLOW.1

        Message: 'Client $1'

        Parameters list:
              $1: flow1-state

        client state changed"
    ::= { flowNotificationsPrefix 1 }

flowNotification2 NOTIFICATION-TYPE
    OBJECTS { 
              flow2-source-ip, 
              flow2-destination-ip,
              flow2-protocol,
              flow2-expiry 
            }
    STATUS current
    DESCRIPTION
        "Notification of Event FLOW.2

        Message: 'New flow created $1->$2 protocol $3 expiry $4'

        Parameters list:
              $1: flow2-source-ip
              $2: flow2-destination-ip
              $3: flow2-protocol
              $4: flow2-expiry

        new flow created"
    ::= { flowNotificationsPrefix 2 }

flowNotification3 NOTIFICATION-TYPE
    OBJECTS { 
              flow3-source-ip, 
              flow3-destination-ip,
              flow3-protocol,
              flow3-expiry 
            }
    STATUS current
    DESCRIPTION
        "Notification of Event FLOW.3

        Message: 'Flow matched $1->$2 protocol $3 expiry $4'

        Parameters list:
              $1: flow3-source-ip
              $2: flow3-destination-ip
              $3: flow3-protocol
              $4: flow3-expiry

        flow matched"
    ::= { flowNotificationsPrefix 3 }

flowNotification4 NOTIFICATION-TYPE
    OBJECTS { 
              flow4-srvr-ip, 
              flow4-srvr-port,
              flow4-length,
              flow4-flows,
              flow4-template 
            }
    STATUS current
    DESCRIPTION
        "Notification of Event FLOW.4

        Message: 'NetflowV9 packet sent to $1:$2 length $3 number of flows $4 template $5'

        Parameters list:
              $1: flow4-srvr-ip
              $2: flow4-srvr-port
              $3: flow4-length
              $4: flow4-flows
              $5: flow4-template

        netflow v9 packet sent"
    ::= { flowNotificationsPrefix 4 }

flowNotification5 NOTIFICATION-TYPE
    OBJECTS { 
              flow5-srvr-ip, 
              flow5-srvr-port,
              flow5-length,
              flow5-flows 
            }
    STATUS current
    DESCRIPTION
        "Notification of Event FLOW.5

        Message: 'NetflowV5 packet sent to $1:$2 length $3 number of flows $4'

        Parameters list:
              $1: flow5-srvr-ip
              $2: flow5-srvr-port
              $3: flow5-length
              $4: flow5-flows

        netflow v5 packet sent"
    ::= { flowNotificationsPrefix 5 }

flowNotification6 NOTIFICATION-TYPE
    OBJECTS { 
              flow6-source-ip, 
              flow6-destination-ip,
              flow6-protocol 
            }
    STATUS current
    DESCRIPTION
        "Notification of Event FLOW.6

        Message: 'Flow deleted $1->$2 protocol $3'

        Parameters list:
              $1: flow6-source-ip
              $2: flow6-destination-ip
              $3: flow6-protocol

        flow deleted"
    ::= { flowNotificationsPrefix 6 }

flowNotification7 NOTIFICATION-TYPE
    OBJECTS { 
              flow7-source-ip, 
              flow7-destination-ip,
              flow7-protocol 
            }
    STATUS current
    DESCRIPTION
        "Notification of Event FLOW.7

        Message: 'IP fragment ignored $1->$2 protocol $3'

        Parameters list:
              $1: flow7-source-ip
              $2: flow7-destination-ip
              $3: flow7-protocol

        an ip fragment has been ignored"
    ::= { flowNotificationsPrefix 7 }

flowNotification8 NOTIFICATION-TYPE
    OBJECTS { 
              flow8-source-ip, 
              flow8-destination-ip,
              flow8-protocol 
            }
    STATUS current
    DESCRIPTION
        "Notification of Event FLOW.8

        Message: 'Ipsec packet ignored $1->$2 protocol $3'

        Parameters list:
              $1: flow8-source-ip
              $2: flow8-destination-ip
              $3: flow8-protocol

        an ipsec packet has been ignored"
    ::= { flowNotificationsPrefix 8 }

flowNotification9 NOTIFICATION-TYPE
    OBJECTS { 
              flow9-source-ip, 
              flow9-destination-ip,
              flow9-protocol,
              flow9-sampling-factor 
            }
    STATUS current
    DESCRIPTION
        "Notification of Event FLOW.9

        Message: 'IP packet sampled $1->$2 protocol $3 factor $4'

        Parameters list:
              $1: flow9-source-ip
              $2: flow9-destination-ip
              $3: flow9-protocol
              $4: flow9-sampling-factor

        ip packtet ignored due to sampling"
    ::= { flowNotificationsPrefix 9 }

flowNotification10 NOTIFICATION-TYPE
    STATUS current
    DESCRIPTION
        "Notification of Event FLOW.10

        Message: 'IP packet procesing error'

        ip packtet processing error"
    ::= { flowNotificationsPrefix 10 }


END
