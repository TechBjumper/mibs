LUMINOUS-SHELF-MIB DEFINITIONS ::= BEGIN
    IMPORTS
            MODULE-IDENTITY, OBJECT-TYPE, NOTIFICATION-TYPE,
            ObjectName, Integer32, Counter32, Unsigned32, TimeTicks, enterprises
                                    FROM SNMPv2-SMI
            MacAddress, DisplayString, TruthValue
                                    FROM SNMPv2-TC
            LumSlotNum, LumAdminStatus, LumOperStatus,
            LumName, LumDescr, LumPortNum, LumSimpleIndex,
            LumAlarmSeverity, LumCardBaseType, LumCardType,
            LumVersionString, LumSerialNumString,  LumCleiString,
            LumCardAdminState, LumCardOperState, LumCardFailureState,
            LumShelfType, LumChassisPlane, LumImageState, LumDateTimeString,
            LumPercent, LumManufactureString
                                    FROM LUMINOUS-TC-MIB;


  -- IANA-registered  Luminous Network Enterprise Number of 4614

     luminous OBJECT IDENTIFIER ::= { enterprises 4614}

  -- leaving tree-space for the future products:

     lumADM   OBJECT IDENTIFIER ::= { luminous 1}


  --  This MIB module defines Shelf and Card groups.

     lumADMShelfMIB  MODULE-IDENTITY        
        LAST-UPDATED "0012140000Z"
        ORGANIZATION "Luminous Networks"
        CONTACT-INFO 
                        "  Luminous Technical Support

                        Postal: Luminous Networks,
                                14060 Bubb Road,
                                Cupertino, CA 95014

                        Tel: +1 408 342 6400
                        Fax: +1 408 863 1100
                        E-mail: support@luminous.com"
        DESCRIPTION  "The Luminous Shelf MIB contains         
                    Information related to the  
                    equipment contained in Luminous
                    Shelf." 

        REVISION     "0107050000Z"
        DESCRIPTION "Added lumShelfSyncType"

        REVISION     "0106270000Z"
        DESCRIPTION "Added lumCardType values:
                        asi(34)
                        asiIOIn(35)
                        asiIOIn(36)
                        gigERouting(37)
                        unknown(38)"

        REVISION     "0106270000Z"
        DESCRIPTION "Added new lumAlarmSummaryGroup and lumAlarmSummaryChangeTrap."

        REVISION     "0106210000Z"
        DESCRIPTION "Added lumCardType values:
                        ether24(32)
                        ether24IO(33)"

        REVISION     "0106130000Z"
        DESCRIPTION "1. Change name of T1CrossConnect to
                        TDM CrossConnect, and use TC's from
                        shelf.my
                    2.  Add TdmConnectType attribute"

        REVISION     "0105240000Z"
        DESCRIPTION "Added lumCardType values:
            
                        wdmBand1(24),
                        wdmBand2(25),
                        wdmBand3(26),
                        wdmBand4(27),
                        ds3cc12(28),
                        ds3cc12IO(29),
                        t3cc12(30),
                        e3cc12(31)"

        REVISION     "0103151330Z"
        DESCRIPTION "Added new objects to lumCardTable:
                        lumCardPROMVersion
                        lumCardManufacDateAndLocation
                        lumCardCPULast2Seconds
                        lumCardCPULast1Minute
                        lumCardCPULast10Minutes
                        lumCardTotalRAMMemory
                        lumCardRAMMemoryUsed
                    
                    Added to the Shelf Group:
                        lumShelfCurrentTime."

        REVISION     "0103130000Z"
        DESCRIPTION "Added lumCardType values:
                     ring2(20),
                     ring2IO(21) "

        REVISION     "0101260000Z"
        DESCRIPTION "Added lumCardType values:
                     sysconR(20),
                     ringIOLR(21) "

        REVISION     "0012140000Z"
        DESCRIPTION "Added CardOperStates values of 
                      present(7) and initializing(8)."
 
        REVISION     "0012080000Z"
        DESCRIPTION "Added wdm(18) and wdmIO(19) value
                      to lumCardType. Changed value of
                      newCardType(20) from 18 to 20"

        REVISION     "0010100000Z"
        DESCRIPTION "Added newCardType(18) value to
                      lumCardType."

        REVISION     "0009260000Z"
        DESCRIPTION " Two shelf objects were made writable:
                    - lumPrimaryOptinetClockSourcePort
                    - lumSecondaryOptinetClockSourcePort

                    A new shelf object is introduced:
                    - lumCurrentOptinetClockSourcePort
                    - *accecpted* typo corrected."

        REVISION     "0009190000Z"
        DESCRIPTION "lumShelfType of adm1000(1)removed;
                    remaining values decrimented"

        REVISION     "0008240000Z"
        DESCRIPTION "1. lumNodeType's MAX-ACCESS changed
                        from read-only to read-write.
                    2. two new objects in the shelf
                        group:
                        - lumPrimaryOptinetClockSourcePort
                        - lumSecondaryOptinetClockSourcePort "

        REVISION     "0008150000Z"
        DESCRIPTION "1.Added gigE and gigEIO card types."

        REVISION     "0007280000Z"
        DESCRIPTION "1.Added flash image versions and
                        stats info.  
                    2.Added card reset in-progress."

        REVISION     "0007140000Z"
        DESCRIPTION "1. Description for allowed values of lumCardAdminState
                        added.
        MAX-ACCESS clause
                        changed to read-write to
                        allow slot pre-allocation.
        DESCRIPTION
                        clause filled in."

        REVISION     "0006300000Z"
        DESCRIPTION "1. Description clauses filled in.
                    2. lumShelfType values added to
                        reflect the actual naming scheme.
                    3. CardType oc12(12) and oc12IO(13) added.  
                    4. lumCardOperState down(6) 
                        added: a card in present in
                        the slot not but not
                        responding. 
                    5. lumCardAdminState value of reset(6) added.
                    6. lumCardAdminState value of switchover(7) added
                    7. lumStandbySlot read-write object added
                    8. lumShelfCommand added. When 
                        setting to a value of 
                        reset(2) the shelf reset
                        will result."   
    ::= { lumADM    1}

--
-- Textual Conventions
-- 

---
-- MIB Objects
--

    lumADMShelf OBJECT IDENTIFIER ::= { lumADMShelfMIB 1}

    lumNodeId  OBJECT-TYPE
        SYNTAX  Integer32
        MAX-ACCESS read-only
        STATUS  current
        DESCRIPTION  "Used to identify the node."
        ::= { lumADMShelf 1 }

    lumShelfId  OBJECT-TYPE
        SYNTAX  OCTET STRING (SIZE(1..80))
        MAX-ACCESS read-only
        STATUS  current
        DESCRIPTION  "Shelf ID"
        ::= { lumADMShelf 2 }
 
    lumNodeType  OBJECT-TYPE
        SYNTAX  INTEGER {
                        co(1),
                        cpe(2)
                        }
        MAX-ACCESS read-write
        STATUS    current
        DESCRIPTION  "A Central Office(CO) or Customer Premise Equipment(CPE).
                    CO nodes act as timing sources for the ring."
        ::= { lumADMShelf 3 }

    lumShelfType   OBJECT-TYPE
        SYNTAX  LumShelfType
        MAX-ACCESS read-only
        STATUS  current
        DESCRIPTION  "LMS shelf type. This object may be used
                        to identify Luminous shelves/nodes types."
        ::= { lumADMShelf 4 }

    lumShelfHWVersion OBJECT-TYPE
        SYNTAX  LumVersionString
        MAX-ACCESS read-only
        STATUS  current
        DESCRIPTION  "The Shelf Hardware Version."
        ::= { lumADMShelf   5 }

    lumShelfSerialNumber OBJECT-TYPE
        SYNTAX  LumSerialNumString
        MAX-ACCESS read-only
        STATUS  current
        DESCRIPTION  "Luminous assigned Shelf Serial Number"
        ::= { lumADMShelf 6 }

    lumShelfCleiCode  OBJECT-TYPE
        SYNTAX  LumCleiString
        MAX-ACCESS read-only
        STATUS  current
        DESCRIPTION  "The CLEI code of the shelf."
        ::= { lumADMShelf 7 }

    lumShelfManufactureDate  OBJECT-TYPE
        SYNTAX  LumManufactureString    
        MAX-ACCESS read-only
        STATUS  current
        DESCRIPTION  "The date this shelf has been manufactured."
        ::= { lumADMShelf 8 }

    lumNodeStatus                 OBJECT-TYPE
        SYNTAX  INTEGER  { 
                        normal(1),
                        minorAlarm(2),
                        minorFailure(3),
                        criticalFailure(4)
                        }
        MAX-ACCESS read-only
        STATUS  current
        DESCRIPTION  "
                        minorAlarm(2) indicates that no action is
                        needed but some alarming event has happened.

                        minorFailure(3) indicates that a fault has
                        occured but does not persist. The action
                        from the management may not be needed.

                        criticalFailure(4) indicates that
                        the shelf cannot function properly.
                        The management action is recommended
                        (can be even reset or, if mulfunctioning,
                        be replace) to correct the problem.
                        Otherwise the problem may persist.

                        This field is only an indication to the
                        management of the failure/alarm occured.
                        The management may decide to discover the
                        route cause of the problem by analizing
                        MIB objects on this and other shelves."
        ::= { lumADMShelf 9 }

    lumShelfChanges             OBJECT-TYPE
        SYNTAX  Counter32
        MAX-ACCESS read-only
        STATUS  current
        DESCRIPTION  "Number of shelf changes such
                        as card inserts/removes, switchovers,
                        downloads (i.e. ones resulting
                        in traps) since the last reboot."
        ::= { lumADMShelf 10 }

    lumShelfCommand        OBJECT-TYPE 
        SYNTAX  INTEGER {
                        none (1),         
                        reset (2)                             
                        }
        MAX-ACCESS read-write
        STATUS  current
        DESCRIPTION  "reset (2) - resets the shelf."
        ::= { lumADMShelf 11 }

    lumPrimaryOptinetClockSourcePort OBJECT-TYPE
        SYNTAX  Integer32
        MAX-ACCESS read-write
        STATUS  current
        DESCRIPTION  "ifIndex of the port desired to be used as as a primary
                        optinet clock source. Can be set on CO nodes only."
        DEFVAL {0}
        ::= { lumADMShelf 12 }

    lumSecondaryOptinetClockSourcePort OBJECT-TYPE
        SYNTAX  Integer32
        MAX-ACCESS read-write
        STATUS  current
        DESCRIPTION  "ifIndex of the port desired to be used as as a secondary
                        optinet clock source.  Can be set on CO nodes only."
        DEFVAL {0}
        ::= { lumADMShelf 13 }


    lumCurrentOptinetClockSourcePort OBJECT-TYPE
        SYNTAX  INTEGER { 
                        none (1),
                        internal(2),
                        primary(3),
                        secondary(4),
                        clockWise(5),
                        counterClockWise(6)
                        }
        MAX-ACCESS read-only
        STATUS  current
        DESCRIPTION  "The current source of the optinet clock. 
                        
                        primary(3),
                        secondary(4)
                            can be reported only on CO nodes, and indicate 
                            which clock source has been currently selected 
                            by this CO node.

                        clockWise(5),
                        counterClockWise(6)
                            can be reported only on CPE nodes and indicate 
                            the ring direction to the closest CO node from 
                            where the clock source is taken.

                        none(1)
                            indicates that the clock source has not been chosen.

                        internal(2)
                            indicates a node using its internal oscillator 
                            for a clock source. The internal oscillator is 
                            an oven-controlled oscillator (OCXO)
                            on the switch(ring) card."
        ::= { lumADMShelf 14 }

    lumShelfCurrentTime  OBJECT-TYPE
        SYNTAX  LumDateTimeString
        MAX-ACCESS read-only
        STATUS  current
        DESCRIPTION  "The current date and time on this shelf."
        ::= { lumADMShelf 15 }

    lumSyncType  OBJECT-TYPE
        SYNTAX  INTEGER {
                        nonRevertive(1),
                        revertive(2)
                        }
        MAX-ACCESS read-write
        STATUS    current
        DESCRIPTION  "This control the behaviour of the timing synchronisation for
                    this node."
        ::= { lumADMShelf 16 }

     -- The ADM MIB  Card Table


     lumADMCard OBJECT IDENTIFIER ::= { lumADMShelfMIB 2}

 
    lumADMCardTable OBJECT-TYPE
        SYNTAX  SEQUENCE OF LumADMCardEntry 
        MAX-ACCESS not-accessible
        STATUS  current
        DESCRIPTION
                "Luminous Card Table."
        ::= { lumADMCard 1   }

    lumADMCardEntry OBJECT-TYPE
        SYNTAX      LumADMCardEntry 
        MAX-ACCESS  not-accessible
        STATUS      current
        DESCRIPTION "."
        INDEX   { lumShelfPlane,
                lumSlotID }
        ::= { lumADMCardTable 1 }

    LumADMCardEntry ::= SEQUENCE {
            lumShelfPlane                   LumChassisPlane,
            lumSlotID                       LumSlotNum,
            lumCardType                     LumCardType,
            lumCardHWVersion                LumVersionString,
            lumCardSWVersion                LumVersionString,
            lumCardSerialNumber             LumSerialNumString,
            lumCardCleiCode                 LumCleiString,
            lumCardLEDs                     OCTET STRING,
            lumCardOperState                LumCardOperState,
            lumCardAdminState               LumCardAdminState,
            lumCardFailureState             LumCardFailureState,
            lumCardNumbOfPorts              LumPortNum,
            lumCardVoltage                  Unsigned32,
            lumCardTemperature              Unsigned32,
            lumCardCPUtilization            LumPercent,
            lumCardNVMemoryAvailable        Unsigned32,
            lumCardNVMemoryUsed             Unsigned32,
            lumCardUpTime                   TimeTicks,
            lumStandbySlot                  LumSlotNum,
            lumCardFlashImage1Ver           LumVersionString,
            lumCardFlashImage2Ver           LumVersionString,
            lumCardFlashImage3Ver           LumVersionString,
            lumCardFlashImage1State         LumImageState,
            lumCardFlashImage2State         LumImageState,
            lumCardFlashImage3State         LumImageState,                 
            lumCardResetInProgress          TruthValue,
            lumCardPROMVersion              LumVersionString,
            lumCardManufDateAndLocation     LumManufactureString,
            lumCardCPULast2Seconds          LumPercent,
            lumCardCPULast1Minute           LumPercent,
            lumCardCPULast10Minutes         LumPercent,
            lumCardTotalRAMMemory           Unsigned32,
            lumCardRAMMemoryUsed            Unsigned32,
            lumCardBaseType                 LumCardBaseType
      }

    lumShelfPlane  OBJECT-TYPE
        SYNTAX  LumChassisPlane
        MAX-ACCESS read-only
        STATUS  current
        DESCRIPTION  "Either front or back plane."
        ::= { lumADMCardEntry 1 }

    lumSlotID    OBJECT-TYPE
        SYNTAX  LumSlotNum
        MAX-ACCESS read-only
        STATUS  current
        DESCRIPTION  "Starts with 1 for the both front plane
                       and for the back plane. The second
                       slot of the double-slot cards is
                       reported as with lumCardType equal to 
                       none(1)."
        ::= { lumADMCardEntry 2 }

    lumCardType OBJECT-TYPE
        SYNTAX  LumCardType
        MAX-ACCESS read-write
        STATUS  current
        DESCRIPTION  "The type of a card in the slot.
                           none(1)indicates that
                           the card is either not present
                           in the slot. 
                           present(38)indicates that
                           the card is present but not
                           responding. 

                           In order to pre-allocate a slot
                           for a particular card type, an
                           SNMP Manager must change the value
                           of a lumCardType object instance
                           from the value of none(1) to the 
                           desired value."
        ::= { lumADMCardEntry 3 }
      
    lumCardHWVersion            OBJECT-TYPE
        SYNTAX  LumVersionString
        MAX-ACCESS read-only
        STATUS  current
        DESCRIPTION  "The version of the card's hardware."
        ::= { lumADMCardEntry 4 }

    lumCardSWVersion            OBJECT-TYPE
        SYNTAX  LumVersionString
        MAX-ACCESS read-only
        STATUS  current
        DESCRIPTION  "The version of the card's software."
        ::= { lumADMCardEntry 5 }

    lumCardSerialNumber     OBJECT-TYPE
        SYNTAX  DisplayString
        MAX-ACCESS read-only
        STATUS  current
        DESCRIPTION  "The card's Serial Number."
        ::= { lumADMCardEntry 6 }

    lumCardCleiCode         OBJECT-TYPE
        SYNTAX  DisplayString
        MAX-ACCESS read-only
        STATUS  current
        DESCRIPTION  "The cards CLEI code."
        ::= { lumADMCardEntry 7 }

    lumCardLEDs             OBJECT-TYPE
        SYNTAX  OCTET STRING (SIZE (0..24))
        MAX-ACCESS read-only
        STATUS  current
        DESCRIPTION  "Each byte is a LED.   1 - off; 2 - on; "
        ::= { lumADMCardEntry 8 }

    lumCardOperState            OBJECT-TYPE
        SYNTAX  LumCardOperState
        MAX-ACCESS read-only
        STATUS  current
        DESCRIPTION  "The Operational State indicates the
                        current state of the card"
        ::= { lumADMCardEntry 9 }

    lumCardAdminState        OBJECT-TYPE 
        SYNTAX  LumCardAdminState
        MAX-ACCESS read-write
        STATUS  current
        DESCRIPTION  "This object indicates the state transition
                        desired by the management. 

                        Below are the valid values that SNMP Manager
                        can set, depending on lumCardType:

                            lumCardType  lumCardAdminState SET request
                            ===========  =============================

                            syscon(2)    switchover(7)

                            ring(3)      switchover(7)

                            t1(4)        active(1), standby(2), 
                                         outOfService(4),  reset(6),
                                         switchover(7)

                            ether(5)     active(1), standby(2),
                                         outOfService(4),  reset(6) 

                         Other values set by SNMP Manager for the 
                         cards above, or any value set for other cards
                         will be rejected by SNMP Agent."
        ::= { lumADMCardEntry 10 }

    lumCardFailureState     OBJECT-TYPE
        SYNTAX  LumCardFailureState
        MAX-ACCESS read-only
        STATUS  current
        DESCRIPTION  "Failure state of the card."
        ::= { lumADMCardEntry 11 }

    lumCardNumbOfPorts   OBJECT-TYPE
        SYNTAX  Unsigned32 
        MAX-ACCESS read-only
        STATUS  current
        DESCRIPTION  "The total number of ports on this card."
        ::= { lumADMCardEntry 12 }

    lumCardVoltage   OBJECT-TYPE
        SYNTAX  Unsigned32 
        MAX-ACCESS read-only
        STATUS  current
        DESCRIPTION  "The current card voltage as
                        measured by the voltage sensors."
        ::= { lumADMCardEntry 13 }

    lumCardTemperature   OBJECT-TYPE
        SYNTAX  Unsigned32 
        MAX-ACCESS read-only
        STATUS  current
        DESCRIPTION  "The current card temperature as
                        measured by the temperature sensors."
        ::= { lumADMCardEntry 14 }

    lumCardCPUtilization        OBJECT-TYPE
        SYNTAX  LumPercent
        MAX-ACCESS read-only
        STATUS  current
        DESCRIPTION  "The cards main CPU utilization in percents.
                        Its expected that this field may oscilate
                        and should not be taken for granted.
                        When CPU utilization reaches 100%, the 
                        card may have no spare CPU cycles to
                        actually report it."
        ::= { lumADMCardEntry 15 }

    lumCardNVMemoryAvailable    OBJECT-TYPE
        SYNTAX  Unsigned32
        MAX-ACCESS read-only
        STATUS  current
        DESCRIPTION  "The currently available to use
                        part of the non-volatile memory."
        ::= { lumADMCardEntry 16 }

    lumCardNVMemoryUsed     OBJECT-TYPE
        SYNTAX  Unsigned32
        MAX-ACCESS read-only
        STATUS  current
        DESCRIPTION  "The currently unavailable 
                        part of the non-volatile memory."
        ::= { lumADMCardEntry 17 }

    lumCardUpTime           OBJECT-TYPE
        SYNTAX  TimeTicks
        MAX-ACCESS read-only
        STATUS  current
        DESCRIPTION  "Time of the last reboot relative
                        to SYSCON sysUpTime."
        ::= { lumADMCardEntry 18 }

    lumStandbySlot      OBJECT-TYPE
        SYNTAX    LumSlotNum
        MAX-ACCESS read-write
        STATUS    current
        DESCRIPTION "The slot number of the card that
                     serves as a standby for this
                     card. SNMP Manager must set a
                     desired card to standby state before
                     attempting to set lumStandbySlot
                     object's instance to to the
                     value of that's slot."
        DEFVAL {0}
        ::= { lumADMCardEntry 19 }
       
    lumCardFlashImage1Ver     OBJECT-TYPE
        SYNTAX   LumVersionString
        MAX-ACCESS read-only
        STATUS   current
        DESCRIPTION  "The version number of the flash image #1."
        ::= { lumADMCardEntry 20 }

    lumCardFlashImage2Ver     OBJECT-TYPE
        SYNTAX   LumVersionString
        MAX-ACCESS read-only
        STATUS   current
        DESCRIPTION  "The version number of the flash image #2."
        ::= { lumADMCardEntry 21 }

    lumCardFlashImage3Ver     OBJECT-TYPE
        SYNTAX   LumVersionString
        MAX-ACCESS read-only
        STATUS   current
        DESCRIPTION  "The version number of the flash image #3."
        ::= { lumADMCardEntry 22 }
       
    lumCardFlashImage1State    OBJECT-TYPE
        SYNTAX  LumImageState
        MAX-ACCESS read-only
        STATUS   current
        DESCRIPTION  "The state of the flash image #1."
        DEFVAL { unknown }
        ::= { lumADMCardEntry 23 }

    lumCardFlashImage2State    OBJECT-TYPE
        SYNTAX  LumImageState
        MAX-ACCESS read-only
        STATUS   current
        DESCRIPTION  "The state of the flash image #2."
        DEFVAL { unknown }
        ::= { lumADMCardEntry 24 }
      
    lumCardFlashImage3State    OBJECT-TYPE
        SYNTAX  LumImageState
        MAX-ACCESS read-only
        STATUS   current
        DESCRIPTION  "The version number of the flash image #3."
        DEFVAL { unknown }
        ::= { lumADMCardEntry 25 }

    lumCardResetInProgress      OBJECT-TYPE
        SYNTAX  TruthValue 
        MAX-ACCESS read-only
        STATUS   current
        DESCRIPTION  "The card reset indicator."
        DEFVAL { false }
        ::= { lumADMCardEntry 26 }

    lumCardPROMVersion        OBJECT-TYPE
        SYNTAX  LumVersionString
        MAX-ACCESS read-only
        STATUS  current
        DESCRIPTION  "The version of the PROM on this card."
        ::= { lumADMCardEntry 27 }

    lumCardManufDateAndLocation OBJECT-TYPE
        SYNTAX  LumManufactureString
        MAX-ACCESS read-only
        STATUS  current
        DESCRIPTION  "The date and location where the
                        card has been manufactured."
        ::= { lumADMCardEntry 28 }

    lumCardCPULast2Seconds      OBJECT-TYPE
        SYNTAX  LumPercent
        MAX-ACCESS read-only
        STATUS  current
        DESCRIPTION  "The cards main CPU utilization during the last
                       two seconds in percents multiplied by hundred."
        ::= { lumADMCardEntry 29 }

    lumCardCPULast1Minute    OBJECT-TYPE
        SYNTAX  LumPercent
        MAX-ACCESS read-only
        STATUS  current
        DESCRIPTION  "The cards main CPU utilization during the last
                     one minute in percents multiplied by hundred."
        ::= { lumADMCardEntry 30 }

    lumCardCPULast10Minutes    OBJECT-TYPE
        SYNTAX  LumPercent
        MAX-ACCESS read-only
        STATUS  current
        DESCRIPTION  "The cards main CPU utilization during the last
                        ten minutes in percents multiplied by hundred."
        ::= { lumADMCardEntry 31 }

    lumCardTotalRAMMemory     OBJECT-TYPE
        SYNTAX  Unsigned32
        MAX-ACCESS read-only
        STATUS  current
        DESCRIPTION  "The total RAM memory on this card in bytes."
        ::= { lumADMCardEntry 32 }

    lumCardRAMMemoryUsed         OBJECT-TYPE
        SYNTAX  Unsigned32
        MAX-ACCESS read-only
        STATUS  current
        DESCRIPTION  "The RAM memory used on this card in bytes."
        ::= { lumADMCardEntry 33 }

    lumCardBaseType OBJECT-TYPE
        SYNTAX  LumCardBaseType
        MAX-ACCESS read-only
        STATUS  current
        DESCRIPTION  "The base type of a card in the slot."
        ::= { lumADMCardEntry 34 }
      
END
