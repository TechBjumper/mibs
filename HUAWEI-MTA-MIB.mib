HUAWEI-MTA-MIB DEFINITIONS ::= BEGIN
IMPORTS
	MODULE-IDENTITY, OBJECT-TYPE
		FROM SNMPv2-SMI

	Integer32
		FROM SNMPv2-SMI
	RowStatus
		FROM SNMPv2-TC
        hwFrameIndex,hwSlotIndex,hwPortIndex
                FROM HUAWEI-DEVICE-MIB
	huaweiUtility 
                FROM HUAWEI-MIB;

hwMTA MODULE-IDENTITY
			LAST-UPDATED "200210010900Z"
			ORGANIZATION
				"
				 "
			CONTACT-INFO
				"
				
				"
	DESCRIPTION "V01-01  
				mta MIB:HUAWEI-MTA-MIB.mib V1.0 
				tangrong 17270/huawei, liguanrong 26321/huawei, liaoshunquan 24705/huawei, 
				wangxinran 19281/huawei, liuguoping 17383/huawei, wangxiaoman 20905/huawei, 
				luohui 14047/huawei, chenjiangming 18851/huawei, liuchenglong 25279/huawei, 
				zhuyangbin 30583/huawei, weijiahong 14192/huawei, zhoupeng 22164/huawei, 
				xucongyuan 17403/huawei "
	::= { huaweiUtility 14 }

		hwMTAMibObjects       OBJECT IDENTIFIER  ::= { hwMTA   1 }
		hwMTAMibTrap OBJECT IDENTIFIER ::= { hwMTA 2 }
	hwMTATrapOid      OBJECT IDENTIFIER    ::= { hwMTAMibTrap  1 }
	hwMTATrapsDefine  OBJECT IDENTIFIER    ::= { hwMTAMibTrap  2 }
	hwMTATraps        OBJECT IDENTIFIER    ::= { hwMTATrapsDefine  0 }
			
		hwMTAMibCompance      OBJECT IDENTIFIER  ::= { hwMTA   3 }

  mtaTable OBJECT-TYPE
    SYNTAX      SEQUENCE OF MtaEntry
    MAX-ACCESS  not-accessible
    STATUS      current
    DESCRIPTION
      "MTA"
    ::= { hwMTAMibObjects 1 }

  mtaEntry OBJECT-TYPE
    SYNTAX      MtaEntry
    MAX-ACCESS  not-accessible
    STATUS      current
    DESCRIPTION
      "MTA"
    INDEX    {  
              hwFrameIndex,
              hwSlotIndex,
              hwPortIndex
             }
    ::= { mtaTable 1 }

  MtaEntry ::=
    SEQUENCE
    {
      hwMtaState	INTEGER,
      hwMtaHardWareVersion	OCTET STRING,
      hwMtaSoftWareVersion	OCTET STRING,
      hwMtaProtocol	INTEGER,
      hwChannel1Mode	INTEGER,
      hwChannel1Rate	INTEGER,
      hwChannel1DteDce	INTEGER,
      hwChannel1Clock	INTEGER,
      hwChannel1SignalLinePhase	Integer32,
      hwChannel1AsynLen	Integer32,
      hwChannel1BChannelNo	INTEGER,
      hwChannel1EnvolopPhase	INTEGER,
      hwChannel1Status	INTEGER,
      hwChannel2Mode	INTEGER,
      hwChannel2Rate	INTEGER,
      hwChannel2DteDce	INTEGER,
      hwChannel2Clock	INTEGER,
      hwChannel2SignalLinePhase	Integer32,
      hwChannel2AsynLen	Integer32,
      hwChannel2BChannelNo	INTEGER,
      hwChannel2EnvolopPhase	INTEGER,
      hwChannel2Status	INTEGER,
      hwChannel3Mode	INTEGER,
      hwChannel3Rate	INTEGER,
      hwChannel3DteDce	INTEGER,
      hwChannel3Clock	INTEGER,
      hwChannel3SignalLinePhase	Integer32,
      hwChannel3AsynLen	Integer32,
      hwChannel3BChannelNo	INTEGER,
      hwChannel3EnvolopPhase	INTEGER,
      hwChannel3Status	INTEGER,
      hwUserIdentity	OCTET STRING,
      hwMaintainOper	INTEGER,
      hwLoopObject	INTEGER,
      hwChannel1AlarmStatus	Integer32,
      hwChannel2AlarmStatus	Integer32,
      hwChannel3AlarmStatus	Integer32,
      hwBChannel1AlarmStatus	Integer32,
      hwBChannel2AlarmStatus	Integer32,
      hwRowStatus	RowStatus
    }

  hwMtaState OBJECT-TYPE
    SYNTAX      INTEGER{normal(1),waitCfg(2),cfgError(3),selfTestError(4),fault(5)}
    MAX-ACCESS  read-only
    STATUS      current
    DESCRIPTION
        " 
          the current state of MTA device, including 1.normal, 2.waiting config, 
          3.new config error, 4.self detect failed, 5.MTA fault
        "
    ::= { mtaEntry 1 }

  hwMtaHardWareVersion OBJECT-TYPE
    SYNTAX      OCTET STRING (SIZE (0..20))
    MAX-ACCESS  read-only
    STATUS      current
    DESCRIPTION
        " 
          the current hardware version of MTA device
        "
    ::= { mtaEntry 2 }

  hwMtaSoftWareVersion OBJECT-TYPE
    SYNTAX      OCTET STRING (SIZE (0..20))
    MAX-ACCESS  read-only
    STATUS      current
    DESCRIPTION
        " 
          the current software version of MTA device
        "
    ::= { mtaEntry 3 }

  hwMtaProtocol OBJECT-TYPE
    SYNTAX      INTEGER{honet(1), x50SBitLoop(2),x50SBitEqu1(3), x50SBitEqu0(4), i460(5)}
    MAX-ACCESS  read-create
    STATUS      current
    DESCRIPTION
        " 
          the protocol that MTA support, including:1. Defined privately by HONET, 2. x.50 s bit loop, 
          3. x.50 s bit=1, 4. x.50 s bit=0 5. I.460 protocol. ( the 4th and 5th is not supported now)
           "
    DEFVAL      { 3 }
    ::= { mtaEntry 4 }

  hwChannel1Mode OBJECT-TYPE
    SYNTAX      INTEGER{syn(1),asyn(2),prohibit(3)}
    MAX-ACCESS  read-create
    STATUS      current
    DESCRIPTION
        " 
          determine working mode of channel 1: a syn. mode, an asyn. mode, or a prohibited mode
           "
    DEFVAL      { 1 }
    ::= { mtaEntry 5 }

  hwChannel1Rate OBJECT-TYPE
    SYNTAX      INTEGER {r2400bps(1),r4800bps(2),r9600bps(3),r19200bps(4),r64000bps(5),r128000bps(6) }
    MAX-ACCESS  read-create
    STATUS      current
    DESCRIPTION
        " 
          determine the service speed of channel 1
           "
    DEFVAL      { 2 }
    ::= { mtaEntry 6 }

  hwChannel1DteDce OBJECT-TYPE
    SYNTAX      INTEGER{dCE(1),dTE(2)}
    MAX-ACCESS  read-create
    STATUS      current
    DESCRIPTION
        " 
          determine the polarity of channel 1: DCE or DTE
           "
    DEFVAL      { 2 }
    ::= { mtaEntry 7 }

  hwChannel1Clock OBJECT-TYPE
    SYNTAX      INTEGER{internal(1),external(2),slave(3)}
    MAX-ACCESS  read-create
    STATUS      current
    DESCRIPTION
        " 
          the clock locked mode of channel 1: 1. Internal means the clock in MTA device, 
          2.External means the superior device's clock, 3. Slave means the clock of device access to this channel
           "
    DEFVAL      { 1 }
    ::= { mtaEntry 8 }

  hwChannel1SignalLinePhase OBJECT-TYPE
    SYNTAX      Integer32(0..15)
    MAX-ACCESS  read-create
    STATUS      current
    DESCRIPTION
        "
          the signal line phase of channel 1, determined by four bits of which the less significant defines 
          the clock sending phase, the 2th the clock receiving phase, the 3th the data sending phase, the 4th the data receiving phase.
          and value 1 means reverse phase, value 0 means in-phase.
           "
    DEFVAL      { 0 }
    ::= { mtaEntry 9 }

  hwChannel1AsynLen OBJECT-TYPE
    SYNTAX      Integer32(6..12)
    MAX-ACCESS  read-create
    STATUS      current
    DESCRIPTION
        " 
          the word length of channel 1 working in the asynchro mode, including the starting bit,the data bits and the end bit
           "
    DEFVAL      { 8 }
    ::= { mtaEntry 10 }

  hwChannel1BChannelNo OBJECT-TYPE
    SYNTAX      INTEGER {b1(1),b2(2)}
    MAX-ACCESS  read-create
    STATUS      current
    DESCRIPTION
        " 
        determins the B channel N.O. to carry the data in channel 1
           "
    DEFVAL      { 1 }
    ::= { mtaEntry 11 }

  hwChannel1EnvolopPhase OBJECT-TYPE
    SYNTAX      INTEGER{sequence(1),interleave(2)}
    MAX-ACCESS  read-create
    STATUS      current
    DESCRIPTION
        " 
        determins the envolop phase to carry the data in channel 1
           "
    DEFVAL      { 1 }
    ::= { mtaEntry 12 }

  hwChannel1Status OBJECT-TYPE
    SYNTAX      INTEGER{idle(1),normal(2),localLoop(3),remoteLoop(4),block(5),bChannelLocalLof(6),dteNotReady(7),bChannelRemoteLof(8),bChannelLocalLoop(9),bChannelRemoteLoop(10),fault(11)}
    MAX-ACCESS  read-only
    STATUS      current
    DESCRIPTION
        " 
        describes the current state of channel 1
         "
    DEFVAL      { 1 }
    ::= { mtaEntry 13 }

  hwChannel2Mode OBJECT-TYPE
    SYNTAX      INTEGER{syn(1),asyn(2),prohibit(3)}
    MAX-ACCESS  read-create
    STATUS      current
    DESCRIPTION
        " 
          determine working mode of channel 2: a syn. mode, an asyn. mode, or a prohibited mode
         "
    DEFVAL      { 1 }
    ::= { mtaEntry 14 }

  hwChannel2Rate OBJECT-TYPE
    SYNTAX      INTEGER {
                         r2400bps(1),
                         r4800bps(2),
                         r9600bps(3),
                         r19200bps(4),
                         r64000bps(5),
                         r128000bps(6) 
                         }
    MAX-ACCESS  read-create
    STATUS      current
    DESCRIPTION
        " 
          determine the service speed of channel 2
       "
    DEFVAL      { 2 }
    ::= { mtaEntry 15 }

  hwChannel2DteDce OBJECT-TYPE
    SYNTAX      INTEGER{dCE(1),dTE(2)}
    MAX-ACCESS  read-create
    STATUS      current
    DESCRIPTION
        " 
          determine the polarity of channel 2: DCE or DTE
         "
    DEFVAL      { 2 }
    ::= { mtaEntry 16 }

  hwChannel2Clock OBJECT-TYPE
    SYNTAX      INTEGER{internal(1),external(2),slave(3)}
    MAX-ACCESS  read-create
    STATUS      current
    DESCRIPTION
        " 
        the clock locked mode of channel 2: 1. Internal means the clock in MTA device, 
        2.External means the superior device's clock, 3. Slave means the clock of device access to this channel
        "
    DEFVAL      { 1 }
    ::= { mtaEntry 17 }

  hwChannel2SignalLinePhase OBJECT-TYPE
    SYNTAX      Integer32(0..15)
    MAX-ACCESS  read-create
    STATUS      current
    DESCRIPTION
        " 
          the signal line phase of channel 2, determined by four bits of which the less significant defines 
          the clock sending phase, the 2th the clock receiving phase, the 3th the data sending phase, the 4th the data receiving phase.
          and value 1 means reverse phase, value 0 means in-phase.
        "
    DEFVAL      { 0 }
    ::= { mtaEntry 18 }

  hwChannel2AsynLen OBJECT-TYPE
    SYNTAX      Integer32(6..12)
    MAX-ACCESS  read-create
    STATUS      current
    DESCRIPTION
        " 
        the word length of channel 2 working in the asynchro mode, including the starting bit,the data bits and the end bit
        "
    DEFVAL      { 8 }
    ::= { mtaEntry 19 }

  hwChannel2BChannelNo OBJECT-TYPE
    SYNTAX      INTEGER{b1(1),b2(2)}
    MAX-ACCESS  read-create
    STATUS      current
    DESCRIPTION
        " 
        determins the B channel N.O. to carry the data in channel 2
        "
    DEFVAL      { 1 }
    ::= { mtaEntry 20 }

  hwChannel2EnvolopPhase OBJECT-TYPE
    SYNTAX      INTEGER{sequencal(1),interleave(2)}
    MAX-ACCESS  read-create
    STATUS      current
    DESCRIPTION
        " 
        determins the envolop phase to carry the data in channel 2
        "
    DEFVAL      { 1 }
    ::= { mtaEntry 21 }

  hwChannel2Status OBJECT-TYPE
    SYNTAX      INTEGER{idle(1),normal(2),localLoop(3),remoteLoop(4),block(5),bChannelLocalLof(6),dteNotReady(7),bChannelRemoteLof(8),bChannelLocalLoop(9),bChannelRemoteLoop(10),fault(11)}
    MAX-ACCESS  read-only
    STATUS      current
    DESCRIPTION
        " 
        describes the current state of channel 2
        "
    DEFVAL      { 1 }
    ::= { mtaEntry 22 }

  hwChannel3Mode OBJECT-TYPE
    SYNTAX      INTEGER{syn(1),asyn(2),prohibit(3)}
    MAX-ACCESS  read-create
    STATUS      current
    DESCRIPTION
        " 
        determine working mode of channel 3: a syn. mode, an asyn. mode, or a prohibited mode
        "
    DEFVAL      { 1 }
    ::= { mtaEntry 23 }

  hwChannel3Rate OBJECT-TYPE
    SYNTAX      INTEGER {r2400bps(1),r4800bps(2),r9600bps(3),r19200bps(4),r64000bps(5),r128000bps(6) }
    MAX-ACCESS  read-create
    STATUS      current
    DESCRIPTION
        " 
          determine the service speed of channel 3
         "
    DEFVAL      { 2 }
    ::= { mtaEntry 24 }

  hwChannel3DteDce OBJECT-TYPE
    SYNTAX      INTEGER{dCE(1),dTE(2)}
    MAX-ACCESS  read-create
    STATUS      current
    DESCRIPTION
        " 
          determine the polarity of channel 3: DCE or DTE
        "
    DEFVAL      { 2 }
    ::= { mtaEntry 25 }

  hwChannel3Clock OBJECT-TYPE
    SYNTAX      INTEGER{internal(1),external(2),slave(3)}
    MAX-ACCESS  read-create
    STATUS      current
    DESCRIPTION
        " 
          the clock locked mode of channel 3: 1. Internal means the clock in MTA device, 
          2.External means the superior device's clock, 3. Slave means the clock of device access to this channel
        "
    DEFVAL      { 1 }
    ::= { mtaEntry 26 }

  hwChannel3SignalLinePhase OBJECT-TYPE
    SYNTAX      Integer32(0..15)
    MAX-ACCESS  read-create
    STATUS      current
    DESCRIPTION
        " 
          the signal line phase of channel 1, determined by four bits of which the less significant defines 
          the clock sending phase, the 2th the clock receiving phase, the 3th the data sending phase, the 4th the data receiving phase.
          and value 1 means reverse phase, value 0 means in-phase.
        "
    DEFVAL      { 0 }
    ::= { mtaEntry 27 }

  hwChannel3AsynLen OBJECT-TYPE
    SYNTAX      Integer32(6..12)
    MAX-ACCESS  read-create
    STATUS      current
    DESCRIPTION
        " 
          the word length of channel 3 working in the asynchro mode, including the starting bit,the data bits and the end bit
        "
    DEFVAL      { 8 }
    ::= { mtaEntry 28 }

  hwChannel3BChannelNo OBJECT-TYPE
    SYNTAX      INTEGER{b1(1),b2(2)}
    MAX-ACCESS  read-create
    STATUS      current
    DESCRIPTION
        " 
        determins the B channel N.O. to carry the data in channel 3
        "
    DEFVAL      { 1 }
    ::= { mtaEntry 29 }

  hwChannel3EnvolopPhase OBJECT-TYPE
    SYNTAX      INTEGER{sequencal(1),interleave(2)}
    MAX-ACCESS  read-create
    STATUS      current
    DESCRIPTION
        " 
        determins the envolop phase to carry the data in channel 3
        "
    DEFVAL      { 1 }
    ::= { mtaEntry 30 }

  hwChannel3Status OBJECT-TYPE
    SYNTAX      INTEGER{
                       idle(1),
                       normal(2),
                       localLoop(3),
                       remoteLoop(4),
                       block(5),
                       bChannelLocalLof(6),
                       dteNotReady(7),
                       bChannelRemoteLof(8),
                       bChannelLocalLoop(9),
                       bChannelRemoteLoop(10),
                       fault(11)
                       }
    MAX-ACCESS  read-only
    STATUS      current
    DESCRIPTION
        " 
        describes the current state of channel 3
        "
    DEFVAL      { 1 }
    ::= { mtaEntry 31 }

  hwUserIdentity OBJECT-TYPE
    SYNTAX      OCTET STRING (SIZE (0..9))
    MAX-ACCESS  read-create
    STATUS      current
    DESCRIPTION
        " 
        the identity label of this MTA, and two or more MTAs may have the same identity label
        "
    DEFVAL      { '0'b  }
    ::= { mtaEntry 32 }

  hwMaintainOper OBJECT-TYPE
    SYNTAX      INTEGER{noOperation(1),cancelLoop(2),localLoop(3),remoteLoop(4),reset(5)}
    MAX-ACCESS  read-write
    STATUS      current
    DESCRIPTION
        " 
        defines the maintain operation type, no operation(1) is just for GET, and is of no meaning
        for SET, CancelLoop(2) cancels all loops of the MTA, thus should not be set alongside Loop Object,
        LocalLoop and RemoteLoop must be bound to the Loop Object,
        reset operation will reset the MTA, and MTA will not be at loop state.
        "
    ::= { mtaEntry 33 }

  hwLoopObject OBJECT-TYPE
    SYNTAX      INTEGER{
                        noOperation(1),
                        dataChannel1(2),
                        dataChannel2(3),
                        dataChannel3(4),
                        b1Channel(5),
                        b2Channel(6),
                        doubleBPlusDChannel(7)
                        }
    MAX-ACCESS  read-write
    STATUS      current
    DESCRIPTION
        " 
        defines the loop object when setting LocalLoop or RemoteLoop operation,
        Getting this object will get value noOperation(1), while is of no meaning when Setting
        "
    ::= { mtaEntry 34 }

  hwChannel1AlarmStatus OBJECT-TYPE
    SYNTAX      Integer32(0..1)
    MAX-ACCESS  read-only
    STATUS      current
    DESCRIPTION
        " 
        describes the current alarm status of channel 1, 
        1 means the device access to MTA channel 1 is not ready,
        while 0 means the device is ready
        "
    DEFVAL      { 0 }
    ::= { mtaEntry 35 }

  hwChannel2AlarmStatus OBJECT-TYPE
    SYNTAX      Integer32(0..1)
    MAX-ACCESS  read-only
    STATUS      current
    DESCRIPTION
        " 
        describes the current alarm status of channel 2, 
        1 means the device access to MTA channel 1 is not ready,
        while 0 means the device is ready
        "
    DEFVAL      { 0 }
    ::= { mtaEntry 36 }

  hwChannel3AlarmStatus OBJECT-TYPE
    SYNTAX      Integer32(0..1)
    MAX-ACCESS  read-only
    STATUS      current
    DESCRIPTION
        " 
        describes the current alarm status of channel 3, 
        1 means the device access to MTA channel 1 is not ready,
        while 0 means the device is ready
        "
    DEFVAL      { 0 }
    ::= { mtaEntry 37 }
    
  hwBChannel1AlarmStatus OBJECT-TYPE
    SYNTAX      Integer32(0..3)
    MAX-ACCESS  read-only
    STATUS      current
    DESCRIPTION
        " 
        
        describes the current alarm status of B channel 1,
        determined by two bits of which the less significant defines whether
        adaptive loss of multi-frame alignment of B channel 1 happened 
        to MTA local equipment, 1 means yes, 0 means no,
        the most significant bit defines whether adaptive loss 
        of multi-frame alignment of B channel 1 happened 
        to MTA remote equipment, 1 means yes, 0 means no,
        "
    DEFVAL      { 0 }
    ::= { mtaEntry 38 }

  hwBChannel2AlarmStatus OBJECT-TYPE
    SYNTAX      Integer32(0..3)
    MAX-ACCESS  read-only
    STATUS      current
    DESCRIPTION
        " 
        
        describes the current alarm status of B channel 2,
        determined by two bits of which the less significant defines whether
        adaptive loss of multi-frame alignment of B channel 2 happened 
        to MTA local equipment, 1 means yes, 0 means no,
        the most significant bit defines whether adaptive loss 
        of multi-frame alignment of B channel 1 happened 
        to MTA remote equipment, 1 means yes, 0 means no,
        "
    DEFVAL      { 0 }
    ::= { mtaEntry 39 }


  hwRowStatus OBJECT-TYPE
    SYNTAX      RowStatus
    MAX-ACCESS  read-create
    STATUS      current
    DESCRIPTION
        " 
        MTA supports the operation createAndGo(4) and Destroy(6) only
        "
    ::= { mtaEntry 40 }





END
