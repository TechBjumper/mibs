--  ************************************************************************************
--  $Id: ZXR10-DHCP-RELAY-SERVER-MIB.mib 13 2010-12-09 01:01:26Z suqing $
--
--  ZXR10-DHCP-RELAY-SERVER-MIB.mib:  ROSNG DHCP RELAY AND SERVER Configuration MIB file
--  
--  Dec. 2010, Su Qing
--   
--  Copyright(c) 2010 by ZTE Corporaton
--  All rights reservered
--
--  *************************************************************************************

    ZXR10-DHCP-RELAY-SERVER-MIB DEFINITIONS ::= BEGIN

    IMPORTS
        MODULE-IDENTITY, 
        OBJECT-TYPE, 
        Unsigned32,
        enterprises 
            FROM SNMPv2-SMI 
        ifIndex           
            FROM RFC1213-MIB
        TruthValue,
        DisplayString
            FROM SNMPv2-TC
        IpAddress      
            FROM SNMPv2-SMI
        Ipv6Address
            FROM IPV6-TC;                                                                                                     
    
    zxr10dhcp MODULE-IDENTITY
        LAST-UPDATED "201906200000Z"  -- Jun. 20, 2019
        ORGANIZATION "ZTE Corporation"
        CONTACT-INFO
            "ZTE Corporation 
             Nanjing Institute of ZTE Corporation
         
             No.68 Zijinghua Rd. Yuhuatai District, Nanjing, China
         
             Tel: +86-25-52870000"

        DESCRIPTION
            "ROSNG 2.0 DHCP config MIB"

        REVISION "201906200000Z"
        DESCRIPTION
            "Add a new object zxr10dhcprUserStatObjects for DHCP relay 
            user connection statistics. The object of zxr10dhcprUserStatObjects 
            include:
            zxr10dhcprUserConnectStatTable,
            zxr10dhcprUserConnectStatEntry,
            zxr10dhcprUserStatBoardName,
            zxr10dhcprUserStatTimestart,
            zxr10dhcprUserStatTimeend,
            zxr10dhcprUserStatCapacity,
            zxr10dhcprUserStatCurrentOnline,
            zxr10dhcprUserStatFailedTimes"

        REVISION "201904180000Z"
        DESCRIPTION
            "Add a new leaf node zxr10dhcpUserIdentifierFormat in zxr10dhcpGlobalCommConfig"

        REVISION "201904030000Z"
        DESCRIPTION
            "Add a new leaf node zxr10dhcpRelaySvrGrpCos in zxr10dhcpRelaySvrGrpTable"

        REVISION "201901230000Z"
        DESCRIPTION
            "Add a new table zxr10dhcpRlySvrGrpFwdTable for DHCP relay 
            information, here are five leaves under this table:
            zxr10dhcpRlySvrOnlineFwdAlg,
            zxr10dhcpRlySvrOnlineFwdRenew,
            zxr10dhcpRlySvrOnlineFwdRebind,
            zxr10dhcpRlySvrOnlineFwdRelease,
            zxr10dhcpRlySvrOnlineFwdDecline"

        REVISION "201812240000Z"
        DESCRIPTION
            "Add a new leaf node zxr10dhcpPoolOptionFromReqPkt in zxr10dhcpPoolOptionTable."

        REVISION "201801230000Z"
        DESCRIPTION
            "Add a new leaf node zxr10dhcpPoolCommLsTimSecond in zxr10dhcpPoolCommTable."

        REVISION "201712260000Z"
        DESCRIPTION
            "Change SYNTAX of zxr10dhcpRelaySvrGrpDead from (5..3600) to (0..3600) ."

        REVISION "201704180000Z"
        DESCRIPTION
            "Add a new INTEGER value in zxr10dhcpMode."
            
        REVISION "201612060000Z"
        DESCRIPTION
            "Add a new leaf zxr10dhcpRelaySvrGrpServerVrf in zxr10dhcpRelaySvrGrpServerTabl."
             
        REVISION "201611160000Z"
        DESCRIPTION
            "Add a new leaf zxr10dhcpRelaySvrGrpServerPublic in zxr10dhcpRelaySvrGrpServerTabl."

        REVISION "201608230000Z"
        DESCRIPTION
            "Add a new table zxr10dhcpPoolOption125Table for DHCP pool information,
            here are thirteen leaf under this table:
            zxr10dhcpPoolOpt125DhcpPoolName,
            zxr10dhcpPoolOption125code,
            zxr10dhcpPoolOption125SubOptCode,
            zxr10dhcpPoolOption125AsciiStr,
            zxr10dhcpPoolOption125HexStr,
            zxr10dhcpPoolOption125IpAddress1,
            zxr10dhcpPoolOption125IpAddress2,
            zxr10dhcpPoolOption125IpAddress3,
            zxr10dhcpPoolOption125IpAddress4,
            zxr10dhcpPoolOption125IpAddress5,
            zxr10dhcpPoolOption125IpAddress6,
            zxr10dhcpPoolOption125IpAddress7,
            zxr10dhcpPoolOption125IpAddress8"

        REVISION "201607050000Z"  
        DESCRIPTION
            "Add node zxr10dhcpRelayReportUserCfg in zxr10dhcpGlobalRelayConf."
        
        REVISION "201603160000Z"  
        DESCRIPTION
            "1.Add node zxr10dhcpUpgradeLsTimDays in 
               zxr10dhcpGlobalCommConfig;
             2.Add node zxr10dhcpUpgradeLsTimHours in 
               zxr10dhcpGlobalCommConfig;
             3.Add node zxr10dhcpUpgradeLsTimMinutes in 
               zxr10dhcpGlobalCommConfig."

        REVISION "201601050000Z"  
        DESCRIPTION
            "Add a new leaf node zxr10dhcpPoolIgnoreRequestList in zxr10dhcpPoolCommTable."

        REVISION "201407090000Z"  
        DESCRIPTION
            "Add a new table zxr10dhcpRelayAgentIndexConfTable,
             here are six leaf under this table:
             zxr10dhcpRlyAgentIndexIfName,
             zxr10dhcpRlyAgentIndex,
             zxr10dhcpRlyAgentIndexIP,
             zxr10dhcpRlyAgentIndexOptCode,
             zxr10dhcpRlyAgentIndexOptType,
             zxr10dhcpRlyAgentIndexOptText."

        REVISION "201406060000Z"  
        DESCRIPTION
            "1.Change SYNTAX of zxr10dhcpRelaySvrGrpSvrIndex from (1..8)
             to (1..128);     
             2.Change SYNTAX of zxr10dhcpRelaySvrGrpServerIndex from (1..8)
             to (1..128)."

        REVISION "201403110000Z"  
        DESCRIPTION
            "1.Modify SYNTAX of zxr10dhcpRelayOpt82Policy,delete 
               drop(1) and rewrite(4);      
             2.Modify SYNTAX of zxr10dhcpRelayOpt82UserCfgPolicy,
               delete vlan(3)."


        REVISION "201402180000Z"
        DESCRIPTION
            "1.Modify the node zxr10dhcpPoolCommIppoolName in 
               zxr10dhcpPoolCommTable,change this displayString 
               SIZE(0..16) to SIZE(0..32)."
    
    
        REVISION "201401170000Z"
        DESCRIPTION
            "1.Modify the node zxr10dhcpRelaySvrGrpSvrMode in 
               zxr10dhcpRelaySvrGrpSvrTable,change the STATUS from current
               to obsolete;
             2.Modify the node zxr10dhcpRelaySvrGrpServerMode in 
               zxr10dhcpRelaySvrGrpServerTable,change the STATUS from current
               to obsolete;
             3.Add node zxr10dhcpRelayIfConfFwdMode in 
               zxr10dhcpRelayIfConfTable;
             4.Add node zxr10dhcpRelaySvrGrpLocalSvr in 
               zxr10dhcpRelaySvrGrpTable."


        REVISION "201310240000Z"  
        DESCRIPTION
            "1.Change length range of zxr10dhcpPoolOptionAsciiStr from (0..64)
             to (0..200);      
             2.Change length range of zxr10dhcpPoolOptionHexStr from (0..64)
             to (0..200)."
        REVISION "201310140000Z"  
        DESCRIPTION
            "1.Modify description of zxr10dhcpPoolCommLsTimMinute for 
               'DHCP pool leasetime minutes.';      
             2.Modify description of zxr10dhcpPoolStaticClientMask for
               'DHCP pool static user mask address.';
             3.Modify description of zxr10dhcpPoolStaticClientIp for
               'DHCP pool static user IP address.';
             4.Modify 'numbers' in description of zxr10dhcpRelayMaxUserCfg
               for 'number';
             5.Modify 'numbers' in description of zxr10dhcpRelayMaxUser
               for 'number'."
        REVISION "201306240000Z"  
        DESCRIPTION
            "1.Add one table for DHCP relay information:
               zxr10dhcpGlobalRelayConf;
             2.Add six table for DHCP pool information:
               zxr10dhcpPoolCommTable,zxr10dhcpPoolDnsTable,
               zxr10dhcpPoolDftRouterTable,zxr10dhcpPoolStaticTable,
               zxr10dhcpPoolOptionTable,zxr10dhcpPoolOpt212Table."
        REVISION "201305240000Z"  
        DESCRIPTION
            "1.Add client mode for zxr10dhcpIfMode;
             2.Add zxr10dhcpRelaySvrGrpServerTable."
        REVISION "201305060000Z"  
        DESCRIPTION
            "As the revision of 201304010000Z which has not published was
             not designed well,this revision is added for modifing the last
             revision.
             1.Move zxr10dhcpAccListTable and zxr10dhcpAccListRuleTable
             from zxr10dhcpRelayConfig to zxr10dhcpGlobalCommConfig.
             2.Move zxr10dhcpRelayUserTable and zxr10dhcpRelayIfConfTable
             forward.
             3.Change data type of zxr10dhcpRelayUserMac from DisplayString
             to OCTET STRING.
             4.Change length range of zxr10dhcpRelayUserBoardName from (1..32)
             to (1..31)."
        REVISION "201304010000Z"  
        DESCRIPTION
            "Add one table for DHCP interface information:
             zxr10dhcpIfCommonTable,and add four tables for DHCP relay
             information:zxr10dhcpAccListTable, zxr10dhcpAccListRuleTable,
             zxr10dhcpRelayUserTable, zxr10dhcpRelayIfConfTable." 
        REVISION "201012250000Z"  
        DESCRIPTION
            "This mib defines management information objects for DHCP" 
        ::= { zxr10 349 } 
    
    zte   OBJECT IDENTIFIER ::= { enterprises 3902 }  
    zxr10 OBJECT IDENTIFIER ::= { zte 3 }
         
    -- Mib oid define
 
    zxr10dhcpGlobalCommConfig   OBJECT IDENTIFIER ::= { zxr10dhcp 1 }     
    zxr10dhcpIfCommConfig       OBJECT IDENTIFIER ::= { zxr10dhcp 2 }
    zxr10dhcpRelayConfig        OBJECT IDENTIFIER ::= { zxr10dhcp 3 }
    zxr10dhcpPoolConfig         OBJECT IDENTIFIER ::= { zxr10dhcp 4 }       
   
     -- DHCP global common config
     zxr10dhcpEnable OBJECT-TYPE
        SYNTAX       INTEGER{
                        disable(0),
                        enable(1)
                      }
        MAX-ACCESS    read-only
        STATUS        current
        DESCRIPTION   "Enable DHCP process"
        ::= { zxr10dhcpGlobalCommConfig 1 }
                
     zxr10dhcpRamble OBJECT-TYPE
        SYNTAX      INTEGER{
                        disable(0),
                        enable(1)
                    }
        MAX-ACCESS    read-only
        STATUS        current
        DESCRIPTION   "Enable DHCP user ramble"
        ::= { zxr10dhcpGlobalCommConfig 2 } 
        
     zxr10dhcpMaxHops OBJECT-TYPE
        SYNTAX        Unsigned32(1..16) 
        MAX-ACCESS    read-only
        STATUS        current
        DESCRIPTION   "Max hops of DHCP message"  
        DEFVAL { 4 }
        ::= { zxr10dhcpGlobalCommConfig 3 } 
                
     zxr10dhcpSuppressNak OBJECT-TYPE
        SYNTAX      INTEGER{
                        disable(0),
                        enable(1)
                    }
        MAX-ACCESS    read-only
        STATUS        current
        DESCRIPTION   "Suppress DHCPNAK message"
        ::= { zxr10dhcpGlobalCommConfig 4 }   
        
     zxr10dhcpUpgradeLsTimDays OBJECT-TYPE
        SYNTAX        Unsigned32(0..365) 
        MAX-ACCESS    read-only
        STATUS        current
        DESCRIPTION   "DHCP upgrade leasetime days."
        ::= { zxr10dhcpGlobalCommConfig 7 }
        
     zxr10dhcpUpgradeLsTimHours OBJECT-TYPE
        SYNTAX        Unsigned32(0..23) 
        MAX-ACCESS    read-only
        STATUS        current
        DESCRIPTION   "DHCP upgrade leasetime hours."
        ::= { zxr10dhcpGlobalCommConfig 8 }

     zxr10dhcpUpgradeLsTimMinutes OBJECT-TYPE
        SYNTAX        Unsigned32(0..59) 
        MAX-ACCESS    read-only
        STATUS        current
        DESCRIPTION   "DHCP upgrade leasetime minutes."
        ::= { zxr10dhcpGlobalCommConfig 9 }
       
        
     -- DHCP access list table  
    
    zxr10dhcpAccListTable  OBJECT-TYPE
        SYNTAX  SEQUENCE OF Zxr10dhcpAccListEntry
        MAX-ACCESS  not-accessible
        STATUS      current
        DESCRIPTION
            "DHCP access list table."
        ::= { zxr10dhcpGlobalCommConfig 5 }

    zxr10dhcpAccListEntry  OBJECT-TYPE
        SYNTAX      Zxr10dhcpAccListEntry
        MAX-ACCESS  not-accessible
        STATUS      current
        DESCRIPTION
            "This list contains DHCP access list parameters"     
        INDEX  { zxr10dhcpAccListName }    
        ::= { zxr10dhcpAccListTable 1 }
        
    Zxr10dhcpAccListEntry ::=
        SEQUENCE {
        zxr10dhcpAccListName         DisplayString,
        zxr10dhcpDefOperType         INTEGER,
        zxr10dhcpDefDataTypeAny      Unsigned32                              
        } 
        
    zxr10dhcpAccListName OBJECT-TYPE
        SYNTAX        DisplayString(SIZE(1..16))
        MAX-ACCESS    not-accessible
        STATUS        current
        DESCRIPTION   "DHCP access list name."
        ::= { zxr10dhcpAccListEntry 1 }  

    zxr10dhcpDefOperType OBJECT-TYPE
        SYNTAX        INTEGER{
                           permit(1), 
                           deny(2)
                      }
        MAX-ACCESS    read-only
        STATUS        current
        DESCRIPTION   "DHCP access list default rule operate type."  
        DEFVAL { permit }       
        ::= { zxr10dhcpAccListEntry 2 }
            
    zxr10dhcpDefDataTypeAny OBJECT-TYPE
        SYNTAX        Unsigned32(0..1) 
        MAX-ACCESS    read-only
        STATUS        current
        DESCRIPTION   "DHCP access list default rule date type."
        ::= { zxr10dhcpAccListEntry 3 }    
                
    -- DHCP access list rule table  
    
    zxr10dhcpAccListRuleTable  OBJECT-TYPE
        SYNTAX  SEQUENCE OF Zxr10dhcpAccListRuleEntry
        MAX-ACCESS  not-accessible
        STATUS      current
        DESCRIPTION
            "DHCP access list rule table."
        ::= { zxr10dhcpGlobalCommConfig 6 }

    zxr10dhcpAccListRuleEntry  OBJECT-TYPE
        SYNTAX      Zxr10dhcpAccListRuleEntry
        MAX-ACCESS  not-accessible
        STATUS      current
        DESCRIPTION
            "This list contains DHCP access list rule parameters"     
        INDEX  { zxr10dhcpAccessListName, zxr10dhcpAccListRuleNo }    
        ::= { zxr10dhcpAccListRuleTable 1 }
        
    Zxr10dhcpAccListRuleEntry ::=
        SEQUENCE {
        zxr10dhcpAccessListName             DisplayString,
        zxr10dhcpAccListRuleNo              Unsigned32,
        zxr10dhcpAccListRuleOperTypeDeny    TruthValue,
        zxr10dhcpAccListRuleOperTypePmt     TruthValue,
        zxr10dhcpAccListRuleDataTypeAny     TruthValue,
        zxr10dhcpAccListRuleDataType60      TruthValue,
        zxr10dhcpAccListRuleOpt60Str        DisplayString,
        zxr10dhcpAccListRuleOpt60ParMth     TruthValue                              
        } 
        
    zxr10dhcpAccessListName OBJECT-TYPE
        SYNTAX        DisplayString(SIZE(1..16))
        MAX-ACCESS    not-accessible
        STATUS        current
        DESCRIPTION   "DHCP access list name."
        ::= { zxr10dhcpAccListRuleEntry 1 }   
 
    zxr10dhcpAccListRuleNo OBJECT-TYPE
        SYNTAX        Unsigned32(1..20) 
        MAX-ACCESS    not-accessible
        STATUS        current
        DESCRIPTION   "The DHCP access list rule number."
        ::= { zxr10dhcpAccListRuleEntry 2 }

    zxr10dhcpAccListRuleOperTypeDeny OBJECT-TYPE
        SYNTAX        TruthValue
        MAX-ACCESS    read-only
        STATUS        current
        DESCRIPTION   "The DHCP access list rule operate type is deny
                       or not." 
        DEFVAL { false }        
        ::= { zxr10dhcpAccListRuleEntry 3 }
        
    zxr10dhcpAccListRuleOperTypePmt OBJECT-TYPE
        SYNTAX        TruthValue
        MAX-ACCESS    read-only
        STATUS        current
        DESCRIPTION   "The DHCP access list rule operate type is permit
                       or not."
        DEFVAL { false }        
        ::= { zxr10dhcpAccListRuleEntry 4 }
  
    zxr10dhcpAccListRuleDataTypeAny OBJECT-TYPE
        SYNTAX        TruthValue 
        MAX-ACCESS    read-only
        STATUS        current
        DESCRIPTION   "The DHCP access list rule data type is any or not." 
        DEFVAL { false }
        ::= { zxr10dhcpAccListRuleEntry 5 }
        
    zxr10dhcpAccListRuleDataType60 OBJECT-TYPE
        SYNTAX        TruthValue 
        MAX-ACCESS    read-only
        STATUS        current
        DESCRIPTION   "The DHCP access list rule data type is option60
                       or not." 
        DEFVAL { false }
        ::= { zxr10dhcpAccListRuleEntry 6 } 
     
    zxr10dhcpAccListRuleOpt60Str OBJECT-TYPE
        SYNTAX        DisplayString(SIZE(0..64))
        MAX-ACCESS    read-only
        STATUS        current
        DESCRIPTION   "The DHCP access list rule option60 string."
        ::= { zxr10dhcpAccListRuleEntry 7 } 
        
    zxr10dhcpAccListRuleOpt60ParMth OBJECT-TYPE
        SYNTAX        TruthValue 
        MAX-ACCESS    read-only
        STATUS        current
        DESCRIPTION   "The DHCP access list rule option60 is partial match
                       or not." 
        DEFVAL { false }
        ::= { zxr10dhcpAccListRuleEntry 8 }  
       
         
  
    -- DHCP interface common configuration 
    
    zxr10dhcpIfCommTable  OBJECT-TYPE
        SYNTAX  SEQUENCE OF Zxr10dhcpIfCommEntry
        MAX-ACCESS  not-accessible
        STATUS      current
        DESCRIPTION
            "DHCP configure table of interface."
        ::= { zxr10dhcpIfCommConfig 1 }

    zxr10dhcpIfCommEntry  OBJECT-TYPE
        SYNTAX      Zxr10dhcpIfCommEntry
        MAX-ACCESS  not-accessible
        STATUS      current
        DESCRIPTION
            "This list contains DHCP common parameters of user access 
             interface"     
        INDEX  { ifIndex }    
        ::= { zxr10dhcpIfCommTable 1 }
       
    Zxr10dhcpIfCommEntry ::=
        SEQUENCE { 
        zxr10dhcpMode        INTEGER,                               
        zxr10dhcpUserQuota   Unsigned32,
        zxr10dhcpSvrDisTimer Unsigned32,
        zxr10dhcpSrcMacChk   INTEGER   
        }  

    zxr10dhcpMode   OBJECT-TYPE
        SYNTAX     INTEGER{
                       none(0),
                       server(1),
                       relay(2),
                       proxy(3),
                       client(4)
                   }
        MAX-ACCESS read-only
        STATUS     current
        DESCRIPTION "DHCP work mode." 
        ::= { zxr10dhcpIfCommEntry 1 }
 
     zxr10dhcpUserQuota   OBJECT-TYPE
        SYNTAX     Unsigned32(0..64000) 
        MAX-ACCESS read-only
        STATUS     current
        DESCRIPTION "Specify quota of DHCP users on this interface." 
        ::= { zxr10dhcpIfCommEntry 2 }   
        
     zxr10dhcpSvrDisTimer   OBJECT-TYPE
        SYNTAX     Unsigned32(0..3600)
        MAX-ACCESS read-only
        STATUS     obsolete
        DESCRIPTION "DHCP server discover timer." 
        ::= { zxr10dhcpIfCommEntry 3 }
 
     zxr10dhcpSrcMacChk   OBJECT-TYPE
        SYNTAX     INTEGER{
                       disable(0),
                       enable(1)
                   }
        MAX-ACCESS read-only
        STATUS     obsolete
        DESCRIPTION "DHCP source mac check." 
        DEFVAL { enable }
        ::= { zxr10dhcpIfCommEntry 4 }   
        
    -- DHCP interface common configuration(new) 
    
    zxr10dhcpIfCommonTable  OBJECT-TYPE
        SYNTAX  SEQUENCE OF Zxr10dhcpIfCommonEntry
        MAX-ACCESS  not-accessible
        STATUS      current
        DESCRIPTION
            "DHCP configuration table of interface."
        ::= { zxr10dhcpIfCommConfig 2 }

    zxr10dhcpIfCommonEntry  OBJECT-TYPE
        SYNTAX      Zxr10dhcpIfCommonEntry
        MAX-ACCESS  not-accessible
        STATUS      current
        DESCRIPTION
            "This list contains DHCP common parameters of user access
             interface"     
        INDEX  { zxr10dhcpInterfaceName }    
        ::= { zxr10dhcpIfCommonTable 1 }
       
    Zxr10dhcpIfCommonEntry ::=
        SEQUENCE { 
        zxr10dhcpInterfaceName DisplayString,
        zxr10dhcpIfMode        INTEGER,                               
        zxr10dhcpIfUserQuota   Unsigned32  
        } 
        
    zxr10dhcpInterfaceName OBJECT-TYPE
        SYNTAX        DisplayString(SIZE(1..31)) 
        MAX-ACCESS    not-accessible
        STATUS        current
        DESCRIPTION   "DHCP interface name."
        ::= { zxr10dhcpIfCommonEntry 1 } 

    zxr10dhcpIfMode   OBJECT-TYPE
        SYNTAX     INTEGER{
                       none(1),
                       server(2),
                       relay(3),
                       proxy(4),
                       client(5)
                   }
        MAX-ACCESS read-only
        STATUS     current
        DESCRIPTION "DHCP work mode." 
        ::= { zxr10dhcpIfCommonEntry 2 }
 
     zxr10dhcpIfUserQuota   OBJECT-TYPE
        SYNTAX     Unsigned32(0..64000) 
        MAX-ACCESS read-only
        STATUS     current
        DESCRIPTION "Specify quota of DHCP users on this interface." 
        ::= { zxr10dhcpIfCommonEntry 3 }   
           
    -- DHCP Relay Global configuration under DHCP MODE  
                  
    zxr10dhcpGlobalRelayConfig OBJECT IDENTIFIER ::= { zxr10dhcpRelayConfig 1 } 
    
    zxr10dhcpRelayMaxUser OBJECT-TYPE
        SYNTAX        Unsigned32(1..64000)
        MAX-ACCESS    read-only
        STATUS        current
        DESCRIPTION   "Max user number of DHCP relay, default value is set
                       by project."
        ::= { zxr10dhcpGlobalRelayConfig 1 }  
        
    zxr10dhcpRelayForbidSendRls OBJECT-TYPE
        SYNTAX      INTEGER { 
                         disable(0),
                         enable(1)
                    }
        MAX-ACCESS  read-only
        STATUS      current
        DESCRIPTION   "Forbid DHCP relay sends DHCPRELEASE to server or not."
        ::= { zxr10dhcpGlobalRelayConfig 2 }
        
   zxr10dhcpRelayProxyLease OBJECT-TYPE
        SYNTAX        Unsigned32(30..3600)
        MAX-ACCESS    read-only
        STATUS        current
        DESCRIPTION   
             "Set client lease time of proxy." 
        DEFVAL { 60 }     
        ::= { zxr10dhcpGlobalRelayConfig 3 }                   
        
    zxr10dhcpRelayOpt82Format OBJECT-TYPE
        SYNTAX      INTEGER { 
                         chinaTel(1), 
                         dslForum(2),  
                         telenor(3), 
                         userConfiguration(4)
                    }
        MAX-ACCESS  read-only
        STATUS      current
        DESCRIPTION   "DHCP relay option82 format."  
        DEFVAL { chinaTel }
        ::= { zxr10dhcpGlobalRelayConfig 4 }      
        
    zxr10dhcpRelayOpt82Option OBJECT-TYPE
        SYNTAX      INTEGER { 
                         disable(0),
                         enable(1)
                    }
        MAX-ACCESS    read-only
        STATUS        current
        DESCRIPTION   "Insert relay option82 or not in BOOTREQUEST."
        ::= { zxr10dhcpGlobalRelayConfig 5 }

    zxr10dhcpRelayOpt82Policy OBJECT-TYPE
        SYNTAX      INTEGER{ 
                         keep(2), 
                         replace(3), 
                         add(5)
                    }  
        MAX-ACCESS    read-only
        STATUS        current
        DESCRIPTION   "The option82 policy of DHCP relay." 
        DEFVAL { replace }
        ::= { zxr10dhcpGlobalRelayConfig 6 }   
        
    zxr10dhcpRelayOpt82UserCfgPolicy OBJECT-TYPE
        SYNTAX        INTEGER{ 
                           interface(1), 
                           uniform(2)
                      }          
        MAX-ACCESS    read-only
        STATUS        current
        DESCRIPTION   "DHCP option82 policy of user configuration." 
        DEFVAL { interface }        
        ::= { zxr10dhcpGlobalRelayConfig 7 }
        
    zxr10dhcpRelayOpt82UniformCir OBJECT-TYPE
        SYNTAX        DisplayString(SIZE(0..64))
        MAX-ACCESS    read-only
        STATUS        current
        DESCRIPTION   "The circuit-id subitem of uniform option82."
        ::= { zxr10dhcpGlobalRelayConfig 8 }

    zxr10dhcpRelayOpt82UniformRem OBJECT-TYPE
        SYNTAX        DisplayString(SIZE(0..64))
        MAX-ACCESS    read-only
        STATUS        current
        DESCRIPTION   "The remote-id subitem of uniform option82."
        ::= { zxr10dhcpGlobalRelayConfig 9 }
    
    zxr10dhcpRelaySrcIpEnable OBJECT-TYPE
        SYNTAX        INTEGER{ 
                           disable(0),
                           enable(1)   
                      }
        MAX-ACCESS    read-only
        STATUS        obsolete
        DESCRIPTION   "Enable DHCP relay configurate source ip or not."
        ::= { zxr10dhcpGlobalRelayConfig 10 }  
        
    zxr10dhcpRelaySrcIp OBJECT-TYPE
        SYNTAX        IpAddress 
        MAX-ACCESS    read-only
        STATUS        obsolete
        DESCRIPTION   "DHCP relay source ip."
        ::= { zxr10dhcpGlobalRelayConfig 11 }       

    zxr10dhcpRelayUptArp OBJECT-TYPE
        SYNTAX        INTEGER{ 
                           disable(0),
                           enable(1)   
                      }     
        MAX-ACCESS    read-only
        STATUS        current
        DESCRIPTION   "Set the arp deadtime to dhcp lease or not."
        ::= { zxr10dhcpGlobalRelayConfig 12 }
                                          
                                     
    -- DHCP Relay Interface configuration        

    zxr10dhcpRelayIfTable  OBJECT-TYPE
        SYNTAX  SEQUENCE OF Zxr10dhcpRelayIfEntry
        MAX-ACCESS  not-accessible
        STATUS      current
        DESCRIPTION
            "DHCP relay configure table of interface."
        ::= { zxr10dhcpRelayConfig 2 }

    zxr10dhcpRelayIfEntry  OBJECT-TYPE
        SYNTAX      Zxr10dhcpRelayIfEntry
        MAX-ACCESS  not-accessible
        STATUS      current
        DESCRIPTION
            "This list contains DHCP relay parameters of user access interface"     
        INDEX  { ifIndex }    
        ::= { zxr10dhcpRelayIfTable 1 }
       
    Zxr10dhcpRelayIfEntry ::=
        SEQUENCE {
        zxr10dhcpRelayIfAgentIP      IpAddress,                               
        zxr10dhcpRelayIfOpt82Cir     DisplayString,
        zxr10dhcpRelayIfOpt82Rem     DisplayString,                                 
        zxr10dhcpRelayIfSvrGrp       Unsigned32,
        zxr10dhcpRelayIfSvrPlc       INTEGER,
        zxr10dhcpRelayIfSrcIp        IpAddress           
        }
            
    zxr10dhcpRelayIfAgentIP OBJECT-TYPE
        SYNTAX        IpAddress 
        MAX-ACCESS    read-only
        STATUS        current
        DESCRIPTION   "DHCP relay agent ip address."
        ::= { zxr10dhcpRelayIfEntry 1 }
    
    zxr10dhcpRelayIfOpt82Cir OBJECT-TYPE
        SYNTAX        DisplayString(SIZE(0..64)) 
        MAX-ACCESS    read-only
        STATUS        current
        DESCRIPTION   "Option82 circuit-id of the interface."
        ::= { zxr10dhcpRelayIfEntry 2 }

    zxr10dhcpRelayIfOpt82Rem OBJECT-TYPE
        SYNTAX        DisplayString(SIZE(0..64)) 
        MAX-ACCESS    read-only
        STATUS        current
        DESCRIPTION   "Option82 remote-id of the interface."
        ::= { zxr10dhcpRelayIfEntry 3 }
        
    zxr10dhcpRelayIfSvrGrp OBJECT-TYPE
        SYNTAX        Unsigned32(0..20) 
        MAX-ACCESS    read-only
        STATUS        current
        DESCRIPTION   "DHCP relay server group index of the interface."
        ::= { zxr10dhcpRelayIfEntry 4 } 
                  
    zxr10dhcpRelayIfSvrPlc OBJECT-TYPE
        SYNTAX        INTEGER{
                           none(0), 
                           vclassId(1),
                           vlanId(2)
                      }         
        MAX-ACCESS    read-only
        STATUS        current
        DESCRIPTION   "DHCP relay helper-address policy of the interface."
        ::= { zxr10dhcpRelayIfEntry 5 } 
        
    zxr10dhcpRelayIfSrcIp OBJECT-TYPE
        SYNTAX        IpAddress 
        MAX-ACCESS    read-only
        STATUS        current
        DESCRIPTION   "DHCP relay source ip."
        ::= { zxr10dhcpRelayIfEntry 6 } 
        
    -- DHCP relay server group configuration
    
    zxr10dhcpRelaySvrGrpTable  OBJECT-TYPE
        SYNTAX  SEQUENCE OF Zxr10dhcpRelaySvrGrpEntry
        MAX-ACCESS  not-accessible
        STATUS      current
        DESCRIPTION
            "DHCP relay server group table."
        ::= { zxr10dhcpRelayConfig 3 }

    zxr10dhcpRelaySvrGrpEntry  OBJECT-TYPE
        SYNTAX      Zxr10dhcpRelaySvrGrpEntry
        MAX-ACCESS  not-accessible
        STATUS      current
        DESCRIPTION
            "This list contains DHCP relay server group parameters"     
        INDEX  { zxr10dhcpRelaySvrGrpIndex }    
        ::= { zxr10dhcpRelaySvrGrpTable 1 }
        
    Zxr10dhcpRelaySvrGrpEntry ::=
        SEQUENCE {
        zxr10dhcpRelaySvrGrpIndex    Unsigned32,
        zxr10dhcpRelaySvrGrpAlg      INTEGER,
        zxr10dhcpRelaySvrGrpDead     Unsigned32,
        zxr10dhcpRelaySvrGrpRetry    Unsigned32,
        zxr10dhcpRelaySvrGrpDescrib  DisplayString,
        zxr10dhcpRelaySvrGrpLocalSvr INTEGER                               
        }
        
     zxr10dhcpRelaySvrGrpIndex OBJECT-TYPE
        SYNTAX        Unsigned32(1..20) 
        MAX-ACCESS    read-only
        STATUS        current
        DESCRIPTION   "DHCP relay server group number."
        ::= { zxr10dhcpRelaySvrGrpEntry 1 } 
        
     zxr10dhcpRelaySvrGrpAlg OBJECT-TYPE
        SYNTAX        INTEGER{
                           first(0), 
                           roundRobin(1),
                           forwardAll(2)
                      }
        MAX-ACCESS    read-only
        STATUS        current
        DESCRIPTION   "DHCP relay server group algorithm."  
        DEFVAL { first }        
        ::= { zxr10dhcpRelaySvrGrpEntry 2 }  
        
     zxr10dhcpRelaySvrGrpDead OBJECT-TYPE
        SYNTAX        Unsigned32(0..3600)
        MAX-ACCESS    read-only
        STATUS        current
        DESCRIPTION   "Deadtime of DHCP relay server."  
        DEFVAL { 60 }       
        ::= { zxr10dhcpRelaySvrGrpEntry 3 }  
        
     zxr10dhcpRelaySvrGrpRetry OBJECT-TYPE
        SYNTAX        Unsigned32(5..20)
        MAX-ACCESS    read-only
        STATUS        current
        DESCRIPTION   "Max retry times of DHCP relay server group server."   
        DEFVAL { 10 }       
        ::= { zxr10dhcpRelaySvrGrpEntry 4 }  
        
     zxr10dhcpRelaySvrGrpDescrib OBJECT-TYPE
        SYNTAX        DisplayString(SIZE(0..32))
        MAX-ACCESS    read-only
        STATUS        current
        DESCRIPTION   "Description of DHCP relay server group."
        ::= { zxr10dhcpRelaySvrGrpEntry 5 } 
     
     zxr10dhcpRelaySvrGrpLocalSvr OBJECT-TYPE
        SYNTAX       INTEGER{
                          off(1),
                          on(2)
                       }
        MAX-ACCESS    read-only
        STATUS        current
        DESCRIPTION   "DHCP relay switch to local server"
        ::= { zxr10dhcpRelaySvrGrpEntry 6 } 

    -- DHCP relay server group server table
    
    zxr10dhcpRelaySvrGrpSvrTable  OBJECT-TYPE
        SYNTAX  SEQUENCE OF Zxr10dhcpRelaySvrGrpSvrEntry
        MAX-ACCESS  not-accessible
        STATUS      current
        DESCRIPTION
            "DHCP relay server group server table."
        ::= { zxr10dhcpRelayConfig 4 }

    zxr10dhcpRelaySvrGrpSvrEntry  OBJECT-TYPE
        SYNTAX      Zxr10dhcpRelaySvrGrpSvrEntry
        MAX-ACCESS  not-accessible
        STATUS      current
        DESCRIPTION
            "This list contains DHCP relay server group server parameters"     
        INDEX  { zxr10dhcpRelaySvrGrpIndex, zxr10dhcpRelaySvrGrpSvrIndex }    
        ::= { zxr10dhcpRelaySvrGrpSvrTable 1 }
        
    Zxr10dhcpRelaySvrGrpSvrEntry ::=
        SEQUENCE {
        zxr10dhcpRelaySvrGrpSvrIndex Unsigned32,
        zxr10dhcpRelaySvrGrpSvrIp    IpAddress, 
        zxr10dhcpRelaySvrGrpSvrMode  INTEGER,
        zxr10dhcpRelaySvrGrpSvrMast  INTEGER                                 
        }    
 
     zxr10dhcpRelaySvrGrpSvrIndex OBJECT-TYPE
        SYNTAX        Unsigned32(1..128)
        MAX-ACCESS    read-only
        STATUS        current
        DESCRIPTION   "The server number."
        ::= { zxr10dhcpRelaySvrGrpSvrEntry 1 }

     zxr10dhcpRelaySvrGrpSvrIp OBJECT-TYPE
        SYNTAX        IpAddress 
        MAX-ACCESS    read-only
        STATUS        current
        DESCRIPTION   "The IP address of the relay server group server."
        ::= { zxr10dhcpRelaySvrGrpSvrEntry 2 } 
         
     zxr10dhcpRelaySvrGrpSvrMode OBJECT-TYPE
        SYNTAX        INTEGER{
                           standard(0),
                           security(1)                      
                      }
        MAX-ACCESS    read-only
        STATUS        obsolete
        DESCRIPTION   "The server mode."
        ::= { zxr10dhcpRelaySvrGrpSvrEntry 3 } 
     
    zxr10dhcpRelaySvrGrpSvrMast OBJECT-TYPE
        SYNTAX        INTEGER{
                          slave(0),
                          master(1)                        
                      }
        MAX-ACCESS    read-only
        STATUS        current
        DESCRIPTION   "The server is master or slave."
        ::= { zxr10dhcpRelaySvrGrpSvrEntry 4 } 
 
    -- DHCP relay server policy group configuration 
    
    zxr10dhcpRelayPlcGrpTable  OBJECT-TYPE
        SYNTAX  SEQUENCE OF Zxr10dhcpRelayPlcGrpEntry
        MAX-ACCESS  not-accessible
        STATUS      current
        DESCRIPTION
            "DHCP relay server policy group table."
        ::= { zxr10dhcpRelayConfig 5 }

    zxr10dhcpRelayPlcGrpEntry  OBJECT-TYPE
        SYNTAX      Zxr10dhcpRelayPlcGrpEntry
        MAX-ACCESS  not-accessible
        STATUS      current
        DESCRIPTION
            "This list contains DHCP relay server policy group parameters"     
        INDEX  { zxr10dhcpRelayPlcGrpIndex }    
        ::= { zxr10dhcpRelayPlcGrpTable 1 } 
        
    Zxr10dhcpRelayPlcGrpEntry ::=
        SEQUENCE {
        zxr10dhcpRelayPlcGrpIndex          Unsigned32,
        zxr10dhcpRelayPlcGrpSvrGrpNo       Unsigned32,
        zxr10dhcpRelayPlcGrpVclass         DisplayString,
        zxr10dhcpRelayPlcGrpVlanInStart    Unsigned32,
        zxr10dhcpRelayPlcGrpVlanExStart    Unsigned32,
        zxr10dhcpRelayPlcGrpVlanInEnd      Unsigned32,
        zxr10dhcpRelayPlcGrpVlanExEnd      Unsigned32                               
        }
        
     zxr10dhcpRelayPlcGrpIndex OBJECT-TYPE
        SYNTAX        Unsigned32(1..20)
        MAX-ACCESS    read-only
        STATUS        current
        DESCRIPTION   "Relay server policy group number."
        ::= { zxr10dhcpRelayPlcGrpEntry 1 } 
        
     zxr10dhcpRelayPlcGrpSvrGrpNo OBJECT-TYPE
        SYNTAX        Unsigned32(0..20)
        MAX-ACCESS    read-only
        STATUS        current
        DESCRIPTION   "Relay server group number of this relay server policy
                       group."
        ::= { zxr10dhcpRelayPlcGrpEntry 2 }          

     zxr10dhcpRelayPlcGrpVclass OBJECT-TYPE
        SYNTAX        DisplayString(SIZE(0..32))
        MAX-ACCESS    read-only
        STATUS        current
        DESCRIPTION   "Vclass id of this relay server policy group."
        ::= { zxr10dhcpRelayPlcGrpEntry 3 }  
        
     zxr10dhcpRelayPlcGrpVlanInStart OBJECT-TYPE
        SYNTAX        Unsigned32(0..4094) 
        MAX-ACCESS    read-only
        STATUS        obsolete
        DESCRIPTION   "The start vlan id of internal vlan."
        ::= { zxr10dhcpRelayPlcGrpEntry 4 } 
        
     zxr10dhcpRelayPlcGrpVlanExStart OBJECT-TYPE
        SYNTAX        Unsigned32(0..4094) 
        MAX-ACCESS    read-only
        STATUS        obsolete
        DESCRIPTION   "The start vlan id of external vlan."
        ::= { zxr10dhcpRelayPlcGrpEntry 5 } 
        
     zxr10dhcpRelayPlcGrpVlanInEnd OBJECT-TYPE
        SYNTAX        Unsigned32(0..4094) 
        MAX-ACCESS    read-only
        STATUS        obsolete
        DESCRIPTION   "The end vlan id of internal vlan."
        ::= { zxr10dhcpRelayPlcGrpEntry 6 } 
        
     zxr10dhcpRelayPlcGrpVlanExEnd OBJECT-TYPE
        SYNTAX        Unsigned32(0..4094) 
        MAX-ACCESS    read-only
        STATUS        obsolete
        DESCRIPTION   "The end vlan id of external vlan."
        ::= { zxr10dhcpRelayPlcGrpEntry 7 } 
     

   -- DHCP relay server policy group vlan configuration 
       
    zxr10dhcpRelayPlcGrpVlanTable  OBJECT-TYPE
        SYNTAX  SEQUENCE OF Zxr10dhcpRelayPlcGrpVlanEntry
        MAX-ACCESS  not-accessible
        STATUS      current
        DESCRIPTION
            "DHCP relay server policy group vlan table."
        ::= { zxr10dhcpRelayConfig 6 }

    zxr10dhcpRelayPlcGrpVlanEntry  OBJECT-TYPE
        SYNTAX      Zxr10dhcpRelayPlcGrpVlanEntry
        MAX-ACCESS  not-accessible
        STATUS      current
        DESCRIPTION
            "This list contains DHCP relay server policy group vlan parameters"     
        INDEX  { zxr10dhcpRelayPlcGrpIndex,  zxr10dhcpRelayPlcGrpVlanIndex }    
        ::= { zxr10dhcpRelayPlcGrpVlanTable 1 } 
        
    Zxr10dhcpRelayPlcGrpVlanEntry ::=
        SEQUENCE {
        zxr10dhcpRelayPlcGrpVlanIndex           Unsigned32,
        zxr10dhcpRelayPlcGrpVlanInStartVlan     Unsigned32,
        zxr10dhcpRelayPlcGrpVlanExStartVlan     Unsigned32,
        zxr10dhcpRelayPlcGrpVlanInEndVlan       Unsigned32,
        zxr10dhcpRelayPlcGrpVlanExEndVlan       Unsigned32                               
        }                       

     zxr10dhcpRelayPlcGrpVlanIndex OBJECT-TYPE
        SYNTAX        Unsigned32(1..8)
        MAX-ACCESS    read-only
        STATUS        current
        DESCRIPTION   "Relay server policy group vlan index."
        ::= { zxr10dhcpRelayPlcGrpVlanEntry 1 } 
        
     zxr10dhcpRelayPlcGrpVlanInStartVlan OBJECT-TYPE
        SYNTAX        Unsigned32(0..4094) 
        MAX-ACCESS    read-only
        STATUS        current
        DESCRIPTION   "The start vlan id of internal vlan."
        ::= { zxr10dhcpRelayPlcGrpVlanEntry 2 } 
        
     zxr10dhcpRelayPlcGrpVlanExStartVlan OBJECT-TYPE
        SYNTAX        Unsigned32(1..4094) 
        MAX-ACCESS    read-only
        STATUS        current
        DESCRIPTION   "The start vlan id of external vlan."
        ::= { zxr10dhcpRelayPlcGrpVlanEntry 3 } 
        
     zxr10dhcpRelayPlcGrpVlanInEndVlan OBJECT-TYPE
        SYNTAX        Unsigned32(0..4094) 
        MAX-ACCESS    read-only
        STATUS        current
        DESCRIPTION   "The end vlan id of internal vlan."
        ::= { zxr10dhcpRelayPlcGrpVlanEntry 4 } 
        
     zxr10dhcpRelayPlcGrpVlanExEndVlan OBJECT-TYPE
        SYNTAX        Unsigned32(1..4094) 
        MAX-ACCESS    read-only
        STATUS        current
        DESCRIPTION   "The end vlan id of external vlan."
        ::= { zxr10dhcpRelayPlcGrpVlanEntry 5 } 
        
        -- DHCP relay user table
     
    zxr10dhcpRelayUserTable  OBJECT-TYPE
        SYNTAX  SEQUENCE OF Zxr10dhcpRelayUserEntry
        MAX-ACCESS  not-accessible
        STATUS      current
        DESCRIPTION
            "DHCP relay user table."
        ::= { zxr10dhcpRelayConfig 7 }

    zxr10dhcpRelayUserEntry  OBJECT-TYPE
        SYNTAX      Zxr10dhcpRelayUserEntry
        MAX-ACCESS  not-accessible
        STATUS      current
        DESCRIPTION
            "This list contains DHCP relay user parameters"     
        INDEX  { zxr10dhcpRelayUserBoardName, zxr10dhcpRelayUserMac }    
        ::= { zxr10dhcpRelayUserTable 1 }
        
    Zxr10dhcpRelayUserEntry ::=
        SEQUENCE {
        zxr10dhcpRelayUserBoardName      DisplayString,
        zxr10dhcpRelayUserMac            OCTET STRING, 
        zxr10dhcpRelayUserIpAddr         IpAddress,
        zxr10dhcpRelayUserBindState      INTEGER,
        zxr10dhcpRelayUserRemLeaseTime   Unsigned32,
        zxr10dhcpRelayUserIfName         DisplayString, 
        zxr10dhcpRelayUserVrf            DisplayString,
        zxr10dhcpRelayUserSlotNo         Unsigned32,
        zxr10dhcpRelayUserTotalCount     Unsigned32                          
        }    
     
     zxr10dhcpRelayUserBoardName OBJECT-TYPE
        SYNTAX        DisplayString(SIZE(1..31))
        MAX-ACCESS    not-accessible
        STATUS        current
        DESCRIPTION   "Board name of the slot on which DHCP relay user be."
        ::= { zxr10dhcpRelayUserEntry 1 }
        
     zxr10dhcpRelayUserMac OBJECT-TYPE
        SYNTAX        OCTET STRING
        MAX-ACCESS    not-accessible
        STATUS        current
        DESCRIPTION   "DHCP relay user MAC."
        ::= { zxr10dhcpRelayUserEntry 2 }  
  
     zxr10dhcpRelayUserIpAddr OBJECT-TYPE
        SYNTAX        IpAddress 
        MAX-ACCESS    read-only
        STATUS        current
        DESCRIPTION   "DHCP relay user IP address."
        ::= { zxr10dhcpRelayUserEntry 3 }
        
     zxr10dhcpRelayUserBindState OBJECT-TYPE
        SYNTAX        INTEGER{
                           offering(1), 
                           bound(2)
                      }
        MAX-ACCESS    read-only
        STATUS        current
        DESCRIPTION   "DHCP relay user bind state." 
        DEFVAL { offering }         
        ::= { zxr10dhcpRelayUserEntry 4 }

     zxr10dhcpRelayUserRemLeaseTime OBJECT-TYPE
        SYNTAX        Unsigned32(0..4294967295) 
        MAX-ACCESS    read-only
        STATUS        current
        DESCRIPTION   "DHCP relay user remanent leasetime(sec)."
        ::= { zxr10dhcpRelayUserEntry 5 } 
         
     zxr10dhcpRelayUserIfName OBJECT-TYPE
        SYNTAX        DisplayString(SIZE(0..31)) 
        MAX-ACCESS    read-only
        STATUS        current
        DESCRIPTION   "DHCP relay user access interface name."
        ::= { zxr10dhcpRelayUserEntry 6 } 
     
    zxr10dhcpRelayUserVrf OBJECT-TYPE
        SYNTAX        DisplayString(SIZE(0..35))
        MAX-ACCESS    read-only
        STATUS        current
        DESCRIPTION   "DHCP relay user VRF name."
        ::= { zxr10dhcpRelayUserEntry 7 } 
        
    zxr10dhcpRelayUserSlotNo OBJECT-TYPE
        SYNTAX        Unsigned32(0..64) 
        MAX-ACCESS    read-only
        STATUS        current
        DESCRIPTION   "Number of the slot on which DHCP relay user be"
        ::= { zxr10dhcpRelayUserEntry 8 } 
    
    zxr10dhcpRelayUserTotalCount OBJECT-TYPE
        SYNTAX        Unsigned32
        MAX-ACCESS    read-only
        STATUS        current
        DESCRIPTION   "DHCP relay user total count on this board."
        ::= { zxr10dhcpRelayUserEntry 9 }   
        
     -- DHCP Relay Interface configuration(new)       

    zxr10dhcpRelayIfConfTable  OBJECT-TYPE
        SYNTAX  SEQUENCE OF Zxr10dhcpRelayIfConfEntry
        MAX-ACCESS  not-accessible
        STATUS      current
        DESCRIPTION
            "DHCP relay configuration table of interface."
        ::= { zxr10dhcpRelayConfig 8 }

    zxr10dhcpRelayIfConfEntry  OBJECT-TYPE
        SYNTAX      Zxr10dhcpRelayIfConfEntry
        MAX-ACCESS  not-accessible
        STATUS      current
        DESCRIPTION
            "This list contains DHCP relay parameters of user access interface"     
        INDEX  { zxr10dhcpIfName }    
        ::= { zxr10dhcpRelayIfConfTable 1 }
       
    Zxr10dhcpRelayIfConfEntry ::=
        SEQUENCE {
        zxr10dhcpIfName                  DisplayString,
        zxr10dhcpRelayIfConfAgentIP      IpAddress,                               
        zxr10dhcpRelayIfConfOpt82Cir     DisplayString,
        zxr10dhcpRelayIfConfOpt82Rem     DisplayString,                                 
        zxr10dhcpRelayIfConfSvrGrp       Unsigned32,
        zxr10dhcpRelayIfConfSvrPlc       INTEGER,
        zxr10dhcpRelayIfConfSrcIp        IpAddress,
        zxr10dhcpRelayIfConfAccList      DisplayString,
        zxr10dhcpRelayIfConfDscpVal      Unsigned32,
        zxr10dhcpRelayIfConfUdpPort      Unsigned32,
        zxr10dhcpRelayIfConfFwdMode      INTEGER,
        zxr10dhcpRelayIfConfAgentIfName  DisplayString,
        zxr10dhcpRelayIfConfAgentAlgth   INTEGER
        }
    
    zxr10dhcpIfName OBJECT-TYPE
        SYNTAX        DisplayString(SIZE(1..31)) 
        MAX-ACCESS    not-accessible
        STATUS        current
        DESCRIPTION   "DHCP interface name."
        ::= { zxr10dhcpRelayIfConfEntry 1 }
                
    zxr10dhcpRelayIfConfAgentIP OBJECT-TYPE
        SYNTAX        IpAddress 
        MAX-ACCESS    read-only
        STATUS        current
        DESCRIPTION   "DHCP relay agent ip address."
        ::= { zxr10dhcpRelayIfConfEntry 2 }
    
    zxr10dhcpRelayIfConfOpt82Cir OBJECT-TYPE
        SYNTAX        DisplayString(SIZE(0..64)) 
        MAX-ACCESS    read-only
        STATUS        current
        DESCRIPTION   "Option82 circuit-id of the interface."
        ::= { zxr10dhcpRelayIfConfEntry 3 }

    zxr10dhcpRelayIfConfOpt82Rem OBJECT-TYPE
        SYNTAX        DisplayString(SIZE(0..64)) 
        MAX-ACCESS    read-only
        STATUS        current
        DESCRIPTION   "Option82 remote-id of the interface."
        ::= { zxr10dhcpRelayIfConfEntry 4 }
        
    zxr10dhcpRelayIfConfSvrGrp OBJECT-TYPE
        SYNTAX        Unsigned32(0..20) 
        MAX-ACCESS    read-only
        STATUS        current
        DESCRIPTION   "DHCP relay server group index of the interface."
        ::= { zxr10dhcpRelayIfConfEntry 5 } 
                  
    zxr10dhcpRelayIfConfSvrPlc OBJECT-TYPE
        SYNTAX        INTEGER{
                           none(1), 
                           vclassId(2),
                           vlanId(3)
                      }         
        MAX-ACCESS    read-only
        STATUS        current
        DESCRIPTION   "DHCP relay helper-address policy of the interface."
        ::= { zxr10dhcpRelayIfConfEntry 6 } 
        
    zxr10dhcpRelayIfConfSrcIp OBJECT-TYPE
        SYNTAX        IpAddress 
        MAX-ACCESS    read-only
        STATUS        current
        DESCRIPTION   "DHCP relay source ip."
        ::= { zxr10dhcpRelayIfConfEntry 7 } 
        
    zxr10dhcpRelayIfConfAccList OBJECT-TYPE
        SYNTAX        DisplayString(SIZE(0..16)) 
        MAX-ACCESS    read-only
        STATUS        current
        DESCRIPTION   "DHCP access list name of the interface."
        ::= { zxr10dhcpRelayIfConfEntry 8 }
        
    zxr10dhcpRelayIfConfDscpVal OBJECT-TYPE
        SYNTAX        Unsigned32(0..63) 
        MAX-ACCESS    read-only
        STATUS        current
        DESCRIPTION   "DSCP value of the interface."
        ::= { zxr10dhcpRelayIfConfEntry 9 } 
        
    zxr10dhcpRelayIfConfUdpPort OBJECT-TYPE
        SYNTAX        Unsigned32(67..68)
        MAX-ACCESS    read-only
        STATUS        current
        DESCRIPTION   "DHCP server relay destination UDP port of the
                       interface."          
        ::= { zxr10dhcpRelayIfConfEntry 10 } 
        
    zxr10dhcpRelayIfConfFwdMode OBJECT-TYPE
        SYNTAX        INTEGER{
                        standard(1),
                        security(2)
                      }
        MAX-ACCESS    read-only
        STATUS        current
        DESCRIPTION   "DHCP relay forward mode."
        ::= { zxr10dhcpRelayIfConfEntry 11 }              
        
    zxr10dhcpRelayIfConfAgentIfName OBJECT-TYPE
        SYNTAX        DisplayString(SIZE(1..31)) 
        MAX-ACCESS    read-only
        STATUS        current
        DESCRIPTION   "DHCP relay agent algorithm configurate under interface."
        ::= { zxr10dhcpRelayIfConfEntry 12 }

    zxr10dhcpRelayIfConfAgentAlgth OBJECT-TYPE
        SYNTAX        INTEGER{
                        first(1),
                        roundRobin(2)
                      }
        MAX-ACCESS    read-only
        STATUS        current
        DESCRIPTION   "DHCP relay agent algorithm."
        ::= { zxr10dhcpRelayIfConfEntry 13 }

    -- DHCP relay server group server table(new)
    
    zxr10dhcpRelaySvrGrpServerTable  OBJECT-TYPE
        SYNTAX  SEQUENCE OF Zxr10dhcpRelaySvrGrpServerEntry
        MAX-ACCESS  not-accessible
        STATUS      current
        DESCRIPTION
            "DHCP relay server group server table."
        ::= { zxr10dhcpRelayConfig 9 }

    zxr10dhcpRelaySvrGrpServerEntry  OBJECT-TYPE
        SYNTAX      Zxr10dhcpRelaySvrGrpServerEntry
        MAX-ACCESS  not-accessible
        STATUS      current
        DESCRIPTION
            "This list contains DHCP relay server group server parameters"     
        INDEX  { zxr10dhcpRelayServerGrpIndex, zxr10dhcpRelaySvrGrpServerIndex }    
        ::= { zxr10dhcpRelaySvrGrpServerTable 1 }
        
    Zxr10dhcpRelaySvrGrpServerEntry ::=
        SEQUENCE { 
        zxr10dhcpRelayServerGrpIndex    Unsigned32,
        zxr10dhcpRelaySvrGrpServerIndex Unsigned32,
        zxr10dhcpRelaySvrGrpServerIp    IpAddress, 
        zxr10dhcpRelaySvrGrpServerMode  INTEGER,
        zxr10dhcpRelaySvrGrpServerMast  INTEGER,
        zxr10dhcpRelaySvrGrpServerDscp  Unsigned32,                                
        zxr10dhcpRelaySvrGrpServerPublic  TruthValue,
        zxr10dhcpRelaySvrGrpServerVrf     DisplayString
        }    
 
     zxr10dhcpRelayServerGrpIndex OBJECT-TYPE
        SYNTAX        Unsigned32(1..20) 
        MAX-ACCESS    not-accessible
        STATUS        current
        DESCRIPTION   "The DHCP relay server group number."
        ::= { zxr10dhcpRelaySvrGrpServerEntry 1 } 
        
    zxr10dhcpRelaySvrGrpServerIndex OBJECT-TYPE
        SYNTAX        Unsigned32(1..128)
        MAX-ACCESS    not-accessible
        STATUS        current
        DESCRIPTION   "The server number."
        ::= { zxr10dhcpRelaySvrGrpServerEntry 2 }

     zxr10dhcpRelaySvrGrpServerIp OBJECT-TYPE
        SYNTAX        IpAddress 
        MAX-ACCESS    read-only
        STATUS        current
        DESCRIPTION   "The IP address of the relay server group server."
        ::= { zxr10dhcpRelaySvrGrpServerEntry 3 } 
         
     zxr10dhcpRelaySvrGrpServerMode OBJECT-TYPE
        SYNTAX        INTEGER{
                           standard(1),
                           security(2)                      
                      }
        MAX-ACCESS    read-only
        STATUS        obsolete
        DESCRIPTION   "The server mode."
        ::= { zxr10dhcpRelaySvrGrpServerEntry 4 } 
     
    zxr10dhcpRelaySvrGrpServerMast OBJECT-TYPE
        SYNTAX        INTEGER{
                          slave(1),
                          master(2)                        
                      }
        MAX-ACCESS    read-only
        STATUS        current
        DESCRIPTION   "The server is master or slave."
        ::= { zxr10dhcpRelaySvrGrpServerEntry 5 } 
        
    zxr10dhcpRelaySvrGrpServerDscp OBJECT-TYPE
        SYNTAX        Unsigned32(0..63) 
        MAX-ACCESS    read-only
        STATUS        current
        DESCRIPTION   "DSCP value of DHCP relay when it sends packet to the server."
        ::= { zxr10dhcpRelaySvrGrpServerEntry 6 }      
    
    zxr10dhcpRelaySvrGrpServerPublic OBJECT-TYPE
        SYNTAX        TruthValue
        MAX-ACCESS    read-only
        STATUS        current
        DESCRIPTION   "The server is public server or not." 
        DEFVAL { false }        
        ::= { zxr10dhcpRelaySvrGrpServerEntry 7 }

    zxr10dhcpRelaySvrGrpServerVrf OBJECT-TYPE
        SYNTAX        DisplayString(SIZE(0..32)) 
        MAX-ACCESS    read-only
        STATUS        current
        DESCRIPTION   "The VRF of this server." 
        ::= { zxr10dhcpRelaySvrGrpServerEntry 8 }
    -- DHCP relay global config table(new)
    
    zxr10dhcpGlobalRelayConf  OBJECT IDENTIFIER ::= { zxr10dhcpRelayConfig 10 } 
    
    zxr10dhcpRelayMaxUserCfg OBJECT-TYPE
        SYNTAX        Unsigned32(1..64000)
        MAX-ACCESS    read-only
        STATUS        current
        DESCRIPTION   "Max user number of DHCP relay, default value is set
                       by project."
        ::= { zxr10dhcpGlobalRelayConf 1 }  
        
    zxr10dhcpRelayForbidSendRlsCfg OBJECT-TYPE
        SYNTAX      TruthValue
        MAX-ACCESS  read-only
        STATUS      current
        DESCRIPTION   "Forbid DHCP relay sends DHCPRELEASE to server or not." 
        DEFVAL { false }
        ::= { zxr10dhcpGlobalRelayConf 2 }
        
   zxr10dhcpRelayProxyLeaseCfg OBJECT-TYPE
        SYNTAX        Unsigned32(30..3600)
        MAX-ACCESS    read-only
        STATUS        current
        DESCRIPTION   
             "Set client lease time of proxy." 
        DEFVAL { 60 }     
        ::= { zxr10dhcpGlobalRelayConf 3 }                   
        
    zxr10dhcpRelayOpt82FormatCfg OBJECT-TYPE
        SYNTAX      INTEGER { 
                         chinaTel(1), 
                         dslForum(2),  
                         telenor(3), 
                         userConfiguration(4)
                    }
        MAX-ACCESS  read-only
        STATUS      current
        DESCRIPTION   "DHCP relay option82 format."  
        DEFVAL { chinaTel }
        ::= { zxr10dhcpGlobalRelayConf 4 }      
        
    zxr10dhcpRelayOpt82OptionCfg OBJECT-TYPE
        SYNTAX        TruthValue
        MAX-ACCESS    read-only
        STATUS        current
        DESCRIPTION   "Insert relay option82 or not in BOOTREQUEST."
        DEFVAL { false }
        ::= { zxr10dhcpGlobalRelayConf 5 }

    zxr10dhcpRelayOpt82PolicyCfg OBJECT-TYPE
        SYNTAX      INTEGER{ 
                         keep(2), 
                         replace(3), 
                         add(4)
                    }  
        MAX-ACCESS    read-only
        STATUS        current
        DESCRIPTION   "The option82 policy of DHCP relay." 
        DEFVAL { replace }
        ::= { zxr10dhcpGlobalRelayConf 6 }   
        
    zxr10dhcpRelayOpt82UserPlcyCfg OBJECT-TYPE
        SYNTAX        INTEGER{ 
                           interface(1), 
                           uniform(2) 
                      }          
        MAX-ACCESS    read-only
        STATUS        current
        DESCRIPTION   "DHCP option82 policy of user configuration." 
        DEFVAL { interface }        
        ::= { zxr10dhcpGlobalRelayConf 7 }
        
    zxr10dhcpRelayOpt82UniformCirCfg OBJECT-TYPE
        SYNTAX        DisplayString(SIZE(0..64))
        MAX-ACCESS    read-only
        STATUS        current
        DESCRIPTION   "The circuit-id subitem of uniform option82."
        ::= { zxr10dhcpGlobalRelayConf 8 }

    zxr10dhcpRelayOpt82UniformRemCfg OBJECT-TYPE
        SYNTAX        DisplayString(SIZE(0..64))
        MAX-ACCESS    read-only
        STATUS        current
        DESCRIPTION   "The remote-id subitem of uniform option82."
        ::= { zxr10dhcpGlobalRelayConf 9 }     

    zxr10dhcpRelayUptArpCfg OBJECT-TYPE
        SYNTAX        TruthValue     
        MAX-ACCESS    read-only
        STATUS        current
        DESCRIPTION   "Set the arp deadtime to dhcp lease or not."
        DEFVAL { false }
        ::= { zxr10dhcpGlobalRelayConf 10 } 
        
    zxr10dhcpRelayFwdRplUnrstrctdCfg OBJECT-TYPE
        SYNTAX        TruthValue     
        MAX-ACCESS    read-only
        STATUS        current
        DESCRIPTION   "Set forwarding DHCP reply packet without limit or not."
        DEFVAL { false }
        ::= { zxr10dhcpGlobalRelayConf 11 }

    zxr10dhcpRelayReportUserCfg OBJECT-TYPE
        SYNTAX        TruthValue     
        MAX-ACCESS    read-only
        STATUS        current
        DESCRIPTION   "Set reporting DHCP relay user information or not."
        DEFVAL { false }
        ::= { zxr10dhcpGlobalRelayConf 12 }

    -- DHCP relay agent index config table(new)
    zxr10dhcpRelayAgentIndexConfTable  OBJECT-TYPE
        SYNTAX  SEQUENCE OF Zxr10dhcpRelayAgentIndexConfEntry
        MAX-ACCESS  not-accessible
        STATUS      current
        DESCRIPTION
            "DHCP relay agent index configuration table."
        ::= { zxr10dhcpRelayConfig 11 }

    zxr10dhcpRelayAgentIndexConfEntry  OBJECT-TYPE
        SYNTAX      Zxr10dhcpRelayAgentIndexConfEntry
        MAX-ACCESS  not-accessible
        STATUS      current
        DESCRIPTION
            "This list contains DHCP relay agent index parameters of user access interface"     
        INDEX  { zxr10dhcpRlyAgentIndexIfName, zxr10dhcpRlyAgentIndex}    
        ::= { zxr10dhcpRelayAgentIndexConfTable 1 }
       
    Zxr10dhcpRelayAgentIndexConfEntry ::=
        SEQUENCE {
        zxr10dhcpRlyAgentIndexIfName     DisplayString,
        zxr10dhcpRlyAgentIndex           Unsigned32,                               
        zxr10dhcpRlyAgentIndexIP         IpAddress,
        zxr10dhcpRlyAgentIndexOptCode    Unsigned32,                                 
        zxr10dhcpRlyAgentIndexOptType    INTEGER,
        zxr10dhcpRlyAgentIndexOptText    DisplayString
        }
    
    zxr10dhcpRlyAgentIndexIfName OBJECT-TYPE
        SYNTAX        DisplayString(SIZE(1..31)) 
        MAX-ACCESS    not-accessible
        STATUS        current
        DESCRIPTION   "Under this DHCP interface,configurate DHCP relay agent index parameters."
        ::= { zxr10dhcpRelayAgentIndexConfEntry 1 }
 
    zxr10dhcpRlyAgentIndex OBJECT-TYPE
        SYNTAX        Unsigned32(1..32) 
        MAX-ACCESS    not-accessible
        STATUS        current
        DESCRIPTION   "DHCP relay agent index."
        ::= { zxr10dhcpRelayAgentIndexConfEntry 2 } 

    zxr10dhcpRlyAgentIndexIP OBJECT-TYPE
        SYNTAX        IpAddress 
        MAX-ACCESS    read-only
        STATUS        current
        DESCRIPTION   "DHCP relay agent ip address."
        ::= { zxr10dhcpRelayAgentIndexConfEntry 3 }

    zxr10dhcpRlyAgentIndexOptCode OBJECT-TYPE
        SYNTAX        Unsigned32(1..254) 
        MAX-ACCESS    read-only
        STATUS        current
        DESCRIPTION   "DHCP relay agent index option code."
        ::= { zxr10dhcpRelayAgentIndexConfEntry 4 } 

    zxr10dhcpRlyAgentIndexOptType OBJECT-TYPE
        SYNTAX        INTEGER{
                           ascii(1), 
                           hex(2)
                      }         
        MAX-ACCESS    read-only
        STATUS        current
        DESCRIPTION   "DHCP relay agent index option type."
        ::= { zxr10dhcpRelayAgentIndexConfEntry 5 } 
        
    zxr10dhcpRlyAgentIndexOptText OBJECT-TYPE
        SYNTAX        DisplayString(SIZE(1..64)) 
        MAX-ACCESS    read-only
        STATUS        current
        DESCRIPTION   "DHCP relay agent index option text."
        ::= { zxr10dhcpRelayAgentIndexConfEntry 6 }

    -- DHCP relay server group online user forward algorithm table

    zxr10dhcpRlySvrGrpFwdTable  OBJECT-TYPE
        SYNTAX  SEQUENCE OF Zxr10dhcpRlySvrGrpFwdEntry
        MAX-ACCESS  not-accessible
        STATUS      current
        DESCRIPTION
            "DHCP relay server group online user forward algorithm table."
        ::= { zxr10dhcpRelayConfig 12 }

    zxr10dhcpRlySvrGrpFwdEntry  OBJECT-TYPE
        SYNTAX      Zxr10dhcpRlySvrGrpFwdEntry
        MAX-ACCESS  not-accessible
        STATUS      current
        DESCRIPTION
            "This list contains DHCP relay online user fwd algorithm params"
        INDEX  { zxr10dhcpRelaySvrGrpIndex }
        ::= { zxr10dhcpRlySvrGrpFwdTable 1 }

    Zxr10dhcpRlySvrGrpFwdEntry ::=
        SEQUENCE {
        zxr10dhcpRlySvrOnlineFwdAlg       INTEGER,
        zxr10dhcpRlySvrOnlineFwdRenew     INTEGER,
        zxr10dhcpRlySvrOnlineFwdRebind    INTEGER,
        zxr10dhcpRlySvrOnlineFwdRelease   INTEGER,
        zxr10dhcpRlySvrOnlineFwdDecline   INTEGER
        }

    zxr10dhcpRlySvrOnlineFwdAlg OBJECT-TYPE
        SYNTAX        INTEGER{
                           forwardAll(1)
                      }
        MAX-ACCESS    read-only
        STATUS        current
        DESCRIPTION   "DHCP relay server group online-user forward algorithm."
        ::= { zxr10dhcpRlySvrGrpFwdEntry 1 }

    zxr10dhcpRlySvrOnlineFwdRenew OBJECT-TYPE
        SYNTAX      INTEGER { 
                         disable(1),
                         enable(2)
                    }
        MAX-ACCESS    read-only
        STATUS        current
        DESCRIPTION   "DHCP relay forward online-user renew-request or not."
        ::= { zxr10dhcpRlySvrGrpFwdEntry 2 }

    zxr10dhcpRlySvrOnlineFwdRebind OBJECT-TYPE
        SYNTAX      INTEGER { 
                         disable(1),
                         enable(2)
                    }
        MAX-ACCESS    read-only
        STATUS        current
        DESCRIPTION   "DHCP relay forward online-user rebinding-request or not."
        ::= { zxr10dhcpRlySvrGrpFwdEntry 3 }

    zxr10dhcpRlySvrOnlineFwdRelease OBJECT-TYPE
        SYNTAX      INTEGER { 
                         disable(1),
                         enable(2)
                    }
        MAX-ACCESS    read-only
        STATUS        current
        DESCRIPTION   "DHCP relay forward online-user release or not."
        ::= { zxr10dhcpRlySvrGrpFwdEntry 4 }

    zxr10dhcpRlySvrOnlineFwdDecline OBJECT-TYPE
        SYNTAX      INTEGER { 
                         disable(1),
                         enable(2)
                    }
        MAX-ACCESS    read-only
        STATUS        current
        DESCRIPTION   "DHCP relay forward online-user decline or not."
        ::= { zxr10dhcpRlySvrGrpFwdEntry 5 }

    -- DHCP pool common config table
    
    zxr10dhcpPoolCommTable  OBJECT-TYPE
        SYNTAX  SEQUENCE OF Zxr10dhcpPoolCommEntry
        MAX-ACCESS  not-accessible
        STATUS      current
        DESCRIPTION
            "DHCP pool common configure table."
        ::= { zxr10dhcpPoolConfig 1 }

    zxr10dhcpPoolCommEntry  OBJECT-TYPE
        SYNTAX      Zxr10dhcpPoolCommEntry
        MAX-ACCESS  not-accessible
        STATUS      current
        DESCRIPTION
            "This list contains DHCP pool common configure parameters"     
        INDEX  { zxr10dhcpPoolCommPoolName }    
        ::= { zxr10dhcpPoolCommTable 1 }
    
    Zxr10dhcpPoolCommEntry ::=
        SEQUENCE { 
        zxr10dhcpPoolCommPoolName       DisplayString,
        zxr10dhcpPoolCommIppoolName     DisplayString,
        zxr10dhcpPoolCommLsTimDay       Unsigned32,
        zxr10dhcpPoolCommLsTimHours     Unsigned32,
        zxr10dhcpPoolCommLsTimMinute    Unsigned32,
        zxr10dhcpPoolCommLsTimInfinite  TruthValue,                         
        zxr10dhcpPoolIgnoreRequestList  TruthValue,
        zxr10dhcpPoolCommLsTimSecond    Unsigned32
        }   
      
     zxr10dhcpPoolCommPoolName OBJECT-TYPE
        SYNTAX        DisplayString(SIZE(1..16)) 
        MAX-ACCESS    not-accessible
        STATUS        current
        DESCRIPTION   "DHCP pool name."
        ::= { zxr10dhcpPoolCommEntry 1 }    
 
     zxr10dhcpPoolCommIppoolName OBJECT-TYPE
        SYNTAX        DisplayString(SIZE(0..32)) 
        MAX-ACCESS    read-only
        STATUS        current
        DESCRIPTION   "DHCP pool IP pool name."
        ::= { zxr10dhcpPoolCommEntry 2 }
        
     zxr10dhcpPoolCommLsTimDay OBJECT-TYPE
        SYNTAX        Unsigned32(0..365) 
        MAX-ACCESS    read-only
        STATUS        current
        DESCRIPTION   "DHCP pool leasetime days."
        ::= { zxr10dhcpPoolCommEntry 3 }
        
     zxr10dhcpPoolCommLsTimHours OBJECT-TYPE
        SYNTAX        Unsigned32(0..23) 
        MAX-ACCESS    read-only
        STATUS        current
        DESCRIPTION   "DHCP pool leasetime hours."
        ::= { zxr10dhcpPoolCommEntry 4 }

     zxr10dhcpPoolCommLsTimMinute OBJECT-TYPE
        SYNTAX        Unsigned32(0..59) 
        MAX-ACCESS    read-only
        STATUS        current
        DESCRIPTION   "DHCP pool leasetime minutes."
        ::= { zxr10dhcpPoolCommEntry 5 }

    zxr10dhcpPoolCommLsTimInfinite OBJECT-TYPE
        SYNTAX        TruthValue 
        MAX-ACCESS    read-only
        STATUS        current    
        DESCRIPTION   "DHCP pool leasetime is infinite or not." 
        DEFVAL { false }
        ::= { zxr10dhcpPoolCommEntry 6 } 
        
    zxr10dhcpPoolIgnoreRequestList OBJECT-TYPE
        SYNTAX        TruthValue 
        MAX-ACCESS    read-only
        STATUS        current    
        DESCRIPTION   "DHCP pool is ignore request list or not." 
        DEFVAL { false }
        ::= { zxr10dhcpPoolCommEntry 7 } 

     zxr10dhcpPoolCommLsTimSecond OBJECT-TYPE
        SYNTAX        Unsigned32(0..59) 
        MAX-ACCESS    read-only
        STATUS        current
        DESCRIPTION   "DHCP pool leasetime seconds."
        ::= { zxr10dhcpPoolCommEntry 8 }        
    -- DHCP pool DNS server table
    
    zxr10dhcpPoolDnsTable  OBJECT-TYPE
        SYNTAX  SEQUENCE OF Zxr10dhcpPoolDnsEntry
        MAX-ACCESS  not-accessible
        STATUS      current
        DESCRIPTION
            "DHCP relay server group server table."
        ::= { zxr10dhcpPoolConfig 2 }

    zxr10dhcpPoolDnsEntry  OBJECT-TYPE
        SYNTAX      Zxr10dhcpPoolDnsEntry
        MAX-ACCESS  not-accessible
        STATUS      current
        DESCRIPTION
            "This list contains DHCP pool DNS server parameters"     
        INDEX  { zxr10dhcpPoolDnsDhcpPoolName, zxr10dhcpPoolDnsServer }    
        ::= { zxr10dhcpPoolDnsTable 1 }
    
    Zxr10dhcpPoolDnsEntry ::=
        SEQUENCE {
        zxr10dhcpPoolDnsDhcpPoolName    DisplayString, 
        zxr10dhcpPoolDnsServer          IpAddress                              
        }
        
     zxr10dhcpPoolDnsDhcpPoolName OBJECT-TYPE
        SYNTAX        DisplayString(SIZE(1..16)) 
        MAX-ACCESS    not-accessible
        STATUS        current
        DESCRIPTION   "DHCP pool name."
        ::= { zxr10dhcpPoolDnsEntry 1 }     
        
     zxr10dhcpPoolDnsServer OBJECT-TYPE
        SYNTAX        IpAddress 
        MAX-ACCESS    read-only
        STATUS        current
        DESCRIPTION   "DHCP pool DNS server IP address."
        ::= { zxr10dhcpPoolDnsEntry 2 } 
        
    -- DHCP pool default router table
    
    zxr10dhcpPoolDftRouterTable  OBJECT-TYPE
        SYNTAX  SEQUENCE OF Zxr10dhcpPoolDftRouterEntry
        MAX-ACCESS  not-accessible
        STATUS      current
        DESCRIPTION
            "DHCP pool default router table."
        ::= { zxr10dhcpPoolConfig 3 }

    zxr10dhcpPoolDftRouterEntry  OBJECT-TYPE
        SYNTAX      Zxr10dhcpPoolDftRouterEntry
        MAX-ACCESS  not-accessible
        STATUS      current
        DESCRIPTION
            "This list contains DHCP pool default router parameters"     
        INDEX  { zxr10dhcpPoolDftRouterPoolName, zxr10dhcpPoolDftRouterIpAddr }    
        ::= { zxr10dhcpPoolDftRouterTable 1 }
        
    Zxr10dhcpPoolDftRouterEntry ::=
        SEQUENCE {
        zxr10dhcpPoolDftRouterPoolName    DisplayString, 
        zxr10dhcpPoolDftRouterIpAddr      IpAddress                              
        } 
        
     zxr10dhcpPoolDftRouterPoolName OBJECT-TYPE
        SYNTAX        DisplayString(SIZE(1..16)) 
        MAX-ACCESS    not-accessible
        STATUS        current
        DESCRIPTION   "DHCP pool name."
        ::= { zxr10dhcpPoolDftRouterEntry 1 }
                      
     zxr10dhcpPoolDftRouterIpAddr OBJECT-TYPE
        SYNTAX        IpAddress 
        MAX-ACCESS    read-only
        STATUS        current
        DESCRIPTION   "DHCP pool default router IP address."
        ::= { zxr10dhcpPoolDftRouterEntry 2 }

    -- DHCP pool static table
    
    zxr10dhcpPoolStaticTable  OBJECT-TYPE
        SYNTAX  SEQUENCE OF Zxr10dhcpPoolStaticEntry
        MAX-ACCESS  not-accessible
        STATUS      current
        DESCRIPTION
            "DHCP pool common configure table."
        ::= { zxr10dhcpPoolConfig 4 }

    zxr10dhcpPoolStaticEntry  OBJECT-TYPE
        SYNTAX      Zxr10dhcpPoolStaticEntry
        MAX-ACCESS  not-accessible
        STATUS      current
        DESCRIPTION
            "This list contains DHCP pool common configure parameters"     
        INDEX  { zxr10dhcpPoolStaticDhcpPoolName, zxr10dhcpPoolStaticVrfName, 
                zxr10dhcpPoolStaticMacAddr }    
        ::= { zxr10dhcpPoolStaticTable 1 }
    
    Zxr10dhcpPoolStaticEntry ::=
        SEQUENCE {
        zxr10dhcpPoolStaticDhcpPoolName DisplayString, 
        zxr10dhcpPoolStaticVrfName      DisplayString,
        zxr10dhcpPoolStaticMacAddr      OCTET STRING,
        zxr10dhcpPoolStaticClientIp     IpAddress,
        zxr10dhcpPoolStaticClientMask   IpAddress                        
        }
        
     zxr10dhcpPoolStaticDhcpPoolName OBJECT-TYPE
        SYNTAX        DisplayString(SIZE(1..16)) 
        MAX-ACCESS    not-accessible
        STATUS        current
        DESCRIPTION   "DHCP pool name."
        ::= { zxr10dhcpPoolStaticEntry 1 }    
 
     zxr10dhcpPoolStaticVrfName OBJECT-TYPE
        SYNTAX        DisplayString(SIZE(0..35)) 
        MAX-ACCESS    not-accessible
        STATUS        current
        DESCRIPTION   "DHCP pool VRF name."
        ::= { zxr10dhcpPoolStaticEntry 2 }
        
     zxr10dhcpPoolStaticMacAddr OBJECT-TYPE
        SYNTAX        OCTET STRING 
        MAX-ACCESS    not-accessible
        STATUS        current
        DESCRIPTION   "DHCP pool static user MAC address."
        ::= { zxr10dhcpPoolStaticEntry 3 }
        
     zxr10dhcpPoolStaticClientIp OBJECT-TYPE
        SYNTAX        IpAddress 
        MAX-ACCESS    read-only
        STATUS        current
        DESCRIPTION   "DHCP pool static user IP address."
        ::= { zxr10dhcpPoolStaticEntry 4 }

     zxr10dhcpPoolStaticClientMask OBJECT-TYPE
        SYNTAX        IpAddress 
        MAX-ACCESS    read-only
        STATUS        current
        DESCRIPTION   "DHCP pool static user mask address."
        ::= { zxr10dhcpPoolStaticEntry 5 }
        
    -- DHCP pool common option table
    
    zxr10dhcpPoolOptionTable  OBJECT-TYPE
        SYNTAX  SEQUENCE OF Zxr10dhcpPoolOptionEntry
        MAX-ACCESS  not-accessible
        STATUS      current
        DESCRIPTION
            "DHCP pool common configure table."
        ::= { zxr10dhcpPoolConfig 5 }

    zxr10dhcpPoolOptionEntry  OBJECT-TYPE
        SYNTAX      Zxr10dhcpPoolOptionEntry
        MAX-ACCESS  not-accessible
        STATUS      current
        DESCRIPTION
            "This list contains DHCP pool common option configure parameters"     
        INDEX  { zxr10dhcpPoolOptionPoolName, zxr10dhcpPoolOptionCode, 
                zxr10dhcpPoolOptionSubOptCode }    
        ::= { zxr10dhcpPoolOptionTable 1 }
    
    Zxr10dhcpPoolOptionEntry ::=
        SEQUENCE {
        zxr10dhcpPoolOptionPoolName     DisplayString, 
        zxr10dhcpPoolOptionCode         Unsigned32,
        zxr10dhcpPoolOptionSubOptCode   Unsigned32,
        zxr10dhcpPoolOptionAsciiStr     DisplayString,
        zxr10dhcpPoolOptionHexStr       DisplayString,
        zxr10dhcpPoolOptionIpAddress1   IpAddress,
        zxr10dhcpPoolOptionIpAddress2   IpAddress,
        zxr10dhcpPoolOptionIpAddress3   IpAddress,
        zxr10dhcpPoolOptionIpAddress4   IpAddress,
        zxr10dhcpPoolOptionIpAddress5   IpAddress,
        zxr10dhcpPoolOptionIpAddress6   IpAddress,
        zxr10dhcpPoolOptionIpAddress7   IpAddress, 
        zxr10dhcpPoolOptionIpAddress8   IpAddress                       
        }
   
     zxr10dhcpPoolOptionPoolName OBJECT-TYPE
        SYNTAX        DisplayString(SIZE(1..16)) 
        MAX-ACCESS    not-accessible
        STATUS        current
        DESCRIPTION   "DHCP pool name."
        ::= { zxr10dhcpPoolOptionEntry 1 }    
 
     zxr10dhcpPoolOptionCode OBJECT-TYPE
        SYNTAX        Unsigned32 
        MAX-ACCESS    not-accessible
        STATUS        current
        DESCRIPTION   "DHCP pool option code."
        ::= { zxr10dhcpPoolOptionEntry 2 }
        
     zxr10dhcpPoolOptionSubOptCode OBJECT-TYPE
        SYNTAX        Unsigned32 
        MAX-ACCESS    not-accessible
        STATUS        current
        DESCRIPTION   "DHCP pool option sub-option code."
        ::= { zxr10dhcpPoolOptionEntry 3 }
        
     zxr10dhcpPoolOptionAsciiStr OBJECT-TYPE
        SYNTAX        DisplayString(SIZE(0..200)) 
        MAX-ACCESS    read-only
        STATUS        current
        DESCRIPTION   "DHCP pool option ASCII string configured."
        ::= { zxr10dhcpPoolOptionEntry 4 }

     zxr10dhcpPoolOptionHexStr OBJECT-TYPE
        SYNTAX        DisplayString(SIZE(0..200)) 
        MAX-ACCESS    read-only
        STATUS        current
        DESCRIPTION   "DHCP pool option HEX string configured."
        ::= { zxr10dhcpPoolOptionEntry 5 }
        
     zxr10dhcpPoolOptionIpAddress1 OBJECT-TYPE
        SYNTAX        IpAddress 
        MAX-ACCESS    read-only
        STATUS        current
        DESCRIPTION   "DHCP pool option IP address configured."
        ::= { zxr10dhcpPoolOptionEntry 6 } 
        
     zxr10dhcpPoolOptionIpAddress2 OBJECT-TYPE
        SYNTAX        IpAddress 
        MAX-ACCESS    read-only
        STATUS        current
        DESCRIPTION   "DHCP pool option IP address configured."
        ::= { zxr10dhcpPoolOptionEntry 7 }
        
     zxr10dhcpPoolOptionIpAddress3 OBJECT-TYPE
        SYNTAX        IpAddress 
        MAX-ACCESS    read-only
        STATUS        current
        DESCRIPTION   "DHCP pool option IP address configured."
        ::= { zxr10dhcpPoolOptionEntry 8 }
        
     zxr10dhcpPoolOptionIpAddress4 OBJECT-TYPE
        SYNTAX        IpAddress 
        MAX-ACCESS    read-only
        STATUS        current
        DESCRIPTION   "DHCP pool option IP address configured."
        ::= { zxr10dhcpPoolOptionEntry 9 }
        
     zxr10dhcpPoolOptionIpAddress5 OBJECT-TYPE
        SYNTAX        IpAddress 
        MAX-ACCESS    read-only
        STATUS        current
        DESCRIPTION   "DHCP pool option IP address configured."
        ::= { zxr10dhcpPoolOptionEntry 10 } 
        
     zxr10dhcpPoolOptionIpAddress6 OBJECT-TYPE
        SYNTAX        IpAddress 
        MAX-ACCESS    read-only
        STATUS        current
        DESCRIPTION   "DHCP pool option IP address configured."
        ::= { zxr10dhcpPoolOptionEntry 11 }

     zxr10dhcpPoolOptionIpAddress7 OBJECT-TYPE
        SYNTAX        IpAddress 
        MAX-ACCESS    read-only
        STATUS        current
        DESCRIPTION   "DHCP pool option IP address configured."
        ::= { zxr10dhcpPoolOptionEntry 12 }
        
     zxr10dhcpPoolOptionIpAddress8 OBJECT-TYPE
        SYNTAX        IpAddress 
        MAX-ACCESS    read-only
        STATUS        current
        DESCRIPTION   "DHCP pool option IP address configured."
        ::= { zxr10dhcpPoolOptionEntry 13 }
        
        
    -- DHCP pool option212 table
    
    zxr10dhcpPoolOpt212Table  OBJECT-TYPE
        SYNTAX  SEQUENCE OF Zxr10dhcpPoolOpt212Entry
        MAX-ACCESS  not-accessible
        STATUS      current
        DESCRIPTION
            "DHCP pool option212 table."
        ::= { zxr10dhcpPoolConfig 6 }

    zxr10dhcpPoolOpt212Entry  OBJECT-TYPE
        SYNTAX      Zxr10dhcpPoolOpt212Entry
        MAX-ACCESS  not-accessible
        STATUS      current
        DESCRIPTION
            "This list contains DHCP pool option212 configure parameters"     
        INDEX  { zxr10dhcpPoolOpt212DhcpPoolName }    
        ::= { zxr10dhcpPoolOpt212Table 1 }
    
    Zxr10dhcpPoolOpt212Entry ::=
        SEQUENCE {
        zxr10dhcpPoolOpt212DhcpPoolName    DisplayString,
        zxr10dhcpPoolOpt212Ipv6Prefix      Ipv6Address,
        zxr10dhcpPoolOpt212Ipv6PrefixLen   Unsigned32,
        zxr10dhcpPoolOpt212MaskLen         Unsigned32,
        zxr10dhcpPoolOpt212BrAddress1      IpAddress,
        zxr10dhcpPoolOpt212BrAddress2      IpAddress,
        zxr10dhcpPoolOpt212BrAddress3      IpAddress,
        zxr10dhcpPoolOpt212BrAddress4      IpAddress,
        zxr10dhcpPoolOpt212BrAddress5      IpAddress             
        }
        
     zxr10dhcpPoolOpt212DhcpPoolName OBJECT-TYPE
        SYNTAX        DisplayString(SIZE(1..16)) 
        MAX-ACCESS    not-accessible
        STATUS        current
        DESCRIPTION   "DHCP pool name."
        ::= { zxr10dhcpPoolOpt212Entry 1 }    
 
     zxr10dhcpPoolOpt212Ipv6Prefix OBJECT-TYPE
        SYNTAX        Ipv6Address 
        MAX-ACCESS    read-only
        STATUS        current
        DESCRIPTION   "DHCP pool option212 IPv6 prefix address."
        ::= { zxr10dhcpPoolOpt212Entry 2 }
        
     zxr10dhcpPoolOpt212Ipv6PrefixLen OBJECT-TYPE
        SYNTAX        Unsigned32 
        MAX-ACCESS    read-only
        STATUS        current
        DESCRIPTION   "DHCP pool option212 IPv6 prefix length."
        ::= { zxr10dhcpPoolOpt212Entry 3 }
        
     zxr10dhcpPoolOpt212MaskLen OBJECT-TYPE
        SYNTAX        Unsigned32 
        MAX-ACCESS    read-only
        STATUS        current
        DESCRIPTION   "DHCP pool option212 mask length."
        ::= { zxr10dhcpPoolOpt212Entry 4 }
        
     zxr10dhcpPoolOpt212BrAddress1 OBJECT-TYPE
        SYNTAX        IpAddress 
        MAX-ACCESS    read-only
        STATUS        current
        DESCRIPTION   "DHCP pool option212 BR address 1."
        ::= { zxr10dhcpPoolOpt212Entry 5 }

     zxr10dhcpPoolOpt212BrAddress2 OBJECT-TYPE
        SYNTAX        IpAddress 
        MAX-ACCESS    read-only
        STATUS        current
        DESCRIPTION   "DHCP pool option212 BR address 2."
        ::= { zxr10dhcpPoolOpt212Entry 6 }
        
     zxr10dhcpPoolOpt212BrAddress3 OBJECT-TYPE
        SYNTAX        IpAddress 
        MAX-ACCESS    read-only
        STATUS        current
        DESCRIPTION   "DHCP pool option212 BR address 3."
        ::= { zxr10dhcpPoolOpt212Entry 7 } 
        
     zxr10dhcpPoolOpt212BrAddress4 OBJECT-TYPE
        SYNTAX        IpAddress 
        MAX-ACCESS    read-only
        STATUS        current
        DESCRIPTION   "DHCP pool option212 BR address 4."
        ::= { zxr10dhcpPoolOpt212Entry 8 }
        
     zxr10dhcpPoolOpt212BrAddress5 OBJECT-TYPE
        SYNTAX        IpAddress 
        MAX-ACCESS    read-only
        STATUS        current
        DESCRIPTION   "DHCP pool option212 BR address 5."
        ::= { zxr10dhcpPoolOpt212Entry 9 }
        
    -- DHCP pool common option125 table
                 
    zxr10dhcpPoolOption125Table  OBJECT-TYPE
        SYNTAX  SEQUENCE OF Zxr10dhcpPoolOption125Entry
        MAX-ACCESS  not-accessible
        STATUS      current
        DESCRIPTION
            "DHCP pool common configure table."
        ::= { zxr10dhcpPoolConfig 7 }

    zxr10dhcpPoolOption125Entry  OBJECT-TYPE
        SYNTAX      Zxr10dhcpPoolOption125Entry
        MAX-ACCESS  not-accessible
        STATUS      current
        DESCRIPTION
            "This list contains DHCP pool common option125 configure parameters"     
        INDEX  { zxr10dhcpPoolOpt125DhcpPoolName, zxr10dhcpPoolOption125code, 
                zxr10dhcpPoolOption125SubOptCode }    
        ::= { zxr10dhcpPoolOption125Table 1 }
    
    Zxr10dhcpPoolOption125Entry ::=
        SEQUENCE {
        zxr10dhcpPoolOpt125DhcpPoolName         DisplayString, 
        zxr10dhcpPoolOption125code              Unsigned32,
        zxr10dhcpPoolOption125SubOptCode        Unsigned32,
        zxr10dhcpPoolOption125AsciiStr          DisplayString,
        zxr10dhcpPoolOption125HexStr            DisplayString,
        zxr10dhcpPoolOption125IpAddress1        IpAddress,
        zxr10dhcpPoolOption125IpAddress2        IpAddress,
        zxr10dhcpPoolOption125IpAddress3        IpAddress,
        zxr10dhcpPoolOption125IpAddress4        IpAddress,
        zxr10dhcpPoolOption125IpAddress5        IpAddress,
        zxr10dhcpPoolOption125IpAddress6        IpAddress,
        zxr10dhcpPoolOption125IpAddress7        IpAddress, 
        zxr10dhcpPoolOption125IpAddress8        IpAddress                       
        }
   
     zxr10dhcpPoolOpt125DhcpPoolName OBJECT-TYPE
        SYNTAX        DisplayString(SIZE(1..16)) 
        MAX-ACCESS    not-accessible
        STATUS        current
        DESCRIPTION   "DHCP pool name."
        ::= { zxr10dhcpPoolOption125Entry 1 }    
 
     zxr10dhcpPoolOption125code OBJECT-TYPE
        SYNTAX        Unsigned32 
        MAX-ACCESS    not-accessible
        STATUS        current
        DESCRIPTION   "DHCP pool option125 enterprise code."
        ::= { zxr10dhcpPoolOption125Entry 2 }
        
     zxr10dhcpPoolOption125SubOptCode OBJECT-TYPE
        SYNTAX        Unsigned32 
        MAX-ACCESS    not-accessible
        STATUS        current
        DESCRIPTION   "DHCP pool option125 sub-option code."
        ::= { zxr10dhcpPoolOption125Entry 3 }
        
     zxr10dhcpPoolOption125AsciiStr OBJECT-TYPE
        SYNTAX        DisplayString(SIZE(0..200)) 
        MAX-ACCESS    read-only
        STATUS        current
        DESCRIPTION   "DHCP pool option125 ASCII string configured."
        ::= { zxr10dhcpPoolOption125Entry 4 }

     zxr10dhcpPoolOption125HexStr OBJECT-TYPE
        SYNTAX        DisplayString(SIZE(0..200)) 
        MAX-ACCESS    read-only
        STATUS        current
        DESCRIPTION   "DHCP pool option125 HEX string configured."
        ::= { zxr10dhcpPoolOption125Entry 5 }

     zxr10dhcpPoolOption125IpAddress1 OBJECT-TYPE
        SYNTAX        IpAddress 
        MAX-ACCESS    read-only
        STATUS        current
        DESCRIPTION   "DHCP pool option125 IP address configured."
        ::= { zxr10dhcpPoolOption125Entry 6 } 
        
     zxr10dhcpPoolOption125IpAddress2 OBJECT-TYPE
        SYNTAX        IpAddress 
        MAX-ACCESS    read-only
        STATUS        current
        DESCRIPTION   "DHCP pool option125 IP address configured."
        ::= { zxr10dhcpPoolOption125Entry 7 }
        
     zxr10dhcpPoolOption125IpAddress3 OBJECT-TYPE
        SYNTAX        IpAddress 
        MAX-ACCESS    read-only
        STATUS        current
        DESCRIPTION   "DHCP pool option125 IP address configured."
        ::= { zxr10dhcpPoolOption125Entry 8 }
        
     zxr10dhcpPoolOption125IpAddress4 OBJECT-TYPE
        SYNTAX        IpAddress 
        MAX-ACCESS    read-only
        STATUS        current
        DESCRIPTION   "DHCP pool option125 IP address configured."
        ::= { zxr10dhcpPoolOption125Entry 9 }
        
     zxr10dhcpPoolOption125IpAddress5 OBJECT-TYPE
        SYNTAX        IpAddress 
        MAX-ACCESS    read-only
        STATUS        current
        DESCRIPTION   "DHCP pool option125 IP address configured."
        ::= { zxr10dhcpPoolOption125Entry 10 } 
        
     zxr10dhcpPoolOption125IpAddress6 OBJECT-TYPE
        SYNTAX        IpAddress 
        MAX-ACCESS    read-only
        STATUS        current
        DESCRIPTION   "DHCP pool option125 IP address configured."
        ::= { zxr10dhcpPoolOption125Entry 11 }

     zxr10dhcpPoolOption125IpAddress7 OBJECT-TYPE
        SYNTAX        IpAddress 
        MAX-ACCESS    read-only
        STATUS        current
        DESCRIPTION   "DHCP pool option125 IP address configured."
        ::= { zxr10dhcpPoolOption125Entry 12 }
        
     zxr10dhcpPoolOption125IpAddress8 OBJECT-TYPE
        SYNTAX        IpAddress 
        MAX-ACCESS    read-only
        STATUS        current
        DESCRIPTION   "DHCP pool option125 IP address configured."
        ::= { zxr10dhcpPoolOption125Entry 13 }
 END
