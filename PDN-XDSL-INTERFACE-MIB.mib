PDN-XDSL-INTERFACE-MIB DEFINITIONS ::= BEGIN





-- Version : 1.0


-- Added xdslDevGenericIfConfigSnType.


-- Removed unused IMPORTS to clear compile warnings.


-- Updated by Jesus A. Pinto, January 3th 2002





-- Version : 0.9


-- Changed description for xdslDevMVLSpecificIfConfigOnHookPowerAttenuation


-- to include new permissable values for this object as described by the


-- NMS Spec and as implemented.


-- Changed description for xdslDevMVLSpecificIfConfigOffHookPowerAttenuation


-- to include new permissable values for this object as described by the


-- NMS Spec and as implemented.


-- Updated by Jesus A. Pinto, June 29th 2001





-- Version : 0.8


-- deprecated xdslDevMVLSpecificIfConfigMaxPortSpeed


-- Added xdslDevMVLSpecificIfConfigMaxUpStreamPortSpeed


-- Added xdslDevMVLSpecificIfConfigMaxDownStreamPortSpeed


-- Changed the description for xdslDevMVLSpecificIfConfigMaxPortSpeed


-- Updated by Mohan Mohankumar, June 20th 2001





-- Version : 0.7


-- Added xdslDevGenericIfConfigLineEncapType


-- Updated by Dragana Gough, March 22nd 2001





-- Version : 0.6


-- Added xdslDevGenericIfConfigLineEncodeType


-- xdslDevMVLSpecificIfConfigOnHookPC and SN Voltage Drop ThresholdValue


-- restored xdslDevIDSLSpecificChannel


-- Updated by Dragana Gough, March 22nd 2001





-- Version :  0.5


-- Added xdslDevSDSLSpecificIfConfigMinSnrMargin in 


-- 	xdslDevSDSLSpecificIfConfigTable


-- Removed xdslDevGenericIfConfigMaxSnrMargin in xdslDevGenericIfConfigTable


-- Added xdslDevSDSLSpecificIfConfigTargetSnrMargin in 


--	xdslDevSDSLSpecificIfConfigTable


-- Updated by R.A.Bowhall, March 9th, 2001





-- Version :  0.4


-- Added xdslDevGenericIfConfigMinSnrMargin in xdslDevGenericIfConfigTable


-- Added xdslDevGenericIfConfigMaxSnrMargin in xdslDevGenericIfConfigTable


-- Added xdslDevGenericIfConfigTargetSnrMargin in xdslDevGenericIfConfigTable


-- Updated by R.A.Bowhall, March 8th, 2001





-- Version :  0.3


-- Added xdslLinkUpDownTransitions TRAP (under protest in that it already is defined


--       in the HOT MIB for Mirror objects)


-- Version :  0.2


-- Added xdslDevGenericIfConfigLineRateMode in xdslDevGenericIfConfigTable


-- Added xdslDevSDSLSpecificIfConfigFixedPortSpeedNx128Mode and


--       xdslDevSDSLSpecificIfConfigMaxPortSpeedNx128Mode


-- Updated by Z. Pan





-- Version :  0.1 DRAFT


-- Enterprise Time mib


-- Copyright (C) 1999 Paradyne Corporation.





-- Created by : Rajesh Gowda





IMPORTS


     


   DisplayString


    FROM SNMPv2-TC


   OBJECT-TYPE


     FROM RFC-1212


   TRAP-TYPE


     FROM RFC-1215


   ifIndex


     FROM RFC1213-MIB


   pdn-xdsl


     FROM PDN-HEADER-MIB


     ;





 xdslIfConfigMIBObjects        OBJECT IDENTIFIER ::= { pdn-xdsl 2 }


 xdslIfConfigMIBTraps          OBJECT IDENTIFIER ::= { pdn-xdsl 4 }


 xdslDevGenericIfConfig        OBJECT IDENTIFIER ::= { xdslIfConfigMIBObjects 1 }


 xdslDevRADSLSpecificIfConfig  OBJECT IDENTIFIER ::= { xdslIfConfigMIBObjects 2 }


 xdslDevMVLSpecificIfConfig    OBJECT IDENTIFIER ::= { xdslIfConfigMIBObjects 3 }


 xdslDevSDSLSpecificIfConfig   OBJECT IDENTIFIER ::= { xdslIfConfigMIBObjects 4 }


 xdslDevIDSLSpecificIfConfig   OBJECT IDENTIFIER ::= { xdslIfConfigMIBObjects 5 }





 -- The xdslDevGenericIfConfig group. Implementation of this group is


 -- mandatory for all type of DSL.





 xdslDevGenericIfConfigTable OBJECT-TYPE


   SYNTAX SEQUENCE OF XdslDevGenericIfConfigEntry


   ACCESS not-accessible


   STATUS mandatory


   DESCRIPTION


     "The xdslDevGenericIfConfigTable provides config information 


      generic to a xDSL device, or system. The table is indexed by an 


      object which corresponds to ifIndex. These ifIndex entries, 


      themselves, denote and identify specific xdsl interfaces on


      the board or module. Also the configuration parameters are


      grouped into two broad categories, 'up' and 'down'. 'up'


      reflects the upstream direction (from the customer premises


      to the central office). 'Down' reflects the downstream


      direction (from the central office to the customer premises)"


 ::= { xdslDevGenericIfConfig 1 }





 xdslDevGenericIfConfigEntry OBJECT-TYPE


   SYNTAX XdslDevGenericIfConfigEntry


   ACCESS not-accessible


   STATUS mandatory


   DESCRIPTION


     "Describes a specific xDSL interface entry."


   INDEX { ifIndex }


 ::= { xdslDevGenericIfConfigTable 1 }





 XdslDevGenericIfConfigEntry ::=


   SEQUENCE {


     xdslDevGenericIfConfigPortSpeedBehaviour


       INTEGER,


     xdslDevGenericIfConfigMarginThreshold 


       INTEGER,


     xdslDevGenericIfConfigPortID


       DisplayString (SIZE (1..40)),


     xdslDevGenericIfConfigLinkUpDownTransitionThreshold


       INTEGER,


     xdslDevGenericIfConfigLineEncodeType


       INTEGER,


     xdslDevGenericIfConfigLineRateMode


       INTEGER,


     xdslDevGenericIfConfigLinkEncapType


       INTEGER,


     xdslDevGenericIfConfigSnType


       OBJECT IDENTIFIER


  }





 xdslDevGenericIfConfigPortSpeedBehaviour OBJECT-TYPE


   SYNTAX INTEGER {


     fixed (1),


     adaptive (2)


   }


   ACCESS read-write


   STATUS mandatory


   DESCRIPTION


     "The value of this object corresponds to the


      behaviour of the specified port. The default


      value for this object is fixed (1). "


 ::= { xdslDevGenericIfConfigEntry 1 }





 xdslDevGenericIfConfigMarginThreshold OBJECT-TYPE


   SYNTAX INTEGER 


   ACCESS read-write


   STATUS mandatory


   DESCRIPTION


    "The value of this object corresponds to the offset from


     the startup margin. The threshold margin is calculated


     by subtracting the offset from the startup margin. 


     Permissible range of values are between -7 and 14.


     A value of -9999 disables the threshold check. The default


     value of this object is 3"


 ::= { xdslDevGenericIfConfigEntry 2 }





 xdslDevGenericIfConfigPortID OBJECT-TYPE


   SYNTAX DisplayString (SIZE (1..40))


   ACCESS read-write


   STATUS mandatory


   DESCRIPTION


     "The value of this object corresponds to  40 character


      information only field that identifies what the DSL


      port is connected to (Circuit ID, MDF location, 


      Customer name, etc.)"


 ::= { xdslDevGenericIfConfigEntry 3 }





 xdslDevGenericIfConfigLinkUpDownTransitionThreshold OBJECT-TYPE


   SYNTAX INTEGER


   ACCESS read-write


   STATUS mandatory


   DESCRIPTION


     "The value of this object corresponds to the threshold


      value for link up-down transitions. If link up-down's exceed


      this threshold value a xdslLinkupDownTransitions


      trap is generated. This value would represent the number


      of link up-down transitions in a 15 minute interval. A value


      of -9999 disables the threshold check. The default value for this


      object is 0"


 ::= { xdslDevGenericIfConfigEntry 4 }


 


 xdslDevGenericIfConfigLineEncodeType OBJECT-TYPE


   SYNTAX INTEGER {


       other  (1),


       cap    (2),


       twoB1q (3),


       mvl    (4),


       g-lite (5),


       dmt    (6)


    }


   ACCESS read-only


   STATUS mandatory


   DESCRIPTION


     "The value of this object corresponds to the line


      encoding technology used for data transmission over


      the the dsl link."


 ::= { xdslDevGenericIfConfigEntry 5 }


     


 xdslDevGenericIfConfigLineRateMode OBJECT-TYPE


   SYNTAX INTEGER {


       standard (1),


       nx128    (2)


    }


   ACCESS read-write


   STATUS mandatory


   DESCRIPTION


     "The value of this object is used to choose the line


      rate list for data transmission over the dsl link.


      The default value is standard(1). "


 ::= { xdslDevGenericIfConfigEntry 6 }





 xdslDevGenericIfConfigLinkEncapType OBJECT-TYPE


   SYNTAX INTEGER {


       linkNone   (1),


       ethernet   (2),


       ppp 	  (3),


       slip       (4),


       frameRelay-PLL (5),


       x23PVC    (6),


       x25SVC	  (7),


       hdlc      (8),


       etherHDLC  (9),


       rfc1483-MPOA (10),


       funi-MPOA    (11),


       frf5	  (12),


       frf8	  (13),


       pppoAVC-Mux (14),


       pppoALLC  (15)


    }


   ACCESS read-write


   STATUS mandatory


   DESCRIPTION


     "The value of this object corresponds to the link


      encapsulation type. Following are valid settings:


       linkNone   (1)


       ethernet   (2)


       ppp 	  (3)


       slip       (4)


       frameRelay-PLL (5)


       x23PVC    (6)


       x25SVC	  (7)


       hdlc      (8)


       etherHDLC  (9)


       rfc1483-MPOA (10)


       funi-MPOA    (11)


       frf5	  (12)


       frf8	  (13)


       pppoAVC-Mux (14)


       pppoALLC  (15) "


 ::= { xdslDevGenericIfConfigEntry 7 }





 xdslDevGenericIfConfigSnType OBJECT-TYPE


   SYNTAX OBJECT IDENTIFIER


   ACCESS read-write


   STATUS mandatory


   DESCRIPTION


     "The value of this object is used to choose a valid 


      Service Node Type to be configured in the port. The


      configurable values are the object identifiers of the


      remote endpoints as defined in the xdsl-remote group


      of the pdn-xdsl-products.


      The following are examples of valid endpoints for the


      8312 Reach port card:


	xdsl_6350,


	xdsl_6351,


	xdsl_6310


      By default, this object will be set to the default


      service node associated with the portcard."


 ::= { xdslDevGenericIfConfigEntry 8 }


 


 -- The xdslDevRADSLSpecificIfConfig group. Implementation of this


 -- group is mandatory for RADSL.





 xdslDevRADSLSpecificIfConfigTable OBJECT-TYPE


   SYNTAX SEQUENCE OF XdslDevRADSLSpecificIfConfigEntry


   ACCESS not-accessible


   STATUS mandatory


   DESCRIPTION


     "The xdslDevRADSLSpecificIfConfigTable provides config information


      specific to a xDSL device, or system. The table is indexed by


      an object which corresponds to ifIndex. These ifIndex entries, 


      themselves, denote and identify specific xdsl interfaces on


      the board or module. Also the configuration parameters are


      grouped into two broad categories, 'up' and 'down'. 'up'


      reflects the upstream direction (from the customer premises


      to the central office). 'Down' reflects the downstream


      direction (from the central office to the customer premises)"


 ::= { xdslDevRADSLSpecificIfConfig 1 }





 xdslDevRADSLSpecificIfConfigEntry OBJECT-TYPE


   SYNTAX XdslDevRADSLSpecificIfConfigEntry


   ACCESS not-accessible


   STATUS mandatory


   DESCRIPTION


     "Describes a specific xDSL interface entry."


   INDEX { ifIndex }


 ::= { xdslDevRADSLSpecificIfConfigTable 1 }





 XdslDevRADSLSpecificIfConfigEntry ::=


   SEQUENCE {


     xdslDevRADSLSpecificIfConfigUpFixedPortSpeed 


       INTEGER,


     xdslDevRADSLSpecificIfConfigDownFixedPortSpeed 


       INTEGER,


     xdslDevRADSLSpecificIfConfigUpAdaptiveUpperBoundPortSpeed 


       INTEGER,


     xdslDevRADSLSpecificIfConfigUpAdaptiveLowerBoundPortSpeed 


       INTEGER,


     xdslDevRADSLSpecificIfConfigDownAdaptiveUpperBoundPortSpeed 


       INTEGER,


     xdslDevRADSLSpecificIfConfigDownAdaptiveLowerBoundPortSpeed 


       INTEGER,


     xdslDevRADSLSpecificIfConfigReedSolomonDownFwdErrCorrection 


       INTEGER,


     xdslDevRADSLSpecificIfConfigStartUpMargin


       INTEGER (-3..9),


     xdslDevRADSLSpecificIfConfigTxPowerAttenuation


       INTEGER,


     xdslDevRADSLSpecificIfConfigSnTxPowerAttenuation


       INTEGER


  }





 xdslDevRADSLSpecificIfConfigUpFixedPortSpeed OBJECT-TYPE


   SYNTAX INTEGER 


   ACCESS read-write


   STATUS mandatory


   DESCRIPTION


     "The value of this object corresponds to the upstream


      speed of the specified port for fixed port speed


      behaviour. All the speeds are in kbps.


      If the port speed behaviour is adaptive an error


      of noSuchName will be returned by the agent."


 ::= { xdslDevRADSLSpecificIfConfigEntry 1 }





 xdslDevRADSLSpecificIfConfigDownFixedPortSpeed OBJECT-TYPE


   SYNTAX INTEGER


   ACCESS read-write


   STATUS mandatory


   DESCRIPTION


     "The value of this object corresponds to the downstream


      speed of the specified port for fixed port speed


      behaviour. All the speeds are in kbps. 


      If the port speed behaviour is adaptive an error of noSuchName


      will be returned by the agent.  "


 ::= { xdslDevRADSLSpecificIfConfigEntry 2 }





 xdslDevRADSLSpecificIfConfigUpAdaptiveUpperBoundPortSpeed OBJECT-TYPE


   SYNTAX INTEGER


   ACCESS read-write


   STATUS mandatory


   DESCRIPTION


     "The value of this object corresponds to the 


      upper bound for the upstream port speed of the specified port


      for adaptive port speed behaviour. The speeds are measured


      in kbps. If the port speed behaviour is fixed


      an error of noSuchName will be returned by the agent."


 ::= { xdslDevRADSLSpecificIfConfigEntry 3 }





 xdslDevRADSLSpecificIfConfigUpAdaptiveLowerBoundPortSpeed OBJECT-TYPE


   SYNTAX INTEGER


   ACCESS read-write


   STATUS mandatory


   DESCRIPTION


     "The value of this object corresponds to the


      lower bound for the upstream port speed of the 


      specified port for adaptive port speed behaviour


      in kbps. If the port speed behaviour is fixed an 


	  error of noSuchName will be returned by the agent.  


	  The value -9999 should be used to disable the lower


      bound threshold check. The default value for this 


	  object is -9999 "


 ::= { xdslDevRADSLSpecificIfConfigEntry 4 }





 xdslDevRADSLSpecificIfConfigDownAdaptiveUpperBoundPortSpeed OBJECT-TYPE


   SYNTAX INTEGER


   ACCESS read-write


   STATUS mandatory


   DESCRIPTION


     "The value of this object corresponds to 


      the upper bound allowed for the downstream port speed 


      of the specified port for adaptive port speed 


      behaviour. The speeds are measured in kbps. 


      If the port speed behaviour is fixed an error of noSuchName


      will be returned by the agent."


 ::= { xdslDevRADSLSpecificIfConfigEntry 5 }





 xdslDevRADSLSpecificIfConfigDownAdaptiveLowerBoundPortSpeed OBJECT-TYPE


   SYNTAX INTEGER


   ACCESS read-write


   STATUS mandatory


   DESCRIPTION


     "The value of this object corresponds to the


      Minimum lower bound allowed for the downstream port speed 


      of the specified port for adaptive port speed behaviour.


      If the port speed behaviour is fixed an error of noSuchName


      will be returned by the agent.  The speeds are measured in kbps.


      The value -9999 is used to disable the lower bound threshold 


      check.The default value for this object is -9999"


 ::= { xdslDevRADSLSpecificIfConfigEntry 6 }





 xdslDevRADSLSpecificIfConfigReedSolomonDownFwdErrCorrection OBJECT-TYPE


   SYNTAX INTEGER {


     minimizeError (1),


     minimizeDelay (2),


     reedSolomonNotSupported(3)


   }


   ACCESS read-write


   STATUS mandatory


   DESCRIPTION


     "The value of this object corresponds to the


      Reed-Solomon forward error correction in the downstream


      direction. The default value of this object should be 


      minimizeError (1)."


 ::= { xdslDevRADSLSpecificIfConfigEntry 7 }





 xdslDevRADSLSpecificIfConfigStartUpMargin OBJECT-TYPE


   SYNTAX INTEGER (-3..9)


   ACCESS read-write


   STATUS mandatory


   DESCRIPTION


     " The value of this object corresponds to the startup value


       of the margin for a DSL interface (specified by ifIndex).


       The unit is db (decibels. The higher the margin the better


       the quality of the line. The default value of this object is 3."


 ::= { xdslDevRADSLSpecificIfConfigEntry 8 }





 xdslDevRADSLSpecificIfConfigTxPowerAttenuation OBJECT-TYPE


   SYNTAX INTEGER


   ACCESS read-write


   STATUS mandatory


   DESCRIPTION


     " This value corresponds to the Transmitt Power Attenuation in


       dB for the access node. This value represents the downstream


       power level in dB. Permissible values are -6, -3 and 0.


       The default value of this object is 0 dB. The power levels +3


       and +6 may be used in future."


 ::= { xdslDevRADSLSpecificIfConfigEntry 9 }





 xdslDevRADSLSpecificIfConfigSnTxPowerAttenuation OBJECT-TYPE


   SYNTAX INTEGER


   ACCESS read-write


   STATUS mandatory


   DESCRIPTION


     " This value corresponds to the Transmitt Power Attenuation in dB


       for the service node. This value represents the upstream power


       level in dB. Permissible values are -9, -6, -3 and 0. The 


       default value of this object is -6 dB."





 ::= { xdslDevRADSLSpecificIfConfigEntry 10 }





 -- The xdslDevMVLSpecificConfig group. Implementation of this group is


 -- mandatory for MVL 





 xdslDevMVLSpecificIfConfigTable OBJECT-TYPE


   SYNTAX SEQUENCE OF XdslDevMVLSpecificIfConfigEntry


   ACCESS not-accessible


   STATUS mandatory


   DESCRIPTION


     "The xdslDevMVLSpecificIfConfigTable provides config information specific 


      to a xDSL(MVL) device, or system. The table is indexed by an 


      object which corresponds to ifIndex. These ifIndex entries, 


      themselves, denote and identify specific xdsl(Mvl) interfaces on


      the board or module. "


 ::= { xdslDevMVLSpecificIfConfig 1 }





 xdslDevMVLSpecificIfConfigEntry OBJECT-TYPE


   SYNTAX XdslDevMVLSpecificIfConfigEntry


   ACCESS not-accessible


   STATUS mandatory


   DESCRIPTION


     "Describes a specific xDSL(MVL) interface entry."


   INDEX { ifIndex }


 ::= { xdslDevMVLSpecificIfConfigTable 1 }





 XdslDevMVLSpecificIfConfigEntry ::=


   SEQUENCE {


     xdslDevMVLSpecificIfConfigMaxPortSpeed 


       INTEGER,


     xdslDevMVLSpecificIfConfigOnHookTxPowerAttenuation


       INTEGER,


     xdslDevMVLSpecificIfConfigOffHookTxPowerAttenuation


       INTEGER,


     xdslDevMVLSpecificIfConfigOnHookPCVoltageDropThresholdValue


       INTEGER,


     xdslDevMVLSpecificIfConfigOnHookSNVoltageDropThresholdValue


       INTEGER,


     xdslDevMVLSpecificIfConfigMaxDownStreamPortSpeed


       INTEGER,


     xdslDevMVLSpecificIfConfigMaxUpStreamPortSpeed


       INTEGER


  }





 xdslDevMVLSpecificIfConfigMaxPortSpeed OBJECT-TYPE


   SYNTAX INTEGER 


   ACCESS read-write


   STATUS deprecated


   DESCRIPTION


     "The value of this object corresponds to the upper bound 


      port speed of the specified port. The speeds are measured 


      in kbps.


      Prior to GrandSlam 2.3, this object was used for both upstream and downstream


      port speeds. Now there are 2 new objects created for downstream and upstream


      port speeds. 


      Setting this value will also set the same value for the objects


      xdslDevMVLSpecificIfConfigMaxDownStreamPortSpeed and


      xdslDevMVLSpecificIfConfigMaxUpStreamPortSpeed."





 ::= { xdslDevMVLSpecificIfConfigEntry 1 }





 xdslDevMVLSpecificIfConfigOnHookTxPowerAttenuation OBJECT-TYPE


   SYNTAX INTEGER


   ACCESS read-write


   STATUS mandatory


   DESCRIPTION


     " This value corresponds to the On-hook Transmitt Power Attenuation 


       in dB for the access node and the service node. This value represents


       both downstream and upstream power level in dB while the phone is


       On-hook. Permissible values are -2, 1, 4, 7, 10, and +12. The


       default value of this object is 12 dB."


 ::= { xdslDevMVLSpecificIfConfigEntry 2 }





 xdslDevMVLSpecificIfConfigOffHookTxPowerAttenuation OBJECT-TYPE


   SYNTAX INTEGER


   ACCESS read-write


   STATUS mandatory


   DESCRIPTION


     " This value corresponds to the Off-hook Transmitt Power Attenuation 


       in dB for the access node and the service node. This value represents


       both downstream and upstream power level in dB while the phone is


       Off-hook. Permissible values are -11, -8, -5, -2, 1, 4, 7, 10


       and +12. The default value of this object is 12 dB. "


 ::= { xdslDevMVLSpecificIfConfigEntry 3 }





 xdslDevMVLSpecificIfConfigOnHookPCVoltageDropThresholdValue OBJECT-TYPE


   SYNTAX INTEGER


   ACCESS read-write


   STATUS mandatory


   DESCRIPTION


	"This value correspond to the portcard Voltage Drop


	 Threshold Value and valid settings are 0 and 6.


	 If the corresponding value at the endpoint is


	 set for Max (255) than only valid value for this


	 object is 0. This only applies for MVL configuration


	 If Reach configuration is used only valid value is 6


	 which is a default value."


 ::= { xdslDevMVLSpecificIfConfigEntry 4 }





 xdslDevMVLSpecificIfConfigOnHookSNVoltageDropThresholdValue OBJECT-TYPE


   SYNTAX INTEGER


   ACCESS read-write


   STATUS mandatory


   DESCRIPTION


	"This corresponds to the endpoint Voltage Drop


	Threshold Value and valid settings are 17, 34 and 255(Max).


	If Reach is used than only valid value is 34 - default."


	


 ::= { xdslDevMVLSpecificIfConfigEntry 5 }





 xdslDevMVLSpecificIfConfigMaxDownStreamPortSpeed OBJECT-TYPE


   SYNTAX INTEGER 


   ACCESS read-write


   STATUS mandatory


   DESCRIPTION


     "The value of this object corresponds to the upper bound downstream


      port speed of the specified port. The speeds are measured 


      in kbps.


      Setting the value of this object will also set the same value to the object


      xdslDevMVLSpecificIfConfigMaxPortSpeed.


      Prior to GrandSlam 2.3, the object xdslDevMVLSpecificIfConfigMaxPortSpeed 


      was used for both upstream and downstream port speeds. Now there are 


      two different objects for upstream and downstream port speeds."


      


 ::= { xdslDevMVLSpecificIfConfigEntry 6 }


      


 xdslDevMVLSpecificIfConfigMaxUpStreamPortSpeed OBJECT-TYPE


   SYNTAX INTEGER 


   ACCESS read-write


   STATUS mandatory


   DESCRIPTION


     "The value of this object corresponds to the upper bound upstream


      port speed of the specified port. The speeds are measured 


      in kbps.


      Prior to GrandSlam 2.3, the object MaxPortSpeed was used for both upstream 


      and downstream port speeds. Now there are two different objects for


      upstream and downstream port speeds."


      


 ::= { xdslDevMVLSpecificIfConfigEntry 7 }








 -- The xdslDevSDSLSpecificIfConfig group. Implementation of this group is


 -- mandatory for SDSL 





 xdslDevSDSLSpecificIfConfigTable OBJECT-TYPE


   SYNTAX SEQUENCE OF XdslDevSDSLSpecificIfConfigEntry


   ACCESS not-accessible


   STATUS mandatory


   DESCRIPTION


     "The xdslDevSDSLSpecificIfConfigTable provides configuration 


      specific to the SDSL link."


 ::= { xdslDevSDSLSpecificIfConfig 1 }





 xdslDevSDSLSpecificIfConfigEntry OBJECT-TYPE


   SYNTAX XdslDevSDSLSpecificIfConfigEntry


   ACCESS not-accessible


   STATUS mandatory


   DESCRIPTION


     "Describes a specific SDSL configuration entry."


   INDEX { ifIndex }


 ::= { xdslDevSDSLSpecificIfConfigTable 1 }





 XdslDevSDSLSpecificIfConfigEntry ::=


   SEQUENCE {


     xdslDevSDSLSpecificIfConfigFixedPortSpeed


       INTEGER,


    xdslDevSDSLSpecificIfConfigMaxPortSpeed


       INTEGER,


    xdslDevSDSLSpecificIfConfigFixedPortSpeedNx128Mode


       INTEGER,


    xdslDevSDSLSpecificIfConfigMaxPortSpeedNx128Mode


       INTEGER,


    xdslDevSDSLSpecificIfConfigMinSnrMargin


       INTEGER,


    xdslDevSDSLSpecificIfConfigTargetSnrMargin


       INTEGER


 }





 xdslDevSDSLSpecificIfConfigFixedPortSpeed OBJECT-TYPE


   SYNTAX INTEGER


   ACCESS read-write


   STATUS mandatory


   DESCRIPTION


     "The value of this object corresponds to both upstream


      and downstream speed of the specified port. All the


      speeds are in kbps. The value of this  object is used


      only when the port behaviour is fixed."


 ::= { xdslDevSDSLSpecificIfConfigEntry 1 }





 xdslDevSDSLSpecificIfConfigMaxPortSpeed OBJECT-TYPE


   SYNTAX INTEGER


   ACCESS read-write


   STATUS mandatory


   DESCRIPTION


     "The value of this object corresponds to the upper bound


      port speed of the specified port when the port behaviour


      is adaptive. The speeds are measured in kbps."


 ::= { xdslDevSDSLSpecificIfConfigEntry 2 }





 xdslDevSDSLSpecificIfConfigFixedPortSpeedNx128Mode OBJECT-TYPE


   SYNTAX INTEGER (0..2147483647)


   ACCESS read-write


   STATUS mandatory


   DESCRIPTION


     "The value of this object applies to both upstream


      and downstream speed of the specified port when the 


      line rate mode is configured as Nx128 mode. All the 


      speeds are in kbps. The value of this object is used


      only when the port behaviour is fixed and the line rate


      is Nx128 mode, and doesn't take effect in the standard mode."


 ::= { xdslDevSDSLSpecificIfConfigEntry 3 }





 xdslDevSDSLSpecificIfConfigMaxPortSpeedNx128Mode OBJECT-TYPE


   SYNTAX INTEGER (0..2147483647)


   ACCESS read-write


   STATUS mandatory


   DESCRIPTION


     "The value of this object corresponds to the upper bound


      port speed of the specified port when the port behaviour


      is adaptive and the line rate is Nx128 mode, and doesn't


      take effect in the standard mode. The speeds are measured


      in kbps."


 ::= { xdslDevSDSLSpecificIfConfigEntry 4 }





 xdslDevSDSLSpecificIfConfigMinSnrMargin OBJECT-TYPE


   SYNTAX INTEGER (0..15)


   ACCESS read-write


   STATUS mandatory


   DESCRIPTION


        "Configured Minimum acceptable Signal/Noise Margin."


 ::= { xdslDevSDSLSpecificIfConfigEntry 5 }





 xdslDevSDSLSpecificIfConfigTargetSnrMargin OBJECT-TYPE


   SYNTAX INTEGER (0..15)


   ACCESS read-write


   STATUS mandatory


   DESCRIPTION


        "Configured Target Signal/Noise Margin."


 ::= { xdslDevSDSLSpecificIfConfigEntry 6 }


 


 -- The xdslDevIDSLSpecificIfConfig group. Implementation of this group is


 -- mandatory for IDSL 





 xdslDevIDSLSpecificIfConfigTable OBJECT-TYPE


   SYNTAX SEQUENCE OF XdslDevIDSLSpecificIfConfigEntry


   ACCESS not-accessible


   STATUS mandatory


   DESCRIPTION


     "The xdslDevIDSLSpecificIfConfigTable provides configuration 


      specific to the IDSL link."


 ::= { xdslDevIDSLSpecificIfConfig 1 }





 xdslDevIDSLSpecificIfConfigEntry OBJECT-TYPE


   SYNTAX XdslDevIDSLSpecificIfConfigEntry


   ACCESS not-accessible


   STATUS mandatory


   DESCRIPTION


     "Describes a specific IDSL configuration entry."


   INDEX { ifIndex }


 ::= { xdslDevIDSLSpecificIfConfigTable 1 }





 XdslDevIDSLSpecificIfConfigEntry ::=


   SEQUENCE {


     xdslDevIDSLSpecificIfConfigPortSpeed


       INTEGER,


     xdslDevIDSLSpecificIfConfigTimingPortTransceiverMode


       INTEGER,


     xdslDevIDSLSpecificChannel


       INTEGER


 }





 xdslDevIDSLSpecificIfConfigPortSpeed OBJECT-TYPE


   SYNTAX INTEGER


   ACCESS read-write


   STATUS mandatory


   DESCRIPTION


     "The value of this object corresponds to both upstream


      and downstream speed of the specified port. All the


      speeds are in kbps. Allowed speeds are 64, 128 and 144


      kbps. The default value for this object is 128 kbps."


 ::= { xdslDevIDSLSpecificIfConfigEntry 1 }





 xdslDevIDSLSpecificIfConfigTimingPortTransceiverMode OBJECT-TYPE


   SYNTAX INTEGER {


          networkTiming (1),


          localTiming (2)


   }


   ACCESS read-write


   STATUS mandatory


   DESCRIPTION


     "The transceiver mode selected on the timing source port.


      Only one IDSL port can be set to NT mode. This timing


      will then be distributed to all other IDSL ports in the


      chassis that are set to LT.





      The selected xdslDevIDSLPrimaryTimingSourcePort provides clocking


      signals to the DSLAM when the transceiver mode is set to Network


      timing. The port selected for Network Timing mode will probably not


      used for customer data, but will receive a 2.048 Mhz Network clocking


      signal from a central office timing source and distribute this timing


      to other IDSL port cards."


 ::= { xdslDevIDSLSpecificIfConfigEntry 2 }





 xdslDevIDSLSpecificChannel	OBJECT-TYPE


   SYNTAX INTEGER {


          b1 (1),


          b2 (2),


	  noOp (3)


   }


   ACCESS read-write


   STATUS mandatory


   DESCRIPTION


	" The channel type for 64 Kbps. Default value is B1."


 ::= { xdslDevIDSLSpecificIfConfigEntry 3 }


 -- Trap definitions


 -- All traps sent from the DSL cards will have the MCC card's address 


 -- (in the NAP domain) in the ip-address field of the TRAP PDU.





-- NOTE: This trap obsoletes the xdslLinkUpDownTransitions trap of hot_xdsl.mib


xdslLinkUpDownTransitions TRAP-TYPE


   ENTERPRISE xdslIfConfigMIBTraps


   VARIABLES { ifIndex }


   DESCRIPTION


     "This trap signifies that the sending protocol


      entity recognizes that one of the xDSL communication 


      links is in a fluctuating state."


 ::= 1





END
