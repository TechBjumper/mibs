--
-- (c) 2004-2011 Avamar.  All rights reserved.
--
-- AVAMAR-MCS-MIB.txt
--
-- ORGANIZATION "EMC Corporation"
-- CONTACT-INFO "135 Technology Drive
--               Irvine, CA 92618 USA"
-- DESCRIPTION "The MIB module for EMC's Avamar MCS product"
--
-- History: 20040809 vlm Initial definition
--          20040913 evt Updated definition
--          20040915 vlm Added activity definition comments
--          20050307 evt Correct enterprise number.  Add comments of
--                       uses of fields, and noting unimplemented items
--          20060504 evt Define burmActivityTrap
--          20111118 jjb Conversion to strict SMIv1 standards
--
-- This is in sync with event_catalog.dtd
--
-- Avamar : iso.org.dod.internet.private.enterprises.avamar
--          (1.3.6.1.4.1.15597)
--
-- 15597 - avamar
--   .1 - software
--     .1 - MCS
--       .1 - event
--         .1 - eventTraps
--           .1 - eventTrap
--           .2 - testEventTrap                  # test only
--         .2 - eventData
--           .1 - eventCode                      # eventTrap data
--           .2 - eventTimestamp                 # eventTrap data
--           .3 - eventCategory                  # eventTrap data
--           .4 - eventType                      # eventTrap data
--           .5 - eventSummary                   # eventTrap data
--           .6 - eventHwSource                  # eventTrap data
--           .7 - eventSwSource                  # eventTrap data
--       .2 - burm
--         .1 - burmTraps
--           .1 - burmActivityTrap
--           .2 - schedulerStatusChangeTrap      # Not implemented
--         .2 - burmLastActivityData
--           .1 - lastActivityClient             # burmActivityTrap data
--           .2 - lastActivityDomain             # burmActivityTrap data
--           .3 - lastActivityGroup              # burmActivityTrap data
--           .4 - lastActivityPlugInName         # burmActivityTrap data
--           .5 - lastActivityType               # burmActivityTrap data
--           .6 - lastActivityDataset            # burmActivityTrap data
--           .7 - lastActivitySchedule           # burmActivityTrap data
--           .8 - lastActivityRetentionPolicy    # burmActivityTrap data
--           .9 - lastActivityBytesScanned       # burmActivityTrap data
--           .10- lastActivityBytesModifiedSent  # burmActivityTrap data
--           .11- lastActivityStatusCode         # burmActivityTrap data
--           .12- lastActivityErrorCode          # burmActivityTrap data
--           .13- lastActivityBackupLabel        # burmActivityTrap data
--           .14- lastActivityBackupNumber       # burmActivityTrap data
--         .3 - burmSchedulerData
--           .1 - schedulerStatus                # Getable
--           .2 - waitQueue                      # Not implemented
--           .3 - readyQueue                     # Not implemented
--           .4 - running                        # Not implemented
--       .3 - dpn
--         .1 - dpnTraps
--           .1 - dpnStatusChangeTrap            # Not implemented
--         .2 - dpnData
--           .1 - serverStatus                       # Getable
--           .2 - activeSessions                     # Getable
--           .3 - freeMegabytes                      # Getable
--           .4 - reservedMegabytes                  # Getable
--           .5 - utilization                        # Getable
--           .6 - protectedMegabytes                 # Getable
--           .7 - lastCheckpoint                     # Getable
--           .8 - lastValidatedCheckpoint            # Getable
--           .9 - timeSinceLastCheckpoint            # Getable
--           .10 - timeSinceLastValidatedCheckpoint  # Getable
--
-- Last event trap
-- 15597.1.1.1.2.1     : Reports the last event generated by mcs
--
-- Test event trap
-- 15597.1.1.1.2.2     : Use for testing sending traps
--
--


-- NOTE the following v1 conversions
--
-- The avamar.system object renamed to avamar.software as system is
-- a pre-defined reserved object
--
-- The avamar.system.mcs.events object renamed to event
--
-- The avamar.software.mcs.dpn.dpnData.serverStatus value unknown(0)
-- removed as a 0 value is not supported with v1
--
-- The avamar.software.mcs.dpn.dpnData.activeSessions syntax changed
-- from Gauge32 to Gauge
--
-- The avamar.software.mcs.dpn.dpnData.timeSinceLastCheckpoint syntax
-- changed from TimeTick to TimeTicks
--
-- The avamar.software.mcs.dpn.dpnData.timeSinceLastValidatedCheckpoint
-- syntax changed from TimeTick to TimeTicks
--

-- MIB validated at http://www.muonics.com/Tools/smicheck.php
-- with no errors or warnings


AVAMAR-MCS-MIB DEFINITIONS ::= BEGIN

IMPORTS
    enterprises, Gauge, TimeTicks  FROM RFC1155-SMI
    OBJECT-TYPE                    FROM RFC-1212
    TRAP-TYPE                      FROM RFC-1215
    DisplayString                  FROM RFC1213-MIB
  ;

------------------------------------------------------------------------
-- avamar enterprise-specific objects
------------------------------------------------------------------------
avamar                OBJECT IDENTIFIER ::= { enterprises 15597 }
  software              OBJECT IDENTIFIER ::= { avamar 1 }
    mcs                   OBJECT IDENTIFIER ::= { software 1 }
      event                 OBJECT IDENTIFIER ::= { mcs 1 }
        eventTraps            OBJECT IDENTIFIER ::= { event 1 }
        eventData             OBJECT IDENTIFIER ::= { event 2 }
      burm                  OBJECT IDENTIFIER ::= { mcs 2 }
        burmTraps             OBJECT IDENTIFIER ::= { burm 1 }
        burmLastActivityData  OBJECT IDENTIFIER ::= { burm 2 }
        burmSchedulerData     OBJECT IDENTIFIER ::= { burm 3 }
      dpn                   OBJECT IDENTIFIER ::= { mcs 3 }
        dpnTraps              OBJECT IDENTIFIER ::= { dpn 1 }
        dpnData               OBJECT IDENTIFIER ::= { dpn 2 }

------------------------------------------------------------------------
-- avamar.software.mcs.events.eventTraps
------------------------------------------------------------------------
eventTrap TRAP-TYPE
    ENTERPRISE eventTraps
    VARIABLES { eventCode,
                eventTimestamp,
                eventCategory,
                eventType,
                eventSummary,
                eventHwSource,
                eventSwSource
              }
    DESCRIPTION "The last event reported by the mcs."
  ::= 1

testEventTrap TRAP-TYPE
    ENTERPRISE eventTraps
    VARIABLES { eventCode }
    DESCRIPTION "Test trap for verifying profile."
  ::= 2

------------------------------------------------------------------------
-- avamar.software.mcs.events.eventData
------------------------------------------------------------------------
eventCode OBJECT-TYPE
    SYNTAX INTEGER
    ACCESS read-only
    STATUS mandatory
    DESCRIPTION "Unique code identifying the specific activity,
                 condition, or status."
  ::= { eventData 1 }

eventTimestamp OBJECT-TYPE
    SYNTAX DisplayString (SIZE (0..100))
    ACCESS read-only
    STATUS mandatory
    DESCRIPTION "Date event was reported"
  ::= { eventData 2 }

eventCategory OBJECT-TYPE
    SYNTAX DisplayString (SIZE (0..25))
    ACCESS read-only
    STATUS mandatory
    DESCRIPTION "Category of event (SYSTEM, APPLICATION, USER,
                 SECURITY)"
  ::= { eventData 3 }

eventType OBJECT-TYPE
    SYNTAX DisplayString (SIZE (0..25))
    ACCESS read-only
    STATUS mandatory
    DESCRIPTION "Type of event (INTERNAL, ERROR, WARNING, INFORMATION,
                 DEBUG"
  ::= { eventData 4 }

eventSummary OBJECT-TYPE
    SYNTAX DisplayString (SIZE (0..256))
    ACCESS read-only
    STATUS mandatory
    DESCRIPTION "One line summary description of event reported"
  ::= { eventData 5 }

eventHwSource OBJECT-TYPE
    SYNTAX DisplayString (SIZE (0..100))
    ACCESS read-only
    STATUS mandatory
    DESCRIPTION "System node that reported the event"
  ::= { eventData 6 }

eventSwSource OBJECT-TYPE
    SYNTAX DisplayString (SIZE (0..100))
    ACCESS read-only
    STATUS mandatory
    DESCRIPTION "System or application module that reported the event"
  ::= { eventData 7 }

------------------------------------------------------------------------
-- avamar.software.mcs.burm.burmTraps
------------------------------------------------------------------------
burmActivityTrap TRAP-TYPE
    ENTERPRISE burmTraps
    VARIABLES { lastActivityClient,
                lastActivityDomain,
                lastActivityGroup,
                lastActivityPlugInName,
                lastActivityType,
                lastActivityDataset,
                lastActivitySchedule,
                lastActivityRetentionPolicy,
                lastActivityBytesScanned,
                lastActivityBytesModifiedSent,
                lastActivityStatusCode,
                lastActivityErrorCode,
                lastActivityBackupLabel,
                lastActivityBackupNumber
              }
    DESCRIPTION "The last activity reported by the mcs."
  ::= 1

------------------------------------------------------------------------
-- avamar.software.mcs.burm.burmLastActivityData
------------------------------------------------------------------------
lastActivityClient OBJECT-TYPE
    SYNTAX DisplayString (SIZE (0..256))
    ACCESS read-only
    STATUS mandatory
    DESCRIPTION "The client name."
  ::= { burmLastActivityData 1 }

lastActivityDomain OBJECT-TYPE
    SYNTAX DisplayString (SIZE (0..256))
    ACCESS read-only
    STATUS mandatory
    DESCRIPTION "The domain of the client is in."
  ::= { burmLastActivityData 2 }

lastActivityGroup OBJECT-TYPE
    SYNTAX DisplayString (SIZE (0..256))
    ACCESS read-only
    STATUS mandatory
    DESCRIPTION "The group that this client belongs to."
  ::= { burmLastActivityData 3 }

lastActivityPlugInName OBJECT-TYPE
    SYNTAX DisplayString (SIZE (0..32))
    ACCESS read-only
    STATUS mandatory
    DESCRIPTION "The plug-in this client is using for this activity."
  ::= { burmLastActivityData 4 }

lastActivityType OBJECT-TYPE
    SYNTAX DisplayString (SIZE (0..256))
    ACCESS read-only
    STATUS mandatory
    DESCRIPTION "The activity type."
  ::= { burmLastActivityData 5 }

lastActivityDataset OBJECT-TYPE
    SYNTAX DisplayString (SIZE (0..256))
    ACCESS read-only
    STATUS mandatory
    DESCRIPTION "The dataset this client is using for this activity."
  ::= { burmLastActivityData 6 }

lastActivitySchedule OBJECT-TYPE
    SYNTAX DisplayString (SIZE (0..256))
    ACCESS read-only
    STATUS mandatory
    DESCRIPTION "The schedule that initiated this activity."
  ::= { burmLastActivityData 7 }

lastActivityRetentionPolicy OBJECT-TYPE
    SYNTAX DisplayString (SIZE (0..256))
    ACCESS read-only
    STATUS mandatory
    DESCRIPTION "The retention policy for the backup resulting from this
                 activity."
  ::= { burmLastActivityData 8 }

lastActivityBytesScanned OBJECT-TYPE
    SYNTAX DisplayString (SIZE (0..25))
    ACCESS read-only
    STATUS mandatory
    DESCRIPTION "The number of bytes scanned during this activity."
  ::= { burmLastActivityData 9 }

lastActivityBytesModifiedSent OBJECT-TYPE
    SYNTAX DisplayString (SIZE (0..25))
    ACCESS read-only
    STATUS mandatory
    DESCRIPTION "The number of modified bytes sent during a backup."
  ::= { burmLastActivityData 10 }

lastActivityStatusCode OBJECT-TYPE
    SYNTAX INTEGER
    ACCESS read-only
    STATUS mandatory
    DESCRIPTION "The activity status event code."
  ::= { burmLastActivityData 11 }

lastActivityErrorCode OBJECT-TYPE
    SYNTAX INTEGER
    ACCESS read-only
    STATUS mandatory
    DESCRIPTION "A failure event code if this activity failed."
  ::= { burmLastActivityData 12 }

lastActivityBackupLabel OBJECT-TYPE
    SYNTAX DisplayString (SIZE (0..256))
    ACCESS read-only
    STATUS mandatory
    DESCRIPTION "The backup label for this activity."
  ::= { burmLastActivityData 13 }

lastActivityBackupNumber OBJECT-TYPE
    SYNTAX INTEGER
    ACCESS read-only
    STATUS mandatory
    DESCRIPTION "The backup number for this activity."
  ::= { burmLastActivityData 14 }

------------------------------------------------------------------------
-- avamar.software.mcs.burm.burmSchedulerData
------------------------------------------------------------------------
schedulerStatus OBJECT-TYPE
    SYNTAX INTEGER { suspended(1), running(2) }
    ACCESS read-only
    STATUS mandatory
    DESCRIPTION "Status of scheduler, either suspended or running."
  ::= { burmSchedulerData 1 }

------------------------------------------------------------------------
-- avamar.software.mcs.dpn.dpnTraps  # Not implemented
------------------------------------------------------------------------

------------------------------------------------------------------------
-- avamar.software.mcs.dpn.dpnData
------------------------------------------------------------------------
serverStatus OBJECT-TYPE
    SYNTAX INTEGER { unsupported(1),
                     inactive(2),
                     offline(3),
                     suspended(4),
                     adminreadonly(5),
                     adminonly(6),
                     readonly(7),
                     synchronizing(8),
                     admin(9),
                     fullaccess(10),
                     degraded(11),
                     ddrinactive(12)
                   }

    ACCESS read-only
    STATUS mandatory
    DESCRIPTION "Status of Avamar Server"
  ::= { dpnData 1 }

activeSessions OBJECT-TYPE
    SYNTAX Gauge
    ACCESS read-only
    STATUS mandatory
    DESCRIPTION "Number of active avtar sessions"
  ::= { dpnData 2 }

freeMegabytes OBJECT-TYPE
    SYNTAX INTEGER
    ACCESS read-only
    STATUS mandatory
    DESCRIPTION "Number of megabytes free on the Avamar Server"
  ::= { dpnData 3 }

reservedMegabytes OBJECT-TYPE
    SYNTAX INTEGER
    ACCESS read-only
    STATUS mandatory
    DESCRIPTION "Number of megabytes reserved for data storage on the
                 Avamar Server"
  ::= { dpnData 4 }

utilization OBJECT-TYPE
    SYNTAX INTEGER (0..1000)
    ACCESS read-only
    STATUS mandatory
    DESCRIPTION "Percentage of storage used on the Avamar Server in
                 tenths of a percent"
  ::= { dpnData 5 }

protectedMegabytes OBJECT-TYPE
    SYNTAX INTEGER
    ACCESS read-only
    STATUS mandatory
    DESCRIPTION "Number of megabytes of protected data stored on the
                 Avamar Server"
  ::= { dpnData 6 }

lastCheckpoint OBJECT-TYPE
    SYNTAX DisplayString (SIZE (0..100))
    ACCESS read-only
    STATUS mandatory
    DESCRIPTION "The date & time the last checkpoint was taken"
  ::= { dpnData 7 }

lastValidatedCheckpoint OBJECT-TYPE
    SYNTAX DisplayString (SIZE (0..100))
    ACCESS read-only
    STATUS mandatory
    DESCRIPTION "The date & time of the last checkpoint that has been
                 validated"
  ::= { dpnData 8 }

timeSinceLastCheckpoint OBJECT-TYPE
    SYNTAX TimeTicks
    ACCESS read-only
    STATUS mandatory
    DESCRIPTION "The time since the last checkpoint was taken"
  ::= { dpnData 9 }

timeSinceLastValidatedCheckpoint OBJECT-TYPE
    SYNTAX TimeTicks
    ACCESS read-only
    STATUS mandatory
    DESCRIPTION "The time since the last validated checkpoint was taken"
  ::= { dpnData 10 }


------------------------------------------------------------------------
END
