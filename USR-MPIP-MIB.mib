USR-MPIP-MIB DEFINITIONS ::= BEGIN
          IMPORTS
                OBJECT-TYPE, MODULE-IDENTITY,
                IpAddress, Integer32
                    FROM SNMPv2-SMI
                RowStatus
                    FROM SNMPv2-TC
                DisplayString, common, UsrConfigStatus
                    FROM USR-DEFINITIONS-MIB;
usrMPIP MODULE-IDENTITY
        LAST-UPDATED "200205051610Z"
        ORGANIZATION "CommWorks Corporation, a 3Com Company"
        CONTACT-INFO "Customer Support"
        DESCRIPTION
                "The commWorks enterprise defined MIB objects
                  for MPIP."
--      REVISION "200105051610Z"
--      DESCRIPTION "Converted to SNMPv2"
        ::= { common 54 }
          usrMPIPBase      OBJECT IDENTIFIER ::= { usrMPIP 1 }
--
-- The MPIP Base Group.
--
usrMPIPBaseCfgFileName OBJECT-TYPE
    SYNTAX       DisplayString
    MAX-ACCESS   read-only
    STATUS       current
    DESCRIPTION
            "The name of a ConfigFile to read/write
            permanent database records. If the value of this
            object is an empty string, then the PPP process
            uses the default name `@file://MPIPProcess.cfg'."
::= { usrMPIPBase 1 }
usrMPIPBaseCFMSaveStatus OBJECT-TYPE
    SYNTAX  UsrConfigStatus
    MAX-ACCESS  read-write
    STATUS      current
    DESCRIPTION
            "Setting the value of this object to `save'
            causes the values of the MPIP Base Group
            entries to be written out to the current MPIP
            config file. While the new config file is being
            written, the MPIP process will set the value
            of this flag set to `saving''. Any attempts to set
            the value while it is  not `normal' (i.e. the file
            is currently being written to the config file)
            while result in a badValue error being returned.
            Setting the value to `normal' will result in no
            action."
::= { usrMPIPBase 2 }
usrMPIPServerStatus OBJECT-TYPE
    SYNTAX  INTEGER {
                    on(1),
                    off(0)
                    }
    MAX-ACCESS   read-write
    STATUS       current
    DESCRIPTION
            "Indicates whether MPIP server is turned off or on."
    DEFVAL { 0 }
    --CONFIGURABLE
::= { usrMPIPBase 3 }
usrMPIPClientStatus OBJECT-TYPE
    SYNTAX  INTEGER {
                    turned-on(1),
                    turned-off(0)
                    }
    MAX-ACCESS   read-write
    STATUS       current
    DESCRIPTION
            "Indicates whether MPIP Client is turned off or on."
    DEFVAL { 0 }
    --CONFIGURABLE
::= { usrMPIPBase 4 }
usrMPIPUDPPort OBJECT-TYPE
    SYNTAX        Integer32
    MAX-ACCESS    read-write
    STATUS        current
    DESCRIPTION
            "Indicates the UDP Port used by MPIP process\n"
    DEFVAL { 5912 }
    --CONFIGURABLE
::= { usrMPIPBase 5 }
usrMPIPGlobalSharedSecret OBJECT-TYPE
    SYNTAX   OCTET STRING (SIZE(16))
    MAX-ACCESS   read-write
    STATUS       current
    DESCRIPTION
            "Indicates the shared secret for auto-configuration.
             Reading this from SNMP returns NULL."
    --CONFIGURABLE
::= { usrMPIPBase 6 }
--
-- The Client Entry Table.
--
-- The following object reflect the Entries in the
-- MPIP Client Entry Table
--   usrMPIPClientIpaddr
--   usrMPIPSharedSecret
usrMPIPClientEntryTable   OBJECT-TYPE
     SYNTAX    SEQUENCE OF UsrMPIPClientEntry
     MAX-ACCESS    not-accessible
     STATUS        current
     DESCRIPTION
     "Table containing the MPIP client IP addresses
       and shared secrets."
::= { usrMPIPBase 7 }
    usrMPIPClientEntry   OBJECT-TYPE
        SYNTAX    UsrMPIPClientEntry
        MAX-ACCESS    not-accessible
        STATUS        current
        DESCRIPTION
               "Each entry in the Client Entry Table."
        INDEX     { usrMPIPClientIpaddr }
    ::= { usrMPIPClientEntryTable 1 }
          UsrMPIPClientEntry ::= SEQUENCE {
                        usrMPIPClientIpaddr         IpAddress,
                        usrMPIPClientSharedSecret   OCTET STRING,
                        usrMpipcStatus              RowStatus,
                        usrMPIPClientType           INTEGER,
                        usrMPIPClientEntryType      OCTET STRING
                        }
usrMPIPClientIpaddr OBJECT-TYPE
     SYNTAX    IpAddress
     MAX-ACCESS     not-accessible 
     STATUS         current
     DESCRIPTION
               "The unique identifier of the MPIP Client."
::= { usrMPIPClientEntry 1 }
usrMPIPClientSharedSecret OBJECT-TYPE
     SYNTAX  OCTET STRING (SIZE(16))
     MAX-ACCESS    read-write
     STATUS        current
     DESCRIPTION
               "The Shared secret between MPIP Client and Server.
                Reading this from SNMP returns NULL."
     --CONFIGURABLE
::= { usrMPIPClientEntry 2 }
usrMpipcStatus OBJECT-TYPE
     SYNTAX     RowStatus
     MAX-ACCESS read-write
     STATUS     current
     DESCRIPTION
               "The status of this row of the MPIP 
                Client Table." 
     --CONFIGURABLE
::= { usrMPIPClientEntry 3 }
usrMPIPClientType    OBJECT-TYPE
     SYNTAX        INTEGER {
                            hiper(0),
                            netserver(1)
                            }
     MAX-ACCESS        read-write
     STATUS            current
     DESCRIPTION
              "Tells whether the client is a HiperARC or Netserver"
     --CONFIGURABLE
::= { usrMPIPClientEntry 4 }
usrMPIPClientEntryType OBJECT-TYPE
     SYNTAX  OCTET STRING (SIZE(0..10))
     MAX-ACCESS    read-only
     STATUS        current
     DESCRIPTION
               "Is the client added dynamically or statically?"
::= { usrMPIPClientEntry 5 }
--
-- The Server Entry Table.
--
--  The following object reflect the Entries in the
--  MPIP Server Entry Table
--  usrMPIPServerIpaddr
--  usrMPIPServerPortNum
--  usrMPIPServerSharedSecret
--  usrMPIPCurrentState
--  usrMPIPSendSequenceNum
--  usrMPIPExpectedSequenceNum 
--  usrMPIPLastExpectedSequenceNum
--  usrMPIPSentTime
--  usrMPIPIdentification
--  usrMPIPRetransmit
usrMPIPServerEntryTable   OBJECT-TYPE
     SYNTAX    SEQUENCE OF UsrMPIPServerEntry
     MAX-ACCESS    not-accessible
     STATUS        current
     DESCRIPTION
               "Table containing the MPIP server IP addresse,
                 UDP port number, shared secret, current state,
                 send sequence number, expected sequence number,
                 last expected sequence number, MPIP sent time,
                 MPIP ID and MPIP retransmit."
     ::= { usrMPIPBase 8 }
    usrMPIPServerEntry   OBJECT-TYPE
         SYNTAX    UsrMPIPServerEntry
         MAX-ACCESS    not-accessible
         STATUS        current
         DESCRIPTION
               "Each entry in the Server Entry Table."
         INDEX     { usrMPIPServerIpaddr }
    ::= { usrMPIPServerEntryTable 1 }
UsrMPIPServerEntry ::= SEQUENCE {
                usrMPIPServerIpaddr         IpAddress,
                usrMPIPServerPortNum        Integer32,
                usrMPIPServerSharedSecret   OCTET STRING,
                usrMPIPServerPreference     Integer32,
                usrMpipsStatus              RowStatus,
                usrMPIPServerEntryType      OCTET STRING
           }
usrMPIPServerIpaddr OBJECT-TYPE
     SYNTAX    IpAddress
     MAX-ACCESS    not-accessible
     STATUS         current
     DESCRIPTION
               "The unique identifier of the MPIP Server."
::= { usrMPIPServerEntry 1 }
usrMPIPServerPortNum OBJECT-TYPE
     SYNTAX        Integer32
     MAX-ACCESS    read-write
     STATUS        current
     DESCRIPTION
               "The Server UDP Port Number."
     --CONFIGURABLE
::= { usrMPIPServerEntry 2 }
usrMPIPServerSharedSecret OBJECT-TYPE
    SYNTAX  OCTET STRING (SIZE(16))
    MAX-ACCESS    read-write
    STATUS        current
    DESCRIPTION
              "The Server's Shared secret with Client."
    --CONFIGURABLE
::= { usrMPIPServerEntry 3 }
usrMPIPServerPreference OBJECT-TYPE
    SYNTAX        Integer32
    MAX-ACCESS    read-write
    STATUS        current
    DESCRIPTION
              "The Server Priority."
    --CONFIGURABLE
::= { usrMPIPServerEntry 4 }
usrMpipsStatus OBJECT-TYPE
    SYNTAX    RowStatus
    MAX-ACCESS    read-write
    STATUS        current
    DESCRIPTION
              "Row status."
    --CONFIGURABLE
::= { usrMPIPServerEntry 5 }
usrMPIPServerEntryType OBJECT-TYPE
     SYNTAX  OCTET STRING (SIZE(0..10))
     MAX-ACCESS    read-only
     STATUS        current
     DESCRIPTION
               "Is the server added dynamically or statically?"
::= { usrMPIPServerEntry 6 }
--
-- The Bundle Table 
--
--  The following object reflect the Entries in the
--  MPIP Bundle Index
--  MPIP Bundle Table 
--  usrMPIPBundleEdoType
--  usrMPIPBundleEdoValue
--  usrMPIPBundleUsername
--  usrMPIPBundleCount
usrMPIPBundleTable   OBJECT-TYPE
     SYNTAX    SEQUENCE OF UsrMPIPBundleEntry
     MAX-ACCESS    not-accessible
     STATUS        current
     DESCRIPTION
               "Table containing the MPIP Bundle & links."
::= { usrMPIPBase 9 }
    usrMPIPBundleEntry   OBJECT-TYPE
         SYNTAX    UsrMPIPBundleEntry
         MAX-ACCESS    not-accessible
         STATUS        current
         DESCRIPTION
               "Each entry in the Bundle Table." 
         INDEX     { usrMPIPBundleIndex }
    ::= { usrMPIPBundleTable 1 }
    UsrMPIPBundleEntry ::= SEQUENCE {
                usrMPIPBundleIndex        Integer32,
                usrMPIPBundleUsername     OCTET STRING,
                usrMPIPBundleEdoType      Integer32,
                usrMPIPBundleEdoValue     OCTET STRING,
                usrMPIPBundleOwner        IpAddress,
                usrMPIPNumOfLinks         Integer32
           }
usrMPIPBundleIndex OBJECT-TYPE
    SYNTAX        Integer32
    MAX-ACCESS    read-write 
    STATUS        current
    DESCRIPTION
              "The bundle index number "
::= { usrMPIPBundleEntry 1 }
usrMPIPBundleUsername OBJECT-TYPE
    SYNTAX    OCTET STRING (SIZE(64))
    MAX-ACCESS    read-write 
    STATUS        current
    DESCRIPTION
              "User name." 
::= { usrMPIPBundleEntry 2 }
usrMPIPBundleEdoType OBJECT-TYPE
    SYNTAX    Integer32
    MAX-ACCESS    read-write 
    STATUS        current
    DESCRIPTION
              "The EDO type." 
    --CONFIGURABLE
::= { usrMPIPBundleEntry 3 }
usrMPIPBundleEdoValue OBJECT-TYPE
    SYNTAX    OCTET STRING (SIZE(20))
    MAX-ACCESS    read-write 
    STATUS        current
    DESCRIPTION
              "The EDO value." 
    --CONFIGURABLE
::= { usrMPIPBundleEntry 4 }
usrMPIPBundleOwner OBJECT-TYPE
    SYNTAX    IpAddress 
    MAX-ACCESS    read-write
    STATUS        current
    DESCRIPTION
              "Bundle Owner."
::= { usrMPIPBundleEntry 5 }
usrMPIPNumOfLinks OBJECT-TYPE
    SYNTAX        Integer32
    MAX-ACCESS    read-write
    STATUS        current
    DESCRIPTION
              "The number of links per bundle." 
    --CONFIGURABLE
::= { usrMPIPBundleEntry 6 }
--
-- The Link Table
--
--  The following object reflect the Entries in the
--  MPIP Link Table
--  usrMPIPLinkOwner
--  usrMPIPBundleOwner
--  usrMPIPLinkIdentifier
--  usrMPIPLinkBundleUsername
--  usrMPIPLinkStatus
usrMPIPLinkTable   OBJECT-TYPE
     SYNTAX    SEQUENCE OF UsrMPIPLinkEntry
     MAX-ACCESS    not-accessible
     STATUS        current
     DESCRIPTION
               "Table containing the MPIP Bundle & links."
::= { usrMPIPBase 10 }
    usrMPIPLinkEntry   OBJECT-TYPE
         SYNTAX    UsrMPIPLinkEntry
         MAX-ACCESS    not-accessible
         STATUS        current
         DESCRIPTION 
               "Each entry in the Bundle Table."
         INDEX     { usrMPIPBundleUsername }
    ::= { usrMPIPLinkTable 1 }
          UsrMPIPLinkEntry ::= SEQUENCE {
                    usrMPIPLinkNum              Integer32,
                    usrMPIPLinkBundleOwner      IpAddress, 
                    usrMPIPLinkOwner            IpAddress, 
                    usrMPIPLinkIdentifier       Integer32,
                    usrMPIPLinkBundleUsername   OCTET STRING,
                    usrMpipLinkStatus           RowStatus
           }
usrMPIPLinkNum OBJECT-TYPE
    SYNTAX        Integer32
    MAX-ACCESS    read-write
    STATUS        current
    DESCRIPTION
              "Link Identifier."
::= { usrMPIPLinkEntry 1 }
usrMPIPLinkBundleOwner OBJECT-TYPE
    SYNTAX    IpAddress 
    MAX-ACCESS    read-write
    STATUS        current
    DESCRIPTION
              "Bundle Owner."
::= { usrMPIPLinkEntry 2 }
usrMPIPLinkOwner OBJECT-TYPE
    SYNTAX    IpAddress 
    MAX-ACCESS    read-write
    STATUS        current
    DESCRIPTION
              "Link Owner."
    --CONFIGURABLE
::= { usrMPIPLinkEntry 3 }
usrMPIPLinkIdentifier OBJECT-TYPE
    SYNTAX        Integer32
    MAX-ACCESS    read-write
    STATUS        current
    DESCRIPTION
              "Link Identifier."
    --CONFIGURABLE
::= { usrMPIPLinkEntry 4 }  
usrMPIPLinkBundleUsername OBJECT-TYPE
    SYNTAX    OCTET STRING (SIZE(64))
    MAX-ACCESS    read-write
    STATUS        current
    DESCRIPTION
              "The EDO type."
    --CONFIGURABLE
::= { usrMPIPLinkEntry 5 }
usrMpipLinkStatus OBJECT-TYPE
    SYNTAX      RowStatus
    MAX-ACCESS  read-write
    STATUS      current
    DESCRIPTION
              "The status of this row of the Link Table."
    --CONFIGURABLE
::= { usrMPIPLinkEntry 6 }
--
--
usrMPIPLocalLinkTable   OBJECT-TYPE
     SYNTAX    SEQUENCE OF UsrMPIPLocalLinkEntry
     MAX-ACCESS    not-accessible
     STATUS        current
     DESCRIPTION
               "Table containing the MPIP local links."
     ::= { usrMPIPBase 11 }
    usrMPIPLocalLinkEntry   OBJECT-TYPE
         SYNTAX    UsrMPIPLocalLinkEntry
         MAX-ACCESS    not-accessible
         STATUS        current
         DESCRIPTION 
               "Each entry in the Bundle Table."
         INDEX     { usrMPIPLocalLinkUsername }
    ::= { usrMPIPLocalLinkTable 1 }
        UsrMPIPLocalLinkEntry ::= SEQUENCE {
                  usrMPIPLocalLinkCount         Integer32,
                  usrMPIPLocalLinkBundleOwner   IpAddress, 
                  usrMPIPLocalLinkUsername      OCTET STRING
           }
usrMPIPLocalLinkCount OBJECT-TYPE
    SYNTAX        Integer32
    MAX-ACCESS    read-only
    STATUS        current
    DESCRIPTION
            "Link Count."
    --CONFIGURABLE
::= { usrMPIPLocalLinkEntry 1 }  
usrMPIPLocalLinkBundleOwner OBJECT-TYPE
    SYNTAX    IpAddress 
    MAX-ACCESS    read-only
    STATUS        current
    DESCRIPTION
              "Bundle Owner."
::= { usrMPIPLocalLinkEntry 2 }
usrMPIPLocalLinkUsername OBJECT-TYPE
    SYNTAX    OCTET STRING (SIZE(64))
    MAX-ACCESS    read-only
    STATUS        current
    DESCRIPTION
              "The user name."
    --CONFIGURABLE
::= { usrMPIPLocalLinkEntry 3 }
usrMPIPACEStatus OBJECT-TYPE
    SYNTAX  INTEGER {
                     on(1),
                     off(0)
                    }
    MAX-ACCESS   read-write
    STATUS       current
    DESCRIPTION
            "Indicates whether MPIP ACE_AUTH is turned off or on."
    DEFVAL { 0 }
    --CONFIGURABLE
::= { usrMPIPBase 12 }
END     -- End of USR-MPIP-MIB DEFINITIONS
