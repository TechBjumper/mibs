-- file automatically created


TELDAT-TRAP-TTTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tttpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TTTP event subsystem."
    REVISION "201401200930Z"
    DESCRIPTION "Initial implementation"
        ::= { telEventTraps 175 }


tttpEventsGroup	OBJECT IDENTIFIER	::= { tttpTrapsMIB 1 }

tttpNotifications	OBJECT IDENTIFIER	::= { tttpTrapsMIB 2 }
tttpNotificationsPrefix	OBJECT IDENTIFIER	::= { tttpNotifications 0 }

tttpEventObjects1 OBJECT-IDENTITY
    STATUS current
    DESCRIPTION
        "Event TTTP.1
        Connection was established to an Accounting Server."
    ::= { tttpEventsGroup 1 }

tttp1-ip-address OBJECT-TYPE
    SYNTAX IpAddress
    MAX-ACCESS accessible-for-notify
    STATUS current
    DESCRIPTION
        "Parameter 'ip-address' in event TTTP.1"
    ::= { tttpEventObjects1 1 }

tttp1-port OBJECT-TYPE
    SYNTAX Integer32
    MAX-ACCESS accessible-for-notify
    STATUS current
    DESCRIPTION
        "Parameter 'port' in event TTTP.1"
    ::= { tttpEventObjects1 2 }

tttpEventObjects2 OBJECT-IDENTITY
    STATUS current
    DESCRIPTION
        "Event TTTP.2
        Connection attempt was failed to an Accounting Server."
    ::= { tttpEventsGroup 2 }

tttp2-cause OBJECT-TYPE
    SYNTAX DisplayString
    MAX-ACCESS accessible-for-notify
    STATUS current
    DESCRIPTION
        "Parameter 'cause' in event TTTP.2"
    ::= { tttpEventObjects2 1 }

tttp2-ip-address OBJECT-TYPE
    SYNTAX IpAddress
    MAX-ACCESS accessible-for-notify
    STATUS current
    DESCRIPTION
        "Parameter 'ip-address' in event TTTP.2"
    ::= { tttpEventObjects2 2 }

tttp2-port OBJECT-TYPE
    SYNTAX Integer32
    MAX-ACCESS accessible-for-notify
    STATUS current
    DESCRIPTION
        "Parameter 'port' in event TTTP.2"
    ::= { tttpEventObjects2 3 }

tttpEventObjects3 OBJECT-IDENTITY
    STATUS current
    DESCRIPTION
        "Event TTTP.3
        Connection attempt to an Accounting Server timeout."
    ::= { tttpEventsGroup 3 }

tttp3-ip-address OBJECT-TYPE
    SYNTAX IpAddress
    MAX-ACCESS accessible-for-notify
    STATUS current
    DESCRIPTION
        "Parameter 'ip-address' in event TTTP.3"
    ::= { tttpEventObjects3 1 }

tttp3-port OBJECT-TYPE
    SYNTAX Integer32
    MAX-ACCESS accessible-for-notify
    STATUS current
    DESCRIPTION
        "Parameter 'port' in event TTTP.3"
    ::= { tttpEventObjects3 2 }

tttpEventObjects4 OBJECT-IDENTITY
    STATUS current
    DESCRIPTION
        "Event TTTP.4
        TTTP session drop to an Accounting Server."
    ::= { tttpEventsGroup 4 }

tttp4-ip-address OBJECT-TYPE
    SYNTAX IpAddress
    MAX-ACCESS accessible-for-notify
    STATUS current
    DESCRIPTION
        "Parameter 'ip-address' in event TTTP.4"
    ::= { tttpEventObjects4 1 }

tttp4-port OBJECT-TYPE
    SYNTAX Integer32
    MAX-ACCESS accessible-for-notify
    STATUS current
    DESCRIPTION
        "Parameter 'port' in event TTTP.4"
    ::= { tttpEventObjects4 2 }

tttpEventObjects5 OBJECT-IDENTITY
    STATUS current
    DESCRIPTION
        "Event TTTP.5
        A Trasacctin packet was send to an Accounting Server."
    ::= { tttpEventsGroup 5 }

tttp5-ip-address OBJECT-TYPE
    SYNTAX IpAddress
    MAX-ACCESS accessible-for-notify
    STATUS current
    DESCRIPTION
        "Parameter 'ip-address' in event TTTP.5"
    ::= { tttpEventObjects5 1 }

tttp5-port OBJECT-TYPE
    SYNTAX Integer32
    MAX-ACCESS accessible-for-notify
    STATUS current
    DESCRIPTION
        "Parameter 'port' in event TTTP.5"
    ::= { tttpEventObjects5 2 }

tttp5-secuence OBJECT-TYPE
    SYNTAX Integer32
    MAX-ACCESS accessible-for-notify
    STATUS current
    DESCRIPTION
        "Parameter 'secuence' in event TTTP.5"
    ::= { tttpEventObjects5 3 }

tttpEventObjects6 OBJECT-IDENTITY
    STATUS current
    DESCRIPTION
        "Event TTTP.6
        Data was received from an Accounting Server."
    ::= { tttpEventsGroup 6 }

tttp6-ip-address OBJECT-TYPE
    SYNTAX IpAddress
    MAX-ACCESS accessible-for-notify
    STATUS current
    DESCRIPTION
        "Parameter 'ip-address' in event TTTP.6"
    ::= { tttpEventObjects6 1 }

tttp6-port OBJECT-TYPE
    SYNTAX Integer32
    MAX-ACCESS accessible-for-notify
    STATUS current
    DESCRIPTION
        "Parameter 'port' in event TTTP.6"
    ::= { tttpEventObjects6 2 }

tttp6-length OBJECT-TYPE
    SYNTAX Integer32
    MAX-ACCESS accessible-for-notify
    STATUS current
    DESCRIPTION
        "Parameter 'length' in event TTTP.6"
    ::= { tttpEventObjects6 3 }

tttpEventObjects7 OBJECT-IDENTITY
    STATUS current
    DESCRIPTION
        "Event TTTP.7
        An ACK packet was received from an Accounting Server."
    ::= { tttpEventsGroup 7 }

tttp7-ip-address OBJECT-TYPE
    SYNTAX IpAddress
    MAX-ACCESS accessible-for-notify
    STATUS current
    DESCRIPTION
        "Parameter 'ip-address' in event TTTP.7"
    ::= { tttpEventObjects7 1 }

tttp7-port OBJECT-TYPE
    SYNTAX Integer32
    MAX-ACCESS accessible-for-notify
    STATUS current
    DESCRIPTION
        "Parameter 'port' in event TTTP.7"
    ::= { tttpEventObjects7 2 }

tttp7-secuence OBJECT-TYPE
    SYNTAX Integer32
    MAX-ACCESS accessible-for-notify
    STATUS current
    DESCRIPTION
        "Parameter 'secuence' in event TTTP.7"
    ::= { tttpEventObjects7 3 }

tttpEventObjects8 OBJECT-IDENTITY
    STATUS current
    DESCRIPTION
        "Event TTTP.8
        Connection attempt was make to an Accounting Server."
    ::= { tttpEventsGroup 8 }

tttp8-ip-address OBJECT-TYPE
    SYNTAX IpAddress
    MAX-ACCESS accessible-for-notify
    STATUS current
    DESCRIPTION
        "Parameter 'ip-address' in event TTTP.8"
    ::= { tttpEventObjects8 1 }

tttp8-port OBJECT-TYPE
    SYNTAX Integer32
    MAX-ACCESS accessible-for-notify
    STATUS current
    DESCRIPTION
        "Parameter 'port' in event TTTP.8"
    ::= { tttpEventObjects8 2 }

tttpEventObjects9 OBJECT-IDENTITY
    STATUS current
    DESCRIPTION
        "Event TTTP.9
        Wrong ACK packet was receiver from an Accounting Server."
    ::= { tttpEventsGroup 9 }

tttp9-cause OBJECT-TYPE
    SYNTAX DisplayString
    MAX-ACCESS accessible-for-notify
    STATUS current
    DESCRIPTION
        "Parameter 'cause' in event TTTP.9"
    ::= { tttpEventObjects9 1 }

tttp9-ip-address OBJECT-TYPE
    SYNTAX IpAddress
    MAX-ACCESS accessible-for-notify
    STATUS current
    DESCRIPTION
        "Parameter 'ip-address' in event TTTP.9"
    ::= { tttpEventObjects9 2 }

tttp9-port OBJECT-TYPE
    SYNTAX Integer32
    MAX-ACCESS accessible-for-notify
    STATUS current
    DESCRIPTION
        "Parameter 'port' in event TTTP.9"
    ::= { tttpEventObjects9 3 }

tttpEventObjects10 OBJECT-IDENTITY
    STATUS current
    DESCRIPTION
        "Event TTTP.10
        Internal transaction secuence manipulation error."
    ::= { tttpEventsGroup 10 }

tttp10-secuence OBJECT-TYPE
    SYNTAX Integer32
    MAX-ACCESS accessible-for-notify
    STATUS current
    DESCRIPTION
        "Parameter 'secuence' in event TTTP.10"
    ::= { tttpEventObjects10 1 }

tttp10-ip-address OBJECT-TYPE
    SYNTAX IpAddress
    MAX-ACCESS accessible-for-notify
    STATUS current
    DESCRIPTION
        "Parameter 'ip-address' in event TTTP.10"
    ::= { tttpEventObjects10 2 }

tttp10-port OBJECT-TYPE
    SYNTAX Integer32
    MAX-ACCESS accessible-for-notify
    STATUS current
    DESCRIPTION
        "Parameter 'port' in event TTTP.10"
    ::= { tttpEventObjects10 3 }

tttpEventObjects11 OBJECT-IDENTITY
    STATUS current
    DESCRIPTION
        "Event TTTP.11
        RAM buffer overrun condition start for an Accounting Server."
    ::= { tttpEventsGroup 11 }

tttp11-ip-address OBJECT-TYPE
    SYNTAX IpAddress
    MAX-ACCESS accessible-for-notify
    STATUS current
    DESCRIPTION
        "Parameter 'ip-address' in event TTTP.11"
    ::= { tttpEventObjects11 1 }

tttp11-port OBJECT-TYPE
    SYNTAX Integer32
    MAX-ACCESS accessible-for-notify
    STATUS current
    DESCRIPTION
        "Parameter 'port' in event TTTP.11"
    ::= { tttpEventObjects11 2 }

tttp11-secuence OBJECT-TYPE
    SYNTAX Integer32
    MAX-ACCESS accessible-for-notify
    STATUS current
    DESCRIPTION
        "Parameter 'secuence' in event TTTP.11"
    ::= { tttpEventObjects11 3 }

tttpEventObjects12 OBJECT-IDENTITY
    STATUS current
    DESCRIPTION
        "Event TTTP.12
        RAM buffer overrun condition ends for an Accounting Server."
    ::= { tttpEventsGroup 12 }

tttp12-ip-address OBJECT-TYPE
    SYNTAX IpAddress
    MAX-ACCESS accessible-for-notify
    STATUS current
    DESCRIPTION
        "Parameter 'ip-address' in event TTTP.12"
    ::= { tttpEventObjects12 1 }

tttp12-port OBJECT-TYPE
    SYNTAX Integer32
    MAX-ACCESS accessible-for-notify
    STATUS current
    DESCRIPTION
        "Parameter 'port' in event TTTP.12"
    ::= { tttpEventObjects12 2 }

tttp12-secuence OBJECT-TYPE
    SYNTAX Integer32
    MAX-ACCESS accessible-for-notify
    STATUS current
    DESCRIPTION
        "Parameter 'secuence' in event TTTP.12"
    ::= { tttpEventObjects12 3 }

tttpEventObjects13 OBJECT-IDENTITY
    STATUS current
    DESCRIPTION
        "Event TTTP.13
        RAM buffer overrun condition start for all Accounting Server."
    ::= { tttpEventsGroup 13 }

tttp13-secuence OBJECT-TYPE
    SYNTAX Integer32
    MAX-ACCESS accessible-for-notify
    STATUS current
    DESCRIPTION
        "Parameter 'secuence' in event TTTP.13"
    ::= { tttpEventObjects13 1 }

tttpEventObjects14 OBJECT-IDENTITY
    STATUS current
    DESCRIPTION
        "Event TTTP.14
        RAM buffer overrun condition ends for all Accounting Server."
    ::= { tttpEventsGroup 14 }

tttp14-secuence OBJECT-TYPE
    SYNTAX Integer32
    MAX-ACCESS accessible-for-notify
    STATUS current
    DESCRIPTION
        "Parameter 'secuence' in event TTTP.14"
    ::= { tttpEventObjects14 1 }

tttpEventObjects15 OBJECT-IDENTITY
    STATUS current
    DESCRIPTION
        "Event TTTP.15
        NVRAM buffer overrun condition start."
    ::= { tttpEventsGroup 15 }

tttp15-secuence OBJECT-TYPE
    SYNTAX Integer32
    MAX-ACCESS accessible-for-notify
    STATUS current
    DESCRIPTION
        "Parameter 'secuence' in event TTTP.15"
    ::= { tttpEventObjects15 1 }

tttpEventObjects16 OBJECT-IDENTITY
    STATUS current
    DESCRIPTION
        "Event TTTP.16
        NVRAM buffer overrun condition ends."
    ::= { tttpEventsGroup 16 }

tttp16-secuence OBJECT-TYPE
    SYNTAX Integer32
    MAX-ACCESS accessible-for-notify
    STATUS current
    DESCRIPTION
        "Parameter 'secuence' in event TTTP.16"
    ::= { tttpEventObjects16 1 }

tttpEventObjects17 OBJECT-IDENTITY
    STATUS current
    DESCRIPTION
        "Event TTTP.17
        Trigger condition for transaction buffer overrun occur."
    ::= { tttpEventsGroup 17 }

tttp17-buffer-type OBJECT-TYPE
    SYNTAX DisplayString
    MAX-ACCESS accessible-for-notify
    STATUS current
    DESCRIPTION
        "Parameter 'buffer-type' in event TTTP.17"
    ::= { tttpEventObjects17 1 }

tttpEventObjects18 OBJECT-IDENTITY
    STATUS current
    DESCRIPTION
        "Event TTTP.18
        Trigger condition for transaction buffer overrun ends."
    ::= { tttpEventsGroup 18 }

tttp18-buffer-type OBJECT-TYPE
    SYNTAX DisplayString
    MAX-ACCESS accessible-for-notify
    STATUS current
    DESCRIPTION
        "Parameter 'buffer-type' in event TTTP.18"
    ::= { tttpEventObjects18 1 }


tttpNotification1 NOTIFICATION-TYPE
    OBJECTS { 
              tttp1-ip-address, 
              tttp1-port 
            }
    STATUS current
    DESCRIPTION
        "Notification of Event TTTP.1

        Message: 'Connection is established to Accounting Server IP:$1 Port:$2'

        Parameters list:
              $1: tttp1-ip-address
              $2: tttp1-port

        Connection was established to an Accounting Server."
    ::= { tttpNotificationsPrefix 1 }

tttpNotification2 NOTIFICATION-TYPE
    OBJECTS { 
              tttp2-cause, 
              tttp2-ip-address,
              tttp2-port 
            }
    STATUS current
    DESCRIPTION
        "Notification of Event TTTP.2

        Message: 'Connection attempt failed ($1) to Accounting Server IP:$2 Port:$3'

        Parameters list:
              $1: tttp2-cause
              $2: tttp2-ip-address
              $3: tttp2-port

        Connection attempt was failed to an Accounting Server."
    ::= { tttpNotificationsPrefix 2 }

tttpNotification3 NOTIFICATION-TYPE
    OBJECTS { 
              tttp3-ip-address, 
              tttp3-port 
            }
    STATUS current
    DESCRIPTION
        "Notification of Event TTTP.3

        Message: 'Connecting to Accounting Server Timeout IP:$1 Port:$2'

        Parameters list:
              $1: tttp3-ip-address
              $2: tttp3-port

        Connection attempt to an Accounting Server timeout."
    ::= { tttpNotificationsPrefix 3 }

tttpNotification4 NOTIFICATION-TYPE
    OBJECTS { 
              tttp4-ip-address, 
              tttp4-port 
            }
    STATUS current
    DESCRIPTION
        "Notification of Event TTTP.4

        Message: 'TTTP Session drop with Server IP:$1 Port:$2'

        Parameters list:
              $1: tttp4-ip-address
              $2: tttp4-port

        TTTP session drop to an Accounting Server."
    ::= { tttpNotificationsPrefix 4 }

tttpNotification5 NOTIFICATION-TYPE
    OBJECTS { 
              tttp5-ip-address, 
              tttp5-port,
              tttp5-secuence 
            }
    STATUS current
    DESCRIPTION
        "Notification of Event TTTP.5

        Message: 'Tx Transaction packet to Server IP:$1 Port:$2 Secuence:$3'

        Parameters list:
              $1: tttp5-ip-address
              $2: tttp5-port
              $3: tttp5-secuence

        A Trasacctin packet was send to an Accounting Server."
    ::= { tttpNotificationsPrefix 5 }

tttpNotification6 NOTIFICATION-TYPE
    OBJECTS { 
              tttp6-ip-address, 
              tttp6-port,
              tttp6-length 
            }
    STATUS current
    DESCRIPTION
        "Notification of Event TTTP.6

        Message: 'Rx Acknowledge packet from Server IP:$1 Port:$2 length:$3'

        Parameters list:
              $1: tttp6-ip-address
              $2: tttp6-port
              $3: tttp6-length

        Data was received from an Accounting Server."
    ::= { tttpNotificationsPrefix 6 }

tttpNotification7 NOTIFICATION-TYPE
    OBJECTS { 
              tttp7-ip-address, 
              tttp7-port,
              tttp7-secuence 
            }
    STATUS current
    DESCRIPTION
        "Notification of Event TTTP.7

        Message: 'Rx Acknowledge packet from Server IP:$1 Port:$2 Secuence:$3'

        Parameters list:
              $1: tttp7-ip-address
              $2: tttp7-port
              $3: tttp7-secuence

        An ACK packet was received from an Accounting Server."
    ::= { tttpNotificationsPrefix 7 }

tttpNotification8 NOTIFICATION-TYPE
    OBJECTS { 
              tttp8-ip-address, 
              tttp8-port 
            }
    STATUS current
    DESCRIPTION
        "Notification of Event TTTP.8

        Message: 'Connecting to Accounting Server IP:$1 Port:$2'

        Parameters list:
              $1: tttp8-ip-address
              $2: tttp8-port

        Connection attempt was make to an Accounting Server."
    ::= { tttpNotificationsPrefix 8 }

tttpNotification9 NOTIFICATION-TYPE
    OBJECTS { 
              tttp9-cause, 
              tttp9-ip-address,
              tttp9-port 
            }
    STATUS current
    DESCRIPTION
        "Notification of Event TTTP.9

        Message: 'Rx Wrong ACK packet ($1) from Accounting Server IP:$2 Port:$3'

        Parameters list:
              $1: tttp9-cause
              $2: tttp9-ip-address
              $3: tttp9-port

        Wrong ACK packet was receiver from an Accounting Server."
    ::= { tttpNotificationsPrefix 9 }

tttpNotification10 NOTIFICATION-TYPE
    OBJECTS { 
              tttp10-secuence, 
              tttp10-ip-address,
              tttp10-port 
            }
    STATUS current
    DESCRIPTION
        "Notification of Event TTTP.10

        Message: 'Secuence manipulation error Secuence:$1 Server IP:$2 Port:$3'

        Parameters list:
              $1: tttp10-secuence
              $2: tttp10-ip-address
              $3: tttp10-port

        Internal transaction secuence manipulation error."
    ::= { tttpNotificationsPrefix 10 }

tttpNotification11 NOTIFICATION-TYPE
    OBJECTS { 
              tttp11-ip-address, 
              tttp11-port,
              tttp11-secuence 
            }
    STATUS current
    DESCRIPTION
        "Notification of Event TTTP.11

        Message: 'Transaction RAM buffer overrun for Server IP:$1 Port:$2 Secuence:$3'

        Parameters list:
              $1: tttp11-ip-address
              $2: tttp11-port
              $3: tttp11-secuence

        RAM buffer overrun condition start for an Accounting Server."
    ::= { tttpNotificationsPrefix 11 }

tttpNotification12 NOTIFICATION-TYPE
    OBJECTS { 
              tttp12-ip-address, 
              tttp12-port,
              tttp12-secuence 
            }
    STATUS current
    DESCRIPTION
        "Notification of Event TTTP.12

        Message: 'Transaction RAM buffer overrun ends for Server IP:$1 Port:$2 Secuence:$3'

        Parameters list:
              $1: tttp12-ip-address
              $2: tttp12-port
              $3: tttp12-secuence

        RAM buffer overrun condition ends for an Accounting Server."
    ::= { tttpNotificationsPrefix 12 }

tttpNotification13 NOTIFICATION-TYPE
    OBJECTS { 
              tttp13-secuence 
            }
    STATUS current
    DESCRIPTION
        "Notification of Event TTTP.13

        Message: 'Transaction RAM general buffer overrun Secuence:$1'

        Parameters list:
              $1: tttp13-secuence

        RAM buffer overrun condition start for all Accounting Server."
    ::= { tttpNotificationsPrefix 13 }

tttpNotification14 NOTIFICATION-TYPE
    OBJECTS { 
              tttp14-secuence 
            }
    STATUS current
    DESCRIPTION
        "Notification of Event TTTP.14

        Message: 'Transaction RAM general buffer overrun ends Secuence:$1'

        Parameters list:
              $1: tttp14-secuence

        RAM buffer overrun condition ends for all Accounting Server."
    ::= { tttpNotificationsPrefix 14 }

tttpNotification15 NOTIFICATION-TYPE
    OBJECTS { 
              tttp15-secuence 
            }
    STATUS current
    DESCRIPTION
        "Notification of Event TTTP.15

        Message: 'Transaction NVRAM general buffer overrun secuence:$1'

        Parameters list:
              $1: tttp15-secuence

        NVRAM buffer overrun condition start."
    ::= { tttpNotificationsPrefix 15 }

tttpNotification16 NOTIFICATION-TYPE
    OBJECTS { 
              tttp16-secuence 
            }
    STATUS current
    DESCRIPTION
        "Notification of Event TTTP.16

        Message: 'Transaction NVRAM general buffer overrun ends secuence:$1'

        Parameters list:
              $1: tttp16-secuence

        NVRAM buffer overrun condition ends."
    ::= { tttpNotificationsPrefix 16 }

tttpNotification17 NOTIFICATION-TYPE
    OBJECTS { 
              tttp17-buffer-type 
            }
    STATUS current
    DESCRIPTION
        "Notification of Event TTTP.17

        Message: '$1 transaction buffer overrun trigger'

        Parameters list:
              $1: tttp17-buffer-type

        Trigger condition for transaction buffer overrun occur."
    ::= { tttpNotificationsPrefix 17 }

tttpNotification18 NOTIFICATION-TYPE
    OBJECTS { 
              tttp18-buffer-type 
            }
    STATUS current
    DESCRIPTION
        "Notification of Event TTTP.18

        Message: '$1 transaction buffer overrun trigger ends'

        Parameters list:
              $1: tttp18-buffer-type

        Trigger condition for transaction buffer overrun ends."
    ::= { tttpNotificationsPrefix 18 }


END
