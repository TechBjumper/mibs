PSA-LinTg3Trap-MIB DEFINITIONS ::= BEGIN

--PRIMEQUEST system management MIB for Partition
--
--
--$Copyright$
--Copyright Fujitsu Limited 2004 - 2008
--All rights reserved
--
--
--MIB Revision: 01170000
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaLinTg3Trap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise		OBJECT IDENTIFIER  ::={ partition 201 }
     psaComTrap				OBJECT IDENTIFIER  ::={ partitionEnterprise 1 }
     psaLinLanComTrap			OBJECT IDENTIFIER  ::={ partitionEnterprise 2 }
     psaLinIntelE100Trap		OBJECT IDENTIFIER  ::={ partitionEnterprise 3 }
     psaLinIntelE1000Trap		OBJECT IDENTIFIER  ::={ partitionEnterprise 4 }
     psaLinBcm5700Trap			OBJECT IDENTIFIER  ::={ partitionEnterprise 5 }
     psaLinEmulexTrap			OBJECT IDENTIFIER  ::={ partitionEnterprise 6 }
     psaLinLsiLogicTrap		OBJECT IDENTIFIER  ::={ partitionEnterprise 7 }
     psaLinScsiComTrap			OBJECT IDENTIFIER  ::={ partitionEnterprise 8 }
     psaLinGrmpdTrap			OBJECT IDENTIFIER  ::={ partitionEnterprise 9 }
     psaLinGdsTrap				OBJECT IDENTIFIER  ::={ partitionEnterprise 10 }
     psaLinGlsTrap				OBJECT IDENTIFIER  ::={ partitionEnterprise 11 }
     psaLinTg3Trap				OBJECT IDENTIFIER  ::={ partitionEnterprise 12 }
     psaLinIbTrap				OBJECT IDENTIFIER  ::={ partitionEnterprise 13 }
     psaLinXframe2Trap			OBJECT IDENTIFIER  ::={ partitionEnterprise 14 }
     psaGschTrap				OBJECT IDENTIFIER  ::={ partitionEnterprise 15 }
     psaLinIntelE1000ETrap		OBJECT IDENTIFIER  ::={ partitionEnterprise 16 }
     psaExternalFileUnitTrap	OBJECT IDENTIFIER  ::={ partitionEnterprise 101 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

trapFlagcode OBJECT-TYPE
   SYNTAX   DisplayString
   ACCESS   not-accessible
   STATUS   mandatory
   DESCRIPTION " "
   ::= { trapVarDivInfo 28 }

--***************************************************************************************
--
--FUJITSU PRIMEQUEST system management TRAP definition for Partition
--	Trap enterprise:	psaLinTg3Trap (.1.3.6.1.4.1.211.1.31.1.2.201.12)
--
--***************************************************************************************

tg3Event0 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (transmit timed out. resetting)"
   --#TYPE			"Tg3 Event 0"
   --#SUMMARY		"%s(PID=%d) %s %d %s tg3:%s Software error (transmit timed out. resetting)"
   --#ARGUMENTS		{ 0, 1, 2, 3, 4, 5 }
   --#SEVERITY		MINOR
   ::= 11400

tg3Event1 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (Tx Ring full when queue awake)"
   --#TYPE			"Tg3 Event 1"
   --#SUMMARY		"%s(PID=%d) %s %d %s tg3:%s Software error (Tx Ring full when queue awake)"
   --#ARGUMENTS		{ 0, 1, 2, 3, 4, 5 }
   --#SEVERITY		MINOR
   ::= 11401

tg3Event2 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (tg3_stop_block timed out)"
   --#TYPE			"Tg3 Event 2"
   --#SUMMARY		"%s(PID=%d) %s %d %s tg3:%s Adapter error (tg3_stop_block timed out) vendor-id=%s device-id=%s revision=%s"
   --#ARGUMENTS		{ 0, 1, 2, 3, 4, 5, 6, 7, 8 }
   --#SEVERITY		MINOR
   ::= 11402

tg3Event3 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (tg3_abort_hw timed out)"
   --#TYPE			"Tg3 Event 3"
   --#SUMMARY		"%s(PID=%d) %s %d %s tg3:%s Adapter error (tg3_abort_hw timed out) vendor-id=%s device-id=%s revision=%s"
   --#ARGUMENTS		{ 0, 1, 2, 3, 4, 5, 6, 7, 8 }
   --#SEVERITY		MINOR
   ::= 11403

tg3Event4 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (tg3_reset_hw cannot enable BUFMGR)"
   --#TYPE			"Tg3 Event 4"
   --#SUMMARY		"%s(PID=%d) %s %d %s tg3:%s Adapter error (tg3_reset_hw cannot enable BUFMGR) vendor-id=%s device-id=%s revision=%s"
   --#ARGUMENTS		{ 0, 1, 2, 3, 4, 5, 6, 7, 8 }
   --#SEVERITY		MINOR
   ::= 11404

tg3Event5 TRAP-TYPE
   ENTERPRISE   psaLinTg3Trap
   VARIABLES {
      trapPartitionName,
      trapPartitionId,
      trapEventLevel,
      trapEventId,
      trapUnitName,
      trapMmbVip
   }
   DESCRIPTION "tg3: Adapter error (Register test failed)"
   --#TYPE			"Tg3 Event 5"
   --#SUMMARY		"%s(PID=%d) %s %d %s tg3: Adapter error (Register test failed)"
   --#ARGUMENTS		{ 0, 1, 2, 3, 4 }
   --#SEVERITY		MINOR
   ::= 11405

tg3Event6 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (transition to D0 failed)"
   --#TYPE			"Tg3 Event 6"
   --#SUMMARY		"%s(PID=%d) %s %d %s tg3:%s Software error (transition to D0 failed)"
   --#ARGUMENTS		{ 0, 1, 2, 3, 4, 5 }
   --#SEVERITY		MINOR
   ::= 11406

tg3Event7 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (phy probe failed)"
   --#TYPE			"Tg3 Event 7"
   --#SUMMARY		"%s(PID=%d) %s %d %s tg3:%s Adapter error (phy probe failed) vendor-id=%s device-id=%s revision=%s"
   --#ARGUMENTS		{ 0, 1, 2, 3, 4, 5, 6, 7, 8 }
   --#SEVERITY		MINOR
   ::= 11407

tg3Event8 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (test_dma Write the buffer failed)"
   --#TYPE			"Tg3 Event 8"
   --#SUMMARY		"%s(PID=%d) %s %d %s tg3:%s Adapter error (test_dma Write the buffer failed) vendor-id=%s device-id=%s revision=%s"
   --#ARGUMENTS		{ 0, 1, 2, 3, 4, 5, 6, 7, 8 }
   --#SEVERITY		MINOR
   ::= 11408

tg3Event9 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (test_dma Card buffer corrupted on write)"
   --#TYPE			"Tg3 Event 9"
   --#SUMMARY		"%s(PID=%d) %s %d %s tg3:%s Adapter error (test_dma Card buffer corrupted on write) vendor-id=%s device-id=%s revision=%s"
   --#ARGUMENTS		{ 0, 1, 2, 3, 4, 5, 6, 7, 8 }
   --#SEVERITY		MINOR
   ::= 11409

tg3Event10 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (test_dma Read the buffer failed)"
   --#TYPE			"Tg3 Event 10"
   --#SUMMARY		"%s(PID=%d) %s %d %s tg3:%s Adapter error (test_dma Read the buffer failed) vendor-id=%s device-id=%s revision=%s"
   --#ARGUMENTS		{ 0, 1, 2, 3, 4, 5, 6, 7, 8 }
   --#SEVERITY		MINOR
   ::= 11410

tg3Event11 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (test_dma buffer corrupted on read back)"
   --#TYPE			"Tg3 Event 11"
   --#SUMMARY		"%s(PID=%d) %s %d %s tg3:%s Adapter error (test_dma buffer corrupted on read back) vendor-id=%s device-id=%s revision=%s"
   --#ARGUMENTS		{ 0, 1, 2, 3, 4, 5, 6, 7, 8 }
   --#SEVERITY		MINOR
   ::= 11411

tg3Event12 TRAP-TYPE
   ENTERPRISE   psaLinTg3Trap
   VARIABLES {
      trapPartitionName,
      trapPartitionId,
      trapEventLevel,
      trapEventId,
      trapUnitName,
      trapMmbVip
   }
   DESCRIPTION "tg3: Software error (Cannot enable PCI device. aborting)"
   --#TYPE			"Tg3 Event 12"
   --#SUMMARY		"%s(PID=%d) %s %d %s tg3: Software error (Cannot enable PCI device. aborting)"
   --#ARGUMENTS		{ 0, 1, 2, 3, 4 }
   --#SEVERITY		MINOR
   ::= 11412

tg3Event13 TRAP-TYPE
   ENTERPRISE   psaLinTg3Trap
   VARIABLES {
      trapPartitionName,
      trapPartitionId,
      trapEventLevel,
      trapEventId,
      trapUnitName,
      trapMmbVip
   }
   DESCRIPTION "tg3: Software error (Cannot find proper PCI device base address. aborting)"
   --#TYPE			"Tg3 Event 13"
   --#SUMMARY		"%s(PID=%d) %s %d %s tg3: Software error (Cannot find proper PCI device base address. aborting)"
   --#ARGUMENTS		{ 0, 1, 2, 3, 4 }
   --#SEVERITY		MINOR
   ::= 11413

tg3Event14 TRAP-TYPE
   ENTERPRISE   psaLinTg3Trap
   VARIABLES {
      trapPartitionName,
      trapPartitionId,
      trapEventLevel,
      trapEventId,
      trapUnitName,
      trapMmbVip
   }
   DESCRIPTION "tg3: Software error (Cannot obtain PCI resources. aborting)"
   --#TYPE			"Tg3 Event 14"
   --#SUMMARY		"%s(PID=%d) %s %d %s tg3: Software error (Cannot obtain PCI resources. aborting)"
   --#ARGUMENTS		{ 0, 1, 2, 3, 4 }
   --#SEVERITY		MINOR
   ::= 11414

tg3Event15 TRAP-TYPE
   ENTERPRISE   psaLinTg3Trap
   VARIABLES {
      trapPartitionName,
      trapPartitionId,
      trapEventLevel,
      trapEventId,
      trapUnitName,
      trapMmbVip
   }
   DESCRIPTION "tg3: Software error (Cannot find PowerManagement capability. aborting)"
   --#TYPE			"Tg3 Event 15"
   --#SUMMARY		"%s(PID=%d) %s %d %s tg3: Software error (Cannot find PowerManagement capability. aborting)"
   --#ARGUMENTS		{ 0, 1, 2, 3, 4 }
   --#SEVERITY		MINOR
   ::= 11415

tg3Event16 TRAP-TYPE
   ENTERPRISE   psaLinTg3Trap
   VARIABLES {
      trapPartitionName,
      trapPartitionId,
      trapEventLevel,
      trapEventId,
      trapUnitName,
      trapMmbVip
   }
   DESCRIPTION "tg3: Software error (Etherdev alloc failed. aborting)"
   --#TYPE			"Tg3 Event 16"
   --#SUMMARY		"%s(PID=%d) %s %d %s tg3: Software error (Etherdev alloc failed. aborting)"
   --#ARGUMENTS		{ 0, 1, 2, 3, 4 }
   --#SEVERITY		MINOR
   ::= 11416

tg3Event17 TRAP-TYPE
   ENTERPRISE   psaLinTg3Trap
   VARIABLES {
      trapPartitionName,
      trapPartitionId,
      trapEventLevel,
      trapEventId,
      trapUnitName,
      trapMmbVip
   }
   DESCRIPTION "tg3: Software error (Cannot map device registers. aborting)"
   --#TYPE			"Tg3 Event 17"
   --#SUMMARY		"%s(PID=%d) %s %d %s tg3: Software error (Cannot map device registers. aborting)"
   --#ARGUMENTS		{ 0, 1, 2, 3, 4 }
   --#SEVERITY		MINOR
   ::= 11417

tg3Event18 TRAP-TYPE
   ENTERPRISE   psaLinTg3Trap
   VARIABLES {
      trapPartitionName,
      trapPartitionId,
      trapEventLevel,
      trapEventId,
      trapUnitName,
      trapMmbVip
   }
   DESCRIPTION "tg3: Software error (Problem fetching invariants of chip. aborting)"
   --#TYPE			"Tg3 Event 18"
   --#SUMMARY		"%s(PID=%d) %s %d %s tg3: Software error (Problem fetching invariants of chip. aborting)"
   --#ARGUMENTS		{ 0, 1, 2, 3, 4 }
   --#SEVERITY		MINOR
   ::= 11418

tg3Event19 TRAP-TYPE
   ENTERPRISE   psaLinTg3Trap
   VARIABLES {
      trapPartitionName,
      trapPartitionId,
      trapEventLevel,
      trapEventId,
      trapUnitName,
      trapMmbVip
   }
   DESCRIPTION "tg3: Software error (Unable to obtain 64 bit DMA for consistent allocations)"
   --#TYPE			"Tg3 Event 19"
   --#SUMMARY		"%s(PID=%d) %s %d %s tg3: Software error (Unable to obtain 64 bit DMA for consistent allocations)"
   --#ARGUMENTS		{ 0, 1, 2, 3, 4 }
   --#SEVERITY		MINOR
   ::= 11419

tg3Event20 TRAP-TYPE
   ENTERPRISE   psaLinTg3Trap
   VARIABLES {
      trapPartitionName,
      trapPartitionId,
      trapEventLevel,
      trapEventId,
      trapUnitName,
      trapMmbVip
   }
   DESCRIPTION "tg3: Software error (No usable DMA configuration. aborting)"
   --#TYPE			"Tg3 Event 20"
   --#SUMMARY		"%s(PID=%d) %s %d %s tg3: Software error (No usable DMA configuration. aborting)"
   --#ARGUMENTS		{ 0, 1, 2, 3, 4 }
   --#SEVERITY		MINOR
   ::= 11420

tg3Event21 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (Could not obtain valid ethernet address. aborting)"
   --#TYPE			"Tg3 Event 21"
   --#SUMMARY		"%s(PID=%d) %s %d %s tg3:%s Adapter error (Could not obtain valid ethernet address. aborting) vendor-id=%s device-id=%s revision=%s"
   --#ARGUMENTS		{ 0, 1, 2, 3, 4, 5, 6, 7, 8 }
   --#SEVERITY		MINOR
   ::= 11421

tg3Event22 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (DMA engine test failed. aborting)"
   --#TYPE			"Tg3 Event 22"
   --#SUMMARY		"%s(PID=%d) %s %d %s tg3:%s Adapter error (DMA engine test failed. aborting) vendor-id=%s device-id=%s revision=%s"
   --#ARGUMENTS		{ 0, 1, 2, 3, 4, 5, 6, 7, 8 }
   --#SEVERITY		MINOR
   ::= 11422

tg3Event23 TRAP-TYPE
   ENTERPRISE   psaLinTg3Trap
   VARIABLES {
      trapPartitionName,
      trapPartitionId,
      trapEventLevel,
      trapEventId,
      trapUnitName,
      trapMmbVip
   }
   DESCRIPTION "tg3: Software error (Cannot register net device. aborting)"
   --#TYPE			"Tg3 Event 23"
   --#SUMMARY		"%s(PID=%d) %s %d %s tg3: Software error (Cannot register net device. aborting)"
   --#ARGUMENTS		{ 0, 1, 2, 3, 4 }
   --#SEVERITY		MINOR
   ::= 11423

tg3Event24 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (Invalid power state requested)"
   --#TYPE			"Tg3 Event 24"
   --#SUMMARY		"%s(PID=%d) %s %d %s tg3:%s Software error (Invalid power state requested)"
   --#ARGUMENTS		{ 0, 1, 2, 3, 4, 5 }
   --#SEVERITY		MINOR
   ::= 11424

tg3Event25 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (Failed to re-initialize device; aborting)"
   --#TYPE			"Tg3 Event 25"
   --#SUMMARY		"%s(PID=%d) %s %d %s tg3:%s Software error (Failed to re-initialize device; aborting)"
   --#ARGUMENTS		{ 0, 1, 2, 3, 4, 5 }
   --#SEVERITY		MINOR
   ::= 11425

tg3Event26 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (Cannot get nvarm lock; tg3_nvram_init failed)"
   --#TYPE			"Tg3 Event 26"
   --#SUMMARY		"%s(PID=%d) %s %d %s tg3:%s Software error (Cannot get nvarm lock; tg3_nvram_init failed)"
   --#ARGUMENTS		{ 0, 1, 2, 3, 4, 5 }
   --#SEVERITY		MINOR
   ::= 11426

tg3Event27 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (The system may be re-ordering memory-mapped I/O cycles to the network device)"
   --#TYPE			"Tg3 Event 27"
   --#SUMMARY		"%s(PID=%d) %s %d %s tg3:%s Software error (The system may be re-ordering memory-mapped I/O cycles to the network device)"
   --#ARGUMENTS		{ 0, 1, 2, 3, 4, 5 }
   --#SEVERITY		MINOR
   ::= 11427

tg3Event28 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (Using a smaller RX standard ring)"
   --#TYPE			"Tg3 Event 28"
   --#SUMMARY		"%s(PID=%d) %s %d %s tg3:%s Software error (Using a smaller RX standard ring)"
   --#ARGUMENTS		{ 0, 1, 2, 3, 4, 5 }
   --#SEVERITY		MINOR
   ::= 11428

tg3Event29 TRAP-TYPE
   ENTERPRISE   psaLinTg3Trap
   VARIABLES {
      trapPartitionName,
      trapPartitionId,
      trapEventLevel,
      trapEventId,
      trapUnitName,
      trapSuspect,
      trapMmbVip
   }
   DESCRIPTION "tg3: Software error (Using a smaller RX jumbo ring)"
   --#TYPE			"Tg3 Event 29"
   --#SUMMARY		"%s(PID=%d) %s %d %s tg3:%s Software error (Using a smaller RX jumbo ring)"
   --#ARGUMENTS		{ 0, 1, 2, 3, 4, 5 }
   --#SEVERITY		MINOR
   ::= 11429

tg3Event30 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (readl: PCI parity error detected. retrying)"
   --#TYPE			"Tg3 Event 30"
   --#SUMMARY		"%s(PID=%d) %s %d %s tg3:%s Adapter error (readl: PCI parity error detected. retrying) vendor-id=%s device-id=%s revision=%s"
   --#ARGUMENTS		{ 0, 1, 2, 3, 4, 5, 6, 7, 8 }
   --#SEVERITY		MINOR
   ::= 11430

tg3Event31 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (readl: Cannot recover from a PCI parity error)"
   --#TYPE			"Tg3 Event 31"
   --#SUMMARY		"%s(PID=%d) %s %d %s tg3:%s Adapter error (readl: Cannot recover from a PCI parity error) vendor-id=%s device-id=%s revision=%s"
   --#ARGUMENTS		{ 0, 1, 2, 3, 4, 5, 6, 7, 8 }
   --#SEVERITY		MINOR
   ::= 11431

tg3Event32 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (writel: PCI parity error detected. retrying)"
   --#TYPE			"Tg3 Event 32"
   --#SUMMARY		"%s(PID=%d) %s %d %s tg3:%s Adapter error (writel: PCI parity error detected. retrying) vendor-id=%s device-id=%s revision=%s"
   --#ARGUMENTS		{ 0, 1, 2, 3, 4, 5, 6, 7, 8 }
   --#SEVERITY		MINOR
   ::= 11432

tg3Event33 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (writel: Cannot recover from a PCI parity error)"
   --#TYPE			"Tg3 Event 33"
   --#SUMMARY		"%s(PID=%d) %s %d %s tg3:%s Adapter error (writel: Cannot recover from a PCI parity error) vendor-id=%s device-id=%s revision=%s"
   --#ARGUMENTS		{ 0, 1, 2, 3, 4, 5, 6, 7, 8 }
   --#SEVERITY		MINOR
   ::= 11433

tg3Event34 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (interrupt: PCI parity error detected during a DMA transfer)"
   --#TYPE			"Tg3 Event 34"
   --#SUMMARY		"%s(PID=%d) %s %d %s tg3:%s Adapter error (interrupt: PCI parity error detected during a DMA transfer) vendor-id=%s device-id=%s revision=%s"
   --#ARGUMENTS		{ 0, 1, 2, 3, 4, 5, 6, 7, 8 }
   --#SEVERITY		MINOR
   ::= 11434

tg3Event35 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (readl: PCI master abort error)"
   --#TYPE			"Tg3 Event 35"
   --#SUMMARY		"%s(PID=%d) %s %d %s tg3:%s Adapter error (readl: PCI master abort error) vendor-id=%s device-id=%s revision=%s"
   --#ARGUMENTS		{ 0, 1, 2, 3, 4, 5, 6, 7, 8 }
   --#SEVERITY		MINOR
   ::= 11435

tg3Event36 TRAP-TYPE
   ENTERPRISE   psaLinTg3Trap
   VARIABLES {
      trapPartitionName,
      trapPartitionId,
      trapEventLevel,
      trapEventId,
      trapUnitName,
      trapSuspect,
      trapVendorId,
      trapDeviceId,
      trapRevision,
      trapMmbVip
   }
   DESCRIPTION "tg3: Adapter error (writel: PCI master abort error)"
   --#TYPE			"Tg3 Event 36"
   --#SUMMARY		"%s(PID=%d) %s %d %s tg3:%s Adapter error (writel: PCI master abort error) vendor-id=%s device-id=%s revision=%s"
   --#ARGUMENTS		{ 0, 1, 2, 3, 4, 5, 6, 7, 8 }
   --#SEVERITY		MINOR
   ::= 11436

tg3Event37 TRAP-TYPE
   ENTERPRISE   psaLinTg3Trap
   VARIABLES {
      trapPartitionName,
      trapPartitionId,
      trapEventLevel,
      trapEventId,
      trapUnitName,
      trapMmbVip
   }
   DESCRIPTION "tg3: Adapter error (Cannot find PCI-X capability; aborting.)"
   --#TYPE			"Tg3 Event 37"
   --#SUMMARY		"%s(PID=%d) %s %d %s tg3: Adapter error (Cannot find PCI-X capability; aborting.)"
   --#ARGUMENTS		{ 0, 1, 2, 3, 4 }
   --#SEVERITY		MINOR
   ::= 11437

END
