-- file automatically created


TELDAT-TRAP-GPSF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


gpsfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the GPSF event subsystem."
    REVISION "201401200930Z"
    DESCRIPTION "Initial implementation"
        ::= { telEventTraps 256 }


gpsfEventsGroup	OBJECT IDENTIFIER	::= { gpsfTrapsMIB 1 }

gpsfNotifications	OBJECT IDENTIFIER	::= { gpsfTrapsMIB 2 }
gpsfNotificationsPrefix	OBJECT IDENTIFIER	::= { gpsfNotifications 0 }

gpsfEventObjects1 OBJECT-IDENTITY
    STATUS current
    DESCRIPTION
        "Event GPSF.1
        Shows last position obtained fron GPS fix data."
    ::= { gpsfEventsGroup 1 }

gpsf1-h OBJECT-TYPE
    SYNTAX Integer32
    MAX-ACCESS accessible-for-notify
    STATUS current
    DESCRIPTION
        "Parameter 'h' in event GPSF.1"
    ::= { gpsfEventObjects1 1 }

gpsf1-m OBJECT-TYPE
    SYNTAX Integer32
    MAX-ACCESS accessible-for-notify
    STATUS current
    DESCRIPTION
        "Parameter 'm' in event GPSF.1"
    ::= { gpsfEventObjects1 2 }

gpsf1-s OBJECT-TYPE
    SYNTAX Integer32
    MAX-ACCESS accessible-for-notify
    STATUS current
    DESCRIPTION
        "Parameter 's' in event GPSF.1"
    ::= { gpsfEventObjects1 3 }

gpsf1-la-deg OBJECT-TYPE
    SYNTAX Integer32
    MAX-ACCESS accessible-for-notify
    STATUS current
    DESCRIPTION
        "Parameter 'la-deg' in event GPSF.1"
    ::= { gpsfEventObjects1 4 }

gpsf1-la-min OBJECT-TYPE
    SYNTAX Integer32
    MAX-ACCESS accessible-for-notify
    STATUS current
    DESCRIPTION
        "Parameter 'la-min' in event GPSF.1"
    ::= { gpsfEventObjects1 5 }

gpsf1-la-minfrac OBJECT-TYPE
    SYNTAX Integer32
    MAX-ACCESS accessible-for-notify
    STATUS current
    DESCRIPTION
        "Parameter 'la-minfrac' in event GPSF.1"
    ::= { gpsfEventObjects1 6 }

gpsf1-la-area OBJECT-TYPE
    SYNTAX DisplayString
    MAX-ACCESS accessible-for-notify
    STATUS current
    DESCRIPTION
        "Parameter 'la-area' in event GPSF.1"
    ::= { gpsfEventObjects1 7 }

gpsf1-lo-deg OBJECT-TYPE
    SYNTAX Integer32
    MAX-ACCESS accessible-for-notify
    STATUS current
    DESCRIPTION
        "Parameter 'lo-deg' in event GPSF.1"
    ::= { gpsfEventObjects1 8 }

gpsf1-lo-min OBJECT-TYPE
    SYNTAX Integer32
    MAX-ACCESS accessible-for-notify
    STATUS current
    DESCRIPTION
        "Parameter 'lo-min' in event GPSF.1"
    ::= { gpsfEventObjects1 9 }

gpsf1-lo-minfrac OBJECT-TYPE
    SYNTAX Integer32
    MAX-ACCESS accessible-for-notify
    STATUS current
    DESCRIPTION
        "Parameter 'lo-minfrac' in event GPSF.1"
    ::= { gpsfEventObjects1 10 }

gpsf1-lo-area OBJECT-TYPE
    SYNTAX DisplayString
    MAX-ACCESS accessible-for-notify
    STATUS current
    DESCRIPTION
        "Parameter 'lo-area' in event GPSF.1"
    ::= { gpsfEventObjects1 11 }

gpsf1-altint OBJECT-TYPE
    SYNTAX Integer32
    MAX-ACCESS accessible-for-notify
    STATUS current
    DESCRIPTION
        "Parameter 'altint' in event GPSF.1"
    ::= { gpsfEventObjects1 12 }

gpsf1-altfrac OBJECT-TYPE
    SYNTAX Integer32
    MAX-ACCESS accessible-for-notify
    STATUS current
    DESCRIPTION
        "Parameter 'altfrac' in event GPSF.1"
    ::= { gpsfEventObjects1 13 }

gpsf1-nsat OBJECT-TYPE
    SYNTAX Integer32
    MAX-ACCESS accessible-for-notify
    STATUS current
    DESCRIPTION
        "Parameter 'nsat' in event GPSF.1"
    ::= { gpsfEventObjects1 14 }


gpsfNotification1 NOTIFICATION-TYPE
    OBJECTS { 
              gpsf1-h, 
              gpsf1-m,
              gpsf1-s,
              gpsf1-la-deg,
              gpsf1-la-min,
              gpsf1-la-minfrac,
              gpsf1-la-area,
              gpsf1-lo-deg,
              gpsf1-lo-min,
              gpsf1-lo-minfrac,
              gpsf1-lo-area,
              gpsf1-altint,
              gpsf1-altfrac,
              gpsf1-nsat 
            }
    STATUS current
    DESCRIPTION
        "Notification of Event GPSF.1

        Message: 'Last GPS Fix . Time: $1:$2:$3, Latitude: $4- $5.$6' $7, Longitude: $8- $9.$10' $11, Alt: $12.$13 m, N-sat: $14'

        Parameters list:
              $1: gpsf1-h
              $2: gpsf1-m
              $3: gpsf1-s
              $4: gpsf1-la-deg
              $5: gpsf1-la-min
              $6: gpsf1-la-minfrac
              $7: gpsf1-la-area
              $8: gpsf1-lo-deg
              $9: gpsf1-lo-min
              $10: gpsf1-lo-minfrac
              $11: gpsf1-lo-area
              $12: gpsf1-altint
              $13: gpsf1-altfrac
              $14: gpsf1-nsat

        Shows last position obtained fron GPS fix data."
    ::= { gpsfNotificationsPrefix 1 }


END
