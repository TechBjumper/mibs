-- $Id: gandalf,v 1.43 1995/11/13 21:43:11 bxiao Exp $
--
-- **************************************
--
-- Gandalf Enterprise-Specific SNMP MIB
--
--            Version 2.0.0
--
--            October 16, 1995
--
-- **************************************
--
-- This document contains the Gandalf private-enterprise SNMP MIB
-- definitions used by some of the following Gandalf products:
--     - Xpressway products
--     - LanLine products
--     - WAN proxies 
-- Note that some devices, such as the Gandalf Access Routers and
-- the Xpressway terminal servers, do not support this MIB.
--
-- Questions regarding this MIB may be directed to
--            1-800-GANDALF (North America only)
--
--
-- ==================================================================
--                     Product Descriptions
-- ==================================================================
--
-- I. Xpressway Products
-- =====================
--
-- 1. Ethernet Control Module (ECM)
-- 
--  The ECM definition is based upon the IEEE preliminary draft
--  "Draft 802.3 Hub Management Document" dated September 1990 (HM #90/89).
-- 
--  The following MIB-II (rfc 1213) groups are supported:
--    system, interface, address translation, ip, icmp, tcp, udp, snmp
--  Only the following sets are allowed for these groups:
--    sysName, sysContact, snmpEnableAuthTraps
--
--  The following private-enterprise groups are supported:
--    basic capability, self test capability, address tracking capability,
--    SNMP administration, log
--  The following sets are allowed for these groups:
--            - hubManTelephoneNum
--            - hubSecureMode
--            - hubName
--            - gCardName
--            - gCardRingNumberA
--            - gCardRingNumberB
--            - gCardIbmModeA
--            - gCardIbmModeB
--            - gCardRingSpeedA
--            - gCardRingSpeedB
--            - gPortAdminState
--            - gPortName
--            - gPortRedundantPort
--            - gPortRedundantCard
--            - hubResetAction
--
-- 2. Bridges (XBR series, RSC ISDN bridge)
-- 
--  The bridge definition is based upon IETF's "INTERNET BRIDGE MIB"
--  draft dated June 1991. Many of these groups are now deprecated
--  in favour of RFC1286.
--
--  The following MIB-II (rfc 1213) groups are supported:
--    system, interface, address translation, ip, icmp, tcp, udp, snmp
--  The following sets are allowed for these groups:
--    sysName, sysContact, snmpEnableAuthTraps
--
--  The following private-enterprise groups are supported by the XBR bridges:
--    configuration, transparent, spanning tree protocol, static, WAN physical,
--    IEEE 802.3
--
--  The following private-enterprise groups are supported by the RSC ISDN 
--  bridges:
--    SNMP administration, log
--  Additional RSC attributes are contained in the file "gandalf-rlan".
--
-- 3. Gateways (WGM2590 hub/standalone)
-- 
--  The following MIB-II (rfc 1213) groups are supported:
--    system, interface, address translation, ip, icmp, tcp, udp, snmp
--  The following sets are allowed for these groups:
--    sysName, sysContact, snmpEnableAuthTraps
--
--  The following private-enterprise groups are supported:
--    IEEE 802.3, SNMP administration, log
--
--
-- II. LanLine Products
-- ====================
--
-- 1. Bridges (52XX-series)
--
--  The following MIB-II (rfc 1213) groups are supported:
--    system, interface, address translation, ip, icmp, tcp, udp, snmp
--  The following sets are allowed for these groups:
--    sysName, sysContact, snmpEnableAuthTraps
--
--  The following private-enterprise groups are supported:
--    configuration, transparent, spanning tree protocol, static, WAN physical,
--    IEEE 802.3, SNMP administration, log
--
-- 2. Routers (52XX series)
-- 
--  The LanLine 5250 router supports the log group.
--
-- 3. WAN Proxies
-- 
--  The enterprise specific MIB for the WAN proxy agent
--  is in the document titled "gandalf-wan" .
--
--  The following MIB-II (rfc 1213) groups are supported:
--    system, interface
--  The interfaces group just covers the serial interface on com1 or com2 
--  (IP is excluded).
--  The following sets are allowed for these groups:
-- 	     - sysContact   (For Agent and each proxied WAN node)
--	     - sysName      (For Agent only)
--	     - sysLocation  (For Agent and each proxied node)
--           - snmpEnableAuthTraps (For Agent only)
--
--  The following private-enterprise groups are supported:
--    SNMP administration
--  The following sets are allowed for these groups:
--    snmpCommunityName snmpCommunityIpAddr, snmpCommunityPriv, 
--    snmpTrapCommunityName, snmpTrapIpAddr
--
--
-- ==================================================================
--                     Group Descriptions
-- ==================================================================
--
-- I. MIB-II groups
-- ================
--
-- Gandalf's implementation of MIB-II follows recommendations from
-- RFC 1158. This has subsequently been updated to rfc 1213.
-- RFC 1213 identifies ten groups that can optionally be supported.
-- Gandalf chose to support the following 8 groups:
--
-- 1 The System Group:
--
--  This group provides contact, administrative, location, and service
--  information regarding the managed device.
--
-- 2 The Interface Group:
--
--  This group provides information about the device's interfaces.  The
--  number of interfaces will vary depending of the type of device.
--
--  A local bridge (EBL) will have 2 LAN interfaces.  A remote bridge
--  (EBR) will have 4 interfaces: 2 WANs, 1 LAN and 1 SMI.
--
--  The ECM has a single interface, the ECM's internet stack.
--
-- 3 The Address Translation Group:
--
--  This group contains a table which permits mappings from
--  network addresses (e.g., IP addresses) to physical addresses (e.g.,
--  MAC addresses).  This table is maintained by the device's internet
--  stack.
--
-- 4 The IP Group:
--
--  This table provides information about the device's internet stack
--  IP layer.  Note that the ipRoutingTable is not supported by the
--  device's SNMP agent.
--
-- 5 The ICMP Group:
--
--  This table provides information about ICMP traffic addressed
--  to the device's internet stack.  An example would be PING packets.
--
-- 6 The TCP Group:
--
--  This group provides information about the device's internet stack
--  TCP layer.  The TCP table can be useful to monitor the amount of
--  traffic generated by operators remotely connecting to the console.
--  The tcpConn table can be useful to see who is currently remotely
--  connected to the console.
--
-- 7 The UDP Group:
--
--  This group provides information about the device's internet stack
--  UDP layer.  The udpConn table shows what protocols sitting on top
--  of UDP are listening for packets (for example SNMP (port 161) or
--  RIP (port 57)).
--
-- 8 The SNMP Group:
--
--  This group provides information about the device's internet stack
--  SNMP layer.  It will give indications, for example, on how much
--  traffic or how many TRAPs the device's SNMP agent generates.
--
--
-- II. Gandalf Enterprise-Specific groups
-- ======================================
--
-- A. Generic groups
--
-- The following groups are generic and can be supported by 
-- many Gandalf products:
--
--    - Log group
--    - SNMP Administration group
--
--  1 The Log group:
--
--  This group contains a table showing the device's event log
--  including the date, time, severity and a textual description
--  of the event.
--
--  2 The SNMP Administration group:
--
--  This group contains two tables, the SNMP Community Table and the
--  SNMP TRAP Community table.  The first table provides a management
--  view of which device can poll this resource via SNMP based on the
--  Community Name, IP address and Privilege.  The second table
--  provides a management view of which device(s) (i.e. LAN Managers)
--  this resource will send TRAPs to.
--
--
-- B. ECM Groups
--
-- The ECM definition is based upon the IEEE preliminary draft dated
-- Sept 1990 (HM #90/89) and called "Draft 802.3 Hub Management Document".
-- The ECM supports the following 4 enterprise specific groups:
--
--    - Basic Capability Group 
--    - Self Test Capability Group    
--    - Performance Monitoring Capability Group
--    - Address Tracking Capability Group   
--
--  1 Basic Capability Group 
--
--  This group contains all the Hub, Card and Port configurations. Included are
--  the Basic Card Table and Basic Port Table.
--
--  2 Self Test Capability Group    
--
--  This group contains startup test information and diagnostic information such
--  as last restart time, time since restart etc. Also included in this group is
--  the attribute to cause a system restart.
--
--  3 Performance Monitoring Capability Group
--
--  This group contains all the counters. Included under this group are the
--  Performance Monitoring Relay Table and the Performance Monitoring Port Table.
--  All traffic and error counters are in this group. All counters are read only.
--  Any counters pertaining to address are not in this group, see next group.
--
--  4 Address Tracking Capability Group   
--
--  This group contains all attributes that pertain to MAC addresses. This is at
--  the hub, card and port levels.
--
--
-- III. Bridge Groups
--
-- Gandalf's Bridge MIB implementation is based upon the IETF's
-- Internet-Bridge-MIB draft dated June 1991. There are six groups
-- in all:
--    - Bridge Configuration group
--    - Bridge Transparent group
--    - Bridge Spanning Tree Protocol group
--    - Bridge Static group
--    - Wan Physical group
--    - Ieee 802.3 group
--
-- Of these, all but the last two have been deprecated in favour
-- of RFC1286, which offers equivalent functionality. Newer
-- revisions of Gandalf Bridges support RFC1286.
--
-- The other two groups supported by the bridge's SNMP agent are generic
-- and can be supported by any Gandalf product:
--
--    - Log group
--    - SNMP Administration group
--
--  1 The Bridge Configuration group:
--
--  This group provides general information regarding the managed bridge.
--  the information includes things like the bridge's address, number
--  of ports, hardware and software revision numbers, etc ...
--
--  2 The Bridge Transparent group:
--
--  This group is based upon the IETF's dot1dTp group. It contains
--  objects that describe the entity's state with respect to transparent
--  bridging.  Filtering information falls under this group.  This
--  group also contains a Port table showing the number of frames
--  received, transmitted and discarded on every logical ports, and
--  a Forwarding Database table showing the bridge's table of
--  filtering addresses.
--
--  3 The Bridge Spanning Tree Protocol group:
--
--  This group is based upon the IETF's dot1dStp group.  It contains
--  the objects that denote the bridge's state with respect to the
--  Spanning Tree Protocol. It also contains a table showing the
--  Spanning Tree information particular to every logical port on
--  the bridge.
--
--  4 The Bridge Static group:
--
--  This group is based upon the IETF's dot1dStatic group. It consists
--  of a table containing the destination-filtering static entries,
--  another table containing the Protocol Filtering entries and of
--  a third table containing the Protocol Priority entries.
--
--  5 The Wan Physical group:
--
--  This group is a complement to MIB-II's interface group for
--  WAN interfaces.  It contains information about the WAN ports
--  DCD level, link level, link utilization and compression ratio.
--
--  6 The IEEE 802.3 group:
--
--  This group is a complement to MIB-II's interface group for
--  LAN interfaces.  It is based upon IEEE's recommendation, and
--  contains detailed information about the LAN ports statistics,
--  state and configuration.
--


GANDALF-ENTERPRISE-MIB DEFINITIONS ::= BEGIN

IMPORTS
       enterprises, Counter, Gauge, NetworkAddress, IpAddress, TimeTicks
    FROM RFC1155-SMI
       OBJECT-TYPE
    FROM RFC-1212
       PhysAddress, DisplayString
    FROM RFC1213-MIB
       TRAP-TYPE
    FROM RFC-1215;

gandalf                     OBJECT IDENTIFIER ::= { enterprises 64 }
gandalf-hub                 OBJECT IDENTIFIER ::= { gandalf 1 }
gandalf-bridge              OBJECT IDENTIFIER ::= { gandalf 2 }
gandalf-generic             OBJECT IDENTIFIER ::= { gandalf 3 }
gandalf-2590                OBJECT IDENTIFIER ::= { gandalf 4 }
gandalf-wanNode             OBJECT IDENTIFIER ::= { gandalf 5 }
gandalf-products            OBJECT IDENTIFIER ::= { gandalf 6 }
gandalf-nms                 OBJECT IDENTIFIER ::= { gandalf 7 }
gandalf-wanProxy            OBJECT IDENTIFIER ::= { gandalf 8 }
gandalf-rlanisdn            OBJECT IDENTIFIER ::= { gandalf 9 }
gandalf-termserver          OBJECT IDENTIFIER ::= { gandalf 10 }
gandalf-router              OBJECT IDENTIFIER ::= { gandalf 11 }

-- this group is provided solely for internal use
gandalf-experimental        OBJECT IDENTIFIER ::= { gandalf 12 }

--
--   Preliminary Draft                (September 1990)  HM #90/89
--   IEEE 802.3 Hub Management MIB
--
-- groups from the Hub MIB

hmBasicCapability           OBJECT IDENTIFIER ::= { gandalf-hub 1 }
hmSelfTestCapability        OBJECT IDENTIFIER ::= { gandalf-hub 2 }
hmPerfMonCapability         OBJECT IDENTIFIER ::= { gandalf-hub 3 }
hmAddrTrackCapability       OBJECT IDENTIFIER ::= { gandalf-hub 4 }


--
--
-- groups from the Bridge MIB
 
bridgeConfigObject            OBJECT IDENTIFIER ::= { gandalf-bridge 1 }
bridgeTpObject                OBJECT IDENTIFIER ::= { gandalf-bridge 2 }
bridgeStpObject               OBJECT IDENTIFIER ::= { gandalf-bridge 3 }
bridgeStaticObject            OBJECT IDENTIFIER ::= { gandalf-bridge 4 }
wanPhysicalObject             OBJECT IDENTIFIER ::= { gandalf-bridge 5 }
ieee8023Object                OBJECT IDENTIFIER ::= { gandalf-bridge 6 }

 
-- generic groups for all Gandalf products

gandalfLog                  OBJECT IDENTIFIER ::= { gandalf-generic 1 }
snmpAdminCapability         OBJECT IDENTIFIER ::= { gandalf-generic 2 }

-- values returned for the MIB II sysObjectID property
-- by Gandalf products. Newer sysObjectIds are incorporated into
-- this MIB. The other sysObjectIds are listed below.
 
-- WAN equipment
gProd-wan               OBJECT IDENTIFIER ::= { gandalf-products 1 }
gProxy                  OBJECT IDENTIFIER ::= { gProd-wan 1 }
g2300                   OBJECT IDENTIFIER ::= { gProd-wan 2 }
g2050                   OBJECT IDENTIFIER ::= { gProd-wan 3 }
 
-- Hubs
gProd-hub               OBJECT IDENTIFIER ::= { gandalf-products 2 }
ecm1000                 OBJECT IDENTIFIER ::= { gProd-hub 1 }
rsc9000                 OBJECT IDENTIFIER ::= { gProd-hub 3 }
 
-- Bridges
gProd-bridge            OBJECT IDENTIFIER ::= { gandalf-products 3 }
lanline5220L            OBJECT IDENTIFIER ::= { gProd-bridge 2 }
xbr6202                 OBJECT IDENTIFIER ::= { gProd-bridge 3 }
lanline5220e            OBJECT IDENTIFIER ::= { gProd-bridge 4 }
lanline5225i            OBJECT IDENTIFIER ::= { gProd-bridge 5 }
lanline5240i            OBJECT IDENTIFIER ::= { gProd-bridge 6 }
xbr6204                 OBJECT IDENTIFIER ::= { gProd-bridge 7 }
lanline5221             OBJECT IDENTIFIER ::= { gProd-bridge 8 }
lanline5242             OBJECT IDENTIFIER ::= { gProd-bridge 9 }

 
-- Gateways
gProd-gateway           OBJECT IDENTIFIER ::= { gandalf-products 4 }
wgm2590-hub             OBJECT IDENTIFIER ::= { gProd-gateway 1 }
wgm2590-standalone      OBJECT IDENTIFIER ::= { gProd-gateway 2 }
 
-- Termservers
gProd-termserver        OBJECT IDENTIFIER ::= { gandalf-products 5 }
gts1000                 OBJECT IDENTIFIER ::= { gProd-termserver 1 }
gtsplus                 OBJECT IDENTIFIER ::= { gProd-termserver 2 }
 
-- Routers
gProd-router            OBJECT IDENTIFIER ::= { gandalf-products 6 }
lanline5250i            OBJECT IDENTIFIER ::= { gProd-router 5 }
-- don't want to use 6 for obvious reasons :)
lanline5250L            OBJECT IDENTIFIER ::= { gProd-router 7 }
lanline5242er            OBJECT IDENTIFIER ::= { gProd-router 8}
lanline5250fr            OBJECT IDENTIFIER ::= { gProd-router 9 }
xpressway5250isdn-typ1	OBJECT IDENTIFIER ::= { gProd-router 10 }
xpressway5250isdn-typ2 	OBJECT IDENTIFIER ::= { gProd-router 11 }



-- Other sysObjectIds
-- ==================

-- ACC2120 1.3.6.1.4.1.5.1.1.1.1.1.11.7  
--       Note: the last digit is the rev. of the agent software.
-- AR74XX  1.3.6.1.4.1.1.1.1.41    
--       Note: proXfaceGenericType.2 == csl(26) => AR7220
--             proXfaceGenericType.2 == ether(25) => AR7420
--             proXfaceGenericType.2 == token(26) => AR7422
-- EBM6000 1.3.6.1.4.1.64    
--       Note: bridgeNumOfInterfaces == 4 => EBR6200
--             bridgeNumOfInterfaces == 2 => EBL64X0
-- ECM1000 1.3.6.1.4.1.64.1  
--       Note: hubCardCapacity == 3  => hub 48
--             hubCardCapacity == 10 => hub 132
--             any other value signifies a split hub 132.
-- GTS1000 1.3.6.1.4.1.85
-- ll5240  1.3.6.1.4.1.64    
--       Note: 
--             bridgeNumOfInterfaces == 4 => local strap
--             bridgeNumOfInterfaces == 2 => remote strap
-- WGM2590 1.3.6.1.4.1.64.4  
-- PPM8000 (Xpressway VLS/Prism) 1.3.6.1.4.1.97.1.1  
--
--
--                    GANDALF'S   HUB  SPECIFIC  GROUPS
--                    =================================
--
--  Basic Capability Group 
--
--

hubBasicID OBJECT-TYPE                                        
    SYNTAX OCTET STRING (SIZE(6))
    ACCESS read-only                            
    STATUS mandatory           
    DESCRIPTION
        "A 48-bit unique identifier, the hub ethernet address is used."
    ::= { hmBasicCapability 1 }   

hubCardCapacity OBJECT-TYPE
    SYNTAX INTEGER 
    ACCESS read-only                            
    STATUS mandatory          
    DESCRIPTION
        "The number of groups (cards) that can be contained within the hub."
    ::= { hmBasicCapability 2 }    

hubCardMap OBJECT-TYPE
    SYNTAX OCTET STRING (SIZE (32))
    ACCESS read-only                           
    STATUS mandatory         
    DESCRIPTION
        "A string of bits which reflects the current configuration of units
         which are viewed by the Group managed objects. The length of the
         bitstring is hubGroupCapacity bits. The LSBit relates to the unit
         viewed by group 1. A '1' in the bitstring indicates presence of the
         unit, '0' represent absence of the unit."
    ::= { hmBasicCapability 3 }

hubNumOfRelays OBJECT-TYPE
    SYNTAX INTEGER
    ACCESS read-only                           
    STATUS mandatory        
    DESCRIPTION
        "Shows the number of relays present without regard as to whether
         or not each is enabled or disabled."
    ::= { hmBasicCapability 4 }

hubRelayActive OBJECT-TYPE
    SYNTAX INTEGER
    ACCESS read-only                           
    STATUS mandatory       
    DESCRIPTION
        "An integer that indicates which relay is active.  Zero indicates
         that no relays are active."
    ::= { hmBasicCapability 5 }

hubResourceType OBJECT-TYPE
    SYNTAX INTEGER
    ACCESS read-only      
    STATUS mandatory     
    DESCRIPTION
        "An integer value representing the IEEE802 Standard that applies
         to this resource."
    ::= { hmBasicCapability 6 }
--
hubStandardRevision OBJECT-TYPE
    SYNTAX INTEGER
    ACCESS read-only          
    STATUS mandatory         
    DESCRIPTION
        "An integer value representing the revision of the IEEE802 Standard
         to which the station conforms with respect to that resource."
    ::= { hmBasicCapability 7 }

hubIEEE8023LmeOptions OBJECT-TYPE
    SYNTAX OCTET STRING (SIZE (32))
    ACCESS read-only        
    STATUS mandatory       
    DESCRIPTION
        "A set of option indicators, each of which, if present, indicates
         that a particular option within NM_LME is supported.  Its
         interpretation is specified in the appropriate standard."
    ::= { hmBasicCapability 8 }

hubManID OBJECT-TYPE
    SYNTAX OCTET STRING (SIZE (3))
    ACCESS read-only      
    STATUS mandatory     
    DESCRIPTION
        "A 24 bit value that identifies the manufacturer."
    ::= { hmBasicCapability 9 }
 
hubManProductID OBJECT-TYPE
    SYNTAX OCTET STRING (SIZE (32))
    ACCESS read-only    
    STATUS mandatory   
    DESCRIPTION
        "A manufacturer-defined product identifier."
    ::= { hmBasicCapability 10 }

 hubManProductVersion OBJECT-TYPE
    SYNTAX OCTET STRING (SIZE (32))
    ACCESS read-only  
    STATUS mandatory 
    DESCRIPTION
        "A manufacturer-defined product revision designation."
    ::= { hmBasicCapability 11 }

hubManTelephoneNum OBJECT-TYPE
    SYNTAX OCTET STRING (SIZE (33))
    ACCESS read-write
    STATUS mandatory    
    DESCRIPTION
        "An ascii representation of the manufacturer's telephone number."
    ::= { hmBasicCapability 12 }
--

hubName OBJECT-TYPE
    SYNTAX OCTET STRING (SIZE (32))
    ACCESS read-write                           
    STATUS mandatory   
    DESCRIPTION
        "This attribute is a text string up to 32 characters, of locally
         determined significance."
    ::= { hmBasicCapability 13 }

hubIPaddress OBJECT-TYPE
    SYNTAX NetworkAddress
    ACCESS read-only                           
    STATUS mandatory                      
    DESCRIPTION
        "This attribute contains the IP address of the hub."
    ::= { hmBasicCapability 14 }

hubEEpromRev OBJECT-TYPE
    SYNTAX OCTET STRING (SIZE (32))
    ACCESS read-only                           
    STATUS mandatory                     
    DESCRIPTION
        "This attribute provides the eeprom revision number and
         is read from the hardware."
    ::= { hmBasicCapability 15 }

hubSecureMode OBJECT-TYPE
    SYNTAX INTEGER {
         off(1),
         on(2)
    }
    ACCESS read-write         
    STATUS mandatory         
    DESCRIPTION
        "An integer value to set the hub in secure mode.  In secure mode
         all ports are disabled by default, otherwise ports are enabled
         by default upon creation."  
    ::= { hmBasicCapability 16 }

--
--
--  Basic Capability Group 
--
--  Basic Card Table                       
--
                                                
hmBasicCardTable OBJECT-TYPE
    SYNTAX SEQUENCE OF HmBasicCardEntry
    ACCESS not-accessible
    STATUS mandatory
    DESCRIPTION
        "This table provide a management view of the HUB
         configuration specific to individual cards."
    ::= { hmBasicCapability 17 }

hmBasicCardEntry OBJECT-TYPE
    SYNTAX HmBasicCardEntry
    ACCESS not-accessible
    STATUS mandatory
DESCRIPTION ""
    INDEX { gCardID }
    ::= { hmBasicCardTable 1 }

HmBasicCardEntry ::=
    SEQUENCE {
        gCardID
            INTEGER,
        gCardNumberOfPorts
            INTEGER,
        gCardName                   
            OCTET STRING,
        gCardType
            OCTET STRING,
        gCardRingNumberA
            INTEGER,
        gCardRingNumberB
            INTEGER,
        gCardIbmModeA
            INTEGER,
        gCardIbmModeB
            INTEGER,
        gCardRingSpeedA
            INTEGER,
        gCardRingSpeedB
            INTEGER
    }

gCardID OBJECT-TYPE
    SYNTAX INTEGER (1..255)
    ACCESS read-only                           
    STATUS mandatory              
    DESCRIPTION
        "An 8 bit value unique within the hub."
    ::= { hmBasicCardEntry 1 }

gCardNumberOfPorts OBJECT-TYPE
    SYNTAX INTEGER (1..255)
    ACCESS read-only                           
    STATUS mandatory             
    DESCRIPTION
        "This attribute contains the number of ports in the card object
         instance (MAC Entities)."
    ::= { hmBasicCardEntry 2 }

gCardName OBJECT-TYPE
    SYNTAX OCTET STRING (SIZE (32))          
    ACCESS read-write                           
    STATUS mandatory            
    DESCRIPTION
        "This attribute is a text string up to 32 characters, of locally
         determined significance."
    ::= { hmBasicCardEntry 3 }

gCardType OBJECT-TYPE
    SYNTAX OCTET STRING
    ACCESS read-only                           
    STATUS mandatory             
    DESCRIPTION
        "This attribute contains the type of card."
    ::= { hmBasicCardEntry 4 }

gCardRingNumberA OBJECT-TYPE
    SYNTAX INTEGER {
        ring1(1),
        ring2(2),
        ring3(3),
        ring4(4),
        standalone(5) 
    }
    ACCESS read-write
    STATUS mandatory
    DESCRIPTION
        "This attribute contains the Ring number associated with a UTP2112
         type of card, or with RI/RO set of ports 'A' for a STP4104 type of 
         card." 
    ::= { hmBasicCardEntry 5 }
 
gCardRingNumberB OBJECT-TYPE
    SYNTAX INTEGER {
        ring1(1),
        ring2(2),
        ring3(3),
        ring4(4),
        standalone(5)
    }
    ACCESS read-write
    STATUS mandatory
    DESCRIPTION
        "This attribute contains the Ring number associated with RI/RO set
         of ports 'B' for a STP4104 type of card."
    ::= { hmBasicCardEntry 6 }

gCardIbmModeA OBJECT-TYPE
    SYNTAX INTEGER {
        nonIbmMode(1),
        ibmMode(2)
    }
    ACCESS read-write
    STATUS mandatory
    DESCRIPTION
        "This attribute specifies wether RI/RO set of ports 'A' for a STP4104
         type of card is in IBM mode or normal mode."
    ::= { hmBasicCardEntry 7 }
  
gCardIbmModeB OBJECT-TYPE
    SYNTAX INTEGER {
        ibmMode(1),
        nonIbmMode(2)
    }
    ACCESS read-write
    STATUS mandatory
    DESCRIPTION
        "This attribute specifies wether RI/RO set of ports 'B' for a STP4104
         type of card is in IBM mode or normal mode."
    ::= { hmBasicCardEntry 8 }
  
gCardRingSpeedA OBJECT-TYPE
    SYNTAX INTEGER {
        fourMbps(4),
        sixteenMbps(16),
        unknown(255) 
    }
    ACCESS read-write
    STATUS mandatory
    DESCRIPTION
        "This attribute specifies wether RI/RO set of ports 'A' for a STP4104
         runs at 4 or 16 Mbps. It is also used to display the speed of a UTP2112
         type of cards."
    ::= { hmBasicCardEntry 9 }
  
gCardRingSpeedB OBJECT-TYPE
    SYNTAX INTEGER {
        fourMbps(4),
        sixteenMbps(16),
        unknown(255) 
    }
    ACCESS read-write
    STATUS mandatory
    DESCRIPTION
        "This attribute specifies wether RI/RO set of ports 'B' for a STP4104
         runs at 4 or 16 Mbps."
    ::= { hmBasicCardEntry 10 }
  
--
--
--  Basic Port Table                 
--

hmBasicPortTable OBJECT-TYPE
    SYNTAX SEQUENCE OF HmBasicPortEntry
    ACCESS not-accessible
    STATUS mandatory
    DESCRIPTION
        "This table provide a management view of the HUB
         configuration specific to individual ports."
    ::= { hmBasicCapability 18 }

hmBasicPortEntry OBJECT-TYPE
    SYNTAX HmBasicPortEntry
    ACCESS not-accessible
    STATUS mandatory
DESCRIPTION ""
    INDEX { gCardBasicID,
            gPortID
    }
    ::= { hmBasicPortTable 1 }

HmBasicPortEntry ::=
    SEQUENCE {
        gCardBasicID
            INTEGER,
        gPortID
            INTEGER,
        gPortType
            INTEGER,
        gPortAdminState
            INTEGER,
        gPortAutoPartitionState
            INTEGER,
        gPortName 
            OCTET STRING, 
        gPortEffectiveState        
            INTEGER,
        gPortConfiguration         
            INTEGER,
        gPortRedundantPort
            INTEGER,
        gPortRedundantCard
            INTEGER,
        gPortLinkStatus
            INTEGER
    }

gCardBasicID OBJECT-TYPE
    SYNTAX INTEGER (1..255)
    ACCESS read-only                           
    STATUS mandatory            
    DESCRIPTION
        "An 8 bit value unique within the hub."
    ::= { hmBasicPortEntry 1 }

gPortID OBJECT-TYPE
    SYNTAX INTEGER (1..255)
    ACCESS read-only           
    STATUS mandatory          
    DESCRIPTION
        "An 8 bit value unique in the group."
    ::= { hmBasicPortEntry 2 }

gPortType OBJECT-TYPE
    SYNTAX INTEGER {
         aui(1),
         bnc(2),
         rj45(3),
         rj71(4),
         thin(5),
         st(6),
         fsma(7),
         other(8)
    }
    ACCESS read-only         
    STATUS mandatory        
    DESCRIPTION
        "Port connector type."
    ::= { hmBasicPortEntry 3 }

gPortAdminState OBJECT-TYPE
    SYNTAX INTEGER {
        other(1),
        disabled(2),
        enabled(3)
    }
    ACCESS read-write                     
    STATUS mandatory                    
    DESCRIPTION
        "Indicates whether the port is enabled or disabled.  A disabled port
         neither transmit nor receives."
    ::= { hmBasicPortEntry 4 }    

gPortAutoPartitionState OBJECT-TYPE
    SYNTAX INTEGER {
        other(1),
        nonAutoPartitioned(2),
        autoPartitioned(3)
    }
    ACCESS read-only                   
    STATUS mandatory                  
    DESCRIPTION
        "Indicates whether the port is currently partitioned by the hub's
         auto-partition protection."
    ::= { hmBasicPortEntry 5 }

gPortName OBJECT-TYPE
    SYNTAX OCTET STRING (SIZE(32))
    ACCESS read-write                 
    STATUS mandatory                
    DESCRIPTION
        "This attribute is a text string up to 32 characters, of locally
         determined significance."
    ::= { hmBasicPortEntry 6 }

gPortEffectiveState OBJECT-TYPE
    SYNTAX INTEGER {
        enabled(1),
        disabled(2),
        masterReady(3),
        masterActive(4),
        masterFaulty(5),
        masterDisabled(6),
        standbyReady(7),
        standbyActive(8),
        standbyFaulty(9),
        standbyDisabled(10)
    }
    ACCESS read-only                           
    STATUS mandatory            
    DESCRIPTION
        "Indicates redundant port's effective state."
    ::= { hmBasicPortEntry 7 }

gPortConfiguration OBJECT-TYPE
    SYNTAX INTEGER {
        nonRedundant(1),
        master(2),
        standby(3)
    }
    ACCESS read-only                           
    STATUS mandatory            
    DESCRIPTION
        "Indicates port's redundant configuration status."
    ::= { hmBasicPortEntry 8 }

gPortRedundantPort OBJECT-TYPE
    SYNTAX INTEGER (1..255)
    ACCESS read-write
    STATUS mandatory
    DESCRIPTION
        "Indicates redundant port's port number."
    ::= { hmBasicPortEntry 9 }

gPortRedundantCard OBJECT-TYPE
    SYNTAX INTEGER (1..255)
    ACCESS read-write
    STATUS mandatory
    DESCRIPTION
        "Indicates redundant port's card number."
    ::= { hmBasicPortEntry 10 }
 
gPortLinkStatus OBJECT-TYPE
    SYNTAX INTEGER {
        linkUp(1),
        linkDown(2)
    }
    ACCESS read-only                           
    STATUS mandatory            
    DESCRIPTION
        "Indicates port's link integrity status."
    ::= { hmBasicPortEntry 11 }

 
-- 
--
--  Self Test Capability Group    
--

hubSelfTestID OBJECT-TYPE
    SYNTAX  OCTET STRING (SIZE(6))
    ACCESS  read-only                   
    STATUS  mandatory                  
    DESCRIPTION
        "A 48-bit unique identifier, the hub ethernet address is used."
    ::= { hmSelfTestCapability 1 }

hubTimeSinceReset OBJECT-TYPE   
    SYNTAX  TimeTicks
    ACCESS  read-only          
    STATUS  mandatory         
    DESCRIPTION
        "The time in tens of milliseconds since the  last time that
         the system was reset.  This counter has a value of 0 when
         initialized."
    ::= { hmSelfTestCapability 2 }

hubResetTimeStamp OBJECT-TYPE
    SYNTAX  TimeTicks
    ACCESS  read-only        
    STATUS  mandatory       
    DESCRIPTION
        "Not a counter, this attribute provides the value of hubTimeSinceReset
         when the hub was last reset."
    ::= { hmSelfTestCapability 3 }

hubHealthState OBJECT-TYPE
    SYNTAX  INTEGER {
        other(1),
        ok(2),
        failed(3)
    }
    ACCESS  read-only     
    STATUS  mandatory      
    DESCRIPTION
        "This attribute will store the results of the startup
         diagnostics.  The first octet indicates the overall results
         of the startup tests, while the remaining 8 octets will
         contain the results of the individual test.  Each octet
         will contain a 1 if the test was passed, 2 if the test failed.
         The following list defines the meanings of each octet in
         the string:  Octet 1 - overall test result
                      Octet 2 - system NMI test
                      Octet 3 - system timers test
                      Octet 4 - system DMA test
                      Octet 5 - 82586 test
                      Octet 6 - backplane ethernet address test
                      Octet 7 - NVRAM test
                      Octet 8 - dual port RAM test
                      Octet 9 - real time clock test"
    ::= { hmSelfTestCapability 4 }   

hubHealthText OBJECT-TYPE
    SYNTAX  DisplayString (SIZE (0..255))
    ACCESS  read-only             
    STATUS  mandatory            
    DESCRIPTION
        "This attribute provides a textual description of which test,
         if any, failed during diagnostics."
    ::= { hmSelfTestCapability 5 }
                               
hubHealthData OBJECT-TYPE
    SYNTAX  OCTET STRING (SIZE (0..255))
    ACCESS  read-only         
    STATUS  mandatory        
    DESCRIPTION
        "This attribute provides a textual description of which test,
         if any, failed during diagnostics."
    ::= { hmSelfTestCapability 6 } 

hubSystemResetting OBJECT-TYPE
    SYNTAX  INTEGER {
        notResetting(1),
        resetting(2)
    }
    ACCESS  read-only        
    STATUS  mandatory                         
    DESCRIPTION
        "Indicates whether the hub is in the process of resetting 
         completely (coldstart)."
    ::= { hmSelfTestCapability 7 }

hubResetting OBJECT-TYPE
    SYNTAX  INTEGER {
        notResetting(1),
        resetting(2)
    }
    ACCESS  read-only       
    STATUS  mandatory                       
    DESCRIPTION
        "Indicates whether the hub is in the process of resetting
         or not (warmstart)."
    ::= { hmSelfTestCapability 8 }

hubExecutingSelfTest OBJECT-TYPE
    SYNTAX  INTEGER {
        notSelfTesting(1),
        selfTesting(2)
    }
    ACCESS  read-only      
    STATUS  mandatory                         
    DESCRIPTION
        "Indicates whether the hub is in the process of executing
         self diagnostics."
    ::= { hmSelfTestCapability 9 }

hubResetAction OBJECT-TYPE
    SYNTAX  INTEGER {
        noreset(1),
        reset(2)
    }
    ACCESS  read-write      
    STATUS  mandatory                         
    DESCRIPTION
        "Restart the hub if selecting reset."
    ::= { hmSelfTestCapability 10 }

--
--
--  Performance Monitoring Capability Group
--

--
--   Performance Monitoring Relay Table   
--

hmPerfMonRelayTable OBJECT-TYPE
    SYNTAX SEQUENCE OF HmPerfMonRelayEntry
    ACCESS not-accessible
    STATUS mandatory
    DESCRIPTION
        "This table provide a management view individual
         relay performance capability."
    ::= { hmPerfMonCapability 1 }

hmPerfMonRelayEntry OBJECT-TYPE
    SYNTAX  HmPerfMonRelayEntry
    ACCESS  not-accessible
    STATUS  mandatory
DESCRIPTION ""
    INDEX { relayPerfID }
    ::= { hmPerfMonRelayTable 1 }

HmPerfMonRelayEntry ::= SEQUENCE {
    relayPerfID
        INTEGER,
    relayTotalCollisions
        Counter
}
relayPerfID OBJECT-TYPE
    SYNTAX  INTEGER (1..4)
    ACCESS  read-only                   
    STATUS  mandatory                  
    DESCRIPTION
        "This attribute is the value used in addressing the relay."
    ::= { hmPerfMonRelayEntry 1 }

relayTotalCollisions OBJECT-TYPE
    SYNTAX  Counter
    ACCESS  read-only                
    STATUS  mandatory               
    DESCRIPTION
        "The counter is incremented every time the hub enters a condition
         caused by simultaneous transmission and detection of external
         activity on one or more of its ports."
    ::= { hmPerfMonRelayEntry 2 }

--
--   Performance Monitoring Port Table      
--

hmPerfMonPortTable OBJECT-TYPE
    SYNTAX SEQUENCE OF HmPerfMonPortEntry
    ACCESS not-accessible
    STATUS mandatory
    DESCRIPTION
        "This table provide a management view of individual
         ports performance capability."
    ::= { hmPerfMonCapability 2 }

hmPerfMonPortEntry OBJECT-TYPE
    SYNTAX  HmPerfMonPortEntry
    ACCESS  not-accessible
    STATUS  mandatory
DESCRIPTION ""
    INDEX { gCardPerfID,
            gPortPerfID
    }
    ::= { hmPerfMonPortTable 1 }

HmPerfMonPortEntry ::= SEQUENCE {
    gCardPerfID
        INTEGER,
    gPortPerfID
        INTEGER,
    gPortReadableFrames
        Counter,
    gPortReadableOctets
        Counter,
    gPortPygmys
        Counter,
    gPortRunts
        Counter,
    gPortFrameCheckSeqErrs
        Counter,
    gPortAlignmentErrors
        Counter,
    gPortFramesTooLong
        Counter,
    gPortAutoPartitionCount
        Counter,
    gPortLateCollisions      
        Counter,
    gPortCollisions         
        Counter,
    gPortAlarms            
        Counter,
    gPortMulticastFrames  
        Counter,
    gPortBroadcastFrames 
        Counter
}

--

gCardPerfID OBJECT-TYPE
    SYNTAX  INTEGER (1..255)
    ACCESS  read-only              
    STATUS  mandatory             
    DESCRIPTION
        "This attribute represent the card number and is used to address
         the performance monitoring table."
    ::= { hmPerfMonPortEntry 1 }
  
gPortPerfID OBJECT-TYPE
    SYNTAX  INTEGER (1..255)
    ACCESS  read-only            
    STATUS  mandatory           
    DESCRIPTION
        "This attribute represent the port number and is used to address
         the performance monitoring table."
    ::= { hmPerfMonPortEntry 2 }

gPortReadableFrames OBJECT-TYPE
    SYNTAX  Counter
    ACCESS  read-only          
    STATUS  mandatory         
    DESCRIPTION
        "A representation of the total frames of legal length that have not
         been corrupted in transmission counted by the port object."
    ::= { hmPerfMonPortEntry 3 }

gPortReadableOctets OBJECT-TYPE
    SYNTAX  Counter
    ACCESS  read-only        
    STATUS  mandatory       
    DESCRIPTION
        "It is sum of data and padding octets contained in ReadableFrames
         counted by the port object."
    ::= { hmPerfMonPortEntry 4 }
 
gPortPygmys OBJECT-TYPE
    SYNTAX  Counter
    ACCESS  read-only      
    STATUS  mandatory     
    DESCRIPTION
        "The sum of pygmy frame fragments counted by the port object. 
         They occur when a frame fragment was received which was not in 
         collision and was not recognized as a valid ethernet packet. 
         They normally make up less than 5% of Rx frames on hub-to-hub 
         or hub-to-backbone connections and < 1% of total Rx frames for hub-DTE
         connections. Significantly higher levels may indicate external noise
         hits on the cabling, i.e. UTP in a noisy environment."
    ::= { hmPerfMonPortEntry 5 }
 
gPortRunts OBJECT-TYPE
    SYNTAX  Counter
    ACCESS  read-only    
    STATUS  mandatory   
    DESCRIPTION
        "The sum of frames which were received then collided with 
         another fram(e)s received by the hub. The port(s) which 
         receive the collider frame(s) will increment their 
         gPortCollisions and the port which was collided with
         will increment this counter. It is possible to
         count more runts than collisions for a specific port.
         As a rough guideline, less than 5% of the Rx frames 
         should be runts."
    ::= { hmPerfMonPortEntry 6 }

gPortFrameCheckSeqErrs OBJECT-TYPE
    SYNTAX  Counter
    ACCESS  read-only  
    STATUS  mandatory 
    DESCRIPTION
        "The sum of frames received on this port that are an integral
         number of octets in length and do not pass the FCS check. 
         Normally less than 1% of Rx frames. Could be caused by line
         noise, loose connections, a faulty DTE, or a faulty hub."
    ::= { hmPerfMonPortEntry 7 }

--

gPortAlignmentErrors OBJECT-TYPE
    SYNTAX  Counter
    ACCESS  read-only
    STATUS  mandatory                 
    DESCRIPTION
        "The sum of frames received on this port that are not an 
         integral number of octets in length. Should be less than
         1% of the total number of Rx frames and greater than or
         equal to gPortFramesTooLong and gPortFrameCheckSeqErrors. 
         Could be caused by line noise, loose connections, a faulty 
         DTE, or a faulty hub. "
    ::= { hmPerfMonPortEntry 8 }

gPortFramesTooLong OBJECT-TYPE
    SYNTAX  Counter
    ACCESS  read-only                
    STATUS  mandatory               
    DESCRIPTION
        "The sum of frames received on this port that are more than
         1518 octets long. Should be < 1% of the total number of Rx 
         frames. Could be caused by a faulty DTE or a faulty hub."
    ::= { hmPerfMonPortEntry 9 }
 
gPortAutoPartitionCount OBJECT-TYPE
    SYNTAX  Counter
    ACCESS  read-only              
    STATUS  mandatory             
    DESCRIPTION
        "It is the number of times that this port has been automatically
         partitioned."
    ::= { hmPerfMonPortEntry 10 }
 
gPortLateCollisions OBJECT-TYPE   
    SYNTAX  Counter
    ACCESS  read-only           
    STATUS  mandatory          
    DESCRIPTION
        "This attribute is the total number of late collisions experienced
         by the port object. Usually indicates a DTE trying to Tx w/o
         checking the Ethernet for traffic first. May be due to a
         hardware fault on the sending DTE, or a segment which is too long 
         for collision detection to work properly. Should normally be < 1% 
         of total Rx frames."
    ::= { hmPerfMonPortEntry 11 }

gPortCollisions OBJECT-TYPE    
    SYNTAX  Counter
    ACCESS  read-only        
    STATUS  mandatory       
    DESCRIPTION
        "This attribute provides the total number of collisions encountered
         by the port object. The port that was collided with will count a
         runt. Normally less than 5% of the Rx frames should be collisions.
         Numbers significantly higher than this may indicate hardware
         problems or congestion."
    ::= { hmPerfMonPortEntry 12 }

gPortAlarms OBJECT-TYPE      
    SYNTAX  Counter
    ACCESS  read-only      
    STATUS  mandatory     
    DESCRIPTION
        "The number of times a threshold was exceeded on that port."
    ::= { hmPerfMonPortEntry 13 }

gPortMulticastFrames OBJECT-TYPE    
    SYNTAX  Counter
    ACCESS  read-only             
    STATUS  mandatory            
    DESCRIPTION
        "This attribute contains a count of frames successfully received
         by the port and are directed to an active non-broadcast group of
         addresses."
    ::= { hmPerfMonPortEntry 14 }

--

gPortBroadcastFrames OBJECT-TYPE 
    SYNTAX  Counter
    ACCESS  read-only          
    STATUS  mandatory         
    DESCRIPTION
        "This attribute contains the total number of broadcast frames
         received by the port object since system restart."
    ::= { hmPerfMonPortEntry 15 }

--
--
--  Address Tracking Capability Group   
--
--
--
--  Address Tracking Port Table
--

hmAddrTrackPortTable OBJECT-TYPE
    SYNTAX SEQUENCE OF HmAddrTrackPortEntry
    ACCESS not-accessible
    STATUS mandatory
    DESCRIPTION
        "This table provide a management view of individual
         port address tracking capability."
    ::= { hmAddrTrackCapability 1 }

hmAddrTrackPortEntry OBJECT-TYPE
    SYNTAX  HmAddrTrackPortEntry
    ACCESS  not-accessible
    STATUS  mandatory
DESCRIPTION ""
    INDEX { gCardAddrID,
            gPortAddrID
    }
    ::= { hmAddrTrackPortTable 1 }

HmAddrTrackPortEntry ::= SEQUENCE {
    gCardAddrID
        INTEGER,
    gPortAddrID
        INTEGER,
    gPortLastSourceAddress
        OCTET STRING,
    gPortSourceAddrChanges
        Counter
}

gCardAddrID OBJECT-TYPE
    SYNTAX  INTEGER  (1..255)                  
    ACCESS  read-only                     
    STATUS  mandatory                    
    DESCRIPTION
        "An 8 bit value unique within the hub."
    ::= { hmAddrTrackPortEntry 1 }

gPortAddrID OBJECT-TYPE
    SYNTAX  INTEGER (1..255)
    ACCESS  read-only                   
    STATUS  mandatory                  
    DESCRIPTION
        "An 8 bit value unique within the group."
    ::= { hmAddrTrackPortEntry 2 }

--

gPortLastSourceAddress OBJECT-TYPE
    SYNTAX  OCTET STRING (SIZE(6))
    ACCESS  read-only                 
    STATUS  mandatory                
    DESCRIPTION
        "The source (ethernet) address of the last ReadableFrame
         received by this port."
    ::= { hmAddrTrackPortEntry 3 }

gPortSourceAddrChanges OBJECT-TYPE
    SYNTAX  Counter
    ACCESS  read-only               
    STATUS  mandatory              
    DESCRIPTION
        "This attribute counts the number of times the last source
         address has changed."
    ::= { hmAddrTrackPortEntry 4 }

 
-- 
--                    GANDALF'S   BRIDGE  SPECIFIC  GROUPS
--                    =====================================
--
-- N.B. many of the attributes derived from dot1d have been
--      deprecated. Agents do not need to support them. New
--      agents should use the equivalents (as noted below) in 
--      RFC1286.
--

-- the Bridge Configuration group
 
          bridgeBaseAddress OBJECT-TYPE
              SYNTAX  OCTET STRING
              ACCESS  read-only
              STATUS  mandatory
              DESCRIPTION
                      "The MAC address used by this bridge when it must
                      be referred to in a unique fashion.   It is
                      recommended that this be the numerically smallest
                      MAC address of all ports that belong to this
                      bridge.  However it is only required to be unique."
          ::= { bridgeConfigObject 1 }
 
          bridgeNumPorts OBJECT-TYPE
              SYNTAX  INTEGER
              ACCESS  read-only
              STATUS  mandatory
              DESCRIPTION
                      "The number of (logical) ports controlled by this 
                      bridging entity."
          ::= { bridgeConfigObject 2 }
 
 
          bridgeType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated by
                      entries in the port table for the given type."
          ::= { bridgeConfigObject 3 }
 
  
 
          bridgeNumOfInterfaces OBJECT-TYPE
              SYNTAX  INTEGER
              ACCESS  read-only
              STATUS  mandatory
              DESCRIPTION
                      "The number of interfaces controlled by this bridging
                      entity, the interface stats are managed by MIB II
                      interface group."
          ::= { bridgeConfigObject 4 }
 
--
           bridgePowerUpStatus OBJECT-TYPE
               SYNTAX  INTEGER {
                   other(1),
                   ok(2),
                   failed(3)
               }
               ACCESS read-only
               STATUS mandatory
               DESCRIPTION
                   "This attribute contains the result of any non fatal hardware
                    diagnostics performed during the power on procedure."
               ::= { bridgeConfigObject 5 }
            
           bridgeIpAddr OBJECT-TYPE
               SYNTAX NetworkAddress
               ACCESS read-only
               STATUS mandatory
               DESCRIPTION
                   "This attribute contains the IP address of the bridge."
               ::= { bridgeConfigObject 6 }
            
           bridgeManID OBJECT-TYPE
               SYNTAX OCTET STRING
               ACCESS read-only
               STATUS mandatory
               DESCRIPTION
                   "This is a 24 bit value that identifies the manufacturer."
               ::= { bridgeConfigObject 7 }
            
           bridgeManProductVersion OBJECT-TYPE
               SYNTAX OCTET STRING
               ACCESS read-only
               STATUS mandatory
               DESCRIPTION
                   "This attribute provides the software revision number."
               ::= { bridgeConfigObject 8 }
            
           bridgeEEpromRev OBJECT-TYPE
               SYNTAX OCTET STRING
               ACCESS read-only
               STATUS mandatory
               DESCRIPTION
                   "This attribute provides the eeprom revision number and
                    is read from the hardware."
               ::= { bridgeConfigObject 9 }
           
           bridgeSerialNum OBJECT-TYPE
               SYNTAX OCTET STRING 
               ACCESS read-only
               STATUS mandatory
               DESCRIPTION
                   "This attribute provides the EBM Serial Number and
                    is read from the hardware."
               ::= { bridgeConfigObject 10 }

           bridgeHubChassis OBJECT-TYPE
               SYNTAX OCTET STRING 
               ACCESS read-only
               STATUS mandatory
               DESCRIPTION
                   "This attribute provides information on the type of
                    Hub Chassis this bridge is currently using."
               ::= { bridgeConfigObject 11 }
            
--            
--  The Transparent Object group
--
--  Filtering Information for a Transparent Bridge
--
          filterDatabaseSize OBJECT-TYPE
              SYNTAX INTEGER
              ACCESS read-only
              STATUS mandatory
              DESCRIPTION
                   "This attribute represents the number of entries
                    into the filtering database."
              ::= { bridgeTpObject 1 }

          numberOfDynamicEntries OBJECT-TYPE
              SYNTAX INTEGER
              ACCESS read-only
              STATUS mandatory
              DESCRIPTION
                   "This attribute contains a number of dynamic entries
                    currently in the Filtering Database."
              ::= { bridgeTpObject 2 }

           numberOfStaticEntries OBJECT-TYPE
              SYNTAX INTEGER
              ACCESS read-only
              STATUS mandatory
              DESCRIPTION
                      "This attribute contains a number of static entries
                      currently in the Filtering Database."
              ::= { bridgeTpObject 3 }


          agingState OBJECT-TYPE
              SYNTAX INTEGER {
                  off(1),
                  on(2)
              }
              ACCESS read-only                           
              STATUS mandatory       
              DESCRIPTION
                   "When this attribute is ON, the Bridge will age dynamic station 
                    entries from the filter table automatically."
              ::= { bridgeTpObject 4 }

          agingTime OBJECT-TYPE
              SYNTAX   INTEGER
              ACCESS   read-only
              STATUS   mandatory
              DESCRIPTION
                      "The timeout period in seconds for aging out
                      dynamically learned forwarding information."
              ::= { bridgeTpObject 5 }


           learningState OBJECT-TYPE
               SYNTAX INTEGER {
                  off(1),
                  on(2)
               }
               ACCESS read-only                           
               STATUS mandatory       
               DESCRIPTION
                   "When this attribute is ON, the Bridge will learn LAN station
                    addresses automatically."
               ::= { bridgeTpObject 6 }

           protocolFilterState OBJECT-TYPE
               SYNTAX INTEGER {
                  off(1),
                  on(2)
               }
               ACCESS read-only                           
               STATUS mandatory       
               DESCRIPTION
                   "This attribute specifies whether protocol filtering is enabled or
                    disabled."
               ::= { bridgeTpObject 7 }

           broadcastForwardingState OBJECT-TYPE
               SYNTAX INTEGER {
                  off(1),
                  on(2)
               }
               ACCESS read-only                           
               STATUS mandatory       
               DESCRIPTION
                   "This attribute specifies whether broadcast frames are being
                    forwarded."
               ::= { bridgeTpObject 8 }

             multicastForwardingState OBJECT-TYPE
               SYNTAX INTEGER {
                  off(1),
                  on(2)
               }
               ACCESS read-only                           
               STATUS mandatory       
               DESCRIPTION
                    "This attribute specifies whether multicast frames
                     are being forwarded."
               ::= { bridgeTpObject 9 }

--
--  The Forwarding Database for Transparent Bridges

          bridgeTpFdbTable OBJECT-TYPE
              SYNTAX  SEQUENCE OF BridgeTpFdbEntry
              ACCESS  not-accessible
              STATUS  mandatory
              DESCRIPTION
                      "A table that contains information about unicast
                      entries for which the bridge has forwarding and/or
                      filtering information.  This information is used
                      by the transparent bridging function in
                      determining how to propagate a received frame."
               ::= { bridgeTpObject 10 }

          bridgeTpFdbEntry OBJECT-TYPE
              SYNTAX  BridgeTpFdbEntry
              ACCESS  not-accessible
              STATUS  mandatory
              DESCRIPTION
                      "Information about a specific unicast MAC address
                      for which the bridge has some forwarding and/or
                      filtering information."
              INDEX   { bridgeDot1dTpFdbAddress }
              ::= { bridgeTpFdbTable 1 }

          BridgeTpFdbEntry ::=
              SEQUENCE {
                  bridgeDot1dTpFdbAddress
                      PhysAddress,
                  bridgeDot1dTpFdbPort
                      INTEGER,
                  bridgeDot1dTpFdbStatus
                      INTEGER
              }

          bridgeDot1dTpFdbAddress OBJECT-TYPE
              SYNTAX  PhysAddress
              ACCESS  read-only
              STATUS  mandatory
              DESCRIPTION
                      "A unicast MAC address for which the bridge has
                      forwarding and/or filtering information."
              REFERENCE
                      "P802.1d/D9, July 14, 1989: Section 3.9.1, 3.9.2"
              ::= { bridgeTpFdbEntry 1 }

          bridgeDot1dTpFdbPort OBJECT-TYPE
              SYNTAX  INTEGER
              ACCESS  read-only
              STATUS  mandatory
              DESCRIPTION
                      "Either the value '0', or the port number of the
                      port on which a frame having a source address
                      equal to the value of the corresponding instance
                      of dot1dTpFdbAddress has been seen.  A value of
                      '0' indicates that the port number has not been
                      learned but that the bridge does have some
                      forwarding/filtering information about this
                      address (e.g. in the dot1dStaticTable).
                      Implementors are encouraged to assign the port
                      value to this object whenever it is learned even
                      for addresses for which the corresponding value of
                      dot1dTpFdbStatus is not learned(3)."
              ::= { bridgeTpFdbEntry 2 }

          bridgeDot1dTpFdbStatus OBJECT-TYPE
              SYNTAX  INTEGER {
                          other(1),
                          invalid(2),
                          learned(3),
                          self(4),
                          mgmt(5)
                      }
              ACCESS  read-only
              STATUS  mandatory
              DESCRIPTION
                      "The status of this entry.  The meanings of the
                      values are:

                        other(1)   : none of the following.  This would
                                     include the case where some other
                                     MIB object (not the corresponding
                                     instance of dot1dTpFdbPort, nor an
                                     entry in the dot1dStaticTable) is
                                     being used to determine if and how
                                     frames addressed to the value of
                                     the corresponding instance of
                                     dot1dTpFdbAddress are being
                                     forwarded.

                        invalid(2) : this entry is not longer valid
                                     (e.g., it was learned but has since
                                     aged-out), but has not yet been
                                     flushed from the table.

                        learned(3) : the value of the corresponding
                                     instance of dot1dTpFdbPort was
                                     learned, and is being used.

                        self(4)    : the value of the corresponding
                                     instance of dot1dTpFdbAddress
                                     represents one of the bridge's
                                     addresses.  The corresponding
                                     instance of dot1dTpFdbPort
                                     indicates which of the bridge's
                                     ports has this address.

                        mgmt(5)    : the value of the corresponding
                                     instance of dot1dTpFdbAddress is
                                     also the value of an existing
                                     instance of dot1dStaticAddress."
              ::= { bridgeTpFdbEntry 3 }


--
--  Logical Port Table for Transparent Bridges
--
--  replaced by the dot1dTpPortTable in RFC1286
--

          bridgeLogicalPortTable OBJECT-TYPE
              SYNTAX  SEQUENCE OF BridgeLogicalPortEntry
              ACCESS  not-accessible
              STATUS  deprecated
              DESCRIPTION
                      "A table that contains information about every
                      port that is associated with this transparent
                      bridge."
               ::= { bridgeTpObject 11 }

          bridgeLogicalPortEntry OBJECT-TYPE
              SYNTAX  BridgeLogicalPortEntry
              ACCESS  not-accessible
              STATUS  deprecated
              DESCRIPTION
                      "A list of information for each port of a
                      transparent bridge."
              INDEX   { bridgeDot1dTpPort }
              ::= { bridgeLogicalPortTable 1 }

          BridgeLogicalPortEntry ::=
              SEQUENCE {
                  bridgeDot1dTpPort
                      INTEGER,
                  bridgeDot1dTpPortMaxInfo
                      INTEGER,
                  bridgeDot1dTpPortInFrames
                      Counter,
                  bridgeDot1dTpPortOutFrames
                      Counter,
                  bridgeDot1dTpPortInDiscards
                      Counter
              }

          bridgeDot1dTpPort OBJECT-TYPE
              SYNTAX  INTEGER
              ACCESS  read-only
              STATUS  deprecated
              DESCRIPTION
                      "The port number of the port for which this entry
                      contains Transparent bridging management
                      information."
              ::= { bridgeLogicalPortEntry 1 }

          -- It would be nice if we could use ifMtu as the size of the
          -- largest INFO field, but we can't because ifMtu is defined
          -- to be the size that the (inter-)network layer can use which
          -- can differ from the MAC layer (especially if several layers
          -- of encapsulation are used).

          bridgeDot1dTpPortMaxInfo OBJECT-TYPE
              SYNTAX  INTEGER
              ACCESS  read-only
              STATUS  deprecated
              DESCRIPTION
                      "The maximum size of the INFO (non-MAC) field that
                      this port will receive or transmit."
              ::= { bridgeLogicalPortEntry 2 }

          bridgeDot1dTpPortInFrames OBJECT-TYPE
              SYNTAX  Counter
              ACCESS  read-only
              STATUS  deprecated
              DESCRIPTION
                      "The number of frames that have been received by
                      this port from its segment. Note that a frame
                      received on the interface corresponding to this
                      port is only counted by this object if and only if
                      it is for a protocol being processed by the local
                      bridging function."
              REFERENCE
                      "P802.1d/D9, July 14, 1989: Section 6.6.1.1.3"
              ::= { bridgeLogicalPortEntry 3 }

          bridgeDot1dTpPortOutFrames OBJECT-TYPE
              SYNTAX  Counter
              ACCESS  read-only
              STATUS  deprecated
              DESCRIPTION
                      "The number of frames that have been transmitted
                      by this port to its segment.  Note that a frame
                      transmitted on the interface corresponding to this
                      port is only counted by this object if and only if
                      it is for a protocol being processed by the local
                      bridging function."
              REFERENCE
                      "P802.1d/D9, July 14, 1989: Section 6.6.1.1.3"
              ::= { bridgeLogicalPortEntry 4 }

          bridgeDot1dTpPortInDiscards OBJECT-TYPE
              SYNTAX   Counter
              ACCESS   read-only
              STATUS   deprecated
              DESCRIPTION
                      "Count of valid frames received which were
                      discarded (i.e., filtered) by the Forwarding
                      Process."
              REFERENCE
                      "P802.1d/D9, July 14, 1989: Section 6.6.1.1.3"
              ::= { bridgeLogicalPortEntry 5 }
--
-- The Spanning Tree group

-- Implemented on all bridges that supports the Spanning Tree Protocol.
--
--  replaced by the dot1dStpProtocolSpecification in RFC1286
--


          bridgeDot1dStpProtocolSpecification OBJECT-TYPE
              SYNTAX  INTEGER {
                          unknown(1),
                          decLb100(2),
                          ieee8021d(3)
                      }
              ACCESS  read-only
              STATUS  deprecated
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { bridgeStpObject 1 }

          bridgeDot1dStpPriority OBJECT-TYPE
              SYNTAX  INTEGER (0..65535)
              ACCESS  read-only
              STATUS  deprecated
              DESCRIPTION
                      "The value of the write-able portion of the Bridge
                      ID, i.e., the first two octets of the (8 octet
                      long) Bridge ID.  The other (last) 6 octets of the
                      Bridge ID are given by the value of
                      dot1dBaseBridgeAddress."
              REFERENCE
                      "P802.1d/D9, July 14, 1989: Section 4.5.3.7"
              ::= { bridgeStpObject 2 }

          bridgeDot1dStpTimeSinceTopologyChange OBJECT-TYPE
              SYNTAX  TimeTicks
              ACCESS  read-only
              STATUS  deprecated
              DESCRIPTION
                      "The time (in hundredths of a second) since the
                      last time a topology change was detected by the
                      bridge entity."
              REFERENCE
                      "P802.1d/D9, July 14, 1989: Section 6.8.1.1.3"
              ::= { bridgeStpObject 3 }

          bridgeDot1dStpTopChanges OBJECT-TYPE
              SYNTAX  Counter
              ACCESS  read-only
              STATUS  deprecated
              DESCRIPTION
                      "The total number of topology changes detected by
                      this bridge since the management entity was last
                      reset or initialized."
              REFERENCE
                      "P802.1d/D9, July 14, 1989: Section 6.8.1.1.3"
              ::= { bridgeStpObject 4 }

          bridgeDot1dStpDesignatedRoot OBJECT-TYPE
              SYNTAX  OCTET STRING
              ACCESS  read-only
              STATUS  deprecated
              DESCRIPTION
                      "The bridge identifier of the root of the spanning
                      tree as determined by the Spanning Tree Protocol
                      as executed by this node.  This value is used as
                      the Root Identifier parameter in all Configuration
                      Bridge PDUs originated by this node."
              REFERENCE
                      "P802.1d/D9, July 14, 1989: Section 4.5.3.1"
              ::= { bridgeStpObject 5 }

          bridgeDot1dStpRootCost OBJECT-TYPE
              SYNTAX  INTEGER
              ACCESS  read-only
              STATUS  deprecated
              DESCRIPTION
                      "The cost of the path to the root as seen from
                      this bridge."
              REFERENCE
                      "P802.1d/D9, July 14, 1989: Section 4.5.3.2"
              ::= { bridgeStpObject 6 }

          bridgeDot1dStpRootPort OBJECT-TYPE
              SYNTAX  INTEGER
              ACCESS  read-only
              STATUS  deprecated
              DESCRIPTION
                      "The port number of the port which offers the
                      lowest cost path from this bridge to the root
                      bridge."
              REFERENCE
                      "P802.1d/D9, July 14, 1989: Section 4.5.3.3"
              ::= { bridgeStpObject 7 }



          bridgeDot1dStpMaxAge OBJECT-TYPE
              SYNTAX  INTEGER
              ACCESS  read-only
              STATUS  deprecated
              DESCRIPTION
                      "The maximum age of Spanning Tree Protocol
                      information learned from the network on any port
                      before it is discarded, in units of hundredths of
                      a second.  This is the actual value that this
                      bridge is currently using."
              REFERENCE
                      "P802.1d/D9, July 14, 1989: Section 4.5.3.4"
              ::= { bridgeStpObject 8 }

          bridgeDot1dStpHelloTime OBJECT-TYPE
              SYNTAX  INTEGER
              ACCESS  read-only
              STATUS  deprecated
              DESCRIPTION
                      "The amount of time between the transmission of
                      Configuration bridge PDUs by this node on any port
                      when it is the root of the spanning tree or trying
                      to become so, in units of hundredths of a second.
                      This is the actual value that this bridge is
                      currently using."
              REFERENCE
                      "P802.1d/D9, July 14, 1989: Section 4.5.3.5"
              ::= { bridgeStpObject 9 }

          bridgeDot1dStpHoldTime OBJECT-TYPE
              SYNTAX  INTEGER
              ACCESS  read-only
              STATUS  deprecated
              DESCRIPTION
                      "This time value determines the interval length
                      during which no more than two Configuration bridge
                      PDUs shall be transmitted by this node, in units
                      of hundredths of a second."
              REFERENCE
                      "P802.1d/D9, July 14, 1989: Section 4.5.3.14"
              ::= { bridgeStpObject 10 }

          bridgeDot1dStpForwardDelay OBJECT-TYPE
              SYNTAX  INTEGER
              ACCESS  read-only
              STATUS  deprecated
              DESCRIPTION
                      "This time value, measured in units of hundredths
                      of a second, controls how fast a port changes its
                      spanning state when moving towards the Forwarding
                      state.  The value determines how long the port
                      stays in a particular state before moving to the
                      next state.  For example, how long a port stays in
                      the Listening state when moving from Blocking to
                      Learning.  This value is also used, when a
                      topology change has been detected and is underway,
                      to age all dynamic entries in the Forwarding
                      Database.  [Note that this value is the one that
                      this bridge is currently using, in contrast to
                      dot1dStpBridgeForwardDelay which is the value that
                      this bridge and all others would start using
                      if/when this bridge were to become the root.]"
              REFERENCE
                      "P802.1d/D9, July 14, 1989: Section 4.5.3.6"
              ::= { bridgeStpObject 11 }

          bridgeDot1dStpBridgeMaxAge OBJECT-TYPE
              SYNTAX  INTEGER (600..4000)
              ACCESS  read-only
              STATUS  deprecated
              DESCRIPTION
                      "The value that all bridges use for MaxAge when
                      this bridge is acting as the root.  Note that
                      802.1d/D9 specifies that the range for this
                      parameter is related to the value of
                      dot1dStpBridgeHelloTime. The granularity of this
                      timer is specified by 802.1d/D9 to be 1 second.
                      An agent may return a badValue error if a set is
                      attempted to a value which is not a whole number
                      of seconds."
              REFERENCE
                      "P802.1d/D9, July 14, 1989: Section 4.5.3.8"
              ::= { bridgeStpObject 12 }

          bridgeDot1dStpBridgeHelloTime OBJECT-TYPE
              SYNTAX  INTEGER (100..1000)
              ACCESS  read-only
              STATUS  deprecated
              DESCRIPTION
                      "The value that all bridges use for HelloTime when
                      this bridge is acting as the root.  The
                      granularity of this timer is specified by
                      802.1d/D9 to be 1 second.  An agent may return a
                      badValue error if a set is attempted to a value
                      which is not a whole number of seconds."
              REFERENCE
                      "P802.1d/D9, July 14, 1989: Section 4.5.3.9"
              ::= { bridgeStpObject 13 }

          bridgeDot1dStpBridgeForwardDelay OBJECT-TYPE
              SYNTAX  INTEGER (400..3000)
              ACCESS  read-only
              STATUS  deprecated
              DESCRIPTION
                      "The value that all bridges use for ForwardDelay
                      when this bridge is acting as the root.  Note that
                      802.1d/D9 specifies that the range for this
                      parameter is related to the value of
                      dot1dStpBridgeMaxAge.  The granularity of this
                      timer is specified by 802.1d/D9 to be 1 second.
                      An agent may return a badValue error if a set is
                      attempted to a value which is not a whole number
                      of seconds."
              REFERENCE
                      "P802.1d/D9, July 14, 1989: Section 4.5.3.10"
              ::= { bridgeStpObject 14 }

--
-- The Spanning Tree Port Table
--
--  replaced by the dot1dStpPortTable in RFC1286
--

          bridgeStpPortTable OBJECT-TYPE
              SYNTAX  SEQUENCE OF BridgeStpPortEntry
              ACCESS  not-accessible
              STATUS  deprecated
              DESCRIPTION
                      "A table that contains port-specific information
                      for the Spanning Tree Protocol."
              ::= { bridgeStpObject 15 }

          bridgeStpPortEntry OBJECT-TYPE
              SYNTAX  BridgeStpPortEntry
              ACCESS  not-accessible
              STATUS  deprecated
              DESCRIPTION
                      "A list of information maintained by every port
                      about the Spanning Tree Protocol state for that
                      port."
              INDEX   { bridgeDot1dStpPort }
              ::= { bridgeStpPortTable 1 }

          BridgeStpPortEntry ::=
              SEQUENCE {
                  bridgeDot1dStpPort
                      INTEGER,
                  bridgeDot1dStpPortPriority
                      INTEGER,
                  bridgeDot1dStpPortState
                      INTEGER,
                  bridgeDot1dStpPortEnable
                      INTEGER,
                  bridgeDot1dStpPortPathCost
                      INTEGER,
                  bridgeDot1dStpPortDesignatedRoot
                      OCTET STRING,
                  bridgeDot1dStpPortDesignatedCost
                      INTEGER,
                  bridgeDot1dStpPortDesignatedBridge
                      OCTET STRING,
                  bridgeDot1dStpPortDesignatedPort
                      OCTET STRING,
                  bridgeDot1dStpPortForwardTransitions
                      Counter
              }

          bridgeDot1dStpPort OBJECT-TYPE
              SYNTAX  INTEGER
              ACCESS  read-only
              STATUS  deprecated
              DESCRIPTION
                      "The port number of the port for which this entry
                      contains Spanning Tree Protocol management
                      information."
              REFERENCE
                      "P802.1d/D9, July 14, 1989: Section 6.8.2.1.2"
              ::= { bridgeStpPortEntry 1 }

          bridgeDot1dStpPortPriority OBJECT-TYPE
              SYNTAX  INTEGER (0..255)
              ACCESS  read-only
              STATUS  deprecated
              DESCRIPTION
                      "The value of the priority field which is
                      contained in the first (in network byte order)
                      octet of the (2 octet long) Port ID.  The other
                      octet of the Port ID is given by the value of
                      dot1dStpPort."
              REFERENCE
                      "P802.1d/D9, July 14, 1989: Section 4.5.5.1"
              ::= { bridgeStpPortEntry 2 }

          bridgeDot1dStpPortState OBJECT-TYPE
              SYNTAX  INTEGER {
                          disabled(1),
                          blocking(2),
                          listening(3),
                          learning(4),
                          forwarding(5),
                          broken(6)
                      }
              ACCESS  read-only
              STATUS  deprecated
              DESCRIPTION
                      "The port's current state as defined by
                      application of the Spanning Tree Protocol.  This
                      state controls what action a port takes on
                      reception of a frame.  If the bridge has detected
                      a port that is malfunctioning it will place that
                      port into the broken(6) state.  For ports which
                      are disabled (see dot1dStpPortEnable), this object
                      will have a value of disabled(1)."
              REFERENCE
                      "P802.1d/D9, July 14, 1989: Section 4.5.5.2"
              ::= { bridgeStpPortEntry 3 }

          bridgeDot1dStpPortEnable OBJECT-TYPE
              SYNTAX  INTEGER {
                          enabled(1),
                          disabled(2)
                      }
              ACCESS  read-only
              STATUS  deprecated
              DESCRIPTION
                      "The enabled/disabled status of the port."
              REFERENCE
                      "P802.1d/D9, July 14, 1989: Section 4.5.5.2"
              ::= { bridgeStpPortEntry 4 }

          bridgeDot1dStpPortPathCost OBJECT-TYPE
              SYNTAX  INTEGER (1..65535)
              ACCESS  read-only
              STATUS  deprecated
              DESCRIPTION
                      "The contribution of this port to the path cost of
                      paths towards the spanning tree root which include
                      this port."
              REFERENCE
                      "P802.1d/D9, July 14, 1989: Section 4.5.5.3"
              ::= { bridgeStpPortEntry 5 }

          bridgeDot1dStpPortDesignatedRoot OBJECT-TYPE
              SYNTAX  OCTET STRING
              ACCESS  read-only
              STATUS  deprecated
              DESCRIPTION
                      "The unique Bridge Identifier of the Bridge
                      recorded as the Root in the Configuration BPDUs
                      transmitted by the Designated Bridge for the
                      segment to which the port is attached."
              REFERENCE
                      "P802.1d/D9, July 14, 1989: Section 4.5.5.4"
              ::= { bridgeStpPortEntry 6 }

          bridgeDot1dStpPortDesignatedCost OBJECT-TYPE
              SYNTAX  INTEGER
              ACCESS  read-only
              STATUS  deprecated
              DESCRIPTION
                      "The path cost of the Designated Port of the
                      segment connected to this port.  This value is
                      compared to the Root Path Cost field in received
                      bridge PDUs."
              REFERENCE
                      "P802.1d/D9, July 14, 1989: Section 4.5.5.5"
              ::= { bridgeStpPortEntry 7 }

          bridgeDot1dStpPortDesignatedBridge OBJECT-TYPE
              SYNTAX  OCTET STRING
              ACCESS  read-only
              STATUS  deprecated
              DESCRIPTION
                      "The Bridge Identifier of the bridge which this
                      port considers to be the Designated Bridge for
                      this port's segment."
              REFERENCE
                      "P802.1d/D9, July 14, 1989: Section 4.5.5.6"
              ::= { bridgeStpPortEntry 8 }

          bridgeDot1dStpPortDesignatedPort OBJECT-TYPE
              SYNTAX  OCTET STRING (SIZE (2))
              ACCESS  read-only
              STATUS  deprecated
              DESCRIPTION
                      "The Port Identifier of the port on the Designated
                      Bridge for this port's segment."
              REFERENCE
                      "P802.1d/D9, July 14, 1989: Section 4.5.5.7"
              ::= { bridgeStpPortEntry 9 }

          bridgeDot1dStpPortForwardTransitions OBJECT-TYPE
              SYNTAX  Counter
              ACCESS  read-only
              STATUS  deprecated
              DESCRIPTION
                      "The number of times this port has transitioned
                      from the Learning state to the Forwarding state."
              ::= { bridgeStpPortEntry 10 }


--
--  The Static Group
--
--  The Static (Destination-Address Filtering) Database
--
--  replaced by the dot1dStaticTable in RFC1286
--


          bridgeStaticTable OBJECT-TYPE
              SYNTAX  SEQUENCE OF BridgeStaticEntry
              ACCESS  not-accessible
              STATUS  deprecated
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "P802.1d/D9, July 14, 1989: Section 6.7.2"
              ::= { bridgeStaticObject 1 }


          bridgeStaticEntry OBJECT-TYPE
              SYNTAX  BridgeStaticEntry
              ACCESS  not-accessible
              STATUS  deprecated
              DESCRIPTION
                      "Filtering information configured into the bridge
                      by (local or network) management specifying the
                      set of ports to which frames received from a
                      specific port and containing a specific
                      destination address are allowed to be forwarded."
              REFERENCE
                      "P802.1d/D9, July 14,1989: Section 6.7.2"
              INDEX   { bridgeDot1dStaticAddress }
              ::= { bridgeStaticTable 1 }

          BridgeStaticEntry ::=
              SEQUENCE {
                  bridgeDot1dStaticAddress
                      PhysAddress,
                  bridgeDot1dStaticReceivePort
                      INTEGER,
                  bridgeDot1dStaticAllowedToGoTo
                      OCTET STRING,
                  bridgeDot1dStaticStatus
                      INTEGER
              }

          bridgeDot1dStaticAddress OBJECT-TYPE
              SYNTAX  PhysAddress
              ACCESS  read-only
              STATUS  deprecated
              DESCRIPTION
                      "The destination MAC address in a frame to which
                      this entry's filtering information applies.  This
                      object can take the value of a unicast address, a
                      group address or the broadcast address."
              REFERENCE
                      "P802.1d/D9, July 14, 1989: Section 3.9.1, 3.9.2"
              ::= { bridgeStaticEntry 1 }

          bridgeDot1dStaticReceivePort OBJECT-TYPE
              SYNTAX  INTEGER
              ACCESS  read-only
              STATUS  deprecated
              DESCRIPTION
                      "Either the value '0', or the port number of the
                      port from which a frame must be received in order
                      for this entry's filtering information to apply.
                      A value of zero indicates that this entry applies
                      on all ports of the bridge for which there is no
                      other applicable entry."
              ::= { bridgeStaticEntry 2 }

          bridgeDot1dStaticAllowedToGoTo OBJECT-TYPE
              SYNTAX  OCTET STRING
              ACCESS  read-only
              STATUS  deprecated
              DESCRIPTION
                     "This attribute contains a representation of
                      the Outbound  Ports associated with this static entry."
              ::= { bridgeStaticEntry 3 }

          bridgeDot1dStaticStatus OBJECT-TYPE
              SYNTAX  INTEGER {
                          other(1),
                          invalid(2),
                          permanent(3),
                          deleteOnReset(4),
                          deleteOnTimeout(5)
                      }
              ACCESS  read-only
              STATUS  deprecated
              DESCRIPTION
                     "This object indicates the status of this entry.
                           other(1) - this entry is currently in use but
                                the conditions under which it will
                                remain so are different from each of the
                                following values.
                           invalid(2) - writing this value to the object
                                removes the corresponding entry.
                           permanent(3) - this entry is currently in use
                                and will remain so after the next reset
                                of the bridge.
                           deleteOnReset(4) - this entry is currently in
                                use and will remain so until the next
                                reset of the bridge.
                           deleteOnTimeout(5) - this entry is currently
                                in use and will remain so until it is
                                aged out."
              ::= { bridgeStaticEntry 4 }

--
--    The Protocol Filtering Table
-- 
          bridgeProtFiltTable OBJECT-TYPE
              SYNTAX  SEQUENCE OF BridgeProtFiltEntry
              ACCESS  not-accessible
              STATUS  mandatory
              DESCRIPTION
                      "A table containing protocol filtering information
                      configured into the bridge by (local or network)
                      management specifying the set of ports to which
                      frames containing protocol ID are allowed to be
                      forwarded."
              ::= { bridgeStaticObject 2 }


          bridgeProtFiltEntry OBJECT-TYPE
              SYNTAX  BridgeProtFiltEntry
              ACCESS  not-accessible
              STATUS  mandatory
              DESCRIPTION
                      "Protocol filtering information configured into the 
                       bridge by (local or network) management."
              INDEX   { brProtFiltIndex }
              ::= { bridgeProtFiltTable 1 }
 
          BridgeProtFiltEntry ::=
              SEQUENCE {
                  brProtFiltIndex
                      INTEGER,
                  brProtFiltName 
                      OCTET STRING,
                  brProtFiltId     
                      OCTET STRING,
                  brProtFiltPortMap
                      OCTET STRING
              }

brProtFiltIndex OBJECT-TYPE
        SYNTAX  INTEGER
        ACCESS  read-only
        STATUS  mandatory
        DESCRIPTION
            "This attribute is used as a unique identifier into the Bridge
             Protocol Filtering Table."
        ::= { bridgeProtFiltEntry 1 }
 
brProtFiltName OBJECT-TYPE
        SYNTAX OCTET STRING (SIZE(32))
        ACCESS  read-only
        STATUS  mandatory
        DESCRIPTION
            "A text string of up to 32 characters, of locally determined
             significance used to identify this Protocol filter."
        ::= { bridgeProtFiltEntry 2 }
 
brProtFiltId OBJECT-TYPE
        SYNTAX  OCTET STRING (SIZE(2))
        ACCESS  read-only
        STATUS  mandatory
        DESCRIPTION
            "This attribute identifies the protocol type to be filtered."
        ::= { bridgeProtFiltEntry 3 }
 
brProtFiltPortMap OBJECT-TYPE
        SYNTAX OCTET STRING
        ACCESS  read-only 
        STATUS  mandatory 
        DESCRIPTION 
            "This attribute contains a representation of
             the Outbound  Ports associated with this static entry."
        ::= { bridgeProtFiltEntry 4 } 
 
 
--    The Protocol Priority Table
-- 
          bridgeProtPriorityTable OBJECT-TYPE
              SYNTAX  SEQUENCE OF BridgeProtPriorityEntry
              ACCESS  not-accessible
              STATUS  mandatory
              DESCRIPTION
                      "A table containing protocol priority information
                      configured into the bridge by (local or network)
                      management specifying the priority in which frames
                      will be transmitted on the wide area network links."
              ::= { bridgeStaticObject 3 }


          bridgeProtPriorityEntry OBJECT-TYPE
              SYNTAX  BridgeProtPriorityEntry
              ACCESS  not-accessible
              STATUS  mandatory
              DESCRIPTION
                      "Protocol priority information configured into the 
                       bridge by (local or network) management."
              INDEX   { brProtPriorityIndex }
              ::= { bridgeProtPriorityTable 1 }
 
          BridgeProtPriorityEntry ::=
              SEQUENCE {
                  brProtPriorityIndex
                      INTEGER,
                  brProtPriorityName 
                      OCTET STRING,
                  brProtPriorityId     
                      OCTET STRING,
                  brProtPriorityLevel
                      INTEGER
              }

brProtPriorityIndex OBJECT-TYPE
        SYNTAX  INTEGER
        ACCESS  read-only
        STATUS  mandatory
        DESCRIPTION
            "This attribute is used as a unique identifier into the Bridge
             Protocol Priority Table."
        ::= { bridgeProtPriorityEntry 1 }
 
brProtPriorityName OBJECT-TYPE
        SYNTAX OCTET STRING (SIZE(32))
        ACCESS  read-only
        STATUS  mandatory
        DESCRIPTION
            "A text string of up to 32 characters, of locally determined
             significance used to identify this Protocol Priority entry."
        ::= { bridgeProtPriorityEntry 2 }
 
brProtPriorityId OBJECT-TYPE
        SYNTAX  OCTET STRING (SIZE(2))
        ACCESS  read-only
        STATUS  mandatory
        DESCRIPTION
            "This attribute identifies the protocol type to be prioritized."
        ::= { bridgeProtPriorityEntry 3 }
 
brProtPriorityLevel OBJECT-TYPE
        SYNTAX INTEGER {
            low(1),
            medium(2),
            high(3)
        }
        ACCESS  read-only 
        STATUS  mandatory 
        DESCRIPTION 
            "The priority assigned to the associated Portocol ID"
        ::= { bridgeProtPriorityEntry 4 } 
 
 
  --^L
  -- 
  -- The WAN Physical group
   
wanPhysTable OBJECT-TYPE
    SYNTAX SEQUENCE OF WanPhysEntry
    ACCESS not-accessible
    STATUS mandatory    
    DESCRIPTION    
        "This table represent a view of Management Facilities for
         WAN physical ports."
    ::= { wanPhysicalObject 1 }
 
wanPhysEntry OBJECT-TYPE
    SYNTAX WanPhysEntry
    ACCESS not-accessible
    STATUS mandatory
    DESCRIPTION
        "This list contains counters and parameters related to the
         management of WAN ports."
    INDEX { wanPhysPortId }
    ::= { wanPhysTable 1 }
 
WanPhysEntry ::= SEQUENCE {
        wanPhysPortId
                INTEGER,
        wanPhysPortName
                OCTET STRING,
        wanPhysLogicalPort
                INTEGER,
        wanPhysDcdLevel
                INTEGER,
        wanPhysLinkLevel
                INTEGER,
        wanTxLinkUtilization
                Gauge,
        wanRxLinkUtilization
                Gauge,
        wanPhysFrameErrors
                INTEGER,
        wanCompressionState 
                INTEGER,
        wanCompressionRatio 
                INTEGER
     } 

wanPhysPortId OBJECT-TYPE
	SYNTAX	INTEGER
	ACCESS	read-only
	STATUS	mandatory
        DESCRIPTION
            "This attribute is used as a unique identifier for the Bridge
             WAN interface."
	::= { wanPhysEntry 1 }

wanPhysPortName OBJECT-TYPE
        SYNTAX OCTET STRING (SIZE(32))
	ACCESS	read-only
	STATUS	mandatory
        DESCRIPTION
            "A text string of up to 32 characters, of locally determined 
             significance used to identify this WAN interface."
	::= { wanPhysEntry 2 }

wanPhysLogicalPort OBJECT-TYPE
	SYNTAX	INTEGER
	ACCESS	read-only
	STATUS	mandatory
        DESCRIPTION
            "This attribute shows the logical port for this Wan interface.
             Redundant links will have the same logical port."
	::= { wanPhysEntry 3 }

wanPhysDcdLevel OBJECT-TYPE
        SYNTAX INTEGER {
            down(1),
            up(2)
        }
	ACCESS	read-only
	STATUS	mandatory
        DESCRIPTION
            "This attribute shows the level of the DCD EIA signal on this
             particular WAN link."
	::= { wanPhysEntry 4 }

wanPhysLinkLevel OBJECT-TYPE
        SYNTAX INTEGER {
            down(1),
            up(2)
        }
	ACCESS	read-only
	STATUS	mandatory
        DESCRIPTION
            "This attribute shows whether the WAN link is 'up' or 'down'."
	::= { wanPhysEntry 5 }

wanTxLinkUtilization OBJECT-TYPE
	SYNTAX	Gauge
	ACCESS	read-only
	STATUS	mandatory
        DESCRIPTION
            "This attribute shows the link utilization in the TX direction.
             The utilization is a percentage of the bandwidth (0 to 100)."
	::= { wanPhysEntry 6 }

wanRxLinkUtilization OBJECT-TYPE
	SYNTAX	Gauge
	ACCESS	read-only
	STATUS	mandatory
        DESCRIPTION
            "This attribute shows the link utilization in the RX direction.
             The utilization is a percentage of the bandwidth (0 to 100)."
	::= { wanPhysEntry 7 }

wanPhysFrameErrors OBJECT-TYPE
	SYNTAX	INTEGER
	ACCESS	read-only
	STATUS	mandatory
        DESCRIPTION
            "This attribute shows the number of frame errors on this WAN
             interface."
	::= { wanPhysEntry 8 }

wanCompressionState OBJECT-TYPE
        SYNTAX INTEGER {
            off(1),
            on(2)
        }
	ACCESS	read-only
	STATUS	mandatory
        DESCRIPTION
            "This attribute shows whether data compression is enabled 
             or disabled."
	::= { wanPhysEntry 9 }

wanCompressionRatio OBJECT-TYPE
	SYNTAX	INTEGER
	ACCESS	read-only
	STATUS	mandatory
        DESCRIPTION
            "An indication of how well the Bridge is compressing data that
             is to be transmitted to another bridge.  A value of 100 shows
             no compression, a value of 300 shows a 3 : 1 compression."
	::= { wanPhysEntry 10 }


  --
  --
  -- IEEE 802.3  MAC group

ieeeIfTable OBJECT-TYPE
    SYNTAX SEQUENCE OF IeeeIfEntry
    ACCESS not-accessible
    STATUS mandatory
    DESCRIPTION
        "This table represent a view of Management Facilities for
         the IEEE802.3 CSMA/CD MAC layer.  The object was defined 
         by IEEE in a 802.3 standard."
    ::= { ieee8023Object 1 }

ieeeIfEntry OBJECT-TYPE
    SYNTAX IeeeIfEntry
    ACCESS not-accessible
    STATUS mandatory
    DESCRIPTION
        "This list contains counters and parameters related to the
         management of the IEEE802.3 MAC layer."
    INDEX { ieeeIfIndex }
    ::= { ieeeIfTable 1 }

IeeeIfEntry ::= SEQUENCE {
	ieeeIfIndex
		INTEGER,
	ieeeFrmsTxOk
		Counter,
	ieeeSingleCollFrms
		Counter,
	ieeeMultipleCollFrms
		Counter,
	ieeeOctetsTxOk
		Counter,
	ieeeDefTx
		Counter,
	ieeeMcastFrmsTxOk
		Counter,
	ieeeBcastFrmsTxOk
		Counter,
	ieeeLateColls
		Counter,
	ieeeExcessColls
		Counter,
	ieeeIntlMacTxError
		Counter,
	ieeeCsErrors
		Counter,
	ieeeExcessDef
		Counter,
	ieeeFrmsRxOk
		Counter,
	ieeeOctetsRxOk
		Counter,
	ieeeMcastFrmsRxOk
		Counter,
	ieeeBcastFrmsRxOk
		Counter,
	ieeeTooLongErrors
		Counter,
	ieeeAlignErrors
		Counter,
	ieeeFcsErrors
		Counter,
	ieeeIrLengthErrors
		Counter,
	ieeeOorLengthFields
		Counter,
	ieeeIntlMacRcvErrors
		Counter,
	ieeeInitMac
		INTEGER,
	ieeePromRxStatus
		INTEGER,
	ieeeMacSubLayerStatus
		INTEGER,
	ieeeTxStatus
		INTEGER,
	ieeeMcastRxStatus
		INTEGER,
	ieeeMacAddress
		OCTET STRING,
	ieeeSqeTestErrors
		Counter
}

ieeeIfIndex OBJECT-TYPE
	SYNTAX	INTEGER
	ACCESS	read-only
	STATUS	mandatory
        DESCRIPTION
            "This attribute is used as a unique identifier for the Bridge
             LAN interface."
	::= { ieeeIfEntry 1 }

ieeeFrmsTxOk OBJECT-TYPE
	SYNTAX	Counter
	ACCESS	read-only
	STATUS	mandatory
        DESCRIPTION
            "This attribute contains a count of frames that are successfully
             transmitted."
	::= { ieeeIfEntry 2 }

ieeeSingleCollFrms OBJECT-TYPE
	SYNTAX	Counter
	ACCESS	read-only
	STATUS	mandatory
        DESCRIPTION
            "This attribute contains a count of frames that are involved
             in a single collision and are subsequently transmitted successfuly."
	::= { ieeeIfEntry 3 }

ieeeMultipleCollFrms OBJECT-TYPE
	SYNTAX	Counter
	ACCESS	read-only
	STATUS	mandatory
        DESCRIPTION
            "This attribute contains a count of frames that are involved 
             in more than one collision and are subsequently transmitted
             successfully."
	::= { ieeeIfEntry 4 }

ieeeOctetsTxOk OBJECT-TYPE
	SYNTAX	Counter
	ACCESS	read-only
	STATUS	mandatory
        DESCRIPTION
            "This attribute contains a count of data and padding octets 
             in frames that are successfully transmitted."
	::= { ieeeIfEntry 5 }

ieeeDefTx OBJECT-TYPE
	SYNTAX	Counter
	ACCESS	read-only
	STATUS	mandatory
        DESCRIPTION
            "This attribute contains a count of frames whose transmission 
             was delayed on its first attempt becasue the medium was busy."
	::= { ieeeIfEntry 6 }

ieeeMcastFrmsTxOk OBJECT-TYPE
	SYNTAX	Counter
	ACCESS	read-only
	STATUS	mandatory
        DESCRIPTION
            "This attribute contains a count of frames that are successfully
             transmitted as indicated by the status value transmitOK, to a 
             group destination address other than broadcast."
	::= { ieeeIfEntry 7 }

ieeeBcastFrmsTxOk OBJECT-TYPE
	SYNTAX	Counter
	ACCESS	read-only
	STATUS	mandatory
        DESCRIPTION
            "This attribute contains a number of broadcast frames transmitted
             to the LAN connection."
	::= { ieeeIfEntry 8 }

ieeeLateColls OBJECT-TYPE
	SYNTAX	Counter
	ACCESS	read-only
	STATUS	mandatory
        DESCRIPTION
            "This attribute contains a count of the times that a collision 
             has been detected later than 512 bit times into the transmitted
             packet."
	::= { ieeeIfEntry 9 }

ieeeExcessColls OBJECT-TYPE
	SYNTAX	Counter
	ACCESS	read-only
	STATUS	mandatory
        DESCRIPTION
            "This attribute contains a count of frames that due to excessive
             collisions are not transmitted successfully."
	::= { ieeeIfEntry 10 }

ieeeIntlMacTxError OBJECT-TYPE
	SYNTAX	Counter
	ACCESS	read-only
	STATUS	mandatory
        DESCRIPTION
            "This attribute contains a count of frames which would otherwise
             be transmitted by the station,but could not be sent due to an
             internal MAC sublayer transmit error."
	::= { ieeeIfEntry 11 }

ieeeCsErrors OBJECT-TYPE
	SYNTAX	Counter
	ACCESS	read-only
	STATUS	mandatory
        DESCRIPTION
            "This attribute contains number of frames that were lost because
             the ethernet carrier signal was lost."
	::= { ieeeIfEntry 12 }

ieeeExcessDef OBJECT-TYPE
	SYNTAX	Counter
	ACCESS	read-only
	STATUS	mandatory
        DESCRIPTION
            "This attribute contains a count of frames which deferred for
             an excessive period of time."
	::= { ieeeIfEntry 13 }

ieeeFrmsRxOk OBJECT-TYPE
	SYNTAX	Counter
	ACCESS	read-only
	STATUS	mandatory
        DESCRIPTION
            "This attribute contains a count of frames that are successfully
             received."
	::= { ieeeIfEntry 14 }

ieeeOctetsRxOk OBJECT-TYPE
	SYNTAX	Counter
	ACCESS	read-only
	STATUS	mandatory
        DESCRIPTION
            "This attribute contains a count of data and padding octets 
             in frames that are successfully received."
	::= { ieeeIfEntry 15 }

ieeeMcastFrmsRxOk OBJECT-TYPE
	SYNTAX	Counter
	ACCESS	read-only
	STATUS	mandatory
        DESCRIPTION
            "This attribute contains a count of frames that are successfully 
             received and are directed to an active non-broadcast group of
             addresses."
	::= { ieeeIfEntry 16 }

ieeeBcastFrmsRxOk OBJECT-TYPE
	SYNTAX	Counter
	ACCESS	read-only
	STATUS	mandatory
        DESCRIPTION
            "This attribute contains a number of broadcast frames received
             from the LAN connection."
	::= { ieeeIfEntry 17 }

ieeeTooLongErrors OBJECT-TYPE
	SYNTAX	Counter
	ACCESS	read-only
	STATUS	mandatory
        DESCRIPTION
            "This attribute contains a count of frames that are received 
             and exceeded the maximum permitted frame size. This counter 
             is incremented when the status of a frame reception is frame
             TooLong."
	::= { ieeeIfEntry 18 }

ieeeAlignErrors OBJECT-TYPE
	SYNTAX	Counter
	ACCESS	read-only
	STATUS	mandatory
        DESCRIPTION
            "This attribute contains a count of frames that are not an 
             integral  of octets in length and do not pass the Frame Check
             Sequence(FCS) check.This counter is incremented when the
             ReceiveStatus is reported as alignmentError."
	::= { ieeeIfEntry 19 }

ieeeFcsErrors OBJECT-TYPE
	SYNTAX	Counter
	ACCESS	read-only
	STATUS	mandatory
        DESCRIPTION
            "This attribute contains a count of frames that are an integral
             of octets in length and do not pass the Frame Check Sequence(FCS)
             check.  This counter is incremented when the ReceiveStatus is 
             reported as frameCheckError."
	::= { ieeeIfEntry 20 }

ieeeIrLengthErrors OBJECT-TYPE
	SYNTAX	Counter
	ACCESS	read-only
	STATUS	mandatory
        DESCRIPTION
            "This attribute contains a count of frames with a length field
             value, between the minimum unpadded LLC data size and the 
             maximum allowed LLC data size inclusive, that does not match 
             the number of LLC data octets received.  The counter also 
             contains frames with a length field value less than the 
             minimum unpadded LLC data size."
	::= { ieeeIfEntry 21 }

ieeeOorLengthFields OBJECT-TYPE
	SYNTAX	Counter
	ACCESS	read-only
	STATUS	mandatory
        DESCRIPTION
            "This attribute contains a count of frames with a length field 
             value greater than the maximum allowed LLC data size."
	::= { ieeeIfEntry 22 }

ieeeIntlMacRcvErrors OBJECT-TYPE
	SYNTAX	Counter
	ACCESS	read-only
	STATUS	mandatory
        DESCRIPTION
            "This attribute contains a count of frames which would otherwise
             be received by the station,but could not be accepted due to an 
             internal MAC sublayer receive error."
	::= { ieeeIfEntry 23 }

ieeeInitMac OBJECT-TYPE
	SYNTAX	INTEGER {
		initialize(1),
		uninitialize(2)
		}
	ACCESS	read-only
	STATUS	mandatory
        DESCRIPTION
            "This attributes indicates wether the underlying IEEE 802.3
             MAC was initialized."
	::= { ieeeIfEntry 24 }

ieeePromRxStatus OBJECT-TYPE
	SYNTAX	INTEGER {
		enabled(1),
		disabled(2)
		}
	ACCESS	read-only
	STATUS	mandatory
        DESCRIPTION
            "This attribute contains the current state of the Prom."
	::= { ieeeIfEntry 25 }

ieeeMacSubLayerStatus OBJECT-TYPE
	SYNTAX	INTEGER {
		enabled(1),
		disabled(2)
		}
	ACCESS	read-only
	STATUS	mandatory
        DESCRIPTION
            "This attribute contains the current state of the Receive 
             side of the underlying IEEE 802.3 resource."
	::= { ieeeIfEntry 26 }

ieeeTxStatus OBJECT-TYPE
	SYNTAX	INTEGER {
		enabled(1),
		disabled(2)
		}
	ACCESS	read-only
	STATUS	mandatory
        DESCRIPTION
            "This attribute contains the current state of the Transmit 
             side of the underlying IEEE 802.3 resource."
	::= { ieeeIfEntry 27 }

ieeeMcastRxStatus OBJECT-TYPE
	SYNTAX	INTEGER {
		enabled(1),
		disabled(2)
		}
	ACCESS	read-only
	STATUS	mandatory
        DESCRIPTION
            "This attribute specifies if Multicast frames will be received
             by the underlying IEEE 802.3 resource."
	::= { ieeeIfEntry 28 }

ieeeMacAddress OBJECT-TYPE
	SYNTAX	OCTET STRING (SIZE(6))
	ACCESS	read-only
	STATUS	mandatory
        DESCRIPTION
            "This attribute contains the specific MAC Address of the
             individual MAC Entity associated with the Port."
	::= { ieeeIfEntry 29 }

ieeeSqeTestErrors OBJECT-TYPE
	SYNTAX	Counter
	ACCESS	read-only
	STATUS	mandatory
        DESCRIPTION
            "This attribute contains a count of errors detected when
             performing an SQE test. This counter is not currently supported."
	::= { ieeeIfEntry 30 }


--
--                    GANDALF'S   GENERIC    GROUPS
--                    =============================
--
--  The LOG Group
--
--  The Event Log History Table

          ganEventLogTable OBJECT-TYPE
              SYNTAX  SEQUENCE OF GanEventLogEntry
              ACCESS  not-accessible
              STATUS  mandatory
              DESCRIPTION
                      "A table containing alarm information."
              ::= { gandalfLog 1 }

 
          ganEventLogEntry OBJECT-TYPE
              SYNTAX  GanEventLogEntry
              ACCESS  not-accessible
              STATUS  mandatory
              DESCRIPTION
                      "Log information of alarms generated by the product,
                       including time of event, severity and description."
              INDEX   { ganEventLogIndex }
              ::= { ganEventLogTable 1 }
 
          GanEventLogEntry ::=
              SEQUENCE {
                  ganEventLogIndex
                      INTEGER,
                  ganEventLogDate
                      OCTET STRING,
                  ganEventLogTime
                      OCTET STRING,
                  ganEventLogEventNum
                      INTEGER,
                  ganEventLogSeverity
                      INTEGER,
                  ganEventLogDescription
                      OCTET STRING
              }
 
          ganEventLogIndex OBJECT-TYPE
              SYNTAX  INTEGER
              ACCESS  read-only 
              STATUS  mandatory
              DESCRIPTION
                      "An index to the alarm table, not relevant other
                      than to display the table."
              ::= { ganEventLogEntry 1 }

          ganEventLogDate OBJECT-TYPE
              SYNTAX  OCTET STRING
              ACCESS  read-only 
              STATUS  mandatory
              DESCRIPTION
                     "This date on which the event causing the alarm to be
                      generated occurred."
              ::= { ganEventLogEntry 2 }
--
          ganEventLogTime OBJECT-TYPE
              SYNTAX  OCTET STRING
              ACCESS  read-only 
              STATUS  mandatory
              DESCRIPTION
                     "This time at which the event causing the alarm to be
                      generated occurred."
              ::= { ganEventLogEntry 3 }
    

          ganEventLogEventNum OBJECT-TYPE
              SYNTAX  INTEGER
              ACCESS  read-only 
              STATUS  deprecated
              DESCRIPTION
                      "An index to the alarm table, not relevant other
                      than to display the table. This attribute has
                      been deprecated because it duplicates the
                      ganEventLogIndex."
              ::= { ganEventLogEntry 4 }
          
          ganEventLogSeverity OBJECT-TYPE
              SYNTAX  INTEGER {
                critical(1),
                major(2),
                minor(3),
                warning(4),
                cleared(5),
                informational(6)
              }
              ACCESS  read-only 
              STATUS  mandatory
              DESCRIPTION
                      "An index to the event log table, not relevant other
                      than to display the table."
              ::= { ganEventLogEntry 5 }

          ganEventLogDescription OBJECT-TYPE
              SYNTAX  OCTET STRING
              ACCESS  read-only 
              STATUS  mandatory
              DESCRIPTION
                      "Textual description of the event log."
              ::= { ganEventLogEntry 6 }


-- 
--
--  SNMP Administration  Group
--
--  This group is fully or partially supported by all of Gandalf's SNMP agents.
--
--  The Gandalf WAN Proxy Agent supports sets to this group. The Passport management
--  station automatically inserts an appropriate trap community to the agent's table
--  so it can receive traps.
--
--  The snmpCommunityTable is optionally supported by Gandalf's SNMP 
--  agents. Agents should implement this group provided the system 
--  administrator can choose to refuse access via SNMP to this group.
--
--  In order to prevent duplicate entries in the community table(s), sets must
--  must done using the following rules or else the agent will reject the entry.
--
--     a.) A new instance is specified by picking an instance value higher 
--         than the current highest index. A convenient number is 25, which is
--	   the maximum number of entries in the agent's table. The agent will
--	   reserve the next available index for the new entry once it is qualified.
--
--     b.) All objects in the group must be set before the entry is qualified and
--	   inserted into the table. Each object will be validated for syntax and
--         acknowledged with an error or good response. When the last object is
--         set, the new entry is compared against every value in the table. 
--         Duplicates are detected when a new entry's community name AND IP address 
--         already appear in the table. An SNMP error is sent back in the response
--	   message, and the new entry discarded.
--
--  Entries can be deleted by setting the community name to one or more SPACES.
--  The agent deletes the entry and moves the last table entry into the deleted spot
--  in the table.
--

snmpCommunityTable OBJECT-TYPE
        SYNTAX SEQUENCE OF SnmpCommunityEntry
        ACCESS not-accessible
        STATUS mandatory
        DESCRIPTION
            "This table provide a management view of which device
             can poll this resource via SNMP based on the
             Community Name, IP address and Privilege.
             
             Sets are supported ONLY in the Gandalf WAN proxy agent.

	     To set a new community entry, use the instance 25
	     as the index value. Example: snmpCommunityName.25
	     Set all objects in the entry using instance 25. When
             the last object is set, the agent checks for duplicate
	     entries and returns an error status if any found, 
             otherwise the new entry is inserted at the next 
             available position in the table.

	     Existing entries may be modified by setting the 
	     a new value using an existing instance. The agent
	     rejects any attempt to duplicate an entry.

	     Objects may be deleted by setting the community name
	     to one or more spaces. The entry is deleted and any
             vacated row is filled in by moving the last valid
	     row there.

	     NOTE: The object snmpTrapRemotePort is not supported 
		   in the Gandalf WAN Proxy agent."
        ::= { snmpAdminCapability 1 }
 
snmpCommunityEntry OBJECT-TYPE
        SYNTAX SnmpCommunityEntry
        ACCESS not-accessible
        STATUS mandatory
        DESCRIPTION
            "This is a list of attributes that make the Community
             Table."
        INDEX  { snmpCommunityIndex }
        ::= { snmpCommunityTable 1 }
 
SnmpCommunityEntry ::=
    SEQUENCE {
        snmpCommunityIndex
            INTEGER,
        snmpCommunityName
            OCTET STRING,
        snmpCommunityIpAddr
            IpAddress,
        snmpCommunityPriv
            INTEGER
     }


snmpCommunityIndex OBJECT-TYPE
        SYNTAX INTEGER (1..5)
        ACCESS read-only                       
        STATUS mandatory                      
        DESCRIPTION
            "An 8 bit value unique within the Community Name."
        ::= { snmpCommunityEntry 1 }


snmpCommunityName OBJECT-TYPE
        SYNTAX OCTET STRING                   
        ACCESS read-only                   
        STATUS mandatory                    
        DESCRIPTION
            "The name of a Community supported by this SNMP agent."
        ::= { snmpCommunityEntry 2 }
--

snmpCommunityIpAddr OBJECT-TYPE
        SYNTAX IpAddress
        ACCESS read-only                  
        STATUS mandatory                  
        DESCRIPTION
            "The Ip Address of a manager  associated with a Community
             that will be supported by the SNMP agent.  A value of
             zero means that all managers from that Community will be
             supported."
        ::= { snmpCommunityEntry 3 }


snmpCommunityPriv OBJECT-TYPE
        SYNTAX  INTEGER {
          readOnly(1),
          readWrite(2)
        }
        ACCESS read-only                
        STATUS mandatory                
        DESCRIPTION
            "The access priviledge associated with a Community."
        ::= { snmpCommunityEntry 4 }


snmpTrapCommunityTable OBJECT-TYPE
        SYNTAX SEQUENCE OF SnmpTrapCommunityEntry
        ACCESS not-accessible
        STATUS mandatory
        DESCRIPTION
            "This table provide a management view of which device(s)
             (i.e. LAN Managers) this resource will send Trap to.

             Sets are supported ONLY in the Gandalf WAN proxy agent.

	     To set a new community entry, use the instance 25
	     as the index value. Example: snmpTrapCommunityName.25
	     Set all objects in the entry using instance 25. When
             the last object is set, the agent checks for duplicate
	     entries and returns an error status if any found, 
             otherwise the new entry is inserted at the next 
             available position in the table.

	     Existing entries may be modified by setting the 
	     a new value using an existing instance. The agent
	     rejects any attempt to duplicate an entry.

	     Objects may be deleted by setting the community name
	     to one or more spaces. The entry is deleted and any
             vacated row is filled in by moving the last valid
	     row there."
        ::= { snmpAdminCapability 2 }
     
snmpTrapCommunityEntry OBJECT-TYPE
        SYNTAX SnmpTrapCommunityEntry
        ACCESS not-accessible
        STATUS mandatory
        DESCRIPTION
            "This is a list of attributes that make the Trap
             Community Table."
        INDEX  { snmpTrapCommunityIndex }
    ::= { snmpTrapCommunityTable 1 }
 
SnmpTrapCommunityEntry ::=
    SEQUENCE {
        snmpTrapCommunityIndex
            INTEGER,
        snmpTrapCommunityName
            OCTET STRING,
        snmpTrapIpAddr
            IpAddress,
        snmpTrapRemotePort
            INTEGER
    }

snmpTrapCommunityIndex OBJECT-TYPE
        SYNTAX INTEGER (1..5)
        ACCESS read-only                       
        STATUS mandatory                      
        DESCRIPTION
            "An 8 bit value unique within the Community Name."
        ::= { snmpTrapCommunityEntry 1 }

snmpTrapCommunityName OBJECT-TYPE
        SYNTAX OCTET STRING                   
        ACCESS read-only                    
        STATUS mandatory                    
        DESCRIPTION
            "The name of a Trap Community associated with a LAN 
             Manager." 
        ::= { snmpTrapCommunityEntry 2 }

snmpTrapIpAddr OBJECT-TYPE
        SYNTAX IpAddress
        ACCESS read-only                   
        STATUS mandatory                  
        DESCRIPTION
            "The Ip Address of a manager that will receive Traps
             generated by this SNMP agent."
        ::= { snmpTrapCommunityEntry 3 }

snmpTrapRemotePort OBJECT-TYPE
        SYNTAX INTEGER 
        ACCESS read-only                
        STATUS mandatory                
        DESCRIPTION
            "The remote UDP port number used by an agent to receive
             Traps (usually port 162 is used)."
        ::= { snmpTrapCommunityEntry 4 }


snmpTrapDescription OBJECT-TYPE
        SYNTAX OCTET STRING                   
        ACCESS read-only                     
        STATUS mandatory                    
        DESCRIPTION
            "This attribute provide a description of Enterprise
             Specific Traps. This is also known as the 'interesting 
             information' of an Enterprise Specific Trap."
        ::= { snmpAdminCapability 3 }
 


--
--
--
-- TrapTypes
-- 
--      This section describes the trap types that the
-- Access Hub or Access Bridge can generate.  
-- 
--      The   SNMP    protocol   provides   a   mechanism   for
-- asynchronusly notifying  management stations  of significant
-- changes in  the network.  This mechanism  is the  SNMP  trap
-- message. This section describes the general format for
-- all trap  messages generated by Gandalf's Hub products.  
-- 
-- 
-- Trap Formats
-- 
--      The  SNMP  trap  messages  are  composed  of  two  user
-- definable areas: the specific trap type and the VarBindings
-- (eg. the interesting information). The specific trap type is
-- an INTEGER  that is used to determine the specific trap that
-- has occurred. The "interesting information" contains one
-- object, the "snmpTrapDescription", which consist of an OCTET
-- STRING which gives a complete description of the trap.  The
-- information will also include the card and port numbers when
-- applicable.
--
--
-- Generic Traps
--
-- Access Hub will generate the "coldStart" and "AuthenticationFailure"
-- generic traps. Access Bridge will generate four generic traps:
--
--    coldStart    trap (0)     A coldStart trap is generated when the
--                              device is restarted
--
--    linkDown     trap (2)     A linkDown trap signifies that the agent
--                              recognized a failure in one of the WAN
--                              communication links.
--
--    linkUp       trap (3)     A linkUp trap signifies that the agent
--                              recognized that one of the WAN communi
--                              cation links represented in the agent's
--                              configuration has come up.
--
--    athenticationFailure (4)  An authenticationFailure trap signifies 
--                              that the sending protocol entity is the
--                              addressee of a protocol message that is not
--                              properly authenticated.
--
--
-- Gandalf Enterprise Specific Traps:
--
-- Gandalf products will generate a number Enterprise Specific Traps:
--
--    enetrpriseSpecific (6)    trap specific to this Gandalf
--                              product
--
-- 
--
--
-- Trap Description
--
-- Note that the trap description is written in the Concise format.
-- It can be compiled in your management system by uncommenting the
-- code. 
--
-- Card Installed  (Access Hub only)
--
        gCardInstalled TRAP-TYPE
            ENTERPRISE  gandalf
            DESCRIPTION
                    "This trap indicates that a card was physically
                    installed in the hub.  The trap description 
                    identify the card slot number."
            ::= 100

--
-- Card Removed    (Access Hub only)
--
        gCardRemoved TRAP-TYPE
            ENTERPRISE  gandalf
            DESCRIPTION
                    "This trap indicates that a card was physically
                    removed from the hub.  The trap description 
                    identify the card slot number."
            ::= 101

--
-- Card Mismatch    (Access Hub only)
--
        gCardMismatch TRAP-TYPE
            ENTERPRISE  gandalf
            DESCRIPTION
                    "This trap indicates that a card was physically
                    installed in a slot configured with a different 
                    card type." 
            ::= 102

--
-- Card Mismatch Cleared    (Access Hub only)
--
        gCardMismatchCleared TRAP-TYPE
            ENTERPRISE  gandalf
            DESCRIPTION
                    "This trap indicates that the slot causing a 
                    Card Mismatch was reconfigured with the proper
                    card type."
            ::= 103
--
--
-- Port Threshold Exceeded    (All Products)
--
        gPortThresholdExceeded TRAP-TYPE
            ENTERPRISE  gandalf
            DESCRIPTION
                    "This trap indicates a time based or frame
                    based threshold is exceeded on a given port.
                    The trap description will indicate the type of
                    threshold, as well as identifing the card
                    and port number."
            ::= 104

--
-- NVRAM Fault                (All Products)
--
        gNvramFault TRAP-TYPE
            ENTERPRISE  gandalf
            DESCRIPTION
                    "This trap indicates a critical hardware 
                    failure: an NVRAM fault."
            ::= 105

--
-- Filtering Database Full    (Bridge Products only)
--
        gFiltDatabaseFull TRAP-TYPE
            ENTERPRISE  gandalf
            DESCRIPTION
                    "This trap indicates that the number of entries
                    in the Filtering Database has reached the bridge's
                    storing capacity."
            ::= 106

--
-- Power Supply Failed      (Access Hub only) 
--
        gPowerSupplyFailed TRAP-TYPE
            ENTERPRISE  gandalf
            DESCRIPTION
                    "This trap indicates that a fault was detected
                    on a power supply.  The trap description will
                    indicate which of the two power supply is
                    faulty."
            ::= 107

--
-- Log Threshold exceeded    (All Products)
--
        gLogThresholdExceeded TRAP-TYPE
            ENTERPRISE  gandalf
            DESCRIPTION
                    "This trap indicates that the event log capacity
                    was exceeded."
            ::= 108
--
--
-- Link Mismatch             (Remote Bridge Only)
--
        gLinkMismatch TRAP-TYPE
            ENTERPRISE  gandalf
            DESCRIPTION
                    "This trap indicates that the configuration of a WAN
                    port is incompatible with the network topology."
            ::= 109

--
-- Link Mismatch Cleared     (Remote Bridge Only)
--
        gLinkMismatchCleared TRAP-TYPE
            ENTERPRISE  gandalf
            DESCRIPTION
                    "This trap indicates that the condition causing a
                    Link Mismatch was corrected."
            ::= 110

--
-- Traps for the Bridge Spanning Tree Protocol
--
        gNewRoot TRAP-TYPE
            ENTERPRISE  gandalf
            DESCRIPTION
                    "The newRoot trap indicates that the sending agent
                    has become the new root of the Spanning Tree; the
                    trap is sent by a bridge soon after its election
                    as the new root, e.g., upon expiration of the
                    Topology Change Timer immediately subsequent to
                    its election."
            ::= 111

        gTopologyChange TRAP-TYPE
            ENTERPRISE  gandalf
            DESCRIPTION
                    "A topologyChange trap is sent by a bridge when
                    any of its configured ports transitions from the
                    Learning state to the Forwarding state, or from
                    the Forwarding state to the Blocking state.  The
                    trap is not sent if a newRoot trap is sent for the
                    same transition."
            ::= 112

--
-- Port Failure     (Access Hub Only)
--
        gPortFailure TRAP-TYPE
            ENTERPRISE  gandalf
            DESCRIPTION
                    "A link to a port has failed. Possible reasons:
                    1.  Master port idle receive timer has expired.
                        Port has been disabled and declared faulty.
                        Standby port will take over if ready.
                    2.  Standby port idle receive timer has expired.
                        Port has been disabled and declared faulty."
            ::= 113

END
