-- file automatically created


TELDAT-TRAP-DHCL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


dhclTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DHCL event subsystem."
    REVISION "201401200930Z"
    DESCRIPTION "Initial implementation"
        ::= { telEventTraps 182 }


dhclEventsGroup	OBJECT IDENTIFIER	::= { dhclTrapsMIB 1 }

dhclNotifications	OBJECT IDENTIFIER	::= { dhclTrapsMIB 2 }
dhclNotificationsPrefix	OBJECT IDENTIFIER	::= { dhclNotifications 0 }

dhclEventObjects1 OBJECT-IDENTITY
    STATUS current
    DESCRIPTION
        "Event DHCL.1
        Generic event to display any information."
    ::= { dhclEventsGroup 1 }

dhcl1-generic-info OBJECT-TYPE
    SYNTAX DisplayString
    MAX-ACCESS accessible-for-notify
    STATUS current
    DESCRIPTION
        "Parameter 'generic-info' in event DHCL.1"
    ::= { dhclEventObjects1 1 }

dhclEventObjects2 OBJECT-IDENTITY
    STATUS current
    DESCRIPTION
        "Event DHCL.2
        An error ocurred starting DHCP client: UDP port could not be registered."
    ::= { dhclEventsGroup 2 }

dhcl2-port OBJECT-TYPE
    SYNTAX Integer32
    MAX-ACCESS accessible-for-notify
    STATUS current
    DESCRIPTION
        "Parameter 'port' in event DHCL.2"
    ::= { dhclEventObjects2 1 }

dhclEventObjects3 OBJECT-IDENTITY
    STATUS current
    DESCRIPTION
        "Event DHCL.3
        DHCP client has started running on this interface."
    ::= { dhclEventsGroup 3 }

dhcl3-interface OBJECT-TYPE
    SYNTAX DisplayString
    MAX-ACCESS accessible-for-notify
    STATUS current
    DESCRIPTION
        "Parameter 'interface' in event DHCL.3"
    ::= { dhclEventObjects3 1 }

dhclEventObjects4 OBJECT-IDENTITY
    STATUS current
    DESCRIPTION
        "Event DHCL.4
        DHCP client could no start running on this interface because DHCP client
        is only supported on Ethernet interfaces or subinterfaces."
    ::= { dhclEventsGroup 4 }

dhcl4-interface OBJECT-TYPE
    SYNTAX DisplayString
    MAX-ACCESS accessible-for-notify
    STATUS current
    DESCRIPTION
        "Parameter 'interface' in event DHCL.4"
    ::= { dhclEventObjects4 1 }

dhclEventObjects5 OBJECT-IDENTITY
    STATUS current
    DESCRIPTION
        "Event DHCL.5
        A DHCP message, whose type is shown, was received on this interface."
    ::= { dhclEventsGroup 5 }

dhcl5-message-type OBJECT-TYPE
    SYNTAX DisplayString
    MAX-ACCESS accessible-for-notify
    STATUS current
    DESCRIPTION
        "Parameter 'message-type' in event DHCL.5"
    ::= { dhclEventObjects5 1 }

dhcl5-interface OBJECT-TYPE
    SYNTAX DisplayString
    MAX-ACCESS accessible-for-notify
    STATUS current
    DESCRIPTION
        "Parameter 'interface' in event DHCL.5"
    ::= { dhclEventObjects5 2 }

dhclEventObjects6 OBJECT-IDENTITY
    STATUS current
    DESCRIPTION
        "Event DHCL.6
        A packet was received on this interface and is discarded because of
        the given reason. Possible causes are:
        - Data inconsistence.
        - No memory.
        - Err parsing opts.
        - Missed magic cookie.
        - No BOOTREPLY.
        - Bad type."
    ::= { dhclEventsGroup 6 }

dhcl6-interface OBJECT-TYPE
    SYNTAX DisplayString
    MAX-ACCESS accessible-for-notify
    STATUS current
    DESCRIPTION
        "Parameter 'interface' in event DHCL.6"
    ::= { dhclEventObjects6 1 }

dhcl6-reason OBJECT-TYPE
    SYNTAX DisplayString
    MAX-ACCESS accessible-for-notify
    STATUS current
    DESCRIPTION
        "Parameter 'reason' in event DHCL.6"
    ::= { dhclEventObjects6 2 }

dhclEventObjects7 OBJECT-IDENTITY
    STATUS current
    DESCRIPTION
        "Event DHCL.7
        A DHCP message, whose type is shown, was received on this interface and
        is discarded because of the given reason. Possible causes are:
        - XID mismatch.
        - No SELECTING (only for DHCPDISCOVER).
        - Not expected
        - MAC mismatch.
        - Duplicated lease (only for DHCPDISCOVER).
        - No memory."
    ::= { dhclEventsGroup 7 }

dhcl7-message-type OBJECT-TYPE
    SYNTAX DisplayString
    MAX-ACCESS accessible-for-notify
    STATUS current
    DESCRIPTION
        "Parameter 'message-type' in event DHCL.7"
    ::= { dhclEventObjects7 1 }

dhcl7-interface OBJECT-TYPE
    SYNTAX DisplayString
    MAX-ACCESS accessible-for-notify
    STATUS current
    DESCRIPTION
        "Parameter 'interface' in event DHCL.7"
    ::= { dhclEventObjects7 2 }

dhcl7-reason OBJECT-TYPE
    SYNTAX DisplayString
    MAX-ACCESS accessible-for-notify
    STATUS current
    DESCRIPTION
        "Parameter 'reason' in event DHCL.7"
    ::= { dhclEventObjects7 3 }

dhclEventObjects8 OBJECT-IDENTITY
    STATUS current
    DESCRIPTION
        "Event DHCL.8
        A DHCP message, whose type is shown, is transmitted on this interface."
    ::= { dhclEventsGroup 8 }

dhcl8-message-type OBJECT-TYPE
    SYNTAX DisplayString
    MAX-ACCESS accessible-for-notify
    STATUS current
    DESCRIPTION
        "Parameter 'message-type' in event DHCL.8"
    ::= { dhclEventObjects8 1 }

dhcl8-interface OBJECT-TYPE
    SYNTAX DisplayString
    MAX-ACCESS accessible-for-notify
    STATUS current
    DESCRIPTION
        "Parameter 'interface' in event DHCL.8"
    ::= { dhclEventObjects8 2 }

dhclEventObjects9 OBJECT-IDENTITY
    STATUS current
    DESCRIPTION
        "Event DHCL.9
        A DHCP message, whose type is shown, is transmitted on this interface.
        Source and destination addresses are also included in this event."
    ::= { dhclEventsGroup 9 }

dhcl9-message-type OBJECT-TYPE
    SYNTAX DisplayString
    MAX-ACCESS accessible-for-notify
    STATUS current
    DESCRIPTION
        "Parameter 'message-type' in event DHCL.9"
    ::= { dhclEventObjects9 1 }

dhcl9-interface OBJECT-TYPE
    SYNTAX DisplayString
    MAX-ACCESS accessible-for-notify
    STATUS current
    DESCRIPTION
        "Parameter 'interface' in event DHCL.9"
    ::= { dhclEventObjects9 2 }

dhcl9-src-addr OBJECT-TYPE
    SYNTAX IpAddress
    MAX-ACCESS accessible-for-notify
    STATUS current
    DESCRIPTION
        "Parameter 'src-addr' in event DHCL.9"
    ::= { dhclEventObjects9 3 }

dhcl9-dest-addr OBJECT-TYPE
    SYNTAX IpAddress
    MAX-ACCESS accessible-for-notify
    STATUS current
    DESCRIPTION
        "Parameter 'dest-addr' in event DHCL.9"
    ::= { dhclEventObjects9 4 }

dhclEventObjects10 OBJECT-IDENTITY
    STATUS current
    DESCRIPTION
        "Event DHCL.10
        A DHCP message could not be transmitted because the interface is not up."
    ::= { dhclEventsGroup 10 }

dhcl10-interface OBJECT-TYPE
    SYNTAX DisplayString
    MAX-ACCESS accessible-for-notify
    STATUS current
    DESCRIPTION
        "Parameter 'interface' in event DHCL.10"
    ::= { dhclEventObjects10 1 }

dhclEventObjects11 OBJECT-IDENTITY
    STATUS current
    DESCRIPTION
        "Event DHCL.11
        DHCP client running on this interface has been assigned the shown IP
        address and it has been added to the interface."
    ::= { dhclEventsGroup 11 }

dhcl11-ip-address OBJECT-TYPE
    SYNTAX IpAddress
    MAX-ACCESS accessible-for-notify
    STATUS current
    DESCRIPTION
        "Parameter 'ip-address' in event DHCL.11"
    ::= { dhclEventObjects11 1 }

dhcl11-interface OBJECT-TYPE
    SYNTAX DisplayString
    MAX-ACCESS accessible-for-notify
    STATUS current
    DESCRIPTION
        "Parameter 'interface' in event DHCL.11"
    ::= { dhclEventObjects11 2 }

dhclEventObjects12 OBJECT-IDENTITY
    STATUS current
    DESCRIPTION
        "Event DHCL.12
        An error has occurred while adding the assigned IP address to the
        specified interface."
    ::= { dhclEventsGroup 12 }

dhcl12-ip-address OBJECT-TYPE
    SYNTAX IpAddress
    MAX-ACCESS accessible-for-notify
    STATUS current
    DESCRIPTION
        "Parameter 'ip-address' in event DHCL.12"
    ::= { dhclEventObjects12 1 }

dhcl12-interface OBJECT-TYPE
    SYNTAX DisplayString
    MAX-ACCESS accessible-for-notify
    STATUS current
    DESCRIPTION
        "Parameter 'interface' in event DHCL.12"
    ::= { dhclEventObjects12 2 }

dhclEventObjects13 OBJECT-IDENTITY
    STATUS current
    DESCRIPTION
        "Event DHCL.13
        DHCP client is releasing the assigned IP address and restoring the
        configured one on this interface."
    ::= { dhclEventsGroup 13 }

dhcl13-ip-address OBJECT-TYPE
    SYNTAX IpAddress
    MAX-ACCESS accessible-for-notify
    STATUS current
    DESCRIPTION
        "Parameter 'ip-address' in event DHCL.13"
    ::= { dhclEventObjects13 1 }

dhcl13-interface OBJECT-TYPE
    SYNTAX DisplayString
    MAX-ACCESS accessible-for-notify
    STATUS current
    DESCRIPTION
        "Parameter 'interface' in event DHCL.13"
    ::= { dhclEventObjects13 2 }

dhclEventObjects14 OBJECT-IDENTITY
    STATUS current
    DESCRIPTION
        "Event DHCL.14
        An error has occurred while deleting the assigned IP address and
        restoring the configured one on this interface."
    ::= { dhclEventsGroup 14 }

dhcl14-ip-address OBJECT-TYPE
    SYNTAX IpAddress
    MAX-ACCESS accessible-for-notify
    STATUS current
    DESCRIPTION
        "Parameter 'ip-address' in event DHCL.14"
    ::= { dhclEventObjects14 1 }

dhcl14-interface OBJECT-TYPE
    SYNTAX DisplayString
    MAX-ACCESS accessible-for-notify
    STATUS current
    DESCRIPTION
        "Parameter 'interface' in event DHCL.14"
    ::= { dhclEventObjects14 2 }

dhclEventObjects15 OBJECT-IDENTITY
    STATUS current
    DESCRIPTION
        "Event DHCL.15
        The default gateway assigned to DHCP client on this interface has been
        added (as a default route)."
    ::= { dhclEventsGroup 15 }

dhcl15-gateway OBJECT-TYPE
    SYNTAX IpAddress
    MAX-ACCESS accessible-for-notify
    STATUS current
    DESCRIPTION
        "Parameter 'gateway' in event DHCL.15"
    ::= { dhclEventObjects15 1 }

dhcl15-interface OBJECT-TYPE
    SYNTAX DisplayString
    MAX-ACCESS accessible-for-notify
    STATUS current
    DESCRIPTION
        "Parameter 'interface' in event DHCL.15"
    ::= { dhclEventObjects15 2 }

dhclEventObjects16 OBJECT-IDENTITY
    STATUS current
    DESCRIPTION
        "Event DHCL.16
        An error has ocurred while adding the default gateway assigned to DHCP
        client on this interface (as a default route)."
    ::= { dhclEventsGroup 16 }

dhcl16-gateway OBJECT-TYPE
    SYNTAX IpAddress
    MAX-ACCESS accessible-for-notify
    STATUS current
    DESCRIPTION
        "Parameter 'gateway' in event DHCL.16"
    ::= { dhclEventObjects16 1 }

dhcl16-interface OBJECT-TYPE
    SYNTAX DisplayString
    MAX-ACCESS accessible-for-notify
    STATUS current
    DESCRIPTION
        "Parameter 'interface' in event DHCL.16"
    ::= { dhclEventObjects16 2 }

dhclEventObjects17 OBJECT-IDENTITY
    STATUS current
    DESCRIPTION
        "Event DHCL.17
        The default gateway assigned to DHCP client on this interface has been
        deleted because the DHCP cliente is performing a shutdown or the lease
        time has expired."
    ::= { dhclEventsGroup 17 }

dhcl17-gateway OBJECT-TYPE
    SYNTAX IpAddress
    MAX-ACCESS accessible-for-notify
    STATUS current
    DESCRIPTION
        "Parameter 'gateway' in event DHCL.17"
    ::= { dhclEventObjects17 1 }

dhcl17-interface OBJECT-TYPE
    SYNTAX DisplayString
    MAX-ACCESS accessible-for-notify
    STATUS current
    DESCRIPTION
        "Parameter 'interface' in event DHCL.17"
    ::= { dhclEventObjects17 2 }

dhclEventObjects18 OBJECT-IDENTITY
    STATUS current
    DESCRIPTION
        "Event DHCL.18
        The maximum number of retransmissions of DHCP messages of the indicated
        type has been reached, so the DHCP client on the given interface is
        going to be restarted."
    ::= { dhclEventsGroup 18 }

dhcl18-message-type OBJECT-TYPE
    SYNTAX DisplayString
    MAX-ACCESS accessible-for-notify
    STATUS current
    DESCRIPTION
        "Parameter 'message-type' in event DHCL.18"
    ::= { dhclEventObjects18 1 }

dhcl18-max-num-retx OBJECT-TYPE
    SYNTAX Integer32
    MAX-ACCESS accessible-for-notify
    STATUS current
    DESCRIPTION
        "Parameter 'max-num-retx' in event DHCL.18"
    ::= { dhclEventObjects18 2 }

dhcl18-interface OBJECT-TYPE
    SYNTAX DisplayString
    MAX-ACCESS accessible-for-notify
    STATUS current
    DESCRIPTION
        "Parameter 'interface' in event DHCL.18"
    ::= { dhclEventObjects18 3 }

dhclEventObjects19 OBJECT-IDENTITY
    STATUS current
    DESCRIPTION
        "Event DHCL.19
        Timer T1 (renewal time) has expired so the DHCP client running on the
        specified interface changes to RENEWING state and tries to extend its
        lease sending DHCPREQUEST messages addressed to the server which
        originally issued the client's network address."
    ::= { dhclEventsGroup 19 }

dhcl19-interface OBJECT-TYPE
    SYNTAX DisplayString
    MAX-ACCESS accessible-for-notify
    STATUS current
    DESCRIPTION
        "Parameter 'interface' in event DHCL.19"
    ::= { dhclEventObjects19 1 }

dhclEventObjects20 OBJECT-IDENTITY
    STATUS current
    DESCRIPTION
        "Event DHCL.20
        Timer T2 (rebind time) has expired so the DHCP client running on the
        specified interface changes to REBINDING state and tries to extend its
        lease broadcasting DHCPREQUEST messages."
    ::= { dhclEventsGroup 20 }

dhcl20-interface OBJECT-TYPE
    SYNTAX DisplayString
    MAX-ACCESS accessible-for-notify
    STATUS current
    DESCRIPTION
        "Parameter 'interface' in event DHCL.20"
    ::= { dhclEventObjects20 1 }

dhclEventObjects21 OBJECT-IDENTITY
    STATUS current
    DESCRIPTION
        "Event DHCL.21
        Lease time has expired so the DHCP client running on the specified
        interface releases the assigned IP address and the other adquired
        parameters, returns to its initialization parameters and restarts."
    ::= { dhclEventsGroup 21 }

dhcl21-interface OBJECT-TYPE
    SYNTAX DisplayString
    MAX-ACCESS accessible-for-notify
    STATUS current
    DESCRIPTION
        "Parameter 'interface' in event DHCL.21"
    ::= { dhclEventObjects21 1 }

dhclEventObjects22 OBJECT-IDENTITY
    STATUS current
    DESCRIPTION
        "Event DHCL.22
        The dhcp-negotiated address has been dynamically deleted, so DHCP client
        must be disabled on this interface."
    ::= { dhclEventsGroup 22 }

dhcl22-interface OBJECT-TYPE
    SYNTAX DisplayString
    MAX-ACCESS accessible-for-notify
    STATUS current
    DESCRIPTION
        "Parameter 'interface' in event DHCL.22"
    ::= { dhclEventObjects22 1 }

dhclEventObjects23 OBJECT-IDENTITY
    STATUS current
    DESCRIPTION
        "Event DHCL.23
        The DHCP client on this interface performs a shutdown due to a release
        command or because the dhcp-negotiated address has been dynamically
        deleted."
    ::= { dhclEventsGroup 23 }

dhcl23-interface OBJECT-TYPE
    SYNTAX DisplayString
    MAX-ACCESS accessible-for-notify
    STATUS current
    DESCRIPTION
        "Parameter 'interface' in event DHCL.23"
    ::= { dhclEventObjects23 1 }


dhclNotification1 NOTIFICATION-TYPE
    OBJECTS { 
              dhcl1-generic-info 
            }
    STATUS current
    DESCRIPTION
        "Notification of Event DHCL.1

        Message: '$1'

        Parameters list:
              $1: dhcl1-generic-info

        Generic event to display any information."
    ::= { dhclNotificationsPrefix 1 }

dhclNotification2 NOTIFICATION-TYPE
    OBJECTS { 
              dhcl2-port 
            }
    STATUS current
    DESCRIPTION
        "Notification of Event DHCL.2

        Message: 'Error starting DHCP client: UDP port $1 could not be registered'

        Parameters list:
              $1: dhcl2-port

        An error ocurred starting DHCP client: UDP port could not be registered."
    ::= { dhclNotificationsPrefix 2 }

dhclNotification3 NOTIFICATION-TYPE
    OBJECTS { 
              dhcl3-interface 
            }
    STATUS current
    DESCRIPTION
        "Notification of Event DHCL.3

        Message: 'DHCP client started on interface $1'

        Parameters list:
              $1: dhcl3-interface

        DHCP client has started running on this interface."
    ::= { dhclNotificationsPrefix 3 }

dhclNotification4 NOTIFICATION-TYPE
    OBJECTS { 
              dhcl4-interface 
            }
    STATUS current
    DESCRIPTION
        "Notification of Event DHCL.4

        Message: 'DHCP client not started on interface $1: only supported on Ethernet interfaces'

        Parameters list:
              $1: dhcl4-interface

        DHCP client could no start running on this interface because DHCP client
        is only supported on Ethernet interfaces or subinterfaces."
    ::= { dhclNotificationsPrefix 4 }

dhclNotification5 NOTIFICATION-TYPE
    OBJECTS { 
              dhcl5-message-type, 
              dhcl5-interface 
            }
    STATUS current
    DESCRIPTION
        "Notification of Event DHCL.5

        Message: 'Received $1 message on interface $2'

        Parameters list:
              $1: dhcl5-message-type
              $2: dhcl5-interface

        A DHCP message, whose type is shown, was received on this interface."
    ::= { dhclNotificationsPrefix 5 }

dhclNotification6 NOTIFICATION-TYPE
    OBJECTS { 
              dhcl6-interface, 
              dhcl6-reason 
            }
    STATUS current
    DESCRIPTION
        "Notification of Event DHCL.6

        Message: 'Discarded received packet on interface $1 (reason: $2)'

        Parameters list:
              $1: dhcl6-interface
              $2: dhcl6-reason

        A packet was received on this interface and is discarded because of
        the given reason. Possible causes are:
        - Data inconsistence.
        - No memory.
        - Err parsing opts.
        - Missed magic cookie.
        - No BOOTREPLY.
        - Bad type."
    ::= { dhclNotificationsPrefix 6 }

dhclNotification7 NOTIFICATION-TYPE
    OBJECTS { 
              dhcl7-message-type, 
              dhcl7-interface,
              dhcl7-reason 
            }
    STATUS current
    DESCRIPTION
        "Notification of Event DHCL.7

        Message: 'Discarded received $1 on interface $2 (reason: $3)'

        Parameters list:
              $1: dhcl7-message-type
              $2: dhcl7-interface
              $3: dhcl7-reason

        A DHCP message, whose type is shown, was received on this interface and
        is discarded because of the given reason. Possible causes are:
        - XID mismatch.
        - No SELECTING (only for DHCPDISCOVER).
        - Not expected
        - MAC mismatch.
        - Duplicated lease (only for DHCPDISCOVER).
        - No memory."
    ::= { dhclNotificationsPrefix 7 }

dhclNotification8 NOTIFICATION-TYPE
    OBJECTS { 
              dhcl8-message-type, 
              dhcl8-interface 
            }
    STATUS current
    DESCRIPTION
        "Notification of Event DHCL.8

        Message: '$1 message transmitted on interface $2'

        Parameters list:
              $1: dhcl8-message-type
              $2: dhcl8-interface

        A DHCP message, whose type is shown, is transmitted on this interface."
    ::= { dhclNotificationsPrefix 8 }

dhclNotification9 NOTIFICATION-TYPE
    OBJECTS { 
              dhcl9-message-type, 
              dhcl9-interface,
              dhcl9-src-addr,
              dhcl9-dest-addr 
            }
    STATUS current
    DESCRIPTION
        "Notification of Event DHCL.9

        Message: '$1 message transmitted on interface $2 ($3 -> $4)'

        Parameters list:
              $1: dhcl9-message-type
              $2: dhcl9-interface
              $3: dhcl9-src-addr
              $4: dhcl9-dest-addr

        A DHCP message, whose type is shown, is transmitted on this interface.
        Source and destination addresses are also included in this event."
    ::= { dhclNotificationsPrefix 9 }

dhclNotification10 NOTIFICATION-TYPE
    OBJECTS { 
              dhcl10-interface 
            }
    STATUS current
    DESCRIPTION
        "Notification of Event DHCL.10

        Message: 'Transmission failed: interface $1 is not up'

        Parameters list:
              $1: dhcl10-interface

        A DHCP message could not be transmitted because the interface is not up."
    ::= { dhclNotificationsPrefix 10 }

dhclNotification11 NOTIFICATION-TYPE
    OBJECTS { 
              dhcl11-ip-address, 
              dhcl11-interface 
            }
    STATUS current
    DESCRIPTION
        "Notification of Event DHCL.11

        Message: 'Added assigned IP address $1 to interface $2'

        Parameters list:
              $1: dhcl11-ip-address
              $2: dhcl11-interface

        DHCP client running on this interface has been assigned the shown IP
        address and it has been added to the interface."
    ::= { dhclNotificationsPrefix 11 }

dhclNotification12 NOTIFICATION-TYPE
    OBJECTS { 
              dhcl12-ip-address, 
              dhcl12-interface 
            }
    STATUS current
    DESCRIPTION
        "Notification of Event DHCL.12

        Message: 'Error adding assigned IP address $1 to interface $2'

        Parameters list:
              $1: dhcl12-ip-address
              $2: dhcl12-interface

        An error has occurred while adding the assigned IP address to the
        specified interface."
    ::= { dhclNotificationsPrefix 12 }

dhclNotification13 NOTIFICATION-TYPE
    OBJECTS { 
              dhcl13-ip-address, 
              dhcl13-interface 
            }
    STATUS current
    DESCRIPTION
        "Notification of Event DHCL.13

        Message: 'Deleted assigned IP address $1 on interface $2'

        Parameters list:
              $1: dhcl13-ip-address
              $2: dhcl13-interface

        DHCP client is releasing the assigned IP address and restoring the
        configured one on this interface."
    ::= { dhclNotificationsPrefix 13 }

dhclNotification14 NOTIFICATION-TYPE
    OBJECTS { 
              dhcl14-ip-address, 
              dhcl14-interface 
            }
    STATUS current
    DESCRIPTION
        "Notification of Event DHCL.14

        Message: 'Error deleting assigned IP address $1 on interface $2'

        Parameters list:
              $1: dhcl14-ip-address
              $2: dhcl14-interface

        An error has occurred while deleting the assigned IP address and
        restoring the configured one on this interface."
    ::= { dhclNotificationsPrefix 14 }

dhclNotification15 NOTIFICATION-TYPE
    OBJECTS { 
              dhcl15-gateway, 
              dhcl15-interface 
            }
    STATUS current
    DESCRIPTION
        "Notification of Event DHCL.15

        Message: 'Added assigned default gateway $1 (DHCP client on interface $2)'

        Parameters list:
              $1: dhcl15-gateway
              $2: dhcl15-interface

        The default gateway assigned to DHCP client on this interface has been
        added (as a default route)."
    ::= { dhclNotificationsPrefix 15 }

dhclNotification16 NOTIFICATION-TYPE
    OBJECTS { 
              dhcl16-gateway, 
              dhcl16-interface 
            }
    STATUS current
    DESCRIPTION
        "Notification of Event DHCL.16

        Message: 'Error adding assigned default gateway $1 (DHCP client on interface $2)'

        Parameters list:
              $1: dhcl16-gateway
              $2: dhcl16-interface

        An error has ocurred while adding the default gateway assigned to DHCP
        client on this interface (as a default route)."
    ::= { dhclNotificationsPrefix 16 }

dhclNotification17 NOTIFICATION-TYPE
    OBJECTS { 
              dhcl17-gateway, 
              dhcl17-interface 
            }
    STATUS current
    DESCRIPTION
        "Notification of Event DHCL.17

        Message: 'Deleted assigned default gateway $1 (DHCP client on interface $2)'

        Parameters list:
              $1: dhcl17-gateway
              $2: dhcl17-interface

        The default gateway assigned to DHCP client on this interface has been
        deleted because the DHCP cliente is performing a shutdown or the lease
        time has expired."
    ::= { dhclNotificationsPrefix 17 }

dhclNotification18 NOTIFICATION-TYPE
    OBJECTS { 
              dhcl18-message-type, 
              dhcl18-max-num-retx,
              dhcl18-interface 
            }
    STATUS current
    DESCRIPTION
        "Notification of Event DHCL.18

        Message: 'Maximum number of retransmissions of $1 messages reached ($2): DHCP client restarted on interface $3'

        Parameters list:
              $1: dhcl18-message-type
              $2: dhcl18-max-num-retx
              $3: dhcl18-interface

        The maximum number of retransmissions of DHCP messages of the indicated
        type has been reached, so the DHCP client on the given interface is
        going to be restarted."
    ::= { dhclNotificationsPrefix 18 }

dhclNotification19 NOTIFICATION-TYPE
    OBJECTS { 
              dhcl19-interface 
            }
    STATUS current
    DESCRIPTION
        "Notification of Event DHCL.19

        Message: 'Timer T1 expired: state changed to RENEWING on interface $1'

        Parameters list:
              $1: dhcl19-interface

        Timer T1 (renewal time) has expired so the DHCP client running on the
        specified interface changes to RENEWING state and tries to extend its
        lease sending DHCPREQUEST messages addressed to the server which
        originally issued the client's network address."
    ::= { dhclNotificationsPrefix 19 }

dhclNotification20 NOTIFICATION-TYPE
    OBJECTS { 
              dhcl20-interface 
            }
    STATUS current
    DESCRIPTION
        "Notification of Event DHCL.20

        Message: 'Timer T2 expired: state changed to REBINDING on interface $1'

        Parameters list:
              $1: dhcl20-interface

        Timer T2 (rebind time) has expired so the DHCP client running on the
        specified interface changes to REBINDING state and tries to extend its
        lease broadcasting DHCPREQUEST messages."
    ::= { dhclNotificationsPrefix 20 }

dhclNotification21 NOTIFICATION-TYPE
    OBJECTS { 
              dhcl21-interface 
            }
    STATUS current
    DESCRIPTION
        "Notification of Event DHCL.21

        Message: 'Lease expired: client restarted on interface $1'

        Parameters list:
              $1: dhcl21-interface

        Lease time has expired so the DHCP client running on the specified
        interface releases the assigned IP address and the other adquired
        parameters, returns to its initialization parameters and restarts."
    ::= { dhclNotificationsPrefix 21 }

dhclNotification22 NOTIFICATION-TYPE
    OBJECTS { 
              dhcl22-interface 
            }
    STATUS current
    DESCRIPTION
        "Notification of Event DHCL.22

        Message: 'Deleted address dhcp-negotiated: disabling DHCP client on interface $1'

        Parameters list:
              $1: dhcl22-interface

        The dhcp-negotiated address has been dynamically deleted, so DHCP client
        must be disabled on this interface."
    ::= { dhclNotificationsPrefix 22 }

dhclNotification23 NOTIFICATION-TYPE
    OBJECTS { 
              dhcl23-interface 
            }
    STATUS current
    DESCRIPTION
        "Notification of Event DHCL.23

        Message: 'Shutdown of DHCP client on interface $1'

        Parameters list:
              $1: dhcl23-interface

        The DHCP client on this interface performs a shutdown due to a release
        command or because the dhcp-negotiated address has been dynamically
        deleted."
    ::= { dhclNotificationsPrefix 23 }


END
