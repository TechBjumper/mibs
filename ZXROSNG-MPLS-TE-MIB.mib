ZXROSNG-MPLS-TE-MIB DEFINITIONS ::= BEGIN

IMPORTS
    OBJECT-TYPE, MODULE-IDENTITY, Unsigned32, IpAddress, Integer32
            FROM SNMPv2-SMI
    MacAddress, DisplayString, RowStatus, TruthValue
            FROM SNMPv2-TC
    zxr10RosngMIB
            FROM ZXR10-SMI;

    zxRosngMplsTeModule MODULE-IDENTITY
            LAST-UPDATED
                "201807111030Z"
            ORGANIZATION
                "ZTE Corporation"
            CONTACT-INFO
                "ZTE Corporation
                 Nanjing Institute of ZTE Corporation
                 No.68 Zijinghua Rd. Yuhuatai District, Nanjing, China
                 Tel: +86-25-52870000 "
            DESCRIPTION
                "MPLS TE"
            REVISION
                "201807111030Z"
            DESCRIPTION
                "add index zxMplsTETnnlAffntyCfgBitName in zxMplsTETnnlAffntyCfgEntry. 
                 add index zxMplsTEIfAffntyCfgBitName in zxMplsTEIfAffntyCfgEntry."
            REVISION
                "201710141330Z"
            DESCRIPTION
                "Modify SYNTAX of zxMplsTEGlobalCfgABandAdjFreq.
                 Modify SYNTAX of zxMplsTETunnelCfgAutoBWFrequency.
                 Modify SYNTAX of zxMplsTETunnelCfgAutoBWMinValue.
                 Modify SYNTAX of zxMplsTETunnelCfgAutoBWMaxValue.
                 Modify SYNTAX of zxMplsTETunnelCfgAutoBWAdjMultiple."
            REVISION
                "201605041630Z"
            DESCRIPTION
                "Add DEFVAL of zxMplsTeP2mpSLspOutSegNexthop,
                modify SYNTAX of zxMplsTeP2mpSLspOutSegNexthop."
            REVISION
                "201511251658Z"
            DESCRIPTION
                "Add zxMplsTeP2mpStaticTnnlCfgTable,zxMplsTeP2mpStaticLspCfgTable,
                zxMplsTeP2mpSLspInSegCfgTable,zxMplsTeP2mpSLspOutSegCfgTable,
                zxMplsTEP2mpSTnnlStatusTable."
            REVISION
                "201511250958Z"
            DESCRIPTION
                "Add a new field zxMplsTEIfCfgAuthKeyChain in ZxMplsTEIfCfgEntry.
                 Add a new field zxMplsTEIfCfgAuthMode in ZxMplsTEIfCfgEntry."
            REVISION
                "201511031425Z"
            DESCRIPTION
                "Add a new field zxMplsStaticTunnelStatusUtilIn in ZxMplsTEStaticTunnelStatusEntry.
                 Add a new field zxMplsTEAccTunnelStatusUtilize in ZxMplsTEAccTunnelStatusEntry.
                 Add a new field zxMplsTEAccTunnelStatusUtilizeIn in ZxMplsTEAccTunnelStatusEntry.
                 Add new table zxMplsTELocalTunnelUtilizeTable.
				 Modify the range of zxMplsTERateLimitCfgCBS in ZxMplsTERateLimitCfgEntry.
                 Modify the range of zxMplsTERateLimitCfgPBS in ZxMplsTERateLimitCfgEntry."
            REVISION
                "201510280958Z"
            DESCRIPTION
                "Add a new field zxMplsTEGlobalCfgMetricAbility in zxMplsTEGlobalCfg.
                 Add a new field zxMplsTETunnelCfgAdvNoneNull in ZxMplsTETunnelCfgEntry."
            REVISION
                "201509200922Z"
            DESCRIPTION
                "Add a new field zxMplsTEIfPassiveNbrIsisFlag in ZxMplsTEIfPassiveCfgEntry."
            REVISION
                "201508041443Z"
            DESCRIPTION
                "Add a new field zxMplsTETunnelCfgActiveLspBfd in ZxMplsTETunnelCfgEntry."
            REVISION
                "201507120955Z"
            DESCRIPTION
                "Add a new field zxMplsTETunnelCfgAutoRouteIpv6 in ZxMplsTETunnelCfgEntry.
                 Add a new field zxMplsTETunnelCfgFAIpv6 in ZxMplsTETunnelCfgEntry.
                 Add a new field zxMplsStaticTunnelCfgARIpv6 in ZxMplsTEStaticTunnelCfgEntry.
                 Add a new field zxMplsStaticTunnelCfgFAIpv6 in ZxMplsTEStaticTunnelCfgEntry.
                 Add a new field zxMplsTETunnelCfgPCEInit in zxMplsTETunnelCfgTable."
            REVISION
                "201505220852Z"
            DESCRIPTION
                "Add a new field zxMplsTEIfBwCfgEIR in ZxMplsTEIfBwCfgEntry."
            REVISION
                "201504231111Z"
            DESCRIPTION
                "Add a new field zxMplsStaticTunnelStatusTnnlUtil in ZxMplsTEStaticTunnelStatusEntry."
            REVISION
                "201502261111Z"
            DESCRIPTION
                "remove index zxMplsTETnnlAffntyCfgType from ZxMplsTETnnlAffntyCfgEntry."
            REVISION
                "201502100955Z"
            DESCRIPTION
                "hop type of zxMplsTEExplicitRouteNCfgTable and zxMplsTEExplicitRouteIDCfgTable support avoid type.
                 add a new field zxMplsTEIfBwCfgSpeedBlind in ZxMplsTEIfBwCfgEntry."
            REVISION
                "201501261111Z"
            DESCRIPTION
                 "Modify the range of zxMplsTEGlobalCfgRetransInterval in zxMplsTEGlobalCfg."
            REVISION
                "201503261111Z"
            DESCRIPTION
                "Modify Size SYNTAX field of zxMplsTEEcmpGroupCfgMinimum in ZxMplsTEEcmpGroupCfgEntry."
            REVISION
                "201411111111Z"
            DESCRIPTION
                "add a new field zxMplsTEEcmpGroupCfgMinimum in ZxMplsTEEcmpGroupCfgEntry.
                 add a new field zxMplsTEEcmpGroupCfgDelay in ZxMplsTEEcmpGroupCfgEntry."				
            REVISION
                "201410281917Z"
            DESCRIPTION
                "add a new field zxMplsStaticTunnelCfgULDiscard in zxMplsTEStaticTunnelCfgTable.
                 add a new field zxMplsTEAccTunnelCfgUlimitDiscard in ZxMplsTEAccTunnelCfgEntry.
                 add a new field zxMplsTETunnelCfgUlimitDiscard in ZxMplsTETunnelCfgEntry."
            REVISION
                "201409170917Z"
            DESCRIPTION
                "Add zxMplsTEGlobalCfgGS in zxMplsTEGlobalCfg table.
                 Add zxMplsTEIfCfgGS in zxMplsTEIfCfgTable table."
            REVISION
                "201407160917Z"
            DESCRIPTION
                "Add DEFVAL of zxMplsTETunnelCfgTnnlEnable in zxMplsTETunnelCfgTable.
                 Modify Size list field of zxMplsTEIfCfgAuthWinSize in zxMplsTEIfCfgTable.
                 Modify Size list field of zxMplsTEEcmpGroupCfgGroupId in zxMplsTEEcmpTunnelCfgTable.
                 Modify Size list field of zxMplsTEEcmpTunnelCfgGroupId in zxMplsTEEcmpTunnelCfgTable.
                 Modify default value of zxMplsTEGlobalCfgUnactiveTime from 300 to 0."
            REVISION
                "201406200917Z"
            DESCRIPTION
                "Modify default value from number to enumeration value."
            REVISION
                "201404290917Z"
            DESCRIPTION
                "Add new field zxMplsTEGlobalCfgWithoutCspf in
                zxMplsTEGlobalCfgTable.
                Add new field zxMplsTEGlobalCfgCspfBestEffort in
                zxMplsTEGlobalCfgTable.
                Add new field zxMplsTEGlobalCfgCspfPrefer in
                zxMplsTEGlobalCfgTable.
                Add new field zxMplsTETunnelCfgWithoutCspf in
                zxMplsTETunnelCfgTable."
            REVISION
                "201403031717Z"
            DESCRIPTION
                "Add new table zxMplsTETnnlPolicyClassCfgTable.
                 Modify STATUS field of zxMplsTEAccTunnelCfgTable
                 and zxMplsTETunnelCfgTable and zxMplsTEStaticTunnelCfgTable.
                 Add four fields in zxMplsTEStaticLspCfgTable.
                 Modify STATUS field of zxMplsTEConvRatioCfgTable.
                 Modify SYNTAX field of zxMplsTETunnelBfdCfgMinTxInterval
                 and zxMplsTETunnelBfdCfgMinRxInterval.
                 Add new field zxMplsTEIfCfgDscpValue in zxMplsTEIfCfgEntry."
            REVISION
                "201402110917Z"
            DESCRIPTION
                "Add new field zxMplsTEGlobalCfgSD in
                zxMplsTEGlobalCfgTable.
                Add new field zxMplsTEGlobalCfgSDInterval in
                zxMplsTEGlobalCfgTable."
            REVISION
                "201401160917Z"
            DESCRIPTION
                    "Add new table zxMplsTETrunkCfgTable.
                     Add new field zxMplsTERateLimitCfgRedAction in ZxMplsTERateLimitCfgEntry."
            REVISION
                "201401061000Z"
            DESCRIPTION
               "TE Tunnel supports configure affinity.
                Add a new table zxMplsTETnnlAffntyCfgTable.
                Add a new table zxMplsTEIfAffntyCfgTable."
            REVISION
                "201312230940Z"
            DESCRIPTION
                    "Add new table. zxMplsTEEcmpGroupCfgTable, zxMplsTEEcmpTunnelCfgTable.
                     Add new field  zxMplsTETunnelCfgHsblspReopt in zxMplsTETunnelCfgTable.
                     Modify the description of field zxMplsTEGlobalCfgRouterID in zxMplsTEGlobalCfg.
                     Modify the description of field zxMplsTEGlobalCfgABackTunnelMinID in
                     zxMplsTEGlobalCfg.
                     Modify the description of field zxMplsTEGlobalCfgABackTunnelMaxID in
                     zxMplsTEGlobalCfg."
            REVISION
                "201312091000Z"
            DESCRIPTION
               "TE Tunnel supports configure tunnel enable or disable.
                Add a new field zxMplsTETunnelCfgTnnlEnable in
                zxMplsTETunnelCfgTable.
                Add a new field zxMplsTEAccTunnelCfgTnnlEnable in
                zxMplsTEAccTunnelCfgTable.
                Delete an old field zxMplsStaticTunnelCfgShareMode in zxMplsTEStaticTunnelCfgTable.
                Add two new fieldes zxMplsStaticTunnelCfgReserveMode,zxMplsStaticTunnelCfgTnnlEnable in
                zxMplsTEStaticTunnelCfgTable.
                Delete eight old fieldes in zxMplsTEStaticLspCfgTable."
            REVISION
                "201311250933Z"
            DESCRIPTION
               "Modify the description of field zxMplsTETunnelCfgFrrFacility in
                zxMplsTETunnelCfgTable.
                Modify the description of field zxMplsTETunnelCfgSessName in
                zxMplsTETunnelCfgTable.
                Modify the description of field zxMplsTEExplicitRouteNCfgIndex in
                zxMplsTEExplicitRouteNCfgTable.
                Modify the description of field zxMplsTEExplicitRouteNCfgNextIP in
                zxMplsTEExplicitRouteNCfgTable.
                Modify the description of field zxMplsTEExplicitRouteNCfgHopType in
                zxMplsTEExplicitRouteNCfgTable.
                Modify the description of field zxMplsTEExplicitRouteIDCfgIndex in
                zxMplsTEExplicitRouteIDCfgTable.
                Modify the description of field zxMplsTEExplicitRouteIDCfgNextIP in
                zxMplsTEExplicitRouteIDCfgTable.
                Modify the description of field zxMplsTEExplicitRouteIDCfgHopType in
                zxMplsTEExplicitRouteIDCfgTable.
                Modify the description of field zxMplsTEPathOptCfgLockDown in
                zxMplsTEPathOptCfgTable.
                Modify the description of field zxMplsTEHotStandbyCfgTunnelName in
                zxMplsTEHotStandbyCfgTable.
                Modify the description of field zxMplsTEHotStandbyCfgProtOptNo in
                zxMplsTEHotStandbyCfgTable.
                Modify the description of field zxMplsTETunnelBfdCfgTunnelName in
                zxMplsTETunnelBfdCfgTable.
                Modify the description of field zxMplsTEIfCfgIfIndex in
                zxMplsTEIfCfgTable."
	    REVISION
                "201310101535Z"
            DESCRIPTION
                "Add new field zxMplsTETunnelCfgSessName in
                zxMplsTETunnelCfgTable."
            REVISION
                "201310101535Z"
            DESCRIPTION
                "Add new field zxMplsTETunnelCfgSoftPreemption in
                zxMplsTETunnelCfgTable.
                Add new field zxMplsTEGlobalCfgSoftPreempt in
                zxMplsTEGlobalCfgTable."
            REVISION
                "201310101136Z"
            DESCRIPTION
                "Add new field zxMplsTETunnelCfgResvStyle in
                zxMplsTETunnelCfgTable."
            REVISION
                "201309171401Z"
            DESCRIPTION
               "Add new field zxMplsTETunnelCfgHopsLimit in
                zxMplsTETunnelCfgTable.
                Add new field zxMplsTETunnelCfgHopsPrior in
                zxMplsTETunnelCfgTable.
                Add new field zxMplsTEGlobalCfgDelaySwOver in
                zxMplsTEGlobalCfgTable.
                Add new field zxMplsTEGlobalCfgDelayReact in
                zxMplsTEGlobalCfgTable.
                Add new field zxMplsTEGlobalCfgDelayLinkUp in
                zxMplsTEGlobalCfgTable.
                Add new field zxMplsTEGlobalCfgAutoBckSrlgExMo in
                zxMplsTEGlobalCfgTable.
                Add new field zxMplsTEGlobalCfgFacFrrSrlgExMo in 
                zxMplsTEGlobalCfgTable.
                Add new field zxMplsTEGlobalCfgHsbSrlgExMo in
                zxMplsTEGlobalCfgTable.
                Add new field zxMplsTEGlobalCfgDetourSrlgExMo in
                zxMplsTEGlobalCfgTable."
            REVISION
                "201308021521Z"
            DESCRIPTION
                "TE supports configure convergence ratio.
                Add a new field zxMplsTEIfCfgConvRatioValue in
                zxMplsTEIfCfgTable,
                and a new table zxMplsTEConvRatioCfgTable."
            REVISION
                "201307191100Z"
            DESCRIPTION
                "modify upper limit of field
                 zxMplsTEGlobalCfgABackTunnelMinID from 65534 to 65535."
            REVISION
                "201307121119Z"
            DESCRIPTION
                "Add a new field zxMplsTEIfBwCfgPercent in
                zxMplsTEIfBwCfgTable."
            REVISION
                "201306291639Z"
            DESCRIPTION
                "Add new field zxMplsTETunnelCfgAssocTnnlID in
                zxMplsTETunnelCfgTable.
                 Add new field zxMplsStaticTunnelCfgAssocTnnlID in
                zxMplsTEStaticTunnelCfgTable
                 Add new field zxMplsStaticTunnelStatusAssoc in
                zxMplsTEStaticTunnelStatusTable
                 Add new field zxMplsTEAccTunnelStatusAssoc in
                zxMplsTEAccTunnelStatusTable."
            REVISION
                "201306281415Z"
            DESCRIPTION
                "Add new fields zxMplsTETunnelCfgBfdEnable,
                zxMplsTETunnelCfgBfdDeteMultiplier,
                zxMplsTETunnelCfgBFDMinTxInterval
                and zxMplsTETunnelCfgBFDMinRxInterval in
                zxMplsTETunnelCfgTable."
            REVISION
                "201306241500Z"
            DESCRIPTION
                "TE supports tunnel crankback."                
            REVISION
                "201306191530Z"
            DESCRIPTION
                "Add new field zxMplsTETunnelCfgBwProtectEnable in
                zxMplsTETunnelCfgTable."
            REVISION
                "201306131136Z"
            DESCRIPTION
                "Add new field zxMplsTEGlobalCfgReoptLooseNode in
                zxMplsTEGlobalCfgTable."
            REVISION
                "201305280952Z"
            DESCRIPTION
                "TE supports tunnel rate-limit."
            REVISION
                "201305161520Z"
            DESCRIPTION
                "Add new fields zxMplsStaticTunnelCfgFAEnable and
                zxMplsStaticTunnelCfgFAHoldtime in
                zxMplsTEStaticTunnelCfgTable."
            REVISION
                "201305101130Z"
            DESCRIPTION
                "Add new fields zxMplsStaticTunnelCfgAutoRoute,
                zxMplsStaticTunnelCfgARMtrType,zxMplsStaticTunnelCfgARRelaMtr
                and zxMplsStaticTunnelCfgARAbsMtr in
                zxMplsTEStaticTunnelCfgTable."
            REVISION
                "201305071030Z"
            DESCRIPTION
                "Add a new field zxMplsTETunnelCfgRefenceHsbPath 
                in zxMplsTETunnelCfgTable."
            REVISION
                "201305021050Z"
            DESCRIPTION
                "Add a new field zxMplsTETunnelCfgHsblspFrr
                in zxMplsTETunnelCfgTable."
            REVISION
                "201304251050Z"
            DESCRIPTION
                "Add a new field zxMplsTETunnelCfgMainlspReopt
                in zxMplsTETunnelCfgTable."
            REVISION
                "201304171556Z"
            DESCRIPTION
                "TE supports hotstandby to exclude path."
            REVISION
                "201304111030Z"
            DESCRIPTION
                "TE supports configure node gr."
            REVISION
                "201304071730Z"
            DESCRIPTION
                "Enlarge policy class value range to 0~7."
            REVISION
                "201303251127Z"
            DESCRIPTION
                "TE LSP supports configure CIR,EIR."
            REVISION
                "201303121700Z"
            DESCRIPTION
                "Revisions modified by MPLS-TE OMI DE."
            REVISION
                "200507260000Z"
            DESCRIPTION
                ""
            ::= { zxr10RosngMIB 204}

            zxRosngMplsTeMIB OBJECT IDENTIFIER ::= { zxRosngMplsTeModule 1}


--*************************************************************************
--  zxMplsTEGlobalCfg
--*************************************************************************
zxMplsTEGlobalCfg
      OBJECT IDENTIFIER ::= { zxRosngMplsTeMIB 1 }

zxMplsTEGlobalCfgTEEnable    OBJECT-TYPE
      SYNTAX   INTEGER {false(0), true(1)}
      MAX-ACCESS   read-write
      STATUS      current
      DESCRIPTION    "If this object is true, then it enables
                      the mplsTETunnel."
      DEFVAL  { false }
      ::= { zxMplsTEGlobalCfg 1}

zxMplsTEGlobalCfgRsvpExpNull  OBJECT-TYPE
     SYNTAX     INTEGER {false(0), true(1)}
     MAX-ACCESS   read-write
     STATUS      current
     DESCRIPTION
            "If this object is true, then it enables the explicit null label."
     DEFVAL  { false }
     ::= { zxMplsTEGlobalCfg 2}

zxMplsTEGlobalCfgRsvpNoneNull    OBJECT-TYPE
     SYNTAX   INTEGER {false(0), true(1)}
     MAX-ACCESS   read-write
     STATUS      current
     DESCRIPTION
            "If this object is true, then it enables the none null label."
     DEFVAL  { false }
     ::= { zxMplsTEGlobalCfg 3}

zxMplsTEGlobalCfgGR  OBJECT-TYPE
     SYNTAX     INTEGER {false(0), true(1)}
     MAX-ACCESS   read-write
     STATUS      current
     DESCRIPTION
            "If this object is true, then it enables the GR."
     DEFVAL  { false }
     ::= { zxMplsTEGlobalCfg 4}


zxMplsTEGlobalCfgGRRefInterval  OBJECT-TYPE
     SYNTAX     Unsigned32(1000..30000)
     MAX-ACCESS   read-write
     STATUS      current
     DESCRIPTION
            "Graceful-restart interval time 1000~30000(ms)."
     DEFVAL  { 10000 }
     ::= { zxMplsTEGlobalCfg 5}

zxMplsTEGlobalCfgGRRefMisses  OBJECT-TYPE
     SYNTAX     Unsigned32(4..10)
     MAX-ACCESS   read-write
     STATUS      current
     DESCRIPTION
            "Graceful-restart miss number 4~10."
      DEFVAL  { 4 }
     ::= { zxMplsTEGlobalCfg 6}

zxMplsTEGlobalCfgGRRecoverTime  OBJECT-TYPE
     SYNTAX     Unsigned32(120000..600000)
     MAX-ACCESS   read-write
     STATUS      current
     DESCRIPTION
            "Graceful-restart RecoveryTime 120000~600000(ms)."
     DEFVAL  { 120000 }
     ::= { zxMplsTEGlobalCfg 7}

zxMplsTEGlobalCfgGRRestartTime  OBJECT-TYPE
     SYNTAX     Unsigned32(120000..600000)
     MAX-ACCESS   read-write
     STATUS      current
     DESCRIPTION
            "Graceful-restart time 120000~600000(ms)."
     DEFVAL  { 120000 }
     ::= { zxMplsTEGlobalCfg 8}

zxMplsTEGlobalCfgSignalRefInterval  OBJECT-TYPE
     SYNTAX     Unsigned32(5000..65535000)
     MAX-ACCESS   read-write
     STATUS      current
     DESCRIPTION
            "RefreshInterval 5000~65535000(ms)."
     DEFVAL  { 30000 }
     ::= { zxMplsTEGlobalCfg 9}


zxMplsTEGlobalCfgSignalRefMisses  OBJECT-TYPE
     SYNTAX     Unsigned32(2..10)
     MAX-ACCESS   read-write
     STATUS      current
     DESCRIPTION
            "SignallingRefreshMisses 2~10."
     DEFVAL  { 4 }
     ::= { zxMplsTEGlobalCfg 10}

zxMplsTEGlobalCfgABackTunnelMinID  OBJECT-TYPE
     SYNTAX     Unsigned32(1..65535)
     MAX-ACCESS   read-write
     STATUS      current
     DESCRIPTION
            "The Min tunnelID can be used by Auto backup tunnel."
     ::= { zxMplsTEGlobalCfg 11}

zxMplsTEGlobalCfgABackTunnelMaxID  OBJECT-TYPE
     SYNTAX     Unsigned32(2..65535)
     MAX-ACCESS   read-write
     STATUS      current
     DESCRIPTION
            "The Max tunnelID can be used by Auto backup tunnel."
     ::= { zxMplsTEGlobalCfg 12}

zxMplsTEGlobalCfgRouterID  OBJECT-TYPE
     SYNTAX      IpAddress
     MAX-ACCESS   read-write
     STATUS      current
     DESCRIPTION
            "MPLS TE Router ID."
     DEFVAL  {'00000000'H }
     ::= { zxMplsTEGlobalCfg 13}

zxMplsTEGlobalCfgResvConfirm  OBJECT-TYPE
     SYNTAX     INTEGER {false(0), true(1)}
     MAX-ACCESS   read-write
     STATUS      current
     DESCRIPTION
            "If this object is true, then it enables the ResvConfirm."
      DEFVAL  { false }
     ::= { zxMplsTEGlobalCfg 14}

zxMplsTEGlobalCfgRefReduction  OBJECT-TYPE
     SYNTAX     INTEGER {false(0), true(1)}
     MAX-ACCESS   read-write
     STATUS      current
     DESCRIPTION
            "If this object is true, then it enables the refresh reduction."
     DEFVAL  { false }
     ::= { zxMplsTEGlobalCfg 15}

zxMplsTEGlobalCfgRetransmit  OBJECT-TYPE
     SYNTAX     INTEGER {false(0), true(1)}
     MAX-ACCESS   read-write
     STATUS      current
     DESCRIPTION
            "If this object is true, then it enables the retransmit."
     DEFVAL  { false }
     ::= { zxMplsTEGlobalCfg 16}

zxMplsTEGlobalCfgRetransInterval  OBJECT-TYPE
     SYNTAX     Unsigned32(500..60000)
     MAX-ACCESS   read-write
     STATUS      current
     DESCRIPTION
            "Retransmit interval time 500~60000(ms)."
     DEFVAL  { 1000 }
     ::= { zxMplsTEGlobalCfg 17}

zxMplsTEGlobalCfgRetransLimit  OBJECT-TYPE
     SYNTAX     Unsigned32(2..10)
     MAX-ACCESS   read-write
     STATUS      current
     DESCRIPTION
            "Retransmit miss number 2~10."
     DEFVAL  { 3 }
     ::= { zxMplsTEGlobalCfg 18}


zxMplsTEGlobalCfgFrrPromTimerInterval  OBJECT-TYPE
     SYNTAX     Unsigned32(60..604800)
     MAX-ACCESS   read-write
     STATUS      current
     DESCRIPTION
            "Fast reroute interval time 60~604800(s)."
     DEFVAL  { 300 }
     ::= { zxMplsTEGlobalCfg 19}

zxMplsTEGlobalCfgABandAdjust  OBJECT-TYPE
     SYNTAX     INTEGER {false(0), true(1)}
     MAX-ACCESS   read-write
     STATUS      current
     DESCRIPTION
            "If this object is true, then it enables sampling bandwidth."
     DEFVAL  { false }
     ::= { zxMplsTEGlobalCfg 20}

zxMplsTEGlobalCfgABandAdjFreq  OBJECT-TYPE
     SYNTAX     Unsigned32(10..604800)
     MAX-ACCESS   read-write
     STATUS      current
     DESCRIPTION
            "Auto bandwidth sampling frequency."
     DEFVAL  { 300 }
     ::= { zxMplsTEGlobalCfg 21}

zxMplsTEGlobalCfgReoptimizeFreq     OBJECT-TYPE
     SYNTAX     Unsigned32(30..604800)
     MAX-ACCESS   read-write
     STATUS      current
     DESCRIPTION
            "The tunnels reoptimize timer frequency 30~604800 (s)."
     DEFVAL  { 0 }
     ::= { zxMplsTEGlobalCfg 22}

zxMplsTEGlobalCfgReoptimizeEvent  OBJECT-TYPE
     SYNTAX     INTEGER {none(0), linkup(1)}
     MAX-ACCESS   read-write
     STATUS      current
     DESCRIPTION
            "The tunnels event reoptimize type."
     DEFVAL  { none }
     ::= { zxMplsTEGlobalCfg 23}

zxMplsTEGlobalCfgFrrHelloEnabled     OBJECT-TYPE
     SYNTAX     INTEGER {false(0), true(1)}
     MAX-ACCESS   read-write
     STATUS      current
     DESCRIPTION
            "Enables or disables hello message in global-configuration mode
            which is defined in RFC3209."
     DEFVAL  { false }
     ::= { zxMplsTEGlobalCfg 24}

zxMplsTEGlobalCfgSrlgExcluMode   OBJECT-TYPE
     SYNTAX     INTEGER{force(0), preferred(1), none(2)}
     MAX-ACCESS   read-write
     STATUS      obsolete
     DESCRIPTION
            "Auto backup tunnels avoid SRLGs mode of protected interface
            (force(0),preferred(1),none(2))."
     DEFVAL  { none }
     ::= { zxMplsTEGlobalCfg 25}

zxMplsTEGlobalCfgNodeHello   OBJECT-TYPE
     SYNTAX     TruthValue
     MAX-ACCESS   read-write
     STATUS      current
     DESCRIPTION
            "If this object is true, then it enables the Node Hello."
     DEFVAL  { false }
     ::= { zxMplsTEGlobalCfg 26}

 zxMplsTEGlobalCfgDsteModel  OBJECT-TYPE
     SYNTAX     INTEGER{mam(1), mplste(2), rdm(3), extendmam(254), nonte(255)}
     MAX-ACCESS   read-write
     STATUS      current
     DESCRIPTION
            "DS-TE bandwidth reserve model."
     ::= { zxMplsTEGlobalCfg 27}
zxMplsTEGlobalCfgFrrProm	 OBJECT-TYPE  
     SYNTAX     INTEGER{true(1), false(2)}
     MAX-ACCESS   read-write
     STATUS      current   
     DESCRIPTION
     " Fast reroute timers promotion enable."  
     DEFVAL  { false }
     ::= { zxMplsTEGlobalCfg 28}  
zxMplsTEGlobalCfgCleanDelayTime  OBJECT-TYPE
     SYNTAX     INTEGER(0..600)
     MAX-ACCESS   read-write
     STATUS      current
     DESCRIPTION
            "The tunnels wait timer  0~600 (s),then delete old lsp."
     DEFVAL  { 15 }
     ::= { zxMplsTEGlobalCfg 29}

zxMplsTEGlobalCfgInstallDelayTime    OBJECT-TYPE
     SYNTAX     INTEGER(0..600)
     MAX-ACCESS   read-write
     STATUS      current
     DESCRIPTION
            "The tunnels wait timer  0~600 (s),then install the active lsp."
     DEFVAL  { 10 }
     ::= { zxMplsTEGlobalCfg 30}

zxMplsTEGlobalCfgUnactiveTime    OBJECT-TYPE
     SYNTAX     Unsigned32(30..300)
     MAX-ACCESS   read-write
     STATUS      current
     DESCRIPTION
            "Wait the timer 30~300 (s) ,then attempt to active the
            down tunnels."
     DEFVAL  { 0 }
     ::= { zxMplsTEGlobalCfg 31}
zxMplsTEGlobalCfgGrExtend  OBJECT-TYPE
     SYNTAX     TruthValue
     MAX-ACCESS   read-write
     STATUS      current
     DESCRIPTION
            "If this object is true, then it enables extend recovery-path."
     DEFVAL  { false }
     ::= { zxMplsTEGlobalCfg 32}

zxMplsTEGlobalCfgReoptLooseNode  OBJECT-TYPE
     SYNTAX     TruthValue
     MAX-ACCESS   read-write
     STATUS      current
     DESCRIPTION
            "Enable or disable loose node reoptimize."
     DEFVAL  { false }
     ::= { zxMplsTEGlobalCfg 33}

zxMplsTEGlobalCfgCrankbackLimit    OBJECT-TYPE
     SYNTAX     INTEGER(1..10)
     MAX-ACCESS   read-write
     STATUS      current
     DESCRIPTION
            "Limited times for crankback retrying."
     DEFVAL  { 5 }
     ::= { zxMplsTEGlobalCfg 34}

zxMplsTEGlobalCfgCrankbackTtl    OBJECT-TYPE
     SYNTAX     Unsigned32(30..300)
     MAX-ACCESS   read-write
     STATUS      current
     DESCRIPTION
            "TTL for crankback information."
     DEFVAL  { 60 }
     ::= { zxMplsTEGlobalCfg 35}
zxMplsTEGlobalCfgAutoBckSrlgExMo   OBJECT-TYPE
     SYNTAX     INTEGER{none(0),force(1), preferred(2) }
     MAX-ACCESS   read-write
     STATUS      current
     DESCRIPTION
            "Auto backup tunnels avoid  avoid SRLGs mode of protected interface
            (none(0),force(1), preferred(2))."
     DEFVAL  { none }
     ::= { zxMplsTEGlobalCfg 36}
zxMplsTEGlobalCfgFacFrrSrlgExMo   OBJECT-TYPE
     SYNTAX     INTEGER{none(0),force(1), preferred(2) }
     MAX-ACCESS   read-write
     STATUS      current
     DESCRIPTION
            "Facility fast route tunnel avoid SRLGs mode of protected interface
            (none(0),force(1), preferred(2))."
     DEFVAL  { none }
     ::= { zxMplsTEGlobalCfg 37}
zxMplsTEGlobalCfgHsbSrlgExMo   OBJECT-TYPE
     SYNTAX     INTEGER{none(0),force(1), preferred(2) }
     MAX-ACCESS   read-write
     STATUS      current
     DESCRIPTION
            "Hotstandby tunnels avoid SRLGs mode of protected main links
            (none(0),force(1), preferred(2))."
     DEFVAL  { 0 }
     ::= { zxMplsTEGlobalCfg 38}
zxMplsTEGlobalCfgDetourSrlgExMo   OBJECT-TYPE
     SYNTAX     INTEGER{none(0),force(1), preferred(2) }
     MAX-ACCESS   read-write
     STATUS      current
     DESCRIPTION
            "Detour fast route tunnel avoid SRLGs mode of protected interface
            (none(0),force(1), preferred(2))."
     DEFVAL  { 0 }
     ::= { zxMplsTEGlobalCfg 39}
     
zxMplsTEGlobalCfgDelaySwOver    OBJECT-TYPE
     SYNTAX     Unsigned32(0..90)
     MAX-ACCESS   read-write
     STATUS      current
     DESCRIPTION
            "Delay time for switch-over."
     DEFVAL  { 0 }
     ::= { zxMplsTEGlobalCfg 40}
zxMplsTEGlobalCfgDelayReact    OBJECT-TYPE
     SYNTAX     Unsigned32(0..30)
     MAX-ACCESS   read-write
     STATUS      current
     DESCRIPTION
            "Delay time for reactive."
     DEFVAL  { 10 }
     ::= { zxMplsTEGlobalCfg 41}
zxMplsTEGlobalCfgDelayLinkUp    OBJECT-TYPE
     SYNTAX     Unsigned32(0..30)
     MAX-ACCESS   read-write
     STATUS      current
     DESCRIPTION
            "Delay time for link-up."
     DEFVAL  { 0 }
     ::= { zxMplsTEGlobalCfg 42}   
zxMplsTEGlobalCfgSoftPreempt  OBJECT-TYPE
     SYNTAX     INTEGER(1..300)
     MAX-ACCESS   read-write
     STATUS      current
     DESCRIPTION
            "Specify timeout for soft-preemption."
     DEFVAL  { 30 }
     ::= { zxMplsTEGlobalCfg 43}
zxMplsTEGlobalCfgSD  OBJECT-TYPE
     SYNTAX     INTEGER {true(1), false(2)}
     MAX-ACCESS   read-write
     STATUS      current
     DESCRIPTION
            "Enable RSVP SD."
     DEFVAL  { false }
     ::= { zxMplsTEGlobalCfg 44}
zxMplsTEGlobalCfgSDInterval  OBJECT-TYPE
     SYNTAX     Unsigned32(10..30)
     MAX-ACCESS   read-write
     STATUS      current
     DESCRIPTION
            "interval between sd alarm 10~30(s)."
     DEFVAL  { 10 }
     ::= { zxMplsTEGlobalCfg 45}
zxMplsTEGlobalCfgWithoutCspf  OBJECT-TYPE
     SYNTAX     INTEGER {true(1), false(2)}
     MAX-ACCESS   read-write
     STATUS      current
     DESCRIPTION
            "Build path ERO without CSPF."
     DEFVAL  { false }
     ::= { zxMplsTEGlobalCfg 46}
zxMplsTEGlobalCfgCspfBestEffort  OBJECT-TYPE
     SYNTAX     INTEGER {true(1), false(2)}
     MAX-ACCESS   read-write
     STATUS      current
     DESCRIPTION
            "Enable best-effort CSPF without bandwidth requirement."
     DEFVAL  { false }
     ::= { zxMplsTEGlobalCfg 47}
zxMplsTEGlobalCfgCspfPrefer  OBJECT-TYPE
     SYNTAX     INTEGER{ospf(1), isis(2)}
     MAX-ACCESS   read-write
     STATUS      current
     DESCRIPTION
            "Specify preferred igp protocol for CSPF."
     DEFVAL  { ospf }
     ::= { zxMplsTEGlobalCfg 48}
     
zxMplsTEGlobalCfgGS  OBJECT-TYPE
     SYNTAX     INTEGER {true(1), false(2)}
     MAX-ACCESS   read-write
     STATUS      current
     DESCRIPTION
            "Enable RSVP GS."
     DEFVAL  { false }
     ::= { zxMplsTEGlobalCfg 49}

zxMplsTEGlobalCfgMetricAbility  OBJECT-TYPE
     SYNTAX     TruthValue
     MAX-ACCESS   read-write
     STATUS      current
     DESCRIPTION
            "Enable RSVP Metric Ability."
     DEFVAL  { true }
     ::= { zxMplsTEGlobalCfg 50}
     
--*************************************************************************
--  zxMplsTEGlobalOper
--*************************************************************************

zxMplsTEGlobalOper OBJECT IDENTIFIER ::= { zxRosngMplsTeMIB 2 }

zxMplsTEGlobalOperFrrPromAtOnce OBJECT-TYPE
    SYNTAX      INTEGER {undo(0), do(1)}
    MAX-ACCESS  read-write
    STATUS      current
    DESCRIPTION
            "This value identifies the rsvp manual frr promote at once."
    ::= { zxMplsTEGlobalOper 1 }

zxMplsTEGlobalOperReoptimizeAll OBJECT-TYPE
    SYNTAX      INTEGER {undo(0), do(1)}
    MAX-ACCESS  read-write
    STATUS      current
    DESCRIPTION
            "This value identifies the manual reoptimize all the tunnel ."
    ::= { zxMplsTEGlobalOper 2 }

zxMplsTEGlobalOperReoptimizeTunnelID OBJECT-TYPE
    SYNTAX      Unsigned32(1..65535)
    MAX-ACCESS  read-write
    STATUS      current
    DESCRIPTION
            "This value identifies the manual reoptimize  the tunnel ."
    ::= { zxMplsTEGlobalOper 3 }

zxMplsTEGlobalOperClearRsvp OBJECT-TYPE
    SYNTAX      INTEGER {undo(0), do(1)}
    MAX-ACCESS  read-write
    STATUS      current
    DESCRIPTION
            "This value identifies the clear mpls rsvp ."
    ::= { zxMplsTEGlobalOper 4 }

--*************************************************************************
--  zxMplsTEAccTunnelCfgTable
--*************************************************************************

zxMplsTEAccTunnelCfgTable OBJECT-TYPE
    SYNTAX      SEQUENCE OF ZxMplsTEAccTunnelCfgEntry
    MAX-ACCESS  not-accessible
    STATUS      current
    DESCRIPTION
            ""
    ::= { zxRosngMplsTeMIB 3 }

zxMplsTEAccTunnelCfgEntry OBJECT-TYPE
    SYNTAX      ZxMplsTEAccTunnelCfgEntry
    MAX-ACCESS  not-accessible
    STATUS      current
    DESCRIPTION
            ""
    INDEX   { zxMplsTEAccTunnelCfgTunnelName }
    ::= { zxMplsTEAccTunnelCfgTable 1 }

ZxMplsTEAccTunnelCfgEntry ::=
    SEQUENCE {
        zxMplsTEAccTunnelCfgTunnelName          DisplayString,
        zxMplsTEAccTunnelCfgTunnelId            Unsigned32,
        zxMplsTEAccTunnelCfgDirectionType       INTEGER,
        zxMplsTEAccTunnelCfgRole                INTEGER,
        zxMplsTEAccTunnelCfgIngressTunnelId     Unsigned32,
        zxMplsTEAccTunnelCfgIngressLSRId        IpAddress,
        zxMplsTEAccTunnelCfgEgressLSRId         IpAddress,
        zxMplsTEAccTunnelCfgPolicyClass         Integer32,
        zxMplsTEAccTunnelCfgRowStatus           RowStatus,
        zxMplsTEAccTunnelCfgTnnlEnable          INTEGER,
        zxMplsTEAccTunnelCfgUlimitDiscard       INTEGER
    }


zxMplsTEAccTunnelCfgTunnelName OBJECT-TYPE
    SYNTAX      DisplayString(SIZE(0..31))
    MAX-ACCESS  not-accessible
    STATUS      current
    DESCRIPTION
            "Access tunnel name."
    ::= { zxMplsTEAccTunnelCfgEntry 1 }

zxMplsTEAccTunnelCfgTunnelId OBJECT-TYPE
    SYNTAX      Unsigned32(1..131072)
    MAX-ACCESS  read-only
    STATUS      current
    DESCRIPTION
            "Uniquely identifies a set of access tunnel instances ."
    ::= { zxMplsTEAccTunnelCfgEntry 2 }

zxMplsTEAccTunnelCfgDirectionType OBJECT-TYPE
    SYNTAX      INTEGER{unidirection(1),bidirecttion(2)}
    MAX-ACCESS  read-create
    STATUS      current
    DESCRIPTION
            "This value signifies the direction of the access tunnel."
    ::= { zxMplsTEAccTunnelCfgEntry 3 }

zxMplsTEAccTunnelCfgRole OBJECT-TYPE
    SYNTAX      INTEGER{transit(2),tail(3)}
    MAX-ACCESS  read-create
    STATUS      current
    DESCRIPTION
            "This value signifies the role that this access tunnel
            entry/instance represents."
    ::= { zxMplsTEAccTunnelCfgEntry 4 }


zxMplsTEAccTunnelCfgIngressTunnelId OBJECT-TYPE
    SYNTAX      Unsigned32(1..65535)
    MAX-ACCESS  read-create
    STATUS      current
    DESCRIPTION
            "The access tunnel's ingress tunnel id."
    ::= { zxMplsTEAccTunnelCfgEntry 5 }

zxMplsTEAccTunnelCfgIngressLSRId OBJECT-TYPE
    SYNTAX      IpAddress
    MAX-ACCESS  read-create
    STATUS      current
    DESCRIPTION
            "Identity of the access tunnel ingress LSR ."
    ::= { zxMplsTEAccTunnelCfgEntry 6 }

zxMplsTEAccTunnelCfgEgressLSRId OBJECT-TYPE
    SYNTAX      IpAddress
    MAX-ACCESS  read-create
    STATUS      current
    DESCRIPTION
            "Identity of the access tunnel egress LSR ."
    ::= { zxMplsTEAccTunnelCfgEntry 7 }


zxMplsTEAccTunnelCfgPolicyClass   OBJECT-TYPE
    SYNTAX      Integer32(0..7|255)
    MAX-ACCESS  read-only
    STATUS      current
    DESCRIPTION
            "The minimal configured policy class on the access tunnel."
    DEFVAL { 255 }            
    ::= { zxMplsTEAccTunnelCfgEntry 8 }

zxMplsTEAccTunnelCfgRowStatus OBJECT-TYPE
    SYNTAX      RowStatus
    MAX-ACCESS  read-create
    STATUS      current
    DESCRIPTION
            "Row status."
    ::= { zxMplsTEAccTunnelCfgEntry 9 }

zxMplsTEAccTunnelCfgTnnlEnable OBJECT-TYPE
    SYNTAX      INTEGER {true(1), false(2), invalid(3)}
    MAX-ACCESS  read-create
    STATUS      current
    DESCRIPTION
            "If this object is true, then activate the tunnel."
    ::= { zxMplsTEAccTunnelCfgEntry 10 }

zxMplsTEAccTunnelCfgUlimitDiscard OBJECT-TYPE
    SYNTAX      INTEGER{disabled(1), enabled(2)}
    MAX-ACCESS  read-create
    STATUS      current
    DESCRIPTION
            "If this tunnel enables ultralimit discard, this value is
            enabled, otherwise it is disabled."
    DEFVAL { disabled }
    ::= { zxMplsTEAccTunnelCfgEntry 11 }

--*************************************************************************
--  zxMplsTETunnelCfgTable
--*************************************************************************

zxMplsTETunnelCfgTable OBJECT-TYPE
    SYNTAX      SEQUENCE OF ZxMplsTETunnelCfgEntry
    MAX-ACCESS  not-accessible
    STATUS      current
    DESCRIPTION
            ""
    ::= { zxRosngMplsTeMIB 4 }

zxMplsTETunnelCfgEntry OBJECT-TYPE
    SYNTAX      ZxMplsTETunnelCfgEntry
    MAX-ACCESS  not-accessible
    STATUS      current
    DESCRIPTION
            ""
    INDEX   { zxMplsTETunnelCfgTunnelName }
    ::= { zxMplsTETunnelCfgTable 1 }

ZxMplsTETunnelCfgEntry ::=
    SEQUENCE {
        zxMplsTETunnelCfgTunnelName         DisplayString,
        zxMplsTETunnelCfgTunnelID           Unsigned32,
        zxMplsTETunnelCfgEgressLSRId        IpAddress,
        zxMplsTETunnelCfgSetupPrio          Integer32,
        zxMplsTETunnelCfgHoldingPrio        Integer32,
        zxMplsTETunnelCfgFrrFacility        INTEGER,
        zxMplsTETunnelCfgFrrDetour          INTEGER,
        zxMplsTETunnelCfgAutoRoute          INTEGER,
        zxMplsTETunnelCfgARMetricType       INTEGER,
        zxMplsTETunnelCfgARRelaMetric       Integer32,
        zxMplsTETunnelCfgARAbsMetric        Unsigned32,
        zxMplsTETunnelCfgRecordRoute        INTEGER,
        zxMplsTETunnelCfgBfdEnable          INTEGER,
        zxMplsTETunnelCfgBfdDeteMultiplier  Unsigned32,
        zxMplsTETunnelCfgBFDMinTxInterval   Unsigned32,
        zxMplsTETunnelCfgBFDMinRxInterval   Unsigned32,
        zxMplsTETunnelCfgCoRoute            INTEGER,
        zxMplsTETunnelCfgBandwidth          Unsigned32,
        zxMplsTETunnelCfgBackupBandwidth    Unsigned32,
        zxMplsTETunnelCfgFAEnable           INTEGER,
        zxMplsTETunnelCfgFAHoldtime         Unsigned32,
        zxMplsTETunnelCfgAdminWeight        Unsigned32,
        zxMplsTETunnelCfgAutoBW             INTEGER,
        zxMplsTETunnelCfgAutoBWFrequency    Unsigned32,
        zxMplsTETunnelCfgAutoBWMinValue     Unsigned32,
        zxMplsTETunnelCfgAutoBWMaxValue     Unsigned32,
        zxMplsTETunnelCfgAutoBWAdjMultiple  Unsigned32,
        zxMplsTETunnelCfgPolicyClass        Integer32,
        zxMplsTETunnelCfgRowStatus          RowStatus,
        zxMplsTETunnelCfgCBS                Unsigned32,
        zxMplsTETunnelCfgEIR                Unsigned32,
        zxMplsTETunnelCfgEBS                Unsigned32,
        zxMplsTETunnelCfgAutoBWThresholdPer    Unsigned32,
        zxMplsTETunnelCfgAutoBWThresholdMin    Unsigned32,
        zxMplsTETunnelCfgAutoBWThresholdLimit    Unsigned32,
        zxMplsTETunnelCfgAutoBWcollectbw        INTEGER,
        zxMplsTETunnelCfgMainlspReopt           TruthValue,
        zxMplsTETunnelCfgHsblspFrr              TruthValue,
        zxMplsTETunnelCfgRefenceHsbPath     TruthValue,
        zxMplsTETunnelCfgBwProtectEnable    TruthValue,
        zxMplsTETunnelCfgCrankbackEnable    TruthValue,
        zxMplsTETunnelCfgAssocTnnlID        Unsigned32,
        zxMplsTETunnelCfgHopsLimit         Unsigned32,
        zxMplsTETunnelCfgHopsPrior            INTEGER,
        zxMplsTETunnelCfgSoftPreemption     TruthValue,
        zxMplsTETunnelCfgResvStyle            INTEGER,
	zxMplsTETunnelCfgSessName           DisplayString,
        zxMplsTETunnelCfgTnnlEnable          INTEGER,
        zxMplsTETunnelCfgHsblspReopt             TruthValue,
        zxMplsTETunnelCfgWithoutCspf         TruthValue,
        zxMplsTETunnelCfgTrackName          DisplayString,
        zxMplsTETunnelCfgEscapePath         TruthValue,
        zxMplsTETunnelCfgUlimitDiscard     INTEGER,
        zxMplsTETunnelCfgE2EProtect         TruthValue,
        zxMplsTETunnelCfgAutoRouteIpv6      TruthValue,
        zxMplsTETunnelCfgFAIpv6             TruthValue,   
        zxMplsTETunnelCfgPCEInit            TruthValue,
        zxMplsTETunnelCfgActiveLspBfd       TruthValue,
        zxMplsTETunnelCfgAdvNoneNull        TruthValue
    }


zxMplsTETunnelCfgTunnelName OBJECT-TYPE
    SYNTAX      DisplayString(SIZE(0..31))
    MAX-ACCESS  not-accessible
    STATUS      current
    DESCRIPTION
            "Tunnel name."
    ::= { zxMplsTETunnelCfgEntry 1 }

zxMplsTETunnelCfgTunnelID OBJECT-TYPE
    SYNTAX      Unsigned32(1..65535)
    MAX-ACCESS  read-only
    STATUS      current
    DESCRIPTION
            "Uniquely identifies a set of tunnel instances between a pair of
            ingress and egress LSRs."
    ::= { zxMplsTETunnelCfgEntry 2 }

zxMplsTETunnelCfgEgressLSRId OBJECT-TYPE
    SYNTAX      IpAddress
    MAX-ACCESS  read-create
    STATUS      current
    DESCRIPTION
            "Identity of the egress LSR associated with this tunnel instance."
    ::= { zxMplsTETunnelCfgEntry 3 }

zxMplsTETunnelCfgSetupPrio OBJECT-TYPE
    SYNTAX      Integer32(0..7)
    MAX-ACCESS  read-create
    STATUS      current
    DESCRIPTION
            "Indicates the setup priority of this tunnel."
    ::= { zxMplsTETunnelCfgEntry 4 }

zxMplsTETunnelCfgHoldingPrio OBJECT-TYPE
    SYNTAX      Integer32(0..7)
    MAX-ACCESS  read-create
    STATUS      current
    DESCRIPTION
            "Indicates the holding priority of this tunnel."
    ::= { zxMplsTETunnelCfgEntry 5 }

zxMplsTETunnelCfgFrrFacility OBJECT-TYPE
    SYNTAX      INTEGER { false(0), true(1) }
    MAX-ACCESS  read-create
    STATUS      current
    DESCRIPTION
            "If this tunnel enables facility FRR,this value is true,
            otherwise it is false."
    ::= { zxMplsTETunnelCfgEntry 6 }

zxMplsTETunnelCfgFrrDetour OBJECT-TYPE
    SYNTAX      INTEGER { false(0), true(1) }
    MAX-ACCESS  read-create
    STATUS      current
    DESCRIPTION
            "If this tunnel enables detour FRR,this value is true,otherwise
            it is false."
    ::= { zxMplsTETunnelCfgEntry 7 }

zxMplsTETunnelCfgAutoRoute OBJECT-TYPE
    SYNTAX      INTEGER { false(0), true(1) }
    MAX-ACCESS  read-create
    STATUS      current
    DESCRIPTION
            "If this object is true, then it enables the Autoroute."
    ::= { zxMplsTETunnelCfgEntry 8 }

zxMplsTETunnelCfgARMetricType OBJECT-TYPE
    SYNTAX      INTEGER {igp(0), defaultAbsolute(1), absolute(2), relative(3)}
    MAX-ACCESS  read-create
    STATUS      current
    DESCRIPTION
            "Indicates the autoroute metric type over this tunnel."
    ::= { zxMplsTETunnelCfgEntry 9 }

zxMplsTETunnelCfgARRelaMetric OBJECT-TYPE
    SYNTAX      Integer32(-10..10)
    MAX-ACCESS  read-create
    STATUS      current
    DESCRIPTION
            "Indicates the value that adjust metric for autoroutes relative
            to IGP."
    ::= { zxMplsTETunnelCfgEntry 10 }

zxMplsTETunnelCfgARAbsMetric OBJECT-TYPE
    SYNTAX      Unsigned32
    MAX-ACCESS  read-create
    STATUS      current
    DESCRIPTION
            "Indicates the value for all autoroutes over tunnel."
    ::= { zxMplsTETunnelCfgEntry 11 }

zxMplsTETunnelCfgRecordRoute OBJECT-TYPE
    SYNTAX      INTEGER {false(0), true(1)}
    MAX-ACCESS  read-create
    STATUS      current
    DESCRIPTION
            "If this object is true, then it enables the RecordRoute."
    ::= { zxMplsTETunnelCfgEntry 12 }

zxMplsTETunnelCfgBfdEnable OBJECT-TYPE
    SYNTAX      INTEGER {true(1), false(2)}
    MAX-ACCESS  read-create
    STATUS      obsolete
    DESCRIPTION
            "If this object is true, then it enables bfd on the tunnel."
    ::= { zxMplsTETunnelCfgEntry 13 }

zxMplsTETunnelCfgBfdDeteMultiplier OBJECT-TYPE
    SYNTAX      Unsigned32(3..50)
    MAX-ACCESS  read-create
    STATUS      obsolete
    DESCRIPTION
            "The detecting multiple of receive/send CONTROL."
    ::= { zxMplsTETunnelCfgEntry 14 }

zxMplsTETunnelCfgBFDMinTxInterval OBJECT-TYPE
    SYNTAX      Unsigned32(10..990)
    MAX-ACCESS  read-create
    STATUS      obsolete
    DESCRIPTION
            "The minimal time to send CONTROL message."
    ::= { zxMplsTETunnelCfgEntry 15 }

zxMplsTETunnelCfgBFDMinRxInterval OBJECT-TYPE
    SYNTAX      Unsigned32(10..990)
    MAX-ACCESS  read-create
    STATUS      obsolete
    DESCRIPTION
            "The minimal time to receive CONTROL message."
    ::= { zxMplsTETunnelCfgEntry 16 }

zxMplsTETunnelCfgCoRoute OBJECT-TYPE
    SYNTAX      INTEGER {false(0), true(1)}
    MAX-ACCESS  read-create
    STATUS      current
    DESCRIPTION
            "If this object is true, then the tunnel is co-route bidirection."
    ::= { zxMplsTETunnelCfgEntry 17 }

zxMplsTETunnelCfgBandwidth OBJECT-TYPE
    SYNTAX      Unsigned32(0..4294967295)
    MAX-ACCESS  read-create
    STATUS      current
    DESCRIPTION
            "The bandwidth of this tunnel."
    ::= { zxMplsTETunnelCfgEntry 18 }

zxMplsTETunnelCfgBackupBandwidth OBJECT-TYPE
    SYNTAX      Unsigned32
    MAX-ACCESS  read-create
    STATUS      current
    DESCRIPTION
            "The backup bandwidth of this tunnel."
    ::= { zxMplsTETunnelCfgEntry 19 }

zxMplsTETunnelCfgFAEnable OBJECT-TYPE
    SYNTAX      INTEGER {false(0), true(1)}
    MAX-ACCESS  read-create
    STATUS      current
    DESCRIPTION
            "If this object is true, then it enables forwarding adjacency."
    ::= { zxMplsTETunnelCfgEntry 20 }

zxMplsTETunnelCfgFAHoldtime OBJECT-TYPE
    SYNTAX      Unsigned32
    MAX-ACCESS  read-create
    STATUS      current
    DESCRIPTION
            "The forwarding adjacency hold time of this tunnel."
    ::= { zxMplsTETunnelCfgEntry 21 }

zxMplsTETunnelCfgAdminWeight OBJECT-TYPE
    SYNTAX      Unsigned32
    MAX-ACCESS  read-create
    STATUS      current
    DESCRIPTION
            "The administrative weight of this tunnel."
    ::= { zxMplsTETunnelCfgEntry 22 }

zxMplsTETunnelCfgAutoBW OBJECT-TYPE
    SYNTAX      INTEGER {false(0), true(1)}
    MAX-ACCESS  read-create
    STATUS      current
    DESCRIPTION
            "If object is 1,auto bandwidth adjustment enable and adjust
            bandwidth."
    DEFVAL { false }
    ::= { zxMplsTETunnelCfgEntry 23 }

zxMplsTETunnelCfgAutoBWFrequency OBJECT-TYPE
    SYNTAX      Unsigned32(60..604800)
    MAX-ACCESS  read-create
    STATUS      current
    DESCRIPTION
            "The auto bandwidth adjustment frequency of this tunnel."
    DEFVAL { 86400}
    ::= { zxMplsTETunnelCfgEntry 24 }

zxMplsTETunnelCfgAutoBWMinValue OBJECT-TYPE
    SYNTAX      Unsigned32(0..4294967295)
    MAX-ACCESS  read-create
    STATUS      current
    DESCRIPTION
            "The auto bandwidth adjustment minimal bandwidth of this tunnel."
    DEFVAL { 0 }
    ::= { zxMplsTETunnelCfgEntry 25 }

zxMplsTETunnelCfgAutoBWMaxValue OBJECT-TYPE
    SYNTAX      Unsigned32(1..4294967295)
    MAX-ACCESS  read-create
    STATUS      current
    DESCRIPTION
            "The auto bandwidth adjustment maximal bandwidth of this tunnel."
        DEFVAL { 0 }
    ::= { zxMplsTETunnelCfgEntry 26 }

zxMplsTETunnelCfgAutoBWAdjMultiple OBJECT-TYPE
    SYNTAX      Unsigned32(50..100)
    MAX-ACCESS  read-create
    STATUS      current
    DESCRIPTION
            "The auto bandwidth adjustment multiple of this tunnel."
    DEFVAL { 100 }
    ::= { zxMplsTETunnelCfgEntry 27 }

zxMplsTETunnelCfgPolicyClass OBJECT-TYPE
    SYNTAX      Integer32(0..7|255)
    MAX-ACCESS  read-only
    STATUS      current
    DESCRIPTION
            "The minimal configured policy class of this tunnel."
    DEFVAL { 255 }            
    ::= { zxMplsTETunnelCfgEntry 28 }

zxMplsTETunnelCfgRowStatus OBJECT-TYPE
    SYNTAX      RowStatus
    MAX-ACCESS  read-create
    STATUS      current
    DESCRIPTION
            "Row status."
    ::= { zxMplsTETunnelCfgEntry 29 }

zxMplsTETunnelCfgCBS OBJECT-TYPE
    SYNTAX      Unsigned32(1..4294967295)
    MAX-ACCESS  read-create
    STATUS      current
    DESCRIPTION
            "The committed burst size of this tunnel."
    DEFVAL  { 0 }
    ::= { zxMplsTETunnelCfgEntry 30 }

zxMplsTETunnelCfgEIR OBJECT-TYPE
    SYNTAX      Unsigned32(1..4294967295)
    MAX-ACCESS  read-create
    STATUS      current
    DESCRIPTION
            "The excess information rate of this tunnel."
    DEFVAL  { 0 }
    ::= { zxMplsTETunnelCfgEntry 31 }

zxMplsTETunnelCfgEBS OBJECT-TYPE
    SYNTAX      Unsigned32(1..4294967295)
    MAX-ACCESS  read-create
    STATUS      current
    DESCRIPTION
            "The excess burst size of this tunnel."
    DEFVAL  { 0 }
    ::= { zxMplsTETunnelCfgEntry 32 }

zxMplsTETunnelCfgAutoBWThresholdPer OBJECT-TYPE
    SYNTAX      Unsigned32(1..100)
    MAX-ACCESS  read-create
    STATUS      current
    DESCRIPTION
            "The auto bandwidth overflow percent of this tunnel."
    DEFVAL { 0 }
    ::= { zxMplsTETunnelCfgEntry 33 }

zxMplsTETunnelCfgAutoBWThresholdMin OBJECT-TYPE
    SYNTAX      Unsigned32(10..4294967295)
    MAX-ACCESS  read-create
    STATUS      current
    DESCRIPTION
            "The auto bandwidth overflow bandwidth of this tunnel."
    DEFVAL { 10 }
    ::= { zxMplsTETunnelCfgEntry 34 }

zxMplsTETunnelCfgAutoBWThresholdLimit OBJECT-TYPE
    SYNTAX      Unsigned32(1..10)
    MAX-ACCESS  read-create
    STATUS      current
    DESCRIPTION
            "The auto bandwidth overflow limit of this tunnel."
    DEFVAL { 0 }
    ::= { zxMplsTETunnelCfgEntry 35 }

zxMplsTETunnelCfgAutoBWcollectbw OBJECT-TYPE
    SYNTAX      INTEGER{true(1), false(2)}
    MAX-ACCESS  read-create
    STATUS      current
    DESCRIPTION
            "If object is 1,auto bandwidth collect enable but not
            adjust bandwidth."
    DEFVAL { false }
    ::= { zxMplsTETunnelCfgEntry 36 }

zxMplsTETunnelCfgMainlspReopt OBJECT-TYPE
    SYNTAX      TruthValue
    MAX-ACCESS  read-create
    STATUS      current
    DESCRIPTION
            "If this tunnel enables main-lsp auto-reoptimize,
             this value is true,otherwise it is false."
    DEFVAL { false }
    ::= { zxMplsTETunnelCfgEntry 37 }

zxMplsTETunnelCfgHsblspFrr OBJECT-TYPE
    SYNTAX      TruthValue
    MAX-ACCESS  read-create
    STATUS      current
    DESCRIPTION
            "If this tunnel enables hot-standby-lsp Frr,
             this value is true,otherwise it is false."
    DEFVAL { false }
    ::= { zxMplsTETunnelCfgEntry 38 }
    
zxMplsTETunnelCfgRefenceHsbPath OBJECT-TYPE
    SYNTAX      TruthValue
    MAX-ACCESS  read-create
    STATUS      current
    DESCRIPTION
            "If this tunnel enables reference hsb-path,
             this value is true,otherwise it is false."
    DEFVAL { false }
    ::= { zxMplsTETunnelCfgEntry 39 }

zxMplsTETunnelCfgBwProtectEnable OBJECT-TYPE
    SYNTAX      TruthValue
    MAX-ACCESS  read-create
    STATUS      current
    DESCRIPTION
            "If this tunnel enables FRR bandwidth protection, this value is
            true, otherwise it is false."
    DEFVAL { false  }
    ::= { zxMplsTETunnelCfgEntry 40}
    
zxMplsTETunnelCfgCrankbackEnable OBJECT-TYPE
    SYNTAX      TruthValue
    MAX-ACCESS  read-create
    STATUS      current
    DESCRIPTION
            "If this tunnel enables crankback, this
             value is true,otherwise it is false."
    DEFVAL { false }
    ::= { zxMplsTETunnelCfgEntry 41 }    

zxMplsTETunnelCfgAssocTnnlID OBJECT-TYPE
    SYNTAX      Unsigned32(1..131072)
    MAX-ACCESS  read-create
    STATUS      current
    DESCRIPTION
            "The associate reverse tunnel id of this dynamic tunnel."
    ::= { zxMplsTETunnelCfgEntry 42 }
zxMplsTETunnelCfgHopsLimit OBJECT-TYPE
    SYNTAX      Unsigned32(0..32)
    MAX-ACCESS  read-create
    STATUS      current
    DESCRIPTION
            "Configure the maximum number of tunnel's hops."
    DEFVAL { 0 }
    ::= { zxMplsTETunnelCfgEntry 43 }
zxMplsTETunnelCfgHopsPrior OBJECT-TYPE
    SYNTAX      INTEGER{true(1), false(2)}
    MAX-ACCESS  read-create
    STATUS      current
    DESCRIPTION
            "Enable few hops of the path select firstly."
    DEFVAL { false }
    ::= { zxMplsTETunnelCfgEntry 44 }
zxMplsTETunnelCfgSoftPreemption OBJECT-TYPE
    SYNTAX      TruthValue
    MAX-ACCESS  read-create
    STATUS      current
    DESCRIPTION
            "If this tunnel enables soft preemption, this value is
            true, otherwise it is false."
    DEFVAL { false  }
    ::= { zxMplsTETunnelCfgEntry 45}	
zxMplsTETunnelCfgResvStyle OBJECT-TYPE
    SYNTAX      INTEGER{se(1), ff(2)}
    MAX-ACCESS  read-create
    STATUS      current
    DESCRIPTION
            "The resv-style of this dynamic tunnel."
    ::= { zxMplsTETunnelCfgEntry 46 }

zxMplsTETunnelCfgSessName OBJECT-TYPE
    SYNTAX      DisplayString(SIZE(1..63))
    MAX-ACCESS  read-create
    STATUS      current
    DESCRIPTION
            "Tunnel session name."
    ::= { zxMplsTETunnelCfgEntry 47}

zxMplsTETunnelCfgTnnlEnable OBJECT-TYPE
    SYNTAX      INTEGER {true(1), false(2)}
    MAX-ACCESS  read-create
    STATUS      current
    DESCRIPTION
            "If this object is true, then activate the tunnel."
    DEFVAL { true }
    ::= { zxMplsTETunnelCfgEntry 48 }
zxMplsTETunnelCfgHsblspReopt   OBJECT-TYPE
    SYNTAX      TruthValue
    MAX-ACCESS  read-create
    STATUS      current
    DESCRIPTION
            "If this tunnel enables hotstandby-lsp auto-reoptimize,
             this value is true,otherwise it is false."
    DEFVAL { false }
    ::= { zxMplsTETunnelCfgEntry 49 }  
zxMplsTETunnelCfgWithoutCspf   OBJECT-TYPE
    SYNTAX      TruthValue
    MAX-ACCESS  read-create
    STATUS      current
    DESCRIPTION
            "Build path ERO without CSPF."
    DEFVAL { false }
    ::= { zxMplsTETunnelCfgEntry 50 }
zxMplsTETunnelCfgTrackName   OBJECT-TYPE
    SYNTAX      DisplayString(SIZE(1..31))
    MAX-ACCESS  read-create
    STATUS      current
    DESCRIPTION
            "The track name of the TE tunnel used."
    DEFVAL {""}
    ::= { zxMplsTETunnelCfgEntry 51 }
zxMplsTETunnelCfgEscapePath   OBJECT-TYPE
    SYNTAX      TruthValue
    MAX-ACCESS  read-create
    STATUS      current
    DESCRIPTION
            "Escape path configuration of dynamic tunnel."
    DEFVAL { false }
    ::= { zxMplsTETunnelCfgEntry 52 }    
zxMplsTETunnelCfgUlimitDiscard OBJECT-TYPE
    SYNTAX      INTEGER{disabled(1), enabled(2)}
    MAX-ACCESS  read-create
    STATUS      current
    DESCRIPTION
            "If this tunnel enables ultralimit discard, this value is
            enabled, otherwise it is disabled."
    DEFVAL { disabled }
    ::= { zxMplsTETunnelCfgEntry 53 }
zxMplsTETunnelCfgE2EProtect   OBJECT-TYPE
    SYNTAX      TruthValue
    MAX-ACCESS  read-create
    STATUS      current
    DESCRIPTION
            "E2E protect configuration of dynamic bi-tunnel."
    DEFVAL { false }
    ::= { zxMplsTETunnelCfgEntry 54 }

zxMplsTETunnelCfgAutoRouteIpv6 OBJECT-TYPE
    SYNTAX      TruthValue
    MAX-ACCESS  read-create
    STATUS      current
    DESCRIPTION
            "If this object is true, then it enables the Autoroute ipv6."
    DEFVAL { false }
    ::= { zxMplsTETunnelCfgEntry 55 }

zxMplsTETunnelCfgFAIpv6 OBJECT-TYPE
    SYNTAX      TruthValue
    MAX-ACCESS  read-create
    STATUS      current
    DESCRIPTION
            "If this object is true, then it enables forwarding adjacency ipv6."
    DEFVAL { false }
    ::= { zxMplsTETunnelCfgEntry 56 }

zxMplsTETunnelCfgPCEInit   OBJECT-TYPE
    SYNTAX      TruthValue
    MAX-ACCESS  read-create
    STATUS      current
    DESCRIPTION
            "PCE-Init configuraion of dynamic tunnel."
    DEFVAL { false }
    ::= { zxMplsTETunnelCfgEntry 57 }
    
zxMplsTETunnelCfgActiveLspBfd OBJECT-TYPE
    SYNTAX      TruthValue
    MAX-ACCESS  read-create
    STATUS      current
    DESCRIPTION
            "If this object is true, then it enables active-lsp bfd."
    DEFVAL { false }
    ::= { zxMplsTETunnelCfgEntry 58 }
    
zxMplsTETunnelCfgAdvNoneNull OBJECT-TYPE
    SYNTAX      TruthValue
    MAX-ACCESS  read-create
    STATUS      current
    DESCRIPTION
            "If this object is true, then it enables adertise none-null for this tunnel."
    DEFVAL { false }
    ::= { zxMplsTETunnelCfgEntry 59 }

--*************************************************************************
--  zxMplsTEDsteCfgTable
--*************************************************************************

zxMplsTEDsteCfgTable OBJECT-TYPE
    SYNTAX      SEQUENCE OF ZxMplsTEDsteCfgEntry
    MAX-ACCESS  not-accessible
    STATUS      current
    DESCRIPTION
            ""
    ::= { zxRosngMplsTeMIB 5 }

zxMplsTEDsteCfgEntry OBJECT-TYPE
    SYNTAX      ZxMplsTEDsteCfgEntry
    MAX-ACCESS  not-accessible
    STATUS      current
    DESCRIPTION
            ""
    INDEX   { zxMplsTEDsteCfgTunnelName,zxMplsTEDsteCfgClassType }
    ::= { zxMplsTEDsteCfgTable 1 }

ZxMplsTEDsteCfgEntry ::=
    SEQUENCE {
        zxMplsTEDsteCfgTunnelName        DisplayString,
        zxMplsTEDsteCfgClassType         Unsigned32,
        zxMplsTEDsteCfgBandwidth         Unsigned32,
        zxMplsTEDsteCfgRowStatus         RowStatus
    }

zxMplsTEDsteCfgTunnelName OBJECT-TYPE
    SYNTAX      DisplayString(SIZE(0..31))
    MAX-ACCESS  not-accessible
    STATUS      current
    DESCRIPTION
            "The canonical name assigned to the tunnel. This name can be used
            to refer to the tunnel on the LSR's console port.If
            mplsTETunnelIsIf is set to true then the ifName of the interface
            corresponding to this tunnel should have a value equal to
            mplsTETunnelName. Also see the description of ifName in RFC 2863."
    ::= { zxMplsTEDsteCfgEntry 1 }


zxMplsTEDsteCfgClassType OBJECT-TYPE
    SYNTAX      Unsigned32(0..7)
    MAX-ACCESS  not-accessible
    STATUS      current
    DESCRIPTION
            "The dste class type of this tunnel."
    ::= { zxMplsTEDsteCfgEntry 2 }

zxMplsTEDsteCfgBandwidth OBJECT-TYPE
    SYNTAX      Unsigned32(1..4294967295)
    MAX-ACCESS  read-create
    STATUS      current
    DESCRIPTION
            "The dste bandwidth of this tunnel."
    ::= { zxMplsTEDsteCfgEntry 3 }

zxMplsTEDsteCfgRowStatus OBJECT-TYPE
    SYNTAX      RowStatus
    MAX-ACCESS  read-create
    STATUS      current
    DESCRIPTION
            "row status."
    ::= { zxMplsTEDsteCfgEntry 4 }

--*************************************************************************
--  zxMplsTEIfSrlgCfgTable
--*************************************************************************

zxMplsTEIfSrlgCfgTable OBJECT-TYPE
    SYNTAX      SEQUENCE OF ZxMplsTEIfSrlgCfgEntry
    MAX-ACCESS  not-accessible
    STATUS      current
    DESCRIPTION
            ""
    ::= { zxRosngMplsTeMIB 7 }

zxMplsTEIfSrlgCfgEntry OBJECT-TYPE
    SYNTAX      ZxMplsTEIfSrlgCfgEntry
    MAX-ACCESS  not-accessible
    STATUS      current
    DESCRIPTION
            ""
    INDEX   { zxMplsTEIfSrlgCfgIfName,zxMplsTEIfSrlgCfgSrlgID}
    ::= { zxMplsTEIfSrlgCfgTable 1 }

ZxMplsTEIfSrlgCfgEntry ::=
    SEQUENCE {
        zxMplsTEIfSrlgCfgIfName             DisplayString,
        zxMplsTEIfSrlgCfgSrlgID             Unsigned32,
        zxMplsTEIfSrlgCfgRowSta             RowStatus

    }


zxMplsTEIfSrlgCfgIfName OBJECT-TYPE
    SYNTAX      DisplayString(SIZE(0..31))
    MAX-ACCESS  not-accessible
    STATUS      current
    DESCRIPTION
            "The name of this interface."
    ::= { zxMplsTEIfSrlgCfgEntry 1 }

zxMplsTEIfSrlgCfgSrlgID OBJECT-TYPE
    SYNTAX      Unsigned32
    MAX-ACCESS  not-accessible
    STATUS      current
    DESCRIPTION
            "The SRLG value on this interface."
    ::= { zxMplsTEIfSrlgCfgEntry 2 }

zxMplsTEIfSrlgCfgRowSta OBJECT-TYPE
    SYNTAX      RowStatus
    MAX-ACCESS  read-create
    STATUS      current
    DESCRIPTION
            ""
    ::= { zxMplsTEIfSrlgCfgEntry 3 }

--*************************************************************************
--  zxMplsTEIfBackupTunnelCfgTable
--*************************************************************************

zxMplsTEIfBackupTunnelCfgTable OBJECT-TYPE
    SYNTAX      SEQUENCE OF ZxMplsTEIfBackupTunnelCfgEntry
    MAX-ACCESS  not-accessible
    STATUS      current
    DESCRIPTION
            ""
    ::= { zxRosngMplsTeMIB 8 }

zxMplsTEIfBackupTunnelCfgEntry OBJECT-TYPE
    SYNTAX      ZxMplsTEIfBackupTunnelCfgEntry
    MAX-ACCESS  not-accessible
    STATUS      current
    DESCRIPTION
            ""
    INDEX   { zxMplsTEIfBackupTunnelCfgIfName,zxMplsTEIfBackupTunnelCfgBakTID}
    ::= { zxMplsTEIfBackupTunnelCfgTable 1 }

ZxMplsTEIfBackupTunnelCfgEntry ::=
    SEQUENCE {
        zxMplsTEIfBackupTunnelCfgIfName         DisplayString,
        zxMplsTEIfBackupTunnelCfgBakTID         Unsigned32,
        zxMplsTEIfBackupTunnelCfgRowSta         RowStatus

    }


zxMplsTEIfBackupTunnelCfgIfName OBJECT-TYPE
    SYNTAX      DisplayString(SIZE(0..31))
    MAX-ACCESS  not-accessible
    STATUS      current
    DESCRIPTION
            "The name of this interface."
    ::= { zxMplsTEIfBackupTunnelCfgEntry 1 }

zxMplsTEIfBackupTunnelCfgBakTID OBJECT-TYPE
    SYNTAX      Unsigned32
    MAX-ACCESS  not-accessible
    STATUS      current
    DESCRIPTION
            "The back up tunnel for this interface."
    ::= { zxMplsTEIfBackupTunnelCfgEntry 2 }

zxMplsTEIfBackupTunnelCfgRowSta OBJECT-TYPE
    SYNTAX      RowStatus
    MAX-ACCESS  read-create
    STATUS      current
    DESCRIPTION
            ""
    ::= { zxMplsTEIfBackupTunnelCfgEntry 3 }

--*************************************************************************
--  zxMplsTEIfPassiveCfgTable
--*************************************************************************

zxMplsTEIfPassiveCfgTable OBJECT-TYPE
    SYNTAX      SEQUENCE OF ZxMplsTEIfPassiveCfgEntry
    MAX-ACCESS  not-accessible
    STATUS      current
    DESCRIPTION
            ""
    ::= { zxRosngMplsTeMIB 9 }

zxMplsTEIfPassiveCfgEntry OBJECT-TYPE
    SYNTAX      ZxMplsTEIfPassiveCfgEntry
    MAX-ACCESS  not-accessible
    STATUS      current
    DESCRIPTION
            ""
    INDEX   { zxMplsTEIfPassiveIfName,zxMplsTEIfPassiveNbrRID }
    ::= { zxMplsTEIfPassiveCfgTable 1 }

ZxMplsTEIfPassiveCfgEntry ::=
    SEQUENCE {
        zxMplsTEIfPassiveIfName          DisplayString,
        zxMplsTEIfPassiveNbrRID          IpAddress,
        zxMplsTEIfPassiveNbrIfAddress    IpAddress,
        zxMplsTEIfPassiveNbrOspfNodeId   IpAddress,
        zxMplsTEIfPassiveNbrIsisSystemId MacAddress,
        zxMplsTEIfPassiveRowStatus       RowStatus,
        zxMplsTEIfPassiveNbrIsisFlag     INTEGER
    }

zxMplsTEIfPassiveIfName OBJECT-TYPE
    SYNTAX      DisplayString(SIZE(0..31))
    MAX-ACCESS  not-accessible
    STATUS      current
    DESCRIPTION
            "A unique value, greater than zero, used by interface to get
            the passive attributes configure."
    ::= { zxMplsTEIfPassiveCfgEntry 1 }

zxMplsTEIfPassiveNbrRID OBJECT-TYPE
    SYNTAX      IpAddress
    MAX-ACCESS  not-accessible
    STATUS      current
    DESCRIPTION
            "The passive interface neighbor TE ID."
    ::= { zxMplsTEIfPassiveCfgEntry 2 }

zxMplsTEIfPassiveNbrIfAddress OBJECT-TYPE
    SYNTAX      IpAddress
    MAX-ACCESS  read-create
    STATUS      current
    DESCRIPTION
            "The passive interface neighbor interface address."
    DEFVAL   { '00000000'H }    -- 0.0.0.0
    ::= { zxMplsTEIfPassiveCfgEntry 3 }

zxMplsTEIfPassiveNbrOspfNodeId OBJECT-TYPE
    SYNTAX      IpAddress
    MAX-ACCESS  read-create
    STATUS      current
    DESCRIPTION
            "The passive interface neighbor ospf node id."
    DEFVAL   { '00000000'H }    -- 0.0.0.0
    ::= { zxMplsTEIfPassiveCfgEntry 4 }

zxMplsTEIfPassiveNbrIsisSystemId OBJECT-TYPE
    SYNTAX      MacAddress
    MAX-ACCESS  read-create
    STATUS      current
    DESCRIPTION
        "The passive interface neighbor isis system id."
    DEFVAL   {'000000000000'H}
    ::= { zxMplsTEIfPassiveCfgEntry 5 }

zxMplsTEIfPassiveRowStatus OBJECT-TYPE
    SYNTAX      RowStatus
    MAX-ACCESS  read-create
    STATUS      current
    DESCRIPTION
        "row status."
    ::= { zxMplsTEIfPassiveCfgEntry 6 }

zxMplsTEIfPassiveNbrIsisFlag OBJECT-TYPE
    SYNTAX      INTEGER {true(1), false(2)}
    MAX-ACCESS  read-only
    STATUS      current
    DESCRIPTION
            "If this object is true, then the passive interface 
                   neighbor isis system id is configured."
    ::= { zxMplsTEIfPassiveCfgEntry 7 }
--*************************************************************************
--  zxMplsTEExplicitPathNCfgTable
--*************************************************************************
zxMplsTEExplicitPathNCfgTable OBJECT-TYPE
    SYNTAX      SEQUENCE OF ZxMplsTEExplicitPathNCfgEntry
    MAX-ACCESS  not-accessible
    STATUS      current
    DESCRIPTION
            ""
    ::= { zxRosngMplsTeMIB 10 }

zxMplsTEExplicitPathNCfgEntry OBJECT-TYPE
    SYNTAX      ZxMplsTEExplicitPathNCfgEntry
    MAX-ACCESS  not-accessible
    STATUS      current
    DESCRIPTION
            ""
    INDEX   { zxMplsTEExplicitPathNCfgName }
    ::= { zxMplsTEExplicitPathNCfgTable 1 }

ZxMplsTEExplicitPathNCfgEntry ::=
    SEQUENCE {
        zxMplsTEExplicitPathNCfgName        DisplayString,
        zxMplsTEExplicitPathNCfgRowSta      RowStatus
    }

zxMplsTEExplicitPathNCfgName OBJECT-TYPE
    SYNTAX      DisplayString(SIZE(1..64))
    MAX-ACCESS  not-accessible
    STATUS      current
    DESCRIPTION
            "Uniquely identifies the name of the explicit-path."
    ::= { zxMplsTEExplicitPathNCfgEntry 1 }

zxMplsTEExplicitPathNCfgRowSta OBJECT-TYPE
    SYNTAX      RowStatus
    MAX-ACCESS  read-create
    STATUS      current
    DESCRIPTION
            ""
    ::= { zxMplsTEExplicitPathNCfgEntry 2 }

--*************************************************************************
--  zxMplsTEExplicitPathIDCfgTable
--*************************************************************************
zxMplsTEExplicitPathIDCfgTable OBJECT-TYPE
    SYNTAX      SEQUENCE OF ZxMplsTEExplicitPathIDCfgEntry
    MAX-ACCESS  not-accessible
    STATUS      current
    DESCRIPTION
            ""
    ::= { zxRosngMplsTeMIB 11 }

zxMplsTEExplicitPathIDCfgEntry OBJECT-TYPE
    SYNTAX      ZxMplsTEExplicitPathIDCfgEntry
    MAX-ACCESS  not-accessible
    STATUS      current
    DESCRIPTION
            ""
    INDEX   { zxMplsTEExplicitPathIDCfgIdentifer }
    ::= { zxMplsTEExplicitPathIDCfgTable 1 }

ZxMplsTEExplicitPathIDCfgEntry ::=
    SEQUENCE {
        zxMplsTEExplicitPathIDCfgIdentifer        Unsigned32,
        zxMplsTEExplicitPathIDCfgRowSta           RowStatus
    }

zxMplsTEExplicitPathIDCfgIdentifer OBJECT-TYPE
    SYNTAX      Unsigned32(1..65535)
    MAX-ACCESS  not-accessible
    STATUS      current
    DESCRIPTION
            "Uniquely identifies the id of the explicit-path."
    ::= { zxMplsTEExplicitPathIDCfgEntry 1 }

zxMplsTEExplicitPathIDCfgRowSta OBJECT-TYPE
    SYNTAX      RowStatus
    MAX-ACCESS  read-create
    STATUS      current
    DESCRIPTION
            ""
    ::= { zxMplsTEExplicitPathIDCfgEntry 2 }


--*************************************************************************
--  zxMplsTEExplicitRouteNCfgTable
--*************************************************************************
zxMplsTEExplicitRouteNCfgTable OBJECT-TYPE
    SYNTAX      SEQUENCE OF ZxMplsTEExplicitRouteNCfgEntry
    MAX-ACCESS  not-accessible
    STATUS      current
    DESCRIPTION
            ""
    ::= { zxRosngMplsTeMIB 12 }

zxMplsTEExplicitRouteNCfgEntry OBJECT-TYPE
    SYNTAX      ZxMplsTEExplicitRouteNCfgEntry
    MAX-ACCESS  not-accessible
    STATUS      current
    DESCRIPTION
            ""
    INDEX   {zxMplsTEExplicitRouteNCfgName, zxMplsTEExplicitRouteNCfgIndex }
    ::= { zxMplsTEExplicitRouteNCfgTable 1 }

ZxMplsTEExplicitRouteNCfgEntry ::=
    SEQUENCE {
        zxMplsTEExplicitRouteNCfgName          DisplayString,
        zxMplsTEExplicitRouteNCfgIndex         Unsigned32,
        zxMplsTEExplicitRouteNCfgNextIP        IpAddress,
        zxMplsTEExplicitRouteNCfgHopType       INTEGER,
        zxMplsTEExplicitRouteNCfgHopAttribute  INTEGER,
        zxMplsTEExplicitRouteNCfgRowStatus     RowStatus
    }

zxMplsTEExplicitRouteNCfgName OBJECT-TYPE
    SYNTAX      DisplayString(SIZE(1..64))
    MAX-ACCESS  not-accessible
    STATUS      current
    DESCRIPTION
            "Uniquely identifies the name of the explicit-path."
    ::= { zxMplsTEExplicitRouteNCfgEntry 1 }

zxMplsTEExplicitRouteNCfgIndex OBJECT-TYPE
    SYNTAX      Unsigned32(1..64)
    MAX-ACCESS  not-accessible
    STATUS      current
    DESCRIPTION
            "Uniquely identifier the index of the name of explicit-path."
    ::= { zxMplsTEExplicitRouteNCfgEntry 2 }

zxMplsTEExplicitRouteNCfgNextIP OBJECT-TYPE
    SYNTAX      IpAddress
    MAX-ACCESS  read-create
    STATUS      current
    DESCRIPTION
            "This value identifies the next hop IP address of
            the name of explicit-path."
    ::= { zxMplsTEExplicitRouteNCfgEntry 3 }

zxMplsTEExplicitRouteNCfgHopType OBJECT-TYPE
    SYNTAX      INTEGER{include(1),exclude(2),avoid(3)}
    MAX-ACCESS  read-create
    STATUS      current
    DESCRIPTION
            "This value identifies the hop type of the explicit-path
            address,1:include,2:exclude,3:avoid."
    ::= { zxMplsTEExplicitRouteNCfgEntry 4 }

zxMplsTEExplicitRouteNCfgHopAttribute OBJECT-TYPE
    SYNTAX      INTEGER{strict(1),loose(2),interface(3),routerid(4),interface(15),routerid(16)}
    MAX-ACCESS  read-create
    STATUS      current
    DESCRIPTION
            "This value identifies the hop attribute of the explicit-path
            address,1:strict ,2:loose,3:interface;4:routerid."
    ::= { zxMplsTEExplicitRouteNCfgEntry 5 }

zxMplsTEExplicitRouteNCfgRowStatus OBJECT-TYPE
    SYNTAX      RowStatus
    MAX-ACCESS  read-create
    STATUS      current
    DESCRIPTION
            "Row status."
    ::= { zxMplsTEExplicitRouteNCfgEntry 6 }

--*************************************************************************
--  zxMplsTEExplicitRouteIDCfgTable
--*************************************************************************
zxMplsTEExplicitRouteIDCfgTable OBJECT-TYPE
    SYNTAX      SEQUENCE OF ZxMplsTEExplicitRouteIDCfgEntry
    MAX-ACCESS  not-accessible
    STATUS      current
    DESCRIPTION
            ""
    ::= { zxRosngMplsTeMIB 13 }

zxMplsTEExplicitRouteIDCfgEntry OBJECT-TYPE
    SYNTAX      ZxMplsTEExplicitRouteIDCfgEntry
    MAX-ACCESS  not-accessible
    STATUS      current
    DESCRIPTION
            ""
    INDEX   {zxMplsTEExplicitRouteIDCfgIdentifer,
             zxMplsTEExplicitRouteIDCfgIndex }
    ::= { zxMplsTEExplicitRouteIDCfgTable 1 }

ZxMplsTEExplicitRouteIDCfgEntry ::=
    SEQUENCE {
        zxMplsTEExplicitRouteIDCfgIdentifer       Unsigned32,
        zxMplsTEExplicitRouteIDCfgIndex           Unsigned32,
        zxMplsTEExplicitRouteIDCfgNextIP          IpAddress,
        zxMplsTEExplicitRouteIDCfgHopType         INTEGER,
        zxMplsTEExplicitRouteIDCfgHopAttribute    INTEGER,
        zxMplsTEExplicitRouteIDCfgRowStatus       RowStatus
    }

zxMplsTEExplicitRouteIDCfgIdentifer OBJECT-TYPE
    SYNTAX      Unsigned32(1..65535)
    MAX-ACCESS  not-accessible
    STATUS      current
    DESCRIPTION
            "Uniquely identifies the id of the explicit-path."
    ::= { zxMplsTEExplicitRouteIDCfgEntry 1 }

zxMplsTEExplicitRouteIDCfgIndex OBJECT-TYPE
    SYNTAX      Unsigned32(1..64)
    MAX-ACCESS  not-accessible
    STATUS      current
    DESCRIPTION
            "Uniquely identifier the index of the id of explicit-path."
    ::= { zxMplsTEExplicitRouteIDCfgEntry 2 }

zxMplsTEExplicitRouteIDCfgNextIP OBJECT-TYPE
    SYNTAX      IpAddress
    MAX-ACCESS  read-create
    STATUS      current
    DESCRIPTION
            "This value identifies the next hop IP address of the id
            of explicit-path."
    ::= { zxMplsTEExplicitRouteIDCfgEntry 3 }

zxMplsTEExplicitRouteIDCfgHopType OBJECT-TYPE
    SYNTAX      INTEGER{include(1),exclude(2),avoid(3)}
    MAX-ACCESS  read-create
    STATUS      current
    DESCRIPTION
            "This value identifies the hop type of the explicit-path
            address,1:include,2:exclude,3:avoid."
    ::= { zxMplsTEExplicitRouteIDCfgEntry 4 }

zxMplsTEExplicitRouteIDCfgHopAttribute OBJECT-TYPE
    SYNTAX      INTEGER{strict(1),loose(2),interface(3),routerid(4),interface(15),routerid(16)}
    MAX-ACCESS  read-create
    STATUS      current
    DESCRIPTION
            "This value identifies the hop attribute of the explicit-path
            address,1:strict ,2:loose,3:interface;4:routerid."
    ::= { zxMplsTEExplicitRouteIDCfgEntry 5 }

zxMplsTEExplicitRouteIDCfgRowStatus OBJECT-TYPE
    SYNTAX      RowStatus
    MAX-ACCESS  read-create
    STATUS      current
    DESCRIPTION
            "Row status."
    ::= { zxMplsTEExplicitRouteIDCfgEntry 6 }
--*************************************************************************
--  zxMplsTEPathOptCfgTable
--*************************************************************************
zxMplsTEPathOptCfgTable OBJECT-TYPE
    SYNTAX      SEQUENCE OF ZxMplsTEPathOptCfgEntry
    MAX-ACCESS  not-accessible
    STATUS      current
    DESCRIPTION
            ""
    ::= { zxRosngMplsTeMIB 14 }

zxMplsTEPathOptCfgEntry OBJECT-TYPE
    SYNTAX      ZxMplsTEPathOptCfgEntry
    MAX-ACCESS  not-accessible
    STATUS      current
    DESCRIPTION
            ""
    INDEX   {zxMplsTEPathOptCfgTunnelName, zxMplsTEPathOptCfgNumber }
    ::= { zxMplsTEPathOptCfgTable 1 }

ZxMplsTEPathOptCfgEntry ::=
    SEQUENCE {
        zxMplsTEPathOptCfgTunnelName       DisplayString,
        zxMplsTEPathOptCfgNumber           Unsigned32,
        zxMplsTEPathOptCfgPathType         INTEGER ,
        zxMplsTEPathOptCfgExpPathName      DisplayString,
        zxMplsTEPathOptCfgExpPathID        Unsigned32,
        zxMplsTEPathOptCfgLockDown         INTEGER,
        zxMplsTEPathOptCfgRowStatus        RowStatus
    }

zxMplsTEPathOptCfgTunnelName OBJECT-TYPE
    SYNTAX      DisplayString(SIZE(0..31))
    MAX-ACCESS  not-accessible
    STATUS      current
    DESCRIPTION
            "Uniquely identifies the name of the tunnel."
    ::= { zxMplsTEPathOptCfgEntry 1 }

zxMplsTEPathOptCfgNumber OBJECT-TYPE
    SYNTAX      Unsigned32(1..16)
    MAX-ACCESS  not-accessible
    STATUS      current
    DESCRIPTION
            "Uniquely identifies the path-option num which the tunnel have,the
            list is from 1 to 16."
    ::= { zxMplsTEPathOptCfgEntry 2 }

zxMplsTEPathOptCfgPathType OBJECT-TYPE
    SYNTAX      INTEGER {dynamic(1),explicitId(2),explicitName(3)}
    MAX-ACCESS  read-create
    STATUS      current
    DESCRIPTION
            "This value identifier the type of the path-option,include about
            three type,such as: 1:dynamic;2:explicitID,3:explicitName."
    ::= { zxMplsTEPathOptCfgEntry 3 }

zxMplsTEPathOptCfgExpPathName OBJECT-TYPE
    SYNTAX      DisplayString(SIZE(1..64))
    MAX-ACCESS  read-create
    STATUS      current
    DESCRIPTION
            "This value identifier the name of the path-option,when the type
             of the path-option is explicitName,the other times the value is
             null."
    ::= { zxMplsTEPathOptCfgEntry 4 }

 zxMplsTEPathOptCfgExpPathID OBJECT-TYPE
    SYNTAX      Unsigned32(1..65535)
    MAX-ACCESS  read-create
    STATUS      current
    DESCRIPTION
            "This value identifier the ID of the path-option,when the type of
            the path-option is explicitID,the other times the value is 0."
    ::= { zxMplsTEPathOptCfgEntry 5 }

 zxMplsTEPathOptCfgLockDown OBJECT-TYPE
    SYNTAX      INTEGER {false(0), true(1)}
    MAX-ACCESS  read-create
    STATUS      current
    DESCRIPTION
            "This value identifier the path-option has been config lockdown."
    ::= { zxMplsTEPathOptCfgEntry 6 }

zxMplsTEPathOptCfgRowStatus OBJECT-TYPE
    SYNTAX      RowStatus
    MAX-ACCESS  read-create
    STATUS      current
    DESCRIPTION
            "Row status."
    ::= { zxMplsTEPathOptCfgEntry 7 }

--*************************************************************************
--  zxMplsTEHotStandbyCfgTable
--*************************************************************************

zxMplsTEHotStandbyCfgTable OBJECT-TYPE
    SYNTAX      SEQUENCE OF ZxMplsTEHotStandbyCfgEntry
    MAX-ACCESS  not-accessible
    STATUS      current
    DESCRIPTION
            ""
    ::= { zxRosngMplsTeMIB 15 }

zxMplsTEHotStandbyCfgEntry OBJECT-TYPE
    SYNTAX      ZxMplsTEHotStandbyCfgEntry
    MAX-ACCESS  not-accessible
    STATUS      current
    DESCRIPTION
            ""
    INDEX   { zxMplsTEHotStandbyCfgTunnelName,zxMplsTEHotStandbyCfgProtOptNo}
    ::= { zxMplsTEHotStandbyCfgTable 1 }

ZxMplsTEHotStandbyCfgEntry ::=
    SEQUENCE {
        zxMplsTEHotStandbyCfgTunnelName       DisplayString,
        zxMplsTEHotStandbyCfgProtOptNo        Unsigned32,
        zxMplsTEHotStandbyCfgPathType         INTEGER,
        zxMplsTEHotStandbyCfgExpPathName      DisplayString,
        zxMplsTEHotStandbyCfgExpPathID        Unsigned32,
        zxMplsTEHotStandbyCfgDynaPrefer       INTEGER,
        zxMplsTEHotStandbyCfgRowStatus        RowStatus,
        zxMplsTEHotStandbyCfgExpPathExclude   TruthValue
    }


zxMplsTEHotStandbyCfgTunnelName OBJECT-TYPE
    SYNTAX      DisplayString(SIZE(0..31))
    MAX-ACCESS  not-accessible
    STATUS      current
    DESCRIPTION
            "The index of path option which equals to tunnel name."
    ::= { zxMplsTEHotStandbyCfgEntry 1 }

zxMplsTEHotStandbyCfgProtOptNo OBJECT-TYPE
    SYNTAX      Unsigned32(1..16)
    MAX-ACCESS  not-accessible
    STATUS      current
    DESCRIPTION
            "Secondary index which identifies the configure value of path
            option."
    ::= { zxMplsTEHotStandbyCfgEntry 2 }

zxMplsTEHotStandbyCfgPathType OBJECT-TYPE
    SYNTAX      INTEGER {dynamic(1),explicitId(2),explicitName(3)}
    MAX-ACCESS  read-create
    STATUS      current
    DESCRIPTION
            "Specifies the hotstandby protect type of the path_option."
    ::= { zxMplsTEHotStandbyCfgEntry 3 }

zxMplsTEHotStandbyCfgExpPathName OBJECT-TYPE
    SYNTAX      DisplayString(SIZE(1..64))
    MAX-ACCESS  read-create
    STATUS      current
    DESCRIPTION
            "This value identifier the name of the path-option,when the type
             of the path-option is explicitName,the other times the value is
             null."
    ::= { zxMplsTEHotStandbyCfgEntry 4 }

zxMplsTEHotStandbyCfgExpPathID OBJECT-TYPE
    SYNTAX      Unsigned32(1..65535)
    MAX-ACCESS  read-create
    STATUS      current
    DESCRIPTION
            "This value identifier the ID of the path-option,when the type of
            the path-option is explicitID,the other times the value is 0."
    ::= { zxMplsTEHotStandbyCfgEntry 5 }

zxMplsTEHotStandbyCfgDynaPrefer OBJECT-TYPE
    SYNTAX      INTEGER {false(0), true(1)}
    MAX-ACCESS  read-create
    STATUS      current
    DESCRIPTION
            "Specifies the backup lsp path is as same as its primary lsp."
    ::= { zxMplsTEHotStandbyCfgEntry 6 }

zxMplsTEHotStandbyCfgRowStatus OBJECT-TYPE
    SYNTAX      RowStatus
    MAX-ACCESS  read-create
    STATUS      current
    DESCRIPTION
            "Row status."
    ::= { zxMplsTEHotStandbyCfgEntry 7 }

zxMplsTEHotStandbyCfgExpPathExclude OBJECT-TYPE
    SYNTAX      TruthValue
    MAX-ACCESS  read-create
    STATUS      current
    DESCRIPTION
            "The backup lsp path is whether or not to exclude the primary path.
            False means not exclude.True means exclude. The default value is
            false."
    DEFVAL { false }
    ::= { zxMplsTEHotStandbyCfgEntry 8 }

--*************************************************************************
--  zxMplsTEStaticTunnelCfgTable
--*************************************************************************

zxMplsTEStaticTunnelCfgTable OBJECT-TYPE
    SYNTAX      SEQUENCE OF ZxMplsTEStaticTunnelCfgEntry
    MAX-ACCESS  not-accessible
    STATUS      current
    DESCRIPTION
            ""
    ::= { zxRosngMplsTeMIB 16 }

zxMplsTEStaticTunnelCfgEntry OBJECT-TYPE
    SYNTAX      ZxMplsTEStaticTunnelCfgEntry
    MAX-ACCESS  not-accessible
    STATUS      current
    DESCRIPTION
            ""
    INDEX   { zxMplsStaticTunnelCfgTunnelName }
    ::= { zxMplsTEStaticTunnelCfgTable 1 }

ZxMplsTEStaticTunnelCfgEntry ::=
    SEQUENCE {
        zxMplsStaticTunnelCfgTunnelName         DisplayString,
        zxMplsStaticTunnelCfgTunnelID           Unsigned32,
        zxMplsStaticTunnelCfgDirectionType      INTEGER,
        zxMplsStaticTunnelCfgTunnelRole         INTEGER,
        zxMplsStaticTunnelCfgIngressTunnelID    Unsigned32,
        zxMplsStaticTunnelCfgIngressLSRID       IpAddress,
        zxMplsStaticTunnelCfgEgressLSRID        IpAddress,
        zxMplsStaticTunnelCfgPolicyClass        Integer32,
        zxMplsStaticTunnelCfgTrackName          DisplayString,
        zxMplsStaticTunnelCfgRowStatus          RowStatus,
        zxMplsStaticTunnelCfgAutoRoute          TruthValue,
        zxMplsStaticTunnelCfgARMtrType          INTEGER,
        zxMplsStaticTunnelCfgARRelaMtr          Integer32,
        zxMplsStaticTunnelCfgARAbsMtr           Unsigned32,
        zxMplsStaticTunnelCfgFAEnable           TruthValue,
        zxMplsStaticTunnelCfgFAHoldtime         Unsigned32,
        zxMplsStaticTunnelCfgAssocTnnlID        Unsigned32,
        zxMplsStaticTunnelCfgReserveMode        INTEGER,
        zxMplsStaticTunnelCfgTnnlEnable         INTEGER,
        zxMplsStaticTunnelCfgULDiscard          INTEGER,
        zxMplsStaticTunnelCfgARIpv6             TruthValue,
        zxMplsStaticTunnelCfgFAIpv6             TruthValue
    }


zxMplsStaticTunnelCfgTunnelName OBJECT-TYPE
    SYNTAX      DisplayString(SIZE(1..32))
    MAX-ACCESS  not-accessible
    STATUS      current
    DESCRIPTION
            "tunnel name."
    ::= { zxMplsTEStaticTunnelCfgEntry 1 }

zxMplsStaticTunnelCfgTunnelID OBJECT-TYPE
    SYNTAX      Unsigned32(1..131072)
    MAX-ACCESS  read-only
    STATUS      current
    DESCRIPTION
            "Uniquely identifies a set of static tunnel instances between a
            pair of ingress and egress LSRs."
    ::= { zxMplsTEStaticTunnelCfgEntry 2 }

zxMplsStaticTunnelCfgDirectionType OBJECT-TYPE
    SYNTAX      INTEGER{unidirection(1),bidirecttion(2)}
    MAX-ACCESS  read-create
    STATUS      current
    DESCRIPTION
            "This value signifies the direction of the static tunnel."
    ::= { zxMplsTEStaticTunnelCfgEntry 3 }

zxMplsStaticTunnelCfgTunnelRole OBJECT-TYPE
    SYNTAX      INTEGER{head(1),transit(2),tail(3)}
    MAX-ACCESS  read-create
    STATUS      current
    DESCRIPTION
            "This value signifies the role that this static tunnel
            entry/instance represents."
    ::= { zxMplsTEStaticTunnelCfgEntry 4 }


zxMplsStaticTunnelCfgIngressTunnelID OBJECT-TYPE
    SYNTAX      Unsigned32(1..65535)
    MAX-ACCESS  read-create
    STATUS      current
    DESCRIPTION
            "The static tunnel's ingress tunnel id."
    DEFVAL { 0 }
    ::= { zxMplsTEStaticTunnelCfgEntry 5 }

zxMplsStaticTunnelCfgIngressLSRID OBJECT-TYPE
    SYNTAX      IpAddress
    MAX-ACCESS  read-create
    STATUS      current
    DESCRIPTION
            "Identity of the ingress LSR ."
    DEFVAL   { '00000000'H }    -- 0.0.0.0
    ::= { zxMplsTEStaticTunnelCfgEntry 6 }

zxMplsStaticTunnelCfgEgressLSRID OBJECT-TYPE
    SYNTAX      IpAddress
    MAX-ACCESS  read-create
    STATUS      current
    DESCRIPTION
            "Identity of the egress LSR ."
    DEFVAL   { '00000000'H }    -- 0.0.0.0
    ::= { zxMplsTEStaticTunnelCfgEntry 7 }


zxMplsStaticTunnelCfgPolicyClass   OBJECT-TYPE
    SYNTAX      Integer32(0..7|255)
    MAX-ACCESS  read-only
    STATUS      current
    DESCRIPTION
            "The minimal configured policy class on the tunnel."
    DEFVAL { 255 }            
    ::= { zxMplsTEStaticTunnelCfgEntry 8 }

zxMplsStaticTunnelCfgTrackName   OBJECT-TYPE
    SYNTAX      DisplayString(SIZE(1..31))
    MAX-ACCESS  read-create
    STATUS      current
    DESCRIPTION
            "The track name of the static tunnel used."
    DEFVAL {""}
    ::= { zxMplsTEStaticTunnelCfgEntry 9 }


zxMplsStaticTunnelCfgRowStatus   OBJECT-TYPE
    SYNTAX      RowStatus
    MAX-ACCESS  read-create
    STATUS      current
    DESCRIPTION
            "row status."
    ::= { zxMplsTEStaticTunnelCfgEntry 10 }

zxMplsStaticTunnelCfgAutoRoute OBJECT-TYPE
    SYNTAX      TruthValue
    MAX-ACCESS  read-create
    STATUS      current
    DESCRIPTION
            "If this object is true, then it enables the Autoroute."
    ::= { zxMplsTEStaticTunnelCfgEntry 11 }

zxMplsStaticTunnelCfgARMtrType OBJECT-TYPE
    SYNTAX      INTEGER { defaultAbsolute(1), absolute(2), relative(3),igp(4) }
    MAX-ACCESS  read-create
    STATUS      current
    DESCRIPTION
            "Indicates the autoroute metric type over this tunnel."
    ::= { zxMplsTEStaticTunnelCfgEntry 12 }

zxMplsStaticTunnelCfgARRelaMtr OBJECT-TYPE
    SYNTAX      Integer32(-10..10)
    MAX-ACCESS  read-create
    STATUS      current
    DESCRIPTION
            "Indicates the value that adjust metric for autoroutes relative
            to IGP."
    ::= { zxMplsTEStaticTunnelCfgEntry 13 }

zxMplsStaticTunnelCfgARAbsMtr OBJECT-TYPE
    SYNTAX      Unsigned32
    MAX-ACCESS  read-create
    STATUS      current
    DESCRIPTION
            "Indicates the value for all autoroutes over tunnel."
    ::= { zxMplsTEStaticTunnelCfgEntry 14 }

zxMplsStaticTunnelCfgFAEnable OBJECT-TYPE
    SYNTAX      TruthValue
    MAX-ACCESS  read-create
    STATUS      current
    DESCRIPTION
            "If this object is true, then it enables forwarding adjacency."
    ::= { zxMplsTEStaticTunnelCfgEntry 15 }

zxMplsStaticTunnelCfgFAHoldtime OBJECT-TYPE
    SYNTAX      Unsigned32
    MAX-ACCESS  read-create
    STATUS      current
    DESCRIPTION
            "The forwarding adjacency hold time of this tunnel."
    ::= { zxMplsTEStaticTunnelCfgEntry 16 }

zxMplsStaticTunnelCfgAssocTnnlID   OBJECT-TYPE
    SYNTAX      Unsigned32(1..131072)
    MAX-ACCESS  read-create
    STATUS      current
    DESCRIPTION
            "The associate reverse tunnel id of this static tunnel."     
    ::= { zxMplsTEStaticTunnelCfgEntry 17 }

zxMplsStaticTunnelCfgReserveMode   OBJECT-TYPE
    SYNTAX      INTEGER{reserve(1),noReserve(2)}
    MAX-ACCESS  read-create
    STATUS      current
    DESCRIPTION
            "The bandwidth reserve mode of this static tunnel."
    DEFVAL  { reserve }
    ::= { zxMplsTEStaticTunnelCfgEntry 19 }

zxMplsStaticTunnelCfgTnnlEnable OBJECT-TYPE
    SYNTAX      INTEGER {true(1), false(2)}
    MAX-ACCESS  read-create
    STATUS      current
    DESCRIPTION
            "If this object is true, then activate the tunnel."
    ::= { zxMplsTEStaticTunnelCfgEntry 20}
    
zxMplsStaticTunnelCfgULDiscard OBJECT-TYPE
    SYNTAX      INTEGER {disabled(1), enabled(2)}
    MAX-ACCESS  read-create
    STATUS      current
    DESCRIPTION
            "If this object is true, then activate ultralimit discard."
    DEFVAL  { disabled }
    ::= { zxMplsTEStaticTunnelCfgEntry 21}

zxMplsStaticTunnelCfgARIpv6 OBJECT-TYPE
    SYNTAX      TruthValue
    MAX-ACCESS  read-create
    STATUS      current
    DESCRIPTION
            "If this object is true, then it enables the Autoroute ipv6."
    DEFVAL { false }
    ::= { zxMplsTEStaticTunnelCfgEntry 22 }

zxMplsStaticTunnelCfgFAIpv6 OBJECT-TYPE
    SYNTAX      TruthValue
    MAX-ACCESS  read-create
    STATUS      current
    DESCRIPTION
            "If this object is true, then it enables forwarding adjacency ipv6."
    DEFVAL { false }
    ::= { zxMplsTEStaticTunnelCfgEntry 23 }

--*************************************************************************
--  zxMplsTEStaticLspCfgTable
--*************************************************************************

zxMplsTEStaticLspCfgTable OBJECT-TYPE
    SYNTAX      SEQUENCE OF ZxMplsTEStaticLspCfgEntry
    MAX-ACCESS  not-accessible
    STATUS      current
    DESCRIPTION
            ""
    ::= { zxRosngMplsTeMIB 17 }

zxMplsTEStaticLspCfgEntry OBJECT-TYPE
    SYNTAX      ZxMplsTEStaticLspCfgEntry
    MAX-ACCESS  not-accessible
    STATUS      current
    DESCRIPTION
            ""
    INDEX   { zxMplsStaticLspCfgTunnelID,zxMplsStaticLspCfgLSPID }
    ::= { zxMplsTEStaticLspCfgTable 1 }

ZxMplsTEStaticLspCfgEntry ::=
    SEQUENCE {
        zxMplsStaticLspCfgTunnelID             Unsigned32,
        zxMplsStaticLspCfgLSPID                Unsigned32,
        zxMplsStaticLspCfgInPort               DisplayString,
        zxMplsStaticLspCfgInLabel              Unsigned32,
        zxMplsStaticLspCfgOutPort              DisplayString,
        zxMplsStaticLspCfgOutLabel             Unsigned32,
        zxMplsStaticLspCfgNextHop              IpAddress,
        zxMplsStaticLspCfgReverseInPort        DisplayString,
        zxMplsStaticLspCfgReverseInLabel       Unsigned32,
        zxMplsStaticLspCfgReverseOutPort       DisplayString,
        zxMplsStaticLspCfgReverseOutLabel      Unsigned32,
        zxMplsStaticLspCfgReverseNextHop       IpAddress,
        zxMplsStaticLspCfgRowStatus            RowStatus,
        zxMplsStaticLspCfgOutBandwith          Unsigned32,
        zxMplsStaticLspCfgOutPeak              Unsigned32,
        zxMplsStaticLspCfgOutBurst             Unsigned32,
        zxMplsStaticLspCfgOutExcessBurst       Unsigned32,
        zxMplsStaticLspCfgReverseOutBandwith   Unsigned32,
        zxMplsStaticLspCfgReverseOutPeak       Unsigned32,
        zxMplsStaticLspCfgReverseOutBurst      Unsigned32,
        zxMplsStaticLspCfgReverseOutExcessBurst Unsigned32,
        zxMplsStaticLspCfgShareTnnl             DisplayString,
        zxMplsStaticLspCfgRvShareTnnl           DisplayString,
        zxMplsStaticLspCfgCratioMode            INTEGER,
        zxMplsStaticLspCfgCratioValue           Integer32,
        zxMplsStaticLspCfgRvCratioMode          INTEGER,
        zxMplsStaticLspCfgRvCratioValue         Integer32
    }


zxMplsStaticLspCfgTunnelID OBJECT-TYPE
    SYNTAX      Unsigned32(1..131072)
    MAX-ACCESS  not-accessible
    STATUS      current
    DESCRIPTION
            "Uniquely identifies a set of static tunnel instances between a
            pair of ingress and egress LSRs."
    ::= { zxMplsTEStaticLspCfgEntry 1 }


zxMplsStaticLspCfgLSPID OBJECT-TYPE
    SYNTAX      Unsigned32
    MAX-ACCESS  not-accessible
    STATUS      current
    DESCRIPTION
            "Uniquely identifies a static tunnel lsp."
    ::= { zxMplsTEStaticLspCfgEntry 2 }

zxMplsStaticLspCfgInPort OBJECT-TYPE
    SYNTAX      DisplayString(SIZE(0..32))
    MAX-ACCESS  read-create
    STATUS      current
    DESCRIPTION
            "The entry interface name of the forward direction static lsp."
    DEFVAL {""}
    ::= { zxMplsTEStaticLspCfgEntry 3 }

zxMplsStaticLspCfgInLabel OBJECT-TYPE
    SYNTAX      Unsigned32
    MAX-ACCESS  read-create
    STATUS      current
    DESCRIPTION
            "The entry label of the forward direction static lsp."
    DEFVAL { 'FFFFFFFE'H }      -- 4294967294
    ::= { zxMplsTEStaticLspCfgEntry 4 }

zxMplsStaticLspCfgOutPort OBJECT-TYPE
    SYNTAX      DisplayString(SIZE(0..32))
    MAX-ACCESS  read-create
    STATUS      current
    DESCRIPTION
            "Out interface name of the forward direction static lsp."
    DEFVAL {""}
    ::= { zxMplsTEStaticLspCfgEntry 5 }

zxMplsStaticLspCfgOutLabel OBJECT-TYPE
    SYNTAX      Unsigned32
    MAX-ACCESS  read-create
    STATUS      current
    DESCRIPTION
            "Out label of the forward direction static lsp."
    DEFVAL { 'FFFFFFFE'H }      -- 4294967294
    ::= { zxMplsTEStaticLspCfgEntry 6 }

zxMplsStaticLspCfgNextHop OBJECT-TYPE
    SYNTAX      IpAddress
    MAX-ACCESS  read-create
    STATUS      current
    DESCRIPTION
            "The next hop of the forward direction static lsp."
    DEFVAL   { '00000000'H }    -- 0.0.0.0
    ::= { zxMplsTEStaticLspCfgEntry 7 }


zxMplsStaticLspCfgReverseInPort OBJECT-TYPE
    SYNTAX      DisplayString(SIZE(0..32))
    MAX-ACCESS  read-create
    STATUS      current
    DESCRIPTION
            "The entry interface name of the reverse direction static lsp."
    DEFVAL {""}
    ::= { zxMplsTEStaticLspCfgEntry 8 }

zxMplsStaticLspCfgReverseInLabel OBJECT-TYPE
    SYNTAX      Unsigned32
    MAX-ACCESS  read-create
    STATUS      current
    DESCRIPTION
            "The entry label of the reverse direction static lsp."
    DEFVAL { 'FFFFFFFE'H }      -- 4294967294
    ::= { zxMplsTEStaticLspCfgEntry 9 }

zxMplsStaticLspCfgReverseOutPort OBJECT-TYPE
    SYNTAX      DisplayString
    MAX-ACCESS  read-create
    STATUS      current
    DESCRIPTION
            "Out interface name of the reverse direction static lsp."
    DEFVAL {""}
    ::= { zxMplsTEStaticLspCfgEntry 10 }

zxMplsStaticLspCfgReverseOutLabel OBJECT-TYPE
    SYNTAX      Unsigned32
    MAX-ACCESS  read-create
    STATUS      current
    DESCRIPTION
            "Out label of the reverse direction static lsp."
    DEFVAL { 'FFFFFFFE'H }      -- 4294967294
    ::= { zxMplsTEStaticLspCfgEntry 11 }

zxMplsStaticLspCfgReverseNextHop OBJECT-TYPE
    SYNTAX      IpAddress
    MAX-ACCESS  read-create
    STATUS      current
    DESCRIPTION
            "The next hop of the reverse direction static lsp."
    DEFVAL   { '00000000'H }    -- 0.0.0.0
    ::= { zxMplsTEStaticLspCfgEntry 12 }

zxMplsStaticLspCfgRowStatus  OBJECT-TYPE
    SYNTAX      RowStatus
    MAX-ACCESS  read-create
    STATUS      current
    DESCRIPTION
            "row status."
    ::= { zxMplsTEStaticLspCfgEntry 13 }

zxMplsStaticLspCfgOutBandwith OBJECT-TYPE
    SYNTAX      Unsigned32(0..4294967295)
    MAX-ACCESS  read-create
    STATUS      current
    DESCRIPTION
            "The out bandwidth of the forward direction static lsp."
    DEFVAL  { 0 }
    ::= { zxMplsTEStaticLspCfgEntry 14 }

zxMplsStaticLspCfgOutPeak OBJECT-TYPE
    SYNTAX      Unsigned32(1..4294967295)
    MAX-ACCESS  read-create
    STATUS      current
    DESCRIPTION
            "The out peak of the forward direction static lsp."
    DEFVAL  { 0 }
    ::= { zxMplsTEStaticLspCfgEntry 15 }

zxMplsStaticLspCfgOutBurst OBJECT-TYPE
    SYNTAX      Unsigned32(1..4294967295)
    MAX-ACCESS  read-create
    STATUS      current
    DESCRIPTION
            "The out burst of the forward direction static lsp."
    DEFVAL  { 0 }
    ::= { zxMplsTEStaticLspCfgEntry 16 }

zxMplsStaticLspCfgOutExcessBurst OBJECT-TYPE
    SYNTAX      Unsigned32(1..4294967295)
    MAX-ACCESS  read-create
    STATUS      current
    DESCRIPTION
            "The out excess burst of the forward direction static lsp."
    DEFVAL  { 0 }
    ::= { zxMplsTEStaticLspCfgEntry 17 }

zxMplsStaticLspCfgReverseOutBandwith OBJECT-TYPE
    SYNTAX      Unsigned32(0..4294967295)
    MAX-ACCESS  read-create
    STATUS      current
    DESCRIPTION
            "The out bandwidth of the reverse direction static lsp."
    DEFVAL  { 0 }
    ::= { zxMplsTEStaticLspCfgEntry 18 }

zxMplsStaticLspCfgReverseOutPeak OBJECT-TYPE
    SYNTAX      Unsigned32(1..4294967295)
    MAX-ACCESS  read-create
    STATUS      current
    DESCRIPTION
            "The out peak of the reverse direction static lsp."
    DEFVAL  { 0 }
    ::= { zxMplsTEStaticLspCfgEntry 19 }

zxMplsStaticLspCfgReverseOutBurst OBJECT-TYPE
    SYNTAX      Unsigned32(1..4294967295)
    MAX-ACCESS  read-create
    STATUS      current
    DESCRIPTION
            "The out burst of the reverse direction static lsp."
    DEFVAL  { 0 }
    ::= { zxMplsTEStaticLspCfgEntry 20 }

zxMplsStaticLspCfgReverseOutExcessBurst OBJECT-TYPE
    SYNTAX      Unsigned32(1..4294967295)
    MAX-ACCESS  read-create
    STATUS      current
    DESCRIPTION
            "The out excess burst of the reverse direction static lsp."
    DEFVAL  { 0 }
    ::= { zxMplsTEStaticLspCfgEntry 21 }

zxMplsStaticLspCfgShareTnnl OBJECT-TYPE
    SYNTAX      DisplayString(SIZE(0..32))
    MAX-ACCESS  read-create
    STATUS      current
    DESCRIPTION
            "The shared tunnel name of the forward direction static lsp."
    ::= { zxMplsTEStaticLspCfgEntry 22 }

zxMplsStaticLspCfgRvShareTnnl OBJECT-TYPE
    SYNTAX      DisplayString(SIZE(0..32))
    MAX-ACCESS  read-create
    STATUS      current
    DESCRIPTION
            "The shared tunnel name of the reverse direction static lsp."
    ::= { zxMplsTEStaticLspCfgEntry 27 }

zxMplsStaticLspCfgCratioMode OBJECT-TYPE
    SYNTAX      INTEGER {inherit(1), configure(2),invalid(3)}
    MAX-ACCESS  read-create
    STATUS      current
    DESCRIPTION
            "The convergence ratio mode of the forward direction static lsp."
    ::= { zxMplsTEStaticLspCfgEntry 28}

zxMplsStaticLspCfgCratioValue OBJECT-TYPE
    SYNTAX      Integer32(1..100)
    MAX-ACCESS  read-create
    STATUS      current
    DESCRIPTION
            "The convergence ratio value of the forward direction static lsp."
    ::= { zxMplsTEStaticLspCfgEntry 29}

zxMplsStaticLspCfgRvCratioMode OBJECT-TYPE
    SYNTAX      INTEGER {inherit(1), configure(2),invalid(3)}
    MAX-ACCESS  read-create
    STATUS      current
    DESCRIPTION
            "The convergence ratio mode of the reverse direction static lsp."
    ::= { zxMplsTEStaticLspCfgEntry 30}

zxMplsStaticLspCfgRvCratioValue OBJECT-TYPE
    SYNTAX      Integer32(1..100)
    MAX-ACCESS  read-create
    STATUS      current
    DESCRIPTION
            "The convergence ratio value of the reverse direction static lsp."
    ::= { zxMplsTEStaticLspCfgEntry 31}

--*************************************************************************
--  zxMplsTEStaticTunnelStatusTable
--*************************************************************************

zxMplsTEStaticTunnelStatusTable OBJECT-TYPE
    SYNTAX      SEQUENCE OF ZxMplsTEStaticTunnelStatusEntry
    MAX-ACCESS  not-accessible
    STATUS      current
    DESCRIPTION
            ""
    ::= { zxRosngMplsTeMIB 18 }

zxMplsTEStaticTunnelStatusEntry OBJECT-TYPE
    SYNTAX      ZxMplsTEStaticTunnelStatusEntry
    MAX-ACCESS  not-accessible
    STATUS      current
    DESCRIPTION
            ""
    INDEX   { zxMplsStaticTunnelStatusTunnelID}
    ::= { zxMplsTEStaticTunnelStatusTable 1 }

ZxMplsTEStaticTunnelStatusEntry ::=
    SEQUENCE {
        zxMplsStaticTunnelStatusTunnelID   Unsigned32,
        zxMplsStaticTunnelStatusProtStat   INTEGER,
        zxMplsStaticTunnelStatusAdminStat  INTEGER,
        zxMplsStaticTunnelStatusAssoc      INTEGER,
        zxMplsStaticTunnelStatusTnnlUtil   Unsigned32,
        zxMplsStaticTunnelStatusUtilIn     Unsigned32
    }


zxMplsStaticTunnelStatusTunnelID OBJECT-TYPE
    SYNTAX      Unsigned32(1..131072)
    MAX-ACCESS  not-accessible
    STATUS      current
    DESCRIPTION
            "Uniquely identifies a set of static tunnel instances between a
            pair of ingress and egress LSRs."
    ::= { zxMplsTEStaticTunnelStatusEntry 1 }


zxMplsStaticTunnelStatusProtStat OBJECT-TYPE
    SYNTAX      INTEGER{down(0),up(1)}
    MAX-ACCESS  read-only
    STATUS      current
    DESCRIPTION
            "This value identifies actual operational status of this static
            tunnel."
    ::= { zxMplsTEStaticTunnelStatusEntry 2 }

zxMplsStaticTunnelStatusAdminStat OBJECT-TYPE
    SYNTAX      INTEGER{down(0),up(1)}
    MAX-ACCESS  read-only
    STATUS      current
    DESCRIPTION
            "This value identifies the administrator status of this static
            tunnel."
    ::= { zxMplsTEStaticTunnelStatusEntry 3 }

zxMplsStaticTunnelStatusAssoc OBJECT-TYPE
    SYNTAX      INTEGER{disabled(1),unbound(2),bound(3)}
    MAX-ACCESS  read-only
    STATUS      current
    DESCRIPTION
            "This value identifies the associate bidirect status of this
             static tunnel."
    ::= { zxMplsTEStaticTunnelStatusEntry 4 }

zxMplsStaticTunnelStatusTnnlUtil OBJECT-TYPE
    SYNTAX      Unsigned32(0..4294967294|4294967295)
    MAX-ACCESS  read-only
    STATUS      current
    DESCRIPTION
            "This value identifies the bandwidth utilization of this
             static tunnel. It's default value is 4294967295."
    ::= { zxMplsTEStaticTunnelStatusEntry 5 }
zxMplsStaticTunnelStatusUtilIn OBJECT-TYPE
    SYNTAX      Unsigned32(0..4294967294|4294967295)
    MAX-ACCESS  read-only
    STATUS      current
    DESCRIPTION
            "This value identifies the bandwidth in utilization of this
             static tunnel. It's default value is 4294967295."
    ::= { zxMplsTEStaticTunnelStatusEntry 6 }

--*************************************************************************
--  zxMplsTEStaticLspStatusTable
--*************************************************************************

zxMplsTEStaticLspStatusTable OBJECT-TYPE
    SYNTAX      SEQUENCE OF ZxMplsTEStaticLspStatusEntry
    MAX-ACCESS  not-accessible
    STATUS      current
    DESCRIPTION
            ""
    ::= { zxRosngMplsTeMIB 19 }

zxMplsTEStaticLspStatusEntry OBJECT-TYPE
    SYNTAX      ZxMplsTEStaticLspStatusEntry
    MAX-ACCESS  not-accessible
    STATUS      current
    DESCRIPTION
            ""
    INDEX   { zxMplsStaticLspStatusTunnelId,zxMplsStaticLspStatusLspId }
    ::= { zxMplsTEStaticLspStatusTable 1 }

ZxMplsTEStaticLspStatusEntry ::=
    SEQUENCE {
        zxMplsStaticLspStatusTunnelId        Unsigned32,
        zxMplsStaticLspStatusLspId           Unsigned32,
        zxMplsStaticLspStatusInIfIndex       Unsigned32,
        zxMplsStaticLspStatusOutIfindex      Unsigned32,
        zxMplsStaticLspStatusReverseInIntf   Unsigned32,
        zxMplsStaticLspStatusReverseOutIntf  Unsigned32,
        zxMplsStaticLspStatusProtStat        INTEGER
    }


zxMplsStaticLspStatusTunnelId OBJECT-TYPE
    SYNTAX      Unsigned32(1..131072)
    MAX-ACCESS  not-accessible
    STATUS      current
    DESCRIPTION
            "Uniquely identifies a set of static tunnel instances between a
            pair of ingress and egress LSRs."
    ::= { zxMplsTEStaticLspStatusEntry 1 }


zxMplsStaticLspStatusLspId OBJECT-TYPE
    SYNTAX      Unsigned32
    MAX-ACCESS  not-accessible
    STATUS      current
    DESCRIPTION
            "Uniquely identifies a static tunnel lsp."
    ::= { zxMplsTEStaticLspStatusEntry 2 }

zxMplsStaticLspStatusInIfIndex OBJECT-TYPE
    SYNTAX      Unsigned32
    MAX-ACCESS  read-only
    STATUS      current
    DESCRIPTION
            "The entry interface index of the forward direction static lsp."
    ::= { zxMplsTEStaticLspStatusEntry 3 }

zxMplsStaticLspStatusOutIfindex OBJECT-TYPE
    SYNTAX      Unsigned32
    MAX-ACCESS  read-only
    STATUS      current
    DESCRIPTION
            "Out interface index of the forward direction static lsp."
    ::= { zxMplsTEStaticLspStatusEntry 4 }

zxMplsStaticLspStatusReverseInIntf OBJECT-TYPE
    SYNTAX      Unsigned32
    MAX-ACCESS  read-only
    STATUS      current
    DESCRIPTION
            "The entry interface index of the reverse direction static lsp."
    ::= { zxMplsTEStaticLspStatusEntry 5 }

zxMplsStaticLspStatusReverseOutIntf OBJECT-TYPE
    SYNTAX      Unsigned32
    MAX-ACCESS  read-only
    STATUS      current
    DESCRIPTION
            "Out interface index of the reverse direction static lsp."
    ::= { zxMplsTEStaticLspStatusEntry 6 }

zxMplsStaticLspStatusProtStat OBJECT-TYPE
    SYNTAX      INTEGER{down(0),up(1)}
    MAX-ACCESS  read-only
    STATUS      current
    DESCRIPTION
            "This value identifies actual operational status of this static
            tunnel lsp."
    ::= { zxMplsTEStaticLspStatusEntry 7 }

--*************************************************************************
--  zxMplsTEAccTunnelStatusTable
--*************************************************************************

zxMplsTEAccTunnelStatusTable OBJECT-TYPE
    SYNTAX      SEQUENCE OF ZxMplsTEAccTunnelStatusEntry
    MAX-ACCESS  not-accessible
    STATUS      current
    DESCRIPTION
            ""
    ::= { zxRosngMplsTeMIB 20 }

zxMplsTEAccTunnelStatusEntry OBJECT-TYPE
    SYNTAX      ZxMplsTEAccTunnelStatusEntry
    MAX-ACCESS  not-accessible
    STATUS      current
    DESCRIPTION
            ""
    INDEX   { zxMplsTEAccTunnelStatusTunnelID}
    ::= { zxMplsTEAccTunnelStatusTable 1 }

ZxMplsTEAccTunnelStatusEntry ::=
    SEQUENCE {
        zxMplsTEAccTunnelStatusTunnelID         Unsigned32,
        zxMplsTEAccTunnelStatusOperStat         INTEGER,
        zxMplsTEAccTunnelStatusAdminStat        INTEGER,
        zxMplsTEAccTunnelStatusAssoc            INTEGER,
        zxMplsTEAccTunnelStatusUtilize         Unsigned32,
        zxMplsTEAccTunnelStatusUtilizeIn         Unsigned32
    }


zxMplsTEAccTunnelStatusTunnelID OBJECT-TYPE
    SYNTAX      Unsigned32 (1..131072)
    MAX-ACCESS  not-accessible
    STATUS      current
    DESCRIPTION
            "Uniquely identifies a set of access tunnel instances between a
            pair of ingress and egress LSRs."
    ::= { zxMplsTEAccTunnelStatusEntry 1 }

zxMplsTEAccTunnelStatusOperStat OBJECT-TYPE
    SYNTAX      INTEGER{down(0),up(1)}
    MAX-ACCESS  read-only
    STATUS      current
    DESCRIPTION
            "This value identifies actual operational status of this access
            tunnel."
    ::= { zxMplsTEAccTunnelStatusEntry 2 }

zxMplsTEAccTunnelStatusAdminStat OBJECT-TYPE
    SYNTAX      INTEGER{down(0),up(1)}
    MAX-ACCESS  read-only
    STATUS      current
    DESCRIPTION
            "This value identifies the administrator status of this access
            tunnel."
    ::= { zxMplsTEAccTunnelStatusEntry 3 }

zxMplsTEAccTunnelStatusAssoc OBJECT-TYPE
    SYNTAX      INTEGER{disabled(1),unbound(2),bound(3)}
    MAX-ACCESS  read-only
    STATUS      current
    DESCRIPTION
            "This value identifies the associate bidirect status of this
            access tunnel."
    ::= { zxMplsTEAccTunnelStatusEntry 4 }
zxMplsTEAccTunnelStatusUtilize OBJECT-TYPE
    SYNTAX      Unsigned32(0..4294967294|4294967295)
    MAX-ACCESS  read-only
    STATUS      current
    DESCRIPTION
            "The bw utilize of access tunnel. It's default value is 4294967295."
    ::= { zxMplsTEAccTunnelStatusEntry 5 }
zxMplsTEAccTunnelStatusUtilizeIn OBJECT-TYPE
    SYNTAX      Unsigned32(0..4294967294|4294967295)
    MAX-ACCESS  read-only
    STATUS      current
    DESCRIPTION
            "The bw in utilize of access tunnel. It's default value is 4294967295."
    ::= { zxMplsTEAccTunnelStatusEntry 6 }

--*************************************************************************
--  zxMplsTETunnelBfdCfgTable
--*************************************************************************

zxMplsTETunnelBfdCfgTable OBJECT-TYPE
    SYNTAX      SEQUENCE OF ZxMplsTETunnelBfdCfgEntry
    MAX-ACCESS  not-accessible
    STATUS      current
    DESCRIPTION
            ""
    ::= { zxRosngMplsTeMIB 21 }

zxMplsTETunnelBfdCfgEntry OBJECT-TYPE
    SYNTAX      ZxMplsTETunnelBfdCfgEntry
    MAX-ACCESS  not-accessible
    STATUS      current
    DESCRIPTION
            ""
    INDEX   { zxMplsTETunnelBfdCfgTunnelName,zxMplsTETunnelBfdCfgMSAttribute }
    ::= { zxMplsTETunnelBfdCfgTable 1 }

ZxMplsTETunnelBfdCfgEntry ::=
    SEQUENCE {
        zxMplsTETunnelBfdCfgTunnelName        DisplayString,
        zxMplsTETunnelBfdCfgMSAttribute       INTEGER,
        zxMplsTETunnelBfdCfgDeteMultiplier    Unsigned32,
        zxMplsTETunnelBfdCfgMinTxInterval     Unsigned32,
        zxMplsTETunnelBfdCfgMinRxInterval     Unsigned32,
        zxMplsTETunnelBfdCfgRowStatus         RowStatus
    }

zxMplsTETunnelBfdCfgTunnelName OBJECT-TYPE
    SYNTAX      DisplayString(SIZE(0..32))
    MAX-ACCESS  not-accessible
    STATUS      current
    DESCRIPTION
            "The index of path option which equals to tunnel name."
    ::= { zxMplsTETunnelBfdCfgEntry 1 }

zxMplsTETunnelBfdCfgMSAttribute OBJECT-TYPE
    SYNTAX      INTEGER{master(1),slave(2)}
    MAX-ACCESS  not-accessible
    STATUS      current
    DESCRIPTION
            "If this value is master ,indicates the entry is primary lsp's bfd
            configuration;If this value is slave ,indicates the entry is
            secondary lsp's bfd configuration."
    ::= { zxMplsTETunnelBfdCfgEntry 2 }

zxMplsTETunnelBfdCfgDeteMultiplier  OBJECT-TYPE
    SYNTAX      Unsigned32(3..50)
    MAX-ACCESS  read-create
    STATUS      current
    DESCRIPTION
            "The detecting multiple of receive/send CONTROL message."
    ::= { zxMplsTETunnelBfdCfgEntry 3 }

zxMplsTETunnelBfdCfgMinTxInterval OBJECT-TYPE
    SYNTAX      Unsigned32(3..990)
    MAX-ACCESS  read-create
    STATUS      current
    DESCRIPTION
            "The minimal time to send CONTROL message."
    ::= { zxMplsTETunnelBfdCfgEntry 4 }

zxMplsTETunnelBfdCfgMinRxInterval OBJECT-TYPE
    SYNTAX      Unsigned32(3..990)
    MAX-ACCESS  read-create
    STATUS      current
    DESCRIPTION
        "The minimal time to receive CONTROL message."
    ::= { zxMplsTETunnelBfdCfgEntry 5 }

zxMplsTETunnelBfdCfgRowStatus OBJECT-TYPE
    SYNTAX      RowStatus
    MAX-ACCESS  read-create
    STATUS      current
    DESCRIPTION
        "row status."
    ::= { zxMplsTETunnelBfdCfgEntry 6 }

--*************************************************************************
--  zxMplsTEIfCfgTable
--*************************************************************************

zxMplsTEIfCfgTable OBJECT-TYPE
    SYNTAX      SEQUENCE OF ZxMplsTEIfCfgEntry
    MAX-ACCESS  not-accessible
    STATUS      current
    DESCRIPTION
            "A list of mpls traffic-eng interface entries."
    ::= { zxRosngMplsTeMIB 6 }

zxMplsTEIfCfgEntry OBJECT-TYPE
    SYNTAX      ZxMplsTEIfCfgEntry
    MAX-ACCESS  not-accessible
    STATUS      current
    DESCRIPTION
            "An entry containing mpls traffic-eng interface."
    INDEX   { zxMplsTEIfCfgIfName }
    ::= { zxMplsTEIfCfgTable 1 }

ZxMplsTEIfCfgEntry ::=
    SEQUENCE {
        zxMplsTEIfCfgIfName     DisplayString,
        zxMplsTEIfCfgIfIndex            Unsigned32,
        zxMplsTEIfCfgBfdEnable    INTEGER,
        zxMplsTEIfCfgAuthenti       INTEGER,
        zxMplsTEIfCfgAuthChallage   INTEGER,
        zxMplsTEIfCfgAuthChallageImp        INTEGER,
        zxMplsTEIfCfgAuthKey        DisplayString,
        zxMplsTEIfCfgAuthType       INTEGER,
        zxMplsTEIfCfgAuthWinSize        Integer32,
        zxMplsTEIfCfgAdminWeight Unsigned32,
        zxMplsTEIfCfgAutoBackup INTEGER,
        zxMplsTEIfCfgAutobackNHoponly INTEGER,
        zxMplsTEIfCfgHelloRefresh INTEGER,
        zxMplsTEIfCfgHelloRefInterval Unsigned32,
        zxMplsTEIfCfgHelloRefMisses Unsigned32 ,
        zxMplsTEIfCfgRowStatus    RowStatus,
        zxMplsTEIfCfgConvRatioValue Unsigned32,
        zxMplsTEIfCfgDscpValue   Unsigned32,
        zxMplsTEIfCfgGS          INTEGER,
        zxMplsTEIfCfgAuthKeyChain DisplayString,
        zxMplsTEIfCfgAuthMode     INTEGER
    }


zxMplsTEIfCfgIfName OBJECT-TYPE
    SYNTAX      DisplayString(SIZE(0..32))
    MAX-ACCESS  not-accessible
    STATUS      current
    DESCRIPTION
            "The name of this interface."
    ::= { zxMplsTEIfCfgEntry 1 }

zxMplsTEIfCfgIfIndex OBJECT-TYPE
    SYNTAX      Unsigned32
    MAX-ACCESS  read-only
    STATUS      current
    DESCRIPTION
            "A unique value, greater than zero, for each interface which
            enables mpls traffic-eng."
    ::= { zxMplsTEIfCfgEntry 2 }

zxMplsTEIfCfgBfdEnable OBJECT-TYPE
    SYNTAX      INTEGER {false(0), true(1)}
    MAX-ACCESS  read-create
    STATUS      current
    DESCRIPTION
            "If this interface enables bfd,this value is true,otherwise
            it is false."
    DEFVAL {false}
    ::= { zxMplsTEIfCfgEntry 3 }

zxMplsTEIfCfgAuthenti OBJECT-TYPE
    SYNTAX      INTEGER {false(0), true(1)}
    MAX-ACCESS  read-create
    STATUS      current
    DESCRIPTION
            "If this interface enables RSVP cryptographic authentication, this
            value is true,otherwise it is false."
    DEFVAL {false}
    ::= { zxMplsTEIfCfgEntry 4 }


zxMplsTEIfCfgAuthChallage OBJECT-TYPE
    SYNTAX      INTEGER {false(0), true(1)}
    MAX-ACCESS  read-create
    STATUS      current
    DESCRIPTION
            "If this interface as a receiver enables rsvp authentication
            challenge,this value is true,otherwise it is false."
    DEFVAL { false }
    ::= { zxMplsTEIfCfgEntry 5 }

zxMplsTEIfCfgAuthChallageImp OBJECT-TYPE
    SYNTAX      INTEGER {false(0), true(1)}
    MAX-ACCESS  read-create
    STATUS      current
    DESCRIPTION
            "If this interface as a sender enables rsvp authentication
            challenge,this value is true,otherwise it is false."
    DEFVAL { false }
    ::= { zxMplsTEIfCfgEntry 6 }

zxMplsTEIfCfgAuthKey OBJECT-TYPE
    SYNTAX      DisplayString(SIZE(8..40))
    MAX-ACCESS  read-create
    STATUS      current
    DESCRIPTION
            "Specifies shared secret for all neighbors on this interface."
    DEFVAL { "RSVP-AUTH" }
    ::= { zxMplsTEIfCfgEntry 7 }


zxMplsTEIfCfgAuthType   OBJECT-TYPE
    SYNTAX      INTEGER {md5(1), sha1(2)}
    MAX-ACCESS  read-create
    STATUS      current
    DESCRIPTION
            "Specifies the type of authentication algorithm on this interface."
    DEFVAL {md5}
    ::= { zxMplsTEIfCfgEntry 8 }

zxMplsTEIfCfgAuthWinSize   OBJECT-TYPE
    SYNTAX      Integer32(1..64)
    MAX-ACCESS  read-create
    STATUS      current
    DESCRIPTION
            "Specifies received window size for authenticated messages on this
            interface."
    DEFVAL { 32 }
    ::= { zxMplsTEIfCfgEntry 9 }

zxMplsTEIfCfgAdminWeight   OBJECT-TYPE
    SYNTAX      Unsigned32(1..65535)
    MAX-ACCESS  read-create
    STATUS      current
    DESCRIPTION
            "The config metric of mpls te interface."
    DEFVAL { 0 }
    ::= { zxMplsTEIfCfgEntry 10 }

zxMplsTEIfCfgAutoBackup   OBJECT-TYPE
    SYNTAX      INTEGER {false(0), true(1)}
    MAX-ACCESS  read-create
    STATUS      current
    DESCRIPTION
            "If this object is true, then it prefers NODE_PROTECT to
            LINK_PROTECT by autobackup tunnel."
    DEFVAL { false }
    ::= { zxMplsTEIfCfgEntry 11 }

zxMplsTEIfCfgAutobackNHoponly   OBJECT-TYPE
    SYNTAX      INTEGER {false(0), true(1)}
    MAX-ACCESS  read-create
    STATUS      current
    DESCRIPTION
            "If this object is true, then it only requires LINK_PROTECT
            by autobackup tunnel."
    DEFVAL { false }
    ::= { zxMplsTEIfCfgEntry 12 }

zxMplsTEIfCfgHelloRefresh   OBJECT-TYPE
    SYNTAX      INTEGER {false(0), true(1)}
    MAX-ACCESS  read-create
    STATUS      current
    DESCRIPTION
            "If this object is true, then the interface hello
            refresh is enable."
    DEFVAL { false }
    ::= { zxMplsTEIfCfgEntry 13 }

zxMplsTEIfCfgHelloRefInterval   OBJECT-TYPE
    SYNTAX      Unsigned32(10..30000)
    MAX-ACCESS  read-create
    STATUS      current
    DESCRIPTION
            "hello refresh interval on if."
    DEFVAL { 10000 }
    ::= { zxMplsTEIfCfgEntry 14 }

zxMplsTEIfCfgHelloRefMisses   OBJECT-TYPE
    SYNTAX      Unsigned32(4..10)
    MAX-ACCESS  read-create
    STATUS      current
    DESCRIPTION
            "hello refresh misses on if."
    DEFVAL { 4 }
    ::= { zxMplsTEIfCfgEntry 15 }

zxMplsTEIfCfgRowStatus   OBJECT-TYPE
    SYNTAX      RowStatus
    MAX-ACCESS  read-create
    STATUS      current
    DESCRIPTION
            "row status."
    ::= { zxMplsTEIfCfgEntry 16 }

zxMplsTEIfCfgConvRatioValue   OBJECT-TYPE
    SYNTAX      Unsigned32(1..100)
    MAX-ACCESS  read-create
    STATUS      current
    DESCRIPTION
            "Interface's convergence ratio value."
    DEFVAL { 100 }
    ::= { zxMplsTEIfCfgEntry 17 }

zxMplsTEIfCfgDscpValue   OBJECT-TYPE
    SYNTAX      Unsigned32(0..63)
    MAX-ACCESS  read-create
    STATUS      current
    DESCRIPTION
            "The dscp value of the interface."
    ::= { zxMplsTEIfCfgEntry 18 }

zxMplsTEIfCfgGS   OBJECT-TYPE
    SYNTAX      INTEGER {false(2), true(1)}
    MAX-ACCESS  read-create
    STATUS      current
    DESCRIPTION
            "Enable interface RSVP GS."
    DEFVAL { false }
    ::= { zxMplsTEIfCfgEntry 19 }
	
zxMplsTEIfCfgAuthKeyChain OBJECT-TYPE
    SYNTAX      DisplayString(SIZE(1..31))
    MAX-ACCESS  read-create
    STATUS      current
    DESCRIPTION
            "Specifies key chain for all neighbors on this interface."
    ::= { zxMplsTEIfCfgEntry 20 }
    
zxMplsTEIfCfgAuthMode OBJECT-TYPE
    SYNTAX      INTEGER {key(1), keychain(2)}
    MAX-ACCESS  read-create
    STATUS      current
    DESCRIPTION
            "Specifies the mode of authentication on this interface."
    DEFVAL {key}
    ::= { zxMplsTEIfCfgEntry 21 }
--*************************************************************************
--  zxMplsTEDSTEClassCfgTable
--*************************************************************************

zxMplsTEDSTEClassCfgTable OBJECT-TYPE
    SYNTAX      SEQUENCE OF ZxMplsTEDSTEClassCfgEntry
    MAX-ACCESS  not-accessible
    STATUS      current
    DESCRIPTION
            "A list of DS-TE TE-Class entries."
    ::= { zxRosngMplsTeMIB 22 }

zxMplsTEDSTEClassCfgEntry OBJECT-TYPE
    SYNTAX      ZxMplsTEDSTEClassCfgEntry
    MAX-ACCESS  not-accessible
    STATUS      current
    DESCRIPTION
            "An entry containing DS-TE TE-Class."
    INDEX   { zxMplsTEDSTEClassCfgTEClassID }
    ::= { zxMplsTEDSTEClassCfgTable 1 }

ZxMplsTEDSTEClassCfgEntry ::=
    SEQUENCE {
        zxMplsTEDSTEClassCfgTEClassID    Unsigned32,
        zxMplsTEDSTEClassCfgClassType    Unsigned32,
        zxMplsTEDSTEClassCfgPriority     Unsigned32,
        zxMplsTEDSTEClassCfgRowStatus    RowStatus
    }


zxMplsTEDSTEClassCfgTEClassID OBJECT-TYPE
    SYNTAX      Unsigned32(0..7)
    MAX-ACCESS  not-accessible
    STATUS      current
    DESCRIPTION
            "The TE-Class id."
    ::= { zxMplsTEDSTEClassCfgEntry 1 }

zxMplsTEDSTEClassCfgClassType OBJECT-TYPE
    SYNTAX      Unsigned32(0..7)
    MAX-ACCESS  read-create
    STATUS      current
    DESCRIPTION
            "The class type."
    ::= { zxMplsTEDSTEClassCfgEntry 2 }

zxMplsTEDSTEClassCfgPriority OBJECT-TYPE
    SYNTAX      Unsigned32(0..7)
    MAX-ACCESS  read-create
    STATUS      current
    DESCRIPTION
            "The priority."
    ::= { zxMplsTEDSTEClassCfgEntry 3 }

zxMplsTEDSTEClassCfgRowStatus   OBJECT-TYPE
    SYNTAX      RowStatus
    MAX-ACCESS  read-create
    STATUS      current
    DESCRIPTION
            "row status."
    ::= { zxMplsTEDSTEClassCfgEntry 4 }

--*************************************************************************
--  zxMplsTEIfBwCfgTable
--*************************************************************************

zxMplsTEIfBwCfgTable OBJECT-TYPE
    SYNTAX      SEQUENCE OF ZxMplsTEIfBwCfgEntry
    MAX-ACCESS  not-accessible
    STATUS      current
    DESCRIPTION
            "A list of TE interface bandwidth entries."
    ::= { zxRosngMplsTeMIB 23 }

zxMplsTEIfBwCfgEntry OBJECT-TYPE
    SYNTAX      ZxMplsTEIfBwCfgEntry
    MAX-ACCESS  not-accessible
    STATUS      current
    DESCRIPTION
            "An entry containing TE interface bandwidth."
    INDEX   { zxMplsTEIfBwCfgIfName, zxMplsTEIfBwCfgReserveTunnelType }
    ::= { zxMplsTEIfBwCfgTable 1 }

ZxMplsTEIfBwCfgEntry ::=
    SEQUENCE {
        zxMplsTEIfBwCfgIfName               DisplayString,
        zxMplsTEIfBwCfgReserveTunnelType    INTEGER,
        zxMplsTEIfBwCfgIfBw                 Unsigned32,
        zxMplsTEIfBwCfgPerFlowBw            Unsigned32,
        zxMplsTEIfBwCfgBC0                  Unsigned32,
        zxMplsTEIfBwCfgBC1                  Unsigned32,
        zxMplsTEIfBwCfgBC2                  Unsigned32,
        zxMplsTEIfBwCfgBC3                  Unsigned32,
        zxMplsTEIfBwCfgBC4                  Unsigned32,
        zxMplsTEIfBwCfgBC5                  Unsigned32,
        zxMplsTEIfBwCfgBC6                  Unsigned32,
        zxMplsTEIfBwCfgBC7                  Unsigned32,
        zxMplsTEIfBwCfgRowStatus            RowStatus,
        zxMplsTEIfBwCfgPercent              Unsigned32,
        zxMplsTEIfBwCfgSpeedBlind           INTEGER,
        zxMplsTEIfBwCfgEIR                  Unsigned32
    }


zxMplsTEIfBwCfgIfName OBJECT-TYPE
    SYNTAX      DisplayString(SIZE(0..32))
    MAX-ACCESS  not-accessible
    STATUS      current
    DESCRIPTION
            "The name of this interface."
    ::= { zxMplsTEIfBwCfgEntry 1 }

zxMplsTEIfBwCfgReserveTunnelType OBJECT-TYPE
    SYNTAX      INTEGER {dynamic(1), static(2)}
    MAX-ACCESS  not-accessible
    STATUS      current
    DESCRIPTION
            "The tunnel type of bandwidth reserve."
    ::= { zxMplsTEIfBwCfgEntry 2 }

zxMplsTEIfBwCfgIfBw OBJECT-TYPE
    SYNTAX      Unsigned32(1..4294967295)
    MAX-ACCESS  read-create
    STATUS      current
    DESCRIPTION
            "TE interface bandwidth."
    ::= { zxMplsTEIfBwCfgEntry 3 }

zxMplsTEIfBwCfgPerFlowBw OBJECT-TYPE
    SYNTAX      Unsigned32(1..4294967295)
    MAX-ACCESS  read-create
    STATUS      current
    DESCRIPTION
            "PerFlow bandwidth."
    DEFVAL {0}
    ::= { zxMplsTEIfBwCfgEntry 4 }


zxMplsTEIfBwCfgBC0 OBJECT-TYPE
    SYNTAX      Unsigned32(1..4294967295)
    MAX-ACCESS  read-create
    STATUS      current
    DESCRIPTION
            "TE interface bc0 bandwidth."
    DEFVAL { 0 }
    ::= { zxMplsTEIfBwCfgEntry 5 }

zxMplsTEIfBwCfgBC1 OBJECT-TYPE
    SYNTAX      Unsigned32(1..4294967295)
    MAX-ACCESS  read-create
    STATUS      current
    DESCRIPTION
            "TE interface bc1 bandwidth."
    DEFVAL { 0 }
    ::= { zxMplsTEIfBwCfgEntry 6 }

zxMplsTEIfBwCfgBC2 OBJECT-TYPE
    SYNTAX      Unsigned32(1..4294967295)
    MAX-ACCESS  read-create
    STATUS      current
    DESCRIPTION
            "TE interface bc2 bandwidth."
    DEFVAL { 0 }
    ::= { zxMplsTEIfBwCfgEntry 7 }


zxMplsTEIfBwCfgBC3 OBJECT-TYPE
    SYNTAX      Unsigned32(1..4294967295)
    MAX-ACCESS  read-create
    STATUS      current
    DESCRIPTION
            "TE interface bc3 bandwidth."
    DEFVAL { 0 }
    ::= { zxMplsTEIfBwCfgEntry 8 }

zxMplsTEIfBwCfgBC4 OBJECT-TYPE
    SYNTAX      Unsigned32(1..4294967295)
    MAX-ACCESS  read-create
    STATUS      current
    DESCRIPTION
            "TE interface bc4 bandwidth."
    DEFVAL { 0 }
    ::= { zxMplsTEIfBwCfgEntry 9 }

zxMplsTEIfBwCfgBC5 OBJECT-TYPE
    SYNTAX      Unsigned32(1..4294967295)
    MAX-ACCESS  read-create
    STATUS      current
    DESCRIPTION
            "TE interface bc5 bandwidth."
    DEFVAL { 0 }
    ::= { zxMplsTEIfBwCfgEntry 10 }

zxMplsTEIfBwCfgBC6 OBJECT-TYPE
    SYNTAX      Unsigned32(1..4294967295)
    MAX-ACCESS  read-create
    STATUS      current
    DESCRIPTION
            "TE interface bc6 bandwidth."
    DEFVAL { 0 }
    ::= { zxMplsTEIfBwCfgEntry 11 }

zxMplsTEIfBwCfgBC7 OBJECT-TYPE
    SYNTAX      Unsigned32(1..4294967295)
    MAX-ACCESS  read-create
    STATUS      current
    DESCRIPTION
            "TE interface bc7 bandwidth."
    DEFVAL { 0 }
    ::= { zxMplsTEIfBwCfgEntry 12 }

zxMplsTEIfBwCfgRowStatus   OBJECT-TYPE
    SYNTAX      RowStatus
    MAX-ACCESS  read-create
    STATUS      current
    DESCRIPTION
            "row status."
    ::= { zxMplsTEIfBwCfgEntry 13 }

zxMplsTEIfBwCfgPercent OBJECT-TYPE
    SYNTAX      Unsigned32(0..100)
    MAX-ACCESS  read-create
    STATUS      current
    DESCRIPTION
            "The percentage of interface speed."
    ::= { zxMplsTEIfBwCfgEntry 14 }
    
zxMplsTEIfBwCfgSpeedBlind OBJECT-TYPE
    SYNTAX      INTEGER {enabled(1), disabled(2)}
    MAX-ACCESS  read-create
    STATUS      current
    DESCRIPTION
            "If this interface enables speed blind,this value is enabled,
            otherwise it is disabled."
    DEFVAL  { disabled }
    ::= { zxMplsTEIfBwCfgEntry 15 }

zxMplsTEIfBwCfgEIR OBJECT-TYPE
    SYNTAX      Unsigned32(0..4294967295)
    MAX-ACCESS  read-create
    STATUS      current
    DESCRIPTION
            "TE interface excess information rate."
    DEFVAL  { 0 }
    ::= { zxMplsTEIfBwCfgEntry 16 }

--*************************************************************************
--  zxMplsTEGrExtendCfgTable
--*************************************************************************
zxMplsTEGrExtendCfgTable OBJECT-TYPE
    SYNTAX      SEQUENCE OF ZxMplsTEGrExtendCfgEntry
    MAX-ACCESS  not-accessible
    STATUS      current
    DESCRIPTION
            ""
    ::= { zxRosngMplsTeMIB 24 }

zxMplsTEGrExtendCfgEntry OBJECT-TYPE
    SYNTAX      ZxMplsTEGrExtendCfgEntry
    MAX-ACCESS  not-accessible
    STATUS      current
    DESCRIPTION
            ""
    INDEX   {zxMplsTEGrExtendCfgNbrRid}
    ::= { zxMplsTEGrExtendCfgTable 1 }

ZxMplsTEGrExtendCfgEntry ::=
    SEQUENCE {
        zxMplsTEGrExtendCfgNbrRid        IpAddress,
        zxMplsTEGrExtendCfgRowStatus     RowStatus
    }

zxMplsTEGrExtendCfgNbrRid OBJECT-TYPE
    SYNTAX      IpAddress
    MAX-ACCESS  not-accessible
    STATUS      current
    DESCRIPTION
            "Neighbor router id."
    ::= { zxMplsTEGrExtendCfgEntry 1 }

zxMplsTEGrExtendCfgRowStatus OBJECT-TYPE
    SYNTAX      RowStatus
    MAX-ACCESS  read-create
    STATUS      current
    DESCRIPTION
            "Row status."
    ::= { zxMplsTEGrExtendCfgEntry 2 }


--*************************************************************************
--  zxMplsTERateLimitCfgTable
--*************************************************************************

zxMplsTERateLimitCfgTable OBJECT-TYPE
    SYNTAX      SEQUENCE OF ZxMplsTERateLimitCfgEntry
    MAX-ACCESS  not-accessible
    STATUS      current
    DESCRIPTION
            "A list of TE tunnel rate-limit entries."
    ::= { zxRosngMplsTeMIB 25 }

zxMplsTERateLimitCfgEntry OBJECT-TYPE
    SYNTAX      ZxMplsTERateLimitCfgEntry
    MAX-ACCESS  not-accessible
    STATUS      current
    DESCRIPTION
            "An entry containing TE tunnel rate-limit."
    INDEX   { zxMplsTERateLimitCfgTunnelName }
    ::= { zxMplsTERateLimitCfgTable 1 }

ZxMplsTERateLimitCfgEntry ::=
    SEQUENCE {
        zxMplsTERateLimitCfgTunnelName           DisplayString,
        zxMplsTERateLimitCfgMode                 INTEGER,
        zxMplsTERateLimitCfgCIR                  Unsigned32,
        zxMplsTERateLimitCfgCBS                  Unsigned32,
        zxMplsTERateLimitCfgPIR                  Unsigned32,
        zxMplsTERateLimitCfgPBS                  Unsigned32,
        zxMplsTERateLimitCfgRedAction            INTEGER,
        zxMplsTERateLimitCfgRowStatus            RowStatus
    }


zxMplsTERateLimitCfgTunnelName OBJECT-TYPE
    SYNTAX      DisplayString(SIZE(0..32))
    MAX-ACCESS  not-accessible
    STATUS      current
    DESCRIPTION
            "Tunnel name."
    ::= { zxMplsTERateLimitCfgEntry 1 }

zxMplsTERateLimitCfgMode OBJECT-TYPE
    SYNTAX      INTEGER {blind(1), aware(2)}
    MAX-ACCESS  read-create
    STATUS      current
    DESCRIPTION
            "The rate-limit mode."
    ::= { zxMplsTERateLimitCfgEntry 2 }

zxMplsTERateLimitCfgCIR OBJECT-TYPE
    SYNTAX      Unsigned32(0..4294967295)
    MAX-ACCESS  read-create
    STATUS      current
    DESCRIPTION
            "The committed information rate of this tunnel."
    ::= { zxMplsTERateLimitCfgEntry 3 }

zxMplsTERateLimitCfgCBS OBJECT-TYPE
    SYNTAX      Unsigned32(1..4294967295)
    MAX-ACCESS  read-create
    STATUS      current
    DESCRIPTION
            "The committed burst size of this tunnel."
    ::= { zxMplsTERateLimitCfgEntry 4 }


zxMplsTERateLimitCfgPIR OBJECT-TYPE
    SYNTAX      Unsigned32(1..4294967295)
    MAX-ACCESS  read-create
    STATUS      current
    DESCRIPTION
            "The peak information rate of this tunnel."
    ::= { zxMplsTERateLimitCfgEntry 5 }

zxMplsTERateLimitCfgPBS OBJECT-TYPE
    SYNTAX      Unsigned32(1..4294967295)
    MAX-ACCESS  read-create
    STATUS      current
    DESCRIPTION
            "The peak burst size of this tunnel."
    ::= { zxMplsTERateLimitCfgEntry 6 }
	
zxMplsTERateLimitCfgRedAction OBJECT-TYPE
    SYNTAX      INTEGER {discard(1), forward(2)}
    MAX-ACCESS  read-create
    STATUS      current
    DESCRIPTION
            "The rate-limit red action."
    ::= { zxMplsTERateLimitCfgEntry 7 }

zxMplsTERateLimitCfgRowStatus OBJECT-TYPE
    SYNTAX      RowStatus
    MAX-ACCESS  read-create
    STATUS      current
    DESCRIPTION
            "row status."
    ::= { zxMplsTERateLimitCfgEntry 100 }
	
--*************************************************************************
--  zxMplsTEConvRatioCfgTable
--*************************************************************************

zxMplsTEConvRatioCfgTable OBJECT-TYPE
    SYNTAX      SEQUENCE OF ZxMplsTEConvRatioCfgEntry
    MAX-ACCESS  not-accessible
    STATUS      obsolete
    DESCRIPTION
            "A list of static TE tunnel convergence ratio entries."
    ::= { zxRosngMplsTeMIB 26 }

zxMplsTEConvRatioCfgEntry OBJECT-TYPE
    SYNTAX      ZxMplsTEConvRatioCfgEntry
    MAX-ACCESS  not-accessible
    STATUS      obsolete
    DESCRIPTION
            "An entry containing static TE tunnel convergence ratio."
    INDEX   { zxMplsTEConvRatioCfgStTnnlName }
    ::= { zxMplsTEConvRatioCfgTable 1 }

ZxMplsTEConvRatioCfgEntry ::=
    SEQUENCE {
        zxMplsTEConvRatioCfgStTnnlName           DisplayString,
        zxMplsTEConvRatioCfgMode                 INTEGER,
        zxMplsTEConvRatioCfgValue                Unsigned32,
        zxMplsTEConvRatioCfgRowStatus            RowStatus
    }


zxMplsTEConvRatioCfgStTnnlName OBJECT-TYPE
    SYNTAX      DisplayString(SIZE(0..32))
    MAX-ACCESS  not-accessible
    STATUS      obsolete
    DESCRIPTION
            "Static Tunnel name."
    ::= { zxMplsTEConvRatioCfgEntry 1 }

zxMplsTEConvRatioCfgMode OBJECT-TYPE
    SYNTAX      INTEGER {inherit(1), config(2)}
    MAX-ACCESS  read-create
    STATUS      obsolete
    DESCRIPTION
            "The convergence ratio mode."
    ::= { zxMplsTEConvRatioCfgEntry 2 }

zxMplsTEConvRatioCfgValue OBJECT-TYPE
    SYNTAX      Unsigned32(1..100)
    MAX-ACCESS  read-create
    STATUS      obsolete
    DESCRIPTION
            "The convergence ratio value."
    ::= { zxMplsTEConvRatioCfgEntry 3 }

zxMplsTEConvRatioCfgRowStatus OBJECT-TYPE
    SYNTAX      RowStatus
    MAX-ACCESS  read-create
    STATUS      obsolete
    DESCRIPTION
            "row status."
    ::= { zxMplsTEConvRatioCfgEntry 100 }

--*************************************************************************
--  zxMplsTEEcmpGroupCfgTable
--*************************************************************************

zxMplsTEEcmpGroupCfgTable OBJECT-TYPE
    SYNTAX      SEQUENCE OF ZxMplsTEEcmpGroupCfgEntry
    MAX-ACCESS  not-accessible
    STATUS      current
    DESCRIPTION
            "A list of TE-ECMP group entries."
    ::= { zxRosngMplsTeMIB 27 }

zxMplsTEEcmpGroupCfgEntry OBJECT-TYPE
    SYNTAX      ZxMplsTEEcmpGroupCfgEntry
    MAX-ACCESS  not-accessible
    STATUS      current
    DESCRIPTION
            "An entry containing TE-ECMP group."
    INDEX   { zxMplsTEEcmpGroupCfgGroupId }
    ::= { zxMplsTEEcmpGroupCfgTable 1 }

ZxMplsTEEcmpGroupCfgEntry ::=
    SEQUENCE {
        zxMplsTEEcmpGroupCfgGroupId              Integer32,
        zxMplsTEEcmpGroupCfgLoadShare            INTEGER,
        zxMplsTEEcmpGroupCfgMinimum              Integer32,
        zxMplsTEEcmpGroupCfgDelay                Integer32,
        zxMplsTEEcmpGroupCfgRowStatus            RowStatus
    }

zxMplsTEEcmpGroupCfgGroupId   OBJECT-TYPE
    SYNTAX      Integer32(1..65535)
    MAX-ACCESS  not-accessible
    STATUS      current
    DESCRIPTION
            "configure TE-ECMP group."
    ::= { zxMplsTEEcmpGroupCfgEntry 1 }

zxMplsTEEcmpGroupCfgLoadShare   OBJECT-TYPE
    SYNTAX      INTEGER {perStream(1), perPacket(2)}
    MAX-ACCESS  read-create
    STATUS      current
    DESCRIPTION
            "configure the load-sharing policy of this TE-ECMP group."
    ::= { zxMplsTEEcmpGroupCfgEntry 2 }
 
zxMplsTEEcmpGroupCfgMinimum   OBJECT-TYPE
    SYNTAX      Integer32(1..65535)
    MAX-ACCESS  read-create
    STATUS      current
    DESCRIPTION
            "configure the minimum-member of this TE-ECMP group."
    ::= { zxMplsTEEcmpGroupCfgEntry 3 }

zxMplsTEEcmpGroupCfgDelay   OBJECT-TYPE
    SYNTAX      Integer32(0..1200)
    MAX-ACCESS  read-create
    STATUS      current
    DESCRIPTION
            "configure the update-delay of this TE-ECMP group."
    ::= { zxMplsTEEcmpGroupCfgEntry 4 }

zxMplsTEEcmpGroupCfgRowStatus   OBJECT-TYPE
    SYNTAX      RowStatus
    MAX-ACCESS  read-create
    STATUS      current
    DESCRIPTION
            "row status."
    ::= { zxMplsTEEcmpGroupCfgEntry 100 }

--*************************************************************************
--  zxMplsTEEcmpTunnelCfgTable
--*************************************************************************

zxMplsTEEcmpTunnelCfgTable OBJECT-TYPE
    SYNTAX      SEQUENCE OF ZxMplsTEEcmpTunnelCfgEntry
    MAX-ACCESS  not-accessible
    STATUS      current
    DESCRIPTION
            "A list of TE-ECMP tunnel entries."
    ::= { zxRosngMplsTeMIB 28 }
        
zxMplsTEEcmpTunnelCfgEntry OBJECT-TYPE
    SYNTAX      ZxMplsTEEcmpTunnelCfgEntry
    MAX-ACCESS  not-accessible
    STATUS      current
    DESCRIPTION
            "An entry containing TE-ECMP tunnel."
    INDEX   { zxMplsTEEcmpTunnelCfgGroupId,  zxMplsTEEcmpTunnelCfgTunnelId}
    ::= { zxMplsTEEcmpTunnelCfgTable 1 }

ZxMplsTEEcmpTunnelCfgEntry ::=
    SEQUENCE {
        zxMplsTEEcmpTunnelCfgGroupId          Integer32,
        zxMplsTEEcmpTunnelCfgTunnelId      		Unsigned32,
        zxMplsTEEcmpTunnelCfgRowStatus        RowStatus
    }

zxMplsTEEcmpTunnelCfgGroupId   OBJECT-TYPE
    SYNTAX      Integer32(1..65535)
    MAX-ACCESS  not-accessible
    STATUS      current
    DESCRIPTION
            "configure TE-ECMP group."
    ::= { zxMplsTEEcmpTunnelCfgEntry 1 }

zxMplsTEEcmpTunnelCfgTunnelId   OBJECT-TYPE
    SYNTAX      Unsigned32
    MAX-ACCESS  not-accessible
    STATUS      current
    DESCRIPTION
            "configure TE-ECMP tunnel."
    ::= { zxMplsTEEcmpTunnelCfgEntry 2 }
    
zxMplsTEEcmpTunnelCfgRowStatus   OBJECT-TYPE
    SYNTAX      RowStatus
    MAX-ACCESS  read-create
    STATUS      current
    DESCRIPTION
            "row status."
    ::= { zxMplsTEEcmpTunnelCfgEntry 100 }

--*************************************************************************
--  zxMplsTETnnlAffntyCfgTable
--*************************************************************************
zxMplsTETnnlAffntyCfgTable OBJECT-TYPE
    SYNTAX      SEQUENCE OF ZxMplsTETnnlAffntyCfgEntry
    MAX-ACCESS  not-accessible
    STATUS      current
    DESCRIPTION
            "A list of mpls traffic-eng tunnel affinity entries."
    ::= { zxRosngMplsTeMIB 29 }

zxMplsTETnnlAffntyCfgEntry OBJECT-TYPE
    SYNTAX      ZxMplsTETnnlAffntyCfgEntry
    MAX-ACCESS  not-accessible
    STATUS      current
    DESCRIPTION
            "An entry containing mpls traffic-eng tunnel affinities.
             The bit position or name can only be chosen to configure one of them."
    INDEX   {zxMplsTETnnlAffntyCfgTnnlName,
             zxMplsTETnnlAffntyCfgBitPos,
             zxMplsTETnnlAffntyCfgBitName}
    ::= { zxMplsTETnnlAffntyCfgTable 1 }

ZxMplsTETnnlAffntyCfgEntry ::=
    SEQUENCE {
        zxMplsTETnnlAffntyCfgTnnlName      DisplayString,
        zxMplsTETnnlAffntyCfgType          INTEGER,
        zxMplsTETnnlAffntyCfgBitPos        INTEGER,
        zxMplsTETnnlAffntyCfgBitName       DisplayString,
        zxMplsTETnnlAffntyCfgRowStatus     RowStatus
    }

zxMplsTETnnlAffntyCfgTnnlName OBJECT-TYPE
    SYNTAX      DisplayString(SIZE(0..31))
    MAX-ACCESS  not-accessible
    STATUS      current
    DESCRIPTION
            "The name of this tunnel."
    ::= { zxMplsTETnnlAffntyCfgEntry 1 }
    
zxMplsTETnnlAffntyCfgType OBJECT-TYPE
    SYNTAX      INTEGER{excludeAny(1),includeAny(2),includeAll(3)}
    MAX-ACCESS  read-create
    STATUS      current
    DESCRIPTION
            "The affinity type of this tunnel."
    ::= { zxMplsTETnnlAffntyCfgEntry 2 }
    
zxMplsTETnnlAffntyCfgBitPos OBJECT-TYPE
    SYNTAX      INTEGER(0..31)
    MAX-ACCESS  not-accessible
    STATUS      current
    DESCRIPTION
            "The bit position value of this type affinity on the tunnel."
    ::= { zxMplsTETnnlAffntyCfgEntry 3 }

zxMplsTETnnlAffntyCfgBitName OBJECT-TYPE
    SYNTAX      DisplayString(SIZE(0..32))
    MAX-ACCESS  not-accessible
    STATUS      current
    DESCRIPTION
            "The bit name of this type affinity on the tunnel."
    ::= { zxMplsTETnnlAffntyCfgEntry 4 }

zxMplsTETnnlAffntyCfgRowStatus OBJECT-TYPE
    SYNTAX      RowStatus
    MAX-ACCESS  read-create
    STATUS      current
    DESCRIPTION
            "Row status."
    ::= { zxMplsTETnnlAffntyCfgEntry 100 }

--*************************************************************************
--  zxMplsTEIfAffntyCfgTable
--*************************************************************************
zxMplsTEIfAffntyCfgTable OBJECT-TYPE
    SYNTAX      SEQUENCE OF ZxMplsTEIfAffntyCfgEntry
    MAX-ACCESS  not-accessible
    STATUS      current
    DESCRIPTION
            "A list of mpls traffic-eng interface affinity entries."
    ::= { zxRosngMplsTeMIB 30 }

zxMplsTEIfAffntyCfgEntry OBJECT-TYPE
    SYNTAX      ZxMplsTEIfAffntyCfgEntry
    MAX-ACCESS  not-accessible
    STATUS      current
    DESCRIPTION
            "An entry containing mpls traffic-eng interface affinities.
             The bit position or name can only be chosen to configure one of them."
    INDEX   {zxMplsTEIfAffntyCfgIfName,
             zxMplsTEIfAffntyCfgBitPos,
             zxMplsTEIfAffntyCfgBitName}
    ::= { zxMplsTEIfAffntyCfgTable 1 }

ZxMplsTEIfAffntyCfgEntry ::=
    SEQUENCE {
        zxMplsTEIfAffntyCfgIfName        DisplayString,
        zxMplsTEIfAffntyCfgBitPos        INTEGER,
        zxMplsTEIfAffntyCfgBitName       DisplayString,
        zxMplsTEIfAffntyCfgRowStatus     RowStatus
    }

zxMplsTEIfAffntyCfgIfName OBJECT-TYPE
    SYNTAX      DisplayString(SIZE(0..31))
    MAX-ACCESS  not-accessible
    STATUS      current
    DESCRIPTION
            "The name of this interface."
    ::= { zxMplsTEIfAffntyCfgEntry 1 }
    
zxMplsTEIfAffntyCfgBitPos OBJECT-TYPE
    SYNTAX      INTEGER(0..31)
    MAX-ACCESS  not-accessible
    STATUS      current
    DESCRIPTION
            "The bit position value of the affinity on this interface."
    ::= { zxMplsTEIfAffntyCfgEntry 2 }

zxMplsTEIfAffntyCfgBitName OBJECT-TYPE
    SYNTAX      DisplayString(SIZE(0..32))
    MAX-ACCESS  not-accessible
    STATUS      current
    DESCRIPTION
            "The bit name of the affinity on the interface."
    ::= { zxMplsTEIfAffntyCfgEntry 3 }
    
zxMplsTEIfAffntyCfgRowStatus OBJECT-TYPE
    SYNTAX      RowStatus
    MAX-ACCESS  read-create
    STATUS      current
    DESCRIPTION
            "Row status."
    ::= { zxMplsTEIfAffntyCfgEntry 100 }
    
--*************************************************************************
--  zxMplsTETrunkCfgTable
--*************************************************************************
zxMplsTETrunkCfgTable OBJECT-TYPE
    SYNTAX      SEQUENCE OF ZxMplsTETrunkCfgEntry
    MAX-ACCESS  not-accessible
    STATUS      current
    DESCRIPTION
            "A list of TE-Trunk entries."
    ::= { zxRosngMplsTeMIB 31 }

zxMplsTETrunkCfgEntry OBJECT-TYPE
    SYNTAX      ZxMplsTETrunkCfgEntry
    MAX-ACCESS  not-accessible
    STATUS      current
    DESCRIPTION
            "An entry containing TE-Trunk."
    INDEX   {zxMplsTETrunkCfgIfName}
    ::= { zxMplsTETrunkCfgTable 1 }

ZxMplsTETrunkCfgEntry ::=
    SEQUENCE {
        zxMplsTETrunkCfgIfName        DisplayString,
        zxMplsTETrunkCfgRowStatus     RowStatus
    }

zxMplsTETrunkCfgIfName OBJECT-TYPE
    SYNTAX      DisplayString(SIZE(0..32))
    MAX-ACCESS  not-accessible
    STATUS      current
    DESCRIPTION
            "The name of this interface."
    ::= { zxMplsTETrunkCfgEntry 1 }

zxMplsTETrunkCfgRowStatus OBJECT-TYPE
    SYNTAX      RowStatus
    MAX-ACCESS  read-create
    STATUS      current
    DESCRIPTION
            "Row status."
    ::= { zxMplsTETrunkCfgEntry 100 }

--*************************************************************************
--  zxMplsTETnnlPolicyClassCfgTable
--*************************************************************************
zxMplsTETnnlPolicyClassCfgTable OBJECT-TYPE
    SYNTAX      SEQUENCE OF ZxMplsTETnnlPolicyClassCfgEntry
    MAX-ACCESS  not-accessible
    STATUS      current
    DESCRIPTION
            "A list of TE tunnel policy-class entries."
    ::= { zxRosngMplsTeMIB 32 }

zxMplsTETnnlPolicyClassCfgEntry OBJECT-TYPE
    SYNTAX      ZxMplsTETnnlPolicyClassCfgEntry
    MAX-ACCESS  not-accessible
    STATUS      current
    DESCRIPTION
            "An entry containing TE tunnel policy-class."
    INDEX   { zxMplsTETnnlPolicyClassTnnlName,zxMplsTETnnlPolicyClassValue}
    ::= { zxMplsTETnnlPolicyClassCfgTable 1 }

ZxMplsTETnnlPolicyClassCfgEntry ::=
    SEQUENCE {
        zxMplsTETnnlPolicyClassTnnlName     DisplayString,
        zxMplsTETnnlPolicyClassValue        Integer32,
        zxMplsTETnnlPolicyClassRowSta       RowStatus
    }

zxMplsTETnnlPolicyClassTnnlName OBJECT-TYPE
    SYNTAX      DisplayString(SIZE(0..31))
    MAX-ACCESS  not-accessible
    STATUS      current
    DESCRIPTION
            "The name of this tunnel."
    ::= { zxMplsTETnnlPolicyClassCfgEntry 1 }

zxMplsTETnnlPolicyClassValue OBJECT-TYPE
    SYNTAX      Integer32(0..7|255)
    MAX-ACCESS  not-accessible
    STATUS      current
    DESCRIPTION
            "The Policy-Class value on this tunnel."
    DEFVAL { 255 }
    ::= { zxMplsTETnnlPolicyClassCfgEntry 2 }

zxMplsTETnnlPolicyClassRowSta OBJECT-TYPE
    SYNTAX      RowStatus
    MAX-ACCESS  read-create
    STATUS      current
    DESCRIPTION
            "row status."
    ::= { zxMplsTETnnlPolicyClassCfgEntry 100 }

--*************************************************************************
--  zxMplsTeP2mpStaticTnnlCfgTable
--*************************************************************************

zxMplsTeP2mpStaticTnnlCfgTable OBJECT-TYPE
    SYNTAX      SEQUENCE OF ZxMplsTeP2mpStaticTnnlCfgEntry
    MAX-ACCESS  not-accessible
    STATUS      current
    DESCRIPTION
            "A list of static P2MP tunnel entries."
    ::= { zxRosngMplsTeMIB 33 }

zxMplsTeP2mpStaticTnnlCfgEntry OBJECT-TYPE
    SYNTAX      ZxMplsTeP2mpStaticTnnlCfgEntry
    MAX-ACCESS  not-accessible
    STATUS      current
    DESCRIPTION
            "An entry containing static P2MP tunnel."
    INDEX   { zxMplsTeP2mpStaticTnnlName }
    ::= { zxMplsTeP2mpStaticTnnlCfgTable 1 }

ZxMplsTeP2mpStaticTnnlCfgEntry ::=
    SEQUENCE {
        zxMplsTeP2mpStaticTnnlName         DisplayString,
        zxMplsTeP2mpStaticTnnlID           Unsigned32,
        zxMplsTeP2mpStaticTnnlRole         INTEGER,
        zxMplsTeP2mpStaticTnnlLeaf         INTEGER,
        zxMplsTeP2mpStaticTnnlEnable       INTEGER,
        zxMplsTeP2mpStaticTnnlRowStatus    RowStatus   
    }

zxMplsTeP2mpStaticTnnlName OBJECT-TYPE
    SYNTAX      DisplayString(SIZE(1..32))
    MAX-ACCESS  not-accessible
    STATUS      current
    DESCRIPTION
            "static P2MP tunnel name."
    ::= { zxMplsTeP2mpStaticTnnlCfgEntry 1 }

zxMplsTeP2mpStaticTnnlID OBJECT-TYPE
    SYNTAX      Unsigned32(1..4294967294)
    MAX-ACCESS  read-only
    STATUS      current
    DESCRIPTION
            "static P2MP tunnel id."
    ::= { zxMplsTeP2mpStaticTnnlCfgEntry 2 }

zxMplsTeP2mpStaticTnnlRole OBJECT-TYPE
    SYNTAX      INTEGER{root(1),unroot(2)}
    MAX-ACCESS  read-create
    STATUS      current
    DESCRIPTION
            "static P2MP tunnel role."
    ::= { zxMplsTeP2mpStaticTnnlCfgEntry 3 }

zxMplsTeP2mpStaticTnnlLeaf OBJECT-TYPE
    SYNTAX      INTEGER{enabled(1),disabled(2)}
    MAX-ACCESS  read-create
    STATUS      current
    DESCRIPTION
            "static P2MP tunnel leaf enable/disable."
    ::= { zxMplsTeP2mpStaticTnnlCfgEntry 4 }

zxMplsTeP2mpStaticTnnlEnable OBJECT-TYPE
    SYNTAX      INTEGER{enabled(1),disabled(2)}
    MAX-ACCESS  read-create
    STATUS      current
    DESCRIPTION
            "static P2MP tunnel enable/disable."
    ::= { zxMplsTeP2mpStaticTnnlCfgEntry 5 }

zxMplsTeP2mpStaticTnnlRowStatus OBJECT-TYPE
    SYNTAX      RowStatus
    MAX-ACCESS  read-create
    STATUS      current
    DESCRIPTION
            "row status."
    ::= { zxMplsTeP2mpStaticTnnlCfgEntry 100 }

--*************************************************************************
--  zxMplsTeP2mpStaticLspCfgTable
--*************************************************************************
zxMplsTeP2mpStaticLspCfgTable OBJECT-TYPE
    SYNTAX      SEQUENCE OF ZxMplsTeP2mpStaticLspCfgEntry
    MAX-ACCESS  not-accessible
    STATUS      current
    DESCRIPTION
            "A list of static P2MP tunnel LSP entries."
    ::= { zxRosngMplsTeMIB 34 }

zxMplsTeP2mpStaticLspCfgEntry OBJECT-TYPE
    SYNTAX      ZxMplsTeP2mpStaticLspCfgEntry
    MAX-ACCESS  not-accessible
    STATUS      current
    DESCRIPTION
            "An entry containing static P2MP tunnel LSP."
    INDEX   { zxMplsTeP2mpStaticLspTnnlName, zxMplsTeP2mpStaticLspId}
    ::= { zxMplsTeP2mpStaticLspCfgTable 1 }

ZxMplsTeP2mpStaticLspCfgEntry ::=
    SEQUENCE {
        zxMplsTeP2mpStaticLspTnnlName         DisplayString,
        zxMplsTeP2mpStaticLspTnnlID           Unsigned32,
        zxMplsTeP2mpStaticLspId               Unsigned32,
        zxMplsTeP2mpStaticLspCir              Unsigned32,
        zxMplsTeP2mpStaticLspCbs              Unsigned32,
        zxMplsTeP2mpStaticLspEir              Unsigned32,
        zxMplsTeP2mpStaticLspEbs              Unsigned32,
        zxMplsTeP2mpStaticLspRowStatus        RowStatus   
    }

zxMplsTeP2mpStaticLspTnnlName OBJECT-TYPE
    SYNTAX      DisplayString(SIZE(1..32))
    MAX-ACCESS  not-accessible
    STATUS      current
    DESCRIPTION
            "static P2MP tunnel name."
    ::= { zxMplsTeP2mpStaticLspCfgEntry 1 }

zxMplsTeP2mpStaticLspTnnlID OBJECT-TYPE
    SYNTAX      Unsigned32(1..4294967294)
    MAX-ACCESS  read-only
    STATUS      current
    DESCRIPTION
            "static P2MP tunnel id."
    ::= { zxMplsTeP2mpStaticLspCfgEntry 2 }

zxMplsTeP2mpStaticLspId OBJECT-TYPE
    SYNTAX      Unsigned32
    MAX-ACCESS  not-accessible
    STATUS      current
    DESCRIPTION
            "static P2MP tunnel name."
    ::= { zxMplsTeP2mpStaticLspCfgEntry 3 }

zxMplsTeP2mpStaticLspCir OBJECT-TYPE
    SYNTAX      Unsigned32(0..4294967295)
    MAX-ACCESS  read-create
    STATUS      current
    DESCRIPTION
            "The bandwidth of this LSP cir."
    ::= { zxMplsTeP2mpStaticLspCfgEntry 4 }

zxMplsTeP2mpStaticLspCbs OBJECT-TYPE
    SYNTAX      Unsigned32(0..4294967295)
    MAX-ACCESS  read-create
    STATUS      current
    DESCRIPTION
            "The bandwidth of this LSP cbs."
    ::= { zxMplsTeP2mpStaticLspCfgEntry 5 }

zxMplsTeP2mpStaticLspEir OBJECT-TYPE
    SYNTAX      Unsigned32(0..4294967295)
    MAX-ACCESS  read-create
    STATUS      current
    DESCRIPTION
            "The bandwidth of this LSP eir."
    ::= { zxMplsTeP2mpStaticLspCfgEntry 6 }

zxMplsTeP2mpStaticLspEbs OBJECT-TYPE
    SYNTAX      Unsigned32(0..4294967295)
    MAX-ACCESS  read-create
    STATUS      current
    DESCRIPTION
            "The bandwidth of this LSP ebs."
    ::= { zxMplsTeP2mpStaticLspCfgEntry 7 }

zxMplsTeP2mpStaticLspRowStatus OBJECT-TYPE
    SYNTAX      RowStatus
    MAX-ACCESS  read-create
    STATUS      current
    DESCRIPTION
            "row status."
    ::= { zxMplsTeP2mpStaticLspCfgEntry 100 } 

--*************************************************************************
--  zxMplsTeP2mpSLspInSegCfgTable
--*************************************************************************

zxMplsTeP2mpSLspInSegCfgTable OBJECT-TYPE
    SYNTAX      SEQUENCE OF ZxMplsTeP2mpSLspInSegCfgEntry
    MAX-ACCESS  not-accessible
    STATUS      current
    DESCRIPTION
            "A list of static P2MP tunnel inseg entries."
    ::= { zxRosngMplsTeMIB 35 }

zxMplsTeP2mpSLspInSegCfgEntry OBJECT-TYPE
    SYNTAX      ZxMplsTeP2mpSLspInSegCfgEntry
    MAX-ACCESS  not-accessible
    STATUS      current
    DESCRIPTION
            "An entry containing static P2MP tunnel inseg."
    INDEX   { zxMplsTeP2mpSLspInSegTnnlName,
              zxMplsTeP2mpSLspInSegLspID}
    ::= { zxMplsTeP2mpSLspInSegCfgTable 1 }    

ZxMplsTeP2mpSLspInSegCfgEntry ::=
    SEQUENCE {
        zxMplsTeP2mpSLspInSegTnnlName         DisplayString,
        zxMplsTeP2mpSLspInSegTnnlID           Unsigned32,
        zxMplsTeP2mpSLspInSegLspID            INTEGER,
        zxMplsTeP2mpSLspInSegInPort           DisplayString,
        zxMplsTeP2mpSLspInSegInLabel          Unsigned32, 
        zxMplsTeP2mpSLspInSegRowStatus        RowStatus    
    }

zxMplsTeP2mpSLspInSegTnnlName OBJECT-TYPE
    SYNTAX      DisplayString(SIZE(1..32))
    MAX-ACCESS  not-accessible
    STATUS      current
    DESCRIPTION
            "static P2MP tunnel name."
    ::= { zxMplsTeP2mpSLspInSegCfgEntry 1 }

zxMplsTeP2mpSLspInSegTnnlID OBJECT-TYPE
    SYNTAX      Unsigned32(1..4294967294)
    MAX-ACCESS  read-only
    STATUS      current
    DESCRIPTION
            "static P2MP tunnel id."
    ::= { zxMplsTeP2mpSLspInSegCfgEntry 2 }

zxMplsTeP2mpSLspInSegLspID OBJECT-TYPE
    SYNTAX      INTEGER(1)
    MAX-ACCESS  not-accessible
    STATUS      current
    DESCRIPTION
            "static P2MP tunnel lsp id."
    ::= { zxMplsTeP2mpSLspInSegCfgEntry 3 }

zxMplsTeP2mpSLspInSegInPort OBJECT-TYPE
    SYNTAX      DisplayString(SIZE(1..32))
    MAX-ACCESS  read-create
    STATUS      current
    DESCRIPTION
            "static P2MP tunnel inseg port."
    ::= { zxMplsTeP2mpSLspInSegCfgEntry 4 }        

zxMplsTeP2mpSLspInSegInLabel OBJECT-TYPE
    SYNTAX      Unsigned32(16..1048575)
    MAX-ACCESS  read-create
    STATUS      current
    DESCRIPTION
            "static P2MP tunnel inseg label."
    ::= { zxMplsTeP2mpSLspInSegCfgEntry 5 }

zxMplsTeP2mpSLspInSegRowStatus OBJECT-TYPE
    SYNTAX      RowStatus
    MAX-ACCESS  read-create
    STATUS      current
    DESCRIPTION
            "row status."
    ::= { zxMplsTeP2mpSLspInSegCfgEntry 100 } 

--*************************************************************************
--  zxMplsTeP2mpSLspOutSegCfgTable
--*************************************************************************

zxMplsTeP2mpSLspOutSegCfgTable OBJECT-TYPE
    SYNTAX      SEQUENCE OF ZxMplsTeP2mpSLspOutSegCfgEntry
    MAX-ACCESS  not-accessible
    STATUS      current
    DESCRIPTION
            "A list of static P2MP tunnel outseg entries."
    ::= { zxRosngMplsTeMIB 36 }

zxMplsTeP2mpSLspOutSegCfgEntry OBJECT-TYPE
    SYNTAX      ZxMplsTeP2mpSLspOutSegCfgEntry
    MAX-ACCESS  not-accessible
    STATUS      current
    DESCRIPTION
            "An entry containing static P2MP tunnel outseg."
    INDEX   { zxMplsTeP2mpSLspOutSegTnnlName,
              zxMplsTeP2mpSLspOutSegLspID,
              zxMplsTeP2mpSLspOutSegID}
    ::= { zxMplsTeP2mpSLspOutSegCfgTable 1 }

ZxMplsTeP2mpSLspOutSegCfgEntry ::=
    SEQUENCE {
        zxMplsTeP2mpSLspOutSegTnnlName         DisplayString,
        zxMplsTeP2mpSLspOutSegTnnlID           Unsigned32,
        zxMplsTeP2mpSLspOutSegLspID            INTEGER,   
        zxMplsTeP2mpSLspOutSegID               INTEGER,
        zxMplsTeP2mpSLspOutSegOutPort          DisplayString,
        zxMplsTeP2mpSLspOutSegOutLabel         Unsigned32, 
        zxMplsTeP2mpSLspOutSegNexthop          IpAddress,  
        zxMplsTeP2mpSLspOutSegRowStatus        RowStatus
    }

zxMplsTeP2mpSLspOutSegTnnlName OBJECT-TYPE
    SYNTAX      DisplayString(SIZE(1..32))
    MAX-ACCESS  not-accessible
    STATUS      current
    DESCRIPTION
            "static P2MP tunnel name."
    ::= { zxMplsTeP2mpSLspOutSegCfgEntry 1 }

zxMplsTeP2mpSLspOutSegTnnlID OBJECT-TYPE
    SYNTAX      Unsigned32(1..4294967294)
    MAX-ACCESS  read-only
    STATUS      current
    DESCRIPTION
            "static P2MP tunnel id."
    ::= { zxMplsTeP2mpSLspOutSegCfgEntry 2 }

zxMplsTeP2mpSLspOutSegLspID OBJECT-TYPE
    SYNTAX      INTEGER(1)
    MAX-ACCESS  not-accessible
    STATUS      current
    DESCRIPTION
            "static P2MP tunnel lsp id."
    ::= { zxMplsTeP2mpSLspOutSegCfgEntry 3 }       

zxMplsTeP2mpSLspOutSegID OBJECT-TYPE
    SYNTAX      INTEGER(1..32)
    MAX-ACCESS  not-accessible
    STATUS      current
    DESCRIPTION
            "static P2MP tunnel outseg id."
    ::= { zxMplsTeP2mpSLspOutSegCfgEntry 4 }

zxMplsTeP2mpSLspOutSegOutPort OBJECT-TYPE
    SYNTAX      DisplayString(SIZE(1..32))
    MAX-ACCESS  read-create
    STATUS      current
    DESCRIPTION
            "static P2MP tunnel outseg port."
    ::= { zxMplsTeP2mpSLspOutSegCfgEntry 5 }        

zxMplsTeP2mpSLspOutSegOutLabel OBJECT-TYPE
    SYNTAX      Unsigned32(16..1048575)
    MAX-ACCESS  read-create
    STATUS      current
    DESCRIPTION
            "static P2MP tunnel outseg label."
    ::= { zxMplsTeP2mpSLspOutSegCfgEntry 6 }

zxMplsTeP2mpSLspOutSegNexthop OBJECT-TYPE
    SYNTAX      IpAddress
    MAX-ACCESS  read-create
    STATUS      current
    DESCRIPTION
            "static P2MP tunnel outseg next_hop."
    DEFVAL   { '00000000'H }    -- 0.0.0.0
    ::= { zxMplsTeP2mpSLspOutSegCfgEntry 7 }

zxMplsTeP2mpSLspOutSegRowStatus OBJECT-TYPE
    SYNTAX      RowStatus
    MAX-ACCESS  read-create
    STATUS      current
    DESCRIPTION
            "row status."
    ::= { zxMplsTeP2mpSLspOutSegCfgEntry 100 }

--*************************************************************************
--  zxMplsTEP2mpSTnnlStatusTable
--*************************************************************************    

zxMplsTEP2mpSTnnlStatusTable OBJECT-TYPE
    SYNTAX      SEQUENCE OF ZxMplsTEP2mpSTnnlStatusEntry
    MAX-ACCESS  not-accessible
    STATUS      current
    DESCRIPTION
            "A list of static P2MP tunnel status entries."
    ::= { zxRosngMplsTeMIB 37 }

zxMplsTEP2mpSTnnlStatusEntry OBJECT-TYPE
    SYNTAX      ZxMplsTEP2mpSTnnlStatusEntry
    MAX-ACCESS  not-accessible
    STATUS      current
    DESCRIPTION
            "An entry containing static P2MP tunnel status."
    INDEX   { zxMplsTEP2mpSTnnlID}
    ::= { zxMplsTEP2mpSTnnlStatusTable 1 }

ZxMplsTEP2mpSTnnlStatusEntry ::=
    SEQUENCE {
        zxMplsTEP2mpSTnnlID   Unsigned32,
        zxMplsTEP2mpSTnnlAdminStatus  INTEGER,
        zxMplsTEP2mpSTnnlProtStatus   INTEGER
    }

zxMplsTEP2mpSTnnlID OBJECT-TYPE
    SYNTAX      Unsigned32(1..4294967294)
    MAX-ACCESS  not-accessible
    STATUS      current
    DESCRIPTION
            "Uniquely identifies a set of static P2MP tunnel instances between
             a pair of ingress and egress LSRs."
    ::= { zxMplsTEP2mpSTnnlStatusEntry 1 }

zxMplsTEP2mpSTnnlAdminStatus OBJECT-TYPE
    SYNTAX      INTEGER{down(1),up(2)}
    MAX-ACCESS  read-only
    STATUS      current
    DESCRIPTION
            "This value identifies the administrator status of this
            static P2MP tunnel."
    ::= { zxMplsTEP2mpSTnnlStatusEntry 2 }

zxMplsTEP2mpSTnnlProtStatus OBJECT-TYPE
    SYNTAX      INTEGER{down(1),up(2)}
    MAX-ACCESS  read-only
    STATUS      current
    DESCRIPTION
            "This value identifies actual operational status of this 
            static P2MP tunnel."
    ::= { zxMplsTEP2mpSTnnlStatusEntry 3 }

--*************************************************************************
--  zxMplsTELocalTunnelUtilizeTable
--*************************************************************************
zxMplsTELocalTunnelUtilizeTable OBJECT-TYPE
    SYNTAX      SEQUENCE OF ZxMplsTELocalTunnelUtilizeEntry
    MAX-ACCESS  not-accessible
    STATUS      current
    DESCRIPTION
            ""
    ::= { zxRosngMplsTeMIB 55 }
zxMplsTELocalTunnelUtilizeEntry OBJECT-TYPE
    SYNTAX      ZxMplsTELocalTunnelUtilizeEntry
    MAX-ACCESS  not-accessible
    STATUS      current
    DESCRIPTION
            ""
    INDEX   { zxMplsTELocalTunnelUtilizeTnnlID}
    ::= { zxMplsTELocalTunnelUtilizeTable 1 }
ZxMplsTELocalTunnelUtilizeEntry ::=
    SEQUENCE {
        zxMplsTELocalTunnelUtilizeTnnlID           Unsigned32,
        zxMplsTELocalTunnelUtilize                 Unsigned32,
        zxMplsTELocalTunnelUtilizeIn               Unsigned32
    }
zxMplsTELocalTunnelUtilizeTnnlID OBJECT-TYPE
    SYNTAX      Unsigned32 (1..65535)
    MAX-ACCESS  not-accessible
    STATUS      current
    DESCRIPTION
            "Uniquely identifies a set of local tunnel instances between a
            pair of ingress and egress LSRs."
    ::= { zxMplsTELocalTunnelUtilizeEntry 1 }
zxMplsTELocalTunnelUtilize OBJECT-TYPE
    SYNTAX      Unsigned32(0..4294967294|4294967295)
    MAX-ACCESS  read-only
    STATUS      current
    DESCRIPTION
            "The bw utilize of local tunnel.It's default value is 4294967295."
    ::= { zxMplsTELocalTunnelUtilizeEntry 2 }
zxMplsTELocalTunnelUtilizeIn OBJECT-TYPE
    SYNTAX      Unsigned32(0..4294967294|4294967295)
    MAX-ACCESS  read-only
    STATUS      current
    DESCRIPTION
            "The bw in utilize of local tunnel.It's default value is 4294967295."
    ::= { zxMplsTELocalTunnelUtilizeEntry 3 }
END
