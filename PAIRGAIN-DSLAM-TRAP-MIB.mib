PAIRGAIN-DSLAM-TRAP-MIB

-- Trap MIB Release 1.0
-- Revision 08/1/97
-- Printed 

-- Copyright 1997 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.  
--
-- It is PairGain's intent to encourage the widespread use of
-- this Specification in connection with the management of
-- PairGain's products. PairGain grants vendors, end-users,
-- and other interested parties a non-exclusive license to
-- use this Specification in connection with the management
-- of PairGain products.
--
-- This Specification is supplied "AS IS," and PairGain makes
-- no warranty, either expressed or implied, as to the use,
-- operation, condition, or performance of the Specification.


DEFINITIONS ::= BEGIN

-- SECTION 1: Top Level Definitions

-- Imports

IMPORTS
        snmp, ifIndex                   FROM RFC1213-MIB
        TRAP-TYPE                       FROM RFC-1215

        pgainDSLAM                      FROM PAIRGAIN-COMMON-HD-MIB

--        pairgain, 
        pgDSLAMChassisPsStatus, 
        pgDSLAMChassisFanStatus, 
        pgDSLAMChassisTemperature,
        pgDSLAMConfigChangeCnts, 
        pgDSLAMConfigLastChange         FROM PAIRGAIN-DSLAM-CHASSIS-MIB;


-- SECTION 2: Generic Trap Definitions

coldStart TRAP-TYPE
        ENTERPRISE      snmp
--      STATUS          mandatory for all PairGain agents
        DESCRIPTION
                "A coldStart trap signifies that the sending protocol entity 
                is reinitializing itself such that the agent's configuration 
                or the protocol entity implementation may be altered."
        ::= 0

linkDown TRAP-TYPE
        ENTERPRISE      snmp
        VARIABLES       { ifIndex }
--      STATUS          optional
        DESCRIPTION
                "A linkDown trap signifies that the sending protocol entity 
                recognizes a failure in one of the communication links 
                represented in the agent's configuration."
        ::= 2

linkUp TRAP-TYPE
        ENTERPRISE      snmp
        VARIABLES       { ifIndex }
--      STATUS          optional
        DESCRIPTION
                "A linkUp trap signifies that the sending protocol entity 
                recognizes that one of the communication links represented in 
                the agent's configuration has come up."
        ::= 3

authenticationFailure TRAP-TYPE
        ENTERPRISE      snmp
--      STATUS          mandatory for all PairGain agents
        DESCRIPTION
                "An authenticationFailure trap signifies that the sending 
                protocol entity is the addressee of a protocol message that is
                not properly authenticated. While implementations of the SNMP 
                must be capable of generating this trap, they must also be 
                capable of suppressing the emission of such traps via an 
                implementation-specific mechanism."
        ::= 4


-- SECTION 3: PairGain Enterprise DSLAM Chassis Trap Definitions

pgDSLAMchassisPowerSupplyFailure TRAP-TYPE
        ENTERPRISE      pgainDSLAM
        VARIABLES       { pgDSLAMChassisPsStatus }
--      STATUS          mandatory for all PairGain agents
        DESCRIPTION
                "Power supply failure."
        ::= 0           -- 0x00

pgDSLAMchassisFanFailure TRAP-TYPE
        ENTERPRISE      pgainDSLAM
        VARIABLES       { pgDSLAMChassisFanStatus }
--      STATUS          mandatory for all PairGain agents
        DESCRIPTION
                "Fan failure."
        ::= 1           -- 0x01

pgDSLAMchassisConfigChange TRAP-TYPE
        ENTERPRISE      pgainDSLAM
        VARIABLES       { pgDSLAMConfigChangeCnts, pgDSLAMConfigLastChange }
--      STATUS          mandatory for all PairGain agents
        DESCRIPTION
                "General configuration change detected."
        ::= 2           -- 0x02

pgDSLAMchassisTemperatureThresholdExceeded TRAP-TYPE
        ENTERPRISE      pgainDSLAM
--      STATUS          mandatory for all PairGain agents
        DESCRIPTION
                "Temperature Threshold Exceeded."
        ::= 3           -- 0x03


-- SECTION 4: PairGain Enterprise DSLAM HDSL Trap Definitions

pgDSLAMHDSLESThresholdExceeded TRAP-TYPE
        ENTERPRISE      pgainDSLAM
        VARIABLES       { ifIndex }
--      STATUS          mandatory for all PairGain agents
        DESCRIPTION
                "HDSL ES Threshold Exceeded."
        ::= 4           -- 0x04

pgDSLAMHDSLMarginThresholdExceeded TRAP-TYPE
        ENTERPRISE      pgainDSLAM
        VARIABLES       { ifIndex }
--      STATUS          mandatory for all PairGain agents
        DESCRIPTION
                "HDSL Margin Threshold Exceeded."
        ::= 5           -- 0x05

pgDSLAMHDSLPFO TRAP-TYPE
        ENTERPRISE      pgainDSLAM
        VARIABLES       { ifIndex }
--      STATUS          mandatory for all PairGain agents
        DESCRIPTION
                "HDSL Power Feed Open."
        ::= 6           -- 0x06

pgDSLAMHDSLPFS TRAP-TYPE
        ENTERPRISE      pgainDSLAM
        VARIABLES       { ifIndex }
--      STATUS          mandatory for all PairGain agents
        DESCRIPTION
                "HDSL Power Feed Short."
        ::= 7           -- 0x07

END
