-- Avaya Aura Session Manager MIB
-- Copyright (c) 2008-2009 by Avaya Inc. All rights reserved. 
-- MIB version 1.0.0 
-- Avaya Compas ID: NA

AV-AURA-SESSION-MANAGER-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--
avaya              OBJECT IDENTIFIER ::= { enterprises 6889 }
products           OBJECT IDENTIFIER ::= { avaya 1 }
mibs               OBJECT IDENTIFIER ::= { avaya 2 }

avAuraSessMgrProd OBJECT IDENTIFIER ::= { products 36 }
avAuraSessMgrMibs MODULE-IDENTITY
       LAST-UPDATED "201301211353Z" -- 21 January 2013
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201301211353Z" -- 21 January 2013
       DESCRIPTION "MIB Version 1.0.0 - autobuild. Generated via the MIBTOOL."
             
       
       ::= { mibs 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-----------------------------------------------------------------------
-- According to RFC 2578 section 8.5, the next to last sub-identifier
-- in the name of any newly defined notification must have the value
-- zero. This is to achieve compatibility with SNMPv1 traps.
------------------------------------------------------------------------
-------------------NOTIFICATION OBJECTS *********************************START
avSessMgrTALM00100 NOTIFICATION-TYPE
	STATUS current
	DESCRIPTION
	"Test alarm for testing only, no recovery action necessary(Indeterminate)"
	::= { avAuraSessMgrMibNotifications 31001 }

avSessMgrTestAlarm NOTIFICATION-TYPE
	STATUS current
	DESCRIPTION
	"Clear event for testing only, no recovery action necessary(Indeterminate)"
	::= { avAuraSessMgrMibNotifications 31002 }

avSessMgrMMTC20011 NOTIFICATION-TYPE
	STATUS current
	DESCRIPTION
	"Postgres database sanity check failed; the database is unaccessible(Major)"
	::= { avAuraSessMgrMibNotifications 321 }

avSessMgrMMTC20013 NOTIFICATION-TYPE
	STATUS current
	DESCRIPTION
	"SIP A/S Service Host(s) sanity check failed; call processing is down(Minor)"
	::= { avAuraSessMgrMibNotifications 323 }

avSessMgrMMTC20015 NOTIFICATION-TYPE
	STATUS current
	DESCRIPTION
	"SIP A/S Service Director sanity check failed; call processing is down(Minor)"
	::= { avAuraSessMgrMibNotifications 325 }

avSessMgrMMTC20017 NOTIFICATION-TYPE
	STATUS current
	DESCRIPTION
	"SIP A/S Management Server sanity check failed; SIP A/S admin is unavailable(Minor)"
	::= { avAuraSessMgrMibNotifications 327 }

avSessMgrMMTC20019 NOTIFICATION-TYPE
	STATUS current
	DESCRIPTION
	"SAL-Agent sanity check failed; alarms are not being processed(Minor)"
	::= { avAuraSessMgrMibNotifications 329 }

avSessMgrMMTC20021 NOTIFICATION-TYPE
	STATUS current
	DESCRIPTION
	"Management jboss sanity check failed; services are unavailable(Minor)"
	::= { avAuraSessMgrMibNotifications 3211 }

avSessMgrMMTC20025 NOTIFICATION-TYPE
	STATUS current
	DESCRIPTION
	"Security Module sanity check failed; call processing is down(Major)"
	::= { avAuraSessMgrMibNotifications 3213 }

avSessMgrMMTC20029 NOTIFICATION-TYPE
	STATUS current
	DESCRIPTION
	"Call Processing SAR is not deployed(Major)"
	::= { avAuraSessMgrMibNotifications 3215 }

avSessMgrMMTC20031 NOTIFICATION-TYPE
	STATUS current
	DESCRIPTION
	"Data Distribution/Redundancy is down(Minor)"
	::= { avAuraSessMgrMibNotifications 3217 }

avSessMgrMMTC20047 NOTIFICATION-TYPE
	STATUS current
	DESCRIPTION
	"Session Manager using default authentication file(Warning)"
	::= { avAuraSessMgrMibNotifications 3219 }

avSessMgrMMTC20048 NOTIFICATION-TYPE
	STATUS current
	DESCRIPTION
	"Certificates nearing expiration date(Warning)"
	::= { avAuraSessMgrMibNotifications 3221 }

avSessMgrMMTC20049 NOTIFICATION-TYPE
	STATUS current
	DESCRIPTION
	"Certificates nearing expiration date(Major)"
	::= { avAuraSessMgrMibNotifications 3223 }

avSessMgrMMTC20050 NOTIFICATION-TYPE
	STATUS current
	DESCRIPTION
	"Certificates nearing expiration date(Critical)"
	::= { avAuraSessMgrMibNotifications 3225 }

avSessMgrMAMA20100 NOTIFICATION-TYPE
	STATUS current
	DESCRIPTION
	"Security Module Management Agent is unable to connect to SIP A/S Management Server(Minor)"
	::= { avAuraSessMgrMibNotifications 331 }

avSessMgrMAMA20102 NOTIFICATION-TYPE
	STATUS current
	DESCRIPTION
	"Security Module Management Agent is not able to configure Security Module(Major)"
	::= { avAuraSessMgrMibNotifications 333 }

avSessMgrMWD20202 NOTIFICATION-TYPE
	STATUS current
	DESCRIPTION
	"Service monitored by Watchdog has totally failed.(Minor)"
	::= { avAuraSessMgrMibNotifications 341 }

avSessMgrCSVH58003 NOTIFICATION-TYPE
	STATUS current
	DESCRIPTION
	"Product version not found. Certain operations may not work properly.(Minor)"
	::= { avAuraSessMgrMibNotifications 3101 }

avSessMgrCSVH58005 NOTIFICATION-TYPE
	STATUS current
	DESCRIPTION
	"Product version has invalid format. Certain operations may not work properly.(Minor)"
	::= { avAuraSessMgrMibNotifications 3103 }

avSessMgrCSVH58007 NOTIFICATION-TYPE
	STATUS current
	DESCRIPTION
	"Product type not found. System will likely exhibit widespread failures.(Major)"
	::= { avAuraSessMgrMibNotifications 3105 }

avSessMgrCSVH58009 NOTIFICATION-TYPE
	STATUS current
	DESCRIPTION
	"Product type not found. System will likely exhibit widespread failures.(Major)"
	::= { avAuraSessMgrMibNotifications 3107 }

avSessMgrCDAO50001 NOTIFICATION-TYPE
	STATUS current
	DESCRIPTION
	"The database connection is down.  Administration updates will not function during this outage.(Minor)"
	::= { avAuraSessMgrMibNotifications 351 }

avSessMgrCDAO50002 NOTIFICATION-TYPE
	STATUS current
	DESCRIPTION
	"Administration relating to the certain screen(s) may have caused a database query failure (SQL Exception).(Minor)"
	::= { avAuraSessMgrMibNotifications 353 }

avSessMgrCDAO50003 NOTIFICATION-TYPE
	STATUS current
	DESCRIPTION
	"Administration relating to the certain screen(s) may have recently created an entry in the database which will not be actualized in the runtime system due to an error with imposed restrictions.(Minor)"
	::= { avAuraSessMgrMibNotifications 355 }

avSessMgrCDAO50009 NOTIFICATION-TYPE
	STATUS current
	DESCRIPTION
	"A file I/O error occurred trying to write the local DNS server configuration or zone files.(Minor)"
	::= { avAuraSessMgrMibNotifications 357 }

avSessMgrCDAO50011 NOTIFICATION-TYPE
	STATUS current
	DESCRIPTION
	"The Session Manager Instance cannot be resolved.(Critical)"
	::= { avAuraSessMgrMibNotifications 359 }

avSessMgrCDAO50012 NOTIFICATION-TYPE
	STATUS current
	DESCRIPTION
	"Multiple Session Manager IP addresses map to the local Session Manager Instance. Double check administration screen(s), or real DNS such as /etc/hosts.(Minor)"
	::= { avAuraSessMgrMibNotifications 3511 }

avSessMgrCDAO50013 NOTIFICATION-TYPE
	STATUS current
	DESCRIPTION
	"DNS resolved to multiple IP addresses for Security Module.(Minor)"
	::= { avAuraSessMgrMibNotifications 3513 }

avSessMgrCDAO50018 NOTIFICATION-TYPE
	STATUS current
	DESCRIPTION
	"JGroups Keystore has not been replicated(Major)"
	::= { avAuraSessMgrMibNotifications 3514 }

avSessMgrCDAO50020 NOTIFICATION-TYPE
	STATUS current
	DESCRIPTION
	"There is a problem with the Call Detail Recording (CDR) system. Call accounting is not operational.(Minor)"
	::= { avAuraSessMgrMibNotifications 3515 }

avSessMgrCDAO50024 NOTIFICATION-TYPE
	STATUS current
	DESCRIPTION
	"BSM Entity Links to core subtended CM not administered.(Major)"
	::= { avAuraSessMgrMibNotifications 3517 }

avSessMgrCDAO50026 NOTIFICATION-TYPE
	STATUS current
	DESCRIPTION
	"The BSM cannot find the avaya-lsp entry in /etc/hosts.(Major)"
	::= { avAuraSessMgrMibNotifications 3519 }

avSessMgrCDAO50022 NOTIFICATION-TYPE
	STATUS current
	DESCRIPTION
	"Entity Link Missing for Route Through.(Warning)"
	::= { avAuraSessMgrMibNotifications 3521 }

avSessMgrCSRE52005 NOTIFICATION-TYPE
	STATUS current
	DESCRIPTION
	"ELIN Entity Link Missing(Minor)"
	::= { avAuraSessMgrMibNotifications 363 }

avSessMgrCMON55001 NOTIFICATION-TYPE
	STATUS current
	DESCRIPTION
	"SIP monitoring state for entity is PARTIALLY UP.(Warning)"
	::= { avAuraSessMgrMibNotifications 371 }

avSessMgrCMON55002 NOTIFICATION-TYPE
	STATUS current
	DESCRIPTION
	"SIP monitoring state for entity is DOWN.(Minor)"
	::= { avAuraSessMgrMibNotifications 373 }

avSessMgrCURE56023 NOTIFICATION-TYPE
	STATUS current
	DESCRIPTION
	"Sequencing application unreachable.(Minor)"
	::= { avAuraSessMgrMibNotifications 377 }

avSessMgrCURE56021 NOTIFICATION-TYPE
	STATUS current
	DESCRIPTION
	"Unable to store subscription for a given user.(Warning)"
	::= { avAuraSessMgrMibNotifications 379 }

avSessMgrCURE56027 NOTIFICATION-TYPE
	STATUS current
	DESCRIPTION
	"Session Manager detected that one or more users has been failed over to a non-primary Session Manager while under the manual failback policy.(Minor)"
	::= { avAuraSessMgrMibNotifications 381 }

avSessMgrCURE56029 NOTIFICATION-TYPE
	STATUS current
	DESCRIPTION
	"1 or more branch users have failed over to Branch Survivability Server.(Minor)"
	::= { avAuraSessMgrMibNotifications 383 }

avSessMgrCURE56010 NOTIFICATION-TYPE
	STATUS current
	DESCRIPTION
	"Unable to process registration for non-local user.(Warning)"
	::= { avAuraSessMgrMibNotifications 385 }

avSessMgrCURE56018 NOTIFICATION-TYPE
	STATUS current
	DESCRIPTION
	"Unable to process user subscription due to invalid credentials.(Warning)"
	::= { avAuraSessMgrMibNotifications 387 }

avSessMgrCURE56001 NOTIFICATION-TYPE
	STATUS current
	DESCRIPTION
	"Unable to process user registration due to invalid credentials.(Warning)"
	::= { avAuraSessMgrMibNotifications 389 }

avSessMgrCCAC54003 NOTIFICATION-TYPE
	STATUS current
	DESCRIPTION
	"The used bandwidth threshold for location has been exceeded(Minor)"
	::= { avAuraSessMgrMibNotifications 391 }

avSessMgrPCFF40000 NOTIFICATION-TYPE
	STATUS current
	DESCRIPTION
	"Missing configuration file.(Major)"
	::= { avAuraSessMgrMibNotifications 3201 }

avSessMgrPCFF40002 NOTIFICATION-TYPE
	STATUS current
	DESCRIPTION
	"SMGR connection timeout(Minor)"
	::= { avAuraSessMgrMibNotifications 3203 }

avSessMgrDRSDBG0001 NOTIFICATION-TYPE
	STATUS current
	DESCRIPTION
	"DRS client batch error(Major)"
	::= { avAuraSessMgrMibNotifications 3301 }

avSessMgrArbiter001 NOTIFICATION-TYPE
	STATUS current
	DESCRIPTION
	"SM switched to a different SMGR(Warning)"
	::= { avAuraSessMgrMibNotifications 3401 }

avSessMgrArbiter002 NOTIFICATION-TYPE
	STATUS current
	DESCRIPTION
	"Session Manager does not have a master Session Manager(Warning)"
	::= { avAuraSessMgrMibNotifications 3403 }

avSessMgrArbiter003 NOTIFICATION-TYPE
	STATUS current
	DESCRIPTION
	"GEO Session Managers in Active/Standby mode(Warning)"
	::= { avAuraSessMgrMibNotifications 3405 }

-------------------NOTIFICATION OBJECTS*******************************************END
END
