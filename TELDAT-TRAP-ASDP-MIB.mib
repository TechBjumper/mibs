-- file automatically created


TELDAT-TRAP-ASDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


asdpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ASDP event subsystem."
    REVISION "201401200930Z"
    DESCRIPTION "Initial implementation"
        ::= { telEventTraps 145 }


asdpEventsGroup	OBJECT IDENTIFIER	::= { asdpTrapsMIB 1 }

asdpNotifications	OBJECT IDENTIFIER	::= { asdpTrapsMIB 2 }
asdpNotificationsPrefix	OBJECT IDENTIFIER	::= { asdpNotifications 0 }

asdpEventObjects1 OBJECT-IDENTITY
    STATUS current
    DESCRIPTION
        "Event ASDP.1
        Data has been received from TCP."
    ::= { asdpEventsGroup 1 }

asdp1-size OBJECT-TYPE
    SYNTAX Integer32
    MAX-ACCESS accessible-for-notify
    STATUS current
    DESCRIPTION
        "Parameter 'size' in event ASDP.1"
    ::= { asdpEventObjects1 1 }

asdp1-State OBJECT-TYPE
    SYNTAX Integer32
    MAX-ACCESS accessible-for-notify
    STATUS current
    DESCRIPTION
        "Parameter 'State' in event ASDP.1"
    ::= { asdpEventObjects1 2 }

asdp1-Interface OBJECT-TYPE
    SYNTAX DisplayString
    MAX-ACCESS accessible-for-notify
    STATUS current
    DESCRIPTION
        "Parameter 'Interface' in event ASDP.1"
    ::= { asdpEventObjects1 3 }

asdpEventObjects2 OBJECT-IDENTITY
    STATUS current
    DESCRIPTION
        "Event ASDP.2
        Data has been sent to TCP."
    ::= { asdpEventsGroup 2 }

asdp2-size OBJECT-TYPE
    SYNTAX Integer32
    MAX-ACCESS accessible-for-notify
    STATUS current
    DESCRIPTION
        "Parameter 'size' in event ASDP.2"
    ::= { asdpEventObjects2 1 }

asdp2-State OBJECT-TYPE
    SYNTAX Integer32
    MAX-ACCESS accessible-for-notify
    STATUS current
    DESCRIPTION
        "Parameter 'State' in event ASDP.2"
    ::= { asdpEventObjects2 2 }

asdp2-Interface OBJECT-TYPE
    SYNTAX DisplayString
    MAX-ACCESS accessible-for-notify
    STATUS current
    DESCRIPTION
        "Parameter 'Interface' in event ASDP.2"
    ::= { asdpEventObjects2 3 }

asdpEventObjects3 OBJECT-IDENTITY
    STATUS current
    DESCRIPTION
        "Event ASDP.3
        Data has been sent from ASDP interface handler through serial line."
    ::= { asdpEventsGroup 3 }

asdp3-size OBJECT-TYPE
    SYNTAX Integer32
    MAX-ACCESS accessible-for-notify
    STATUS current
    DESCRIPTION
        "Parameter 'size' in event ASDP.3"
    ::= { asdpEventObjects3 1 }

asdp3-State OBJECT-TYPE
    SYNTAX Integer32
    MAX-ACCESS accessible-for-notify
    STATUS current
    DESCRIPTION
        "Parameter 'State' in event ASDP.3"
    ::= { asdpEventObjects3 2 }

asdp3-Interface OBJECT-TYPE
    SYNTAX DisplayString
    MAX-ACCESS accessible-for-notify
    STATUS current
    DESCRIPTION
        "Parameter 'Interface' in event ASDP.3"
    ::= { asdpEventObjects3 3 }

asdpEventObjects4 OBJECT-IDENTITY
    STATUS current
    DESCRIPTION
        "Event ASDP.4
        Data has been received from serial line."
    ::= { asdpEventsGroup 4 }

asdp4-size OBJECT-TYPE
    SYNTAX Integer32
    MAX-ACCESS accessible-for-notify
    STATUS current
    DESCRIPTION
        "Parameter 'size' in event ASDP.4"
    ::= { asdpEventObjects4 1 }

asdp4-State OBJECT-TYPE
    SYNTAX Integer32
    MAX-ACCESS accessible-for-notify
    STATUS current
    DESCRIPTION
        "Parameter 'State' in event ASDP.4"
    ::= { asdpEventObjects4 2 }

asdp4-Interface OBJECT-TYPE
    SYNTAX DisplayString
    MAX-ACCESS accessible-for-notify
    STATUS current
    DESCRIPTION
        "Parameter 'Interface' in event ASDP.4"
    ::= { asdpEventObjects4 3 }

asdpEventObjects5 OBJECT-IDENTITY
    STATUS current
    DESCRIPTION
        "Event ASDP.5
        TCP input session has been established."
    ::= { asdpEventsGroup 5 }

asdp5-rem-ip OBJECT-TYPE
    SYNTAX IpAddress
    MAX-ACCESS accessible-for-notify
    STATUS current
    DESCRIPTION
        "Parameter 'rem-ip' in event ASDP.5"
    ::= { asdpEventObjects5 1 }

asdp5-rem-port OBJECT-TYPE
    SYNTAX Integer32
    MAX-ACCESS accessible-for-notify
    STATUS current
    DESCRIPTION
        "Parameter 'rem-port' in event ASDP.5"
    ::= { asdpEventObjects5 2 }

asdp5-State OBJECT-TYPE
    SYNTAX Integer32
    MAX-ACCESS accessible-for-notify
    STATUS current
    DESCRIPTION
        "Parameter 'State' in event ASDP.5"
    ::= { asdpEventObjects5 3 }

asdp5-Interface OBJECT-TYPE
    SYNTAX DisplayString
    MAX-ACCESS accessible-for-notify
    STATUS current
    DESCRIPTION
        "Parameter 'Interface' in event ASDP.5"
    ::= { asdpEventObjects5 4 }

asdpEventObjects6 OBJECT-IDENTITY
    STATUS current
    DESCRIPTION
        "Event ASDP.6
        TCP output session has been established."
    ::= { asdpEventsGroup 6 }

asdp6-State OBJECT-TYPE
    SYNTAX Integer32
    MAX-ACCESS accessible-for-notify
    STATUS current
    DESCRIPTION
        "Parameter 'State' in event ASDP.6"
    ::= { asdpEventObjects6 1 }

asdp6-Interface OBJECT-TYPE
    SYNTAX DisplayString
    MAX-ACCESS accessible-for-notify
    STATUS current
    DESCRIPTION
        "Parameter 'Interface' in event ASDP.6"
    ::= { asdpEventObjects6 2 }

asdpEventObjects7 OBJECT-IDENTITY
    STATUS current
    DESCRIPTION
        "Event ASDP.7
        TCP output session has been established."
    ::= { asdpEventsGroup 7 }

asdp7-State OBJECT-TYPE
    SYNTAX Integer32
    MAX-ACCESS accessible-for-notify
    STATUS current
    DESCRIPTION
        "Parameter 'State' in event ASDP.7"
    ::= { asdpEventObjects7 1 }

asdp7-Interface OBJECT-TYPE
    SYNTAX DisplayString
    MAX-ACCESS accessible-for-notify
    STATUS current
    DESCRIPTION
        "Parameter 'Interface' in event ASDP.7"
    ::= { asdpEventObjects7 2 }

asdpEventObjects8 OBJECT-IDENTITY
    STATUS current
    DESCRIPTION
        "Event ASDP.8
        Timer expired."
    ::= { asdpEventsGroup 8 }

asdp8-timer OBJECT-TYPE
    SYNTAX DisplayString
    MAX-ACCESS accessible-for-notify
    STATUS current
    DESCRIPTION
        "Parameter 'timer' in event ASDP.8"
    ::= { asdpEventObjects8 1 }

asdp8-State OBJECT-TYPE
    SYNTAX Integer32
    MAX-ACCESS accessible-for-notify
    STATUS current
    DESCRIPTION
        "Parameter 'State' in event ASDP.8"
    ::= { asdpEventObjects8 2 }

asdp8-Interface OBJECT-TYPE
    SYNTAX DisplayString
    MAX-ACCESS accessible-for-notify
    STATUS current
    DESCRIPTION
        "Parameter 'Interface' in event ASDP.8"
    ::= { asdpEventObjects8 3 }

asdpEventObjects9 OBJECT-IDENTITY
    STATUS current
    DESCRIPTION
        "Event ASDP.9
        Timer expired."
    ::= { asdpEventsGroup 9 }

asdp9-timer OBJECT-TYPE
    SYNTAX Integer32
    MAX-ACCESS accessible-for-notify
    STATUS current
    DESCRIPTION
        "Parameter 'timer' in event ASDP.9"
    ::= { asdpEventObjects9 1 }

asdp9-State OBJECT-TYPE
    SYNTAX Integer32
    MAX-ACCESS accessible-for-notify
    STATUS current
    DESCRIPTION
        "Parameter 'State' in event ASDP.9"
    ::= { asdpEventObjects9 2 }

asdp9-Interface OBJECT-TYPE
    SYNTAX DisplayString
    MAX-ACCESS accessible-for-notify
    STATUS current
    DESCRIPTION
        "Parameter 'Interface' in event ASDP.9"
    ::= { asdpEventObjects9 3 }

asdpEventObjects10 OBJECT-IDENTITY
    STATUS current
    DESCRIPTION
        "Event ASDP.10
        A TCP output session attempt has been made."
    ::= { asdpEventsGroup 10 }

asdp10-rem-ip OBJECT-TYPE
    SYNTAX IpAddress
    MAX-ACCESS accessible-for-notify
    STATUS current
    DESCRIPTION
        "Parameter 'rem-ip' in event ASDP.10"
    ::= { asdpEventObjects10 1 }

asdp10-rem-port OBJECT-TYPE
    SYNTAX Integer32
    MAX-ACCESS accessible-for-notify
    STATUS current
    DESCRIPTION
        "Parameter 'rem-port' in event ASDP.10"
    ::= { asdpEventObjects10 2 }

asdp10-State OBJECT-TYPE
    SYNTAX Integer32
    MAX-ACCESS accessible-for-notify
    STATUS current
    DESCRIPTION
        "Parameter 'State' in event ASDP.10"
    ::= { asdpEventObjects10 3 }

asdp10-Interface OBJECT-TYPE
    SYNTAX DisplayString
    MAX-ACCESS accessible-for-notify
    STATUS current
    DESCRIPTION
        "Parameter 'Interface' in event ASDP.10"
    ::= { asdpEventObjects10 4 }

asdpEventObjects11 OBJECT-IDENTITY
    STATUS current
    DESCRIPTION
        "Event ASDP.11
        Serial Line control state change."
    ::= { asdpEventsGroup 11 }

asdp11-Sig-state OBJECT-TYPE
    SYNTAX DisplayString
    MAX-ACCESS accessible-for-notify
    STATUS current
    DESCRIPTION
        "Parameter 'Sig-state' in event ASDP.11"
    ::= { asdpEventObjects11 1 }

asdp11-State OBJECT-TYPE
    SYNTAX Integer32
    MAX-ACCESS accessible-for-notify
    STATUS current
    DESCRIPTION
        "Parameter 'State' in event ASDP.11"
    ::= { asdpEventObjects11 2 }

asdp11-Interface OBJECT-TYPE
    SYNTAX DisplayString
    MAX-ACCESS accessible-for-notify
    STATUS current
    DESCRIPTION
        "Parameter 'Interface' in event ASDP.11"
    ::= { asdpEventObjects11 3 }

asdpEventObjects12 OBJECT-IDENTITY
    STATUS current
    DESCRIPTION
        "Event ASDP.12
        A TCP output session attempt has failed."
    ::= { asdpEventsGroup 12 }

asdp12-rem-ip OBJECT-TYPE
    SYNTAX IpAddress
    MAX-ACCESS accessible-for-notify
    STATUS current
    DESCRIPTION
        "Parameter 'rem-ip' in event ASDP.12"
    ::= { asdpEventObjects12 1 }

asdp12-rem-port OBJECT-TYPE
    SYNTAX Integer32
    MAX-ACCESS accessible-for-notify
    STATUS current
    DESCRIPTION
        "Parameter 'rem-port' in event ASDP.12"
    ::= { asdpEventObjects12 2 }

asdp12-State OBJECT-TYPE
    SYNTAX Integer32
    MAX-ACCESS accessible-for-notify
    STATUS current
    DESCRIPTION
        "Parameter 'State' in event ASDP.12"
    ::= { asdpEventObjects12 3 }

asdp12-Interface OBJECT-TYPE
    SYNTAX DisplayString
    MAX-ACCESS accessible-for-notify
    STATUS current
    DESCRIPTION
        "Parameter 'Interface' in event ASDP.12"
    ::= { asdpEventObjects12 4 }

asdpEventObjects13 OBJECT-IDENTITY
    STATUS current
    DESCRIPTION
        "Event ASDP.13
        An AT command has been received."
    ::= { asdpEventsGroup 13 }

asdp13-cmd OBJECT-TYPE
    SYNTAX DisplayString
    MAX-ACCESS accessible-for-notify
    STATUS current
    DESCRIPTION
        "Parameter 'cmd' in event ASDP.13"
    ::= { asdpEventObjects13 1 }

asdp13-Interface OBJECT-TYPE
    SYNTAX DisplayString
    MAX-ACCESS accessible-for-notify
    STATUS current
    DESCRIPTION
        "Parameter 'Interface' in event ASDP.13"
    ::= { asdpEventObjects13 2 }

asdpEventObjects14 OBJECT-IDENTITY
    STATUS current
    DESCRIPTION
        "Event ASDP.14
        An AT command is transmiting."
    ::= { asdpEventsGroup 14 }

asdp14-cmd OBJECT-TYPE
    SYNTAX DisplayString
    MAX-ACCESS accessible-for-notify
    STATUS current
    DESCRIPTION
        "Parameter 'cmd' in event ASDP.14"
    ::= { asdpEventObjects14 1 }

asdp14-Interface OBJECT-TYPE
    SYNTAX DisplayString
    MAX-ACCESS accessible-for-notify
    STATUS current
    DESCRIPTION
        "Parameter 'Interface' in event ASDP.14"
    ::= { asdpEventObjects14 2 }

asdpEventObjects15 OBJECT-IDENTITY
    STATUS current
    DESCRIPTION
        "Event ASDP.15
        Data has been received from TCP."
    ::= { asdpEventsGroup 15 }

asdp15-Peer OBJECT-TYPE
    SYNTAX Integer32
    MAX-ACCESS accessible-for-notify
    STATUS current
    DESCRIPTION
        "Parameter 'Peer' in event ASDP.15"
    ::= { asdpEventObjects15 1 }

asdp15-size OBJECT-TYPE
    SYNTAX Integer32
    MAX-ACCESS accessible-for-notify
    STATUS current
    DESCRIPTION
        "Parameter 'size' in event ASDP.15"
    ::= { asdpEventObjects15 2 }

asdp15-State OBJECT-TYPE
    SYNTAX Integer32
    MAX-ACCESS accessible-for-notify
    STATUS current
    DESCRIPTION
        "Parameter 'State' in event ASDP.15"
    ::= { asdpEventObjects15 3 }

asdp15-Interface OBJECT-TYPE
    SYNTAX DisplayString
    MAX-ACCESS accessible-for-notify
    STATUS current
    DESCRIPTION
        "Parameter 'Interface' in event ASDP.15"
    ::= { asdpEventObjects15 4 }

asdpEventObjects16 OBJECT-IDENTITY
    STATUS current
    DESCRIPTION
        "Event ASDP.16
        Data has been sent to TCP."
    ::= { asdpEventsGroup 16 }

asdp16-Peer OBJECT-TYPE
    SYNTAX Integer32
    MAX-ACCESS accessible-for-notify
    STATUS current
    DESCRIPTION
        "Parameter 'Peer' in event ASDP.16"
    ::= { asdpEventObjects16 1 }

asdp16-size OBJECT-TYPE
    SYNTAX Integer32
    MAX-ACCESS accessible-for-notify
    STATUS current
    DESCRIPTION
        "Parameter 'size' in event ASDP.16"
    ::= { asdpEventObjects16 2 }

asdp16-State OBJECT-TYPE
    SYNTAX Integer32
    MAX-ACCESS accessible-for-notify
    STATUS current
    DESCRIPTION
        "Parameter 'State' in event ASDP.16"
    ::= { asdpEventObjects16 3 }

asdp16-Interface OBJECT-TYPE
    SYNTAX DisplayString
    MAX-ACCESS accessible-for-notify
    STATUS current
    DESCRIPTION
        "Parameter 'Interface' in event ASDP.16"
    ::= { asdpEventObjects16 4 }

asdpEventObjects17 OBJECT-IDENTITY
    STATUS current
    DESCRIPTION
        "Event ASDP.17
        TCP output session has been established."
    ::= { asdpEventsGroup 17 }

asdp17-Peer OBJECT-TYPE
    SYNTAX Integer32
    MAX-ACCESS accessible-for-notify
    STATUS current
    DESCRIPTION
        "Parameter 'Peer' in event ASDP.17"
    ::= { asdpEventObjects17 1 }

asdp17-State OBJECT-TYPE
    SYNTAX Integer32
    MAX-ACCESS accessible-for-notify
    STATUS current
    DESCRIPTION
        "Parameter 'State' in event ASDP.17"
    ::= { asdpEventObjects17 2 }

asdp17-Interface OBJECT-TYPE
    SYNTAX DisplayString
    MAX-ACCESS accessible-for-notify
    STATUS current
    DESCRIPTION
        "Parameter 'Interface' in event ASDP.17"
    ::= { asdpEventObjects17 3 }

asdpEventObjects18 OBJECT-IDENTITY
    STATUS current
    DESCRIPTION
        "Event ASDP.18
        TCP output session has been established."
    ::= { asdpEventsGroup 18 }

asdp18-Peer OBJECT-TYPE
    SYNTAX Integer32
    MAX-ACCESS accessible-for-notify
    STATUS current
    DESCRIPTION
        "Parameter 'Peer' in event ASDP.18"
    ::= { asdpEventObjects18 1 }

asdp18-State OBJECT-TYPE
    SYNTAX Integer32
    MAX-ACCESS accessible-for-notify
    STATUS current
    DESCRIPTION
        "Parameter 'State' in event ASDP.18"
    ::= { asdpEventObjects18 2 }

asdp18-Interface OBJECT-TYPE
    SYNTAX DisplayString
    MAX-ACCESS accessible-for-notify
    STATUS current
    DESCRIPTION
        "Parameter 'Interface' in event ASDP.18"
    ::= { asdpEventObjects18 3 }

asdpEventObjects19 OBJECT-IDENTITY
    STATUS current
    DESCRIPTION
        "Event ASDP.19
        Timer expired."
    ::= { asdpEventsGroup 19 }

asdp19-Peer OBJECT-TYPE
    SYNTAX Integer32
    MAX-ACCESS accessible-for-notify
    STATUS current
    DESCRIPTION
        "Parameter 'Peer' in event ASDP.19"
    ::= { asdpEventObjects19 1 }

asdp19-timer OBJECT-TYPE
    SYNTAX Integer32
    MAX-ACCESS accessible-for-notify
    STATUS current
    DESCRIPTION
        "Parameter 'timer' in event ASDP.19"
    ::= { asdpEventObjects19 2 }

asdp19-State OBJECT-TYPE
    SYNTAX Integer32
    MAX-ACCESS accessible-for-notify
    STATUS current
    DESCRIPTION
        "Parameter 'State' in event ASDP.19"
    ::= { asdpEventObjects19 3 }

asdp19-Interface OBJECT-TYPE
    SYNTAX DisplayString
    MAX-ACCESS accessible-for-notify
    STATUS current
    DESCRIPTION
        "Parameter 'Interface' in event ASDP.19"
    ::= { asdpEventObjects19 4 }

asdpEventObjects20 OBJECT-IDENTITY
    STATUS current
    DESCRIPTION
        "Event ASDP.20
        Can't open UDP port to Rx DATA."
    ::= { asdpEventsGroup 20 }

asdp20-Peer OBJECT-TYPE
    SYNTAX Integer32
    MAX-ACCESS accessible-for-notify
    STATUS current
    DESCRIPTION
        "Parameter 'Peer' in event ASDP.20"
    ::= { asdpEventObjects20 1 }

asdp20-State OBJECT-TYPE
    SYNTAX Integer32
    MAX-ACCESS accessible-for-notify
    STATUS current
    DESCRIPTION
        "Parameter 'State' in event ASDP.20"
    ::= { asdpEventObjects20 2 }

asdp20-Interface OBJECT-TYPE
    SYNTAX DisplayString
    MAX-ACCESS accessible-for-notify
    STATUS current
    DESCRIPTION
        "Parameter 'Interface' in event ASDP.20"
    ::= { asdpEventObjects20 3 }

asdpEventObjects21 OBJECT-IDENTITY
    STATUS current
    DESCRIPTION
        "Event ASDP.21
        UDP port is open to Rx DATA."
    ::= { asdpEventsGroup 21 }

asdp21-Peer OBJECT-TYPE
    SYNTAX Integer32
    MAX-ACCESS accessible-for-notify
    STATUS current
    DESCRIPTION
        "Parameter 'Peer' in event ASDP.21"
    ::= { asdpEventObjects21 1 }

asdp21-Port OBJECT-TYPE
    SYNTAX Integer32
    MAX-ACCESS accessible-for-notify
    STATUS current
    DESCRIPTION
        "Parameter 'Port' in event ASDP.21"
    ::= { asdpEventObjects21 2 }

asdp21-State OBJECT-TYPE
    SYNTAX Integer32
    MAX-ACCESS accessible-for-notify
    STATUS current
    DESCRIPTION
        "Parameter 'State' in event ASDP.21"
    ::= { asdpEventObjects21 3 }

asdp21-Interface OBJECT-TYPE
    SYNTAX DisplayString
    MAX-ACCESS accessible-for-notify
    STATUS current
    DESCRIPTION
        "Parameter 'Interface' in event ASDP.21"
    ::= { asdpEventObjects21 4 }

asdpEventObjects22 OBJECT-IDENTITY
    STATUS current
    DESCRIPTION
        "Event ASDP.22
        Data has been received from UDP."
    ::= { asdpEventsGroup 22 }

asdp22-Peer OBJECT-TYPE
    SYNTAX Integer32
    MAX-ACCESS accessible-for-notify
    STATUS current
    DESCRIPTION
        "Parameter 'Peer' in event ASDP.22"
    ::= { asdpEventObjects22 1 }

asdp22-size OBJECT-TYPE
    SYNTAX Integer32
    MAX-ACCESS accessible-for-notify
    STATUS current
    DESCRIPTION
        "Parameter 'size' in event ASDP.22"
    ::= { asdpEventObjects22 2 }

asdp22-State OBJECT-TYPE
    SYNTAX Integer32
    MAX-ACCESS accessible-for-notify
    STATUS current
    DESCRIPTION
        "Parameter 'State' in event ASDP.22"
    ::= { asdpEventObjects22 3 }

asdp22-Interface OBJECT-TYPE
    SYNTAX DisplayString
    MAX-ACCESS accessible-for-notify
    STATUS current
    DESCRIPTION
        "Parameter 'Interface' in event ASDP.22"
    ::= { asdpEventObjects22 4 }

asdpEventObjects23 OBJECT-IDENTITY
    STATUS current
    DESCRIPTION
        "Event ASDP.23
        Data has been sent to UDP."
    ::= { asdpEventsGroup 23 }

asdp23-Peer OBJECT-TYPE
    SYNTAX Integer32
    MAX-ACCESS accessible-for-notify
    STATUS current
    DESCRIPTION
        "Parameter 'Peer' in event ASDP.23"
    ::= { asdpEventObjects23 1 }

asdp23-size OBJECT-TYPE
    SYNTAX Integer32
    MAX-ACCESS accessible-for-notify
    STATUS current
    DESCRIPTION
        "Parameter 'size' in event ASDP.23"
    ::= { asdpEventObjects23 2 }

asdp23-State OBJECT-TYPE
    SYNTAX Integer32
    MAX-ACCESS accessible-for-notify
    STATUS current
    DESCRIPTION
        "Parameter 'State' in event ASDP.23"
    ::= { asdpEventObjects23 3 }

asdp23-Interface OBJECT-TYPE
    SYNTAX DisplayString
    MAX-ACCESS accessible-for-notify
    STATUS current
    DESCRIPTION
        "Parameter 'Interface' in event ASDP.23"
    ::= { asdpEventObjects23 4 }

asdpEventObjects24 OBJECT-IDENTITY
    STATUS current
    DESCRIPTION
        "Event ASDP.24
        Overrun occurs sending data to UDP."
    ::= { asdpEventsGroup 24 }

asdp24-Peer OBJECT-TYPE
    SYNTAX Integer32
    MAX-ACCESS accessible-for-notify
    STATUS current
    DESCRIPTION
        "Parameter 'Peer' in event ASDP.24"
    ::= { asdpEventObjects24 1 }

asdp24-timer OBJECT-TYPE
    SYNTAX Integer32
    MAX-ACCESS accessible-for-notify
    STATUS current
    DESCRIPTION
        "Parameter 'timer' in event ASDP.24"
    ::= { asdpEventObjects24 2 }

asdp24-State OBJECT-TYPE
    SYNTAX Integer32
    MAX-ACCESS accessible-for-notify
    STATUS current
    DESCRIPTION
        "Parameter 'State' in event ASDP.24"
    ::= { asdpEventObjects24 3 }

asdp24-Interface OBJECT-TYPE
    SYNTAX DisplayString
    MAX-ACCESS accessible-for-notify
    STATUS current
    DESCRIPTION
        "Parameter 'Interface' in event ASDP.24"
    ::= { asdpEventObjects24 4 }

asdpEventObjects25 OBJECT-IDENTITY
    STATUS current
    DESCRIPTION
        "Event ASDP.25
        UDP port for recive data has been closed."
    ::= { asdpEventsGroup 25 }

asdp25-Peer OBJECT-TYPE
    SYNTAX Integer32
    MAX-ACCESS accessible-for-notify
    STATUS current
    DESCRIPTION
        "Parameter 'Peer' in event ASDP.25"
    ::= { asdpEventObjects25 1 }

asdp25-State OBJECT-TYPE
    SYNTAX Integer32
    MAX-ACCESS accessible-for-notify
    STATUS current
    DESCRIPTION
        "Parameter 'State' in event ASDP.25"
    ::= { asdpEventObjects25 2 }

asdp25-Interface OBJECT-TYPE
    SYNTAX DisplayString
    MAX-ACCESS accessible-for-notify
    STATUS current
    DESCRIPTION
        "Parameter 'Interface' in event ASDP.25"
    ::= { asdpEventObjects25 3 }


asdpNotification1 NOTIFICATION-TYPE
    OBJECTS { 
              asdp1-size, 
              asdp1-State,
              asdp1-Interface 
            }
    STATUS current
    DESCRIPTION
        "Notification of Event ASDP.1

        Message: 'Data received from TCP. Size:$1, State:$2, Ifc:$3'

        Parameters list:
              $1: asdp1-size
              $2: asdp1-State
              $3: asdp1-Interface

        Data has been received from TCP."
    ::= { asdpNotificationsPrefix 1 }

asdpNotification2 NOTIFICATION-TYPE
    OBJECTS { 
              asdp2-size, 
              asdp2-State,
              asdp2-Interface 
            }
    STATUS current
    DESCRIPTION
        "Notification of Event ASDP.2

        Message: 'Data sent to TCP. Size:$1, State:$2, Ifc:$3'

        Parameters list:
              $1: asdp2-size
              $2: asdp2-State
              $3: asdp2-Interface

        Data has been sent to TCP."
    ::= { asdpNotificationsPrefix 2 }

asdpNotification3 NOTIFICATION-TYPE
    OBJECTS { 
              asdp3-size, 
              asdp3-State,
              asdp3-Interface 
            }
    STATUS current
    DESCRIPTION
        "Notification of Event ASDP.3

        Message: 'Data sent to serial line. Size:$1, State:$2, Ifc:$3'

        Parameters list:
              $1: asdp3-size
              $2: asdp3-State
              $3: asdp3-Interface

        Data has been sent from ASDP interface handler through serial line."
    ::= { asdpNotificationsPrefix 3 }

asdpNotification4 NOTIFICATION-TYPE
    OBJECTS { 
              asdp4-size, 
              asdp4-State,
              asdp4-Interface 
            }
    STATUS current
    DESCRIPTION
        "Notification of Event ASDP.4

        Message: 'Data received from serial line. Size:$1, State:$2, Ifc:$3'

        Parameters list:
              $1: asdp4-size
              $2: asdp4-State
              $3: asdp4-Interface

        Data has been received from serial line."
    ::= { asdpNotificationsPrefix 4 }

asdpNotification5 NOTIFICATION-TYPE
    OBJECTS { 
              asdp5-rem-ip, 
              asdp5-rem-port,
              asdp5-State,
              asdp5-Interface 
            }
    STATUS current
    DESCRIPTION
        "Notification of Event ASDP.5

        Message: 'TCP input session from remote IP addr:$1, port:$2, State:$3, Ifc:$4'

        Parameters list:
              $1: asdp5-rem-ip
              $2: asdp5-rem-port
              $3: asdp5-State
              $4: asdp5-Interface

        TCP input session has been established."
    ::= { asdpNotificationsPrefix 5 }

asdpNotification6 NOTIFICATION-TYPE
    OBJECTS { 
              asdp6-State, 
              asdp6-Interface 
            }
    STATUS current
    DESCRIPTION
        "Notification of Event ASDP.6

        Message: 'TCP output session stablished. State:$1, Ifc$2'

        Parameters list:
              $1: asdp6-State
              $2: asdp6-Interface

        TCP output session has been established."
    ::= { asdpNotificationsPrefix 6 }

asdpNotification7 NOTIFICATION-TYPE
    OBJECTS { 
              asdp7-State, 
              asdp7-Interface 
            }
    STATUS current
    DESCRIPTION
        "Notification of Event ASDP.7

        Message: 'TCP session closed. State:$1, Ifc:$2'

        Parameters list:
              $1: asdp7-State
              $2: asdp7-Interface

        TCP output session has been established."
    ::= { asdpNotificationsPrefix 7 }

asdpNotification8 NOTIFICATION-TYPE
    OBJECTS { 
              asdp8-timer, 
              asdp8-State,
              asdp8-Interface 
            }
    STATUS current
    DESCRIPTION
        "Notification of Event ASDP.8

        Message: '$1 timer expired State:$2, Ifc:$3'

        Parameters list:
              $1: asdp8-timer
              $2: asdp8-State
              $3: asdp8-Interface

        Timer expired."
    ::= { asdpNotificationsPrefix 8 }

asdpNotification9 NOTIFICATION-TYPE
    OBJECTS { 
              asdp9-timer, 
              asdp9-State,
              asdp9-Interface 
            }
    STATUS current
    DESCRIPTION
        "Notification of Event ASDP.9

        Message: 'Tx data overrun sending to TCP, Size:$1, State:$2, Ifc:$3'

        Parameters list:
              $1: asdp9-timer
              $2: asdp9-State
              $3: asdp9-Interface

        Timer expired."
    ::= { asdpNotificationsPrefix 9 }

asdpNotification10 NOTIFICATION-TYPE
    OBJECTS { 
              asdp10-rem-ip, 
              asdp10-rem-port,
              asdp10-State,
              asdp10-Interface 
            }
    STATUS current
    DESCRIPTION
        "Notification of Event ASDP.10

        Message: 'TCP output session attempt to IP addr:$1, port:$2, State:$3, Ifc$4'

        Parameters list:
              $1: asdp10-rem-ip
              $2: asdp10-rem-port
              $3: asdp10-State
              $4: asdp10-Interface

        A TCP output session attempt has been made."
    ::= { asdpNotificationsPrefix 10 }

asdpNotification11 NOTIFICATION-TYPE
    OBJECTS { 
              asdp11-Sig-state, 
              asdp11-State,
              asdp11-Interface 
            }
    STATUS current
    DESCRIPTION
        "Notification of Event ASDP.11

        Message: 'Serial Line signal control $1. State:$2, Ifc:$3'

        Parameters list:
              $1: asdp11-Sig-state
              $2: asdp11-State
              $3: asdp11-Interface

        Serial Line control state change."
    ::= { asdpNotificationsPrefix 11 }

asdpNotification12 NOTIFICATION-TYPE
    OBJECTS { 
              asdp12-rem-ip, 
              asdp12-rem-port,
              asdp12-State,
              asdp12-Interface 
            }
    STATUS current
    DESCRIPTION
        "Notification of Event ASDP.12

        Message: 'TCP output session attempt has failed IP addr:$1, port:$2, State:$3, Ifc$4'

        Parameters list:
              $1: asdp12-rem-ip
              $2: asdp12-rem-port
              $3: asdp12-State
              $4: asdp12-Interface

        A TCP output session attempt has failed."
    ::= { asdpNotificationsPrefix 12 }

asdpNotification13 NOTIFICATION-TYPE
    OBJECTS { 
              asdp13-cmd, 
              asdp13-Interface 
            }
    STATUS current
    DESCRIPTION
        "Notification of Event ASDP.13

        Message: 'An AT command has been received $1, Ifc$2'

        Parameters list:
              $1: asdp13-cmd
              $2: asdp13-Interface

        An AT command has been received."
    ::= { asdpNotificationsPrefix 13 }

asdpNotification14 NOTIFICATION-TYPE
    OBJECTS { 
              asdp14-cmd, 
              asdp14-Interface 
            }
    STATUS current
    DESCRIPTION
        "Notification of Event ASDP.14

        Message: 'An AT command is transmiting $1, Ifc$2'

        Parameters list:
              $1: asdp14-cmd
              $2: asdp14-Interface

        An AT command is transmiting."
    ::= { asdpNotificationsPrefix 14 }

asdpNotification15 NOTIFICATION-TYPE
    OBJECTS { 
              asdp15-Peer, 
              asdp15-size,
              asdp15-State,
              asdp15-Interface 
            }
    STATUS current
    DESCRIPTION
        "Notification of Event ASDP.15

        Message: 'Data received from TCP. Peer:$1 Size:$2, State:$3, Ifc:$4'

        Parameters list:
              $1: asdp15-Peer
              $2: asdp15-size
              $3: asdp15-State
              $4: asdp15-Interface

        Data has been received from TCP."
    ::= { asdpNotificationsPrefix 15 }

asdpNotification16 NOTIFICATION-TYPE
    OBJECTS { 
              asdp16-Peer, 
              asdp16-size,
              asdp16-State,
              asdp16-Interface 
            }
    STATUS current
    DESCRIPTION
        "Notification of Event ASDP.16

        Message: 'Data sent to TCP. Peer:$1 Size:$2, State:$3, Ifc:$4'

        Parameters list:
              $1: asdp16-Peer
              $2: asdp16-size
              $3: asdp16-State
              $4: asdp16-Interface

        Data has been sent to TCP."
    ::= { asdpNotificationsPrefix 16 }

asdpNotification17 NOTIFICATION-TYPE
    OBJECTS { 
              asdp17-Peer, 
              asdp17-State,
              asdp17-Interface 
            }
    STATUS current
    DESCRIPTION
        "Notification of Event ASDP.17

        Message: 'TCP output session stablished. Peer:$1 State:$2, Ifc$3'

        Parameters list:
              $1: asdp17-Peer
              $2: asdp17-State
              $3: asdp17-Interface

        TCP output session has been established."
    ::= { asdpNotificationsPrefix 17 }

asdpNotification18 NOTIFICATION-TYPE
    OBJECTS { 
              asdp18-Peer, 
              asdp18-State,
              asdp18-Interface 
            }
    STATUS current
    DESCRIPTION
        "Notification of Event ASDP.18

        Message: 'TCP session closed. Peer:$1 State:$2, Ifc:$3'

        Parameters list:
              $1: asdp18-Peer
              $2: asdp18-State
              $3: asdp18-Interface

        TCP output session has been established."
    ::= { asdpNotificationsPrefix 18 }

asdpNotification19 NOTIFICATION-TYPE
    OBJECTS { 
              asdp19-Peer, 
              asdp19-timer,
              asdp19-State,
              asdp19-Interface 
            }
    STATUS current
    DESCRIPTION
        "Notification of Event ASDP.19

        Message: 'Tx data overrun sending to TCP, Peer:$1 Size:$2, State:$3, Ifc:$4'

        Parameters list:
              $1: asdp19-Peer
              $2: asdp19-timer
              $3: asdp19-State
              $4: asdp19-Interface

        Timer expired."
    ::= { asdpNotificationsPrefix 19 }

asdpNotification20 NOTIFICATION-TYPE
    OBJECTS { 
              asdp20-Peer, 
              asdp20-State,
              asdp20-Interface 
            }
    STATUS current
    DESCRIPTION
        "Notification of Event ASDP.20

        Message: 'Can't open UDP port, Peer:$1, State:$2, Ifc:$3'

        Parameters list:
              $1: asdp20-Peer
              $2: asdp20-State
              $3: asdp20-Interface

        Can't open UDP port to Rx DATA."
    ::= { asdpNotificationsPrefix 20 }

asdpNotification21 NOTIFICATION-TYPE
    OBJECTS { 
              asdp21-Peer, 
              asdp21-Port,
              asdp21-State,
              asdp21-Interface 
            }
    STATUS current
    DESCRIPTION
        "Notification of Event ASDP.21

        Message: 'UDP port OPEN. Peer:$1 port:$2 State:$3, Ifc$4'

        Parameters list:
              $1: asdp21-Peer
              $2: asdp21-Port
              $3: asdp21-State
              $4: asdp21-Interface

        UDP port is open to Rx DATA."
    ::= { asdpNotificationsPrefix 21 }

asdpNotification22 NOTIFICATION-TYPE
    OBJECTS { 
              asdp22-Peer, 
              asdp22-size,
              asdp22-State,
              asdp22-Interface 
            }
    STATUS current
    DESCRIPTION
        "Notification of Event ASDP.22

        Message: 'Data received from UDP. Peer:$1 Size:$2, State:$3, Ifc:$4'

        Parameters list:
              $1: asdp22-Peer
              $2: asdp22-size
              $3: asdp22-State
              $4: asdp22-Interface

        Data has been received from UDP."
    ::= { asdpNotificationsPrefix 22 }

asdpNotification23 NOTIFICATION-TYPE
    OBJECTS { 
              asdp23-Peer, 
              asdp23-size,
              asdp23-State,
              asdp23-Interface 
            }
    STATUS current
    DESCRIPTION
        "Notification of Event ASDP.23

        Message: 'Data sent to UDP. Peer:$1 Size:$2, State:$3, Ifc:$4'

        Parameters list:
              $1: asdp23-Peer
              $2: asdp23-size
              $3: asdp23-State
              $4: asdp23-Interface

        Data has been sent to UDP."
    ::= { asdpNotificationsPrefix 23 }

asdpNotification24 NOTIFICATION-TYPE
    OBJECTS { 
              asdp24-Peer, 
              asdp24-timer,
              asdp24-State,
              asdp24-Interface 
            }
    STATUS current
    DESCRIPTION
        "Notification of Event ASDP.24

        Message: 'Tx data overrun sending to UDP, Peer:$1 Size:$2, State:$3, Ifc:$4'

        Parameters list:
              $1: asdp24-Peer
              $2: asdp24-timer
              $3: asdp24-State
              $4: asdp24-Interface

        Overrun occurs sending data to UDP."
    ::= { asdpNotificationsPrefix 24 }

asdpNotification25 NOTIFICATION-TYPE
    OBJECTS { 
              asdp25-Peer, 
              asdp25-State,
              asdp25-Interface 
            }
    STATUS current
    DESCRIPTION
        "Notification of Event ASDP.25

        Message: 'UDP port is closed. Peer:$1 State:$2, Ifc:$3'

        Parameters list:
              $1: asdp25-Peer
              $2: asdp25-State
              $3: asdp25-Interface

        UDP port for recive data has been closed."
    ::= { asdpNotificationsPrefix 25 }


END
