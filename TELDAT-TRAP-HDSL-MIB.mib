-- file automatically created


TELDAT-TRAP-HDSL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


hdslTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the HDSL event subsystem."
    REVISION "201401200930Z"
    DESCRIPTION "Initial implementation"
        ::= { telEventTraps 157 }


hdslEventsGroup	OBJECT IDENTIFIER	::= { hdslTrapsMIB 1 }

hdslNotifications	OBJECT IDENTIFIER	::= { hdslTrapsMIB 2 }
hdslNotificationsPrefix	OBJECT IDENTIFIER	::= { hdslNotifications 0 }

hdslEventObjects1 OBJECT-IDENTITY
    STATUS current
    DESCRIPTION
        "Event HDSL.1
        Notification of a line event: opening state, open failed and reason,
        opened, monitoring forces reneg, signal lost, orderly closed not granted,
        suicide request, closed..."
    ::= { hdslEventsGroup 1 }

hdsl1-MNEMONIC OBJECT-TYPE
    SYNTAX DisplayString
    MAX-ACCESS accessible-for-notify
    STATUS current
    DESCRIPTION
        "Parameter 'MNEMONIC' in event HDSL.1"
    ::= { hdslEventObjects1 1 }

hdsl1-LINE-INFORMATION OBJECT-TYPE
    SYNTAX DisplayString
    MAX-ACCESS accessible-for-notify
    STATUS current
    DESCRIPTION
        "Parameter 'LINE-INFORMATION' in event HDSL.1"
    ::= { hdslEventObjects1 2 }

hdslEventObjects2 OBJECT-IDENTITY
    STATUS current
    DESCRIPTION
        "Event HDSL.2
        State machine event (each chipset has a different state machine)."
    ::= { hdslEventsGroup 2 }

hdsl2-MNEMONIC OBJECT-TYPE
    SYNTAX DisplayString
    MAX-ACCESS accessible-for-notify
    STATUS current
    DESCRIPTION
        "Parameter 'MNEMONIC' in event HDSL.2"
    ::= { hdslEventObjects2 1 }

hdsl2-STATE-MACHINE-EVENT OBJECT-TYPE
    SYNTAX DisplayString
    MAX-ACCESS accessible-for-notify
    STATUS current
    DESCRIPTION
        "Parameter 'STATE-MACHINE-EVENT' in event HDSL.2"
    ::= { hdslEventObjects2 2 }

hdslEventObjects3 OBJECT-IDENTITY
    STATUS current
    DESCRIPTION
        "Event HDSL.3
        Chipset specific event of level 1 (higher the level, higher the detail)"
    ::= { hdslEventsGroup 3 }

hdsl3-MNEMONIC OBJECT-TYPE
    SYNTAX DisplayString
    MAX-ACCESS accessible-for-notify
    STATUS current
    DESCRIPTION
        "Parameter 'MNEMONIC' in event HDSL.3"
    ::= { hdslEventObjects3 1 }

hdsl3-EVENT-DESCRIPTION OBJECT-TYPE
    SYNTAX DisplayString
    MAX-ACCESS accessible-for-notify
    STATUS current
    DESCRIPTION
        "Parameter 'EVENT-DESCRIPTION' in event HDSL.3"
    ::= { hdslEventObjects3 2 }

hdslEventObjects4 OBJECT-IDENTITY
    STATUS current
    DESCRIPTION
        "Event HDSL.4
        Chipset specific event of level 2"
    ::= { hdslEventsGroup 4 }

hdsl4-MNEMONIC OBJECT-TYPE
    SYNTAX DisplayString
    MAX-ACCESS accessible-for-notify
    STATUS current
    DESCRIPTION
        "Parameter 'MNEMONIC' in event HDSL.4"
    ::= { hdslEventObjects4 1 }

hdsl4-EVENT-DESCRIPTION OBJECT-TYPE
    SYNTAX DisplayString
    MAX-ACCESS accessible-for-notify
    STATUS current
    DESCRIPTION
        "Parameter 'EVENT-DESCRIPTION' in event HDSL.4"
    ::= { hdslEventObjects4 2 }

hdslEventObjects5 OBJECT-IDENTITY
    STATUS current
    DESCRIPTION
        "Event HDSL.5
        Chipset specific event of level 3"
    ::= { hdslEventsGroup 5 }

hdsl5-MNEMONIC OBJECT-TYPE
    SYNTAX DisplayString
    MAX-ACCESS accessible-for-notify
    STATUS current
    DESCRIPTION
        "Parameter 'MNEMONIC' in event HDSL.5"
    ::= { hdslEventObjects5 1 }

hdsl5-EVENT-DESCRIPTION OBJECT-TYPE
    SYNTAX DisplayString
    MAX-ACCESS accessible-for-notify
    STATUS current
    DESCRIPTION
        "Parameter 'EVENT-DESCRIPTION' in event HDSL.5"
    ::= { hdslEventObjects5 2 }

hdslEventObjects6 OBJECT-IDENTITY
    STATUS current
    DESCRIPTION
        "Event HDSL.6
        EOC event"
    ::= { hdslEventsGroup 6 }

hdsl6-MNEMONIC OBJECT-TYPE
    SYNTAX DisplayString
    MAX-ACCESS accessible-for-notify
    STATUS current
    DESCRIPTION
        "Parameter 'MNEMONIC' in event HDSL.6"
    ::= { hdslEventObjects6 1 }

hdsl6-EVENT-DESCRIPTION OBJECT-TYPE
    SYNTAX DisplayString
    MAX-ACCESS accessible-for-notify
    STATUS current
    DESCRIPTION
        "Parameter 'EVENT-DESCRIPTION' in event HDSL.6"
    ::= { hdslEventObjects6 2 }


hdslNotification1 NOTIFICATION-TYPE
    OBJECTS { 
              hdsl1-MNEMONIC, 
              hdsl1-LINE-INFORMATION 
            }
    STATUS current
    DESCRIPTION
        "Notification of Event HDSL.1

        Message: '$1 Line $2'

        Parameters list:
              $1: hdsl1-MNEMONIC
              $2: hdsl1-LINE-INFORMATION

        Notification of a line event: opening state, open failed and reason,
        opened, monitoring forces reneg, signal lost, orderly closed not granted,
        suicide request, closed..."
    ::= { hdslNotificationsPrefix 1 }

hdslNotification2 NOTIFICATION-TYPE
    OBJECTS { 
              hdsl2-MNEMONIC, 
              hdsl2-STATE-MACHINE-EVENT 
            }
    STATUS current
    DESCRIPTION
        "Notification of Event HDSL.2

        Message: '$1 FSM $2'

        Parameters list:
              $1: hdsl2-MNEMONIC
              $2: hdsl2-STATE-MACHINE-EVENT

        State machine event (each chipset has a different state machine)."
    ::= { hdslNotificationsPrefix 2 }

hdslNotification3 NOTIFICATION-TYPE
    OBJECTS { 
              hdsl3-MNEMONIC, 
              hdsl3-EVENT-DESCRIPTION 
            }
    STATUS current
    DESCRIPTION
        "Notification of Event HDSL.3

        Message: '$1 $2'

        Parameters list:
              $1: hdsl3-MNEMONIC
              $2: hdsl3-EVENT-DESCRIPTION

        Chipset specific event of level 1 (higher the level, higher the detail)"
    ::= { hdslNotificationsPrefix 3 }

hdslNotification4 NOTIFICATION-TYPE
    OBJECTS { 
              hdsl4-MNEMONIC, 
              hdsl4-EVENT-DESCRIPTION 
            }
    STATUS current
    DESCRIPTION
        "Notification of Event HDSL.4

        Message: '$1 $2'

        Parameters list:
              $1: hdsl4-MNEMONIC
              $2: hdsl4-EVENT-DESCRIPTION

        Chipset specific event of level 2"
    ::= { hdslNotificationsPrefix 4 }

hdslNotification5 NOTIFICATION-TYPE
    OBJECTS { 
              hdsl5-MNEMONIC, 
              hdsl5-EVENT-DESCRIPTION 
            }
    STATUS current
    DESCRIPTION
        "Notification of Event HDSL.5

        Message: '$1 $2'

        Parameters list:
              $1: hdsl5-MNEMONIC
              $2: hdsl5-EVENT-DESCRIPTION

        Chipset specific event of level 3"
    ::= { hdslNotificationsPrefix 5 }

hdslNotification6 NOTIFICATION-TYPE
    OBJECTS { 
              hdsl6-MNEMONIC, 
              hdsl6-EVENT-DESCRIPTION 
            }
    STATUS current
    DESCRIPTION
        "Notification of Event HDSL.6

        Message: '$1 $2'

        Parameters list:
              $1: hdsl6-MNEMONIC
              $2: hdsl6-EVENT-DESCRIPTION

        EOC event"
    ::= { hdslNotificationsPrefix 6 }


END
