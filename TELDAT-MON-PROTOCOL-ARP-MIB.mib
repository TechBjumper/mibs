-- Teldat, S.A.

                -- Parque Tecnolgico de Madrid

                -- 28760, Tres Cantos (Madrid)

                -- Tlf: +34-918076565

                -- Fax: +34-918076521

                -- e-mail: id@teldat.com


            -- MIB privada de Teldat

            -- Monitorizacin del equipo NUCLEOX-PLUS


    -- Historial:
    --      07/02/14  M.A. Pastor   XH 3523. Errors with HP Openview 9.20
    -- 1.2  08/07/09  I. Muoz      Revisin de todas las MIB para
    --                M.A. Pastor   evitar warnings y errores de
    --                              compilacin
    -- 1.1  18/09/08  P. Nogueira   telProdNpMonProtArpAsocType
    -- 1.0  01/07/04  J. Molina     Fichero procedente del fichero arp.mib


    -- Historial del fichero arp.mib

    -- 01-10-01     N.Villaseor    Traduccin a ingles
    -- 01-12-00     M.A. Pastor     Modificaciones para que pueda ser
    --                              compilada utilizando compiladores
    --                              distintos del de Teldat
    -- 20-6-00      J. Alvarez      Implementacion inicial
    --------------------------------------------------------------------------

TELDAT-MON-PROTOCOL-ARP-MIB DEFINITIONS ::= BEGIN

    IMPORTS
            IpAddress
        FROM RFC1155-SMI
            OBJECT-TYPE
        FROM RFC-1212
            DisplayString
        FROM RFC1213-MIB
            telProdNpMonProtocols
        FROM TELDAT-SW-STRUCTURE-MIB;


    telProdNpMonProtArp     OBJECT IDENTIFIER ::= { telProdNpMonProtocols 2 }


    -- Grupo telProdNpMonProtArp

    telProdNpMonProtArpAsocTable OBJECT-TYPE
        SYNTAX  SEQUENCE OF TelProdNpMonProtArpAsocEntry
        ACCESS  not-accessible
        STATUS  mandatory
        DESCRIPTION
            "Parameter list associated to each interface with ARP."
    ::= { telProdNpMonProtArp 1 }

    telProdNpMonProtArpAsocEntry OBJECT-TYPE
        SYNTAX  TelProdNpMonProtArpAsocEntry
        ACCESS  not-accessible
        STATUS  mandatory
        DESCRIPTION
        "Each entry has interface number, order number for each table entry,
        field to delete an entry, MAC address or DLCI, IP address associated and
        a Refresh field."
        INDEX { telProdNpMonProtArpAsocIfcIndex, telProdNpMonProtArpAsocOrdIndex}
    ::= { telProdNpMonProtArpAsocTable 1 }


    TelProdNpMonProtArpAsocEntry ::=
        SEQUENCE{
            telProdNpMonProtArpAsocIfcIndex     INTEGER,
            telProdNpMonProtArpAsocOrdIndex     INTEGER,
            telProdNpMonProtArpAsocClear        INTEGER,
            telProdNpMonProtArpAsocDirMac       DisplayString,
            telProdNpMonProtArpAsocDirIP        IpAddress,
            telProdNpMonProtArpAsocRefr         INTEGER,
            telProdNpMonProtArpAsocType         INTEGER
            }

    telProdNpMonProtArpAsocIfcIndex OBJECT-TYPE
        SYNTAX INTEGER
        ACCESS  read-only
        STATUS  mandatory
        DESCRIPTION
        "Interface number. It is the first index"
        ::= { telProdNpMonProtArpAsocEntry 1 }

    telProdNpMonProtArpAsocOrdIndex OBJECT-TYPE
        SYNTAX INTEGER(1..32)
        ACCESS  read-only
        STATUS  mandatory
        DESCRIPTION
        "Entry order number. It is the second index"
        ::= { telProdNpMonProtArpAsocEntry 2 }

    telProdNpMonProtArpAsocClear OBJECT-TYPE
        SYNTAX INTEGER{
            delete(1),
            ok(2),
            error(3),
            undefined(4)
            }
        ACCESS  read-write
        STATUS  mandatory
        DESCRIPTION
        "Field that enables the deletion of an entry."
        ::= { telProdNpMonProtArpAsocEntry 3 }

    telProdNpMonProtArpAsocDirMac OBJECT-TYPE
        SYNTAX DisplayString
        ACCESS read-only
        STATUS mandatory
        DESCRIPTION
        "MAC address, or DLCI number in case of Frame Relay"
        ::= { telProdNpMonProtArpAsocEntry 4 }

    telProdNpMonProtArpAsocDirIP OBJECT-TYPE
        SYNTAX IpAddress
        ACCESS  read-only
        STATUS  mandatory
        DESCRIPTION
        "IP address associated."
        ::= { telProdNpMonProtArpAsocEntry 5 }

    telProdNpMonProtArpAsocRefr OBJECT-TYPE
        SYNTAX INTEGER(0..20)
        ACCESS  read-only
        STATUS  mandatory
        DESCRIPTION
        "Refresh field."
        ::= { telProdNpMonProtArpAsocEntry 6 }

    telProdNpMonProtArpAsocType OBJECT-TYPE
        SYNTAX INTEGER{
            public(1),
            private(2)
            }
        ACCESS  read-write
        STATUS  mandatory
        DESCRIPTION
        "Type of entry, public (1) or private (2)"
        ::= { telProdNpMonProtArpAsocEntry 7 }


    telProdNpMonProtArpCmdTable OBJECT-TYPE
        SYNTAX  SEQUENCE OF TelProdNpMonProtArpCmdEntry
        ACCESS  not-accessible
        STATUS  mandatory
        DESCRIPTION
        "Table of the delete command associated to ARP prot."
        ::= { telProdNpMonProtArp 2 }

    telProdNpMonProtArpCmdEntry OBJECT-TYPE
        SYNTAX  TelProdNpMonProtArpCmdEntry
        ACCESS  not-accessible
        STATUS  mandatory
        DESCRIPTION
        "It has two fields: interface number and delete field"
        INDEX { telProdNpMonProtArpCmdIndex }
        ::= { telProdNpMonProtArpCmdTable 1 }


    TelProdNpMonProtArpCmdEntry ::=
        SEQUENCE{
            telProdNpMonProtArpCmdIndex     INTEGER,
            telProdNpMonProtArpCmdDelete    INTEGER
            }

    telProdNpMonProtArpCmdIndex OBJECT-TYPE
        SYNTAX INTEGER
        ACCESS  read-only
        STATUS  mandatory
        DESCRIPTION
            "Interface number. It is the table index."
        ::= { telProdNpMonProtArpCmdEntry 1 }

    telProdNpMonProtArpCmdDelete OBJECT-TYPE
        SYNTAX INTEGER{
            delete(1),
            ok(2),
            error(3),
            undefined(4)
            }
        ACCESS  read-write
        STATUS  mandatory
        DESCRIPTION
            "This field is used to signal the complete table deletion."
        ::= { telProdNpMonProtArpCmdEntry 2 }

END
