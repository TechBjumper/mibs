FIBRONICS-MIB DEFINITIONS ::= BEGIN  
  
-- Title:       Fibronics' MIB  
-- Description: Private SNMP MIB for :  FER2061
-- Version:     6.0  
-- Date:        9 September, 1993  
-- By:          Dan R.   
-- By:          Simha K.(extensions for the agent 6.0)
-- Contact      Edna Ganon
-- Email:       edna@fibronics.co.il   
-- Comments:    Fibronics' agents support also standard mibs:  
--              - MIB-II  ( RFC1213-MIB )  
--              - dot5    ( RFC1231-MIB, updated by RFC1239 )  
  
  
-- This Specification is supplied "as is," and FIBRONICS makes  
-- no warranty, either express or implied, as to the use,  
-- operation, condition, or performance of the Specification.  
  
  
  
IMPORTS  
      IpAddress, Counter, enterprises, TimeTicks  
    FROM RFC1155-SMI  
      OBJECT-TYPE  
    FROM RFC-1212  
      DisplayString  
    FROM RFC1213-MIB;  
-- Some MIB Compilers need these two lines:  
--  enterprises  OBJECT IDENTIFIER ::=   
--                { iso org(3) dod(6) internet(1) private(4) 1 }  
  
fibronics  OBJECT IDENTIFIER ::= { enterprises 22 }  
fbr101  OBJECT IDENTIFIER ::= { fibronics 101 }  
fbr2    OBJECT IDENTIFIER ::= { fbr101 2 }  
fbrStack OBJECT IDENTIFIER ::= { fbr2 2 }   
  
-- Obsolete Groups  
  
-- fbrStandard OBJECT IDENTIFIER ::= { fbrStack 1 }    standard fbrStack tree  
-- fbrSpecific OBJECT IDENTIFIER ::= { fbrStack 2 }    Specific FIBRONICS tree  
-- trSpecific OBJECT IDENTIFIER ::= { fbrStack 3 }     Specific Token Ring  Tree  
-- srlSpecific OBJECT IDENTIFIER ::= { fbrStack 4 }    Specific serial tree  
-- ltSpecific OBJECT IDENTIFIER ::= { fbrStack 5 }    Specific Local Talk tree  
-- lclSpecific OBJECT IDENTIFIER ::= { fbrStack 6 }    Specific Clock Modules tree  
  
-- ===========================================================================  
  
chassis    OBJECT IDENTIFIER ::= { fbrStack 7 } -- chassis group  
genGroup   OBJECT IDENTIFIER ::= { fbrStack 8 } -- gen group SNMP group  
genPort    OBJECT IDENTIFIER ::= { fbrStack 9 } -- gen port group  
genIntPort OBJECT IDENTIFIER ::= { fbrStack 10 }   
					    -- gen internal port group  
softRedundancy OBJECT IDENTIFIER ::= { fbrStack 11 } -- software redundancy group  
eth            OBJECT IDENTIFIER ::= { fbrStack 12 } -- ethernet group  
tok            OBJECT IDENTIFIER ::= { fbrStack 13 } -- token ring group  
ts             OBJECT IDENTIFIER ::= { fbrStack 14 } -- terminal server group   
ltalk          OBJECT IDENTIFIER ::= { fbrStack 15 } -- Local Talk group   
cl             OBJECT IDENTIFIER ::= { fbrStack 16 } -- clock group   
fbrOID         OBJECT IDENTIFIER ::= { fbrStack 17 } -- FIBRONICS OIDs group  
  
fbrSecurity    OBJECT IDENTIFIER ::= { fbrStack 18 } -- security group  
fbrLanSwitch   OBJECT IDENTIFIER ::= { fbrStack 19 } -- switch group  
deviceMgr      OBJECT IDENTIFIER ::= { fbrStack 20 } -- device manager group  
bRouter        OBJECT IDENTIFIER ::= { fbrStack 21 } -- bridges/routers group  
probe          OBJECT IDENTIFIER ::= { fbrStack 22 } -- RMON probes  
  
-- FIBRONICS chassis group  
-- Implementation of this group is mandatory for all FIBRONICS box agents.  
  
chHWType OBJECT-TYPE  
      SYNTAX  INTEGER {  
	let18(1),  
	let3(2),  
	let36(3),  
	let18Extended(4),  
	lert40(5),  
	let10(6),  
	fdx100(7),  
	stack(8),  
	unknown(255)  
      }  
      ACCESS  read-only  
      STATUS  mandatory  
      DESCRIPTION  
      "Indicates type of enclosure in which the FIBRONICS SNMP agent operates."  
      ::= { chassis 1 }     
  
chNumberOfSlots OBJECT-TYPE  
      SYNTAX  INTEGER (1..255)       
      ACCESS  read-only  
      STATUS  mandatory  
      DESCRIPTION  
      "Number of manageable slots in the chassis.  
      In FIBRONICS implementation it describes the number of manageable slots  
      in the chassis (not all slots should be occuppied)."   
      ::= { chassis 2 }     
  
chNumberOfEthernetBuses OBJECT-TYPE          
      SYNTAX  INTEGER (0..255)  
      ACCESS  read-only  
      STATUS  mandatory  
      DESCRIPTION  
      "Indicates the number of internal Ethernet buses provided by the box."  
      ::= { chassis 3 }     
  
chNumberOfTRBuses OBJECT-TYPE       
      SYNTAX  INTEGER (0..255)  
      ACCESS  read-only  
      STATUS  mandatory  
      DESCRIPTION  
      "Indicates the number of internal Token Ring buses provided by the box."  
      ::= { chassis 4 }  
        
chNumberOfFDDIBuses OBJECT-TYPE           
      SYNTAX  INTEGER (0..255)  
      ACCESS  read-only  
      STATUS  mandatory  
      DESCRIPTION  
      "Indicates the number of internal FDDI buses provided by the box."  
      ::= { chassis 5 }     
  
chNumberOfLocalTalkBuses OBJECT-TYPE           
      SYNTAX  INTEGER (0..255)  
      ACCESS  read-only  
      STATUS  mandatory  
      DESCRIPTION  
      "Indicates the number of internal Local Talk buses provided by the box."  
      ::= { chassis 6 }     
  
chReset OBJECT-TYPE  
      SYNTAX  INTEGER {    
	on(1),  
	off(2)  
      }  
      ACCESS  read-write      
      STATUS  mandatory  
      DESCRIPTION  
      "Setting the value of this attribute to ON is interpreted as a reset  
      command for the whole chassis.  
      It initiates a complete reinitialisation of the chassis and of all  
      the devices incorporated inside the chassis."   
      ::= { chassis 7 }  
  
chFullConfig OBJECT-TYPE     
      SYNTAX  OCTET STRING  
      ACCESS  read-only  
      STATUS  mandatory  
      DESCRIPTION  
      "Full configuration message retrieved by FIBRONICS management stations   
      at periodic interrogation times. Coded in compact internal FIBRONICS   
      application format."  
      ::= { chassis 8 }  
  
  
-- Agent Group - attributes of SNMP agents   
   
chAg OBJECT IDENTIFIER              
      ::= { chassis 9 }   
  
  
chGenAgTable OBJECT-TYPE   
      SYNTAX  SEQUENCE OF ChGenAgEntry  
      ACCESS  not-accessible  
      STATUS  mandatory  
      DESCRIPTION  
      "Table of configuration attributes common to all SNMP agents in   
      FIBRONICS hubs."  
      ::= { chAg 1 }   
  
chGenAgEntry OBJECT-TYPE  
      SYNTAX  ChGenAgEntry  
      ACCESS  not-accessible  
      STATUS  mandatory  
      DESCRIPTION  
      "An entry in the table, containing configuration attributes for a single  
      agent."   
      INDEX  { chGenAgId }  
      ::= { chGenAgTable 1 }  
  
ChGenAgEntry  ::=  
      SEQUENCE  {  
	chGenAgId   
	  INTEGER,  
	chGenAgType  
	  INTEGER,  
	chGenAgMgmtIfType  
	  INTEGER,  
	chGenAgAddr  
	  OCTET STRING,  
	chGenAgSpecificOID  
	  OBJECT IDENTIFIER  
      }  
			   
chGenAgId OBJECT-TYPE  
      SYNTAX  INTEGER (1..255)  
      ACCESS  read-only  
      STATUS  mandatory  
      DESCRIPTION  
      "Agent index for identifying the agent.Takes the value of the slot  
      number where the agent card is inserted. For box agents the value  
      of chGenAgId is chNumberOfSlots+1."  
      ::= { chGenAgEntry 1 }  
  
chGenAgType OBJECT-TYPE  
      SYNTAX  INTEGER {  
	 nma1-et(1),  
	 nma1-et-e(2),  
	 nma1-tr(3),  
	 nma2-et(4),  
	 nma2-tr(5),  
	 nma2-fddi(6),  
	 ielb(7),  
	 itlb(8),  
	 lts16(9),  
	 ierp(10),  
	 iefn(11),  
	 itfn(12),  
	 nm2069(13),  
	 nma-rt(14),  
	 unknown(255)   
      }  
      ACCESS  read-only  
      STATUS  mandatory  
      DESCRIPTION  
      "Agent type."  
      ::= { chGenAgEntry 2 }  
  
chGenAgMgmtIfType OBJECT-TYPE  
      SYNTAX  INTEGER {  
	      none(1),  
	      regular1822(2),  
	      hdh1822(3),  
	      ddn-x25(4),  
	      rfc877-x25(5),  
	      ethernet-csmacd(6),  
	      iso88023-csmacd(7),  
	      iso88024-tokenBus(8),  
	      iso88025-tokenRing(9),  
	      iso88026-man(10),  
	      starLan(11),  
	      proteon-10MBit(12),  
	      proteon-80MBit(13),  
	      hyperchannel(14),  
	      fddi(15),  
	      lapb(16),  
	      sdlc(17),  
	      t1-carrier(18),  
	      cept(19),  
	      basicIsdn(20),  
	      primaryIsdn(21),  
	      propPointToPointSerial(22),    -- proprietary serial  
	      ppp(23),  
	      softwareLoopback(24),  
	      eon(25),                       -- CLNP over IP  
	      ethernet-3Mbit(26),  
	      nsip(27),                      -- XNS over IP  
	      slip(28),                      -- generic SLIP  
	      ip(255)  
      }  
      ACCESS  read-only   
      STATUS  mandatory  
     DESCRIPTION  
     "This attribute describes one of the interfaces of agents existing on  
     FIBRONICS modules and their type. Value 'none' defines the lack of    
     an interface recognized by the management console.  Any other value  
     defines an interface whose type is recognized by the management console  
     and may be used as a management channel."  
      ::= { chGenAgEntry 3 }  
  
chGenAgAddr OBJECT-TYPE  
      SYNTAX  OCTET STRING ( SIZE (0..15))   
      ACCESS  read-only                     
      STATUS  mandatory  
     DESCRIPTION  
     "This attribute defines an unique address by which the agent may be   
     addressed by the management console. The address format should be   
     consistent with the type defined by chGenAgMgmtIfType."   
      ::= { chGenAgEntry 4 }  
  
chGenAgSpecificOID OBJECT-TYPE  
	SYNTAX OBJECT IDENTIFIER  
	ACCESS read-only  
	STATUS mandatory  
	DESCRIPTION  
	"This attribute provides the OID of another group containing   
	additional more specific information regarding this instance."  
	::= { chGenAgEntry 5 }  
  
  
chFbrAgTable OBJECT-TYPE  
      SYNTAX  SEQUENCE OF ChFbrAgEntry  
      ACCESS  not-accessible  
      STATUS  mandatory  
      DESCRIPTION  
      "Table of configuration attributes of FIBRONICS SNMP box agents in   
      FIBRONICS hubs."  
      ::= { chAg 2 }  
        
chFbrAgEntry OBJECT-TYPE  
      SYNTAX  ChFbrAgEntry  
      ACCESS  not-accessible  
      STATUS  mandatory  
      DESCRIPTION  
      "An entry in the table, containing configuration attributes for a single  
      agent."   
      INDEX  { chFbrAgId }  
      ::= { chFbrAgTable 1 }  
  
ChFbrAgEntry  ::=  
      SEQUENCE  {  
	chFbrAgId  
	  INTEGER,  
	chFbrAgSLIPAddress  
	  IpAddress,  
	chFbrAgSWVersion  
	  DisplayString,  
	chFbrAgKernelVersion  
	  DisplayString,  
	chFbrAgCoprocSWVersion  
	  DisplayString,  
	chFbrAgSWFault  
	  DisplayString,  
	chFbrAgMgmtBusSelection  
	  INTEGER,  
	chFbrAgCoprocCommStatus  
	  INTEGER,  
	chFbrAgCommDebugMode  
	  INTEGER,  
	chFbrAgConfigChangeTraps  
	  INTEGER,  
	chFbrAgFaultTraps  
	  INTEGER,  
	chFbrAgTrafficThreshTraps  
	  INTEGER,  
	chFbrAgGroupEnrollDeenrollTraps  
	  INTEGER,  
	chFbrAgSoftFaultTraps  
	  INTEGER,  
	chFbrAgHubEnrollTraps  
	  INTEGER,  
	chFbrAgTempThreshTraps  
	  INTEGER,  
	chFbrAgSpecificOID  
	  OBJECT IDENTIFIER,  
	chFbrAgLastAddrConfig  
	  OCTET STRING,  
	chFbrAgSecAddrConfig  
	  OCTET STRING,  
	chFbrAgSoftwareStatus  
	  INTEGER,  
	chFbrAgConfigurationSymbol  
	  DisplayString,  
	chFbrAgIntTemp  
	  INTEGER,  
	chFbrAgBootVersion  
	  DisplayString,  
	chFbrAgSensorFault  
	  INTEGER,  
	chFbrAgSensorFaultTraps  
	  INTEGER,  
	chFbrAgInterProcFault  
	  INTEGER,  
	chFbrAgInterProcFaultTraps  
	  INTEGER  
      }  
			   
chFbrAgId OBJECT-TYPE  
      SYNTAX  INTEGER (1..255)  
      ACCESS  read-only  
      STATUS  mandatory  
      DESCRIPTION  
      "Agent index for identifying the agent. Identical to the index in   
      chGenAgTable for the described agent."  
      ::= { chFbrAgEntry 1 }  
  
chFbrAgSLIPAddress OBJECT-TYPE  
      SYNTAX  IpAddress  
      ACCESS  read-only  
      STATUS  mandatory  
      DESCRIPTION  
      "IP address of the SLIP channel of the agent"  
      ::= { chFbrAgEntry 2 }  
  
chFbrAgSWVersion OBJECT-TYPE  
      SYNTAX  DisplayString  
      ACCESS  read-only  
      STATUS  mandatory  
      DESCRIPTION  
      "ASCII string for description and display of the agent software version."  
      ::= { chFbrAgEntry 3 }  
  
chFbrAgKernelVersion OBJECT-TYPE  
      SYNTAX  DisplayString  
      ACCESS  read-only  
      STATUS  mandatory  
      DESCRIPTION  
      "ASCII string for description and display of the agent operating system  
      (kernel) version."  
      ::= { chFbrAgEntry 4 }  
  
chFbrAgCoprocSWVersion OBJECT-TYPE  
      SYNTAX  DisplayString  
      ACCESS  read-only  
      STATUS  mandatory  
      DESCRIPTION  
      "ASCII string describing the software version of the agent's coprocessor."  
      ::= { chFbrAgEntry 5 }  
  
chFbrAgSWFault OBJECT-TYPE  
      SYNTAX  DisplayString  
      ACCESS  read-only  
      STATUS  mandatory  
      DESCRIPTION  
      "System fault emitted by agent software. It covers faults detected  
      by the agent operating system and drivers. EnterpriseSpecific traps   
      mechanism is used for transfering these traps to the management   
      system."  
      ::= { chFbrAgEntry 6 }  
  
chFbrAgMgmtBusSelection OBJECT-TYPE  
      SYNTAX  INTEGER  
      ACCESS  read-only  
      STATUS  mandatory  
      DESCRIPTION  
      "Attribute describing the number of the bus on which management data  
      are reported."  
      ::= { chFbrAgEntry 7 }  
  
chFbrAgCoprocCommStatus OBJECT-TYPE  
      SYNTAX  INTEGER {  
	      ok(1),  
	      commProblems(2),  
	      timeout(3)  
	 }  
      ACCESS  read-only  
      STATUS  mandatory  
      DESCRIPTION  
      "Attribute describing the status of the communication between the  
      agent and its coprocessor."  
      ::= { chFbrAgEntry 8 }  
  
chFbrAgCommDebugMode OBJECT-TYPE  
      SYNTAX  INTEGER {  
	      on(1),  
	      off(2)  
	 }  
      ACCESS  read-write  
      STATUS  mandatory  
      DESCRIPTION  
      "Attribute describing the agent mode in which communication problem  
      traps are sent to managers (value 'on') or are not sent to managers  
      (value 'off')."  
      ::= { chFbrAgEntry 9 }  
  
chFbrAgConfigChangeTraps OBJECT-TYPE  
	SYNTAX  INTEGER {  
		enabled(1),  
		disabled(2)  
	}  
	ACCESS  read-write  
	STATUS  mandatory  
	DESCRIPTION  
	"The value of this attributes determines whether or not the agent  
	sends Configuration Change traps to the manager."  
	::= {chFbrAgEntry 10 }  
  
chFbrAgFaultTraps OBJECT-TYPE  
	SYNTAX  INTEGER {  
		enabled(1),  
		disabled(2)  
	}  
	ACCESS  read-write  
	STATUS  mandatory  
	DESCRIPTION  
	"The value of this attributes determines whether or not the agent  
	sends Fault traps to the manager."  
	::= {chFbrAgEntry 11 }  
  
chFbrAgTrafficThreshTraps OBJECT-TYPE  
	SYNTAX  INTEGER {  
		enabled(1),  
		disabled(2)  
	}  
	ACCESS  read-write  
	STATUS  mandatory  
	DESCRIPTION  
	"The value of this attributes determines whether or not the agent  
	sends Traffic Threshold traps to the manager."  
	::= {chFbrAgEntry 12 }  
  
chFbrAgGroupEnrollDeenrollTraps OBJECT-TYPE  
	SYNTAX  INTEGER {  
		enabled(1),  
		disabled(2)  
	}  
	ACCESS  read-write  
	STATUS  mandatory  
	DESCRIPTION  
	"The value of this attributes determines whether or not the agent  
	sends Group Enrollment and Group Deenrollment traps to the manager."  
	::= {chFbrAgEntry 13 }  
  
chFbrAgSoftFaultTraps OBJECT-TYPE  
	SYNTAX  INTEGER {  
		enabled(1),  
		disabled(2)  
	}  
	ACCESS  read-write  
	STATUS  mandatory  
	DESCRIPTION  
	"The value of this attributes determines whether or not the agent  
	sends Software Fault traps to the manager."  
	::= {chFbrAgEntry 14 }  
  
chFbrAgHubEnrollTraps OBJECT-TYPE  
	SYNTAX  INTEGER {  
		enabled(1),  
		disabled(2)  
	}  
	ACCESS  read-write  
	STATUS  obsolete  
	DESCRIPTION  
	"The value of this attributes determines whether or not the agent  
	sends periodic Hub Enrollment traps to the manager."  
	::= {chFbrAgEntry 15 }  
  
chFbrAgTempThreshTraps OBJECT-TYPE  
	SYNTAX  INTEGER {  
		enabled(1),  
		disabled(2)  
	}  
	ACCESS  read-write  
	STATUS  mandatory  
	DESCRIPTION  
	"The value of this attributes determines whether or not the agent  
	sends Temperature Threshold traps to the manager."  
	::= {chFbrAgEntry 16 }  
  
chFbrAgSpecificOID OBJECT-TYPE  
	SYNTAX OBJECT IDENTIFIER  
	ACCESS read-only  
	STATUS mandatory  
	DESCRIPTION  
	"This attribute provides the OID of another group containing   
	additional more specific information regarding this instance."  
	::= { chFbrAgEntry 17 }  
  
chFbrAgLastAddrConfig OBJECT-TYPE  
      SYNTAX  OCTET STRING  
      ACCESS  read-only  
      STATUS  mandatory  
      DESCRIPTION  
      "Configuration attribute describing the last physical address detected   
       at each port. Coded in internal FIBRONICS application format. "  
      ::= { chFbrAgEntry 18 }  
        
chFbrAgSecAddrConfig OBJECT-TYPE  
      SYNTAX  OCTET STRING  
      ACCESS  read-only   
      STATUS  mandatory  
      DESCRIPTION  
      "Configuration attribute describing the configuration of the secure   
       addresses. Coded in internal FIBRONICS application format. "  
      ::= { chFbrAgEntry 19 }  
  
chFbrAgSoftwareStatus OBJECT-TYPE  
      SYNTAX  INTEGER {  
	unLoadable(1),  
	loaded(2),  
	downLoading(3)  
      }       
      ACCESS  read-write  
      STATUS  mandatory  
      DESCRIPTION  
      "Describes configuration of the firmware on this agent.  
      unLoadable(1) - is returned by agents which do not support the Software  
      Download feature;  
      loaded(2) - is returned by agents with loaded software;  
      downLoading(3) - when the attribute is set to this value by manager,  
      it triggers the Software Download procedure. When procedure finished,  
      agent software will restablish value loaded(2)."   
      ::= { chFbrAgEntry 20 }  
  
chFbrAgConfigurationSymbol OBJECT-TYPE  
      SYNTAX  DisplayString (SIZE(1))  
      ACCESS  read-write  
      STATUS  mandatory  
      DESCRIPTION  
      "Defines the Configuration Symbol attached to any hardware module  
      manufactured by FIBRONICS. One single character A..Z defines the CS  
      version. For older modules which did not support this option on  
      SNMP character '*' will be returned."  
      ::= { chFbrAgEntry 21 }  
  
chFbrAgIntTemp OBJECT-TYPE  
      SYNTAX  INTEGER  
      ACCESS  read-only  
      STATUS  mandatory  
      DESCRIPTION  
      "Internal temperature measured by the temperature sensor placed on the  
      agent card. Expressed in Celsius degrees."  
      ::= { chFbrAgEntry 22 }  
  
chFbrAgBootVersion OBJECT-TYPE  
      SYNTAX  DisplayString  
      ACCESS  read-only  
      STATUS  mandatory  
      DESCRIPTION  
      "ASCII string for description and display of the agent boot software  
      version."  
      ::= { chFbrAgEntry 23 }  
--      Agent 6.0  
chFbrAgSensorFault OBJECT-TYPE  
	SYNTAX  INTEGER  
	ACCESS  read-only  
	STATUS  mandatory  
	DESCRIPTION  
	"A code of a sensor fault discovered by the agent."  
	::= { chFbrAgEntry 24 }  
  
chFbrAgSensorFaultTraps OBJECT-TYPE  
	SYNTAX  INTEGER { enabled(1), disabled(2) }  
	ACCESS  read-write  
	STATUS  mandatory  
	DESCRIPTION  
	"This attribute enables/disables generation of the sensor fault  
	trap."  
	::= { chFbrAgEntry 25 }  
  
  
chFbrAgInterProcFault OBJECT-TYPE  
	SYNTAX  INTEGER  
	ACCESS  read-only  
	STATUS  mandatory  
	DESCRIPTION  
	"A code of intercommunication fault between Main - Master processors."  
	::= { chFbrAgEntry 26 }  
  
chFbrAgInterProcFaultTraps OBJECT-TYPE  
	SYNTAX  INTEGER  
	ACCESS  read-write  
	STATUS  mandatory  
	DESCRIPTION  
	"This attribute enables/disables generation of the intercommunication  
	fault trap."  
	::= { chFbrAgEntry 27 }  
  
--      Agent 6.0  
chFbrAgSetup OBJECT IDENTIFIER ::= { chAg 3 }  
  
chFbrAgMaxNmbOfMngrs OBJECT-TYPE  
	SYNTAX  INTEGER  
	ACCESS  read-only  
	STATUS  mandatory  
	DESCRIPTION  
	"Maximum number of permanent managers."  
	::= { chFbrAgSetup 1 }  
  
chFbrAgPermMngrTable OBJECT-TYPE  
	SYNTAX  SEQUENCE OF ChFbrAgPermMngrEntry  
	ACCESS  not-accessible  
	STATUS  mandatory  
	DESCRIPTION  
	"Table of permanent managers."  
	::= { chFbrAgSetup 2 }  
  
chFbrAgPermMngrEntry OBJECT-TYPE  
	SYNTAX  ChFbrAgPermMngrEntry  
	ACCESS  not-accessible  
	STATUS  mandatory  
	DESCRIPTION  
	"An entry in the permanent managers table."  
	INDEX           { chFbrAgPermMngrId }  
	::= { chFbrAgPermMngrTable 1 }  
  
ChFbrAgPermMngrEntry ::=  
	SEQUENCE {  
	   chFbrAgPermMngrId  
		INTEGER,  
	   chFbrAgPermMngrAddr  
		IpAddress  
	}  
  
  
chFbrAgPermMngrId OBJECT-TYPE  
	SYNTAX  INTEGER  
	ACCESS  read-only  
	STATUS  mandatory  
	DESCRIPTION  
	"Index in the permanent managers table. It ranges from 1 to chFbrAgMaxNmbOfMngrs"  
	::= { chFbrAgPermMngrEntry 1 }  
  
chFbrAgPermMngrAddr OBJECT-TYPE  
	SYNTAX  IpAddress  
	ACCESS  read-write  
	STATUS  mandatory  
	DESCRIPTION  
	"IP address of a permanent manager."  
	::= { chFbrAgPermMngrEntry 2 }  
  
chFbrAgMaxNmbOfNets OBJECT-TYPE  
	SYNTAX  INTEGER  
	ACCESS  read-only  
	STATUS  mandatory  
	DESCRIPTION  
	"Maximum number of remote networks."  
	::= { chFbrAgSetup 3 }  
  
chFbrAgRmtNetTable OBJECT-TYPE  
	SYNTAX  SEQUENCE OF ChFbrAgRmtNetEntry  
	ACCESS  not-accessible  
	STATUS  mandatory  
	DESCRIPTION  
	"Remote networks table."  
	::= { chFbrAgSetup 4 }  
  
chFbrAgRmtNetEntry OBJECT-TYPE  
	SYNTAX  ChFbrAgRmtNetEntry  
	ACCESS  not-accessible  
	STATUS  mandatory  
	DESCRIPTION  
	"Entry in the remote networks table."  
	INDEX           { chFbrAgRmtNetId }  
	::= { chFbrAgRmtNetTable 1 }  
  
ChFbrAgRmtNetEntry ::=  
	SEQUENCE {  
	     chFbrAgRmtNetId  
		INTEGER,  
	     chFbrAgRmtNetAddr  
		IpAddress,  
	     chFbrAgRmtNetMask  
		IpAddress  
	}  
  
chFbrAgRmtNetId OBJECT-TYPE  
	SYNTAX  INTEGER  
	ACCESS  read-only  
	STATUS  mandatory  
	DESCRIPTION  
	"Index of a remote network. It ranges from 1 to chFbrAgMaxNmbOfNets."  
	::= { chFbrAgRmtNetEntry 1 }  
  
chFbrAgRmtNetAddr OBJECT-TYPE  
	SYNTAX  IpAddress  
	ACCESS  read-write  
	STATUS  mandatory  
	DESCRIPTION  
	"Address of a remote network. The host portion is always 0."  
	::= { chFbrAgRmtNetEntry 2 }  
  
chFbrAgRmtNetMask OBJECT-TYPE  
	SYNTAX  IpAddress  
	ACCESS  read-write  
	STATUS  mandatory  
	DESCRIPTION  
	"Subnet mask for the remote network."  
	::= { chFbrAgRmtNetEntry 3 }  
  
chFbrAgDateTime OBJECT-TYPE  
	SYNTAX  DisplayString (SIZE(13))  
	ACCESS  read-write  
	STATUS  mandatory  
	DESCRIPTION  
	"Current date and time for NMA-TR. The format is YYMMDDhhmmssw, where w - day of the  
	week e.g.,  1=Mon, 2=Tue,..., 7=Sun."  
	::= { chFbrAgSetup 5 }  
  
chFbrAgReset OBJECT-TYPE  
	SYNTAX  INTEGER { on(1), off(2) }  
	ACCESS  read-write  
	STATUS  mandatory  
	DESCRIPTION  
	"This attribute enables the user to reset the agent."  
	::= { chFbrAgSetup 6 }  
  
  
-- Managers group  
-- includes attributes which define the manager stations for the agent software  
-- while internally organized as a table, only one row (its own) is visible  
-- for each manager, so, externally, from SNMP point of view it is not  
-- represented as a table.  
  
chMgr OBJECT IDENTIFIER  
      ::= { chassis 10 }   
  
chMgrTrapRepStatus OBJECT-TYPE  
      SYNTAX  INTEGER {  
	on(1),  
	off(2)    
      }  
      ACCESS  read-write  
      STATUS  mandatory  
      DESCRIPTION  
      "Value 'on' indicates that SNMP agent should send SNMP traps (traffic ex-  
      cluded) to the manager."  
      ::= { chMgr 1 }  
  
chMgrContPerfRep OBJECT-TYPE  
      SYNTAX  INTEGER {  
	on(1),  
	off(2)            
      }  
      ACCESS  read-write  
      STATUS  mandatory  
      DESCRIPTION  
      "Value 'on' indicates that the SNMP agent should send traffic SNMP traps  
      to the manager."  
      ::= { chMgr 2 }  
  
chMgrMngmtState OBJECT-TYPE  
      SYNTAX  INTEGER {  
	on(1),  
	off(2)  
      }  
      ACCESS  read-write  
      STATUS  mandatory  
      DESCRIPTION  
      "Attribute to be set by manager in order to instruct the agent   
      to enter into a management session with the console.   
      Setting this value to 'on' has the effect of performing   
      an 'I am your manager' action upon the agent."  
      ::= { chMgr 3 }  
  
--      Agent 6.0  
chMgrPollInterval OBJECT-TYPE  
	SYNTAX  INTEGER  
	ACCESS  read-write  
	STATUS  mandatory  
	DESCRIPTION  
	"The attribute defines an interval during which the agent is waiting  
	for the manager's requests. Default value 5 minutes."  
	DEFVAL  { 5 }  
	::= { chMgr 4 }  
  
  
-- chassis Hardware group  
  
chHW OBJECT IDENTIFIER  
      ::= { chassis 11 }   
  
  
chHWPSUTable OBJECT-TYPE  
      SYNTAX  SEQUENCE OF ChHWPSUEntry  
      ACCESS  not-accessible  
      STATUS  mandatory  
      DESCRIPTION  
      "Table of configuration attributes for Power Supply Units.  
      This table can be retrieved only from agents equipped with adequate  
      hardware."  
      ::= { chHW 1 }   
  
chHWPSUEntry OBJECT-TYPE  
      SYNTAX  ChHWPSUEntry  
      ACCESS  not-accessible  
      STATUS  mandatory  
      DESCRIPTION  
      "An entry in the table, containing configuration attributes for a single  
      Power Supply Unit."   
      INDEX  { chHWPSUId }  
      ::= { chHWPSUTable 1 }  
  
ChHWPSUEntry  ::=  
      SEQUENCE  {  
	chHWPSUId  
	  INTEGER,  
	chHWPSUActivityStatus  
	  INTEGER,  
	chHWPSULocation  
	  INTEGER,  
	chHWPSUVoltage  
	  INTEGER  
      }  
			   
chHWPSUId OBJECT-TYPE  
      SYNTAX  INTEGER (1..255)  
      ACCESS  read-only  
      STATUS  mandatory  
      DESCRIPTION  
      "PSU index for identifying the PSU."  
      ::= { chHWPSUEntry 1 }  
        
chHWPSUActivityStatus OBJECT-TYPE  
     SYNTAX  INTEGER {  
	notActive(1),  
	dormant(2),  
	active(3)  
      }  
      ACCESS  read-only  
      STATUS  mandatory  
      DESCRIPTION  
      "This attribute defines the status of the PSU in what concerns   
      supplying power to the chassis.   
      NotActive - indicates a disabled or defective PSU which cannot supply   
      power to the chassis.  
      Dormant - indicates a functional PSU which is installed for backup   
      purposes and can at any moment supply power to the devices in the  
      chassis.  
      Active - indicates that the PSU supplies power to the chassis."  
       ::= { chHWPSUEntry 2 }  
        
chHWPSULocation OBJECT-TYPE  
     SYNTAX  INTEGER {  
	other(1),  
	internal(2),  
	external(3)  
      }  
      ACCESS  read-only  
      STATUS  mandatory  
      DESCRIPTION  
      "Describes the location (internal or external) of the PSU."  
      ::= { chHWPSUEntry 3 }  
        
chHWPSUVoltage OBJECT-TYPE  
      SYNTAX  INTEGER   
      ACCESS  read-only  
      STATUS  mandatory  
      DESCRIPTION  
      "Indicates voltage of PSU expressed in miliVolts."  
      ::= { chHWPSUEntry 4 }  
        
  
chHWIntTempWarning OBJECT-TYPE  
      SYNTAX  INTEGER {  
	ok(1),  
	exceeded(2)  
      }  
      ACCESS  read-only  
      STATUS  mandatory  
      DESCRIPTION  
      "Fault condition indicating that the temperature measured by one of the  
      sensors internal to the box exceeded chHWIntTempThresh."  
      ::= { chHW 2 }  
        
chHWIntTempThresh OBJECT-TYPE  
      SYNTAX  INTEGER  
      ACCESS  read-write  
      STATUS  mandatory  
      DESCRIPTION  
      "Internal enclosure temperature threshold value, expressed in   
      degrees Celsius.  When exceeded, a trap is sent to the   
      management console. "  
      ::= { chHW 3 }  
   
chHWPeakIntTemp OBJECT-TYPE  
      SYNTAX  INTEGER  
      ACCESS  read-only  
      STATUS  mandatory  
      DESCRIPTION  
      "Maximum internal temperature inside the chassis. It is the maximum   
      of the temperature values detected by different temperature sensors  
      inside the box. "  
      ::= { chHW 4 }  
  
  
chSlotLastChange OBJECT-TYPE  
	SYNTAX  TimeTicks  
	ACCESS   read-only  
	STATUS  mandatory  
	DESCRIPTION  
	"This attribute contains the value of sysUpTime at the time any of the modules in the hub  
	was enrolled/deenrolled."  
	::= { chassis 12 }  
  
  
-- Generic Group group  
-- mandatory for all managed FIBRONICS modules (groups)  
  
genGroupTable OBJECT-TYPE  
      SYNTAX  SEQUENCE OF GenGroupEntry  
      ACCESS  not-accessible  
      STATUS  mandatory  
      DESCRIPTION  
      "Table of configuration attributes for managed FIBRONICS modules.  
      Includes configuration data which are independent of the   
      specific functionality of the module."  
      ::= { genGroup 1 }  
  
genGroupEntry OBJECT-TYPE  
      SYNTAX  GenGroupEntry  
      ACCESS  not-accessible  
      STATUS  mandatory  
      DESCRIPTION  
      "An entry in the table, containing data about a single group."   
      INDEX  { genGroupId }  
      ::= { genGroupTable 1 }  
  
GenGroupEntry  ::=  
      SEQUENCE  {  
	genGroupId  
	  INTEGER,  
	genGroupSWVersion  
	  DisplayString,  
	genGroupKernelVersion  
	  DisplayString,  
	genGroupType  
	  INTEGER,  
	genGroupDescr  
	  DisplayString,  
	genGroupNumberOfPorts  
	  INTEGER,  
	genGroupNumberOfIntPorts  
	  INTEGER,  
	genGroupReset  
	  INTEGER,  
	genGroupAutoMan  
	  INTEGER,  
	genGroupFullConfig  
	  OCTET STRING,  
	genGroupRedun12  
	  INTEGER,  
	genGroupRedun34  
	  INTEGER,  
	genGroupRedun13-14  
	  INTEGER,  
	genGroupStandAloneMode  
	  INTEGER,  
	genGroupInterProcCommStatus  
	  INTEGER,  
	genGroupCommStatus  
	  INTEGER,  
	genGroupHWStatus  
	  INTEGER,  
	genGroupSupplyVoltageFault  
	  INTEGER,  
	genGroupIntTemp  
	  INTEGER,  
	genGroupSpecificOID  
	  OBJECT IDENTIFIER,  
	genGroupConfigurationSymbol  
	 DisplayString,  
	genGroupLastChange  
	  TimeTicks  
      }  
			   
genGroupId OBJECT-TYPE  
      SYNTAX  INTEGER (1..255)  
      ACCESS  read-only  
      STATUS  mandatory  
      DESCRIPTION  
      "Index which identifies the group inside the chassis for which this  
      entry contains information. Equals the number of the slot by which  
      the group is accessed. This value is never greater than chNumberOfSlots."  
      ::= { genGroupEntry 1 }  
        
genGroupSWVersion OBJECT-TYPE  
      SYNTAX  DisplayString  
      ACCESS  read-only  
      STATUS  mandatory  
      DESCRIPTION  
      "ASCII string for description and display of the group software version."  
      ::= { genGroupEntry 2 }  
        
genGroupKernelVersion OBJECT-TYPE  
      SYNTAX  DisplayString  
      ACCESS  read-only  
      STATUS  mandatory  
      DESCRIPTION  
      "ASCII string for description and display of the group kernel version."  
      ::= { genGroupEntry 3 }  
        
genGroupType OBJECT-TYPE  
      SYNTAX  INTEGER {  
	  le10b(1),  
	  le10b-2(2),  
	  le10c(3),  
	  le10c-2(4),  
	  le15(5),  
	  le15-2(6),  
	  le20(7),  
	  le30x(8),  
	  le30x-2(9),  
	  le30xd(10),  
	  le40x(11),  
	  le40xt(12),  
	  ltr4-RJ45(13),  
	  ltr4-D9(14),  
	  ltr4-D25(15),  
	  ltr4-FO(16),  
	  ltrio-RJ45(19),  
	  ltrio-D9(20),  
	  ltrio-D25(21),  
	  ltrio-FO(22),  
	  ltrio-Con1(23),  
	  ltrio-Con2(24),  
	  le10b-2r(25),  
	  le10c-2r(26),  
	  le80xt(27),  
	  le140xt(28),  
	  ielb(29),  
	  ltrf4(30),  
	  ltrf16(31),  
	  lts16(32),  
	  le20n(33),  
	  ltr104-RJ45(34),  
	  le20r(35),  
	  llt8(36),  
	  le20s(37),  
	  le10b2n(38),  
	  ltr104-D9(39),  
	  ltr104-D25(40),  
	  ltrt-RJ45(41),  
	  ltrt-D9(42),  
	  ltr104f(43),  
	  itlb(44),  
	  le140xtf(45),  
	  le120r(46),  
	  le120r-2(47),  
	  le140xtc(48),  
	  le110b(49),  
	  le110bq(50),  
	  lcl100(51),  
	  le140xtq(52),  
	  le20n-fb(53),  
	  le20s-fb(54),  
	  le140xtf-fb(55),  
	  ltr104s(56),  
	  lert40-AUI(57),  
	  lert40-10BASET(58),  
	  lfd104-mic(59),            
	  lfd104-stm(60),            
	  lfd104-stl(61),            
	  lfd104-stp(62),            
	  lfd104-utp(63),            
	  lfd102-mic(64),            
	  lfd102-stm(65),            
	  lfd102-sts(66),            
	  le140xtn(67),  
--      Agent 5.1  
	  ltr104a(68),  
--      Agent 6.0  
	  le120q(69),  
	  le120sq2(70),  
	  le120sq5(71),  
	  le120q-fb(72),  
	  le120sq2-fb(73),  
	  le120sq5-fb(74),  
	  ltr108t(75),  
	  ltr108f(76),  
	  lse808(77),  
	  lhs(78),  
	  ierb(79),  
	  iefn(80),  
	  itfn(81),  
	  itre1(82),  
	  istc1(83),  
	  iftc(84),  
	  ietlb(85),  
	  ierp(86),  
	  lse108(87),  
	  lse208(88),  
	  le110cq(89),  
	  itre2(90),  
	  istc2(91),  
	  fer2061(92),  
	  le115q(93),  
	  sh-t16(94),  
	  sh-e8(95),  
	  lhb(96),  
	  sh-efn(97),  
	  sh-tfn(98),  
	  itng(99),  
	  lace100(100),  
	  le140xts(101),  
	  le40xtn(102),  
	  le80xtn(103),  
	  unknown(255)  
	}  
      ACCESS  read-only  
      STATUS  mandatory  
      DESCRIPTION  
      "Attribute describing the type of FIBRONICS Ethernet group."  
      ::= { genGroupEntry 4 }  
        
genGroupDescr OBJECT-TYPE  
      SYNTAX  DisplayString  (SIZE (0..32))  
      ACCESS  read-only  
      STATUS  mandatory  
      DESCRIPTION  
      "Descriptor of the group in ASCII (readable) format, mainly for use with  
      generic management applications."  
      ::= { genGroupEntry 5 }  
        
genGroupNumberOfPorts OBJECT-TYPE  
      SYNTAX  INTEGER (0..255)      
      ACCESS  read-only  
      STATUS  mandatory  
      DESCRIPTION  
      "Number of ports in group. It is assumed that on each group the ports   
      are assigned unique numbers in the range from 1 to genGroupNumberOfPorts.  
      They correspond to the number of ports on the module (FRU)"  
      ::= { genGroupEntry 6 }  
        
genGroupNumberOfIntPorts OBJECT-TYPE  
      SYNTAX  INTEGER (0..255)  
      ACCESS read-only  
      STATUS mandatory  
      DESCRIPTION  
      "Number of internal ports (ports connected to the chassis buses) on  
      the module."  
      ::= { genGroupEntry 7 }  
        
genGroupReset OBJECT-TYPE  
      SYNTAX  INTEGER {    
	on(1),  
	off(2)  
      }  
      ACCESS  read-write      
      STATUS  mandatory  
      DESCRIPTION  
      "Setting the value of this attribute to 'on' is interpreted as a software  
      RESET command. Sensor software is reinitialized and according to the   
      sensor specifications, partial or total reset of the module hardware may  
      be performed."  
      ::= { genGroupEntry 8 }  
        
genGroupAutoMan OBJECT-TYPE  
      SYNTAX  INTEGER {  
	auto(1),            
	man(2)             
      }  
      ACCESS  read-only  
      STATUS  mandatory  
      DESCRIPTION  
      "This attribute reflects the status of the Auto/Manual switch which   
      defines the working mode of FIBRONICS sensors. In the MANUAL mode no set  
      operations may be performed on attributes related to the sensor. The    
      sensor works according to configuration switches set by hardware and    
      transmits all configuration information to the agent. In the AUTO mode,  
      hardware switches are overridden by set commands."  
      ::= { genGroupEntry 9 }  
        
genGroupFullConfig OBJECT-TYPE  
      SYNTAX  OCTET STRING  
      ACCESS  read-only  
      STATUS  mandatory  
      DESCRIPTION  
      "Attribute describing the full configuration of a group in internal  
      FIBRONICS application format."  
      ::= { genGroupEntry 10 }  
        
genGroupRedun12 OBJECT-TYPE  
      SYNTAX  INTEGER {  
	on(1),  
	off(2),  
	notSupported(255)  
      }  
      ACCESS  read-write  
      STATUS  mandatory  
      DESCRIPTION  
      "Value ON of this attribute defines a redundancy (backup) relationship   
      between synchronous external ports 1 and 2 on a FIBRONICS module."   
      ::= { genGroupEntry 11 }  
        
genGroupRedun34 OBJECT-TYPE  
      SYNTAX  INTEGER {  
	on(1),  
	off(2),  
	notSupported(255)  
      }  
      ACCESS  read-write  
      STATUS  mandatory  
      DESCRIPTION  
      "Value ON of this attribute defines a redundancy (backup) relationship   
      between synchronous external ports 3 and 4 on a FIBRONICS module."   
      ::= { genGroupEntry 12 }  
        
genGroupRedun13-14 OBJECT-TYPE  
      SYNTAX  INTEGER {  
	on(1),  
	off(2),  
	notSupported(255)  
      }  
      ACCESS  read-write  
      STATUS  mandatory  
      DESCRIPTION  
      "Value ON of this attribute defines a redundancy (backup) relationship   
      between synchronous external ports 13 and 14 on a FIBRONICS module."   
      ::= { genGroupEntry 13 }  
        
genGroupStandAloneMode OBJECT-TYPE  
      SYNTAX  INTEGER {  
	on(1),  
	off(2),  
	notSupported(255)  
	}  
      ACCESS read-write  
      STATUS mandatory  
      DESCRIPTION  
      "Value ON of this attribute indicates the sensor's operation Stand Alone   
      mode . Internal ports are disabled and the card functions in a local   
      star configuration toward its external ports."  
      ::= { genGroupEntry 14 }  
        
genGroupInterProcCommStatus OBJECT-TYPE  
      SYNTAX  INTEGER {  
	ok(1),  
	commProblems(2),  
	noCommunication(3),  
	notSupported(255)  
      }  
      ACCESS  read-only                     
      STATUS  mandatory  
      DESCRIPTION  
      "This attribute describes the status of the communication between the  
      microprocessor of the sensor and the microprocessor of the agent on cards  
      with embedded agents."   
      ::= { genGroupEntry 15 }  
        
genGroupCommStatus OBJECT-TYPE  
      SYNTAX  INTEGER {  
	ok(1),  
	commProblems(2),  
	noCommunication(3),  
	notSupported(255)  
      }  
      ACCESS  read-only  
      STATUS  mandatory  
      DESCRIPTION  
      "This attribute describes the communication status of the group with  
      the SNMP Agent as detected and reported by the agent."  
      ::= { genGroupEntry 16 }  
        
genGroupHWStatus OBJECT-TYPE  
      SYNTAX  INTEGER {  
	ok(1),  
	hardwareProblems(2),  
	notSupported(255)  
      }  
      ACCESS  read-only  
      STATUS  mandatory  
      DESCRIPTION  
      "This attribute describes the status of the group hardware as detected  
      by the sensors software."  
      ::= { genGroupEntry 17 }  
        
genGroupSupplyVoltageFault OBJECT-TYPE  
     SYNTAX  INTEGER {  
	on(1),  
	off(2),  
	notSupported(255)  
      }  
      ACCESS read-only  
      STATUS mandatory  
      DESCRIPTION  
      "A value 'on' of this attribute informs of a 'voltage supply   
      out-of-range' error condition on sensor equipped with   
      hardware which checks this condition."  
      ::= { genGroupEntry 18 }  
  
genGroupIntTemp OBJECT-TYPE  
     SYNTAX  INTEGER   
     ACCESS read-only  
     STATUS mandatory  
     DESCRIPTION  
     "Internal temperature of the enclosure as measured by the   
     specific module instance."  
     ::= { genGroupEntry 19 }  
  
genGroupSpecificOID OBJECT-TYPE  
	SYNTAX OBJECT IDENTIFIER  
	ACCESS read-only  
	STATUS mandatory  
	DESCRIPTION  
	"This attribute provides the OID of another group containing   
	additional more specific information regarding this instance."  
	::= { genGroupEntry 20 }  
  
genGroupConfigurationSymbol OBJECT-TYPE  
      SYNTAX  DisplayString (SIZE(1))  
      ACCESS  read-write  
      STATUS  mandatory  
      DESCRIPTION  
      "Defines the Configuration Symbol attached to any hardware module  
      manufactured by FIBRONICS. One single character A..Z defines the CS  
      version. For older modules which did not support this option on  
      SNMP character '*' will be returned."  
      ::= { genGroupEntry 21 }  
  
genGroupLastChange OBJECT-TYPE  
	SYNTAX  TimeTicks  
	ACCESS  read-only  
	STATUS  mandatory  
	DESCRIPTION  
	"This attribute contains the value of sysUpTime at the time any change pertaining to the  
	specified group occurred."  
	::= { genGroupEntry 22 }  
  
  
  
-- Generic Port group  
-- mandatory for all managed FIBRONICS ports  
  
  
genPortTable OBJECT-TYPE         
      SYNTAX  SEQUENCE OF GenPortEntry  
      ACCESS  not-accessible  
      STATUS  mandatory  
      DESCRIPTION  
      "Table of configuration attributes for managed FIBRONICS ports.  
      Includes configuration data which are independent of the   
      specific functionality of the port."  
      ::= { genPort 1 }   
  
genPortEntry OBJECT-TYPE  
      SYNTAX  GenPortEntry  
      ACCESS  not-accessible  
      STATUS  mandatory  
      DESCRIPTION  
      "An entry in the table, containing data about a single port."   
      INDEX  { genPortGroupId, genPortId }  
      ::= { genPortTable 1 }  
  
GenPortEntry  ::=  
      SEQUENCE  {  
	genPortGroupId  
	  INTEGER,  
	genPortId  
	  INTEGER,  
	genPortFunctionality  
	  INTEGER,  
	genPortType  
	  INTEGER,  
	genPortDescr  
	  DisplayString,  
	genPortActivityStatus  
	  INTEGER,  
	genPortSecurityPolicy  
	  OCTET STRING,  
	genPortSecureAddresses  
	  OCTET STRING,  
	genPortIntPortConnection  
	  INTEGER,  
	genPortAdminStatus  
	  INTEGER,  
	genPortSpecificOID  
	  OBJECT IDENTIFIER  
      }  
  
genPortGroupId OBJECT-TYPE  
      SYNTAX  INTEGER (1..255)  
      ACCESS  read-only  
      STATUS  mandatory  
      DESCRIPTION  
      "Index which identifies the group inside the chassis for which this  
      entry contains information. Equals the number of the slot by which  
      the group containing the port is accessed. This value is never greater  
      than chNumberOfSlots."  
      ::= { genPortEntry 1 }  
        
genPortId OBJECT-TYPE  
      SYNTAX  INTEGER (1..255)  
      ACCESS  read-only  
      STATUS  mandatory  
      DESCRIPTION  
      "Index which identifies the port inside the group for which this  
      entry contains information. It generally corresponds with the number  
      by which the port is identified and is marked on the module.  
      This value is never greater than genGroupNumberOfPorts of the group  
      to which the port belongs."  
      ::= { genPortEntry 2 }  
        
genPortFunctionality OBJECT-TYPE  
      SYNTAX  INTEGER {    
	private(1),  
	repeaterAUI(2),  
	repeaterThin(3),  
	repeater10BaseT(4),  
	tenBaseFSyncAct(5),  
	foirl(6),  
	xcvr(7),  
	lobe(8),  
	ri(9),  
	ro(10),  
	serial(11),  
	localTalk(12),  
	fddi(13),  
	clock(14),  
	genTokenRing(15),  
	dte(16),  
--      Agent 5.1  
	activeLobe(17),  
	genActiveTokenRing(18),  
--      Agent 6.0  
	tenBaseFB(19),  
	lse10BaseT(20),  
	lhsFiber(21),  
	wan(22),  
	star(23),  
	activeRI(24),  
	activeRO(25)  
      }  
      ACCESS  read-only  
      STATUS  mandatory  
      DESCRIPTION  
      "Describes the functionality of the port according to international  
      standards."  
      ::= { genPortEntry 3 }  
        
genPortType OBJECT-TYPE  
      SYNTAX  INTEGER {  
	le10bPort(1),  
	le10cPort(2),  
	le15Port(3),  
	le20Port(4),  
	le30xPort(5),  
	le30xdPort(6),  
	le40xPort(7),  
	le40xtPort(8),  
	lobeRJ45(9),               
	lobeD9(10),  
	lobeD25(11),  
	lobeFO(12),  
	ri104D25(13),  
	ro104D25(14),  
	riRJ45(15),  
	riD9(16),  
	riD25(17),  
	riFO(18),  
	ri104RJ45(19),  
	ri104D9(20),  
	roRJ45(21),  
	roD9(22),  
	roD25(23),  
	roFO(24),  
	ro104RJ45(25),  
	ro104D9(26),  
	le80xtPort(27),  
	le140xtPort(28),  
	ielb-AUIPort(29),  
	ielb-10btPort(30),  
	ltrf4Port(31),  
	ltrf16Port(32),  
	lts16Port(33),  
	llt8Port(34),  
	le20rPort(35),  
	itlbRoPort(36),  
	itlbRiPort(37),  
	itlbDTEPort(38),  
	starFO(39),  
	le10bnPort(40),  
	le120rPort(41),  
	le140xtf-foPort(42),  
	le140xtf-10btPort(43),  
	le140xtcPort(44),  
	le110bPort(45),  
	le110bqPort(46),  
	le140xtqPort(47),  
	lert40-AUIPort(48),  
	lert40-10btPort(49),  
	clock-int(50),  
	clock-ext(51),  
	ri104RJ45S(52),  
	r0104RJ45S(53),  
	lobe104RJ45S(54),  
	le20fbPort(55),  
	le140xtf-fofbPort(56),  
	fddi-micPort1(57),  
	fddi-micPort2(58),  
	fddi-micPort3(59),  
	fddi-stmPort1(60),  
	fddi-stmPort2(61),  
	fddi-stmPort3(62),  
	fddi-stlPort1(63),  
	fddi-stlPort2(64),  
	fddi-stlPort3(65),  
	fddi-stpPort1(66),  
	fddi-stpPort2(67),  
	fddi-stpPort3(68),  
	fddi-utpPort1(69),  
	fddi-utpPort2(70),  
	fddi-utpPort3(71),  
	fddi-stsPort1(72),  
	fddi-stsPort2(73),  
	fddi-stsPort3(74),  
	le140xtnPort(75),  
--      Agent 5.1  
	ltr104a-lobePort(76),  
	ltr104a-riPort(77),  
	ltr104a-roPort(78),  
--      Agent 6.0  
	le120qPort(79),  
	le120sq2PortS(80),  
	le120sq2PortM(81),  
	le120sq5Port(82),  
	le120q-fbPort(83),  
	le120sq2-fbPortS(84),  
	le120sq2-fbPortM(85),  
	le120sq5-fbPort(86),  
	ltr108t-lobePort1(87),  
	ltr108t-riPort1(88),  
	ltr108t-roPort1(89),  
	ltr108t-lobePort(90),  
	ltr108f-lobePort(91),  
	ltr108f-starPortFO(92),  
	ltr108f-riPortFO(93),  
	ltr108f-roPortFO(94),  
	lse808Port(95),  
	lhsPort(96),  
	ierbPort(97),  
	iefnPort(98),  
	itfnPort(99),  
	itrePort(100),  
	istcPort(101),  
	iftcPort(102),  
	ietlb-lobePort(103),  
	ietlb-riPort(104),  
	ietlb-roPort(105),  
	ietlb-10BaseTPort(106),  
	ierpPort(107),  
	lse108Port(108),  
	lse208Port(109),  
	le110cqPort(110),  
	ltr108t-starPort1(111),  
	fer2061-10btPort(112),  
	fer2061-AUIPort(113),  
	fer2061-FOPort(114),  
	fer2061-FOSyncPort(115),  
	le115qPort(116),  
	sht-lobePort(117),  
	sht-riRJ45Port(118),  
	sht-riD9Port(119),  
	sht-riFOPort(120),  
	sht-roRJ45Port(121),  
	sht-roD9Port(122),  
	sht-roFOPort(123),  
	lhbPort(124),  
	itngPort(125),  
	le140xtsPort(126),  
	le40xtnPort(127),  
	le80xtnPort(128),  
	unknownPort(255)   
      }  
      ACCESS  read-only  
      STATUS  mandatory  
      DESCRIPTION  
      "Attribute describing the type of FIBRONICS port."  
      ::= { genPortEntry 4 }  
        
genPortDescr OBJECT-TYPE  
      SYNTAX  DisplayString  (SIZE (0..32))  
      ACCESS  read-only  
      STATUS  mandatory  
      DESCRIPTION  
      "Descriptor of the port in ASCII (readable) format, mainly for use with  
      generic management applications."  
      ::= { genPortEntry 5 }  
        
genPortActivityStatus OBJECT-TYPE  
      SYNTAX  INTEGER {  
	notActive(1),  
	dormant(2),  
	active(3),  
	notSupported(255)  
      }  
      ACCESS  read-only  
      STATUS  mandatory  
      DESCRIPTION  
      "This attribute defines the status of ports that may be part of   
      a redundancy scheme.   
      NotActive - indicates a disabled port which cannot transmit or receive   
      packets even if included in a redundancy scheme.  
      Dormant - indicates an enabled port which does not transmit or receive   
      packets, but because it is included in a redundancy scheme, it may at   
      any moment become responsible packet transmission and reception.  
      Active - indicates that the port transmits and receives packets, serving   
      as the main path in the redundant configuration."  
      ::= { genPortEntry 6 }  
        
genPortSecurityPolicy OBJECT-TYPE  
      SYNTAX  OCTET STRING  
      ACCESS  read-write  
      STATUS  mandatory  
      DESCRIPTION  
      "Security policy (Trap Only or Trap and Close) assigned to this port.  
      The information is coded in internal FIBRONICS format."  
      ::= { genPortEntry 7 }  
  
genPortSecureAddresses OBJECT-TYPE  
      SYNTAX  OCTET STRING  
      ACCESS  read-write  
      STATUS  mandatory  
      DESCRIPTION  
      "This attribute defines the security information (physical addresses)  
      relevant for the entry. Coded in internal format, cryptographic   
      methods may be used for privacy purposes."  
      ::= { genPortEntry 8 }  
        
genPortIntPortConnection OBJECT-TYPE  
      SYNTAX  INTEGER (0..255)  
      ACCESS  read-only   
      STATUS  mandatory  
      DESCRIPTION  
      "The value of this attribute defines the internal port to which the port  
      is connected. A value 0 of this attribute would indicate no internal  
      port connection (stand-alone mode). Any other positive value equals  
      the number of the internal port."  
      ::= { genPortEntry 9 }  
  
genPortAdminStatus OBJECT-TYPE  
      SYNTAX  INTEGER {  
	enabled(1),  
	disabled(2)  
      }  
      ACCESS  read-write  
      STATUS  mandatory  
      DESCRIPTION  
      "A disabled port neither transmits nor receives. The port must be explici-  
      tenly enabled to restore operation. For token ring ports, this attribute  
      is read-only."  
      ::= { genPortEntry 10 }  
        
genPortSpecificOID OBJECT-TYPE  
	SYNTAX OBJECT IDENTIFIER  
	ACCESS read-only  
	STATUS mandatory  
	DESCRIPTION  
	"This attribute provides the OID of another group containing   
	additional more specific information regarding this instance."  
	::= { genPortEntry 11 }  
  
        
  
-- Generic Internal Port group  
-- Implementation of this group is mandatory for all FIBRONICS  
-- SNMP agents.  
  
genIntPortTable OBJECT-TYPE  
      SYNTAX  SEQUENCE OF GenIntPortEntry  
      ACCESS  not-accessible  
      STATUS  mandatory  
      DESCRIPTION  
      "Table of configuration attributes of FIBRONICS internal ports.  
      Internal ports are physical and/or logical entities which   
      transfer information and connect FIBRONICS modules to the internal  
      networks (buses)."  
      ::= { genIntPort 1 }   
  
genIntPortEntry OBJECT-TYPE  
      SYNTAX  GenIntPortEntry  
      ACCESS  not-accessible  
      STATUS  mandatory  
      DESCRIPTION  
      "An entry in the table, containing data about a single port."   
      INDEX  { genIntPortGroupId, genIntPortId }  
      ::= { genIntPortTable 1 }  
  
GenIntPortEntry  ::=  
      SEQUENCE  {  
	genIntPortGroupId  
	  INTEGER,  
	genIntPortId  
	  INTEGER,  
	genIntPortAdminStatus  
	  INTEGER,  
	genIntPortActivityStatus  
	  INTEGER,  
	genIntPortBusConnNumber  
	  INTEGER,  
	genIntPortBusConnType  
	  INTEGER,  
	genIntPortSpecificOID  
	  OBJECT IDENTIFIER,  
-- Agent 6.0  
	genIntPortMonitorMode  
	  INTEGER  
      }  
  
genIntPortGroupId OBJECT-TYPE  
      SYNTAX  INTEGER (1..255)  
      ACCESS  read-only  
      STATUS  mandatory  
      DESCRIPTION  
      "Index which identifies the group inside the chassis for which this  
      entry contains information. Equals the number of the slot by which  
      the group containing the internal port is accessed. This value is   
      never greater than chNumberOfSlots."  
      ::= { genIntPortEntry 1 }  
        
genIntPortId OBJECT-TYPE  
      SYNTAX  INTEGER (1..255)  
      ACCESS  read-only  
      STATUS  mandatory  
      DESCRIPTION  
      "Index which identifies the port inside the group for which this  
      entry contains information.   
      This value is never greater than genGroupNumberOfIntPorts  
      of the group to which the port belongs."  
      ::= { genIntPortEntry 2 }  
        
genIntPortAdminStatus OBJECT-TYPE  
      SYNTAX  INTEGER {  
	enabled(1),  
	disabled(2)  
      }  
      ACCESS  read-write  
      STATUS  mandatory  
      DESCRIPTION  
      "Defines the capability of the internal port to transmit or receive data.  
      A disabled internal port neither transmits or receives. The port must be  
      explicitly enabled to restore operation."   
      ::= { genIntPortEntry 3 }  
        
genIntPortActivityStatus OBJECT-TYPE  
      SYNTAX  INTEGER {  
	notActive(1),  
	dormant(2),  
	active(3),  
	notSupported(255)  
      }  
      ACCESS  read-only  
      STATUS  mandatory  
      DESCRIPTION  
      "This attribute defines the status of internal ports that may be part   
      of a redundancy scheme.   
      NotActive - indicates a disabled port which cannot transmit or receive   
      packets even if included in a redundancy scheme.  
      Dormant - indicates an enabled port which does not transmit or receive   
      packets, but because it is included in a redundancy scheme, it may at   
      any moment become responsible for packet transmission and reception.  
      Active - indicates that the port transmits and receives packets, serving  
      as the main path in the redundant configuration."  
      ::= { genIntPortEntry 4 }  
        
genIntPortBusConnNumber OBJECT-TYPE  
      SYNTAX  INTEGER (0..255)  
      ACCESS  read-write  
      STATUS  mandatory  
      DESCRIPTION  
      "The value of this attribute defines the bus to which the internal port  
      is connected. The value '0' indicates that the port is disconnected from  
      the bus."  
      ::= { genIntPortEntry 5 }  
        
genIntPortBusConnType OBJECT-TYPE  
      SYNTAX  INTEGER {  
	ethernet(1),  
	token-ring(2),  
	local-talk(3),  
	fddi(4),  
--      Agent 6.0  
	high-speed(5),  
	other(255)  
      }  
      ACCESS  read-only  
      STATUS  mandatory  
      DESCRIPTION  
      "The value of this attribute defines the type of the bus to which  
      the internal port is connected."  
      ::= { genIntPortEntry 6 }  
        
genIntPortSpecificOID OBJECT-TYPE  
	SYNTAX OBJECT IDENTIFIER  
	ACCESS read-only  
	STATUS mandatory  
	DESCRIPTION  
	"This attribute provides the OID of another group containing   
	additional more specific information regarding this instance."  
	::= { genIntPortEntry 7 }  
  
genIntPortMonitorMode OBJECT-TYPE  
	SYNTAX  INTEGER { on(1), off(2), notSupported(255) }  
	ACCESS   read-write  
	STATUS  mandatory  
	DESCRIPTION  
	"This attribute enables to monitor a specified bus (RMON)."  
	::= { genIntPortEntry 8 }  
  
  
-- Software Redundancy Group  
-- Implementation of this group is mandatory for all chassis FIBRONICS  
-- SNMP agents.  
  
softRedundancyTable OBJECT-TYPE  
      SYNTAX  SEQUENCE OF SoftRedundancyEntry  
      ACCESS  not-accessible  
      STATUS  mandatory  
      DESCRIPTION  
      "Table of attributes which define software redundancy links   
      defined by means of the FIBRONICS chassis SNMP agents."  
      ::= { softRedundancy 1 }   
  
softRedundancyEntry OBJECT-TYPE  
      SYNTAX  SoftRedundancyEntry  
      ACCESS  not-accessible  
      STATUS  mandatory  
      DESCRIPTION  
      "An entry in the table, containing data about a single   
      software redundancy link."   
      INDEX  { softRedundancyId }  
      ::= { softRedundancyTable 1 }  
  
SoftRedundancyEntry  ::=  
      SEQUENCE  {  
	softRedundancyId  
	  INTEGER,  
	softRedundancyName  
	  DisplayString,  
	softRedundancyGroupId1  
	  INTEGER,  
	softRedundancyPortId1  
	  INTEGER,  
	softRedundancyGroupId2  
	  INTEGER,  
	softRedundancyPortId2  
	  INTEGER,  
	softRedundancyStatus  
	  INTEGER  
      }  
  
softRedundancyId OBJECT-TYPE  
      SYNTAX  INTEGER (1..255)  
      ACCESS  read-only  
      STATUS  mandatory  
      DESCRIPTION  
      "Index which identifies the software redundancy link which for   
      which the current entry provides information."  
      ::= { softRedundancyEntry 1 }  
        
softRedundancyName OBJECT-TYPE  
      SYNTAX  DisplayString (SIZE (15))  
      ACCESS  read-write  
      STATUS  mandatory  
      DESCRIPTION  
      "Logical name of the software redundancy link"  
      ::= { softRedundancyEntry 2 }  
        
softRedundancyGroupId1 OBJECT-TYPE  
      SYNTAX  INTEGER (1..255)  
      ACCESS  read-write  
      STATUS  mandatory  
      DESCRIPTION  
      "ID of the group to which the main port on the software redundancy  
      link belongs. This value is never greater than chNumberOfSlots."  
      ::= { softRedundancyEntry 3 }  
        
softRedundancyPortId1 OBJECT-TYPE  
      SYNTAX  INTEGER (1..255)  
      ACCESS  read-write  
      STATUS  mandatory  
      DESCRIPTION  
      "ID of the main port on the software redundancy link."  
      ::= { softRedundancyEntry 4 }  
        
softRedundancyGroupId2 OBJECT-TYPE  
      SYNTAX  INTEGER (1..255)  
      ACCESS  read-write  
      STATUS  mandatory  
      DESCRIPTION  
      "ID of the group to which the secondary port on the software redundancy  
      link belongs. This value is never greater than chNumberOfSlots."  
      ::= { softRedundancyEntry 5 }  
        
softRedundancyPortId2 OBJECT-TYPE  
      SYNTAX  INTEGER (1..255)   
      ACCESS  read-write  
      STATUS  mandatory  
      DESCRIPTION  
      "ID of the secondary port on the software redundancy link."  
      ::= { softRedundancyEntry 6 }  
        
softRedundancyStatus OBJECT-TYPE  
      SYNTAX  INTEGER {  
	valid(1),  
	createRequest(2),  
	underCreation(3),  
	invalid(4)  
      }   
      ACCESS  read-write  
      STATUS  mandatory  
      DESCRIPTION  
      "Status of the entry in the softRedundancy Table:  
	 valid(1) indicates that row is busy with meaningful values;  
	 createRequest(2) will be set by manager when creating a new row;  
	 underCreation(3) indicates that agent accepts create command and  
	    performs it;  
	 invalid(4) indicates that no meaningful values are present in the   
	    row. Managers set this value in order to transmit a 'Delete   
	    row' command to agent."  
      ::= { softRedundancyEntry 7 }  
  
  
-- Ethernet Agent group. The implementation of this group  
-- is mandatory for all FIBRONICS chassis agent which use Ethernet as  
-- in-band management protocol.  
  
ethAg OBJECT IDENTIFIER  
      ::= { eth 1 }   
  
  
ethAgTable OBJECT-TYPE  
      SYNTAX  SEQUENCE OF EthAgEntry  
      ACCESS  not-accessible  
      STATUS  mandatory  
      DESCRIPTION  
      "Table of attributes which define configuration characteristics  
      for FIBRONICS chassis SNMP agents which use Ethernet as in-band   
      management protocol."  
      ::= { ethAg 1 }   
  
ethAgEntry OBJECT-TYPE  
      SYNTAX  EthAgEntry  
      ACCESS  not-accessible  
      STATUS  mandatory  
      DESCRIPTION  
      "An entry in the table, containing data about a single Ethernet  
      agent."  
      INDEX  { ethAgId }  
      ::= { ethAgTable 1 }  
  
EthAgEntry  ::=  
      SEQUENCE  {  
	ethAgId  
	  INTEGER,  
	ethAgPerfBusSelection  
	  INTEGER  
      }  
  
ethAgId OBJECT-TYPE  
      SYNTAX  INTEGER (1..255)  
      ACCESS  read-only  
      STATUS  mandatory  
      DESCRIPTION  
      "Index which identifies the Ethernet agent for which the current   
      entry provides information."  
      ::= { ethAgEntry 1 }  
        
ethAgPerfBusSelection OBJECT-TYPE  
      SYNTAX  INTEGER  
      ACCESS  read-write  
      STATUS  mandatory  
      DESCRIPTION  
      "Attribute describing the bus attached to the performance data collection   
      hardware on those FIBRONICS agent hardware implementations which support  
      configuration management on multi-Ethernet bus enclosures, but performan-  
      ce data collection on a single bus."  
      ::= { ethAgEntry 2 }  
        
  
-- Ethernet Group (module) group.  
-- Implementation of this group is mandatory for all SNMP Agents which  
-- manage the configuration of FIBRONICS Ethernet modules.  
  
ethGroup OBJECT IDENTIFIER  
      ::= { eth 2 }   
  
  
ethGroupTable OBJECT-TYPE  
      SYNTAX  SEQUENCE OF EthGroupEntry  
      ACCESS  not-accessible  
      STATUS  mandatory  
      DESCRIPTION  
      "Table of attributes which define configuration characteristics  
      for FIBRONICS Ethernet modules."  
      ::= { ethGroup 1 }  
  
ethGroupEntry OBJECT-TYPE  
      SYNTAX  EthGroupEntry  
      ACCESS  not-accessible  
      STATUS  mandatory  
      DESCRIPTION  
      "An entry in the table, containing data about a single Ethernet  
      module (group)."  
      INDEX  { ethGroupId }  
      ::= { ethGroupTable 1 }  
  
EthGroupEntry  ::=  
      SEQUENCE  {  
	ethGroupId  
	  INTEGER,  
	ethGroupFIFO  
	  INTEGER,  
	ethGroup10BTPlus  
	  INTEGER,  
	ethGroupIntPortsRedundancy  
	  INTEGER,  
	ethGroupBackboneMode  
	  INTEGER,  
	ethGroupFOIRLPlusMode  
	  INTEGER,  
	ethGroupWrongPortSelection  
	  INTEGER,  
	ethGroupBackupBus  
	  INTEGER,  
	ethGroupSingleBusMode  
	  INTEGER,  
	ethGroupSpecificOID  
	  OBJECT IDENTIFIER,  
	ethGroup10FBPlus  
	  INTEGER,  
	ethGroupMasterClock  
	  INTEGER,  
	ethGroupIdleTrx  
	  INTEGER,  
	ethGroupMJLPStatus  
	  INTEGER  
      }  
  
ethGroupId OBJECT-TYPE  
      SYNTAX  INTEGER (1..255)  
      ACCESS  read-only  
      STATUS  mandatory  
      DESCRIPTION  
      "Index which identifies the group inside the chassis for which this  
      entry contains information. Equals the number of the slot by which  
      the group is accessed. This value is never greater than chNumberOfSlots."  
      ::= { ethGroupEntry 1 }  
        
ethGroupFIFO OBJECT-TYPE  
      SYNTAX  INTEGER {  
	on(1),  
	off(2),  
	notSupported(255)  
      }  
      ACCESS  read-only  
      STATUS  mandatory  
      DESCRIPTION  
      "Value ON of this attribute describes an internal FIFO error sensed by   
      the internal hardware mechanism of a FIBRONICS repeater."  
      ::= { ethGroupEntry 2 }  
        
ethGroup10BTPlus OBJECT-TYPE  
      SYNTAX  INTEGER {  
	on(1),  
	off(2),  
	notSupported(255)  
      }  
      ACCESS read-write  
      STATUS mandatory  
      DESCRIPTION  
      "Value ON of this attribute defines activation of the 10BaseTPlus  
      mode - a FIBRONICS extension of the 10BaseT standard."  
      ::= { ethGroupEntry 3 }  
        
ethGroupIntPortsRedundancy OBJECT-TYPE  
      SYNTAX  INTEGER {  
	on(1),  
	off(2),  
	notSupported(255)  
      }  
      ACCESS read-write  
      STATUS mandatory  
      DESCRIPTION  
      "Value ON of this attribute defines a redundancy (backup) relationship  
      between internal ports 1 and 2 on a FIBRONICS module."   
      ::= { ethGroupEntry 4 }  
        
ethGroupBackboneMode OBJECT-TYPE  
      SYNTAX  INTEGER {  
	on(1),  
	off(2),  
	notSupported(255)  
      }  
      ACCESS read-write  
      STATUS mandatory  
      DESCRIPTION  
      "Value On of this attribute defines Backbone Mode of a sensor. Internal  
      ports are enabled and the information path goes straightly from external   
      port to internal bus, via corresponding internal port."  
      ::= { ethGroupEntry 5 }  
        
ethGroupFOIRLPlusMode OBJECT-TYPE  
      SYNTAX  INTEGER {  
	on(1),  
	off(2),  
	notSupported(255)  
      }  
      ACCESS read-write  
      STATUS mandatory  
      DESCRIPTION  
      "Value On of this attribute defines FOIRL of a sensor. When this attribute  
      has value ON, FOIRL Plus mode is enabled, while value OFF indicates stan-  
      dard FOIRL mode."  
      ::= { ethGroupEntry 6 }  
        
ethGroupWrongPortSelection OBJECT-TYPE  
      SYNTAX  INTEGER {  
	on(1),  
	off(2),  
	notSupported(255)  
      }  
      ACCESS  read-only  
      STATUS  mandatory  
      DESCRIPTION  
      "A value ON of this attribute warns of incorrect selection of enabled  
      ports on sensors which impose restrictions on this configura-  
      tion (e.g. integrated local bridges.)"  
      ::= { ethGroupEntry 7 }  
        
ethGroupBackupBus OBJECT-TYPE  
      SYNTAX  INTEGER (1..4)   
      ACCESS  read-write  
      STATUS  mandatory  
      DESCRIPTION  
      "Defines the common secondary bus for Ethernet groups with bus   
      redundancy defined at port level."  
      ::= { ethGroupEntry 8 }  
        
ethGroupSingleBusMode OBJECT-TYPE  
      SYNTAX  INTEGER {  
	on(1),  
	off(2),  
	notSupported(255)  
      }  
      ACCESS  read-only  
      STATUS  mandatory  
      DESCRIPTION  
      "Value 'on of this attribute defines bus-star mode for cards   
      supporting this type of configuration."  
      ::= { ethGroupEntry 9 }  
  
ethGroupSpecificOID OBJECT-TYPE  
	SYNTAX OBJECT IDENTIFIER  
	ACCESS read-only  
	STATUS mandatory  
	DESCRIPTION  
	"This attribute provides the OID of another group containing   
	additional more specific information regarding this instance."  
	::= { ethGroupEntry 10 }  
  
--      Agent 6.0  
ethGroup10FBPlus OBJECT-TYPE  
	SYNTAX  INTEGER { on(1), off(2), notSupported(255) }  
	ACCESS  read-write  
	STATUS  mandatory  
	DESCRIPTION  
	"This variable enables/disables 10BaseFB plus mode."  
	::= { ethGroupEntry 11 }  
  
  
ethGroupMasterClock OBJECT-TYPE  
	SYNTAX  INTEGER { on(1), off(2), notSupported(255) }  
	ACCESS  read-only  
	STATUS  mandatory  
	DESCRIPTION  
	"This attribute pertains to the SH-E16 chassis and defines the hub in the stack that  
	generates the clock."  
	::= { ethGroupEntry 12 }  
  
  
ethGroupIdleTrx OBJECT-TYPE  
	SYNTAX  INTEGER { on(1), off(2), notSupported(255) }  
	ACCESS  read-write  
	STATUS  mandatory  
	DESCRIPTION  
	"This attribute is relevant to the LE-120Q/SQ modules and when set to 'off' after   
	port disable terminates also light propagation (for redundancy tests)."   
	::= { ethGroupEntry 13 }  
        
ethGroupMJLPStatus OBJECT-TYPE  
	SYNTAX  INTEGER { on(1), off(2), notSupported(255) }  
	ACCESS  read-only  
	STATUS  mandatory  
	DESCRIPTION  
	"This attribute defines the MJLP error status on the group level."  
	::= { ethGroupEntry 14 }  
  
ethPort OBJECT IDENTIFIER         
      ::= { eth 3 }   
  
  
ethPortTable OBJECT-TYPE  
      SYNTAX    SEQUENCE OF EthPortEntry  
      ACCESS    not-accessible  
      STATUS    mandatory  
DESCRIPTION ""
      ::= { ethPort 1 }   
  
ethPortEntry OBJECT-TYPE  
      SYNTAX    EthPortEntry  
      ACCESS    not-accessible  
      STATUS    mandatory  
DESCRIPTION ""
      INDEX     { ethPortGroupId, ethPortId }  
      ::= { ethPortTable 1 }  
  
EthPortEntry ::=  
   SEQUENCE {  
      ethPortGroupId INTEGER,  
      ethPortId INTEGER,  
      ethPortFunctionalStatus INTEGER,  
      ethPortManPart INTEGER,  
      ethPortJabber INTEGER,  
      ethPortNoAUILoop INTEGER,  
      ethPortMJLP INTEGER,  
      ethPortFIFO INTEGER,  
      ethPortAutoPartitionState INTEGER,  
      ethPortSQETest INTEGER,  
      ethPortLastSourceAddr OCTET STRING,  
      ethPortUserStatus INTEGER,  
      ethPortMainBusSelection INTEGER,  
      ethPortTraffic Counter,  
      ethPortFramesReceivedOK Counter,  
      ethPortRunts Counter,  
      ethPortPacketErrors Counter,  
      ethPortSpecificOID OBJECT IDENTIFIER,  
      ethPortCollisions Counter,  
      ethPortPartitions Counter,  
      ethPortPygmys Counter  
   }  
  
ethPortGroupId OBJECT-TYPE  
      SYNTAX  INTEGER  
      ACCESS  read-only  
      STATUS  mandatory  
      DESCRIPTION  
      "Id of the group to which the port belongs."  
      ::= { ethPortEntry 1 }  
        
ethPortId OBJECT-TYPE  
      SYNTAX  INTEGER  
      ACCESS  read-only  
      STATUS  mandatory  
      DESCRIPTION  
      "Unique Id of the port in the ethPortTable."  
      ::= { ethPortEntry 2 }  
        
ethPortFunctionalStatus OBJECT-TYPE  
      SYNTAX  INTEGER {  
	ok(1),  
	rld(2),            -- RxLinkDown (Link Test Fail)  
	localJabber(3),  
	tld(4),            -- TxLinkDown (Remote Link Down)  
	remoteJabber(5),  
	illSeq(6),  
	shortCirc(7),  
	partitionOrLocalJabber(8),  
	remoteFaultOrLockLost(9),  
	remoteFault(10),  
	lockLost(11),  
	notSupported(255)  
      }  
      ACCESS  read-only  
      STATUS  mandatory  
      DESCRIPTION  
      "The value of this attribute reflects the functional status of FIBRONICS  
      synchronous ports. Note that it is not mandatory that all ports  
      support all the enumerated states. Here is the minimal set possible  
      states:  
      OK - fully functional port, transmitting and receiving packets.  
      RLD - receive link down condition on the port.  
      TLD - transmit link down condition on the port.  
      LocalJabber - fault condition indicating that the port emitted jabber.  
      RemoteJabber - fault condition indicating that remote jabber was sensed  
      at the port.  
      IllSeq - Fault condition indicating an illegal synchronization sequence  
      at the port.  
      ShortCircuit - short-circuit fault condition detected at the port.  
      PartitionOrLocalJabber -  
      RemoteFaultOrLockLoss -   "  
      ::= { ethPortEntry 3 }  
        
ethPortManPart OBJECT-TYPE  
      SYNTAX  INTEGER {  
	on(1),  
	off(2),  
	notSupported(255)  
      }  
      ACCESS  read-write  
      STATUS  mandatory  
      DESCRIPTION  
      "Setting the value of this attribute to ON activates the manual  
      partition mechanism at the port  level. Setting the value of this  
      attribute to OFF cancels the partition mechanism. The segment  
       may reconnect after the reception of 32 packets. Attribute vaild  
       for repeater modules from the LE-10 family."  
      ::= { ethPortEntry 4 }  
        
ethPortJabber OBJECT-TYPE  
      SYNTAX  INTEGER {  
	on(1),  
	off(2),  
	notSupported(255)  
      }  
      ACCESS  read-only  
      STATUS  mandatory  
      DESCRIPTION  
      "Value ON of this attribute reflects jabber transmitted to the port by  
      the hardware of a FIBRONICS repeater or transceiver, as a result of  
      collisions detected on the port. Valid for all modules in the LE-10 and  
      LE-15 families."  
      ::= { ethPortEntry 5 }  
        
ethPortNoAUILoop OBJECT-TYPE  
      SYNTAX  INTEGER {  
	on(1),  
	off(2),  
	notSupported(255)  
      }  
      ACCESS  read-only  
      STATUS  mandatory  
      DESCRIPTION  
      "Value ON of this attribute indicates that a No AUI Loop fault condition  
      was detected on an AUI repeater port. Valid for LE-10C family of modu-  
      les."  
      ::= { ethPortEntry 6 }  
        
ethPortMJLP OBJECT-TYPE  
      SYNTAX  INTEGER {  
	on(1),  
	off(2),  
	notSupported(255)  
      }  
      ACCESS  read-only  
      STATUS  mandatory  
      DESCRIPTION  
      "Value ON of this attribute describes an internal MJLP (MAU Jabber  
      Lockup Protection) error sensed by the internal hardware mechanism  
      of a FIBRONICS repeater.  
      Valid for LE140XTF."  
      ::= { ethPortEntry 7 }  
        
ethPortFIFO OBJECT-TYPE  
      SYNTAX  INTEGER {  
	on(1),  
	off(2),  
	notSupported(255)  
      }  
      ACCESS  read-only  
      STATUS  mandatory  
      DESCRIPTION  
      "Value ON of this attribute describes an internal FIFO error sensed by the  
      internal hardware mechanism of a FIBRONICS repeater.  Valid for LE140XTF."  
      ::= { ethPortEntry 8 }  
        
ethPortAutoPartitionState OBJECT-TYPE  
      SYNTAX  INTEGER {  
	autoPartition(1),  
	notAutoPartition(2),  
	notSupported(255)  
      }  
      ACCESS  read-only  
      STATUS  mandatory  
      DESCRIPTION  
      "The AutoPart condition indicates that the port is currently partitioned  
      by the auto-partition protection mechanism."  
      ::= { ethPortEntry 9 }  
        
ethPortSQETest OBJECT-TYPE  
      SYNTAX  INTEGER {  
	enabled(1),  
	disabled(2),  
	notSupported(255)  
      }  
      ACCESS  read-write  
      STATUS  mandatory  
      DESCRIPTION  
      "Settable attribute which allows activation of SQE test for FIBRONICS  
       integrated transceivers."  
      ::= { ethPortEntry 10 }  
        
ethPortLastSourceAddr OBJECT-TYPE  
      SYNTAX  OCTET STRING  
      ACCESS  read-only  
      STATUS  mandatory  
      DESCRIPTION  
      "Ethernet source address of the last readable frame received by this  
      port."  
      ::= { ethPortEntry 11 }  
        
ethPortUserStatus OBJECT-TYPE  
      SYNTAX  INTEGER {  
	singleUser(1),  
	multiUser(2),  
	notSupported(255)  
      }  
      ACCESS  read-only  
      STATUS  mandatory  
      DESCRIPTION  
      "Attribute defining the connection of a port to a single Ethernet source  
      or to a multi-source (segment or star)."  
      ::= { ethPortEntry 12 }  
        
ethPortMainBusSelection OBJECT-TYPE  
      SYNTAX  INTEGER   
      ACCESS  read-write  
      STATUS  mandatory  
      DESCRIPTION  
      "On cards with port-level redundancy, defines the main bus for each   
      port instance as selected by user."  
      ::= { ethPortEntry 13 }  
        
ethPortTraffic OBJECT-TYPE  
      SYNTAX  Counter  
      ACCESS  read-only  
      STATUS  mandatory  
      DESCRIPTION  
      "Counter for the number of bits received on this port in frames with legal  
      length information."  
      ::= { ethPortEntry 14 }  
        
ethPortFramesReceivedOK OBJECT-TYPE  
      SYNTAX  Counter  
      ACCESS  read-only  
      STATUS  mandatory  
      DESCRIPTION  
      "A representation of the total  number of frames of legal length that have  
      not been corrupted in transmission. These frames can be encoded and   
      decoded by the commonly available MACs and provide a measure of the   
      network bandwidth being used. The number does not include frames received   
      with frame-too-long, FCS, alignment errors, frames lost due to internal   
      MAC sublayer errors, runts or pygmys."  
      ::= { ethPortEntry 15 }  
        
ethPortRunts OBJECT-TYPE  
      SYNTAX  Counter  
      ACCESS  read-only  
      STATUS  mandatory  
      DESCRIPTION  
      "Counter for the number of collision fragments longer than a pygmy and  
      shorter than a legal packet, detected on this port."  
      ::= { ethPortEntry 16 }  
        
ethPortPacketErrors OBJECT-TYPE  
      SYNTAX  Counter  
      ACCESS  read-only  
      STATUS  mandatory  
      DESCRIPTION  
      "Counter for the number of frames with errors detected on the port by  
      the FIBRONICS agent hardware. This generic port error comprises too long  
      packets, CRC and alignment errors."  
      ::= { ethPortEntry 17 }  
        
ethPortSpecificOID OBJECT-TYPE  
	SYNTAX OBJECT IDENTIFIER  
	ACCESS read-only  
	STATUS mandatory  
	DESCRIPTION  
	"This attribute provides the OID of another group containing   
	additional more specific information regarding this instance."  
	::= { ethPortEntry 18 }  
  
ethPortCollisions OBJECT-TYPE  
	SYNTAX  Counter  
	ACCESS  read-only  
	STATUS  mandatory  
	DESCRIPTION  
	"The number of collisions observed on a specified port. Relevant  
	for MPR modules."  
	::= { ethPortEntry 19 }  
  
ethPortPartitions OBJECT-TYPE  
	SYNTAX  Counter  
	ACCESS  read-only  
	STATUS  mandatory  
	DESCRIPTION  
	"The number of partitions observed on a specified port. Relevant  
	for MPR modules."  
	::= { ethPortEntry 20 }  
  
ethPortPygmys OBJECT-TYPE  
	SYNTAX  Counter  
	ACCESS  read-only  
	STATUS  mandatory  
	DESCRIPTION  
	"The number of pygmys observed on a specified port. Relevant  
	for MPR modules."  
	::= { ethPortEntry 21 }  
  
  
ethIntPort OBJECT IDENTIFIER  
      ::= { eth 4 }  
  
  
ethIntPortTable OBJECT-TYPE  
      SYNTAX  SEQUENCE OF EthIntPortEntry  
      ACCESS  not-accessible  
      STATUS mandatory  
DESCRIPTION ""
      ::= { ethIntPort 1 }  
  
ethIntPortEntry OBJECT-TYPE  
      SYNTAX    EthIntPortEntry  
      ACCESS    not-accessible  
      STATUS    mandatory  
DESCRIPTION ""
      INDEX     { ethIntPortGroupId, ethIntPortId }  
      ::= { ethIntPortTable 1 }  
  
EthIntPortEntry ::=  
      SEQUENCE {  
	 ethIntPortGroupId   
	    INTEGER,  
	 ethIntPortId  
	    INTEGER,  
	 ethIntPortPartition   
	    INTEGER,  
	 ethIntPortJabber   
	    INTEGER,  
	 ethIntPortBackedUp   
	    INTEGER  
      }  
  
ethIntPortGroupId OBJECT-TYPE  
      SYNTAX  INTEGER (1..255)  
      ACCESS  read-only  
      STATUS  mandatory  
      DESCRIPTION  
      "ID of the group to which the internal port belongs."  
      ::= { ethIntPortEntry 1 }  
        
ethIntPortId OBJECT-TYPE  
      SYNTAX  INTEGER (1..255)  
      ACCESS  read-only  
      STATUS  mandatory  
      DESCRIPTION  
      "ID of the internal port in the ethIntPortTable."  
      ::= { ethIntPortEntry 2 }  
        
ethIntPortPartition OBJECT-TYPE  
      SYNTAX  INTEGER {  
	on(1),  
	off(2),  
	notSupported(255)  
      }  
      ACCESS  read-only  
      STATUS  mandatory  
      DESCRIPTION  
      "This condition indicates that the internal port is currently partitioned  
      from the bus by the auto-partition protection mechanism."  
      ::= { ethIntPortEntry 3 }  
        
ethIntPortJabber OBJECT-TYPE  
      SYNTAX  INTEGER {  
	on(1),  
	off(2),  
	notSupported(255)  
      }  
      ACCESS  read-only  
      STATUS  mandatory  
      DESCRIPTION  
      "Value ON of this attribute reflects jabber being transmitted to the bus   
      by the hardware of a FIBRONICS repeater, as a result of collisions detected   
      on the internal bus of the enclosure. This situation is similar to MJLP  
      as defined by the Repeater Management standard."  
      ::= { ethIntPortEntry 4 }  
        
ethIntPortBackedUp OBJECT-TYPE  
      SYNTAX INTEGER {  
	on(1),  
	off(2),  
	notSupported(255)  
      }  
      ACCESS   read-write  
      STATUS   mandatory  
      DESCRIPTION  
      "Indicates that internal port is part of a redundancy scheme."  
      ::= { ethIntPortEntry 5 }  
  
        
  
ethBus OBJECT IDENTIFIER  
      ::= { eth 5 }   
  
  
ethBusPerfTable OBJECT-TYPE         
      SYNTAX  SEQUENCE OF EthBusPerfEntry  
      ACCESS  not-accessible  
      STATUS mandatory  
DESCRIPTION ""
      ::= { ethBus 1 }  
   
ethBusPerfEntry OBJECT-TYPE  
      SYNTAX    EthBusPerfEntry  
      ACCESS    not-accessible  
      STATUS    mandatory  
DESCRIPTION ""
      INDEX     { ethBusPerfAgId, ethBusPerfId }  
      ::= { ethBusPerfTable 1 }  
   
EthBusPerfEntry ::=  
      SEQUENCE {  
	 ethBusPerfAgId  
	    INTEGER,  
	 ethBusPerfId  
	    INTEGER,  
	 ethBusTrafficBuffer  
	    OCTET STRING,  
	 ethBusTrafficThresh  
	    INTEGER,  
	 ethBusPeakTraffic  
	    INTEGER,  
	 ethBusTotalCollisions  
	    Counter,  
	 ethBusTotalPackets  
	    Counter,  
	 ethBusTotalErrors  
	    Counter,  
	 ethBusTraffic  
	    INTEGER,  
	 ethBusUtilization  
	    INTEGER,  
	 ethBusPeakUtilization  
	    INTEGER  
      }  
  
ethBusPerfAgId OBJECT-TYPE  
      SYNTAX  INTEGER (1..255)  
      ACCESS  read-only  
      STATUS  mandatory  
      DESCRIPTION  
      "ID of the agent in the ethBusPerfTable."  
      ::= { ethBusPerfEntry 1 }  
        
ethBusPerfId OBJECT-TYPE  
      SYNTAX  INTEGER (1..255)  
      ACCESS  read-only  
      STATUS  mandatory  
      DESCRIPTION  
      "ID of the bus in the ethBusPerfTable."  
      ::= { ethBusPerfEntry 2 }  
        
ethBusTrafficBuffer OBJECT-TYPE  
      SYNTAX  OCTET STRING  
      ACCESS  read-only  
      STATUS  mandatory  
      DESCRIPTION  
      "Record of traffic for the last second with a resolution of 100 msec. The  
       traffic is expressed in percents of the maximum Ethernet traffic and each  
      record contains 10 readings, in the range 1..20, expressed on a log(10)  
      scale ( value = 10*log10(percent) )."  
      ::= { ethBusPerfEntry 3 }  
        
ethBusTrafficThresh OBJECT-TYPE  
      SYNTAX  INTEGER  
      ACCESS  read-write  
      STATUS  mandatory  
      DESCRIPTION  
      "Traffic threshold value. When exceeded, a trap is send to the management  
      console. Expressed in percents of the maximum Ethernet traffic, in the  
      range 1..20, expressed on a log(10) scale."  
      ::= { ethBusPerfEntry 4 }  
        
ethBusPeakTraffic OBJECT-TYPE  
      SYNTAX  INTEGER                -- Values 1..20 (Log(10) scale)  
      ACCESS  read-only  
      STATUS  mandatory  
      DESCRIPTION  
      "Maximal traffic value since last reset of hub or relay. Expressed in per-  
      cents of the maximum Ethernet traffic, in the range 1..20,  
      expressed on log(10) scale."  
      ::= { ethBusPerfEntry 5 }  
        
ethBusTotalCollisions OBJECT-TYPE  
      SYNTAX  Counter  
      ACCESS  read-only  
      STATUS  mandatory  
      DESCRIPTION  
      "Counter incremented every time the hub enters a condition caused by  
      simultaneous transmission and detection of external activity on one or  
      more of its ports."  
      ::= { ethBusPerfEntry 6 }  
        
ethBusTotalPackets OBJECT-TYPE  
      SYNTAX  Counter  
      ACCESS  read-only  
      STATUS  mandatory  
      DESCRIPTION  
      "Counter for number of packets (good and errors) detected on the  
      Ethernet bus."  
      ::= { ethBusPerfEntry 7 }  
        
ethBusTotalErrors OBJECT-TYPE  
      SYNTAX  Counter  
      ACCESS  read-only  
      STATUS  mandatory  
      DESCRIPTION  
      "Counter for number of errors detected on the Ethernet bus. Does not  
      take into account the collisions."  
      ::= { ethBusPerfEntry 8 }  
  
ethBusTraffic OBJECT-TYPE  
      SYNTAX  INTEGER  
      ACCESS  read-only  
      STATUS  mandatory  
      DESCRIPTION  
      "Last traffic reading (sampling time =  100 msec). The  
      traffic is expressed in percents of the maximum Ethernet traffic  
      in the range 1..20, expressed on a log(10)  
      scale ( value = 10*log10(percent) )."  
      ::= { ethBusPerfEntry 9 }  
  
ethBusUtilization OBJECT-TYPE  
	SYNTAX  INTEGER  
	ACCESS  read-only  
	STATUS  mandatory  
	DESCRIPTION  
	"Last traffic reading (sampling time =  100 msec). The  traffic is expressed  
	 in percents of the maximum Ethernet traffic."  
	::= { ethBusPerfEntry 10 }  
  
ethBusPeakUtilization OBJECT-TYPE  
	SYNTAX  INTEGER  
	ACCESS  read-only  
	STATUS  mandatory  
	DESCRIPTION  
	"Maximal traffic value since last reset of agent. Expressed in percents  
	of the maximum effective Ethernet traffic."  
	::= { ethBusPerfEntry 11 }  
  
        
  
ethBusClockTable OBJECT-TYPE  
      SYNTAX  SEQUENCE OF EthBusClockEntry  
      ACCESS  not-accessible  
      STATUS mandatory  
DESCRIPTION ""
      ::= { ethBus 2 }  
   
ethBusClockEntry OBJECT-TYPE  
      SYNTAX    EthBusClockEntry  
      ACCESS    not-accessible  
      STATUS    mandatory  
DESCRIPTION ""
      INDEX     { ethBusClockBusId, ethBusClockId }  
      ::= { ethBusClockTable 1 }  
   
EthBusClockEntry ::=  
      SEQUENCE {  
	 ethBusClockBusId  
	    INTEGER,  
	 ethBusClockId  
	    INTEGER,  
	 ethBusClockTestResult  
	    INTEGER  
      }  
  
ethBusClockBusId OBJECT-TYPE  
      SYNTAX  INTEGER (1..255)  
      ACCESS  read-only  
      STATUS  mandatory  
      DESCRIPTION  
      "ID of the bus in the ethBusClockTable."  
      ::= { ethBusClockEntry 1 }  
        
ethBusClockId OBJECT-TYPE  
      SYNTAX  INTEGER (1..255)  
      ACCESS  read-only  
      STATUS  mandatory  
      DESCRIPTION  
      "ID of the clock in the ethBusClockTable."  
      ::= { ethBusClockEntry 2 }  
        
ethBusClockTestResult OBJECT-TYPE  
      SYNTAX  INTEGER {  
	ok(1),  
	clockFailure(2),  
	busFailure(3),  
	notSupported(255)  
      }  
      ACCESS  read-only  
      STATUS  mandatory  
      DESCRIPTION  
      "Values clockFailure and busFailure define the faulty statuses for  
      clock tests. The test is performed by LCL100 module."  
      ::= { ethBusClockEntry 3 }  
  
        
  
tokRing OBJECT IDENTIFIER  
      ::= { tok 1 }   
  
  
tokRingTable OBJECT-TYPE  
      SYNTAX  SEQUENCE OF TokRingEntry  
      ACCESS  not-accessible  
      STATUS mandatory  
DESCRIPTION ""
      ::= { tokRing 1 }  
   
tokRingEntry OBJECT-TYPE  
      SYNTAX    TokRingEntry  
      ACCESS    not-accessible  
      STATUS    mandatory  
DESCRIPTION ""
      INDEX     { tokRingAgId, tokRingId }  
      ::= { tokRingTable 1 }  
   
TokRingEntry ::=  
      SEQUENCE {  
	 tokRingAgId  
	    INTEGER,  
	 tokRingId  
	    INTEGER,  
	 tokRingLeftSlot  
	    INTEGER,  
	 tokRingRightSlot  
	    INTEGER,  
	 tokRingTrafficBuffer  
	    OCTET STRING,  
	 tokRingTrafficThresh  
	    INTEGER,  
	 tokRingPeakTraffic  
	    INTEGER,  
	 tokRingNumberOfStations  
	    INTEGER,  
	 tokRingConfiguration  
	    OCTET STRING,  
	 tokRingBeaconing  
	    INTEGER,  
	 tokRingBeaconingStation  
	    OCTET STRING,  
	 tokRingStationsMatch  
	    INTEGER,  
	 tokRingTraffic  
	    INTEGER,  
	 tokRingSecurityMethod  
	    INTEGER,  
	 tokRingSecurityPolicy  
	    OCTET STRING,  
	 tokRingSecureAddr  
	    OCTET STRING,  
	 tokRingLastViolation  
	    OCTET STRING,  
	 tokRingUtilization  
	    INTEGER,  
	 tokRingPeakUtilization  
	    INTEGER  
      }  
  
tokRingAgId OBJECT-TYPE  
      SYNTAX  INTEGER (1..255)  
      ACCESS  read-only  
      STATUS  mandatory  
      DESCRIPTION  
      "ID of the agent to which the ring belongs in the tokRingTable."  
      ::= { tokRingEntry 1 }  
        
tokRingId OBJECT-TYPE  
      SYNTAX  INTEGER (1..255)  
      ACCESS  read-only  
      STATUS  mandatory  
      DESCRIPTION  
      "ID of the ring in the tokRingTable."  
      ::= { tokRingEntry 2 }  
        
tokRingLeftSlot OBJECT-TYPE  
      SYNTAX  INTEGER (1..255)  
      ACCESS  read-only  
      STATUS  mandatory  
      DESCRIPTION  
      "Slot number of the left-most slot of the ring."  
      ::= { tokRingEntry 3 }  
        
tokRingRightSlot OBJECT-TYPE  
      SYNTAX  INTEGER (1..255)  
      ACCESS  read-write  
      STATUS  mandatory  
      DESCRIPTION  
      "Slot number of the right-most slot of the ring that has a lobe port. "  
      ::= { tokRingEntry 4 }  
        
tokRingTrafficBuffer OBJECT-TYPE  
      SYNTAX  OCTET STRING  
      ACCESS  read-only  
      STATUS  mandatory  
      DESCRIPTION  
      "Record of traffic for the last second with a resolution of 100 msec.  
      The traffic is expressed in percents of the maximum effective TR traffic  
      (token messages are excluded) and each record contains 10 readings,  
      in range 1..20 on log(10) scale."  
      ::= { tokRingEntry 5 }  
        
tokRingTrafficThresh OBJECT-TYPE  
      SYNTAX  INTEGER  
      ACCESS  read-write  
      STATUS  mandatory  
      DESCRIPTION  
      "Traffic threshold value. When exceeded, a trap is send to the management  
      console. Expressed in percents of the maximum effective TR traffic  
      (token messages are excluded) in the range 1..20 on log(10) scale."  
      ::= { tokRingEntry 6 }  
        
tokRingPeakTraffic OBJECT-TYPE  
      SYNTAX  INTEGER                -- Values 1..20 (Log(10) scale)  
      ACCESS  read-only  
      STATUS  mandatory  
      DESCRIPTION  
      "Maximal traffic value since last reset of agent. Expressed in percents  
      of the maximum effective TR traffic (token messages are excluded), in the  
      range 1..20 on log(10) scale."  
      ::= { tokRingEntry 7 }  
        
tokRingNumberOfStations OBJECT-TYPE  
      SYNTAX  INTEGER  
      ACCESS  read-only  
      STATUS  mandatory  
      DESCRIPTION  
      "Number of Token Ring stations (controllers) detected on the ring. The  
      TR controller of the agent card is included in this count."  
      ::= { tokRingEntry 8 }  
        
tokRingConfiguration OBJECT-TYPE  
      SYNTAX  OCTET STRING  
      ACCESS  read-only  
      STATUS  mandatory  
      DESCRIPTION  
      "Configuration attribute describing the list of physical addresses  
      detected on the Token Ring. Coded in internal FIBRONICS application  
      format. "  
      ::= { tokRingEntry 9 }  
        
tokRingBeaconing OBJECT-TYPE  
      SYNTAX  INTEGER {  
	on(1),  
	off(2),  
	notSupported(255)  
      }  
      ACCESS  read-only  
      STATUS  mandatory  
      DESCRIPTION  
      "This attribute indicates if a beaconing condition is currently  
      detected on the ring."  
      ::= { tokRingEntry 10 }  
        
tokRingBeaconingStation OBJECT-TYPE  
      SYNTAX  OCTET STRING  
      ACCESS  read-only  
      STATUS  mandatory  
      DESCRIPTION  
      "The MAC address of the last station which was detected as sending  
      Beaconing MAC frames on the ring."  
      ::= { tokRingEntry 11 }  
        
tokRingStationsMatch OBJECT-TYPE  
      SYNTAX  INTEGER {  
	on(1),  
	off(2),  
	notSupported(255)  
      }  
      ACCESS  read-only  
      STATUS  mandatory  
      DESCRIPTION  
      "This attribute indicates matching between the number of stations  
      detected on the ring between the current agent and the next agent  
      on Up Stream sense and the number of connected lobe ports.Used by  
      the port address correlation mechanism."  
      ::= { tokRingEntry 12 }  
        
tokRingTraffic OBJECT-TYPE  
      SYNTAX  INTEGER  
      ACCESS  read-only  
      STATUS  mandatory  
      DESCRIPTION  
      "Last traffic reading (sampling time =  100 msec). The  
      traffic is expressed in percents of the maximum Ethernet traffic  
      in the range 1..20, expressed on a log(10)  
      scale ( value = 10*log10(percent) )."  
      ::= { tokRingEntry 13 }  
  
tokRingSecurityMethod OBJECT-TYPE  
	SYNTAX  INTEGER { perPort(1), perRing(2), disabled(3),  
			notSupported(255) }  
	ACCESS  read-write  
	STATUS  mandatory  
	DESCRIPTION  
	"Security scheme selected by the user."  
	::= { tokRingEntry 14 }  
  
tokRingSecurityPolicy OBJECT-TYPE  
	SYNTAX  OCTET STRING (SIZE(1))  
	ACCESS  read-write  
	STATUS  mandatory  
	DESCRIPTION  
	"Security policy (trap only or trap and disconnect) selected for the  
	ring. Coded in FIBRONICS internal format."  
	::= { tokRingEntry 15 }  
  
tokRingSecureAddr OBJECT-TYPE  
	SYNTAX  OCTET STRING  
	ACCESS  read-write  
	STATUS  mandatory  
	DESCRIPTION  
	"Secure addresses assigned to the ring. Coded in FIBRONICS internal  
	format."  
	::= { tokRingEntry 16 }  
  
tokRingLastViolation OBJECT-TYPE  
	SYNTAX  OCTET STRING  
	ACCESS  read-only  
	STATUS  mandatory  
	DESCRIPTION  
	"MAC address of a last detected intruder."  
	::= { tokRingEntry 17 }  
  
tokRingUtilization OBJECT-TYPE  
	SYNTAX  INTEGER  
	ACCESS  read-only  
	STATUS  mandatory  
	DESCRIPTION  
	"Last traffic reading (sampling time =  100 msec). The traffic is expressed  
	in percents of the maximum Token Ring traffic."  
	::= { tokRingEntry 18 }  
  
tokRingPeakUtilization OBJECT-TYPE  
	SYNTAX  INTEGER  
	ACCESS  read-only  
	STATUS  mandatory  
	DESCRIPTION  
	"Maximal traffic value since last reset of agent. Expressed in percents  
	of the maximum effective TR traffic (token messages are excluded)."  
	::= { tokRingEntry 19 }  
  
  
        
  
tokGroup OBJECT IDENTIFIER  
      ::= {tok 2}  
  
  
tokGroupTable OBJECT-TYPE        
      SYNTAX  SEQUENCE OF TokGroupEntry  
      ACCESS  not-accessible  
      STATUS mandatory  
DESCRIPTION ""
      ::= {tokGroup 1}  
   
tokGroupEntry OBJECT-TYPE  
      SYNTAX    TokGroupEntry  
      ACCESS    not-accessible  
      STATUS    mandatory  
DESCRIPTION ""
      INDEX     { tokGroupId }  
      ::= { tokGroupTable 1 }  
   
TokGroupEntry ::=  
      SEQUENCE {  
	 tokGroupId  
	    INTEGER,  
	 tokGroupAutoRightLoop  
	    INTEGER,  
	 tokGroupAutoLeftLoop  
	    INTEGER,  
	 tokGroupManRightLoop  
	    INTEGER,  
	 tokGroupManLeftLoop  
	    INTEGER,  
	 tokGroupRightNeighbor  
	    INTEGER,  
	 tokGroupLeftNeighbor  
	    INTEGER,  
	 tokGroupIOMode  
	    INTEGER,  
	 tokGroupBridgeMode  
	    INTEGER,  
	 tokGroupManLinkLoop  
	    INTEGER,  
	 tokGroupManBusLoop  
	    INTEGER,  
	 tokGroupAutoLinkLoop  
	    INTEGER,  
	 tokGroupAutoBusLoop  
	    INTEGER,  
	 tokGroupSpecificOID  
	    OBJECT IDENTIFIER  
      }  
  
tokGroupId OBJECT-TYPE  
      SYNTAX  INTEGER (1..255)  
      ACCESS  read-only  
      STATUS  mandatory  
      DESCRIPTION  
      "Number of the slot in which the group is installed."  
      ::= { tokGroupEntry 1 }  
        
tokGroupAutoRightLoop OBJECT-TYPE  
      SYNTAX  INTEGER {  
	on(1),  
	off(2),  
	notSupported(255)  
      }  
      ACCESS  read-only  
      STATUS  mandatory  
      DESCRIPTION  
      "Value ON of this attribute signifies that a hardware loop was  
      automatically created on a Token Ring module which does not sense  
      the existence of another token ring group on the right hand side."  
      ::= { tokGroupEntry 2 }  
        
tokGroupAutoLeftLoop OBJECT-TYPE  
      SYNTAX  INTEGER {  
	on(1),  
	off(2),  
	notSupported(255)  
      }  
      ACCESS  read-only  
      STATUS  mandatory  
      DESCRIPTION  
      "Value ON of this attribute signifies that a hardware loop was  
      automatically created on a Token Ring module which does not sense  
      the existence of another token ring group on the left hand side."  
      ::= { tokGroupEntry 3 }  
        
tokGroupManRightLoop OBJECT-TYPE  
      SYNTAX  INTEGER {  
	on(1),  
	off(2),  
	notSupported(255)  
      }  
      ACCESS  read-write  
      STATUS  mandatory  
      DESCRIPTION  
      "Setting this attribute to ON signifies a command to the hardware  
      to create a loop on the Token Ring module which isolates the ring  
      from the right hand side."  
      ::= { tokGroupEntry 4 }  
        
tokGroupManLeftLoop OBJECT-TYPE  
      SYNTAX  INTEGER {  
	on(1),  
	off(2),  
	notSupported(255)  
      }  
      ACCESS  read-write  
      STATUS  mandatory  
      DESCRIPTION  
      "Setting this attribute to ON signifies a command to the hardware  
      to create a loop on the Token Ring module which isolates the ring  
      from the left hand side."  
      ::= { tokGroupEntry 5 }  
        
tokGroupRightNeighbor OBJECT-TYPE  
      SYNTAX  INTEGER {  
	   exist(1),  
	   notExist(2)  
      }  
      ACCESS  read-only  
      STATUS  mandatory  
      DESCRIPTION  
      "Attribute defining the existence of a neighbor another token ring  
      group on the right hand side of the module."  
      ::= { tokGroupEntry 6 }  
        
tokGroupLeftNeighbor OBJECT-TYPE  
      SYNTAX  INTEGER {  
	   exist(1),  
	   notExist(2)  
      }  
      ACCESS  read-only  
      STATUS  mandatory  
      DESCRIPTION  
      "Attribute defining the existence of a neighbor another token ring  
      group on the left hand side of the module."  
      ::= { tokGroupEntry 7 }  
        
tokGroupIOMode OBJECT-TYPE  
      SYNTAX  INTEGER {  
		single(1),  
		dualRingIn(2),  
		dualRingOut(3),  
		illegalMode(4),  
		lobe(5),  
		intRepeater(6),  
		star(7),  
		notSupported(255)  
      }  
      ACCESS  read-write  
      STATUS  mandatory  
      DESCRIPTION  
      "Attribute defining the I/O mode (single, dual-ring-in, dual-ring-out)  
      Lobe, Internal Repeater or Star) of a module from the the LTR-IO family."  
      ::= { tokGroupEntry 8 }  
        
tokGroupBridgeMode OBJECT-TYPE  
      SYNTAX  INTEGER {  
		modeA(1),  
		modeB(2),  
		modeC(3),  
		notSupported(255)  
      }  
      ACCESS  read-write  
      STATUS  mandatory  
      DESCRIPTION  
      "Attribute describing the operational mode of the bridge.  
       For ITLB the following modes are defined:  
       - Mode A: First channel connected to an external ring (RI,RO connectors)  
		 and second channel connected to an internal ring;  
       - Mode B: First channel connected to an external ring by a DTE connector  
		 and second channel connected to an internal ring;  
       - Mode C: First channel connected to an internal left ring and second  
		 channel connected to an internal right ring."  
      ::= { tokGroupEntry 9 }  
  
tokGroupManLinkLoop OBJECT-TYPE  
      SYNTAX  INTEGER {  
	on(1),  
	off(2),  
	notSupported(255)  
      }  
      ACCESS  read-write  
      STATUS  mandatory  
      DESCRIPTION  
      "Setting the value of this attribute to ON instructs the  
      hardware of a FIBRONICS Token Ring repeater module to close the loop in the  
      direction of the external connection."  
      ::= { tokGroupEntry 10 }  
        
tokGroupManBusLoop OBJECT-TYPE  
      SYNTAX  INTEGER {  
	on(1),  
	off(2),  
	notSupported(255)  
      }  
      ACCESS  read-write  
      STATUS  mandatory  
      DESCRIPTION  
      "Setting the value of this attribute to ON instructs the  
      hardware of a FIBRONICS Token Ring repeater module to close the loop in the  
      direction of the internal bus."  
      ::= { tokGroupEntry 11 }  
        
tokGroupAutoLinkLoop OBJECT-TYPE  
      SYNTAX  INTEGER {  
	on(1),  
	off(2),  
	notSupported(255)  
      }  
      ACCESS  read-only  
      STATUS  mandatory  
      DESCRIPTION  
      "Value ON of this attribute signifies that a hardware loop has been auto-  
      matically closed by the hardwar of the FIBRONICS Token Ring repeater  
      as a result of problems on the external link."  
      ::= { tokGroupEntry 12 }  
        
tokGroupAutoBusLoop OBJECT-TYPE  
      SYNTAX  INTEGER {  
	on(1),  
	off(2),  
	notSupported(255)  
      }  
      ACCESS  read-only  
      STATUS  mandatory  
      DESCRIPTION  
      "Value ON of this attribute signifies that a hardware loop has been auto-  
      matically closed by the hardware of the FIBRONICS Token Ring repeater  
      as a result of problems on the internal bus."  
      ::= { tokGroupEntry 13 }  
  
tokGroupSpecificOID OBJECT-TYPE  
	SYNTAX OBJECT IDENTIFIER  
	ACCESS read-only  
	STATUS mandatory  
	DESCRIPTION  
	"This attribute provides the OID of another group containing   
	additional more specific information regarding this instance."  
	::= { tokGroupEntry 14 }  
  
  
  
tokGroupRingTable OBJECT-TYPE  
      SYNTAX  SEQUENCE OF TokGroupRingEntry  
      ACCESS  not-accessible  
      STATUS mandatory  
DESCRIPTION ""
      ::= { tokGroup 2 }  
   
tokGroupRingEntry OBJECT-TYPE  
      SYNTAX    TokGroupRingEntry  
      ACCESS    not-accessible  
      STATUS    mandatory  
DESCRIPTION ""
      INDEX     { tokGroupRingGroupId, tokGroupRingId }  
      ::= { tokGroupRingTable 1 }  
   
TokGroupRingEntry ::=  
      SEQUENCE {  
	 tokGroupRingGroupId  
	    INTEGER,  
	 tokGroupRingId  
	    INTEGER,  
	 tokGroupRingSpeed  
	    INTEGER,  
	 tokGroupRingInserted  
	    INTEGER  
      }  
  
tokGroupRingGroupId OBJECT-TYPE  
      SYNTAX  INTEGER (1..255)  
      ACCESS  read-only  
      STATUS  mandatory  
      DESCRIPTION  
      "ID of the group to which the ring belongs."  
      ::= { tokGroupRingEntry 1 }  
        
tokGroupRingId OBJECT-TYPE  
      SYNTAX  INTEGER (1..255)  
      ACCESS  read-only  
      STATUS  mandatory  
      DESCRIPTION  
      "ID of the ring."  
      ::= { tokGroupRingEntry 2 }  
        
tokGroupRingSpeed OBJECT-TYPE  
      SYNTAX  INTEGER {  
		unknown(1),  
		oneMegabit(2),  
		fourMegabit(3),  
		sixteenMegabit(4),  
		sixteenMgbEarly(5) -- for iftc/istc cards  
      }  
      ACCESS  read-write  
      STATUS  mandatory  
      DESCRIPTION  
      "Attribute describing the bandwidth of the ring."  
      ::= { tokGroupRingEntry 3 }  
        
tokGroupRingInserted OBJECT-TYPE  
      SYNTAX  INTEGER {  
		notInserted(1),  
		inserted(2)  
      }  
      ACCESS  read-only  
      STATUS  mandatory  
      DESCRIPTION  
      "Indicates that the bridge interface has inserted itself into  
      the ring."  
      ::= { tokGroupRingEntry 4 }  
        
  
  
tokPort OBJECT IDENTIFIER  
      ::= {tok 3}  
  
  
tokPortTable OBJECT-TYPE  
      SYNTAX  SEQUENCE OF TokPortEntry  
      ACCESS  not-accessible  
      STATUS mandatory  
DESCRIPTION ""
      ::= { tokPort 1 }  
   
tokPortEntry OBJECT-TYPE  
      SYNTAX    TokPortEntry  
      ACCESS    not-accessible  
      STATUS    mandatory  
DESCRIPTION ""
      INDEX     { tokPortGroupId, tokPortId }  
      ::= { tokPortTable 1 }  
   
TokPortEntry ::=  
      SEQUENCE {  
	 tokPortGroupId  
	    INTEGER,  
	 tokPortId  
	    INTEGER,  
	 tokPortBypass  
	    INTEGER,  
	 tokPortConnected  
	    INTEGER,  
	 tokPortTCP  
	    INTEGER,  
	 tokPortCableFault  
	    INTEGER,  
	 tokPortFunctionalStatus  
	    INTEGER,  
	 tokPortLastSourceAddr  
	    OCTET STRING,  
	 tokPortSpecificOID  
	    OBJECT IDENTIFIER,  
	 tokPortRingSpeedError  
	    INTEGER  
      }  
  
tokPortGroupId OBJECT-TYPE  
      SYNTAX  INTEGER (1..255)  
      ACCESS  read-only  
      STATUS  mandatory  
      DESCRIPTION  
      "ID of the group to which the token ring port belongs."  
      ::= { tokPortEntry 1 }  
        
tokPortId OBJECT-TYPE  
      SYNTAX  INTEGER (1..255)  
      ACCESS  read-only  
      STATUS  mandatory  
      DESCRIPTION  
      "ID of the port in the tokPortTable."  
      ::= { tokPortEntry 2 }  
        
tokPortBypass OBJECT-TYPE  
      SYNTAX  INTEGER {  
	  on(1),  
	  off(2),  
	  notSupported(255)  
      }  
      ACCESS  read-write  
      STATUS  mandatory  
      DESCRIPTION  
      "Setting the value of this attribute to ON causes the by-  
      passing of the TokenRing FIBRONICS port."  
      ::= { tokPortEntry 3 }  
        
tokPortConnected OBJECT-TYPE  
      SYNTAX  INTEGER {  
	  connected(1),  
	  notConnected(2),  
	  notSupported(255)  
      }  
      ACCESS  read-only  
      STATUS  mandatory  
      DESCRIPTION  
      "Attribute which describes the connection status of a Token Ring port   
      (inclusion of the Token Ring controller in the ring)."  
      ::= { tokPortEntry 4 }  
        
tokPortTCP OBJECT-TYPE  
      SYNTAX  INTEGER {  
	  on(1),  
	  off(2),  
	  notSupported(255)  
      }  
      ACCESS  read-write  
      STATUS  mandatory  
      DESCRIPTION  
      "Setting the value of this attribute to ON causes the activation of the  
      cable-fault detection mechanism."  
      ::= { tokPortEntry 5 }  
        
tokPortCableFault OBJECT-TYPE  
      SYNTAX  INTEGER {  
	 on(1),  
	 off(2),  
	 notSupported(255)  
      }  
      ACCESS  read-only  
      STATUS  mandatory  
      DESCRIPTION  
      "Value ON of this attribute signifies the detection of a cable-fault on  
      this specific Token Ring port."  
      ::= { tokPortEntry 6 }  
        
tokPortFunctionalStatus OBJECT-TYPE  
      SYNTAX  INTEGER {  
	ok(1),  
	rld(2),            -- RxLinkDown  
	tld(4),            -- TxLinkDown  
	notSupported(255)  
      }  
      ACCESS  read-only  
      STATUS  mandatory  
      DESCRIPTION  
      "The value of this attribute reflects the functional status of FIBRONICS  
      Token Ring ports. Note that it is not mandatory that a certain port  
      support all the enumerated states. Here is the lest of the possible  
      states:  
      OK - fully functional port, transmitting and receiving packets.  
      RLD - receive link down condition on the port.  
      TLD - transmit link down condition on the port."  
      ::= { tokPortEntry 7 }  
  
tokPortLastSourceAddr OBJECT-TYPE  
      SYNTAX  OCTET STRING  
      ACCESS  read-only  
      STATUS  mandatory  
      DESCRIPTION  
      "MAC source address of the last readable frame received by this  
      port."  
      ::= { tokPortEntry 8 }  
  
tokPortSpecificOID OBJECT-TYPE  
	SYNTAX OBJECT IDENTIFIER  
	ACCESS read-only  
	STATUS mandatory  
	DESCRIPTION  
	"This attribute provides the OID of another group containing   
	additional more specific information regarding this instance."  
	::= { tokPortEntry 9 }  
  
tokPortRingSpeedError OBJECT-TYPE  
	SYNTAX  INTEGER { on(1), off(2), notSupported(255) }  
	ACCESS  read-only  
	STATUS  mandatory  
	DESCRIPTION  
	" This attribute is set to 'on' when the station tries to enter  
	the ring with the speed different from the ring's one."  
	::= { tokPortEntry 10 }  
  
  
tsGroup OBJECT IDENTIFIER        
      ::= {ts 1}  
  
  
tsGroupTable OBJECT-TYPE  
      SYNTAX  SEQUENCE OF TsGroupEntry  
      ACCESS  not-accessible  
      STATUS mandatory  
DESCRIPTION ""
      ::= {tsGroup 1}  
   
tsGroupEntry OBJECT-TYPE  
      SYNTAX    TsGroupEntry  
      ACCESS    not-accessible  
      STATUS    mandatory  
DESCRIPTION ""
      INDEX     { tsGroupId }  
      ::= { tsGroupTable 1 }  
   
TsGroupEntry ::=  
      SEQUENCE {  
	 tsGroupId  
	    INTEGER,  
	 tsGroupLATStatus  
	    INTEGER,  
	 tsGroupOperationMode  
	    INTEGER  
      }  
  
tsGroupId OBJECT-TYPE  
      SYNTAX  INTEGER (1..255)  
      ACCESS  read-only  
      STATUS  mandatory  
      DESCRIPTION  
      "Number of the slot in which the group is installed."  
      ::= { tsGroupEntry 1 }  
        
tsGroupLATStatus OBJECT-TYPE  
      SYNTAX  INTEGER {  
	on(1),  
	off(2)  
	}  
      ACCESS read-only  
      STATUS mandatory  
      DESCRIPTION  
      "Value ON of this attribute means that LAT protocol is Enabled on the  
      FIBRONICS Ethernet module."  
      ::= { tsGroupEntry 2 }  
        
tsGroupOperationMode OBJECT-TYPE  
      SYNTAX  INTEGER {  
	      diagnostics(1),  
	      diagnosticsFailure(2),  
	      loading(3),  
	      loadingFailure(4),  
	      operational(5)  
      }  
      ACCESS  read-only  
      STATUS  mandatory  
      DESCRIPTION  
      "This attribute describes the operation mode of the module in a  
      multiprocessor configuration sensor, as reported by interprocessors  
      communication."  
      ::= { tsGroupEntry 3 }  
        
  
ltalkPort OBJECT IDENTIFIER  
      ::= {ltalk 1}  
  
  
ltalkPortTable OBJECT-TYPE  
      SYNTAX  SEQUENCE OF LtalkPortEntry  
      ACCESS  not-accessible  
      STATUS mandatory  
DESCRIPTION ""
      ::= {ltalkPort 1}  
   
ltalkPortEntry OBJECT-TYPE  
      SYNTAX    LtalkPortEntry  
      ACCESS    not-accessible  
      STATUS    mandatory  
DESCRIPTION ""
      INDEX     { ltalkPortGroupId, ltalkPortId }  
      ::= { ltalkPortTable 1 }  
   
LtalkPortEntry ::=  
      SEQUENCE {  
	 ltalkPortGroupId  
	    INTEGER,  
	 ltalkPortId  
	    INTEGER,  
	 ltalkPortTest  
	    INTEGER,  
	 ltalkPortTestResult  
	    INTEGER,  
	 ltalkPortJam  
	    INTEGER  
      }  
  
ltalkPortGroupId OBJECT-TYPE  
      SYNTAX  INTEGER (1..255)  
      ACCESS  read-only  
      STATUS  mandatory  
      DESCRIPTION  
      "Number of the group to which the port belongs."  
      ::= { ltalkPortEntry 1 }  
        
ltalkPortId OBJECT-TYPE  
      SYNTAX  INTEGER (1..255)  
      ACCESS  read-only  
      STATUS  mandatory  
      DESCRIPTION  
      "ID of the port in the ltalkPortTable."  
      ::= { ltalkPortEntry 2 }  
        
ltalkPortTest OBJECT-TYPE  
      SYNTAX  INTEGER {  
	on(1),  
	off(2)  
      }  
      ACCESS  read-write  
      STATUS  mandatory  
      DESCRIPTION  
      "A value ON of this attribute indicates that a port test should be  
      performed upon the port defined by the attribute instance."  
      ::= { ltalkPortEntry 3 }  
        
ltalkPortTestResult OBJECT-TYPE  
      SYNTAX  INTEGER {  
	ok(1),  
	faulty(2)  
      }  
      ACCESS  read-only  
      STATUS  mandatory  
      DESCRIPTION  
      "Indicates the result of a port test performed on this port."  
      ::= { ltalkPortEntry 4 }  
        
ltalkPortJam OBJECT-TYPE  
      SYNTAX  INTEGER {  
	on(1),  
	off(2)  
      }  
      ACCESS  read-only  
      STATUS  mandatory  
      DESCRIPTION  
      "An ON value of this attribute indicates a Jam error on the specific  
      port."  
      ::= { ltalkPortEntry 5 }  
        
  
clGroup OBJECT IDENTIFIER        
      ::= {cl 1}  
  
  
clGroupTable OBJECT-TYPE  
      SYNTAX  SEQUENCE OF ClGroupEntry  
      ACCESS  not-accessible  
      STATUS mandatory  
DESCRIPTION ""
      ::= {clGroup 1}  
   
clGroupEntry OBJECT-TYPE  
      SYNTAX    ClGroupEntry  
      ACCESS    not-accessible  
      STATUS    mandatory  
DESCRIPTION ""
      INDEX     { clGroupId }  
      ::= { clGroupTable 1 }  
   
ClGroupEntry ::=  
      SEQUENCE {  
	 clGroupId  
	    INTEGER,  
	 clGroupClockRedundancy  
	    INTEGER,  
	 clGroupMainClock  
	    INTEGER,  
	 clGroupTestClocks  
	    INTEGER  
      }  
  
clGroupId OBJECT-TYPE  
      SYNTAX  INTEGER (1..255)  
      ACCESS  read-only  
      STATUS  mandatory  
      DESCRIPTION  
      "Number of the slot in which the group is installed."  
      ::= { clGroupEntry 1 }  
        
clGroupClockRedundancy OBJECT-TYPE  
      SYNTAX  INTEGER {  
	on(1),  
	off(2)  
	}  
      ACCESS read-write  
      STATUS mandatory  
      DESCRIPTION  
      "Value ON of this attribute defines a redundancy (backup) relationship  
      between the internal and external clocks on the LCL100 module."  
      ::= { clGroupEntry 2 }  
        
clGroupMainClock OBJECT-TYPE  
      SYNTAX  INTEGER  
      ACCESS  read-write  
      STATUS  mandatory  
      DESCRIPTION  
      "Value of this attribute is an index into clPortTable, and defines the   
      clock that should operate or a main clock in redundancy scheme.  
      Serves as 'Clock selection' switch on the card."  
      ::= { clGroupEntry 3 }  
        
clGroupTestClocks OBJECT-TYPE  
      SYNTAX  INTEGER {  
	on(1),  
	off(2)  
      }  
      ACCESS  read-write  
      STATUS  mandatory  
      DESCRIPTION  
      "A value ON of this attribute indicates that a test should be  
      performed on all clock ports."  
      ::= { clGroupEntry 4 }  
        
  
clPort OBJECT IDENTIFIER        
      ::= {cl 2}  
  
  
clPortTable OBJECT-TYPE  
      SYNTAX  SEQUENCE OF ClPortEntry  
      ACCESS  not-accessible  
      STATUS mandatory  
DESCRIPTION ""
      ::= {clPort 1}  
   
clPortEntry OBJECT-TYPE  
      SYNTAX    ClPortEntry  
      ACCESS    not-accessible  
      STATUS    mandatory  
DESCRIPTION ""
      INDEX     { clPortGroupId, clPortId }  
      ::= { clPortTable 1 }  
   
ClPortEntry ::=  
      SEQUENCE {  
	 clPortGroupId  
	    INTEGER,  
	 clPortId  
	    INTEGER,  
	 clPortFunctionalStatus  
	    INTEGER  
      }  
  
clPortGroupId OBJECT-TYPE  
      SYNTAX  INTEGER (1..255)  
      ACCESS  read-only  
      STATUS  mandatory  
      DESCRIPTION  
      "Number of the group to which the port belongs."  
      ::= { clPortEntry 1 }  
        
clPortId OBJECT-TYPE  
      SYNTAX  INTEGER (1..255)  
      ACCESS  read-only  
      STATUS  mandatory  
      DESCRIPTION  
      "ID of the port in the clPortTable."  
      ::= { clPortEntry 2 }  
        
clPortFunctionalStatus OBJECT-TYPE  
      SYNTAX  INTEGER {  
	ok(1),  
	faulty(2)  
      }  
      ACCESS  read-only  
      STATUS  mandatory  
      DESCRIPTION  
      "Indicates whether the clock is faulty or not."  
      ::= { clPortEntry 3 }  
        
  
lBoxOID  OBJECT IDENTIFIER        
      ::= { fbrOID 1 }  
        
-- Implementation of this group is mandatory for all FIBRONICS Hub Agents  
-- It defines OIDs which allow box identification.  
  
lUnknownBoxOID  OBJECT IDENTIFIER ::= { lBoxOID 1 }  
lLET18BoxOID  OBJECT IDENTIFIER ::= { lBoxOID 2 }  
lLET3BoxOID  OBJECT IDENTIFIER ::= { lBoxOID 3 }  
lLET36BoxOID  OBJECT IDENTIFIER ::= { lBoxOID 4 }  
lLET18EBoxOID  OBJECT IDENTIFIER ::= { lBoxOID 5 }  
lLERT40BoxOID  OBJECT IDENTIFIER ::= { lBoxOID 6 }  
lLET10BoxOID  OBJECT IDENTIFIER ::= { lBoxOID 7 }  
lFDX100BoxOID  OBJECT IDENTIFIER ::= { lBoxOID 8 }  
lSTACKBoxOID  OBJECT IDENTIFIER ::= { lBoxOID 9 }  
  
  
--      Agent 6.0  
  
iwb OBJECT IDENTIFIER ::= { bRouter 1 }  --mandatory for the integrated LAN/WAN bridges   
iwr OBJECT IDENTIFIER ::= { bRouter 2 }   --mandatory for the integrated LAN/WAN routers  
itr OBJECT IDENTIFIER ::= { bRouter 3 }     --mandatory for the integrated LAN/WAN extenders  
  
iwrGroupTable OBJECT-TYPE  
	SYNTAX  SEQUENCE OF IwrGroupEntry  
	ACCESS  not-accessible  
	STATUS  mandatory  
	DESCRIPTION  
	"Attributes pertaining to the module."  
	::= { iwr 1 }  
  
iwrGroupEntry OBJECT-TYPE  
	SYNTAX  IwrGroupEntry  
	ACCESS  not-accessible  
	STATUS  mandatory  
	DESCRIPTION  
	"An entry in the table."  
	INDEX   { iwrGroupId }  
	::= { iwrGroupTable 1 }  
  
IwrGroupEntry ::=  
	SEQUENCE {  
	    iwrGroupId  
		INTEGER,  
	    iwrOperState  
		INTEGER,  
	    iwrPMState  
		INTEGER,  
	    iwrIOMState  
		INTEGER  
	    }  
  
iwrGroupId OBJECT-TYPE  
	SYNTAX  INTEGER  
	ACCESS  read-only  
	STATUS  mandatory  
	DESCRIPTION  
	"Slot number in which the module is located."  
	::= { iwrGroupEntry 1 }  
  
iwrOperState OBJECT-TYPE  
	SYNTAX  INTEGER { run(1), boot(2), fail(3) }  
	ACCESS  read-only  
	STATUS  mandatory  
	DESCRIPTION  
	"One of the possible states of the module."  
	::= { iwrGroupEntry 2 }  
  
iwrPMState OBJECT-TYPE  
	SYNTAX  INTEGER { ok(1), fail(2) }  
	ACCESS  read-only  
	STATUS  mandatory  
	DESCRIPTION  
	"The state of the Processor Module."  
	::= { iwrGroupEntry 3 }  
  
iwrIOMState OBJECT-TYPE  
	SYNTAX  INTEGER { ok(1), fail(2) }  
	ACCESS  read-only  
	STATUS  mandatory  
	DESCRIPTION  
	"The state of the Input/Output Module."  
	::= { iwrGroupEntry 4 }  
  
iwrWANTable OBJECT-TYPE  
	SYNTAX  SEQUENCE OF IwrWANEntry  
	ACCESS  not-accessible  
	STATUS  mandatory  
	DESCRIPTION  
	"WAN data table."  
	::= { iwr 2 }  
  
iwrWANEntry OBJECT-TYPE  
	SYNTAX  IwrWANEntry  
	ACCESS  not-accessible  
	STATUS  mandatory  
	DESCRIPTION  
	"Entry in the table."  
	INDEX           { iwrWANGroupId, iwrWANPortId }  
	::= { iwrWANTable 1 }  
  
IwrWANEntry ::=  
	SEQUENCE {  
	     iwrWANGroupId  
		INTEGER,  
	     iwrWANPortId  
		INTEGER,  
	     iwrWANConnection  
		INTEGER,  
	     iwrWANPortCableType  
		INTEGER  
	}  
  
  
iwrWANGroupId OBJECT-TYPE  
	SYNTAX  INTEGER  
	ACCESS  read-only  
	STATUS  mandatory  
	DESCRIPTION  
	"Slot number in which the module is located."  
	::= { iwrWANEntry 1 }  
  
iwrWANPortId OBJECT-TYPE  
	SYNTAX  INTEGER  
	ACCESS  read-only  
	STATUS  mandatory  
	DESCRIPTION  
	"WAN port index."  
	::= { iwrWANEntry 2 }  
  
iwrWANConnection OBJECT-TYPE  
	SYNTAX  INTEGER { connected(1), disconnected(2) }  
	ACCESS  read-only  
	STATUS  mandatory  
	DESCRIPTION  
	"WAN connection status."  
	::= { iwrWANEntry 3 }  
  
iwrWANPortCableType OBJECT-TYPE  
	SYNTAX  INTEGER { x21(1), rs232(2), v35(3) }  
	ACCESS  read-only  
	STATUS  mandatory  
	DESCRIPTION  
	"Cable type connected to the specified WAN port."  
	::= { iwrWANEntry 4 }  
  
  
itrGroupTable OBJECT-TYPE  
	SYNTAX  SEQUENCE OF ItrGroupEntry  
	ACCESS  not-accessible  
	STATUS  mandatory  
	DESCRIPTION  
	"Table of attributes pertaining to the ITRE module."  
	::= { itr 1 }  
  
itrGroupEntry OBJECT-TYPE  
	SYNTAX  ItrGroupEntry  
	ACCESS  not-accessible  
	STATUS  mandatory  
	DESCRIPTION  
	"An entry in the table."  
	INDEX   { itrGroupId }  
	::= { itrGroupTable 1 }  
  
ItrGroupEntry ::=  
	SEQUENCE {  
	     itrGroupId  
		INTEGER,  
	     itrMainSWVersion  
		DisplayString,  
	     itrConfigState  
		INTEGER,  
	     itrModuleState  
		INTEGER  
	     }  
  
itrGroupId OBJECT-TYPE  
	SYNTAX  INTEGER  
	ACCESS  read-only  
	STATUS  mandatory  
	DESCRIPTION  
	"Slot number in which the module is located."  
	::= { itrGroupEntry 1 }  
  
itrMainSWVersion OBJECT-TYPE  
	SYNTAX  DisplayString  
	ACCESS  read-only  
	STATUS  mandatory  
	DESCRIPTION  
	"Software version of the main CPU."  
	::= { itrGroupEntry 2 }  
  
itrConfigState OBJECT-TYPE  
	SYNTAX  INTEGER { local(1), remote(2), notSupported(255) }  
	ACCESS  read-only  
	STATUS  mandatory  
	DESCRIPTION  
	"Configuration state of the module."  
	::= { itrGroupEntry 3 }  
  
itrModuleState OBJECT-TYPE  
	SYNTAX  INTEGER { oper(1), load(2), setup(3), notSupported(255) }  
	ACCESS  read-only  
	STATUS  mandatory  
	DESCRIPTION  
	"State of the ISTC/IFTC modules."  
	::= { itrGroupEntry 4 }  
  
  
itrLinkTable OBJECT-TYPE  
	SYNTAX  SEQUENCE OF ItrLinkEntry  
	ACCESS  not-accessible  
	STATUS  mandatory  
	DESCRIPTION  
	"ITRE links table."  
	::= { itr 2 }  
  
itrLinkEntry OBJECT-TYPE  
	SYNTAX  ItrLinkEntry  
	ACCESS  not-accessible  
	STATUS  mandatory  
	DESCRIPTION  
	"Entry in the table."  
	INDEX           { itrLinkGroupId, itrLinkPortId }  
	::= { itrLinkTable 1 }  
  
ItrLinkEntry ::=  
	SEQUENCE {  
	     itrLinkGroupId  
		INTEGER,  
	     itrLinkPortId  
		INTEGER,  
	      itrLinkIf  
		INTEGER,  
	      itrLinkMode  
		INTEGER,  
	      itrLinkAsyncRate  
		INTEGER,  
	      itrLinkSyncRate  
		INTEGER,  
	      itrLinkParity  
		INTEGER,  
	      itrLinkParityEvenOdd  
		INTEGER,  
	      itrLinkStopBit  
		INTEGER,  
	      itrLinkRemoteLANConn  
		INTEGER,  
	      itrLinkFunctionalStatus  
		INTEGER  
	}  
  
itrLinkGroupId OBJECT-TYPE  
	SYNTAX  INTEGER  
	ACCESS  read-only  
	STATUS  mandatory  
	DESCRIPTION  
	"Slot number in which the module is located."  
	::= { itrLinkEntry 1 }  
  
itrLinkPortId OBJECT-TYPE  
	SYNTAX  INTEGER  
	ACCESS  read-only  
	STATUS  mandatory  
	DESCRIPTION  
	"Link identifier."  
	::= { itrLinkEntry 2 }  
  
itrLinkIf OBJECT-TYPE  
	SYNTAX  INTEGER { v11(1), v24(2), v35(3), dte-dce(4) }  
	ACCESS  read-only  
	STATUS  mandatory  
	DESCRIPTION  
	"Interface type."  
	::= { itrLinkEntry 3 }  
  
itrLinkMode OBJECT-TYPE  
	SYNTAX  INTEGER { sync(1), async(2) }  
	ACCESS  read-write  
	STATUS  mandatory  
	DESCRIPTION  
	"Synchronous or asynchronous modes on the link."  
	::= { itrLinkEntry 4 }  
  
itrLinkAsyncRate OBJECT-TYPE  
	SYNTAX  INTEGER { r2400(1), r4800(2), r9600(3),  
			r14400(4), r19200(5), r38400(6), r56000(7),  
			r57600(8), r64000(9), r112000(10), unknown(255) }  
	ACCESS  read-write  
	STATUS  mandatory  
	DESCRIPTION  
	"Possible link speeds that can be set in asynchronous mode."  
	::= { itrLinkEntry 5 }  
  
itrLinkSyncRate OBJECT-TYPE  
	SYNTAX  INTEGER {  
				r1200(1), r2400(2), r4800(3),  
				r9600(4), r14400(5), r19200(6),  
				r38400(7), r48000(8), r56000(9),  
				r57600(10), r64000(11), r112000(12),  
				r128000(13), r256000(14), r384000(15),  
				r512000(16), r786000(17), r1024000(18),  
				r1544000(19), r2048000(20), unknown(255) }  
	ACCESS  read-only  
	STATUS  mandatory  
	DESCRIPTION  
	"Link speeds in synchronous mode."  
	::= { itrLinkEntry 6 }  
  
itrLinkParity OBJECT-TYPE  
	SYNTAX  INTEGER { on(1), off(2), notSupported(255) }  
	ACCESS  read-write  
	STATUS  mandatory  
	DESCRIPTION  
	"This attribute enables/disables parity checking."  
	::= { itrLinkEntry 7 }  
  
itrLinkParityEvenOdd OBJECT-TYPE  
	SYNTAX  INTEGER { even(1), odd(2), notSupported(255) }  
	ACCESS  read-write  
	STATUS  mandatory  
	DESCRIPTION  
	"Even or odd parity."  
	::= { itrLinkEntry 8 }  
  
itrLinkStopBit OBJECT-TYPE  
	SYNTAX  INTEGER { one(1), two(2), none(3), notSupported(255) }  
	ACCESS  read-write  
	STATUS  mandatory  
	DESCRIPTION  
	"Number of stop bits (1 or 2 ) in asynchronous mode. The value 'none'  
	is returned in synchronous mode."  
	::= { itrLinkEntry 9 }  
  
itrLinkRemoteLANConn OBJECT-TYPE  
	SYNTAX  INTEGER { connected(1), disconnected(2), notSupported(255) }  
	ACCESS  read-only  
	STATUS  mandatory  
	DESCRIPTION  
	"This attribute shows whether the remote ITRE is connected to the LAN."  
	::= { itrLinkEntry 10 }  
  
itrLinkFunctionalStatus OBJECT-TYPE  
	SYNTAX  INTEGER { ok(1), fail(2), noRxClk(3) }  
	ACCESS  read-only  
	STATUS  mandatory  
	DESCRIPTION  
	"The attribute represents the status of the WAN link."  
	::= { itrLinkEntry 11 }  
  
  
--      Agent 6.0  
  
lse OBJECT IDENTIFIER ::= { fbrLanSwitch 1 }    --mandatory for LANswitch modules  
-- lhs  OBJECT IDENTIFIER ::= { fbrLanSwitch 2 }  
  
  
lseGroupTable OBJECT-TYPE  
      SYNTAX  SEQUENCE OF LseGroupEntry  
      ACCESS  not-accessible  
      STATUS  mandatory  
DESCRIPTION ""
      ::= { lse 1 }  
  
lseGroupEntry OBJECT-TYPE  
      SYNTAX  LseGroupEntry  
      ACCESS  not-accessible  
      STATUS  mandatory  
DESCRIPTION ""
      INDEX  { lseGroupId }  
      ::= { lseGroupTable 1 }  
  
LseGroupEntry  ::=  
      SEQUENCE  {  
	lseGroupId  
	  INTEGER,  
	lseGroupFastOpen  
	  INTEGER,  
	lseGroup10MSqlt  
	  INTEGER,  
	lseGroupSmartSqlt  
	  INTEGER,  
	lseGroupCParameter  
	  INTEGER,  
	lseGroupIPGJamLength  
	  INTEGER,  
	lseGroupJamLength  
	  INTEGER,  
	lseGroupDataBlinderLength  
	  INTEGER,  
	lseGroupIPGDataLength  
	  INTEGER,  
	lseGroupActiveMonitor   
	  INTEGER,  
	lseGroupBackBone  
	  INTEGER,  
	lseGroupSetDefaults  
	  INTEGER  
      }  
			   
lseGroupId OBJECT-TYPE  
      SYNTAX  INTEGER   
      ACCESS  read-only  
      STATUS  mandatory  
      DESCRIPTION  
      "Slot number in which the group is installed."  
      ::= { lseGroupEntry 1 }  
        
lseGroupFastOpen OBJECT-TYPE  
      SYNTAX  INTEGER {  
	on(1),  
	off(2),  
	notSupported(255)  
	}  
      ACCESS read-write  
      STATUS mandatory  
      DESCRIPTION  
      "Setting the value of this attribute to ON activates the port for short idle time  
      when code violation was detected."  
      ::= { lseGroupEntry 2 }  
  
lseGroup10MSqlt OBJECT-TYPE  
      SYNTAX  INTEGER {  
	on(1),  
	off(2),  
	notSupported(255)  
	}  
      ACCESS read-write  
      STATUS mandatory  
      DESCRIPTION  
      "Setting the value of this attribute to ON activates the mechanism of detection  
      preamble of 10Mhz."  
      ::= { lseGroupEntry 3 }  
  
lseGroupSmartSqlt OBJECT-TYPE  
      SYNTAX  INTEGER {  
	on(1),  
	off(2),  
	notSupported(255)  
	}  
      ACCESS read-write  
      STATUS mandatory  
      DESCRIPTION  
      "Control the mechnism of the input sensitivity of the port."  
      ::= { lseGroupEntry 4 }  
  
lseGroupCParameter OBJECT-TYPE  
     SYNTAX  INTEGER  (1..8)  
     ACCESS read-write  
     STATUS mandatory  
     DESCRIPTION  
     "Defines the number of consecutive collisions the port waits before it ceases transmitting  
     of 512 bits time toward the station."  
      ::= { lseGroupEntry 5 }  
  
lseGroupIPGJamLength OBJECT-TYPE  
      SYNTAX  INTEGER (16..112)  
      ACCESS read-write  
      STATUS mandatory  
      DESCRIPTION  
"Defines the IPG jam length in Ethernet bit time (100nS) start at 16 bit time in steps of 16 to 112 bit   
time. Any number between the defined values will take to nearest smaller value."  
      ::= { lseGroupEntry 6 }  
  
lseGroupJamLength OBJECT-TYPE  
      SYNTAX  INTEGER (8..120)  
      ACCESS read-write  
      STATUS mandatory  
      DESCRIPTION  
"Defines the Jam Length in time start from 8 (800micro-seconds) to 120 (12mili-seconds).   
Each step of 8 is equal 800micro-seconds."  
      ::= { lseGroupEntry 7 }  
  
lseGroupDataBlinderLength OBJECT-TYPE  
      SYNTAX  INTEGER (48..120)  
      ACCESS read-write  
      STATUS mandatory  
      DESCRIPTION  
"Defines the Data Blinder Length in Ethernet bit time (100nS) start at 48 bit time in steps of   
8 to 120 bit time. Any number between the defined values will take to nearest smaller value"  
      ::= { lseGroupEntry 8 }  
  
lseGroupIPGDataLength OBJECT-TYPE  
      SYNTAX  INTEGER (48..120)  
      ACCESS read-write  
      STATUS mandatory  
      DESCRIPTION  
"Defines the IPG data length in Ethernet bit time (100nS) start at 48 bit time in steps of 8 to   
120 bit time. Any number between the defined values will take to nearest smaller value."  
      ::= { lseGroupEntry 9 }  
  
lseGroupActiveMonitor OBJECT-TYPE  
      SYNTAX  INTEGER {  
	on(1),  
	off(2),  
	notSupported(255)  
	}  
      ACCESS read-only  
      STATUS mandatory  
      DESCRIPTION  
      "This attribute defines the status of the module which is the high-speed bus active monitor."  
      ::= { lseGroupEntry 10 }  
  
lseGroupBackBone OBJECT-TYPE  
     SYNTAX  INTEGER {  
	on(1),  
	off(2),  
	notSupported(255)  
	}  
     ACCESS  read-write  
     STATUS  mandatory  
     DESCRIPTION  
     "The board is in the Backbone Mode.  
	lse208 - upper subgroup is RX only (ports 1-4) and lower subgroup is TX to line only.  
	lse808 - the first port is RX from line only, the second - TX to line only, the rest are in regular  
		10BaseT mode."  
     ::= { lseGroupEntry 11 }  
  
lseGroupSetDefaults OBJECT-TYPE  
    SYNTAX  INTEGER {  
	on(1),  
	off(2),  
	notSupported(255)  
	}  
   ACCESS  read-write  
   STATUS  mandatory  
   DESCRIPTION  
   "Set all hardware parameters to their default values."  
   ::= { lseGroupEntry 12 }  
  
  
lseIntPort OBJECT IDENTIFIER        
      ::= {lse 2}  
  
  
lseIntPortTable OBJECT-TYPE  
      SYNTAX  SEQUENCE OF LseIntPortEntry  
      ACCESS  not-accessible  
      STATUS  mandatory  
DESCRIPTION ""
      ::= { lseIntPort 1 }  
  
lseIntPortEntry OBJECT-TYPE  
      SYNTAX  LseIntPortEntry  
      ACCESS  not-accessible  
      STATUS  mandatory  
      DESCRIPTION  
      "An entry in the table, containing data about a single internal LanSwitch bank."  
      INDEX  { lseIntPortGroupId, lseIntPortId }  
      ::= { lseIntPortTable 1 }  
  
LseIntPortEntry  ::=  
      SEQUENCE  {  
	lseIntPortGroupId  
	  INTEGER,  
	lseIntPortId  
	  INTEGER,  
	lseIntPortIOMode  
	  INTEGER,  
	lseIntPortResetSwitchCAM  
	  INTEGER,  
	lseIntPortVideoPacket  
	  INTEGER,  
	lseIntPortPriorityStateMachine  
	  INTEGER,  
	lseIntPortActiveBroadcastPriority  
	  INTEGER,  
	lseIntPortPriorityLevel  
	  INTEGER,  
	lseIntPortSuperPriorityEnable  
	  INTEGER,  
	lseIntPortRoutingMode  
	  INTEGER,  
	lseIntPortGlobal  
	  INTEGER,  
	lseIntPortLearnIOCAM  
	  INTEGER,  
	lseIntPortSecurity  
	  INTEGER,  
	lseIntPortIgnoreBusy  
	  INTEGER,  
	lseIntPortRetryPriorityLevel1  
	  INTEGER,  
	lseIntPortRetryPriorityLevel2  
	  INTEGER,  
	lseIntPortRetryPriorityLevel3  
	  INTEGER,  
	lseIntPortIgnoreProtocolType  
	  INTEGER,  
	lseIntPortCompanyMAC   
	  OCTET STRING,  
	lseIntPortTxSafetyZone  
	  INTEGER,  
	lseIntPortRxSafetyZone  
	  INTEGER,  
	lseIntPortTxBurstLength  
	  INTEGER,  
	lseIntPortSecurityIntruder  
	  INTEGER,  
	lseIntPortJabber  
	  INTEGER,  
	lseIntPortCAM  
	  OCTET STRING,  
	lseIntPortVideoStateMachine  
	  INTEGER,  
	lseIntPortTransmitWeight  
	  INTEGER  
      }  
			   
lseIntPortGroupId OBJECT-TYPE  
      SYNTAX  INTEGER (1..255)  
      ACCESS  read-only  
      STATUS  mandatory  
      DESCRIPTION  
      "Id of the group to which the port belongs."  
      ::= { lseIntPortEntry 1 }  
  
lseIntPortId OBJECT-TYPE  
      SYNTAX  INTEGER (1..255)  
      ACCESS  read-only  
      STATUS  mandatory  
      DESCRIPTION  
      "Number of LanSwitch port in the board."  
      ::= { lseIntPortEntry 2 }  
        
lseIntPortIOMode OBJECT-TYPE  
      SYNTAX  INTEGER {  
	on(1),  
	off(2),  
	notSupported(255)  
	}  
      ACCESS read-write  
      STATUS mandatory  
      DESCRIPTION  
      "All packets on the high-speed bus that were not captured by any regular port are captured  
      by the I/O port."  
      ::= { lseIntPortEntry 3 }  
  
lseIntPortResetSwitchCAM OBJECT-TYPE  
      SYNTAX  INTEGER {  
	on(1),  
	off(2),  
	notSupported(255)  
	}  
      ACCESS read-write  
      STATUS mandatory  
      DESCRIPTION  
      "Acting like toggle switch thus always returns OFF"  
      ::= { lseIntPortEntry 4 }  
  
lseIntPortVideoPacket OBJECT-TYPE  
      SYNTAX  INTEGER {  
	on(1),  
	off(2),  
	notSupported(255)  
	}  
      ACCESS read-write  
      STATUS mandatory  
      DESCRIPTION  
      "Set all Tx packets toward the high-speed bus to video type packets."  
      ::= { lseIntPortEntry 5 }  
   
lseIntPortPriorityStateMachine OBJECT-TYPE  
      SYNTAX  INTEGER {  
	on(1),  
	off(2),  
	notSupported(255)  
	}  
      ACCESS read-write  
      STATUS mandatory  
      DESCRIPTION  
      "Setting the value of this attribute to ON activates the priority mechanism."  
      ::= { lseIntPortEntry 6 }  
  
lseIntPortActiveBroadcastPriority OBJECT-TYPE  
      SYNTAX  INTEGER {  
	on(1),  
	off(2),  
	notSupported(255)  
	}  
      ACCESS read-write  
      STATUS mandatory  
      DESCRIPTION  
      "Setting the value of this attribute to ON activates the active broadcast mode in priority  
      mechanism."  
      ::= { lseIntPortEntry 7 }  
  
lseIntPortPriorityLevel OBJECT-TYPE  
      SYNTAX  INTEGER {  
	broadcast(1),  
	multicast(2),  
	video(3),  
	regular(4),  
	default(5),  
	mngrTerminal(6),  
	notSupported(255)  
	}  
      ACCESS read-write  
      STATUS mandatory  
      DESCRIPTION  
      "This attribute defines the priority levels of Tx packets toward the high-speed bus.  
      The highest priority is broadcast."  
      ::= { lseIntPortEntry 8 }  
  
lseIntPortSuperPriorityEnable OBJECT-TYPE  
      SYNTAX  INTEGER {  
	on(1),  
	off(2),  
	notSupported(255)  
	}  
      ACCESS read-only  
      STATUS mandatory  
      DESCRIPTION  
      "The value ON defines the retry parameter for the priority level mechanism."  
      ::= { lseIntPortEntry 9 }  
  
lseIntPortRoutingMode OBJECT-TYPE  
      SYNTAX  INTEGER {  
	generic(1),  
	net(2),  
	dstPort(3),  
	notSupported(255)  
	}  
      ACCESS read-write  
      STATUS mandatory  
      DESCRIPTION  
      "Generic - examines all the packets that are not members of any virtual network.  
      Net - examines only the packets that have the port's network number."  
      ::= { lseIntPortEntry 10 }  
  
lseIntPortGlobal OBJECT-TYPE  
      SYNTAX  INTEGER {  
	on(1),  
	off(2),  
	notSupported(255)  
	}  
      ACCESS read-write  
      STATUS mandatory  
      DESCRIPTION  
      "Port in a network routing mode that examines all packets that are not members of all  
      virtual networks."  
      ::= { lseIntPortEntry 11 }  
  
lseIntPortLearnIOCAM OBJECT-TYPE  
      SYNTAX  INTEGER {  
	on(1),  
	off(2),  
	notSupported(255)  
	}  
      ACCESS read-write  
      STATUS mandatory  
      DESCRIPTION  
      "The ability of an I/O port to learn incoming MAC addresses received in its port and  
      store them in its CAM. The CAM is limited to total of  8 MAC addresses."  
      ::= { lseIntPortEntry 12 }  
  
lseIntPortSecurity OBJECT-TYPE  
      SYNTAX  INTEGER {  
	on(1),  
	off(2),  
	notSupported(255)  
	}  
      ACCESS read-write  
      STATUS mandatory  
      DESCRIPTION  
      "Setting the value of this attribute to ON activates the security mode."  
      ::= { lseIntPortEntry 13 }  
  
lseIntPortIgnoreBusy OBJECT-TYPE  
      SYNTAX  INTEGER {  
	on(1),  
	off(2),  
	notSupported(255)  
	}  
      ACCESS read-write  
      STATUS mandatory  
      DESCRIPTION  
      "Setting the value of this attribute to ON activates the ignore busy mode.  
      The busy signal toward the high-speed bus is not activated even though the TX buffer is full."  
      ::= { lseIntPortEntry 14 }  
  
lseIntPortRetryPriorityLevel1 OBJECT-TYPE  
      SYNTAX  INTEGER (1..32)  
      ACCESS read-write  
      STATUS mandatory  
      DESCRIPTION  
      "The port increases the priority level of the high-speed bus packets after the defined number  
      (1..32) trials."  
      ::= { lseIntPortEntry 15 }  
  
lseIntPortRetryPriorityLevel2 OBJECT-TYPE  
      SYNTAX  INTEGER (1..32)  
      ACCESS read-write  
      STATUS mandatory  
      DESCRIPTION  
      "The port increases the priority level of the high-speed bus packets after the defined number  
      (1..32) trials."  
      ::= { lseIntPortEntry 16 }  
  
lseIntPortRetryPriorityLevel3 OBJECT-TYPE  
      SYNTAX  INTEGER (1..32)  
      ACCESS read-write  
      STATUS mandatory  
      DESCRIPTION  
      "The port increases the priority level of the high-speed bus packets after the defined number  
      (1..32) trials."  
      ::= { lseIntPortEntry 17 }  
  
lseIntPortIgnoreProtocolType OBJECT-TYPE  
      SYNTAX  INTEGER {  
	ignore(1),  
	not-ignore(2),  
	notSupported(255)  
	}  
      ACCESS read-write  
      STATUS mandatory  
      DESCRIPTION  
      "Any packet regardless of thye protocol type is received from the high-speed bus."  
      ::= { lseIntPortEntry 18 }  
  
lseIntPortCompanyMAC  OBJECT-TYPE  
      SYNTAX  OCTET STRING  
      ACCESS read-write  
      STATUS mandatory  
      DESCRIPTION  
      "The attribute defines the first three bytes of the MAC address of the video host server."  
      ::= { lseIntPortEntry 19 }  
  
lseIntPortTxSafetyZone OBJECT-TYPE  
      SYNTAX   INTEGER (1..1024)  
      ACCESS read-write   
      STATUS mandatory  
      DESCRIPTION  
      "Defines the Tx Safety Zone in bits."  
      ::= { lseIntPortEntry 20 }  
  
lseIntPortRxSafetyZone OBJECT-TYPE  
      SYNTAX  INTEGER (1..1024)  
      ACCESS read-write  
      STATUS mandatory  
      DESCRIPTION  
      "Defines the Rx Safety Zone in bits."  
      ::= { lseIntPortEntry 21 }  
  
lseIntPortTxBurstLength OBJECT-TYPE  
      SYNTAX  INTEGER (1..1024)  
      ACCESS read-write  
      STATUS mandatory  
      DESCRIPTION  
      "Defines the TX Burst Length in bits."  
      ::= { lseIntPortEntry 22 }  
  
lseIntPortSecurityIntruder OBJECT-TYPE  
      SYNTAX  INTEGER {  
	on(1),  
	off(2),  
	notSupported(255)  
	}  
      ACCESS read-only  
      STATUS mandatory  
      DESCRIPTION  
      "The value ON of this attribute reflects a security violation occurrence."  
      ::= { lseIntPortEntry 23 }  
  
lseIntPortJabber OBJECT-TYPE  
     SYNTAX  INTEGER {  
	on(1),  
	off(2),  
	notSupported(255)  
	}  
     ACCESS  read-only  
     STATUS  mandatory  
     DESCRIPTION  
     "Value ON of this attribute reflects the jabber transmitted to the port by the high-speed bus."  
     ::= { lseIntPortEntry 24 }  
  
lseIntPortCAM OBJECT-TYPE  
      SYNTAX  OCTET STRING ( SIZE (56))  
      ACCESS  read-write  
      STATUS  mandatory  
      DESCRIPTION  
      "Fifty six bytes of MAC addresses. Each byte with the port number is followed by six byte MAC  
      address."   
      ::= { lseIntPortEntry 25 }  
  
lseIntPortVideoStateMachine OBJECT-TYPE  
      SYNTAX  INTEGER {  
	on(1),  
	off(2),  
	notSupported(255)  
	}  
      ACCESS  read-write  
      STATUS  mandatory  
      DESCRIPTION  
      "Setting the value of this attribute to ON activates the video state machine mode.  
      Received packets are filtered by demand from the station."  
      ::= { lseIntPortEntry 26 }  
  
lseIntPortTransmitWeight  OBJECT-TYPE  
     SYNTAX  INTEGER (0..127)  
     ACCESS  read-write  
     STATUS  mandatory  
     DESCRIPTION  
     "Defines the Transmit Weight of the frames toward the high-speed bus."  
     ::= { lseIntPortEntry 27 }  
  
  
lsePort OBJECT IDENTIFIER        
      ::= {lse 3}  
  
  
lsePortTable OBJECT-TYPE  
      SYNTAX  SEQUENCE OF LsePortEntry  
      ACCESS  not-accessible  
      STATUS  mandatory  
DESCRIPTION ""
      ::= { lsePort 1 }  
  
lsePortEntry OBJECT-TYPE  
      SYNTAX  LsePortEntry  
      ACCESS  not-accessible  
      STATUS  mandatory  
      DESCRIPTION  
      "An entry in the table containing data about a single external switch port."  
      INDEX  { lsePortGroupId, lsePortId }  
      ::= { lsePortTable 1 }  
  
LsePortEntry  ::=  
      SEQUENCE  {  
	lsePortGroupId  
	  INTEGER,  
	lsePortId  
	  INTEGER,  
	lsePortPolarity  
	  INTEGER  
     }  
  
lsePortGroupId OBJECT-TYPE  
      SYNTAX  INTEGER (1..255)  
      ACCESS  read-only  
      STATUS  mandatory  
      DESCRIPTION  
      "Id of the group to which the port belongs."  
      ::= { lsePortEntry 1 }  
  
lsePortId OBJECT-TYPE  
      SYNTAX  INTEGER (1..255)  
      ACCESS  read-only  
      STATUS  mandatory  
      DESCRIPTION  
      "Number of LanSwitch port in the board."  
      ::= { lsePortEntry 2 }  
  
lsePortPolarity OBJECT-TYPE  
      SYNTAX  INTEGER {  
	on(1),  
	off(2),  
	notSupported(255)  
	}  
      ACCESS read-write  
      STATUS mandatory  
		DESCRIPTION  
      "Setting the value of this attribute to ON activates the automatic port polarity  
      detection mode."  
      ::= { lsePortEntry 3 }  
  
  
  
END
