-- file automatically created


TELDAT-TRAP-NHRP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


nhrpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NHRP event subsystem."
    REVISION "201401200930Z"
    DESCRIPTION "Initial implementation"
        ::= { telEventTraps 185 }


nhrpEventsGroup	OBJECT IDENTIFIER	::= { nhrpTrapsMIB 1 }

nhrpNotifications	OBJECT IDENTIFIER	::= { nhrpTrapsMIB 2 }
nhrpNotificationsPrefix	OBJECT IDENTIFIER	::= { nhrpNotifications 0 }

nhrpEventObjects1 OBJECT-IDENTITY
    STATUS current
    DESCRIPTION
        "Event NHRP.1
        NHRP cache is being updated with new information."
    ::= { nhrpEventsGroup 1 }

nhrp1-ip-address OBJECT-TYPE
    SYNTAX IpAddress
    MAX-ACCESS accessible-for-notify
    STATUS current
    DESCRIPTION
        "Parameter 'ip-address' in event NHRP.1"
    ::= { nhrpEventObjects1 1 }

nhrp1-nbma OBJECT-TYPE
    SYNTAX DisplayString
    MAX-ACCESS accessible-for-notify
    STATUS current
    DESCRIPTION
        "Parameter 'nbma' in event NHRP.1"
    ::= { nhrpEventObjects1 2 }

nhrpEventObjects2 OBJECT-IDENTITY
    STATUS current
    DESCRIPTION
        "Event NHRP.2
        A purge reply packet is being sent."
    ::= { nhrpEventsGroup 2 }

nhrp2-ip-address OBJECT-TYPE
    SYNTAX IpAddress
    MAX-ACCESS accessible-for-notify
    STATUS current
    DESCRIPTION
        "Parameter 'ip-address' in event NHRP.2"
    ::= { nhrpEventObjects2 1 }

nhrpEventObjects3 OBJECT-IDENTITY
    STATUS current
    DESCRIPTION
        "Event NHRP.3
        Information included in the header of the mandatory part of an NHRP 
        packet."
    ::= { nhrpEventsGroup 3 }

nhrp3-id OBJECT-TYPE
    SYNTAX Integer32
    MAX-ACCESS accessible-for-notify
    STATUS current
    DESCRIPTION
        "Parameter 'id' in event NHRP.3"
    ::= { nhrpEventObjects3 1 }

nhrp3-flags OBJECT-TYPE
    SYNTAX Integer32
    MAX-ACCESS accessible-for-notify
    STATUS current
    DESCRIPTION
        "Parameter 'flags' in event NHRP.3"
    ::= { nhrpEventObjects3 2 }

nhrp3-src-length OBJECT-TYPE
    SYNTAX Integer32
    MAX-ACCESS accessible-for-notify
    STATUS current
    DESCRIPTION
        "Parameter 'src-length' in event NHRP.3"
    ::= { nhrpEventObjects3 3 }

nhrp3-dest-length OBJECT-TYPE
    SYNTAX Integer32
    MAX-ACCESS accessible-for-notify
    STATUS current
    DESCRIPTION
        "Parameter 'dest-length' in event NHRP.3"
    ::= { nhrpEventObjects3 4 }

nhrpEventObjects4 OBJECT-IDENTITY
    STATUS current
    DESCRIPTION
        "Event NHRP.4
        Retransmission of a NHRP packet with the reqid shown is being held now, 
        next retransmission will happen when the retransmission interval has 
        expired."
    ::= { nhrpEventsGroup 4 }

nhrp4-paktype-string OBJECT-TYPE
    SYNTAX DisplayString
    MAX-ACCESS accessible-for-notify
    STATUS current
    DESCRIPTION
        "Parameter 'paktype-string' in event NHRP.4"
    ::= { nhrpEventObjects4 1 }

nhrp4-interval OBJECT-TYPE
    SYNTAX Integer32
    MAX-ACCESS accessible-for-notify
    STATUS current
    DESCRIPTION
        "Parameter 'interval' in event NHRP.4"
    ::= { nhrpEventObjects4 2 }

nhrp4-request-id OBJECT-TYPE
    SYNTAX Integer32
    MAX-ACCESS accessible-for-notify
    STATUS current
    DESCRIPTION
        "Parameter 'request-id' in event NHRP.4"
    ::= { nhrpEventObjects4 3 }

nhrpEventObjects5 OBJECT-IDENTITY
    STATUS current
    DESCRIPTION
        "Event NHRP.5
        A NHRP broadcast packet is being discarded because it cannot be 
        forwarded over the same interface it has been received."
    ::= { nhrpEventsGroup 5 }

nhrp5-interface-name OBJECT-TYPE
    SYNTAX DisplayString
    MAX-ACCESS accessible-for-notify
    STATUS current
    DESCRIPTION
        "Parameter 'interface-name' in event NHRP.5"
    ::= { nhrpEventObjects5 1 }

nhrpEventObjects6 OBJECT-IDENTITY
    STATUS current
    DESCRIPTION
        "Event NHRP.6
        The router cannot route a NHRP packet for one destination because
        the output interface is not of type ip tunnel."
    ::= { nhrpEventsGroup 6 }

nhrp6-ip-address-nhop OBJECT-TYPE
    SYNTAX IpAddress
    MAX-ACCESS accessible-for-notify
    STATUS current
    DESCRIPTION
        "Parameter 'ip-address-nhop' in event NHRP.6"
    ::= { nhrpEventObjects6 1 }

nhrpEventObjects7 OBJECT-IDENTITY
    STATUS current
    DESCRIPTION
        "Event NHRP.7
        The NHRP packet cannot be sent to the destination. The interface could
        be down or it could be out of memory buffers."
    ::= { nhrpEventsGroup 7 }

nhrp7-ip-address-nhop OBJECT-TYPE
    SYNTAX IpAddress
    MAX-ACCESS accessible-for-notify
    STATUS current
    DESCRIPTION
        "Parameter 'ip-address-nhop' in event NHRP.7"
    ::= { nhrpEventObjects7 1 }

nhrp7-interface-name OBJECT-TYPE
    SYNTAX DisplayString
    MAX-ACCESS accessible-for-notify
    STATUS current
    DESCRIPTION
        "Parameter 'interface-name' in event NHRP.7"
    ::= { nhrpEventObjects7 2 }

nhrpEventObjects8 OBJECT-IDENTITY
    STATUS current
    DESCRIPTION
        "Event NHRP.8
        A NHRP packet is being transmitted to the destination shown."
    ::= { nhrpEventsGroup 8 }

nhrp8-bytes OBJECT-TYPE
    SYNTAX Integer32
    MAX-ACCESS accessible-for-notify
    STATUS current
    DESCRIPTION
        "Parameter 'bytes' in event NHRP.8"
    ::= { nhrpEventObjects8 1 }

nhrp8-ip-address-nhop OBJECT-TYPE
    SYNTAX IpAddress
    MAX-ACCESS accessible-for-notify
    STATUS current
    DESCRIPTION
        "Parameter 'ip-address-nhop' in event NHRP.8"
    ::= { nhrpEventObjects8 2 }

nhrp8-interface-name OBJECT-TYPE
    SYNTAX DisplayString
    MAX-ACCESS accessible-for-notify
    STATUS current
    DESCRIPTION
        "Parameter 'interface-name' in event NHRP.8"
    ::= { nhrpEventObjects8 3 }

nhrpEventObjects9 OBJECT-IDENTITY
    STATUS current
    DESCRIPTION
        "Event NHRP.9
        A NHRP packet is ready to be sent."
    ::= { nhrpEventsGroup 9 }

nhrp9-type OBJECT-TYPE
    SYNTAX DisplayString
    MAX-ACCESS accessible-for-notify
    STATUS current
    DESCRIPTION
        "Parameter 'type' in event NHRP.9"
    ::= { nhrpEventObjects9 1 }

nhrp9-bytes-sent OBJECT-TYPE
    SYNTAX Integer32
    MAX-ACCESS accessible-for-notify
    STATUS current
    DESCRIPTION
        "Parameter 'bytes-sent' in event NHRP.9"
    ::= { nhrpEventObjects9 2 }

nhrpEventObjects10 OBJECT-IDENTITY
    STATUS current
    DESCRIPTION
        "Event NHRP.10
        The NHRP packet is being discarded because the source and the 
        destination are the same."
    ::= { nhrpEventsGroup 10 }

nhrp10-ip-address-dest OBJECT-TYPE
    SYNTAX IpAddress
    MAX-ACCESS accessible-for-notify
    STATUS current
    DESCRIPTION
        "Parameter 'ip-address-dest' in event NHRP.10"
    ::= { nhrpEventObjects10 1 }

nhrpEventObjects11 OBJECT-IDENTITY
    STATUS current
    DESCRIPTION
        "Event NHRP.11
        The router failed to find one valid interface of type ip tunnel in the
        current NBMA network for the destination."
    ::= { nhrpEventsGroup 11 }

nhrp11-ip-address-dest OBJECT-TYPE
    SYNTAX IpAddress
    MAX-ACCESS accessible-for-notify
    STATUS current
    DESCRIPTION
        "Parameter 'ip-address-dest' in event NHRP.11"
    ::= { nhrpEventObjects11 1 }

nhrpEventObjects12 OBJECT-IDENTITY
    STATUS current
    DESCRIPTION
        "Event NHRP.12
        The NHRP packet is being discarded because the output interface is not 
        in the current NBMA network."
    ::= { nhrpEventsGroup 12 }

nhrp12-name OBJECT-TYPE
    SYNTAX DisplayString
    MAX-ACCESS accessible-for-notify
    STATUS current
    DESCRIPTION
        "Parameter 'name' in event NHRP.12"
    ::= { nhrpEventObjects12 1 }

nhrpEventObjects13 OBJECT-IDENTITY
    STATUS current
    DESCRIPTION
        "Event NHRP.13
        The router failed to find one valid interface of type ip tunnel in the
        current NBMA network for the destination."
    ::= { nhrpEventsGroup 13 }

nhrp13-ip-address OBJECT-TYPE
    SYNTAX IpAddress
    MAX-ACCESS accessible-for-notify
    STATUS current
    DESCRIPTION
        "Parameter 'ip-address' in event NHRP.13"
    ::= { nhrpEventObjects13 1 }

nhrpEventObjects14 OBJECT-IDENTITY
    STATUS current
    DESCRIPTION
        "Event NHRP.14
        The NHRP packet destination is out of the current NBMA network."
    ::= { nhrpEventsGroup 14 }

nhrp14-ip-address OBJECT-TYPE
    SYNTAX IpAddress
    MAX-ACCESS accessible-for-notify
    STATUS current
    DESCRIPTION
        "Parameter 'ip-address' in event NHRP.14"
    ::= { nhrpEventObjects14 1 }

nhrp14-if-name OBJECT-TYPE
    SYNTAX DisplayString
    MAX-ACCESS accessible-for-notify
    STATUS current
    DESCRIPTION
        "Parameter 'if-name' in event NHRP.14"
    ::= { nhrpEventObjects14 2 }

nhrpEventObjects15 OBJECT-IDENTITY
    STATUS current
    DESCRIPTION
        "Event NHRP.15
        An static map entry has being found in the routing table."
    ::= { nhrpEventsGroup 15 }

nhrp15-ip-address OBJECT-TYPE
    SYNTAX IpAddress
    MAX-ACCESS accessible-for-notify
    STATUS current
    DESCRIPTION
        "Parameter 'ip-address' in event NHRP.15"
    ::= { nhrpEventObjects15 1 }

nhrp15-if-name OBJECT-TYPE
    SYNTAX DisplayString
    MAX-ACCESS accessible-for-notify
    STATUS current
    DESCRIPTION
        "Parameter 'if-name' in event NHRP.15"
    ::= { nhrpEventObjects15 2 }

nhrpEventObjects16 OBJECT-IDENTITY
    STATUS current
    DESCRIPTION
        "Event NHRP.16
        The router failed to find one valid interface of type ip tunnel in the
        current NBMA network for the destination."
    ::= { nhrpEventsGroup 16 }

nhrp16-packet-type OBJECT-TYPE
    SYNTAX DisplayString
    MAX-ACCESS accessible-for-notify
    STATUS current
    DESCRIPTION
        "Parameter 'packet-type' in event NHRP.16"
    ::= { nhrpEventObjects16 1 }

nhrp16-ip-address OBJECT-TYPE
    SYNTAX IpAddress
    MAX-ACCESS accessible-for-notify
    STATUS current
    DESCRIPTION
        "Parameter 'ip-address' in event NHRP.16"
    ::= { nhrpEventObjects16 2 }

nhrpEventObjects17 OBJECT-IDENTITY
    STATUS current
    DESCRIPTION
        "Event NHRP.17
        A purge reply packet has being received but it had not been requested."
    ::= { nhrpEventsGroup 17 }

nhrp17-id OBJECT-TYPE
    SYNTAX Integer32
    MAX-ACCESS accessible-for-notify
    STATUS current
    DESCRIPTION
        "Parameter 'id' in event NHRP.17"
    ::= { nhrpEventObjects17 1 }

nhrp17-ip-address OBJECT-TYPE
    SYNTAX IpAddress
    MAX-ACCESS accessible-for-notify
    STATUS current
    DESCRIPTION
        "Parameter 'ip-address' in event NHRP.17"
    ::= { nhrpEventObjects17 2 }

nhrpEventObjects18 OBJECT-IDENTITY
    STATUS current
    DESCRIPTION
        "Event NHRP.18
        The fixed part of the NHRP packet holds a wrong protocol version."
    ::= { nhrpEventsGroup 18 }

nhrp18-version OBJECT-TYPE
    SYNTAX Integer32
    MAX-ACCESS accessible-for-notify
    STATUS current
    DESCRIPTION
        "Parameter 'version' in event NHRP.18"
    ::= { nhrpEventObjects18 1 }

nhrp18-ip-address-src OBJECT-TYPE
    SYNTAX IpAddress
    MAX-ACCESS accessible-for-notify
    STATUS current
    DESCRIPTION
        "Parameter 'ip-address-src' in event NHRP.18"
    ::= { nhrpEventObjects18 2 }

nhrp18-ip-address-dest OBJECT-TYPE
    SYNTAX IpAddress
    MAX-ACCESS accessible-for-notify
    STATUS current
    DESCRIPTION
        "Parameter 'ip-address-dest' in event NHRP.18"
    ::= { nhrpEventObjects18 3 }

nhrpEventObjects19 OBJECT-IDENTITY
    STATUS current
    DESCRIPTION
        "Event NHRP.19
        The received NHRP packet has wrong cheksum."
    ::= { nhrpEventsGroup 19 }

nhrp19-ip-address-src OBJECT-TYPE
    SYNTAX IpAddress
    MAX-ACCESS accessible-for-notify
    STATUS current
    DESCRIPTION
        "Parameter 'ip-address-src' in event NHRP.19"
    ::= { nhrpEventObjects19 1 }

nhrp19-ip-address-dest OBJECT-TYPE
    SYNTAX IpAddress
    MAX-ACCESS accessible-for-notify
    STATUS current
    DESCRIPTION
        "Parameter 'ip-address-dest' in event NHRP.19"
    ::= { nhrpEventObjects19 2 }

nhrpEventObjects20 OBJECT-IDENTITY
    STATUS current
    DESCRIPTION
        "Event NHRP.20
        A NHRP register request is being sent to the destination shown."
    ::= { nhrpEventsGroup 20 }

nhrp20-ip-address OBJECT-TYPE
    SYNTAX IpAddress
    MAX-ACCESS accessible-for-notify
    STATUS current
    DESCRIPTION
        "Parameter 'ip-address' in event NHRP.20"
    ::= { nhrpEventObjects20 1 }

nhrpEventObjects21 OBJECT-IDENTITY
    STATUS current
    DESCRIPTION
        "Event NHRP.21
        The protocol failed to find a valid next hop entry in the cache for the 
        destination."
    ::= { nhrpEventsGroup 21 }

nhrp21-ip-address OBJECT-TYPE
    SYNTAX IpAddress
    MAX-ACCESS accessible-for-notify
    STATUS current
    DESCRIPTION
        "Parameter 'ip-address' in event NHRP.21"
    ::= { nhrpEventObjects21 1 }

nhrpEventObjects22 OBJECT-IDENTITY
    STATUS current
    DESCRIPTION
        "Event NHRP.22
        The cache has returned a wrong address type for the destination address."
    ::= { nhrpEventsGroup 22 }

nhrp22-ip-address OBJECT-TYPE
    SYNTAX IpAddress
    MAX-ACCESS accessible-for-notify
    STATUS current
    DESCRIPTION
        "Parameter 'ip-address' in event NHRP.22"
    ::= { nhrpEventObjects22 1 }

nhrp22-type-ret OBJECT-TYPE
    SYNTAX Integer32
    MAX-ACCESS accessible-for-notify
    STATUS current
    DESCRIPTION
        "Parameter 'type-ret' in event NHRP.22"
    ::= { nhrpEventObjects22 2 }

nhrp22-type-exp OBJECT-TYPE
    SYNTAX Integer32
    MAX-ACCESS accessible-for-notify
    STATUS current
    DESCRIPTION
        "Parameter 'type-exp' in event NHRP.22"
    ::= { nhrpEventObjects22 3 }

nhrpEventObjects23 OBJECT-IDENTITY
    STATUS current
    DESCRIPTION
        "Event NHRP.23
        The period of retransmission of a purge request has expired, no more 
        retransmissions of this packet will be done."
    ::= { nhrpEventsGroup 23 }

nhrp23-ip-address OBJECT-TYPE
    SYNTAX IpAddress
    MAX-ACCESS accessible-for-notify
    STATUS current
    DESCRIPTION
        "Parameter 'ip-address' in event NHRP.23"
    ::= { nhrpEventObjects23 1 }

nhrp23-id OBJECT-TYPE
    SYNTAX Integer32
    MAX-ACCESS accessible-for-notify
    STATUS current
    DESCRIPTION
        "Parameter 'id' in event NHRP.23"
    ::= { nhrpEventObjects23 2 }

nhrpEventObjects24 OBJECT-IDENTITY
    STATUS current
    DESCRIPTION
        "Event NHRP.24
        A purge request packet has been received and the cache entry for the
        next hop address shown has been deleted."
    ::= { nhrpEventsGroup 24 }

nhrp24-src-address OBJECT-TYPE
    SYNTAX IpAddress
    MAX-ACCESS accessible-for-notify
    STATUS current
    DESCRIPTION
        "Parameter 'src-address' in event NHRP.24"
    ::= { nhrpEventObjects24 1 }

nhrp24-nhop-address OBJECT-TYPE
    SYNTAX IpAddress
    MAX-ACCESS accessible-for-notify
    STATUS current
    DESCRIPTION
        "Parameter 'nhop-address' in event NHRP.24"
    ::= { nhrpEventObjects24 2 }

nhrpEventObjects25 OBJECT-IDENTITY
    STATUS current
    DESCRIPTION
        "Event NHRP.25
        Contents of the header of the mandatory part of a NHRP error packet."
    ::= { nhrpEventsGroup 25 }

nhrp25-description OBJECT-TYPE
    SYNTAX DisplayString
    MAX-ACCESS accessible-for-notify
    STATUS current
    DESCRIPTION
        "Parameter 'description' in event NHRP.25"
    ::= { nhrpEventObjects25 1 }

nhrp25-error-code OBJECT-TYPE
    SYNTAX Integer32
    MAX-ACCESS accessible-for-notify
    STATUS current
    DESCRIPTION
        "Parameter 'error-code' in event NHRP.25"
    ::= { nhrpEventObjects25 2 }

nhrp25-offset OBJECT-TYPE
    SYNTAX Integer32
    MAX-ACCESS accessible-for-notify
    STATUS current
    DESCRIPTION
        "Parameter 'offset' in event NHRP.25"
    ::= { nhrpEventObjects25 3 }

nhrpEventObjects26 OBJECT-IDENTITY
    STATUS current
    DESCRIPTION
        "Event NHRP.26
        The NHRP protocol is searching its cache for a longest match entry."
    ::= { nhrpEventsGroup 26 }

nhrp26-ip-address OBJECT-TYPE
    SYNTAX IpAddress
    MAX-ACCESS accessible-for-notify
    STATUS current
    DESCRIPTION
        "Parameter 'ip-address' in event NHRP.26"
    ::= { nhrpEventObjects26 1 }

nhrp26-ip-mask OBJECT-TYPE
    SYNTAX IpAddress
    MAX-ACCESS accessible-for-notify
    STATUS current
    DESCRIPTION
        "Parameter 'ip-mask' in event NHRP.26"
    ::= { nhrpEventObjects26 2 }

nhrp26-longest-yes-no OBJECT-TYPE
    SYNTAX DisplayString
    MAX-ACCESS accessible-for-notify
    STATUS current
    DESCRIPTION
        "Parameter 'longest-yes-no' in event NHRP.26"
    ::= { nhrpEventObjects26 3 }

nhrpEventObjects27 OBJECT-IDENTITY
    STATUS current
    DESCRIPTION
        "Event NHRP.27
        A new cache entry is being created in the NHRP protocol cache."
    ::= { nhrpEventsGroup 27 }

nhrp27-ip-address OBJECT-TYPE
    SYNTAX IpAddress
    MAX-ACCESS accessible-for-notify
    STATUS current
    DESCRIPTION
        "Parameter 'ip-address' in event NHRP.27"
    ::= { nhrpEventObjects27 1 }

nhrp27-ip-mask OBJECT-TYPE
    SYNTAX IpAddress
    MAX-ACCESS accessible-for-notify
    STATUS current
    DESCRIPTION
        "Parameter 'ip-mask' in event NHRP.27"
    ::= { nhrpEventObjects27 2 }

nhrpEventObjects28 OBJECT-IDENTITY
    STATUS current
    DESCRIPTION
        "Event NHRP.28
        A cache entry is being deleted from the NHRP protocol cache."
    ::= { nhrpEventsGroup 28 }

nhrp28-ip-address OBJECT-TYPE
    SYNTAX IpAddress
    MAX-ACCESS accessible-for-notify
    STATUS current
    DESCRIPTION
        "Parameter 'ip-address' in event NHRP.28"
    ::= { nhrpEventObjects28 1 }

nhrp28-ip-mask OBJECT-TYPE
    SYNTAX IpAddress
    MAX-ACCESS accessible-for-notify
    STATUS current
    DESCRIPTION
        "Parameter 'ip-mask' in event NHRP.28"
    ::= { nhrpEventObjects28 2 }

nhrp28-if-name OBJECT-TYPE
    SYNTAX DisplayString
    MAX-ACCESS accessible-for-notify
    STATUS current
    DESCRIPTION
        "Parameter 'if-name' in event NHRP.28"
    ::= { nhrpEventObjects28 3 }

nhrpEventObjects29 OBJECT-IDENTITY
    STATUS current
    DESCRIPTION
        "Event NHRP.29
        A purge request packet has being received for a cache entry that is not
        dynamic type and for this reason it cannot be deleted from the NHRP 
        protocol cache."
    ::= { nhrpEventsGroup 29 }

nhrp29-ip-address OBJECT-TYPE
    SYNTAX IpAddress
    MAX-ACCESS accessible-for-notify
    STATUS current
    DESCRIPTION
        "Parameter 'ip-address' in event NHRP.29"
    ::= { nhrpEventObjects29 1 }

nhrp29-ip-mask OBJECT-TYPE
    SYNTAX IpAddress
    MAX-ACCESS accessible-for-notify
    STATUS current
    DESCRIPTION
        "Parameter 'ip-mask' in event NHRP.29"
    ::= { nhrpEventObjects29 2 }

nhrp29-entry-type OBJECT-TYPE
    SYNTAX DisplayString
    MAX-ACCESS accessible-for-notify
    STATUS current
    DESCRIPTION
        "Parameter 'entry-type' in event NHRP.29"
    ::= { nhrpEventObjects29 3 }

nhrpEventObjects30 OBJECT-IDENTITY
    STATUS current
    DESCRIPTION
        "Event NHRP.30
        The NHRP is trying to refresh a cache entry that is being used (packets 
        are traveling though this tunnel) and which is less than one minute time
        to expire and to be deleted."
    ::= { nhrpEventsGroup 30 }

nhrp30-ip-address OBJECT-TYPE
    SYNTAX IpAddress
    MAX-ACCESS accessible-for-notify
    STATUS current
    DESCRIPTION
        "Parameter 'ip-address' in event NHRP.30"
    ::= { nhrpEventObjects30 1 }

nhrp30-ip-mask OBJECT-TYPE
    SYNTAX IpAddress
    MAX-ACCESS accessible-for-notify
    STATUS current
    DESCRIPTION
        "Parameter 'ip-mask' in event NHRP.30"
    ::= { nhrpEventObjects30 2 }

nhrpEventObjects32 OBJECT-IDENTITY
    STATUS current
    DESCRIPTION
        "Event NHRP.32
        There is no cache entry in NHRP protocol cache with the reqid received
        in the purge request packet."
    ::= { nhrpEventsGroup 32 }

nhrp32-id OBJECT-TYPE
    SYNTAX Integer32
    MAX-ACCESS accessible-for-notify
    STATUS current
    DESCRIPTION
        "Parameter 'id' in event NHRP.32"
    ::= { nhrpEventObjects32 1 }

nhrpEventObjects33 OBJECT-IDENTITY
    STATUS current
    DESCRIPTION
        "Event NHRP.33
        All dynamic entries in the NHRP protocol cache of the current interface
        are being deleted."
    ::= { nhrpEventsGroup 33 }

nhrp33-ifc-name OBJECT-TYPE
    SYNTAX DisplayString
    MAX-ACCESS accessible-for-notify
    STATUS current
    DESCRIPTION
        "Parameter 'ifc-name' in event NHRP.33"
    ::= { nhrpEventObjects33 1 }

nhrpEventObjects34 OBJECT-IDENTITY
    STATUS current
    DESCRIPTION
        "Event NHRP.34
        The NHRP protocol is changing its state from down to up because the
        tunnel interface state is now up."
    ::= { nhrpEventsGroup 34 }

nhrp34-ifc-name OBJECT-TYPE
    SYNTAX DisplayString
    MAX-ACCESS accessible-for-notify
    STATUS current
    DESCRIPTION
        "Parameter 'ifc-name' in event NHRP.34"
    ::= { nhrpEventObjects34 1 }

nhrp34-protocol-number OBJECT-TYPE
    SYNTAX Integer32
    MAX-ACCESS accessible-for-notify
    STATUS current
    DESCRIPTION
        "Parameter 'protocol-number' in event NHRP.34"
    ::= { nhrpEventObjects34 2 }

nhrpEventObjects35 OBJECT-IDENTITY
    STATUS current
    DESCRIPTION
        "Event NHRP.35
        Contents of the header of an extension in a NHRP packet."
    ::= { nhrpEventsGroup 35 }

nhrp35-extension-name OBJECT-TYPE
    SYNTAX DisplayString
    MAX-ACCESS accessible-for-notify
    STATUS current
    DESCRIPTION
        "Parameter 'extension-name' in event NHRP.35"
    ::= { nhrpEventObjects35 1 }

nhrp35-extension-length OBJECT-TYPE
    SYNTAX Integer32
    MAX-ACCESS accessible-for-notify
    STATUS current
    DESCRIPTION
        "Parameter 'extension-length' in event NHRP.35"
    ::= { nhrpEventObjects35 2 }

nhrpEventObjects36 OBJECT-IDENTITY
    STATUS current
    DESCRIPTION
        "Event NHRP.36
        A positive or negative reply is being sent in response to a request 
        packet for next hop resolution."
    ::= { nhrpEventsGroup 36 }

nhrp36-type OBJECT-TYPE
    SYNTAX DisplayString
    MAX-ACCESS accessible-for-notify
    STATUS current
    DESCRIPTION
        "Parameter 'type' in event NHRP.36"
    ::= { nhrpEventObjects36 1 }

nhrp36-nhop-ip OBJECT-TYPE
    SYNTAX IpAddress
    MAX-ACCESS accessible-for-notify
    STATUS current
    DESCRIPTION
        "Parameter 'nhop-ip' in event NHRP.36"
    ::= { nhrpEventObjects36 2 }

nhrpEventObjects37 OBJECT-IDENTITY
    STATUS current
    DESCRIPTION
        "Event NHRP.37
        An initial transmission or a retransmission of a resolution or
        registration request is being held. Also a message of end of 
        retransmissions could be shown."
    ::= { nhrpEventsGroup 37 }

nhrp37-string OBJECT-TYPE
    SYNTAX DisplayString
    MAX-ACCESS accessible-for-notify
    STATUS current
    DESCRIPTION
        "Parameter 'string' in event NHRP.37"
    ::= { nhrpEventObjects37 1 }

nhrp37-request-id OBJECT-TYPE
    SYNTAX Integer32
    MAX-ACCESS accessible-for-notify
    STATUS current
    DESCRIPTION
        "Parameter 'request-id' in event NHRP.37"
    ::= { nhrpEventObjects37 2 }

nhrpEventObjects38 OBJECT-IDENTITY
    STATUS current
    DESCRIPTION
        "Event NHRP.38
        Contents of a CIE header (Client Information Entry) in a NHRP packet."
    ::= { nhrpEventsGroup 38 }

nhrp38-tab OBJECT-TYPE
    SYNTAX DisplayString
    MAX-ACCESS accessible-for-notify
    STATUS current
    DESCRIPTION
        "Parameter 'tab' in event NHRP.38"
    ::= { nhrpEventObjects38 1 }

nhrp38-code OBJECT-TYPE
    SYNTAX Integer32
    MAX-ACCESS accessible-for-notify
    STATUS current
    DESCRIPTION
        "Parameter 'code' in event NHRP.38"
    ::= { nhrpEventObjects38 2 }

nhrp38-prefix OBJECT-TYPE
    SYNTAX Integer32
    MAX-ACCESS accessible-for-notify
    STATUS current
    DESCRIPTION
        "Parameter 'prefix' in event NHRP.38"
    ::= { nhrpEventObjects38 3 }

nhrp38-mtu OBJECT-TYPE
    SYNTAX Integer32
    MAX-ACCESS accessible-for-notify
    STATUS current
    DESCRIPTION
        "Parameter 'mtu' in event NHRP.38"
    ::= { nhrpEventObjects38 4 }

nhrp38-hold OBJECT-TYPE
    SYNTAX Integer32
    MAX-ACCESS accessible-for-notify
    STATUS current
    DESCRIPTION
        "Parameter 'hold' in event NHRP.38"
    ::= { nhrpEventObjects38 5 }

nhrp38-pref OBJECT-TYPE
    SYNTAX Integer32
    MAX-ACCESS accessible-for-notify
    STATUS current
    DESCRIPTION
        "Parameter 'pref' in event NHRP.38"
    ::= { nhrpEventObjects38 6 }

nhrpEventObjects39 OBJECT-IDENTITY
    STATUS current
    DESCRIPTION
        "Event NHRP.39
        Contents of a CIE body (Client Information Entry) in a NHRP packet."
    ::= { nhrpEventsGroup 39 }

nhrp39-tab OBJECT-TYPE
    SYNTAX DisplayString
    MAX-ACCESS accessible-for-notify
    STATUS current
    DESCRIPTION
        "Parameter 'tab' in event NHRP.39"
    ::= { nhrpEventObjects39 1 }

nhrp39-nbma-addr OBJECT-TYPE
    SYNTAX DisplayString
    MAX-ACCESS accessible-for-notify
    STATUS current
    DESCRIPTION
        "Parameter 'nbma-addr' in event NHRP.39"
    ::= { nhrpEventObjects39 2 }

nhrp39-snbma-addr OBJECT-TYPE
    SYNTAX DisplayString
    MAX-ACCESS accessible-for-notify
    STATUS current
    DESCRIPTION
        "Parameter 'snbma-addr' in event NHRP.39"
    ::= { nhrpEventObjects39 3 }

nhrp39-prot-addr OBJECT-TYPE
    SYNTAX DisplayString
    MAX-ACCESS accessible-for-notify
    STATUS current
    DESCRIPTION
        "Parameter 'prot-addr' in event NHRP.39"
    ::= { nhrpEventObjects39 4 }

nhrpEventObjects40 OBJECT-IDENTITY
    STATUS current
    DESCRIPTION
        "Event NHRP.40
        Contents of the fixed header of a NHRP packet."
    ::= { nhrpEventsGroup 40 }

nhrp40-pckt-type-name OBJECT-TYPE
    SYNTAX DisplayString
    MAX-ACCESS accessible-for-notify
    STATUS current
    DESCRIPTION
        "Parameter 'pckt-type-name' in event NHRP.40"
    ::= { nhrpEventObjects40 1 }

nhrp40-afn OBJECT-TYPE
    SYNTAX Integer32
    MAX-ACCESS accessible-for-notify
    STATUS current
    DESCRIPTION
        "Parameter 'afn' in event NHRP.40"
    ::= { nhrpEventObjects40 2 }

nhrp40-protocol OBJECT-TYPE
    SYNTAX Integer32
    MAX-ACCESS accessible-for-notify
    STATUS current
    DESCRIPTION
        "Parameter 'protocol' in event NHRP.40"
    ::= { nhrpEventObjects40 3 }

nhrp40-hopcount OBJECT-TYPE
    SYNTAX Integer32
    MAX-ACCESS accessible-for-notify
    STATUS current
    DESCRIPTION
        "Parameter 'hopcount' in event NHRP.40"
    ::= { nhrpEventObjects40 4 }

nhrpEventObjects41 OBJECT-IDENTITY
    STATUS current
    DESCRIPTION
        "Event NHRP.41
        A NHRP packet has been received. The type of packet, size and the
        interface the packet  was received in are shown."
    ::= { nhrpEventsGroup 41 }

nhrp41-type OBJECT-TYPE
    SYNTAX DisplayString
    MAX-ACCESS accessible-for-notify
    STATUS current
    DESCRIPTION
        "Parameter 'type' in event NHRP.41"
    ::= { nhrpEventObjects41 1 }

nhrp41-bytes-rcvd OBJECT-TYPE
    SYNTAX Integer32
    MAX-ACCESS accessible-for-notify
    STATUS current
    DESCRIPTION
        "Parameter 'bytes-rcvd' in event NHRP.41"
    ::= { nhrpEventObjects41 2 }

nhrp41-interface-name OBJECT-TYPE
    SYNTAX DisplayString
    MAX-ACCESS accessible-for-notify
    STATUS current
    DESCRIPTION
        "Parameter 'interface-name' in event NHRP.41"
    ::= { nhrpEventObjects41 3 }

nhrpEventObjects43 OBJECT-IDENTITY
    STATUS current
    DESCRIPTION
        "Event NHRP.43
        A purge request packet is being sent to the destination owning the
        ip address shown."
    ::= { nhrpEventsGroup 43 }

nhrp43-ip-address OBJECT-TYPE
    SYNTAX IpAddress
    MAX-ACCESS accessible-for-notify
    STATUS current
    DESCRIPTION
        "Parameter 'ip-address' in event NHRP.43"
    ::= { nhrpEventObjects43 1 }

nhrpEventObjects44 OBJECT-IDENTITY
    STATUS current
    DESCRIPTION
        "Event NHRP.44
        Contents of a NHRP error packet header."
    ::= { nhrpEventsGroup 44 }

nhrp44-ip-address-nbma OBJECT-TYPE
    SYNTAX IpAddress
    MAX-ACCESS accessible-for-notify
    STATUS current
    DESCRIPTION
        "Parameter 'ip-address-nbma' in event NHRP.44"
    ::= { nhrpEventObjects44 1 }

nhrp44-ip-address-src OBJECT-TYPE
    SYNTAX IpAddress
    MAX-ACCESS accessible-for-notify
    STATUS current
    DESCRIPTION
        "Parameter 'ip-address-src' in event NHRP.44"
    ::= { nhrpEventObjects44 2 }

nhrp44-ip-address-dest OBJECT-TYPE
    SYNTAX IpAddress
    MAX-ACCESS accessible-for-notify
    STATUS current
    DESCRIPTION
        "Parameter 'ip-address-dest' in event NHRP.44"
    ::= { nhrpEventObjects44 3 }

nhrpEventObjects45 OBJECT-IDENTITY
    STATUS current
    DESCRIPTION
        "Event NHRP.45
        A general error message."
    ::= { nhrpEventsGroup 45 }

nhrp45-err-string OBJECT-TYPE
    SYNTAX DisplayString
    MAX-ACCESS accessible-for-notify
    STATUS current
    DESCRIPTION
        "Parameter 'err-string' in event NHRP.45"
    ::= { nhrpEventObjects45 1 }

nhrpEventObjects46 OBJECT-IDENTITY
    STATUS current
    DESCRIPTION
        "Event NHRP.46
        A NHRP packet is being forwarded through the interface shown to the 
        destination shown."
    ::= { nhrpEventsGroup 46 }

nhrp46-packet-type OBJECT-TYPE
    SYNTAX DisplayString
    MAX-ACCESS accessible-for-notify
    STATUS current
    DESCRIPTION
        "Parameter 'packet-type' in event NHRP.46"
    ::= { nhrpEventObjects46 1 }

nhrp46-interface-name OBJECT-TYPE
    SYNTAX DisplayString
    MAX-ACCESS accessible-for-notify
    STATUS current
    DESCRIPTION
        "Parameter 'interface-name' in event NHRP.46"
    ::= { nhrpEventObjects46 2 }

nhrp46-dest-ip OBJECT-TYPE
    SYNTAX IpAddress
    MAX-ACCESS accessible-for-notify
    STATUS current
    DESCRIPTION
        "Parameter 'dest-ip' in event NHRP.46"
    ::= { nhrpEventObjects46 3 }

nhrpEventObjects47 OBJECT-IDENTITY
    STATUS current
    DESCRIPTION
        "Event NHRP.47
        A NHRP packet has been received on an interface but this interface is 
        not configured for using NHRP protocol."
    ::= { nhrpEventsGroup 47 }

nhrp47-interface-name OBJECT-TYPE
    SYNTAX DisplayString
    MAX-ACCESS accessible-for-notify
    STATUS current
    DESCRIPTION
        "Parameter 'interface-name' in event NHRP.47"
    ::= { nhrpEventObjects47 1 }

nhrpEventObjects48 OBJECT-IDENTITY
    STATUS current
    DESCRIPTION
        "Event NHRP.48
        The NHRP protocol is changing its state from up to down for the
        interface shown."
    ::= { nhrpEventsGroup 48 }

nhrp48-interface-name OBJECT-TYPE
    SYNTAX DisplayString
    MAX-ACCESS accessible-for-notify
    STATUS current
    DESCRIPTION
        "Parameter 'interface-name' in event NHRP.48"
    ::= { nhrpEventObjects48 1 }

nhrp48-protocol-type OBJECT-TYPE
    SYNTAX Integer32
    MAX-ACCESS accessible-for-notify
    STATUS current
    DESCRIPTION
        "Parameter 'protocol-type' in event NHRP.48"
    ::= { nhrpEventObjects48 2 }

nhrpEventObjects49 OBJECT-IDENTITY
    STATUS current
    DESCRIPTION
        "Event NHRP.49
        This is the number of requests made to the NHRP protocol for the
        interface shown before sending a NHRP resolution request packet. For 
        more information take a look at the 'nhrp use' command in the DMVPN 
        manual."
    ::= { nhrpEventsGroup 49 }

nhrp49-interface-name OBJECT-TYPE
    SYNTAX DisplayString
    MAX-ACCESS accessible-for-notify
    STATUS current
    DESCRIPTION
        "Parameter 'interface-name' in event NHRP.49"
    ::= { nhrpEventObjects49 1 }

nhrp49-buffer-quota OBJECT-TYPE
    SYNTAX Integer32
    MAX-ACCESS accessible-for-notify
    STATUS current
    DESCRIPTION
        "Parameter 'buffer-quota' in event NHRP.49"
    ::= { nhrpEventObjects49 2 }

nhrpEventObjects50 OBJECT-IDENTITY
    STATUS current
    DESCRIPTION
        "Event NHRP.50
        The cache entry information shown is less than one minute to expire and
        be deleted."
    ::= { nhrpEventsGroup 50 }

nhrp50-ip-address OBJECT-TYPE
    SYNTAX IpAddress
    MAX-ACCESS accessible-for-notify
    STATUS current
    DESCRIPTION
        "Parameter 'ip-address' in event NHRP.50"
    ::= { nhrpEventObjects50 1 }

nhrp50-ip-mask OBJECT-TYPE
    SYNTAX IpAddress
    MAX-ACCESS accessible-for-notify
    STATUS current
    DESCRIPTION
        "Parameter 'ip-mask' in event NHRP.50"
    ::= { nhrpEventObjects50 2 }

nhrpEventObjects51 OBJECT-IDENTITY
    STATUS current
    DESCRIPTION
        "Event NHRP.51
        A negative reply has been received for the reqid shown. The NAK code is
        shown."
    ::= { nhrpEventsGroup 51 }

nhrp51-reqid OBJECT-TYPE
    SYNTAX Integer32
    MAX-ACCESS accessible-for-notify
    STATUS current
    DESCRIPTION
        "Parameter 'reqid' in event NHRP.51"
    ::= { nhrpEventObjects51 1 }

nhrp51-no-ack-string OBJECT-TYPE
    SYNTAX DisplayString
    MAX-ACCESS accessible-for-notify
    STATUS current
    DESCRIPTION
        "Parameter 'no-ack-string' in event NHRP.51"
    ::= { nhrpEventObjects51 2 }

nhrpEventObjects52 OBJECT-IDENTITY
    STATUS current
    DESCRIPTION
        "Event NHRP.52
        Contents of the body of the mandatory part of a NHRP packet."
    ::= { nhrpEventsGroup 52 }

nhrp52-tab OBJECT-TYPE
    SYNTAX DisplayString
    MAX-ACCESS accessible-for-notify
    STATUS current
    DESCRIPTION
        "Parameter 'tab' in event NHRP.52"
    ::= { nhrpEventObjects52 1 }

nhrp52-nbma-ip-address OBJECT-TYPE
    SYNTAX IpAddress
    MAX-ACCESS accessible-for-notify
    STATUS current
    DESCRIPTION
        "Parameter 'nbma-ip-address' in event NHRP.52"
    ::= { nhrpEventObjects52 2 }

nhrp52-src-ip-address OBJECT-TYPE
    SYNTAX IpAddress
    MAX-ACCESS accessible-for-notify
    STATUS current
    DESCRIPTION
        "Parameter 'src-ip-address' in event NHRP.52"
    ::= { nhrpEventObjects52 3 }

nhrp52-dest-ip-address OBJECT-TYPE
    SYNTAX IpAddress
    MAX-ACCESS accessible-for-notify
    STATUS current
    DESCRIPTION
        "Parameter 'dest-ip-address' in event NHRP.52"
    ::= { nhrpEventObjects52 4 }

nhrpEventObjects53 OBJECT-IDENTITY
    STATUS current
    DESCRIPTION
        "Event NHRP.53
        Contents of the body of the fixed part of a NHRP packet."
    ::= { nhrpEventsGroup 53 }

nhrp53-tab OBJECT-TYPE
    SYNTAX DisplayString
    MAX-ACCESS accessible-for-notify
    STATUS current
    DESCRIPTION
        "Parameter 'tab' in event NHRP.53"
    ::= { nhrpEventObjects53 1 }

nhrp53-packet-length OBJECT-TYPE
    SYNTAX Integer32
    MAX-ACCESS accessible-for-notify
    STATUS current
    DESCRIPTION
        "Parameter 'packet-length' in event NHRP.53"
    ::= { nhrpEventObjects53 2 }

nhrp53-protocol-version OBJECT-TYPE
    SYNTAX Integer32
    MAX-ACCESS accessible-for-notify
    STATUS current
    DESCRIPTION
        "Parameter 'protocol-version' in event NHRP.53"
    ::= { nhrpEventObjects53 3 }

nhrp53-nbma-length OBJECT-TYPE
    SYNTAX Integer32
    MAX-ACCESS accessible-for-notify
    STATUS current
    DESCRIPTION
        "Parameter 'nbma-length' in event NHRP.53"
    ::= { nhrpEventObjects53 4 }

nhrp53-sub-nbma-length OBJECT-TYPE
    SYNTAX Integer32
    MAX-ACCESS accessible-for-notify
    STATUS current
    DESCRIPTION
        "Parameter 'sub-nbma-length' in event NHRP.53"
    ::= { nhrpEventObjects53 5 }

nhrpEventObjects54 OBJECT-IDENTITY
    STATUS current
    DESCRIPTION
        "Event NHRP.54
        The router is not able to resolve the NBMA address of the output
        interface."
    ::= { nhrpEventsGroup 54 }

nhrp54-interface-name OBJECT-TYPE
    SYNTAX DisplayString
    MAX-ACCESS accessible-for-notify
    STATUS current
    DESCRIPTION
        "Parameter 'interface-name' in event NHRP.54"
    ::= { nhrpEventObjects54 1 }

nhrpEventObjects55 OBJECT-IDENTITY
    STATUS current
    DESCRIPTION
        "Event NHRP.55
        The input and output interfaces are in the same NBMA network."
    ::= { nhrpEventsGroup 55 }

nhrp55-interface-in-name OBJECT-TYPE
    SYNTAX DisplayString
    MAX-ACCESS accessible-for-notify
    STATUS current
    DESCRIPTION
        "Parameter 'interface-in-name' in event NHRP.55"
    ::= { nhrpEventObjects55 1 }

nhrp55-interface-out-name OBJECT-TYPE
    SYNTAX DisplayString
    MAX-ACCESS accessible-for-notify
    STATUS current
    DESCRIPTION
        "Parameter 'interface-out-name' in event NHRP.55"
    ::= { nhrpEventObjects55 2 }

nhrpEventObjects56 OBJECT-IDENTITY
    STATUS current
    DESCRIPTION
        "Event NHRP.56
        An entry in the routing table has been created and the NHRP protocol 
        will be informed of any change in this entry of the routing table."
    ::= { nhrpEventsGroup 56 }

nhrp56-net-number OBJECT-TYPE
    SYNTAX IpAddress
    MAX-ACCESS accessible-for-notify
    STATUS current
    DESCRIPTION
        "Parameter 'net-number' in event NHRP.56"
    ::= { nhrpEventObjects56 1 }

nhrp56-net-mask OBJECT-TYPE
    SYNTAX IpAddress
    MAX-ACCESS accessible-for-notify
    STATUS current
    DESCRIPTION
        "Parameter 'net-mask' in event NHRP.56"
    ::= { nhrpEventObjects56 2 }

nhrpEventObjects57 OBJECT-IDENTITY
    STATUS current
    DESCRIPTION
        "Event NHRP.57
        The NHRP protocol marks a routing table entry so as to be informed of
        any change that this entry could suffer."
    ::= { nhrpEventsGroup 57 }

nhrp57-redist-flags OBJECT-TYPE
    SYNTAX Integer32
    MAX-ACCESS accessible-for-notify
    STATUS current
    DESCRIPTION
        "Parameter 'redist-flags' in event NHRP.57"
    ::= { nhrpEventObjects57 1 }

nhrpEventObjects58 OBJECT-IDENTITY
    STATUS current
    DESCRIPTION
        "Event NHRP.58
        Contents of the body of the NHRP authentication extension."
    ::= { nhrpEventsGroup 58 }

nhrp58-tab OBJECT-TYPE
    SYNTAX DisplayString
    MAX-ACCESS accessible-for-notify
    STATUS current
    DESCRIPTION
        "Parameter 'tab' in event NHRP.58"
    ::= { nhrpEventObjects58 1 }

nhrp58-auth-spi-value OBJECT-TYPE
    SYNTAX Integer32
    MAX-ACCESS accessible-for-notify
    STATUS current
    DESCRIPTION
        "Parameter 'auth-spi-value' in event NHRP.58"
    ::= { nhrpEventObjects58 2 }

nhrp58-authentication-data OBJECT-TYPE
    SYNTAX DisplayString
    MAX-ACCESS accessible-for-notify
    STATUS current
    DESCRIPTION
        "Parameter 'authentication-data' in event NHRP.58"
    ::= { nhrpEventObjects58 3 }


nhrpNotification1 NOTIFICATION-TYPE
    OBJECTS { 
              nhrp1-ip-address, 
              nhrp1-nbma 
            }
    STATUS current
    DESCRIPTION
        "Notification of Event NHRP.1

        Message: 'Cache update $1 nbma: $2'

        Parameters list:
              $1: nhrp1-ip-address
              $2: nhrp1-nbma

        NHRP cache is being updated with new information."
    ::= { nhrpNotificationsPrefix 1 }

nhrpNotification2 NOTIFICATION-TYPE
    OBJECTS { 
              nhrp2-ip-address 
            }
    STATUS current
    DESCRIPTION
        "Notification of Event NHRP.2

        Message: 'Send Purge Reply to $1'

        Parameters list:
              $1: nhrp2-ip-address

        A purge reply packet is being sent."
    ::= { nhrpNotificationsPrefix 2 }

nhrpNotification3 NOTIFICATION-TYPE
    OBJECTS { 
              nhrp3-id, 
              nhrp3-flags,
              nhrp3-src-length,
              nhrp3-dest-length 
            }
    STATUS current
    DESCRIPTION
        "Notification of Event NHRP.3

        Message: 'Mandatory header id:$1 flags:0x$2, src len:$3 dest len: $4'

        Parameters list:
              $1: nhrp3-id
              $2: nhrp3-flags
              $3: nhrp3-src-length
              $4: nhrp3-dest-length

        Information included in the header of the mandatory part of an NHRP 
        packet."
    ::= { nhrpNotificationsPrefix 3 }

nhrpNotification4 NOTIFICATION-TYPE
    OBJECTS { 
              nhrp4-paktype-string, 
              nhrp4-interval,
              nhrp4-request-id 
            }
    STATUS current
    DESCRIPTION
        "Notification of Event NHRP.4

        Message: 'Retransmitting $1 (retrans interval $2 secs), reqid: $3'

        Parameters list:
              $1: nhrp4-paktype-string
              $2: nhrp4-interval
              $3: nhrp4-request-id

        Retransmission of a NHRP packet with the reqid shown is being held now, 
        next retransmission will happen when the retransmission interval has 
        expired."
    ::= { nhrpNotificationsPrefix 4 }

nhrpNotification5 NOTIFICATION-TYPE
    OBJECTS { 
              nhrp5-interface-name 
            }
    STATUS current
    DESCRIPTION
        "Notification of Event NHRP.5

        Message: 'Suppressing broadcast forwarding - same interface: $1'

        Parameters list:
              $1: nhrp5-interface-name

        A NHRP broadcast packet is being discarded because it cannot be 
        forwarded over the same interface it has been received."
    ::= { nhrpNotificationsPrefix 5 }

nhrpNotification6 NOTIFICATION-TYPE
    OBJECTS { 
              nhrp6-ip-address-nhop 
            }
    STATUS current
    DESCRIPTION
        "Notification of Event NHRP.6

        Message: 'Cannot route packet for destination: $1'

        Parameters list:
              $1: nhrp6-ip-address-nhop

        The router cannot route a NHRP packet for one destination because
        the output interface is not of type ip tunnel."
    ::= { nhrpNotificationsPrefix 6 }

nhrpNotification7 NOTIFICATION-TYPE
    OBJECTS { 
              nhrp7-ip-address-nhop, 
              nhrp7-interface-name 
            }
    STATUS current
    DESCRIPTION
        "Notification of Event NHRP.7

        Message: 'Encapsulation failed for destination: $1 $2'

        Parameters list:
              $1: nhrp7-ip-address-nhop
              $2: nhrp7-interface-name

        The NHRP packet cannot be sent to the destination. The interface could
        be down or it could be out of memory buffers."
    ::= { nhrpNotificationsPrefix 7 }

nhrpNotification8 NOTIFICATION-TYPE
    OBJECTS { 
              nhrp8-bytes, 
              nhrp8-ip-address-nhop,
              nhrp8-interface-name 
            }
    STATUS current
    DESCRIPTION
        "Notification of Event NHRP.8

        Message: 'Output $1 bytes, dest: $2, $3'

        Parameters list:
              $1: nhrp8-bytes
              $2: nhrp8-ip-address-nhop
              $3: nhrp8-interface-name

        A NHRP packet is being transmitted to the destination shown."
    ::= { nhrpNotificationsPrefix 8 }

nhrpNotification9 NOTIFICATION-TYPE
    OBJECTS { 
              nhrp9-type, 
              nhrp9-bytes-sent 
            }
    STATUS current
    DESCRIPTION
        "Notification of Event NHRP.9

        Message: 'Datagram Sent $1, $2 bytes'

        Parameters list:
              $1: nhrp9-type
              $2: nhrp9-bytes-sent

        A NHRP packet is ready to be sent."
    ::= { nhrpNotificationsPrefix 9 }

nhrpNotification10 NOTIFICATION-TYPE
    OBJECTS { 
              nhrp10-ip-address-dest 
            }
    STATUS current
    DESCRIPTION
        "Notification of Event NHRP.10

        Message: 'Discarding src = dest = $1'

        Parameters list:
              $1: nhrp10-ip-address-dest

        The NHRP packet is being discarded because the source and the 
        destination are the same."
    ::= { nhrpNotificationsPrefix 10 }

nhrpNotification11 NOTIFICATION-TYPE
    OBJECTS { 
              nhrp11-ip-address-dest 
            }
    STATUS current
    DESCRIPTION
        "Notification of Event NHRP.11

        Message: 'Discarding: unknown interface, dest = $1'

        Parameters list:
              $1: nhrp11-ip-address-dest

        The router failed to find one valid interface of type ip tunnel in the
        current NBMA network for the destination."
    ::= { nhrpNotificationsPrefix 11 }

nhrpNotification12 NOTIFICATION-TYPE
    OBJECTS { 
              nhrp12-name 
            }
    STATUS current
    DESCRIPTION
        "Notification of Event NHRP.12

        Message: 'Packet out $1 would leave logical nbma network'

        Parameters list:
              $1: nhrp12-name

        The NHRP packet is being discarded because the output interface is not 
        in the current NBMA network."
    ::= { nhrpNotificationsPrefix 12 }

nhrpNotification13 NOTIFICATION-TYPE
    OBJECTS { 
              nhrp13-ip-address 
            }
    STATUS current
    DESCRIPTION
        "Notification of Event NHRP.13

        Message: 'Cannot route error packet for dest: $1'

        Parameters list:
              $1: nhrp13-ip-address

        The router failed to find one valid interface of type ip tunnel in the
        current NBMA network for the destination."
    ::= { nhrpNotificationsPrefix 13 }

nhrpNotification14 NOTIFICATION-TYPE
    OBJECTS { 
              nhrp14-ip-address, 
              nhrp14-if-name 
            }
    STATUS current
    DESCRIPTION
        "Notification of Event NHRP.14

        Message: 'We are egress router for $1 received on $2'

        Parameters list:
              $1: nhrp14-ip-address
              $2: nhrp14-if-name

        The NHRP packet destination is out of the current NBMA network."
    ::= { nhrpNotificationsPrefix 14 }

nhrpNotification15 NOTIFICATION-TYPE
    OBJECTS { 
              nhrp15-ip-address, 
              nhrp15-if-name 
            }
    STATUS current
    DESCRIPTION
        "Notification of Event NHRP.15

        Message: 'Found map entry for $1 received on $2'

        Parameters list:
              $1: nhrp15-ip-address
              $2: nhrp15-if-name

        An static map entry has being found in the routing table."
    ::= { nhrpNotificationsPrefix 15 }

nhrpNotification16 NOTIFICATION-TYPE
    OBJECTS { 
              nhrp16-packet-type, 
              nhrp16-ip-address 
            }
    STATUS current
    DESCRIPTION
        "Notification of Event NHRP.16

        Message: 'Cannot route $1 packet for dest: $2'

        Parameters list:
              $1: nhrp16-packet-type
              $2: nhrp16-ip-address

        The router failed to find one valid interface of type ip tunnel in the
        current NBMA network for the destination."
    ::= { nhrpNotificationsPrefix 16 }

nhrpNotification17 NOTIFICATION-TYPE
    OBJECTS { 
              nhrp17-id, 
              nhrp17-ip-address 
            }
    STATUS current
    DESCRIPTION
        "Notification of Event NHRP.17

        Message: 'Rejected Purge ACK id $1 for dest: $2'

        Parameters list:
              $1: nhrp17-id
              $2: nhrp17-ip-address

        A purge reply packet has being received but it had not been requested."
    ::= { nhrpNotificationsPrefix 17 }

nhrpNotification18 NOTIFICATION-TYPE
    OBJECTS { 
              nhrp18-version, 
              nhrp18-ip-address-src,
              nhrp18-ip-address-dest 
            }
    STATUS current
    DESCRIPTION
        "Notification of Event NHRP.18

        Message: 'Wrong protocol version $1, src: $2, dest: $3'

        Parameters list:
              $1: nhrp18-version
              $2: nhrp18-ip-address-src
              $3: nhrp18-ip-address-dest

        The fixed part of the NHRP packet holds a wrong protocol version."
    ::= { nhrpNotificationsPrefix 18 }

nhrpNotification19 NOTIFICATION-TYPE
    OBJECTS { 
              nhrp19-ip-address-src, 
              nhrp19-ip-address-dest 
            }
    STATUS current
    DESCRIPTION
        "Notification of Event NHRP.19

        Message: 'Bad checksum src: $1, dest: $2'

        Parameters list:
              $1: nhrp19-ip-address-src
              $2: nhrp19-ip-address-dest

        The received NHRP packet has wrong cheksum."
    ::= { nhrpNotificationsPrefix 19 }

nhrpNotification20 NOTIFICATION-TYPE
    OBJECTS { 
              nhrp20-ip-address 
            }
    STATUS current
    DESCRIPTION
        "Notification of Event NHRP.20

        Message: 'Send register to $1'

        Parameters list:
              $1: nhrp20-ip-address

        A NHRP register request is being sent to the destination shown."
    ::= { nhrpNotificationsPrefix 20 }

nhrpNotification21 NOTIFICATION-TYPE
    OBJECTS { 
              nhrp21-ip-address 
            }
    STATUS current
    DESCRIPTION
        "Notification of Event NHRP.21

        Message: 'Cache lookup returned negative response on $1'

        Parameters list:
              $1: nhrp21-ip-address

        The protocol failed to find a valid next hop entry in the cache for the 
        destination."
    ::= { nhrpNotificationsPrefix 21 }

nhrpNotification22 NOTIFICATION-TYPE
    OBJECTS { 
              nhrp22-ip-address, 
              nhrp22-type-ret,
              nhrp22-type-exp 
            }
    STATUS current
    DESCRIPTION
        "Notification of Event NHRP.22

        Message: 'Cache lookup on $1, bad address type returned $2, expected $3'

        Parameters list:
              $1: nhrp22-ip-address
              $2: nhrp22-type-ret
              $3: nhrp22-type-exp

        The cache has returned a wrong address type for the destination address."
    ::= { nhrpNotificationsPrefix 22 }

nhrpNotification23 NOTIFICATION-TYPE
    OBJECTS { 
              nhrp23-ip-address, 
              nhrp23-id 
            }
    STATUS current
    DESCRIPTION
        "Notification of Event NHRP.23

        Message: 'Expired purge request for $1, id: $2'

        Parameters list:
              $1: nhrp23-ip-address
              $2: nhrp23-id

        The period of retransmission of a purge request has expired, no more 
        retransmissions of this packet will be done."
    ::= { nhrpNotificationsPrefix 23 }

nhrpNotification24 NOTIFICATION-TYPE
    OBJECTS { 
              nhrp24-src-address, 
              nhrp24-nhop-address 
            }
    STATUS current
    DESCRIPTION
        "Notification of Event NHRP.24

        Message: 'Accepted ACK for purge of $1 for nhop address $2'

        Parameters list:
              $1: nhrp24-src-address
              $2: nhrp24-nhop-address

        A purge request packet has been received and the cache entry for the
        next hop address shown has been deleted."
    ::= { nhrpNotificationsPrefix 24 }

nhrpNotification25 NOTIFICATION-TYPE
    OBJECTS { 
              nhrp25-description, 
              nhrp25-error-code,
              nhrp25-offset 
            }
    STATUS current
    DESCRIPTION
        "Notification of Event NHRP.25

        Message: 'Madatory header error code: $1 ($2), offset: $3'

        Parameters list:
              $1: nhrp25-description
              $2: nhrp25-error-code
              $3: nhrp25-offset

        Contents of the header of the mandatory part of a NHRP error packet."
    ::= { nhrpNotificationsPrefix 25 }

nhrpNotification26 NOTIFICATION-TYPE
    OBJECTS { 
              nhrp26-ip-address, 
              nhrp26-ip-mask,
              nhrp26-longest-yes-no 
            }
    STATUS current
    DESCRIPTION
        "Notification of Event NHRP.26

        Message: 'Lookup cache entry $1 $2, longest = $3'

        Parameters list:
              $1: nhrp26-ip-address
              $2: nhrp26-ip-mask
              $3: nhrp26-longest-yes-no

        The NHRP protocol is searching its cache for a longest match entry."
    ::= { nhrpNotificationsPrefix 26 }

nhrpNotification27 NOTIFICATION-TYPE
    OBJECTS { 
              nhrp27-ip-address, 
              nhrp27-ip-mask 
            }
    STATUS current
    DESCRIPTION
        "Notification of Event NHRP.27

        Message: 'Adding cache entry $1 $2'

        Parameters list:
              $1: nhrp27-ip-address
              $2: nhrp27-ip-mask

        A new cache entry is being created in the NHRP protocol cache."
    ::= { nhrpNotificationsPrefix 27 }

nhrpNotification28 NOTIFICATION-TYPE
    OBJECTS { 
              nhrp28-ip-address, 
              nhrp28-ip-mask,
              nhrp28-if-name 
            }
    STATUS current
    DESCRIPTION
        "Notification of Event NHRP.28

        Message: 'Deleting cache entry $1 $2, ifc: $3'

        Parameters list:
              $1: nhrp28-ip-address
              $2: nhrp28-ip-mask
              $3: nhrp28-if-name

        A cache entry is being deleted from the NHRP protocol cache."
    ::= { nhrpNotificationsPrefix 28 }

nhrpNotification29 NOTIFICATION-TYPE
    OBJECTS { 
              nhrp29-ip-address, 
              nhrp29-ip-mask,
              nhrp29-entry-type 
            }
    STATUS current
    DESCRIPTION
        "Notification of Event NHRP.29

        Message: 'Rejected purge request of $1 $2, entry $3'

        Parameters list:
              $1: nhrp29-ip-address
              $2: nhrp29-ip-mask
              $3: nhrp29-entry-type

        A purge request packet has being received for a cache entry that is not
        dynamic type and for this reason it cannot be deleted from the NHRP 
        protocol cache."
    ::= { nhrpNotificationsPrefix 29 }

nhrpNotification30 NOTIFICATION-TYPE
    OBJECTS { 
              nhrp30-ip-address, 
              nhrp30-ip-mask 
            }
    STATUS current
    DESCRIPTION
        "Notification of Event NHRP.30

        Message: 'Refreshing cache entry for $1 $2'

        Parameters list:
              $1: nhrp30-ip-address
              $2: nhrp30-ip-mask

        The NHRP is trying to refresh a cache entry that is being used (packets 
        are traveling though this tunnel) and which is less than one minute time
        to expire and to be deleted."
    ::= { nhrpNotificationsPrefix 30 }

nhrpNotification31 NOTIFICATION-TYPE
    STATUS current
    DESCRIPTION
        "Notification of Event NHRP.31

        Message: 'Cache entry failed to delete'

        A NHRP protocol cache entry cannot be deleted."
    ::= { nhrpNotificationsPrefix 31 }

nhrpNotification32 NOTIFICATION-TYPE
    OBJECTS { 
              nhrp32-id 
            }
    STATUS current
    DESCRIPTION
        "Notification of Event NHRP.32

        Message: 'Failed to find cache entry matching reqid $1'

        Parameters list:
              $1: nhrp32-id

        There is no cache entry in NHRP protocol cache with the reqid received
        in the purge request packet."
    ::= { nhrpNotificationsPrefix 32 }

nhrpNotification33 NOTIFICATION-TYPE
    OBJECTS { 
              nhrp33-ifc-name 
            }
    STATUS current
    DESCRIPTION
        "Notification of Event NHRP.33

        Message: 'Cache clear for ifc $1'

        Parameters list:
              $1: nhrp33-ifc-name

        All dynamic entries in the NHRP protocol cache of the current interface
        are being deleted."
    ::= { nhrpNotificationsPrefix 33 }

nhrpNotification34 NOTIFICATION-TYPE
    OBJECTS { 
              nhrp34-ifc-name, 
              nhrp34-protocol-number 
            }
    STATUS current
    DESCRIPTION
        "Notification of Event NHRP.34

        Message: 'ifc $1 up -> nhrp up protocol $2'

        Parameters list:
              $1: nhrp34-ifc-name
              $2: nhrp34-protocol-number

        The NHRP protocol is changing its state from down to up because the
        tunnel interface state is now up."
    ::= { nhrpNotificationsPrefix 34 }

nhrpNotification35 NOTIFICATION-TYPE
    OBJECTS { 
              nhrp35-extension-name, 
              nhrp35-extension-length 
            }
    STATUS current
    DESCRIPTION
        "Notification of Event NHRP.35

        Message: 'Extension: $1, len: $2'

        Parameters list:
              $1: nhrp35-extension-name
              $2: nhrp35-extension-length

        Contents of the header of an extension in a NHRP packet."
    ::= { nhrpNotificationsPrefix 35 }

nhrpNotification36 NOTIFICATION-TYPE
    OBJECTS { 
              nhrp36-type, 
              nhrp36-nhop-ip 
            }
    STATUS current
    DESCRIPTION
        "Notification of Event NHRP.36

        Message: 'Send $1 reply for next hop $2'

        Parameters list:
              $1: nhrp36-type
              $2: nhrp36-nhop-ip

        A positive or negative reply is being sent in response to a request 
        packet for next hop resolution."
    ::= { nhrpNotificationsPrefix 36 }

nhrpNotification37 NOTIFICATION-TYPE
    OBJECTS { 
              nhrp37-string, 
              nhrp37-request-id 
            }
    STATUS current
    DESCRIPTION
        "Notification of Event NHRP.37

        Message: '$1, reqid: $2'

        Parameters list:
              $1: nhrp37-string
              $2: nhrp37-request-id

        An initial transmission or a retransmission of a resolution or
        registration request is being held. Also a message of end of 
        retransmissions could be shown."
    ::= { nhrpNotificationsPrefix 37 }

nhrpNotification38 NOTIFICATION-TYPE
    OBJECTS { 
              nhrp38-tab, 
              nhrp38-code,
              nhrp38-prefix,
              nhrp38-mtu,
              nhrp38-hold,
              nhrp38-pref 
            }
    STATUS current
    DESCRIPTION
        "Notification of Event NHRP.38

        Message: '$1CIE header code:0x$2 prefix:$3 MTU:$4 hold:$5, Pref:0x$6'

        Parameters list:
              $1: nhrp38-tab
              $2: nhrp38-code
              $3: nhrp38-prefix
              $4: nhrp38-mtu
              $5: nhrp38-hold
              $6: nhrp38-pref

        Contents of a CIE header (Client Information Entry) in a NHRP packet."
    ::= { nhrpNotificationsPrefix 38 }

nhrpNotification39 NOTIFICATION-TYPE
    OBJECTS { 
              nhrp39-tab, 
              nhrp39-nbma-addr,
              nhrp39-snbma-addr,
              nhrp39-prot-addr 
            }
    STATUS current
    DESCRIPTION
        "Notification of Event NHRP.39

        Message: '$1CIE addr = NBMA:$2 SNBMA:$3 ProtocolAddr:$4'

        Parameters list:
              $1: nhrp39-tab
              $2: nhrp39-nbma-addr
              $3: nhrp39-snbma-addr
              $4: nhrp39-prot-addr

        Contents of a CIE body (Client Information Entry) in a NHRP packet."
    ::= { nhrpNotificationsPrefix 39 }

nhrpNotification40 NOTIFICATION-TYPE
    OBJECTS { 
              nhrp40-pckt-type-name, 
              nhrp40-afn,
              nhrp40-protocol,
              nhrp40-hopcount 
            }
    STATUS current
    DESCRIPTION
        "Notification of Event NHRP.40

        Message: 'Fixed header type:$1 afn:0x$2 prot:0x$3 hop:$4'

        Parameters list:
              $1: nhrp40-pckt-type-name
              $2: nhrp40-afn
              $3: nhrp40-protocol
              $4: nhrp40-hopcount

        Contents of the fixed header of a NHRP packet."
    ::= { nhrpNotificationsPrefix 40 }

nhrpNotification41 NOTIFICATION-TYPE
    OBJECTS { 
              nhrp41-type, 
              nhrp41-bytes-rcvd,
              nhrp41-interface-name 
            }
    STATUS current
    DESCRIPTION
        "Notification of Event NHRP.41

        Message: 'Datagram Rcvd $1, $2 bytes, $3'

        Parameters list:
              $1: nhrp41-type
              $2: nhrp41-bytes-rcvd
              $3: nhrp41-interface-name

        A NHRP packet has been received. The type of packet, size and the
        interface the packet  was received in are shown."
    ::= { nhrpNotificationsPrefix 41 }

nhrpNotification42 NOTIFICATION-TYPE
    STATUS current
    DESCRIPTION
        "Notification of Event NHRP.42

        Message: 'Cache entry not found'

        There was no entry founded in the NHRP protocol cache for the last 
        cache lookup."
    ::= { nhrpNotificationsPrefix 42 }

nhrpNotification43 NOTIFICATION-TYPE
    OBJECTS { 
              nhrp43-ip-address 
            }
    STATUS current
    DESCRIPTION
        "Notification of Event NHRP.43

        Message: 'Send Purge Request to $1'

        Parameters list:
              $1: nhrp43-ip-address

        A purge request packet is being sent to the destination owning the
        ip address shown."
    ::= { nhrpNotificationsPrefix 43 }

nhrpNotification44 NOTIFICATION-TYPE
    OBJECTS { 
              nhrp44-ip-address-nbma, 
              nhrp44-ip-address-src,
              nhrp44-ip-address-dest 
            }
    STATUS current
    DESCRIPTION
        "Notification of Event NHRP.44

        Message: 'Error header src NBMA:$1 src:$2 dest:$3'

        Parameters list:
              $1: nhrp44-ip-address-nbma
              $2: nhrp44-ip-address-src
              $3: nhrp44-ip-address-dest

        Contents of a NHRP error packet header."
    ::= { nhrpNotificationsPrefix 44 }

nhrpNotification45 NOTIFICATION-TYPE
    OBJECTS { 
              nhrp45-err-string 
            }
    STATUS current
    DESCRIPTION
        "Notification of Event NHRP.45

        Message: 'NHRP Error: $1'

        Parameters list:
              $1: nhrp45-err-string

        A general error message."
    ::= { nhrpNotificationsPrefix 45 }

nhrpNotification46 NOTIFICATION-TYPE
    OBJECTS { 
              nhrp46-packet-type, 
              nhrp46-interface-name,
              nhrp46-dest-ip 
            }
    STATUS current
    DESCRIPTION
        "Notification of Event NHRP.46

        Message: 'Forwarding $1 to $2 destination $3'

        Parameters list:
              $1: nhrp46-packet-type
              $2: nhrp46-interface-name
              $3: nhrp46-dest-ip

        A NHRP packet is being forwarded through the interface shown to the 
        destination shown."
    ::= { nhrpNotificationsPrefix 46 }

nhrpNotification47 NOTIFICATION-TYPE
    OBJECTS { 
              nhrp47-interface-name 
            }
    STATUS current
    DESCRIPTION
        "Notification of Event NHRP.47

        Message: 'NHRP packet via $1, not configured for NHRP'

        Parameters list:
              $1: nhrp47-interface-name

        A NHRP packet has been received on an interface but this interface is 
        not configured for using NHRP protocol."
    ::= { nhrpNotificationsPrefix 47 }

nhrpNotification48 NOTIFICATION-TYPE
    OBJECTS { 
              nhrp48-interface-name, 
              nhrp48-protocol-type 
            }
    STATUS current
    DESCRIPTION
        "Notification of Event NHRP.48

        Message: 'NHRP if-down: $1 proto $2'

        Parameters list:
              $1: nhrp48-interface-name
              $2: nhrp48-protocol-type

        The NHRP protocol is changing its state from up to down for the
        interface shown."
    ::= { nhrpNotificationsPrefix 48 }

nhrpNotification49 NOTIFICATION-TYPE
    OBJECTS { 
              nhrp49-interface-name, 
              nhrp49-buffer-quota 
            }
    STATUS current
    DESCRIPTION
        "Notification of Event NHRP.49

        Message: 'NHRP-RATE: $1: Used $2'

        Parameters list:
              $1: nhrp49-interface-name
              $2: nhrp49-buffer-quota

        This is the number of requests made to the NHRP protocol for the
        interface shown before sending a NHRP resolution request packet. For 
        more information take a look at the 'nhrp use' command in the DMVPN 
        manual."
    ::= { nhrpNotificationsPrefix 49 }

nhrpNotification50 NOTIFICATION-TYPE
    OBJECTS { 
              nhrp50-ip-address, 
              nhrp50-ip-mask 
            }
    STATUS current
    DESCRIPTION
        "Notification of Event NHRP.50

        Message: 'Stale cache entry information for $1 $2'

        Parameters list:
              $1: nhrp50-ip-address
              $2: nhrp50-ip-mask

        The cache entry information shown is less than one minute to expire and
        be deleted."
    ::= { nhrpNotificationsPrefix 50 }

nhrpNotification51 NOTIFICATION-TYPE
    OBJECTS { 
              nhrp51-reqid, 
              nhrp51-no-ack-string 
            }
    STATUS current
    DESCRIPTION
        "Notification of Event NHRP.51

        Message: 'Rcvd no ack in resolution reply id: $1, $2'

        Parameters list:
              $1: nhrp51-reqid
              $2: nhrp51-no-ack-string

        A negative reply has been received for the reqid shown. The NAK code is
        shown."
    ::= { nhrpNotificationsPrefix 51 }

nhrpNotification52 NOTIFICATION-TYPE
    OBJECTS { 
              nhrp52-tab, 
              nhrp52-nbma-ip-address,
              nhrp52-src-ip-address,
              nhrp52-dest-ip-address 
            }
    STATUS current
    DESCRIPTION
        "Notification of Event NHRP.52

        Message: '$1Src NBMA: $2, src: $3, dest: $4'

        Parameters list:
              $1: nhrp52-tab
              $2: nhrp52-nbma-ip-address
              $3: nhrp52-src-ip-address
              $4: nhrp52-dest-ip-address

        Contents of the body of the mandatory part of a NHRP packet."
    ::= { nhrpNotificationsPrefix 52 }

nhrpNotification53 NOTIFICATION-TYPE
    OBJECTS { 
              nhrp53-tab, 
              nhrp53-packet-length,
              nhrp53-protocol-version,
              nhrp53-nbma-length,
              nhrp53-sub-nbma-length 
            }
    STATUS current
    DESCRIPTION
        "Notification of Event NHRP.53

        Message: '$1len:$2 version:0x$3 shtl:$4 sstl:$5'

        Parameters list:
              $1: nhrp53-tab
              $2: nhrp53-packet-length
              $3: nhrp53-protocol-version
              $4: nhrp53-nbma-length
              $5: nhrp53-sub-nbma-length

        Contents of the body of the fixed part of a NHRP packet."
    ::= { nhrpNotificationsPrefix 53 }

nhrpNotification54 NOTIFICATION-TYPE
    OBJECTS { 
              nhrp54-interface-name 
            }
    STATUS current
    DESCRIPTION
        "Notification of Event NHRP.54

        Message: 'Don't know how to resolve NBMA address for $1'

        Parameters list:
              $1: nhrp54-interface-name

        The router is not able to resolve the NBMA address of the output
        interface."
    ::= { nhrpNotificationsPrefix 54 }

nhrpNotification55 NOTIFICATION-TYPE
    OBJECTS { 
              nhrp55-interface-in-name, 
              nhrp55-interface-out-name 
            }
    STATUS current
    DESCRIPTION
        "Notification of Event NHRP.55

        Message: 'Forwarding packet within same fabric $1 -> $2'

        Parameters list:
              $1: nhrp55-interface-in-name
              $2: nhrp55-interface-out-name

        The input and output interfaces are in the same NBMA network."
    ::= { nhrpNotificationsPrefix 55 }

nhrpNotification56 NOTIFICATION-TYPE
    OBJECTS { 
              nhrp56-net-number, 
              nhrp56-net-mask 
            }
    STATUS current
    DESCRIPTION
        "Notification of Event NHRP.56

        Message: 'Redist callback: $1 $2'

        Parameters list:
              $1: nhrp56-net-number
              $2: nhrp56-net-mask

        An entry in the routing table has been created and the NHRP protocol 
        will be informed of any change in this entry of the routing table."
    ::= { nhrpNotificationsPrefix 56 }

nhrpNotification57 NOTIFICATION-TYPE
    OBJECTS { 
              nhrp57-redist-flags 
            }
    STATUS current
    DESCRIPTION
        "Notification of Event NHRP.57

        Message: 'Redist mask now $1'

        Parameters list:
              $1: nhrp57-redist-flags

        The NHRP protocol marks a routing table entry so as to be informed of
        any change that this entry could suffer."
    ::= { nhrpNotificationsPrefix 57 }

nhrpNotification58 NOTIFICATION-TYPE
    OBJECTS { 
              nhrp58-tab, 
              nhrp58-auth-spi-value,
              nhrp58-authentication-data 
            }
    STATUS current
    DESCRIPTION
        "Notification of Event NHRP.58

        Message: '$1spi: $2 data: $3'

        Parameters list:
              $1: nhrp58-tab
              $2: nhrp58-auth-spi-value
              $3: nhrp58-authentication-data

        Contents of the body of the NHRP authentication extension."
    ::= { nhrpNotificationsPrefix 58 }


END
