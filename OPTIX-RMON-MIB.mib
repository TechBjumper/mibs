--
-- OPTIX-RMON-MIB.mib
-- MIB generated by MG-SOFT Visual MIB Builder Version 3.0 Build 253
-- Wednesday, February 22, 2006 at 18:31:53
--

-- =================================================================
-- Copyright (C) 2006 by HUAWEI TECHNOLOGIES. All rights reserved
-- 
-- Description:
-- Reference:
-- Version: V1.00
-- History:
-- <author>,<date>,<contents>
-- =================================================================
-- 

	OPTIX-RMON-MIB DEFINITIONS ::= BEGIN
 
		IMPORTS
			optixCommon			
				FROM OPTIX-OID-MIB			
			OBJECT-GROUP, MODULE-COMPLIANCE, NOTIFICATION-GROUP			
				FROM SNMPv2-CONF			
			Unsigned32, Counter64, OBJECT-TYPE, MODULE-IDENTITY, NOTIFICATION-TYPE			
				FROM SNMPv2-SMI			
			DateAndTime, TEXTUAL-CONVENTION			
				FROM SNMPv2-TC;
	
	
-- -------------------------------------------------------------------------
-- Module Identity
-- -------------------------------------------------------------------------
		optixRmonMib MODULE-IDENTITY 
			LAST-UPDATED "200602250000Z"
			ORGANIZATION 
				"Huawei Technologies Co.,Ltd."
			CONTACT-INFO 
				"R&D Building
				Huawei Technologies Co., Ltd.
				Bantian, Longgang District 
				Shenzhen, P. R. China
				http://www.huawei.com
				Zip:518129
				E-mail:support@huawei.com
				"
			DESCRIPTION 
				"This module describes the private Rmon 
				of Huawei transmit platform."
			REVISION "200602250000Z"
			DESCRIPTION
				"The initial revision of this MIB module."
			::= { optixCommon 35 }
		
	
--
-- Textual conventions
--
	
--  -------------------------------------------------------------------------
-- RMON Performance monitor type
-- ------------------------------------------------------------------------- 
-- 
		PerformanceType ::= TEXTUAL-CONVENTION
			STATUS current
			DESCRIPTION 
				"RMON parameters,sorted by ID"
			SYNTAX INTEGER
				{
				etherStatsPkts64Octets(101),
				etherStatsPkts65to127Octets(102),
				etherStatsPkts128to255Octets(103),
				etherStatsPkts256to511Octets(104),
				etherStatsPkts512to1023Octets(105),
				etherStatsPkts1024to1518Octets(106),
				etherStatsTranPkts64Octets(107),
				etherStatsTranPkts65to127Octets(108),
				etherStatsTranPkts128to255Octets(109),
				etherStatsTranPkts256to511Octets(110),
				etherStatsTranPkts512to1023Octets(111),
				etherStatsTranPkts1024to1518Octets(112),
				etherStatsInUcastPkts(113),
				etherStatsMulticastPkts(114),
				etherStatsBroadcastPkts(115),
				etherStatsOutUcastPkts(116),
				etherStatsOutMulticastPkts(117),
				etherStatsOutBroadcastPkts(118),
				etherStatsInPauseFrames(119),
				etherStatsOutPauseFrames(120),
				etherStatsDropEvents(121),
				etherStatsUndersizePkts(122),
				etherStatsOversizePkts(123),
				etherStatsFragments(124),
				etherStatsJabbers(125),
				etherStatsInGoodOctets(126),
				etherStatsOutGoodOctets(127),
				etherStatsInBadOctets(128),
				etherStatsOutBadOctets(129),
				etherStatsCollisions(130),
				etherStatsAlignmentErrors(131),
				etherStatsFCSErrors(132),
				etherStatsSingleCollisionFrames(133),
				etherStatsMultipleCollisionFrames(134),
				etherStatsLateCollisions(135),
				etherStatsExcessiveCollisions(136),
				etherStatsDeferredTransmissions(137),
				etherStatsCarrierSenseErrors(138),
				etherStatsPkts1519toMTUOctets(139),
				etherStatsTranPkts1519toMTUOctets(140),
				etherStatsRxTxPkts64Octets(141),
				etherStatsRxTxPkts65to127Octets(142),
				etherStatsRxTxPkts128to255Octets(143),
				etherStatsRxTxPkts256to511Octets(144),
				etherStatsRxTxPkts512to1023Octets(145),
				etherStatsRxTxPkts1024to1518Octets(146),
				etherStatsRxTxPkts1519toMTUOctets(147),
				etherStatsInControlFrames(194),
				etherStatsOutControlFrames(195),
				etherStatsOutDropEvents(196),
				etherStatsOutOversizePkts(197),
				etherStatsOutPkts(198),
				etherStatsOutOctets(199),
				etherStatsOctets(200),
				etherStatsPkts(201),
				etherStatsCRCAlignErrors(202),
				etherHistoryUtilization(203)
				}
			
		OwnerString ::= TEXTUAL-CONVENTION
			STATUS current
			DESCRIPTION 
				"This data type is used to model an administratively
				assigned name of the owner of a resource. Implementations
				must accept values composed of well-formed NVT ASCII
				sequences. In addition, implementations should accept
				values composed of well-formed UTF-8 sequences.
				
				It is suggested that this name contain one or more of
				the following: IP address, management station name,
				network manager's name, location, or phone number.
				In some cases the agent itself will be the owner of
				an entry.  In these cases, this string shall be set
				to a string starting with 'monitor'.
				
				SNMP access control is articulated entirely in terms
				of the contents of MIB views; access to a particular
				SNMP object instance depends only upon its presence
				or absence in a particular MIB view and never upon
				its value or the value of related object instances.
				Thus, objects of this type afford resolution of
				resource contention only among cooperating
				managers; they realize no access control function
				with respect to uncooperative parties."
			SYNTAX OCTET STRING (SIZE (0..127))
			
	
--
-- Node definitions
--
	
-- -------------------------------------------------------------------------
-- This module icludes following nodes
-- -------------------------------------------------------------------------   
		-- 1.3.6.1.4.1.2011.2.25.3.35.0
		rmonTraps OBJECT IDENTIFIER ::= { optixRmonMib 0 }
		
-- *******************************************************************
-- rmon trap    
-- *******************************************************************
		-- 1.3.6.1.4.1.2011.2.25.3.35.0.10
		trapCommonObjects OBJECT IDENTIFIER ::= { rmonTraps 10 }
		
		-- 1.3.6.1.4.1.2011.2.25.3.35.0.10.10
		rptAlarmIndex OBJECT-TYPE
			SYNTAX Unsigned32
			MAX-ACCESS accessible-for-notify
			STATUS current
			DESCRIPTION
				"alarmIndex"
			::= { trapCommonObjects 10 }
		
		-- 1.3.6.1.4.1.2011.2.25.3.35.0.10.20
		rptAlarmVariable OBJECT-TYPE
			SYNTAX PerformanceType
			MAX-ACCESS accessible-for-notify
			STATUS current
			DESCRIPTION
				"alarmVariable"
			::= { trapCommonObjects 20 }
		
		-- 1.3.6.1.4.1.2011.2.25.3.35.0.10.30
		rptAlarmSampleType OBJECT-TYPE
			SYNTAX INTEGER
				{
				absoluteValue(1),
				deltaValue(2)
				}
			MAX-ACCESS accessible-for-notify
			STATUS current
			DESCRIPTION
				"alarmSampleType"
			::= { trapCommonObjects 30 }
		
		-- 1.3.6.1.4.1.2011.2.25.3.35.0.10.40
		rptAlarmValue OBJECT-TYPE
			SYNTAX Unsigned32
			MAX-ACCESS accessible-for-notify
			STATUS current
			DESCRIPTION
				"alarmValue"
			::= { trapCommonObjects 40 }
		
		-- 1.3.6.1.4.1.2011.2.25.3.35.0.10.50
		rptAlarmRisingThreshold OBJECT-TYPE
			SYNTAX Unsigned32
			MAX-ACCESS accessible-for-notify
			STATUS current
			DESCRIPTION
				"alarmRisingThreshold"
			::= { trapCommonObjects 50 }
		
		-- 1.3.6.1.4.1.2011.2.25.3.35.0.10.60
		rptAlarmFallingThreshold OBJECT-TYPE
			SYNTAX Unsigned32
			MAX-ACCESS accessible-for-notify
			STATUS current
			DESCRIPTION
				"alarmFallingThreshold"
			::= { trapCommonObjects 60 }
		
		-- 1.3.6.1.4.1.2011.2.25.3.35.0.10.70
		rptAlarmInterval OBJECT-TYPE
			SYNTAX Unsigned32
			MAX-ACCESS accessible-for-notify
			STATUS current
			DESCRIPTION
				"alarmInterval"
			::= { trapCommonObjects 70 }
		
		-- 1.3.6.1.4.1.2011.2.25.3.35.0.10.80
		rptAlarmDateTime OBJECT-TYPE
			SYNTAX DateAndTime
			MAX-ACCESS accessible-for-notify
			STATUS current
			DESCRIPTION
				"Date and time."
			::= { trapCommonObjects 80 }
		
-- ----------------------------------------------------------
-- two traps RisingAlaram and FallingAlarm
-- ---------------------------------------------------------     
		-- 1.3.6.1.4.1.2011.2.25.3.35.0.20
		optixTrapsRmon OBJECT IDENTIFIER ::= { rmonTraps 20 }
		
		-- 1.3.6.1.4.1.2011.2.25.3.35.0.20.1
		rmonRisingAlarm NOTIFICATION-TYPE
			OBJECTS { rptAlarmIndex, rptAlarmVariable, rptAlarmSampleType, rptAlarmValue, rptAlarmRisingThreshold, 
				rptAlarmInterval, rptAlarmDateTime }
			STATUS current
			DESCRIPTION 
				"The SNMP trap that is generated when an alarm
				entry crosses its rising threshold and generates
				an event that is configured for sending SNMP
				traps."
			::= { optixTrapsRmon 1 }
		
		-- 1.3.6.1.4.1.2011.2.25.3.35.0.20.2
		rmonFallingAlarm NOTIFICATION-TYPE
			OBJECTS { rptAlarmIndex, rptAlarmVariable, rptAlarmSampleType, rptAlarmValue, rptAlarmFallingThreshold, 
				rptAlarmInterval, rptAlarmDateTime }
			STATUS current
			DESCRIPTION 
				"The SNMP trap that is generated when an alarm
				entry crosses its falling threshold and generates
				an event that is configured for sending SNMP
				traps."
			::= { optixTrapsRmon 2 }
		
		-- 1.3.6.1.4.1.2011.2.25.3.35.10
		statistics OBJECT IDENTIFIER ::= { optixRmonMib 10 }
		
-- *******************************************************************
-- rmon etherStatsTable    
-- ********************************************************************** 
		-- 1.3.6.1.4.1.2011.2.25.3.35.10.10
		etherStatsTable OBJECT-TYPE
			SYNTAX SEQUENCE OF EtherStatsEntry
			MAX-ACCESS not-accessible
			STATUS current
			DESCRIPTION
				"A list of Ethernet statistics entries."
			::= { statistics 10 }
		
		-- 1.3.6.1.4.1.2011.2.25.3.35.10.10.1
		etherStatsEntry OBJECT-TYPE
			SYNTAX EtherStatsEntry
			MAX-ACCESS not-accessible
			STATUS current
			DESCRIPTION
				"A collection of statistics kept for a particular
				Ethernet interface.  As an example, an instance of the
				etherStatsPkts object might be named etherStatsPkts.1"
			INDEX { etherStatsIndex }
			::= { etherStatsTable 1 }
		
		EtherStatsEntry ::=
			SEQUENCE { 
				etherStatsIndex
					Unsigned32,
				etherStatsDropEvents
					Counter64,
				etherStatsOctets
					Counter64,
				etherStatsPkts
					Counter64,
				etherStatsBroadcastPkts
					Counter64,
				etherStatsMulticastPkts
					Counter64,
				etherStatsCRCAlignErrors
					Counter64,
				etherStatsUndersizePkts
					Counter64,
				etherStatsOversizePkts
					Counter64,
				etherStatsFragments
					Counter64,
				etherStatsJabbers
					Counter64,
				etherStatsCollisions
					Counter64,
				etherStatsPkts64Octets
					Counter64,
				etherStatsPkts65to127Octets
					Counter64,
				etherStatsPkts128to255Octets
					Counter64,
				etherStatsPkts256to511Octets
					Counter64,
				etherStatsPkts512to1023Octets
					Counter64,
				etherStatsPkts1024to1518Octets
					Counter64
			 }

		-- 1.3.6.1.4.1.2011.2.25.3.35.10.10.1.1
		etherStatsIndex OBJECT-TYPE
			SYNTAX Unsigned32
			MAX-ACCESS read-only
			STATUS current
			DESCRIPTION
				"The value of this object uniquely identifies this
				etherStats entry.        
				
				etherStatsIndex of huawei optix devices can be described as following, 
				etherStatsIndex consists of SLOT_ID,PORT_ID and SUB_PORT_ID.       
				etherStatsIndex = SUB_PORT_ID<<31 + SLOT_ID<<24 + PORT_ID; 
				1) bit31(1bit) SUB_PORT_ID: 
				    0 - SUB_PORT_1(east), 1 - SUB_PORT_2(west),
				    for sonet,this para is 0 ,no other means;
				2) 24bit~30bit(7bits) SLOT_ID:   slot id;
				3) 0bit~15bit(16bits) PORT_ID:   mac port id;
				
				For example:
				1:etherStatsIndex.83886081 (gauge) 83886081
				   83886081 = 0x05000001 can be translated as Slot-5, Port-1;
				2:etherStatsIndex.83886082 (gauge) 83886082 
				   83886082 = 0x05000002 can be translated as Slot-5, Port-2;
				"
			::= { etherStatsEntry 1 }
		
		-- 1.3.6.1.4.1.2011.2.25.3.35.10.10.1.3
		etherStatsDropEvents OBJECT-TYPE
			SYNTAX Counter64
			MAX-ACCESS read-only
			STATUS current
			DESCRIPTION
				"The total number of events in which packets
				were dropped by the probe due to lack of resources.
				Note that this number is not necessarily the number of
				packets dropped; it is just the number of times this
				condition has been detected."
			::= { etherStatsEntry 3 }
		
		-- 1.3.6.1.4.1.2011.2.25.3.35.10.10.1.4
		etherStatsOctets OBJECT-TYPE
			SYNTAX Counter64
			UNITS "Octets"
			MAX-ACCESS read-only
			STATUS current
			DESCRIPTION
				"The total number of octets of data (including
				those in bad packets) received on the
				network (excluding framing bits but including
				FCS octets).
				This object can be used as a reasonable estimate of
				10-Megabit ethernet utilization.  If greater precision is
				desired, the etherStatsPkts and etherStatsOctets objects
				should be sampled before and after a common interval.  The
				differences in the sampled values are Pkts and Octets,
				respectively, and the number of seconds in the interval is
				Interval.  These values are used to calculate the Utilization
				as follows:
				
				                 Pkts * (9.6 + 6.4) + (Octets * .8)
				 Utilization = -------------------------------------
				                         Interval * 10,000
				
				The result of this equation is the value Utilization which
				is the percent utilization of the ethernet segment on a
				scale of 0 to 100 percent."
			::= { etherStatsEntry 4 }
		
		-- 1.3.6.1.4.1.2011.2.25.3.35.10.10.1.5
		etherStatsPkts OBJECT-TYPE
			SYNTAX Counter64
			UNITS "Packets"
			MAX-ACCESS read-only
			STATUS current
			DESCRIPTION
				"The total number of packets (including bad packets,
				broadcast packets, and multicast packets) received."
			::= { etherStatsEntry 5 }
		
		-- 1.3.6.1.4.1.2011.2.25.3.35.10.10.1.6
		etherStatsBroadcastPkts OBJECT-TYPE
			SYNTAX Counter64
			UNITS "Packets"
			MAX-ACCESS read-only
			STATUS current
			DESCRIPTION
				"The total number of good packets received that were
				directed to the broadcast address.  Note that this
				does not include multicast packets."
			::= { etherStatsEntry 6 }
		
		-- 1.3.6.1.4.1.2011.2.25.3.35.10.10.1.7
		etherStatsMulticastPkts OBJECT-TYPE
			SYNTAX Counter64
			UNITS "Packets"
			MAX-ACCESS read-only
			STATUS current
			DESCRIPTION
				"The total number of good packets received that were
				directed to a multicast address.  Note that this number
				does not include packets directed to the broadcast
				address."
			::= { etherStatsEntry 7 }
		
		-- 1.3.6.1.4.1.2011.2.25.3.35.10.10.1.8
		etherStatsCRCAlignErrors OBJECT-TYPE
			SYNTAX Counter64
			UNITS "Packets"
			MAX-ACCESS read-only
			STATUS current
			DESCRIPTION
				"The total number of packets received that
				had a length (excluding framing bits, but
				including FCS octets) of between 64 and 1518
				octets, inclusive, but had either a bad
				Frame Check Sequence (FCS) with an integral
				number of octets (FCS Error) or a bad FCS with
				a non-integral number of octets (Alignment Error)."
			::= { etherStatsEntry 8 }
		
		-- 1.3.6.1.4.1.2011.2.25.3.35.10.10.1.9
		etherStatsUndersizePkts OBJECT-TYPE
			SYNTAX Counter64
			UNITS "Packets"
			MAX-ACCESS read-only
			STATUS current
			DESCRIPTION
				"The total number of packets received that were
				less than 64 octets long (excluding framing bits,
				but including FCS octets) and were otherwise well
				formed."
			::= { etherStatsEntry 9 }
		
		-- 1.3.6.1.4.1.2011.2.25.3.35.10.10.1.10
		etherStatsOversizePkts OBJECT-TYPE
			SYNTAX Counter64
			UNITS "Packets"
			MAX-ACCESS read-only
			STATUS current
			DESCRIPTION
				"The total number of packets received that were
				longer than 1518 octets (excluding framing bits,
				but including FCS octets) and were otherwise
				well formed."
			::= { etherStatsEntry 10 }
		
		-- 1.3.6.1.4.1.2011.2.25.3.35.10.10.1.11
		etherStatsFragments OBJECT-TYPE
			SYNTAX Counter64
			UNITS "Packets"
			MAX-ACCESS read-only
			STATUS current
			DESCRIPTION
				"The total number of packets received that were less than
				64 octets in length (excluding framing bits but including
				FCS octets) and had either a bad Frame Check Sequence
				(FCS) with an integral number of octets (FCS Error) or a
				bad FCS with a non-integral number of octets (Alignment
				Error).
				
				Note that it is entirely normal for etherStatsFragments to
				increment.  This is because it counts both runts (which are
				normal occurrences due to collisions) and noise hits."
			::= { etherStatsEntry 11 }
		
		-- 1.3.6.1.4.1.2011.2.25.3.35.10.10.1.12
		etherStatsJabbers OBJECT-TYPE
			SYNTAX Counter64
			UNITS "Packets"
			MAX-ACCESS read-only
			STATUS current
			DESCRIPTION
				"The total number of packets received that were
				longer than 1518 octets (excluding framing bits,
				but including FCS octets), and had either a bad
				Frame Check Sequence (FCS) with an integral number
				of octets (FCS Error) or a bad FCS with a non-integral
				number of octets (Alignment Error).
				
				Note that this definition of jabber is different
				than the definition in IEEE-802.3 section 8.2.1.5
				(10BASE5) and section 10.3.1.4 (10BASE2).  These
				documents define jabber as the condition where any
				packet exceeds 20 ms.  The allowed range to detect
				jabber is between 20 ms and 150 ms."
			::= { etherStatsEntry 12 }
		
		-- 1.3.6.1.4.1.2011.2.25.3.35.10.10.1.13
		etherStatsCollisions OBJECT-TYPE
			SYNTAX Counter64
			UNITS "Collisions"
			MAX-ACCESS read-only
			STATUS current
			DESCRIPTION
				"The best estimate of the total number of collisions
				on this Ethernet segment.
				
				The value returned will depend on the location of the
				RMON probe. Section 8.2.1.3 (10BASE-5) and section
				10.3.1.3 (10BASE-2) of IEEE standard 802.3 states that a
				station must detect a collision, in the receive mode, if
				three or more stations are transmitting simultaneously.  A
				repeater port must detect a collision when two or more
				stations are transmitting simultaneously.  Thus a probe
				placed on a repeater port could record more collisions
				than a probe connected to a station on the same segment
				would.
				
				Probe location plays a much smaller role when considering
				10BASE-T.  14.2.1.4 (10BASE-T) of IEEE standard 802.3
				defines a collision as the simultaneous presence of signals
				on the DO and RD circuits (transmitting and receiving
				at the same time).  A 10BASE-T station can only detect
				collisions when it is transmitting.  Thus probes placed on
				a station and a repeater, should report the same number of
				collisions.
				
				Note also that an RMON probe inside a repeater should
				ideally report collisions between the repeater and one or
				more other hosts (transmit collisions as defined by IEEE
				802.3k) plus receiver collisions observed on any coax
				segments to which the repeater is connected."
			::= { etherStatsEntry 13 }
		
		-- 1.3.6.1.4.1.2011.2.25.3.35.10.10.1.14
		etherStatsPkts64Octets OBJECT-TYPE
			SYNTAX Counter64
			UNITS "Packets"
			MAX-ACCESS read-only
			STATUS current
			DESCRIPTION
				"The total number of packets (including bad
				packets) received that were 64 octets in length
				(excluding framing bits but including FCS octets)."
			::= { etherStatsEntry 14 }
		
		-- 1.3.6.1.4.1.2011.2.25.3.35.10.10.1.15
		etherStatsPkts65to127Octets OBJECT-TYPE
			SYNTAX Counter64
			UNITS "Packets"
			MAX-ACCESS read-only
			STATUS current
			DESCRIPTION
				"The total number of packets (including bad
				packets) received that were between
				65 and 127 octets in length inclusive
				(excluding framing bits but including FCS octets)."
			::= { etherStatsEntry 15 }
		
		-- 1.3.6.1.4.1.2011.2.25.3.35.10.10.1.16
		etherStatsPkts128to255Octets OBJECT-TYPE
			SYNTAX Counter64
			UNITS "Packets"
			MAX-ACCESS read-only
			STATUS current
			DESCRIPTION
				"The total number of packets (including bad
				packets) received that were between
				128 and 255 octets in length inclusive
				(excluding framing bits but including FCS octets)."
			::= { etherStatsEntry 16 }
		
		-- 1.3.6.1.4.1.2011.2.25.3.35.10.10.1.17
		etherStatsPkts256to511Octets OBJECT-TYPE
			SYNTAX Counter64
			UNITS "Packets"
			MAX-ACCESS read-only
			STATUS current
			DESCRIPTION
				"The total number of packets (including bad
				packets) received that were between
				256 and 511 octets in length inclusive
				(excluding framing bits but including FCS octets)."
			::= { etherStatsEntry 17 }
		
		-- 1.3.6.1.4.1.2011.2.25.3.35.10.10.1.18
		etherStatsPkts512to1023Octets OBJECT-TYPE
			SYNTAX Counter64
			UNITS "Packets"
			MAX-ACCESS read-only
			STATUS current
			DESCRIPTION
				"The total number of packets (including bad
				packets) received that were between
				512 and 1023 octets in length inclusive
				(excluding framing bits but including FCS octets)."
			::= { etherStatsEntry 18 }
		
		-- 1.3.6.1.4.1.2011.2.25.3.35.10.10.1.19
		etherStatsPkts1024to1518Octets OBJECT-TYPE
			SYNTAX Counter64
			UNITS "Packets"
			MAX-ACCESS read-only
			STATUS current
			DESCRIPTION
				"The total number of packets (including bad
				packets) received that were between
				1024 and 1518 octets in length inclusive
				(excluding framing bits but including FCS octets)."
			::= { etherStatsEntry 19 }
		
-- *************************************************************************************** 
-- rmon extend etherStats
-- ***************************************************************************************
		-- 1.3.6.1.4.1.2011.2.25.3.35.10.20
		etherExStatsTable OBJECT-TYPE
			SYNTAX SEQUENCE OF EtherExStatsEntry
			MAX-ACCESS not-accessible
			STATUS current
			DESCRIPTION
				"A list of Ethernet statistics entries."
			::= { statistics 20 }
		
		-- 1.3.6.1.4.1.2011.2.25.3.35.10.20.1
		etherExStatsEntry OBJECT-TYPE
			SYNTAX EtherExStatsEntry
			MAX-ACCESS not-accessible
			STATUS current
			DESCRIPTION
				"A collection of statistics kept for a particular
				Ethernet interface.  As an example, an instance of the
				etherStatsPkts object might be named etherStatsPkts.1"
			INDEX { etherExStatsIndex }
			::= { etherExStatsTable 1 }
		
		EtherExStatsEntry ::=
			SEQUENCE { 
				etherExStatsIndex
					Unsigned32,
				etherStatsPkts1519toMTUOctets
					Counter64,
				etherStatsTranPkts64Octets
					Counter64,
				etherStatsTranPkts65to127Octets
					Counter64,
				etherStatsTranPkts128to255Octets
					Counter64,
				etherStatsTranPkts256to511Octets
					Counter64,
				etherStatsTranPkts512to1023Octets
					Counter64,
				etherStatsTranPkts1024to1518Octets
					Counter64,
				etherStatsTranPkts1519toMTUOctets
					Counter64,
				etherStatsRxTxPkts64Octets
					Counter64,
				etherStatsRxTxPkts65to127Octets
					Counter64,
				etherStatsRxTxPkts128to255Octets
					Counter64,
				etherStatsRxTxPkts256to511Octets
					Counter64,
				etherStatsRxTxPkts512to1023Octets
					Counter64,
				etherStatsRxTxPkts1024to1518Octets
					Counter64,
				etherStatsRxTxPkts1519toMTUOctets
					Counter64,
				etherStatsInUcastPkts
					Counter64,
				etherStatsOutUcastPkts
					Counter64,
				etherStatsInPauseFrames
					Counter64,
				etherStatsOutPauseFrames
					Counter64,
				etherStatsOutMulticastPkts
					Counter64,
				etherStatsOutBroadcastPkts
					Counter64,
				etherStatsInGoodOctets
					Counter64,
				etherStatsOutGoodOctets
					Counter64,
				etherStatsInBadOctets
					Counter64,
				etherStatsOutBadOctets
					Counter64,
				etherStatsAlignmentErrors
					Counter64,
				etherStatsFCSErrors
					Counter64,
				etherStatsSingleCollisionFrames
					Counter64,
				etherStatsMultipleCollisionFrames
					Counter64,
				etherStatsLateCollisions
					Counter64,
				etherStatsExcessiveCollisions
					Counter64,
				etherStatsDeferredTransmissions
					Counter64,
				etherStatsCarrierSenseErrors
					Counter64,
				etherStatsInControlFrames
					Counter64,
				etherStatsOutControlFrames
					Counter64,
				etherStatsOutDropEvents
					Counter64,
				etherStatsOutOversizePkts
					Counter64,
				etherStatsOutPkts
					Counter64,
				etherStatsOutOctets
					Counter64
			 }

		-- 1.3.6.1.4.1.2011.2.25.3.35.10.20.1.1
		etherExStatsIndex OBJECT-TYPE
			SYNTAX Unsigned32
			MAX-ACCESS read-only
			STATUS current
			DESCRIPTION
				"The value of this object uniquely identifies this
				etherExStats entry.        
				
				etherExStatsIndex of huawei optix devices can be described as following, 
				etherExStatsIndex consists of SLOT_ID,PORT_ID and SUB_PORT_ID.         
				etherExStatsIndex = SUB_PORT_ID<<31 + SLOT_ID<<24 + PORT_ID; 
				1) bit31(1bit) SUB_PORT_ID: 
				    0 - SUB_PORT_1(east), 1 - SUB_PORT_2(west),
				    for sonet,this para is 0 ,no other means;             
				2) 24bit~30bit(7bits) SLOT_ID:   slot id;   	       
				3) 0bit~15bit(16bits) PORT_ID:   mac port id;
				
				For example: 
				   1: etherExStatsIndex.117440513 (gauge) 117440513  
				      117440513 = 0x07000001(hex) can be translated as Slot-7, Port-1;
				   2: etherExStatsIndex.117440514 (gauge) 117440514 
				      117440514 = 0x07000002 can be translated as Slot-7, Port-2;     
				"
			::= { etherExStatsEntry 1 }
		
		-- 1.3.6.1.4.1.2011.2.25.3.35.10.20.1.3
		etherStatsPkts1519toMTUOctets OBJECT-TYPE
			SYNTAX Counter64
			UNITS "Packets"
			MAX-ACCESS read-only
			STATUS current
			DESCRIPTION
				" "
			::= { etherExStatsEntry 3 }
		
		-- 1.3.6.1.4.1.2011.2.25.3.35.10.20.1.4
		etherStatsTranPkts64Octets OBJECT-TYPE
			SYNTAX Counter64
			UNITS "Packets"
			MAX-ACCESS read-only
			STATUS current
			DESCRIPTION
				" "
			::= { etherExStatsEntry 4 }
		
		-- 1.3.6.1.4.1.2011.2.25.3.35.10.20.1.5
		etherStatsTranPkts65to127Octets OBJECT-TYPE
			SYNTAX Counter64
			UNITS "Packets"
			MAX-ACCESS read-only
			STATUS current
			DESCRIPTION
				" "
			::= { etherExStatsEntry 5 }
		
		-- 1.3.6.1.4.1.2011.2.25.3.35.10.20.1.6
		etherStatsTranPkts128to255Octets OBJECT-TYPE
			SYNTAX Counter64
			UNITS "Packets"
			MAX-ACCESS read-only
			STATUS current
			DESCRIPTION
				" "
			::= { etherExStatsEntry 6 }
		
		-- 1.3.6.1.4.1.2011.2.25.3.35.10.20.1.7
		etherStatsTranPkts256to511Octets OBJECT-TYPE
			SYNTAX Counter64
			UNITS "Packets"
			MAX-ACCESS read-only
			STATUS current
			DESCRIPTION
				" "
			::= { etherExStatsEntry 7 }
		
		-- 1.3.6.1.4.1.2011.2.25.3.35.10.20.1.8
		etherStatsTranPkts512to1023Octets OBJECT-TYPE
			SYNTAX Counter64
			UNITS "Packets"
			MAX-ACCESS read-only
			STATUS current
			DESCRIPTION
				" "
			::= { etherExStatsEntry 8 }
		
		-- 1.3.6.1.4.1.2011.2.25.3.35.10.20.1.9
		etherStatsTranPkts1024to1518Octets OBJECT-TYPE
			SYNTAX Counter64
			UNITS "Packets"
			MAX-ACCESS read-only
			STATUS current
			DESCRIPTION
				" "
			::= { etherExStatsEntry 9 }
		
		-- 1.3.6.1.4.1.2011.2.25.3.35.10.20.1.10
		etherStatsTranPkts1519toMTUOctets OBJECT-TYPE
			SYNTAX Counter64
			UNITS "Packets"
			MAX-ACCESS read-only
			STATUS current
			DESCRIPTION
				" "
			::= { etherExStatsEntry 10 }
		
		-- 1.3.6.1.4.1.2011.2.25.3.35.10.20.1.11
		etherStatsRxTxPkts64Octets OBJECT-TYPE
			SYNTAX Counter64
			UNITS "Packets"
			MAX-ACCESS read-only
			STATUS current
			DESCRIPTION
				" "
			::= { etherExStatsEntry 11 }
		
		-- 1.3.6.1.4.1.2011.2.25.3.35.10.20.1.12
		etherStatsRxTxPkts65to127Octets OBJECT-TYPE
			SYNTAX Counter64
			UNITS "Packets"
			MAX-ACCESS read-only
			STATUS current
			DESCRIPTION
				" "
			::= { etherExStatsEntry 12 }
		
		-- 1.3.6.1.4.1.2011.2.25.3.35.10.20.1.13
		etherStatsRxTxPkts128to255Octets OBJECT-TYPE
			SYNTAX Counter64
			UNITS "Packets"
			MAX-ACCESS read-only
			STATUS current
			DESCRIPTION
				" "
			::= { etherExStatsEntry 13 }
		
		-- 1.3.6.1.4.1.2011.2.25.3.35.10.20.1.14
		etherStatsRxTxPkts256to511Octets OBJECT-TYPE
			SYNTAX Counter64
			UNITS "Packets"
			MAX-ACCESS read-only
			STATUS current
			DESCRIPTION
				" "
			::= { etherExStatsEntry 14 }
		
		-- 1.3.6.1.4.1.2011.2.25.3.35.10.20.1.15
		etherStatsRxTxPkts512to1023Octets OBJECT-TYPE
			SYNTAX Counter64
			UNITS "Packets"
			MAX-ACCESS read-only
			STATUS current
			DESCRIPTION
				" "
			::= { etherExStatsEntry 15 }
		
		-- 1.3.6.1.4.1.2011.2.25.3.35.10.20.1.16
		etherStatsRxTxPkts1024to1518Octets OBJECT-TYPE
			SYNTAX Counter64
			UNITS "Packets"
			MAX-ACCESS read-only
			STATUS current
			DESCRIPTION
				" "
			::= { etherExStatsEntry 16 }
		
		-- 1.3.6.1.4.1.2011.2.25.3.35.10.20.1.17
		etherStatsRxTxPkts1519toMTUOctets OBJECT-TYPE
			SYNTAX Counter64
			UNITS "Packets"
			MAX-ACCESS read-only
			STATUS current
			DESCRIPTION
				" "
			::= { etherExStatsEntry 17 }
		
		-- 1.3.6.1.4.1.2011.2.25.3.35.10.20.1.18
		etherStatsInUcastPkts OBJECT-TYPE
			SYNTAX Counter64
			UNITS "Packets"
			MAX-ACCESS read-only
			STATUS current
			DESCRIPTION
				" "
			::= { etherExStatsEntry 18 }
		
		-- 1.3.6.1.4.1.2011.2.25.3.35.10.20.1.19
		etherStatsOutUcastPkts OBJECT-TYPE
			SYNTAX Counter64
			UNITS "Packets"
			MAX-ACCESS read-only
			STATUS current
			DESCRIPTION
				" "
			::= { etherExStatsEntry 19 }
		
		-- 1.3.6.1.4.1.2011.2.25.3.35.10.20.1.20
		etherStatsInPauseFrames OBJECT-TYPE
			SYNTAX Counter64
			MAX-ACCESS read-only
			STATUS current
			DESCRIPTION
				" "
			::= { etherExStatsEntry 20 }
		
		-- 1.3.6.1.4.1.2011.2.25.3.35.10.20.1.21
		etherStatsOutPauseFrames OBJECT-TYPE
			SYNTAX Counter64
			MAX-ACCESS read-only
			STATUS current
			DESCRIPTION
				" "
			::= { etherExStatsEntry 21 }
		
		-- 1.3.6.1.4.1.2011.2.25.3.35.10.20.1.22
		etherStatsOutMulticastPkts OBJECT-TYPE
			SYNTAX Counter64
			UNITS "Packets"
			MAX-ACCESS read-only
			STATUS current
			DESCRIPTION
				" "
			::= { etherExStatsEntry 22 }
		
		-- 1.3.6.1.4.1.2011.2.25.3.35.10.20.1.23
		etherStatsOutBroadcastPkts OBJECT-TYPE
			SYNTAX Counter64
			UNITS "Packets"
			MAX-ACCESS read-only
			STATUS current
			DESCRIPTION
				" "
			::= { etherExStatsEntry 23 }
		
		-- 1.3.6.1.4.1.2011.2.25.3.35.10.20.1.24
		etherStatsInGoodOctets OBJECT-TYPE
			SYNTAX Counter64
			MAX-ACCESS read-only
			STATUS current
			DESCRIPTION
				" "
			::= { etherExStatsEntry 24 }
		
		-- 1.3.6.1.4.1.2011.2.25.3.35.10.20.1.25
		etherStatsOutGoodOctets OBJECT-TYPE
			SYNTAX Counter64
			MAX-ACCESS read-only
			STATUS current
			DESCRIPTION
				" "
			::= { etherExStatsEntry 25 }
		
		-- 1.3.6.1.4.1.2011.2.25.3.35.10.20.1.26
		etherStatsInBadOctets OBJECT-TYPE
			SYNTAX Counter64
			MAX-ACCESS read-only
			STATUS current
			DESCRIPTION
				" "
			::= { etherExStatsEntry 26 }
		
--  
		-- 1.3.6.1.4.1.2011.2.25.3.35.10.20.1.27
		etherStatsOutBadOctets OBJECT-TYPE
			SYNTAX Counter64
			MAX-ACCESS read-only
			STATUS current
			DESCRIPTION
				" "
			::= { etherExStatsEntry 27 }
		
		-- 1.3.6.1.4.1.2011.2.25.3.35.10.20.1.28
		etherStatsAlignmentErrors OBJECT-TYPE
			SYNTAX Counter64
			MAX-ACCESS read-only
			STATUS current
			DESCRIPTION
				" "
			::= { etherExStatsEntry 28 }
		
		-- 1.3.6.1.4.1.2011.2.25.3.35.10.20.1.29
		etherStatsFCSErrors OBJECT-TYPE
			SYNTAX Counter64
			MAX-ACCESS read-only
			STATUS current
			DESCRIPTION
				" "
			::= { etherExStatsEntry 29 }
		
		-- 1.3.6.1.4.1.2011.2.25.3.35.10.20.1.30
		etherStatsSingleCollisionFrames OBJECT-TYPE
			SYNTAX Counter64
			MAX-ACCESS read-only
			STATUS current
			DESCRIPTION
				" "
			::= { etherExStatsEntry 30 }
		
		-- 1.3.6.1.4.1.2011.2.25.3.35.10.20.1.31
		etherStatsMultipleCollisionFrames OBJECT-TYPE
			SYNTAX Counter64
			MAX-ACCESS read-only
			STATUS current
			DESCRIPTION
				" "
			::= { etherExStatsEntry 31 }
		
--  
		-- 1.3.6.1.4.1.2011.2.25.3.35.10.20.1.32
		etherStatsLateCollisions OBJECT-TYPE
			SYNTAX Counter64
			MAX-ACCESS read-only
			STATUS current
			DESCRIPTION
				" "
			::= { etherExStatsEntry 32 }
		
		-- 1.3.6.1.4.1.2011.2.25.3.35.10.20.1.33
		etherStatsExcessiveCollisions OBJECT-TYPE
			SYNTAX Counter64
			MAX-ACCESS read-only
			STATUS current
			DESCRIPTION
				" "
			::= { etherExStatsEntry 33 }
		
		-- 1.3.6.1.4.1.2011.2.25.3.35.10.20.1.34
		etherStatsDeferredTransmissions OBJECT-TYPE
			SYNTAX Counter64
			MAX-ACCESS read-only
			STATUS current
			DESCRIPTION
				" "
			::= { etherExStatsEntry 34 }
		
		-- 1.3.6.1.4.1.2011.2.25.3.35.10.20.1.35
		etherStatsCarrierSenseErrors OBJECT-TYPE
			SYNTAX Counter64
			MAX-ACCESS read-only
			STATUS current
			DESCRIPTION
				" "
			::= { etherExStatsEntry 35 }
		
		-- 1.3.6.1.4.1.2011.2.25.3.35.10.20.1.36
		etherStatsInControlFrames OBJECT-TYPE
			SYNTAX Counter64
			MAX-ACCESS read-only
			STATUS current
			DESCRIPTION
				" "
			::= { etherExStatsEntry 36 }
		
		-- 1.3.6.1.4.1.2011.2.25.3.35.10.20.1.37
		etherStatsOutControlFrames OBJECT-TYPE
			SYNTAX Counter64
			MAX-ACCESS read-only
			STATUS current
			DESCRIPTION
				" "
			::= { etherExStatsEntry 37 }
		
		-- 1.3.6.1.4.1.2011.2.25.3.35.10.20.1.38
		etherStatsOutDropEvents OBJECT-TYPE
			SYNTAX Counter64
			MAX-ACCESS read-only
			STATUS current
			DESCRIPTION
				" "
			::= { etherExStatsEntry 38 }
		
		-- 1.3.6.1.4.1.2011.2.25.3.35.10.20.1.39
		etherStatsOutOversizePkts OBJECT-TYPE
			SYNTAX Counter64
			MAX-ACCESS read-only
			STATUS current
			DESCRIPTION
				" "
			::= { etherExStatsEntry 39 }
		
		-- 1.3.6.1.4.1.2011.2.25.3.35.10.20.1.40
		etherStatsOutPkts OBJECT-TYPE
			SYNTAX Counter64
			MAX-ACCESS read-only
			STATUS current
			DESCRIPTION
				" "
			::= { etherExStatsEntry 40 }
		
		-- 1.3.6.1.4.1.2011.2.25.3.35.10.20.1.41
		etherStatsOutOctets OBJECT-TYPE
			SYNTAX Counter64
			MAX-ACCESS read-only
			STATUS current
			DESCRIPTION
				" "
			::= { etherExStatsEntry 41 }
		
		-- 1.3.6.1.4.1.2011.2.25.3.35.20
		history OBJECT IDENTIFIER ::= { optixRmonMib 20 }
		
-- ***************************************************************************************
--  The History Control Group
-- ***************************************************************************************
--  Implementation of the History Control group is optional.
--  Consult the MODULE-COMPLIANCE macro for the authoritative
--  conformance information for this MIB.
-- 
--  The history control group controls the periodic statistical
--  sampling of data from various types of networks.  The
--  historyControlTable stores configuration entries that each
--  define an interface, polling period, and other parameters.
--  Once samples are taken, their data is stored in an entry
--  in a media-specific table.  Each such entry defines one
--  sample, and is associated with the historyControlEntry that
--  caused the sample to be taken.  Each counter in the
--  etherHistoryEntry counts the same event as its similarly-named
--  counterpart in the etherStatsEntry, except that each value here
--  is a cumulative sum during a sampling period.
-- 
--  If the probe keeps track of the time of day, it should start
--  the first sample of the history at a time such that
--  when the next hour of the day begins, a sample is
--  started at that instant.  This tends to make more
--  user-friendly reports, and enables comparison of reports
--  from different probes that have relatively accurate time
--  of day.
-- 
--  The probe is encouraged to add two history control entries
--  per monitored interface upon initialization that describe a short
--  term and a long term polling period.  Suggested parameters are 30
--  seconds for the short term polling period and 30 minutes for
--  the long term period.
		-- 1.3.6.1.4.1.2011.2.25.3.35.20.1
		historyControlTable OBJECT-TYPE
			SYNTAX SEQUENCE OF HistoryControlEntry
			MAX-ACCESS not-accessible
			STATUS current
			DESCRIPTION
				"A list of history control entries."
			::= { history 1 }
		
		-- 1.3.6.1.4.1.2011.2.25.3.35.20.1.1
		historyControlEntry OBJECT-TYPE
			SYNTAX HistoryControlEntry
			MAX-ACCESS not-accessible
			STATUS current
			DESCRIPTION
				"A list of parameters that set up a periodic sampling of
				statistics.  As an example, an instance of the
				historyControlInterval object might be named
				historyControlInterval.2"
			INDEX { historyControlIndex }
			::= { historyControlTable 1 }
		
		HistoryControlEntry ::=
			SEQUENCE { 
				historyControlIndex
					Unsigned32,
				historyControlBucketsRequested
					Unsigned32,
				historyControlInterval
					Unsigned32,
				historyControlStatus
					INTEGER
			 }

		-- 1.3.6.1.4.1.2011.2.25.3.35.20.1.1.1
		historyControlIndex OBJECT-TYPE
			SYNTAX Unsigned32
			MAX-ACCESS read-only
			STATUS current
			DESCRIPTION
				"An index that uniquely identifies an entry in the
				historyControl table.  Each such entry defines a
				set of samples at a particular interval for an
				interface on the device. 
				
				historyControlIndex of huawei optix devices can be described as following, 
				historyControlIndex consists of SLOT_ID,PORT_ID,SUB_PORT_ID and PERIOD_TYPE.
				historyControlIndex = SUB_PORT_ID<<31 + SLOT_ID<<24 + PERIOD_TYPE<<16 + PORT_ID;
				1) 31bit(1bit) SUB_PORT_ID 1bit: 
				   0 - SUB_PORT_1(east),  1 - SUB_PORT_2(west)   
				   for sonet,this para is 0 ,no other means;
				2) 24bit~30bit(7bits) SLOT_ID:   slot id;     
				3) 16bit~23(8bits) PERIOD_TYPE:  period type;
				     0x1 - 30s(30 seconds)
				     0x2 - 30m(30 minutes)
				     0x3 - prdvar(var period)
				4) 0bit~15bit(16bits) PORT_ID:    mac port id;
				
				For example:
				1: historyControlIndex.83951617 (gauge) 83951617
				   83951617 = 0x05010001 can be translated as Slot-5,PrdType-30s,Port-1;                
				2: historyControlIndex.84017153 (gauge) 84017153
				   84017153 = 0x05020001 can be translated as Slot-5,PrdType-30m,Port-1;              
				3: historyControlIndex.84082696 (gauge) 84082696       
				   84082696 = 0x05030008 can be translated as Slot-5,PrdType-prdvar,Port-8; 
				"
			::= { historyControlEntry 1 }
		
		-- 1.3.6.1.4.1.2011.2.25.3.35.20.1.1.3
		historyControlBucketsRequested OBJECT-TYPE
			SYNTAX Unsigned32
			MAX-ACCESS read-create
			STATUS current
			DESCRIPTION
				"The requested number of discrete time intervals
				over which data is to be saved in the part of the
				media-specific table associated with this
				historyControlEntry.
				
				When this object is created or modified, the probe
				should set historyControlBucketsGranted as closely to
				this object as is possible for the particular probe
				implementation and available resources."
			DEFVAL { 50 }
			::= { historyControlEntry 3 }
		
		-- 1.3.6.1.4.1.2011.2.25.3.35.20.1.1.5
		historyControlInterval OBJECT-TYPE
			SYNTAX Unsigned32
			UNITS "Seconds"
			MAX-ACCESS read-create
			STATUS current
			DESCRIPTION
				"The interval in seconds over which the data is
				sampled for each bucket in the part of the
				media-specific table associated with this
				historyControlEntry.
				
				Because the counters in a bucket may overflow at their
				maximum value with no indication, a prudent manager will
				take into account the possibility of overflow in any of
				the associated counters.  It is important to consider the
				minimum time in which any counter could overflow on a
				particular media type and set the historyControlInterval
				object to a value less than this interval.  This is
				typically most important for the 'octets' counter in any
				media-specific table.  For example, on an Ethernet
				network, the etherHistoryOctets counter could overflow
				in about one hour at the Ethernet's maximum
				utilization.
				
				This object may not be modified if the associated
				historyControlStatus object is equal to valid(1)."
			DEFVAL { 1800 }
			::= { historyControlEntry 5 }
		
-- 
-- 
		-- 1.3.6.1.4.1.2011.2.25.3.35.20.1.1.7
		historyControlStatus OBJECT-TYPE
			SYNTAX INTEGER
				{
				valid(1),
				invalid(4)
				}
			MAX-ACCESS read-create
			STATUS current
			DESCRIPTION
				"The status of this historyControl ."
			::= { historyControlEntry 7 }
		
-- ***************************************************************************************    
--  The Ethernet History Group
-- ****************************************************************************************
--  Implementation of the Ethernet History group is optional.
--  Consult the MODULE-COMPLIANCE macro for the authoritative
--  conformance information for this MIB.
-- 
--  The Ethernet History group records periodic statistical samples
--  from a network and stores them for later retrieval.
--  Once samples are taken, their data is stored in an entry
--  in a media-specific table.  Each such entry defines one
--  sample, and is associated with the historyControlEntry that
--  caused the sample to be taken.  This group defines the
--  etherHistoryTable, for Ethernet networks.
-- 
		-- 1.3.6.1.4.1.2011.2.25.3.35.20.2
		etherHistoryTable OBJECT-TYPE
			SYNTAX SEQUENCE OF EtherHistoryEntry
			MAX-ACCESS not-accessible
			STATUS current
			DESCRIPTION
				"A list of Ethernet history entries."
			::= { history 2 }
		
		-- 1.3.6.1.4.1.2011.2.25.3.35.20.2.1
		etherHistoryEntry OBJECT-TYPE
			SYNTAX EtherHistoryEntry
			MAX-ACCESS not-accessible
			STATUS current
			DESCRIPTION
				"An historical sample of Ethernet statistics on a particular
				Ethernet interface.  This sample is associated with the
				historyControlEntry which set up the parameters for
				a regular collection of these samples.  As an example, an
				instance of the etherHistoryPkts object might be named
				etherHistoryPkts.2.89"
			INDEX { etherHistoryIndex, etherHistorySampleIndex }
			::= { etherHistoryTable 1 }
		
		EtherHistoryEntry ::=
			SEQUENCE { 
				etherHistoryIndex
					Unsigned32,
				etherHistorySampleIndex
					Unsigned32,
				etherHistoryIntervalStart
					DateAndTime,
				etherHistoryDropEvents
					Counter64,
				etherHistoryOctets
					Counter64,
				etherHistoryPkts
					Counter64,
				etherHistoryBroadcastPkts
					Counter64,
				etherHistoryMulticastPkts
					Counter64,
				etherHistoryCRCAlignErrors
					Counter64,
				etherHistoryUndersizePkts
					Counter64,
				etherHistoryOversizePkts
					Counter64,
				etherHistoryFragments
					Counter64,
				etherHistoryJabbers
					Counter64,
				etherHistoryCollisions
					Counter64,
				etherHistoryUtilization
					Counter64
			 }

		-- 1.3.6.1.4.1.2011.2.25.3.35.20.2.1.1
		etherHistoryIndex OBJECT-TYPE
			SYNTAX Unsigned32
			MAX-ACCESS read-only
			STATUS current
			DESCRIPTION
				"The history of which this entry is a part.  The
				history identified by a particular value of this
				index is the same history as identified
				by the same value of historyControlIndex.   
				 
				etherHistoryIndex of huawei optix devices can be described as following, 
				etherHistoryIndex consists of SLOT_ID,PORT_ID,SUB_PORT_ID and PERIOD_TYPE.
				etherHistoryIndex = SUB_PORT_ID<<31 + SLOT_ID<<24 + PERIOD_TYPE<<16 + PORT_ID;
				1) 31bit(1bit) SUB_PORT_ID 1bit: 
				   0 - SUB_PORT_1(east),  1 - SUB_PORT_2(west)   
				   for sonet,this para is 0 ,no other means;
				2) 24bit~30bit(7bits) SLOT_ID:    slot id;     
				3) 16bit~23(8bits) PERIOD_TYPE:   period type;
				     0x1 - 30s(30 seconds)
				     0x2 - 30m(30 minutes)
				     0x3 - prdvar(var period)
				4) 0bit~15bit(16bits) PORT_ID:     mac port id;
				
				For example:
				1: etherHistoryIndex.83951617 (gauge) 83951617
				   83951617 = 0x05010001 can be translated as Slot-5,PrdType-30s,Port-1;               
				2: etherHistoryIndex.84017153 (gauge) 84017153
				   84017153 = 0x05020001 can be translated as Slot-5,PrdType-30m,Port-1;               
				3: etherHistoryIndex.84082696 (gauge) 84082696       
				   84082696 = 0x05030008 can be translated as Slot-5,PrdType-prdvar,Port-8;                 
				"
			::= { etherHistoryEntry 1 }
		
		-- 1.3.6.1.4.1.2011.2.25.3.35.20.2.1.2
		etherHistorySampleIndex OBJECT-TYPE
			SYNTAX Unsigned32
			MAX-ACCESS read-only
			STATUS current
			DESCRIPTION
				"An index that uniquely identifies the particular
				sample this entry represents among all samples
				associated with the same historyControlEntry.
				This index starts at 1 and increases by one
				as each new sample is taken."
			::= { etherHistoryEntry 2 }
		
		-- 1.3.6.1.4.1.2011.2.25.3.35.20.2.1.3
		etherHistoryIntervalStart OBJECT-TYPE
			SYNTAX DateAndTime
			MAX-ACCESS read-only
			STATUS current
			DESCRIPTION
				" "
			::= { etherHistoryEntry 3 }
		
		-- 1.3.6.1.4.1.2011.2.25.3.35.20.2.1.4
		etherHistoryDropEvents OBJECT-TYPE
			SYNTAX Counter64
			MAX-ACCESS read-only
			STATUS current
			DESCRIPTION
				"The total number of events in which packets
				were dropped by the probe due to lack of resources
				during this sampling interval.  Note that this number
				is not necessarily the number of packets dropped, it
				is just the number of times this condition has been
				detected."
			::= { etherHistoryEntry 4 }
		
		-- 1.3.6.1.4.1.2011.2.25.3.35.20.2.1.5
		etherHistoryOctets OBJECT-TYPE
			SYNTAX Counter64
			UNITS "Octets"
			MAX-ACCESS read-only
			STATUS current
			DESCRIPTION
				"The total number of octets of data (including
				those in bad packets) received on the
				network (excluding framing bits but including
				FCS octets)."
			::= { etherHistoryEntry 5 }
		
		-- 1.3.6.1.4.1.2011.2.25.3.35.20.2.1.6
		etherHistoryPkts OBJECT-TYPE
			SYNTAX Counter64
			UNITS "Packets"
			MAX-ACCESS read-only
			STATUS current
			DESCRIPTION
				"The number of packets (including bad packets)
				received during this sampling interval."
			::= { etherHistoryEntry 6 }
		
		-- 1.3.6.1.4.1.2011.2.25.3.35.20.2.1.7
		etherHistoryBroadcastPkts OBJECT-TYPE
			SYNTAX Counter64
			UNITS "Packets"
			MAX-ACCESS read-only
			STATUS current
			DESCRIPTION
				"The number of good packets received during this
				sampling interval that were directed to the
				broadcast address."
			::= { etherHistoryEntry 7 }
		
		-- 1.3.6.1.4.1.2011.2.25.3.35.20.2.1.8
		etherHistoryMulticastPkts OBJECT-TYPE
			SYNTAX Counter64
			UNITS "Packets"
			MAX-ACCESS read-only
			STATUS current
			DESCRIPTION
				"The number of good packets received during this
				sampling interval that were directed to a
				multicast address.  Note that this number does not
				include packets addressed to the broadcast address."
			::= { etherHistoryEntry 8 }
		
		-- 1.3.6.1.4.1.2011.2.25.3.35.20.2.1.9
		etherHistoryCRCAlignErrors OBJECT-TYPE
			SYNTAX Counter64
			UNITS "Packets"
			MAX-ACCESS read-only
			STATUS current
			DESCRIPTION
				"The number of packets received during this
				sampling interval that had a length (excluding
				framing bits but including FCS octets) between
				64 and 1518 octets, inclusive, but had either a bad Frame
				Check Sequence (FCS) with an integral number of octets
				(FCS Error) or a bad FCS with a non-integral number
				of octets (Alignment Error)."
			::= { etherHistoryEntry 9 }
		
		-- 1.3.6.1.4.1.2011.2.25.3.35.20.2.1.10
		etherHistoryUndersizePkts OBJECT-TYPE
			SYNTAX Counter64
			UNITS "Packets"
			MAX-ACCESS read-only
			STATUS current
			DESCRIPTION
				"The number of packets received during this
				sampling interval that were less than 64 octets
				long (excluding framing bits but including FCS
				octets) and were otherwise well formed."
			::= { etherHistoryEntry 10 }
		
		-- 1.3.6.1.4.1.2011.2.25.3.35.20.2.1.11
		etherHistoryOversizePkts OBJECT-TYPE
			SYNTAX Counter64
			UNITS "Packets"
			MAX-ACCESS read-only
			STATUS current
			DESCRIPTION
				"The number of packets received during this
				sampling interval that were longer than 1518
				octets (excluding framing bits but including
				FCS octets) but were otherwise well formed."
			::= { etherHistoryEntry 11 }
		
		-- 1.3.6.1.4.1.2011.2.25.3.35.20.2.1.12
		etherHistoryFragments OBJECT-TYPE
			SYNTAX Counter64
			UNITS "Packets"
			MAX-ACCESS read-only
			STATUS current
			DESCRIPTION
				"The total number of packets received during this
				sampling interval that were less than 64 octets in
				length (excluding framing bits but including FCS
				octets) had either a bad Frame Check Sequence (FCS)
				with an integral number of octets (FCS Error) or a bad
				FCS with a non-integral number of octets (Alignment
				Error).
				
				Note that it is entirely normal for etherHistoryFragments to
				increment.  This is because it counts both runts (which are
				normal occurrences due to collisions) and noise hits."
			::= { etherHistoryEntry 12 }
		
		-- 1.3.6.1.4.1.2011.2.25.3.35.20.2.1.13
		etherHistoryJabbers OBJECT-TYPE
			SYNTAX Counter64
			UNITS "Packets"
			MAX-ACCESS read-only
			STATUS current
			DESCRIPTION
				"The number of packets received during this
				sampling interval that were longer than 1518 octets
				(excluding framing bits but including FCS octets),
				and  had either a bad Frame Check Sequence (FCS)
				with an integral number of octets (FCS Error) or
				a bad FCS with a non-integral number of octets
				(Alignment Error).
				
				Note that this definition of jabber is different
				than the definition in IEEE-802.3 section 8.2.1.5
				(10BASE5) and section 10.3.1.4 (10BASE2).  These
				documents define jabber as the condition where any
				packet exceeds 20 ms.  The allowed range to detect
				jabber is between 20 ms and 150 ms."
			::= { etherHistoryEntry 13 }
		
		-- 1.3.6.1.4.1.2011.2.25.3.35.20.2.1.14
		etherHistoryCollisions OBJECT-TYPE
			SYNTAX Counter64
			UNITS "Collisions"
			MAX-ACCESS read-only
			STATUS current
			DESCRIPTION
				"The best estimate of the total number of collisions
				on this Ethernet segment during this sampling
				interval.
				
				The value returned will depend on the location of the
				RMON probe. Section 8.2.1.3 (10BASE-5) and section
				10.3.1.3 (10BASE-2) of IEEE standard 802.3 states that a
				station must detect a collision, in the receive mode, if
				three or more stations are transmitting simultaneously.  A
				repeater port must detect a collision when two or more
				stations are transmitting simultaneously.  Thus a probe
				placed on a repeater port could record more collisions
				than a probe connected to a station on the same segment
				would.
				
				Probe location plays a much smaller role when considering
				10BASE-T.  14.2.1.4 (10BASE-T) of IEEE standard 802.3
				defines a collision as the simultaneous presence of signals
				on the DO and RD circuits (transmitting and receiving
				at the same time).  A 10BASE-T station can only detect
				collisions when it is transmitting.  Thus probes placed on
				a station and a repeater, should report the same number of
				collisions.
				
				Note also that an RMON probe inside a repeater should
				ideally report collisions between the repeater and one or
				more other hosts (transmit collisions as defined by IEEE
				802.3k) plus receiver collisions observed on any coax
				segments to which the repeater is connected."
			::= { etherHistoryEntry 14 }
		
		-- 1.3.6.1.4.1.2011.2.25.3.35.20.2.1.15
		etherHistoryUtilization OBJECT-TYPE
			SYNTAX Counter64
			MAX-ACCESS read-only
			STATUS current
			DESCRIPTION
				"The best estimate of the mean physical layer
				network utilization on this interface during this
				sampling interval, in hundredths of a percent."
			::= { etherHistoryEntry 15 }
		
-- *************************************************************************************** 
--  The Ethernet Private Extend History Group
-- ***************************************************************************************
--  Implementation of the Ethernet History group is optional.
--  Consult the MODULE-COMPLIANCE macro for the authoritative
--  conformance information for this MIB.
-- 
--  The Ethernet History group records periodic statistical samples
--  from a network and stores them for later retrieval.
--  Once samples are taken, their data is stored in an entry
--  in a media-specific table.  Each such entry defines one
--  sample, and is associated with the historyControlEntry that
--  caused the sample to be taken.  This group defines the
--  etherHistoryTable, for Ethernet networks.
--         
		-- 1.3.6.1.4.1.2011.2.25.3.35.20.3
		etherExHistoryTable OBJECT-TYPE
			SYNTAX SEQUENCE OF EtherExHistoryEntry
			MAX-ACCESS not-accessible
			STATUS current
			DESCRIPTION
				"A list of Exetend Ethernet  history entries."
			::= { history 3 }
		
		-- 1.3.6.1.4.1.2011.2.25.3.35.20.3.1
		etherExHistoryEntry OBJECT-TYPE
			SYNTAX EtherExHistoryEntry
			MAX-ACCESS not-accessible
			STATUS current
			DESCRIPTION
				"A collection of statistics kept for a particular
				Ethernet interface.  As an example, an instance of the
				etherStatsPkts object might be named etherStatsPkts.1"
			INDEX { etherExHistoryIndex, etherExHistorySampleIndex }
			::= { etherExHistoryTable 1 }
		
		EtherExHistoryEntry ::=
			SEQUENCE { 
				etherExHistoryIndex
					Unsigned32,
				etherExHistorySampleIndex
					Unsigned32,
				etherExHistoryIntervalStart
					DateAndTime,
				etherExHistoryInUcastPkts
					Counter64,
				etherExHistoryOutUcastPkts
					Counter64,
				etherExHistoryInPauseFrames
					Counter64,
				etherExHistoryOutPauseFrames
					Counter64,
				etherExHistoryOutMulticastPkts
					Counter64,
				etherExHistoryOutBroadcastPkts
					Counter64,
				etherExHistoryInGoodOctets
					Counter64,
				etherExHistoryOutGoodOctets
					Counter64,
				etherExHistoryInBadOctets
					Counter64,
				etherExHistoryOutBadOctets
					Counter64,
				etherExHistoryAlignmentErrors
					Counter64,
				etherExHistoryFCSErrors
					Counter64,
				etherExHistorySingleCollisionFrames
					Counter64,
				etherExHistoryMultipleCollisionFrames
					Counter64,
				etherExHistoryLateCollisions
					Counter64,
				etherExHistoryExcessiveCollisions
					Counter64,
				etherExHistoryDeferredTransmissions
					Counter64,
				etherExHistoryCarrierSenseErrors
					Counter64,
				etherExHistoryInControlFrames
					Counter64,
				etherExHistoryOutControlFrames
					Counter64,
				etherExHistorysOutDropEvents
					Counter64,
				etherExHistorysOutOversizePkts
					Counter64,
				etherExHistoryOutPkts
					Counter64,
				etherExHistoryOutOctets
					Counter64
			 }

		-- 1.3.6.1.4.1.2011.2.25.3.35.20.3.1.1
		etherExHistoryIndex OBJECT-TYPE
			SYNTAX Unsigned32
			MAX-ACCESS read-only
			STATUS current
			DESCRIPTION
				"The history of which this entry is a part.  The
				history identified by a particular value of this
				index is the same history as identified
				by the same value of historyControlIndex.   
				
				etherExHistoryIndex of huawei optix devices can be described as following, 
				etherExHistoryIndex consists of SLOT_ID,PORT_ID,SUB_PORT_ID and PERIOD_TYPE.
				etherExHistoryIndex = SUB_PORT_ID<<31 + SLOT_ID<<24 + PERIOD_TYPE<<16 + PORT_ID;
				1) 31bit(1bit) SUB_PORT_ID 1bit: 
				   0 - SUB_PORT_1(east),  1 - SUB_PORT_2(west)   
				   for sonet,this para is 0 ,no other means;
				2) 24bit~30bit(7bits) SLOT_ID:   slot id;     
				3) 16bit~23(8bits) PERIOD_TYPE:  period type;
				     0x1 - 30s(30 seconds)
				     0x2 - 30m(30 minutes)
				     0x3 - prdvar(var period)
				4) 0bit~15bit(16bits) PORT_ID:    mac port id;
				
				For example:
				1: etherExHistoryIndex.83951617 (gauge) 83951617
				   83951617 = 0x05010001 can be translated as Slot-5,PrdType-30s,Port-1;                
				2: etherExHistoryIndex.84017153 (gauge) 84017153
				   84017153 = 0x05020001 can be translated as Slot-5,PrdType-30m,Port-1;
				3: etherExHistoryIndex.84082696 (gauge) 84082696       
				   84082696 = 0x05030008 can be translated as Slot-5,PrdType-prdvar,Port-8;                      
				"
			::= { etherExHistoryEntry 1 }
		
		-- 1.3.6.1.4.1.2011.2.25.3.35.20.3.1.2
		etherExHistorySampleIndex OBJECT-TYPE
			SYNTAX Unsigned32
			MAX-ACCESS read-only
			STATUS current
			DESCRIPTION
				"An index that uniquely identifies the particular
				sample this entry represents among all samples
				associated with the same historyControlEntry.
				This index starts at 1 and increases by one
				as each new sample is taken."
			::= { etherExHistoryEntry 2 }
		
		-- 1.3.6.1.4.1.2011.2.25.3.35.20.3.1.3
		etherExHistoryIntervalStart OBJECT-TYPE
			SYNTAX DateAndTime
			MAX-ACCESS read-only
			STATUS current
			DESCRIPTION
				" "
			::= { etherExHistoryEntry 3 }
		
		-- 1.3.6.1.4.1.2011.2.25.3.35.20.3.1.4
		etherExHistoryInUcastPkts OBJECT-TYPE
			SYNTAX Counter64
			MAX-ACCESS read-only
			STATUS current
			DESCRIPTION
				" "
			::= { etherExHistoryEntry 4 }
		
		-- 1.3.6.1.4.1.2011.2.25.3.35.20.3.1.5
		etherExHistoryOutUcastPkts OBJECT-TYPE
			SYNTAX Counter64
			UNITS "Packets"
			MAX-ACCESS read-only
			STATUS current
			DESCRIPTION
				" "
			::= { etherExHistoryEntry 5 }
		
		-- 1.3.6.1.4.1.2011.2.25.3.35.20.3.1.6
		etherExHistoryInPauseFrames OBJECT-TYPE
			SYNTAX Counter64
			MAX-ACCESS read-only
			STATUS current
			DESCRIPTION
				" "
			::= { etherExHistoryEntry 6 }
		
		-- 1.3.6.1.4.1.2011.2.25.3.35.20.3.1.7
		etherExHistoryOutPauseFrames OBJECT-TYPE
			SYNTAX Counter64
			MAX-ACCESS read-only
			STATUS current
			DESCRIPTION
				" "
			::= { etherExHistoryEntry 7 }
		
		-- 1.3.6.1.4.1.2011.2.25.3.35.20.3.1.8
		etherExHistoryOutMulticastPkts OBJECT-TYPE
			SYNTAX Counter64
			UNITS "Packets"
			MAX-ACCESS read-only
			STATUS current
			DESCRIPTION
				" "
			::= { etherExHistoryEntry 8 }
		
		-- 1.3.6.1.4.1.2011.2.25.3.35.20.3.1.9
		etherExHistoryOutBroadcastPkts OBJECT-TYPE
			SYNTAX Counter64
			UNITS "Packets"
			MAX-ACCESS read-only
			STATUS current
			DESCRIPTION
				" "
			::= { etherExHistoryEntry 9 }
		
		-- 1.3.6.1.4.1.2011.2.25.3.35.20.3.1.10
		etherExHistoryInGoodOctets OBJECT-TYPE
			SYNTAX Counter64
			MAX-ACCESS read-only
			STATUS current
			DESCRIPTION
				" "
			::= { etherExHistoryEntry 10 }
		
		-- 1.3.6.1.4.1.2011.2.25.3.35.20.3.1.11
		etherExHistoryOutGoodOctets OBJECT-TYPE
			SYNTAX Counter64
			MAX-ACCESS read-only
			STATUS current
			DESCRIPTION
				" "
			::= { etherExHistoryEntry 11 }
		
		-- 1.3.6.1.4.1.2011.2.25.3.35.20.3.1.12
		etherExHistoryInBadOctets OBJECT-TYPE
			SYNTAX Counter64
			MAX-ACCESS read-only
			STATUS current
			DESCRIPTION
				" "
			::= { etherExHistoryEntry 12 }
		
		-- 1.3.6.1.4.1.2011.2.25.3.35.20.3.1.13
		etherExHistoryOutBadOctets OBJECT-TYPE
			SYNTAX Counter64
			MAX-ACCESS read-only
			STATUS current
			DESCRIPTION
				" "
			::= { etherExHistoryEntry 13 }
		
		-- 1.3.6.1.4.1.2011.2.25.3.35.20.3.1.14
		etherExHistoryAlignmentErrors OBJECT-TYPE
			SYNTAX Counter64
			MAX-ACCESS read-only
			STATUS current
			DESCRIPTION
				" "
			::= { etherExHistoryEntry 14 }
		
		-- 1.3.6.1.4.1.2011.2.25.3.35.20.3.1.15
		etherExHistoryFCSErrors OBJECT-TYPE
			SYNTAX Counter64
			MAX-ACCESS read-only
			STATUS current
			DESCRIPTION
				" "
			::= { etherExHistoryEntry 15 }
		
		-- 1.3.6.1.4.1.2011.2.25.3.35.20.3.1.16
		etherExHistorySingleCollisionFrames OBJECT-TYPE
			SYNTAX Counter64
			MAX-ACCESS read-only
			STATUS current
			DESCRIPTION
				" "
			::= { etherExHistoryEntry 16 }
		
		-- 1.3.6.1.4.1.2011.2.25.3.35.20.3.1.17
		etherExHistoryMultipleCollisionFrames OBJECT-TYPE
			SYNTAX Counter64
			MAX-ACCESS read-only
			STATUS current
			DESCRIPTION
				" "
			::= { etherExHistoryEntry 17 }
		
		-- 1.3.6.1.4.1.2011.2.25.3.35.20.3.1.18
		etherExHistoryLateCollisions OBJECT-TYPE
			SYNTAX Counter64
			MAX-ACCESS read-only
			STATUS current
			DESCRIPTION
				" "
			::= { etherExHistoryEntry 18 }
		
		-- 1.3.6.1.4.1.2011.2.25.3.35.20.3.1.19
		etherExHistoryExcessiveCollisions OBJECT-TYPE
			SYNTAX Counter64
			MAX-ACCESS read-only
			STATUS current
			DESCRIPTION
				" "
			::= { etherExHistoryEntry 19 }
		
		-- 1.3.6.1.4.1.2011.2.25.3.35.20.3.1.20
		etherExHistoryDeferredTransmissions OBJECT-TYPE
			SYNTAX Counter64
			MAX-ACCESS read-only
			STATUS current
			DESCRIPTION
				" "
			::= { etherExHistoryEntry 20 }
		
		-- 1.3.6.1.4.1.2011.2.25.3.35.20.3.1.21
		etherExHistoryCarrierSenseErrors OBJECT-TYPE
			SYNTAX Counter64
			MAX-ACCESS read-only
			STATUS current
			DESCRIPTION
				" "
			::= { etherExHistoryEntry 21 }
		
		-- 1.3.6.1.4.1.2011.2.25.3.35.20.3.1.22
		etherExHistoryInControlFrames OBJECT-TYPE
			SYNTAX Counter64
			MAX-ACCESS read-only
			STATUS current
			DESCRIPTION
				" "
			::= { etherExHistoryEntry 22 }
		
		-- 1.3.6.1.4.1.2011.2.25.3.35.20.3.1.23
		etherExHistoryOutControlFrames OBJECT-TYPE
			SYNTAX Counter64
			MAX-ACCESS read-only
			STATUS current
			DESCRIPTION
				" "
			::= { etherExHistoryEntry 23 }
		
		-- 1.3.6.1.4.1.2011.2.25.3.35.20.3.1.24
		etherExHistorysOutDropEvents OBJECT-TYPE
			SYNTAX Counter64
			MAX-ACCESS read-only
			STATUS current
			DESCRIPTION
				" "
			::= { etherExHistoryEntry 24 }
		
		-- 1.3.6.1.4.1.2011.2.25.3.35.20.3.1.25
		etherExHistorysOutOversizePkts OBJECT-TYPE
			SYNTAX Counter64
			MAX-ACCESS read-only
			STATUS current
			DESCRIPTION
				" "
			::= { etherExHistoryEntry 25 }
		
		-- 1.3.6.1.4.1.2011.2.25.3.35.20.3.1.26
		etherExHistoryOutPkts OBJECT-TYPE
			SYNTAX Counter64
			MAX-ACCESS read-only
			STATUS current
			DESCRIPTION
				" "
			::= { etherExHistoryEntry 26 }
		
		-- 1.3.6.1.4.1.2011.2.25.3.35.20.3.1.27
		etherExHistoryOutOctets OBJECT-TYPE
			SYNTAX Counter64
			MAX-ACCESS read-only
			STATUS current
			DESCRIPTION
				" "
			::= { etherExHistoryEntry 27 }
		
		-- 1.3.6.1.4.1.2011.2.25.3.35.30
		alarm OBJECT IDENTIFIER ::= { optixRmonMib 30 }
		
-- ********************************************************************************    
-- The Alarm Group        
-- *********************************************************************************
-- Implementation of the Alarm group is optional. The Alarm Group
-- requires the implementation of the Event group.
-- Consult the MODULE-COMPLIANCE macro for the authoritative
-- conformance information for this MIB.
-- 
-- The Alarm group periodically takes statistical samples from
-- variables in the probe and compares them to thresholds that have
-- been configured.  The alarm table stores configuration
-- entries that each define a variable, polling period, and
-- threshold parameters.  If a sample is found to cross the
-- threshold values, an event is generated.  Only variables that
-- resolve to an ASN.1 primitive type of INTEGER (INTEGER, Integer32,
-- Counter32, Counter64, Gauge32, or TimeTicks) may be monitored in
-- this way.
-- 
-- This function has a hysteresis mechanism to limit the generation
-- of events.  This mechanism generates one event as a threshold
-- is crossed in the appropriate direction.  No more events are
-- generated for that threshold until the opposite threshold is
-- crossed.
-- 
-- In the case of a sampling a deltaValue, a probe may implement
-- this mechanism with more precision if it takes a delta sample
-- twice per period, each time comparing the sum of the latest two
-- samples to the threshold.  This allows the detection of threshold
-- crossings that span the sampling boundary.  Note that this does
-- not require any special configuration of the threshold value.
-- It is suggested that probes implement this more precise algorithm.
		-- 1.3.6.1.4.1.2011.2.25.3.35.30.1
		alarmTable OBJECT-TYPE
			SYNTAX SEQUENCE OF AlarmEntry
			MAX-ACCESS not-accessible
			STATUS current
			DESCRIPTION
				"A list of alarm entries."
			::= { alarm 1 }
		
		-- 1.3.6.1.4.1.2011.2.25.3.35.30.1.1
		alarmEntry OBJECT-TYPE
			SYNTAX AlarmEntry
			MAX-ACCESS not-accessible
			STATUS current
			DESCRIPTION
				"A list of parameters that set up a periodic checking
				for alarm conditions.  For example, an instance of the
				alarmValue object might be named alarmValue.8"
			INDEX { alarmIndex, alarmVariable }
			::= { alarmTable 1 }
		
		AlarmEntry ::=
			SEQUENCE { 
				alarmIndex
					Unsigned32,
				alarmVariable
					PerformanceType,
				alarmInterval
					Unsigned32,
				alarmSampleType
					INTEGER,
				alarmStartupAlarm
					INTEGER,
				alarmRisingThreshold
					Unsigned32,
				alarmFallingThreshold
					Unsigned32,
				alarmStatus
					INTEGER
			 }

		-- 1.3.6.1.4.1.2011.2.25.3.35.30.1.1.1
		alarmIndex OBJECT-TYPE
			SYNTAX Unsigned32
			MAX-ACCESS read-only
			STATUS current
			DESCRIPTION
				"An index that uniquely identifies an entry in the
				alarm table.  Each such entry defines a
				diagnostic sample at a particular interval
				for an object on the device.
				
				alarmIndex of huawei optix devices can be described as following, 
				alarmIndex consists of SLOT_ID,PORT_ID and SUB_PORT_ID.        
				alarmIndex = SUB_PORT_ID<<31 + SLOT_ID<<24 + PORT_ID; 
				1) bit31(1bit) SUB_PORT_ID: 
				    0 - SUB_PORT_1(east), 1 - SUB_PORT_2(west),
				    for sonet,this para is 0 ,no other means;
				2) 24bit~30bit(7bits) SLOT_ID:   slot id;
				3) 0bit~15bit(16bits) PORT_ID:   mac port id;
				
				For example:
				1:alarmIndex.83886081.122 (gauge) 83886081
				  83886081 = 0x05000001 can be translated as Slot-5, Port-1;
				2:alarmIndex.83886082.122 (gauge) 83886082
				  83886082 = 0x05000002 can be translated as Slot-5, Port-2;
				"
			::= { alarmEntry 1 }
		
		-- 1.3.6.1.4.1.2011.2.25.3.35.30.1.1.2
		alarmVariable OBJECT-TYPE
			SYNTAX PerformanceType
			MAX-ACCESS read-only
			STATUS current
			DESCRIPTION
				" "
			::= { alarmEntry 2 }
		
		-- 1.3.6.1.4.1.2011.2.25.3.35.30.1.1.3
		alarmInterval OBJECT-TYPE
			SYNTAX Unsigned32
			UNITS "Seconds"
			MAX-ACCESS read-create
			STATUS current
			DESCRIPTION
				" "
			::= { alarmEntry 3 }
		
		-- 1.3.6.1.4.1.2011.2.25.3.35.30.1.1.4
		alarmSampleType OBJECT-TYPE
			SYNTAX INTEGER
				{
				absoluteValue(1),
				deltaValue(2)
				}
			MAX-ACCESS read-create
			STATUS current
			DESCRIPTION
				" "
			::= { alarmEntry 4 }
		
		-- 1.3.6.1.4.1.2011.2.25.3.35.30.1.1.6
		alarmStartupAlarm OBJECT-TYPE
			SYNTAX INTEGER
				{
				risingAlarm(1),
				fallingAlarm(2),
				risingOrFallingAlarm(3)
				}
			MAX-ACCESS read-create
			STATUS current
			DESCRIPTION
				"The alarm that may be sent when this entry is first
				set to valid.  If the first sample after this entry
				becomes valid is greater than or equal to the
				risingThreshold and alarmStartupAlarm is equal to
				risingAlarm(1) or risingOrFallingAlarm(3), then a single
				rising alarm will be generated.  If the first sample
				after this entry becomes valid is less than or equal
				to the fallingThreshold and alarmStartupAlarm is equal
				to fallingAlarm(2) or risingOrFallingAlarm(3), then a
				single falling alarm will be generated.
				
				This object may not be modified if the associated
				alarmStatus object is equal to valid(1)."
			::= { alarmEntry 6 }
		
		-- 1.3.6.1.4.1.2011.2.25.3.35.30.1.1.7
		alarmRisingThreshold OBJECT-TYPE
			SYNTAX Unsigned32
			MAX-ACCESS read-create
			STATUS current
			DESCRIPTION
				"A threshold for the sampled statistic.  When the current
				sampled value is greater than or equal to this threshold,
				and the value at the last sampling interval was less than
				this threshold, a single event will be generated.
				A single event will also be generated if the first
				sample after this entry becomes valid is greater than or
				equal to this threshold and the associated
				alarmStartupAlarm is equal to risingAlarm(1) or
				risingOrFallingAlarm(3).
				
				After a rising event is generated, another such event
				will not be generated until the sampled value
				falls below this threshold and reaches the
				alarmFallingThreshold.
				
				This object may not be modified if the associated
				alarmStatus object is equal to valid(1)."
			::= { alarmEntry 7 }
		
		-- 1.3.6.1.4.1.2011.2.25.3.35.30.1.1.8
		alarmFallingThreshold OBJECT-TYPE
			SYNTAX Unsigned32
			MAX-ACCESS read-create
			STATUS current
			DESCRIPTION
				"A threshold for the sampled statistic.  When the current
				sampled value is less than or equal to this threshold,
				and the value at the last sampling interval was greater than
				this threshold, a single event will be generated.
				A single event will also be generated if the first
				sample after this entry becomes valid is less than or
				equal to this threshold and the associated
				alarmStartupAlarm is equal to fallingAlarm(2) or
				risingOrFallingAlarm(3).
				
				After a falling event is generated, another such event
				will not be generated until the sampled value
				rises above this threshold and reaches the
				alarmRisingThreshold.
				
				This object may not be modified if the associated
				alarmStatus object is equal to valid(1)."
			::= { alarmEntry 8 }
		
		-- 1.3.6.1.4.1.2011.2.25.3.35.30.1.1.12
		alarmStatus OBJECT-TYPE
			SYNTAX INTEGER
				{
				valid(1),
				invalid(4)
				}
			MAX-ACCESS read-create
			STATUS current
			DESCRIPTION
				"The status of this alarm variable."
			::= { alarmEntry 12 }
		
		-- 1.3.6.1.4.1.2011.2.25.3.35.40
		optixRmonMibConformance OBJECT IDENTIFIER ::= { optixRmonMib 40 }
		
		-- 1.3.6.1.4.1.2011.2.25.3.35.40.1
		optixRmonMibGroups OBJECT IDENTIFIER ::= { optixRmonMibConformance 1 }
		
		-- 1.3.6.1.4.1.2011.2.25.3.35.40.1.1
		optixRmonMibObjectGroup OBJECT-GROUP
			OBJECTS { rptAlarmIndex, rptAlarmVariable, rptAlarmSampleType, rptAlarmValue, rptAlarmRisingThreshold, 
				rptAlarmFallingThreshold, rptAlarmInterval, rptAlarmDateTime, etherStatsIndex, etherStatsDropEvents, 
				etherStatsOctets, etherStatsPkts, etherStatsBroadcastPkts, etherStatsMulticastPkts, etherStatsCRCAlignErrors, 
				etherStatsUndersizePkts, etherStatsOversizePkts, etherStatsFragments, etherStatsJabbers, etherStatsCollisions, 
				etherStatsPkts64Octets, etherStatsPkts65to127Octets, etherStatsPkts128to255Octets, etherStatsPkts256to511Octets, etherStatsPkts512to1023Octets, 
				etherStatsPkts1024to1518Octets, etherExStatsIndex, etherStatsPkts1519toMTUOctets, etherStatsTranPkts64Octets, etherStatsTranPkts65to127Octets, 
				etherStatsTranPkts128to255Octets, etherStatsTranPkts256to511Octets, etherStatsTranPkts512to1023Octets, etherStatsTranPkts1024to1518Octets, etherStatsTranPkts1519toMTUOctets, 
				etherStatsRxTxPkts64Octets, etherStatsRxTxPkts65to127Octets, etherStatsRxTxPkts128to255Octets, etherStatsRxTxPkts256to511Octets, etherStatsRxTxPkts512to1023Octets, 
				etherStatsRxTxPkts1024to1518Octets, etherStatsRxTxPkts1519toMTUOctets, etherStatsInUcastPkts, etherStatsOutUcastPkts, etherStatsInPauseFrames, 
				etherStatsOutPauseFrames, etherStatsOutMulticastPkts, etherStatsOutBroadcastPkts, etherStatsInGoodOctets, etherStatsOutGoodOctets, 
				etherStatsInBadOctets, etherStatsOutBadOctets, etherStatsAlignmentErrors, etherStatsFCSErrors, etherStatsSingleCollisionFrames, 
				etherStatsMultipleCollisionFrames, etherStatsLateCollisions, etherStatsExcessiveCollisions, etherStatsDeferredTransmissions, etherStatsCarrierSenseErrors, 
				etherStatsInControlFrames, etherStatsOutControlFrames, etherStatsOutDropEvents, etherStatsOutOversizePkts, etherStatsOutPkts, 
				etherStatsOutOctets, historyControlIndex, historyControlBucketsRequested, historyControlInterval, historyControlStatus, 
				etherHistoryIndex, etherHistorySampleIndex, etherHistoryIntervalStart, etherHistoryDropEvents, etherHistoryOctets, 
				etherHistoryPkts, etherHistoryBroadcastPkts, etherHistoryMulticastPkts, etherHistoryCRCAlignErrors, etherHistoryUndersizePkts, 
				etherHistoryOversizePkts, etherHistoryFragments, etherHistoryJabbers, etherHistoryCollisions, etherHistoryUtilization, 
				etherExHistoryIndex, etherExHistorySampleIndex, etherExHistoryIntervalStart, etherExHistoryInUcastPkts, etherExHistoryOutUcastPkts, 
				etherExHistoryInPauseFrames, etherExHistoryOutPauseFrames, etherExHistoryOutMulticastPkts, etherExHistoryOutBroadcastPkts, etherExHistoryInGoodOctets, 
				etherExHistoryOutGoodOctets, etherExHistoryInBadOctets, etherExHistoryOutBadOctets, etherExHistoryAlignmentErrors, etherExHistoryFCSErrors, 
				etherExHistorySingleCollisionFrames, etherExHistoryMultipleCollisionFrames, etherExHistoryLateCollisions, etherExHistoryExcessiveCollisions, etherExHistoryDeferredTransmissions, 
				etherExHistoryCarrierSenseErrors, etherExHistoryInControlFrames, etherExHistoryOutControlFrames, etherExHistorysOutDropEvents, etherExHistorysOutOversizePkts, 
				etherExHistoryOutPkts, etherExHistoryOutOctets, alarmIndex, alarmVariable, alarmInterval, 
				alarmSampleType, alarmStartupAlarm, alarmRisingThreshold, alarmFallingThreshold, alarmStatus
				 }
			STATUS current
			DESCRIPTION 
				"Enter the description of the created OBJECT-GROUP."
			::= { optixRmonMibGroups 1 }
		
		-- 1.3.6.1.4.1.2011.2.25.3.35.40.1.2
		optixRmonMibNotificationGroup NOTIFICATION-GROUP
			NOTIFICATIONS { rmonRisingAlarm, rmonFallingAlarm }
			STATUS current
			DESCRIPTION 
				"Enter the description of the created NOTIFICATION-GROUP."
			::= { optixRmonMibGroups 2 }
		
		-- 1.3.6.1.4.1.2011.2.25.3.35.40.2
		optixRmonMibCompliances OBJECT IDENTIFIER ::= { optixRmonMibConformance 2 }
		
		-- 1.3.6.1.4.1.2011.2.25.3.35.40.2.1
		optixRmonMibBasicCompliance MODULE-COMPLIANCE
			STATUS current
			DESCRIPTION 
				"Enter the description of the created MODULE-COMPLIANCE."
			MODULE -- this module
				MANDATORY-GROUPS { optixRmonMibObjectGroup, optixRmonMibNotificationGroup }
			::= { optixRmonMibCompliances 1 }
		
	
	END

--
-- OPTIX-RMON-MIB.mib
--
