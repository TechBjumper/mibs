--  =======================================================================
--  File        : gswitch.mib
--  Description : Private MIB for NH218,NH228 Switches
--                Ethernet Switches
--  By          : Shlomo Aran
--  Version     : $Revision:   1.1$ modified by yaki on July 14, 1996
--  Date        : $Date:   February 12, 1996
--  =======================================================================
--
--
-- Copyright (c) 1996 NBase Switch Communications.  All Rights Reserved.
--
-- Reproduction of this document is authorized on condition that this
-- copyright notice is included.  This NBase SNMP MIB Specification
-- embodies NBase's proprietary intellectual property.  NBase
-- retains all title and ownership in the specification, including any
-- revisions.
--
-- It is NBase's intent to encourage the widespread use of this
-- specification in connection with the management of NBase's
-- products. NBase grants vendor, end-users, and other interested
-- parties a non-exclusive license to use this specification in
-- connection with the management of NBase's products.
--
-- This specification is supplied "AS IS," and NBase makes no
-- warranty, either express or implied, as to the use, operation,
-- condition, or performance of the specification.
--
-- NBase retains the right to change this MIB without notification.
--
--  NH218-MIB DEFINITIONS ::= BEGIN

GSWITCH-MIB DEFINITIONS ::= BEGIN

        IMPORTS
                enterprises,
--              NetworkAdress,
                Counter                       FROM RFC1155-SMI

                OBJECT-TYPE                   FROM RFC-1212
                DisplayString                 FROM RFC1213-MIB
                TRAP-TYPE                     FROM RFC-1215;

--  --------------------------------------------------------------------------
--  NBase Object Identifier Definition
--  --------------------------------------------------------------------------

nbase             OBJECT IDENTIFIER ::= { enterprises 629 }
gswitch           OBJECT IDENTIFIER ::= { nbase 2 }

nbsDevIdentify    OBJECT IDENTIFIER ::= { gswitch 2 }
nbsDeviceControl  OBJECT IDENTIFIER ::= { gswitch 3 }
nbsPortsControl   OBJECT IDENTIFIER ::= { gswitch 5 }
nbsPortsStatus    OBJECT IDENTIFIER ::= { gswitch 6 }
nbsPortsCounters  OBJECT IDENTIFIER ::= { gswitch 7 }
nbsAddressTable   OBJECT IDENTIFIER ::= { gswitch 8 }
nbsSlotsTable     OBJECT IDENTIFIER ::= { gswitch 9 }
nbsPALPorts       OBJECT IDENTIFIER ::= { gswitch 12 }

nbsNPorts   OBJECT-TYPE
        SYNTAX  INTEGER
        ACCESS  read-only
        STATUS  mandatory
        DESCRIPTION
                "The number of ports in this device"
        ::= { gswitch 1 }

nbsNMacRecords   OBJECT-TYPE
        SYNTAX  INTEGER
        ACCESS  read-only
        STATUS  mandatory
        DESCRIPTION
                "The number of Records (addresses) in the MAC table"
        ::= { gswitch 10 }

nbsMacFirstGap   OBJECT-TYPE
        SYNTAX  INTEGER
        ACCESS  read-only
        STATUS  mandatory
        DESCRIPTION
                "The index of the first gap (empty record) in the MAC table"
        ::= { gswitch 11 }

--  ***************************************************************************
--  Define the 'nbsDevIdentify' Group
--  ***************************************************************************

nbsUpLinkType  OBJECT-TYPE
        SYNTAX  INTEGER
        {
         notExist                    (1),
         fast2Ethernet100BaseTX      (2),
         fast2Ethernet100BaseTxFx    (3),
         fast2Ethernet100BaseFX      (4),
         atm                         (5),
	 fast8Ethernet100BaseTX      (6),
         fast8Ethernet10or100BaseTX  (7),
         fast5Ethernet100BaseTX      (8),
         fast5Ethernet100BaseFX      (9),
         fast8Ethernet100BaseTP     (10),
	 fast4Ethernet100BaseFO     (11),
	 isdn                       (12),
	 vpn                        (13),
	 fast1Ethernet1000BaseGE    (14),
	 fddi                       (15),
	 fast2Ethernet1000BaseGE    (16)
	}
        ACCESS  read-only
	STATUS  mandatory
        DESCRIPTION
                "Up-Link Type of the device"
        ::= { nbsDevIdentify 1 }

nbsBaseHardVers  OBJECT-TYPE
        SYNTAX  INTEGER
        ACCESS  read-only
        STATUS  mandatory
        DESCRIPTION
                "Hardware version of base card"
        ::= { nbsDevIdentify 3 }

nbsCardHardVers  OBJECT-TYPE
        SYNTAX  INTEGER
        ACCESS  read-only
        STATUS  mandatory
        DESCRIPTION
                "Hardware version of the agent card"
        ::= { nbsDevIdentify 4 }

nbsUpLinkHardVers  OBJECT-TYPE
        SYNTAX  INTEGER
        ACCESS  read-only
        STATUS  mandatory
        DESCRIPTION
                "Up-Link hardware version"
        ::= { nbsDevIdentify 5 }

nbsSoftVers  OBJECT-TYPE
        SYNTAX  INTEGER
        ACCESS  read-only
        STATUS  mandatory
        DESCRIPTION
                "Agent software version"
        ::= { nbsDevIdentify 6 }

nbsSnifferPort  OBJECT-TYPE
        SYNTAX  INTEGER
        ACCESS  read-only
        STATUS  mandatory
        DESCRIPTION
                "Sniffer Port Number.
                 Specify the Sniffer Port Number chosen by
                 the user"
        ::= { nbsDevIdentify 9 }

nbsCreatinDate  OBJECT-TYPE
        SYNTAX  DisplayString
        ACCESS  read-only
        STATUS  mandatory
        DESCRIPTION
                "Agent software creation date and time"
        ::= { nbsDevIdentify 10 }

--  ***************************************************************************
--  Define the 'nbsDeviceControl' Group
--  ***************************************************************************

nbsSpanningTree OBJECT-TYPE
        SYNTAX  INTEGER
        {
         disable  (1),
	 enable   (2)
        }
        ACCESS  read-write
        STATUS  mandatory
        DESCRIPTION
                "Spanning Tree Enable.
                 1 - The BPDU(Bridge Protocol Data Unit) packets are treated
                     as Multicast Packets, and therefore are forwarded to
                     all ports.
                 2 - Forwards BPDU(Bridge Protocol Data Unit) packets to the CPU only."
        ::= { nbsDeviceControl 6 }

nbsLearningProcess OBJECT-TYPE
        SYNTAX  INTEGER
        {
         enable  (1),
         disable (2)
        }
        ACCESS  read-write
        STATUS  mandatory
        DESCRIPTION
                "Disable Learning Process.
                 1 - Learning Process is disabled. The Switch-G will not learn
                     any new addresses from the wire.
                 2 - Learning Process is enabled"
        ::= { nbsDeviceControl 7 }

nbsParitionEnable OBJECT-TYPE
        SYNTAX  INTEGER
        {
         enable  (1),
         disable (2)
        }
        ACCESS  read-write
        STATUS  mandatory
        DESCRIPTION
                "Partition Mode Enable.
                 When more then 32 collisions occur while transmitting, the
                 Switch-G port enters to the Partition mode. It waits for the first
                 good packet from the wire and then return to Normal mode of opration.
                 In Partition mode transmitting fromthe port is enabled but receiving is disabled.
                 1 - Patrition mode,
                 2 - Normal mode"
        ::= { nbsDeviceControl 8 }

nbsRMONmode OBJECT-TYPE
        SYNTAX  INTEGER
        {
         enable  (1),
         disable (2)
        }
        ACCESS  read-write
        STATUS  mandatory
        DESCRIPTION
                "RMON  Enable.
                 1 - The Switch-G enters the RMON mode(Station-to-Station
                     connectivity Matrix).
                 2 - RMON disabled"
        ::= { nbsDeviceControl 9 }

nbsBufferThreshold OBJECT-TYPE
        SYNTAX  INTEGER
        {
         limited (1),
         not-limited (2)
        }
        ACCESS  read-write
        STATUS  mandatory
        DESCRIPTION
                "Buffer Threshold Enable.
                 Meaningful only when RMONEn bit (internal) is set.
                 1 - The buffers allocated to the ports
                     are limited to the number which is written in the
                     Rx Buffers Threshold Register.
                 2 - There is no limitation on the buffers allocation"
        ::= { nbsDeviceControl 10 }

nbsForwardMulticast OBJECT-TYPE
        SYNTAX  INTEGER
        {
         enable  (1),
         disable (2)
        }
        ACCESS  read-write
        STATUS  mandatory
        DESCRIPTION
                "Forward Multicast.
                 Enable - multicast packets are Forwarded only to the CPU.
                 Disable - multicast packets are being forward to all ports"
        ::= { nbsDeviceControl 12 }

nbsForwardUnkPkts OBJECT-TYPE
        SYNTAX  INTEGER
        {
         enable  (1),
         disable (2)
        }
        ACCESS  read-write
        STATUS  mandatory
        DESCRIPTION
                "Forward Unknown Packets.
                 If defines whether the Switch-G will forward Unknown
                 packets to the Agent CPU or not.
                 1 - Forwared,
                 2 - Do not forwared"
        ::= { nbsDeviceControl 15 }

nbsBackOffMode   OBJECT-TYPE
        SYNTAX  INTEGER {
                normal     (1),
                aggressive (2)
               }
        ACCESS  read-write
        STATUS  mandatory
        DESCRIPTION
                "The CSMA/CD normal Back of mode multiples the back-off 
                 time frame after each each collision. In aggressive mode
                 it stops to multiply after the second time. This way it
                 will have an advantage of any other NIC who uses normal
                 back-off mode."
        ::= { nbsDeviceControl 16 }

--  ***************************************************************************
--  Define the 'nbsPortsControl' Group
--  ***************************************************************************

nbsPortsContTable OBJECT-TYPE
        SYNTAX  SEQUENCE OF NbsPortsContEntry
        ACCESS  not-accessible
        STATUS  mandatory
        DESCRIPTION
                "A list of the port counters entries"
        ::= { nbsPortsControl 1 }

nbsPortsContEntry     OBJECT-TYPE
        SYNTAX  NbsPortsContEntry
        ACCESS  not-accessible
        STATUS  mandatory
        DESCRIPTION
                "Contains the information necessary to configure/describe a
                 port configuration. The number of rows/entries is fixed. A
                 row/entry may not be created or deleted"

        INDEX { nbsPortIndex1}

        ::= { nbsPortsContTable 1 }

NbsPortsContEntry ::= SEQUENCE {

        nbsPortIndex1        INTEGER,
        nbsPortEnable        INTEGER,
        nbsPortDuplex        INTEGER,
        nbsPortMonitor       INTEGER,
        nbsPortPolDetection  INTEGER,
        nbsPortBroadcast     INTEGER,
        nbsPortForwardUnk    INTEGER,
	nbsPortSpaning       INTEGER,
	nbsPortSpeed         INTEGER
       }

nbsPortIndex1    OBJECT-TYPE
        SYNTAX  INTEGER
        ACCESS  read-only
        STATUS  mandatory
        DESCRIPTION
                "The port# from 1 to nbsNPorts1"
        ::= { nbsPortsContEntry 1 }

nbsPortEnable OBJECT-TYPE
        SYNTAX  INTEGER
        {
         enable (1),
         disable (2)
        }
        ACCESS  read-write
        STATUS  mandatory
        DESCRIPTION
                "Port Enable.
                 1 - Port is enabled
                 2 - Port is disabled"
        ::= { nbsPortsContEntry 2 }

nbsPortDuplex OBJECT-TYPE
        SYNTAX  INTEGER
        {
         half (1),
         full (2)
        }
        ACCESS  read-write
        STATUS  mandatory
        DESCRIPTION
                "Half/Full Duplex.
                 1 - Port works in Half-Duplex mode
                 2 - Port works in Full-Duplex mode"
        ::= { nbsPortsContEntry 3 }

nbsPortMonitor OBJECT-TYPE
        SYNTAX  INTEGER
        {
         normal  (1),
         sniffer (2)
        }
        ACCESS  read-write
        STATUS  mandatory
        DESCRIPTION
                "Monitoring Mode.
                 1 - Port works in normal mode
                 2 - Port is set as Sniffer port (monitor mode) were all recived
                 and transmit packats from all ports are sent to the Sniffer port"
        ::= { nbsPortsContEntry 5 }

nbsPortPolDetection OBJECT-TYPE
        SYNTAX  INTEGER
        {
         enable (1),
         disabel (2)
        }
        ACCESS  read-write
        STATUS  mandatory
        DESCRIPTION
                "Auto-Polarity Disable.
                  Enable/Disable Auto-Polarity detection function
                  1 - Disable
                  2 - Enable"
        ::= { nbsPortsContEntry 6 }

nbsPortBroadcast OBJECT-TYPE
        SYNTAX  INTEGER
        {
         forward (1),
         discard (2)
        }
        ACCESS  read-write
        STATUS  mandatory
        DESCRIPTION
                "Filter Broadcast.
                 1 - Broadcast packats are forwarded to all ports.
                 2 - The Switch-G discards Broadcast packats"
        ::= { nbsPortsContEntry 7 }

nbsPortForwardUnk OBJECT-TYPE
        SYNTAX  INTEGER
        {
         forward (1),
         discard (2)
        }
        ACCESS  read-write
        STATUS  mandatory
        DESCRIPTION
                "Forward Unknown.
                 1 - Unknown packats are forwarded.
                 2 - The Switch-G does not forward unknown packats
                 to this port"
        ::= { nbsPortsContEntry 8 }

nbsPortSpaning OBJECT-TYPE
        SYNTAX  INTEGER
        {
         accept  (1),
         discard (2)
        }
        ACCESS  read-write
        STATUS  mandatory
        DESCRIPTION
                "Spaning Tree Enable.
                 Meaniningful only when Spaning Tree for the switch is set
                 (nbsSpanningTree) is set.
		 1 - All packets are accepted.
                 2 - The Switch-G discards all incoming/outgoing packets
		 except for BPDU packets"
        ::= { nbsPortsContEntry 9 }

nbsPortSpeed OBJECT-TYPE
        SYNTAX  INTEGER
        {
         none       (1),
         s10MBps    (2),
         s100MBps   (3),
         s1000MBps  (4),
         s10000MBps (5)
        }
        ACCESS  read-write
        STATUS  mandatory
	DESCRIPTION
		"Ports Speed.
		 Meaningfull only for ports that support both 10 and 100
		 MBps speeds.
		 1 - Only for Uplink Ports: Switch-G  -  Ports ## 27,28
					    Switch-G  -  Ports ## 17,18
		 2 - After reset the port will operate in 10 MBps
		 3 - After reset the port will operate in 100 Mbps
		 4 - The port will operate in 1000 Mbps
                 5 - The port will operate in 10000 MBps (for example, XFP)."
	::= { nbsPortsContEntry 10 }

--  ***************************************************************************
--  Define the 'nbsPortsStatus' Group
--  ***************************************************************************

nbsPortsStatTable OBJECT-TYPE
        SYNTAX  SEQUENCE OF NbsPortsStatEntry
        ACCESS  not-accessible
        STATUS  mandatory
        DESCRIPTION
                "A list of all the port status objects"
        ::= { nbsPortsStatus 1 }

nbsPortsStatEntry      OBJECT-TYPE
        SYNTAX  NbsPortsStatEntry
        ACCESS  not-accessible
        STATUS  mandatory
        DESCRIPTION
                "The ports status information.
                 port configuration. The number of rows/entries is fixed. A
                 row/entry may not be created or deleted"

        INDEX { nbsPortIndex }

        ::= { nbsPortsStatTable 1 }

NbsPortsStatEntry ::= SEQUENCE {

        nbsPortIndex         INTEGER,
        nbsPortType          INTEGER,
        nbsPartition         INTEGER,
        nbsLinkTest          INTEGER
        }

nbsPortIndex    OBJECT-TYPE
        SYNTAX  INTEGER
        ACCESS  read-only
        STATUS  mandatory
        DESCRIPTION
                "The port# from 1 to nbsNPorts1"
        ::= { nbsPortsStatEntry 1 }

nbsPortType    OBJECT-TYPE
        SYNTAX  INTEGER
        {
         empty (1),
         normal (2),
         fastCopper   (3),
         fastFiber    (4),
         slowFiber    (5), 
         gigaCopper   (6)  
        }
        ACCESS  read-only
        STATUS  mandatory
        DESCRIPTION
                "Port Type"
        ::= { nbsPortsStatEntry 2 }

nbsPartition    OBJECT-TYPE
        SYNTAX  INTEGER
        {
         yes (1),
         no  (2)
        }
        ACCESS  read-only
        STATUS  mandatory
        DESCRIPTION
                "Ports Partition.
                 Indicates the ports Partition status.
                 1 - No Partition (Normal mode)
                 2 - Partition"
        ::= { nbsPortsStatEntry 3 }

nbsLinkTest    OBJECT-TYPE
        SYNTAX  INTEGER
        {
         pass (1),
         fail (2)
        }
        ACCESS  read-only
        STATUS  mandatory
        DESCRIPTION
                "Ports Link Test Fail.
                 Indicates the ports Link Test status
                 1 - Link Test Pass
                 2 - Link Test Fail"
        ::= { nbsPortsStatEntry 4 }

--  ***************************************************************************
--  Define the 'nbsPortsCounters' Group
--  ***************************************************************************

nbsPortsCountTable OBJECT-TYPE
        SYNTAX  SEQUENCE OF NbsPortsCountEntry
        ACCESS  not-accessible
        STATUS  mandatory
        DESCRIPTION
                "A list of the port counters entries"
        ::= { nbsPortsCounters 1 }

nbsPortsCountEntry     OBJECT-TYPE
        SYNTAX  NbsPortsCountEntry
        ACCESS  not-accessible
        STATUS  mandatory
        DESCRIPTION
                "Contains the information necessary to configure/describe a
                 port configuration. The number of rows/entries is fixed. A
                 row/entry may not be created or deleted"

        INDEX { nbsPortIndex2 }

        ::= { nbsPortsCountTable 1 }

NbsPortsCountEntry ::= SEQUENCE {

        nbsPortIndex2         INTEGER,
        nbsPortByteRec        Counter,
        nbsPortMulByteRec     Counter,
        nbsPortBroadByteRec   Counter,
        nbsPortByteSent       Counter,
        nbsPortFramesRec      Counter,
        nbsPortMulFramesRec   Counter,
        nbsPortBroadFramesRec Counter,
        nbsPortFramesSent     Counter,
        nbsPortCollisions     Counter,
        nbsPortLateColl       Counter,
        nbsPortCRCAligErr     Counter,
        nbsPortFramesShort    Counter,
        nbsPortFrameLong      Counter,
        nbsPortJabber         Counter,
        nbsPortBadByteRec     Counter
        }

nbsPortIndex2    OBJECT-TYPE
        SYNTAX  INTEGER
        ACCESS  read-only
        STATUS  mandatory
        DESCRIPTION
                "The port# from 1 to nbsNPorts1"
        ::= { nbsPortsCountEntry 1 }

nbsPortByteRec OBJECT-TYPE
        SYNTAX  Counter
        ACCESS  read-only
        STATUS  mandatory
        DESCRIPTION
                "Good Bytes Recived"
        ::= { nbsPortsCountEntry 2 }

nbsPortMulByteRec OBJECT-TYPE
        SYNTAX  Counter
        ACCESS  read-only
        STATUS  mandatory
        DESCRIPTION
                "Good Multicast Bytes Recived"
        ::= { nbsPortsCountEntry 3 }

nbsPortBroadByteRec OBJECT-TYPE
        SYNTAX  Counter
        ACCESS  read-only
        STATUS  mandatory
        DESCRIPTION
                "Good Broadcast Bytes Recived"
        ::= { nbsPortsCountEntry 4 }

nbsPortByteSent OBJECT-TYPE
        SYNTAX  Counter
        ACCESS  read-only
        STATUS  mandatory
        DESCRIPTION
                "Good Bytes Sent"
        ::= { nbsPortsCountEntry 5 }

nbsPortFramesRec OBJECT-TYPE
        SYNTAX  Counter
        ACCESS  read-only
        STATUS  mandatory
        DESCRIPTION
                "Good Frames Recived"
        ::= { nbsPortsCountEntry 6 }

nbsPortMulFramesRec OBJECT-TYPE
        SYNTAX  Counter
        ACCESS  read-only
        STATUS  mandatory
        DESCRIPTION
                "Good Multicast Frames Recived"
        ::= { nbsPortsCountEntry 7 }

nbsPortBroadFramesRec OBJECT-TYPE
        SYNTAX  Counter
        ACCESS  read-only
        STATUS  mandatory
        DESCRIPTION
                "Broadcast Frames Recived"
        ::= { nbsPortsCountEntry 8 }

nbsPortFramesSent OBJECT-TYPE
        SYNTAX  Counter
        ACCESS  read-only
        STATUS  mandatory
        DESCRIPTION
                "Frames Sent"
        ::= { nbsPortsCountEntry 9  }

nbsPortCollisions OBJECT-TYPE
        SYNTAX  Counter
        ACCESS  read-only
        STATUS  mandatory
        DESCRIPTION
                "Recive and Transmit Collision"
        ::= { nbsPortsCountEntry 10 }

nbsPortLateColl OBJECT-TYPE
        SYNTAX  Counter
        ACCESS  read-only
        STATUS  mandatory
        DESCRIPTION
                "Recive and Transmit Late Collision"
        ::= { nbsPortsCountEntry 11 }

nbsPortCRCAligErr OBJECT-TYPE
        SYNTAX  Counter
        ACCESS  read-only
        STATUS  mandatory
        DESCRIPTION
                "Recive CRC or Alignment Error"
        ::= { nbsPortsCountEntry 12 }

nbsPortFramesShort OBJECT-TYPE
        SYNTAX  Counter
        ACCESS  read-only
        STATUS  mandatory
        DESCRIPTION
                "Recive Frames"
        ::= { nbsPortsCountEntry 13 }

nbsPortFrameLong OBJECT-TYPE
        SYNTAX  Counter
        ACCESS  read-only
        STATUS  mandatory
        DESCRIPTION
                "Recive Frames > 1518 bytes with Good CRC"
        ::= { nbsPortsCountEntry 14 }

nbsPortJabber OBJECT-TYPE
        SYNTAX  Counter
        ACCESS  read-only
        STATUS  mandatory
        DESCRIPTION
                "Recive Frames > 1518 bytes with Bad CRC"
        ::= { nbsPortsCountEntry 15 }

nbsPortBadByteRec OBJECT-TYPE
        SYNTAX  Counter
        ACCESS  read-only
        STATUS  mandatory
        DESCRIPTION
                "Bad Bytes Recived.
                Bytes with CRC errors and frame too long"
        ::= { nbsPortsCountEntry 16 }

--  ***************************************************************************
--  Define the 'nbsAddressTable' Group
--  ***************************************************************************

nbsMACAddrTable OBJECT-TYPE
        SYNTAX  SEQUENCE OF NbsMACAddrEntry
        ACCESS  not-accessible
        STATUS  mandatory
        DESCRIPTION
                 "The DRAM address table contains all the MAC addresses
                  up to 8K records."

        ::= { nbsAddressTable 1 }

nbsMACAddrEntry  OBJECT-TYPE
        SYNTAX  NbsMACAddrEntry
        ACCESS  not-accessible
        STATUS  mandatory
        DESCRIPTION
                "The entries (records)"

        INDEX { nbsAddrIndex }

        ::= { nbsMACAddrTable 1 }

NbsMACAddrEntry ::= SEQUENCE {

        nbsAddrIndex         INTEGER,
        nbsMACAddress        OCTET STRING,
        nbsAddrPort          INTEGER,
        nbsAddrStatic        INTEGER,
        nbsAddrForwardTo     INTEGER
       }

nbsAddrIndex  OBJECT-TYPE
        SYNTAX  INTEGER
        ACCESS  read-only
        STATUS  mandatory
        DESCRIPTION
                "An index from 1 to 8K. * (number of devices+1)"
        ::= { nbsMACAddrEntry 1 }

nbsMACAddress   OBJECT-TYPE
        SYNTAX  OCTET STRING (SIZE(6))
        ACCESS  read-write
        STATUS  mandatory
        DESCRIPTION
                "The MAC Address where the packet came from"
        ::= { nbsMACAddrEntry 3 }

nbsAddrPort   OBJECT-TYPE
        SYNTAX  INTEGER
        ACCESS  read-write
        STATUS  mandatory
        DESCRIPTION
                "The source port in this device"
        ::= { nbsMACAddrEntry 4 }

nbsAddrStatic   OBJECT-TYPE
        SYNTAX  INTEGER
        {
         yes (1),
         no  (2)
        }
        ACCESS  read-write
        STATUS  mandatory
        DESCRIPTION
                "Static indecation bit in the MAC Address entry"
        ::= { nbsMACAddrEntry 5 }

nbsAddrForwardTo   OBJECT-TYPE
        SYNTAX  INTEGER
        {
         destination-port (1),
         all-ports (2)
        }
        ACCESS  read-write
        STATUS  mandatory
        DESCRIPTION
                "This indicates whether to forward frames destined
                 to this MAC address to all ports or only to the 
                 destination port"
        ::= { nbsMACAddrEntry 6 }

--  ***************************************************************************
--  Define the Cards' Types (for NH5500 and other GSWITCH HUBS..)
--  ***************************************************************************

nbsCardsTable OBJECT-TYPE
        SYNTAX  SEQUENCE OF NbsCardsEntry
        ACCESS  not-accessible
        STATUS  mandatory
        DESCRIPTION
                 "define the Cards' Types 
                  (for NH5500 and other GSWITCH HUBS..)."

        ::= { nbsSlotsTable 1 }

nbsCardsEntry  OBJECT-TYPE
        SYNTAX  NbsCardsEntry
        ACCESS  not-accessible
        STATUS  mandatory
        DESCRIPTION
                "The entries (records)"

        INDEX { nbsAddrIndex }

        ::= { nbsCardsTable 1 }

NbsCardsEntry ::= SEQUENCE {

        nbsCardIndex         INTEGER,
        nbsCardType          INTEGER
       }

nbsCardIndex  OBJECT-TYPE
        SYNTAX  INTEGER
        ACCESS  read-only
        STATUS  mandatory
        DESCRIPTION
                "The slot#. An index from 1 to The number of slots."
        ::= { nbsCardsEntry 1 }

nbsCardType   OBJECT-TYPE
        SYNTAX  INTEGER
        {
	 emptySlot                   (1),
	 copper20Ethernet10or100Base (2),
	 copper40Ethernet10Base      (3),
         powerSupplyError            (4),
         powerSupplyOK               (5),
	 fibre10Ethernet100Base      (6),
	 fansUnitError               (7),
         fansUnitOK                  (8),         
	 universal                   (9)
	}
        ACCESS  read-only
        STATUS  mandatory
        DESCRIPTION
         "The Card's type:
	  copper20Ethernet10or100Base (2) - Slot including 20 fast   copper 10/100 MBps Ports;
	  copper40Ethernet10Base      (3) - Slot including 40 normal copper 10 MBps Ports;
	  fibre10Ethernet100Base      (6) - Slot including 10 fast fibre optic 100 MBps Ports;
	  universal                   (9) - Slot including Uplink Modules of the different types;"
	::= { nbsCardsEntry 2 }

--  ***************************************************************************
--  Ports Optic Power value for the PAL modules
--  ***************************************************************************

nbsPALPortsTable OBJECT-TYPE
        SYNTAX  SEQUENCE OF NbsPALPortsEntry
        ACCESS  not-accessible
        STATUS  mandatory
        DESCRIPTION
        "Table contain data only for
         the existing PAL modules ports."
        ::= { nbsPALPorts 1 }

nbsPALPortsEntry      OBJECT-TYPE
        SYNTAX  NbsPALPortsEntry
        ACCESS  not-accessible
        STATUS  mandatory
        DESCRIPTION
        "The PAL Optic Power Ports status."
        INDEX { nbsPALPortIndex }
        ::= { nbsPALPortsTable 1 }

NbsPALPortsEntry ::= SEQUENCE {

        nbsPALPortIndex              INTEGER,
        nbsPALPortOpticPower         INTEGER
        }

nbsPALPortIndex         OBJECT-TYPE
        SYNTAX  INTEGER
        ACCESS  read-only
        STATUS  mandatory
        DESCRIPTION
        "The number of the real existing PAL port.
         (the same as [ifIndex] in the MIB-II)."
        ::= { nbsPALPortsEntry 1 }

nbsPALPortOpticPower    OBJECT-TYPE
        SYNTAX  INTEGER
        ACCESS  read-only
        STATUS  mandatory
        DESCRIPTION
        "PAL Port Optic Power status.
         (interval: 0 - 15)"
        ::= { nbsPALPortsEntry 2 }

END
