ZTE-AN-PON-PERF-MIB DEFINITIONS ::= BEGIN
    IMPORTS 
        TruthValue                       FROM SNMPv2-TC
        RowStatus                        FROM SNMPv2-TC
        Unsigned32                       FROM SNMPv2-SMI
        Counter64                        FROM SNMPv2-SMI
        Gauge32                          FROM SNMPv2-SMI
        Integer32                        FROM SNMPv2-SMI
        DateAndTime                      FROM SNMPv2-TC
        MODULE-IDENTITY                  FROM SNMPv2-SMI
        OBJECT-GROUP                     FROM SNMPv2-CONF
        MODULE-COMPLIANCE                FROM SNMPv2-CONF
        OBJECT-TYPE                      FROM SNMPv2-SMI
        NOTIFICATION-TYPE                FROM SNMPv2-SMI
        ifIndex                          FROM IF-MIB
        DisplayString                    FROM SNMPv2-TC
        zxAnPon                          FROM ZTE-AN-SMI
        zxAnPonOnuIndex                  FROM ZTE-AN-PON-BASE-MIB
        HCPerfCurrentCount               FROM HC-PerfHist-TC-MIB
        HCPerfTimeElapsed                FROM HC-PerfHist-TC-MIB;
        
zxAnPonPerfMib MODULE-IDENTITY
    LAST-UPDATED    "201207270000Z"
    ORGANIZATION    "ZTE Corporation"
    CONTACT-INFO    "Guo HongJian      ZTE Corporation
                    Mail: guo.hongjian@zte.com.cn
                    Tel : +86-21-68897417"
    DESCRIPTION     
        "The MIB module for the management of PON performance." 
        
    REVISION        "201207270000Z"
    DESCRIPTION
        "Initial version of this MIB module."
    ::= { zxAnPon 4 }

--------------------------------------------------------------------------------
-- Following management objects are defined.

-- zxAnPonPerfObjects
    -- zxAnPonOltPerfObjects
        -- zxAnPonOltIfCurrPerfTable
        -- zxAnPonOltIfCurr15MinPerfTable
        -- zxAnPonOltIfCurr1DayPerfTable
        -- zxAnPonOltIfHis15MinPerfTable
        -- zxAnPonOltIfHis1DayPerfTable
        -- zxAnPonOltPerfAlmPrfTable
        -- zxAnPonOltPerfAlmPrfConfTable
        -- zxAnPonOltPerfAlmPrfApplyTable
        -- zxAnPonOltIfCurrMinPerfTable
        -- zxAnPonOltIfHisMinPerfTable
    -- zxAnPonOnuPerfObjects   
        -- zxAnPonOnuIfCurrPerfTable
        -- zxAnPonOnuIfCurr15MinPerfTable
        -- zxAnPonOnuIfCurr1DayPerfTable
        -- zxAnPonOnuIfHis15MinPerfTable
        -- zxAnPonOnuIfHis1DayPerfTable
        -- zxAnPonOnuPerfAlmPrfTable
        -- zxAnPonOnuPerfAlmPrfConfTable
        -- zxAnPonOnuPerfAlmPrfApplyTable
        -- zxAnPonOnuIfCurrMinPerfTable
        -- zxAnPonOnuIfHisMinPerfTable


-- Following conformance information is defined.
-- zxAnPonPerfConformance
    -- zxAnPonPerfCompliances
    -- zxAnPonPerfGroups
        -- zxAnPonIfPerfGroup
--------------------------------------------------------------------------------   
zxAnPonPerfObjects          OBJECT IDENTIFIER ::= { zxAnPonPerfMib 2 }

zxAnPonOltPerfObjects         OBJECT IDENTIFIER ::= { zxAnPonPerfObjects 1}
zxAnPonOnuPerfObjects         OBJECT IDENTIFIER ::= { zxAnPonPerfObjects 2}

--------------------------------------------------------------------------------
--  zxAnPonOltPerfObjects
--------------------------------------------------------------------------------
--------------------------------------------------------------------------------
--  OLT Interface Perforamance Table
--------------------------------------------------------------------------------
    zxAnPonOltIfCurrPerfTable OBJECT-TYPE
        SYNTAX         SEQUENCE OF ZxAnPonOltIfCurrPerfEntry
        MAX-ACCESS     not-accessible
        STATUS         current
        DESCRIPTION
            "PON interface statistics table.
             The 'IfType' of ifIndex supports 1(physical interface) 
             and 5(PON channel)."
        ::= { zxAnPonOltPerfObjects 2 }

    zxAnPonOltIfCurrPerfEntry OBJECT-TYPE
        SYNTAX         ZxAnPonOltIfCurrPerfEntry
        MAX-ACCESS     not-accessible
        STATUS         current
        DESCRIPTION
            "Entry of zxAnPonOltIfCurrPerfTable."
        INDEX    { ifIndex }
        ::= { zxAnPonOltIfCurrPerfTable 1}

    ZxAnPonOltIfCurrPerfEntry ::=
        SEQUENCE{
                zxAnPonOltIfRxOctets               Counter64,
                zxAnPonOltIfRxPkts                 Counter64,
                zxAnPonOltIfRxOctetRate            Gauge32,
                zxAnPonOltIfRxPktRate              Gauge32,
                zxAnPonOltIfRxOctetPeakRate        Gauge32,
                zxAnPonOltIfRxPktPeakRate          Gauge32,
                zxAnPonOltIfRxUcastPkts            Counter64,
                zxAnPonOltIfRxNUcastPkts           Counter64,
                zxAnPonOltIfRxMcastPkts            Counter64,
                zxAnPonOltIfRxBcastPkts            Counter64,
                zxAnPonOltIfRxDiscardPkts          Counter64,
                zxAnPonOltIfRxErrPkts              Counter64,
                zxAnPonOltIfRxPdr                  Unsigned32,
                zxAnPonOltIfRxPer                  Unsigned32,
                zxAnPonOltIfRxCrcAlignErrors       Counter64,
                zxAnPonOltIfRxUndersizePkts        Counter64,
                zxAnPonOltIfRxOversizePkts         Counter64,
                zxAnPonOltIfRxPkts64Octets         Counter64,
                zxAnPonOltIfRxPkts65To127Octets    Counter64,
                zxAnPonOltIfRxPkts128To255Octets   Counter64,
                zxAnPonOltIfRxPkts256To511Octets   Counter64,
                zxAnPonOltIfRxPkts512To1023Oct     Counter64,
                zxAnPonOltIfRxPkts1024To1518Oct    Counter64,
                zxAnPonOltIfRxBwUtilization        Unsigned32,
                zxAnPonOltIfRxAvgBwUtilization     Unsigned32,
                zxAnPonOltIfRxFragments            Counter64,
                zxAnPonOltIfRxJabbers              Counter64,
                zxAnPonOltIfRxAvgOctetRate         Gauge32,
				zxAnPonOltIfTxOctets               Counter64,
                zxAnPonOltIfTxPkts                 Counter64,
                zxAnPonOltIfTxOctetRate            Gauge32,
                zxAnPonOltIfTxPktRate              Gauge32,
                zxAnPonOltIfTxOctetPeakRate        Gauge32,
                zxAnPonOltIfTxPktPeakRate          Gauge32,
                zxAnPonOltIfTxUcastPkts            Counter64,
                zxAnPonOltIfTxNUcastPkts           Counter64,
                zxAnPonOltIfTxMcastPkts            Counter64,
                zxAnPonOltIfTxBcastPkts            Counter64,
                zxAnPonOltIfTxDiscardPkts          Counter64,
                zxAnPonOltIfTxErrPkts              Counter64,
                zxAnPonOltIfTxPdr                  Unsigned32,
                zxAnPonOltIfTxPer                  Unsigned32,
                zxAnPonOltIfTxCrcAlignErrors       Counter64,
                zxAnPonOltIfTxUndersizePkts        Counter64,
                zxAnPonOltIfTxOversizePkts         Counter64,
                zxAnPonOltIfTxPkts64Octets         Counter64,
                zxAnPonOltIfTxPkts65To127Octets    Counter64,
                zxAnPonOltIfTxPkts128To255Octets   Counter64,
                zxAnPonOltIfTxPkts256To511Octets   Counter64,
                zxAnPonOltIfTxPkts512To1023Oct     Counter64,
                zxAnPonOltIfTxPkts1024To1518Oct    Counter64,
                zxAnPonOltIfTxBwUtilization        Unsigned32,
                zxAnPonOltIfTxAvgBwUtilization     Unsigned32,
                zxAnPonOltIfTxFragments            Counter64,
                zxAnPonOltIfTxJabbers              Counter64,
                zxAnPonOltIfRxCorrFecCodes         Counter64,
                zxAnPonOltIfRxErrFecCodes          Counter64,
                zxAnPonOltIfCollisions             Counter64,
                zxAnPonOltIfDropEvents             Counter64,
				zxAnPonOltIfTxAvgOctetRate         Gauge32,
                zxAnPonOltIfCurrPerfCapability     BITS,
                zxAnPonOltIfCurrPerfReset          INTEGER
                }

    zxAnPonOltIfRxOctets OBJECT-TYPE
        SYNTAX       Counter64
        MAX-ACCESS   read-only
        STATUS       current
        DESCRIPTION
            "Received octets."
        ::= {zxAnPonOltIfCurrPerfEntry 1 }

    zxAnPonOltIfRxPkts OBJECT-TYPE
        SYNTAX       Counter64
        MAX-ACCESS   read-only
        STATUS       current
        DESCRIPTION
            "Received packets."
        ::= {zxAnPonOltIfCurrPerfEntry 2 }

    zxAnPonOltIfRxOctetRate OBJECT-TYPE
        SYNTAX       Gauge32
        UNITS        "Bps"
        MAX-ACCESS   read-only
        STATUS       current
        DESCRIPTION
            "Received bytes per second."
        ::= {zxAnPonOltIfCurrPerfEntry 3 }

    zxAnPonOltIfRxPktRate OBJECT-TYPE
        SYNTAX       Gauge32
        UNITS        "pps"  
        MAX-ACCESS   read-only
        STATUS       current
        DESCRIPTION
            "Received packets per second."
        ::= {zxAnPonOltIfCurrPerfEntry 4 }

    zxAnPonOltIfRxOctetPeakRate OBJECT-TYPE
        SYNTAX       Gauge32
        UNITS        "Bps" 
        MAX-ACCESS   read-only
        STATUS       current
        DESCRIPTION
            "Peak rate of received octets."
        ::= {zxAnPonOltIfCurrPerfEntry 5 }

    zxAnPonOltIfRxPktPeakRate OBJECT-TYPE
        SYNTAX       Gauge32
        UNITS        "pps"  
        MAX-ACCESS   read-only
        STATUS       current
        DESCRIPTION
            "Peak rate of received packets."
        ::= {zxAnPonOltIfCurrPerfEntry 6 }

    zxAnPonOltIfRxUcastPkts OBJECT-TYPE
        SYNTAX       Counter64
        MAX-ACCESS   read-only
        STATUS       current
        DESCRIPTION
            "Received unicast packets."
        ::= {zxAnPonOltIfCurrPerfEntry 7 }

    zxAnPonOltIfRxNUcastPkts OBJECT-TYPE
        SYNTAX       Counter64
        MAX-ACCESS   read-only
        STATUS       current
        DESCRIPTION
            "Received non-unicast packets."
        ::= {zxAnPonOltIfCurrPerfEntry 8 }

    zxAnPonOltIfRxMcastPkts OBJECT-TYPE
        SYNTAX       Counter64
        MAX-ACCESS   read-only
        STATUS       current
        DESCRIPTION
            "Received multicast packets."
        ::= {zxAnPonOltIfCurrPerfEntry 9 }

    zxAnPonOltIfRxBcastPkts OBJECT-TYPE
        SYNTAX       Counter64
        MAX-ACCESS   read-only
        STATUS       current
        DESCRIPTION
            "Received broadcast packets."
        ::= {zxAnPonOltIfCurrPerfEntry 10 }

    zxAnPonOltIfRxDiscardPkts OBJECT-TYPE
        SYNTAX       Counter64
        MAX-ACCESS   read-only
        STATUS       current
        DESCRIPTION
            "Received discarded packets."
        ::= {zxAnPonOltIfCurrPerfEntry 11 }

    zxAnPonOltIfRxErrPkts OBJECT-TYPE
        SYNTAX       Counter64
        MAX-ACCESS   read-only
        STATUS       current
        DESCRIPTION
            "Received errored packets."
        ::= {zxAnPonOltIfCurrPerfEntry 12 }

    zxAnPonOltIfRxPdr OBJECT-TYPE
        SYNTAX       Unsigned32
        MAX-ACCESS   read-only
        STATUS       current
        DESCRIPTION
            "Received packets drop ratio, in 10^-9 granularity."
        ::= {zxAnPonOltIfCurrPerfEntry 13 }

    zxAnPonOltIfRxPer OBJECT-TYPE
        SYNTAX       Unsigned32
        MAX-ACCESS   read-only
        STATUS       current
        DESCRIPTION
            "Received packets error ratio, in 10^-9 granularity."
        ::= {zxAnPonOltIfCurrPerfEntry 14 }

    zxAnPonOltIfRxCrcAlignErrors OBJECT-TYPE
        SYNTAX       Counter64
        MAX-ACCESS   read-only
        STATUS       current
        DESCRIPTION
            "The total number of packets received that
            had a length (excluding framing bits, but
            including FCS octets) of between 64 and 1518
            octets, inclusive, but but had either a bad
            Frame Check Sequence (FCS) with an integral
            number of octets (FCS Error) or a bad FCS with
            a non-integral number of octets (Alignment Error)."
        ::= {zxAnPonOltIfCurrPerfEntry 15 }

    zxAnPonOltIfRxUndersizePkts OBJECT-TYPE
        SYNTAX       Counter64
        MAX-ACCESS   read-only
        STATUS       current
        DESCRIPTION
            "The total number of packets received that were
            less than 64 octets long (excluding framing bits,
            but including FCS octets) and were otherwise well
            formed."
        ::= {zxAnPonOltIfCurrPerfEntry 16 }

    zxAnPonOltIfRxOversizePkts OBJECT-TYPE
        SYNTAX       Counter64
        MAX-ACCESS   read-only
        STATUS       current
        DESCRIPTION
            "The total number of packets received that were
            longer than 1518 octets (excluding framing bits,
            but including FCS octets) and were otherwise
            well formed."
        ::= {zxAnPonOltIfCurrPerfEntry 17 }     

    zxAnPonOltIfRxPkts64Octets      OBJECT-TYPE
        SYNTAX       Counter64
        MAX-ACCESS   read-only
        STATUS       current
        DESCRIPTION
            "The total number of packets (including bad
            packets) received that were 64 octets in length
            (excluding framing bits but including FCS octets)."
        ::= {zxAnPonOltIfCurrPerfEntry 18 }

    zxAnPonOltIfRxPkts65To127Octets OBJECT-TYPE
        SYNTAX       Counter64
        MAX-ACCESS   read-only
        STATUS       current
        DESCRIPTION
            "The total number of packets (including bad
            packets) received that were between 65 and 127 octets 
            in length (excluding framing bits but including FCS octets)."
        ::= {zxAnPonOltIfCurrPerfEntry 19 }

    zxAnPonOltIfRxPkts128To255Octets OBJECT-TYPE
        SYNTAX       Counter64
        MAX-ACCESS   read-only
        STATUS       current
        DESCRIPTION
            "The total number of packets (including bad
            packets) received that were between 128 and 255 octets 
            in length (excluding framing bits but including FCS octets)."
        ::= {zxAnPonOltIfCurrPerfEntry 20 }

    zxAnPonOltIfRxPkts256To511Octets OBJECT-TYPE
        SYNTAX       Counter64
        MAX-ACCESS   read-only
        STATUS       current
        DESCRIPTION
            "The total number of packets (including bad
            packets) received that were between 256 and 511 octets in length
            (excluding framing bits but including FCS octets)."
        ::= {zxAnPonOltIfCurrPerfEntry 21 }

    zxAnPonOltIfRxPkts512To1023Oct OBJECT-TYPE
        SYNTAX       Counter64
        MAX-ACCESS   read-only
        STATUS       current
        DESCRIPTION
            "The total number of packets (including bad
            packets) received that were between 512 and 1023 octets in length
            (excluding framing bits but including FCS octets)."
        ::= {zxAnPonOltIfCurrPerfEntry 22 }

    zxAnPonOltIfRxPkts1024To1518Oct OBJECT-TYPE
        SYNTAX       Counter64
        MAX-ACCESS   read-only
        STATUS       current
        DESCRIPTION
             "The total number of packets (including bad
             packets) received that were between 1024 and 1518 octets in length
             (excluding framing bits but including FCS octets)."
        ::= {zxAnPonOltIfCurrPerfEntry 23 }

    zxAnPonOltIfRxBwUtilization OBJECT-TYPE
        SYNTAX       Unsigned32
        UNITS        "0.1 percent"
        MAX-ACCESS   read-only
        STATUS       current
        DESCRIPTION
            "Received bandwidth throughput."
        ::= {zxAnPonOltIfCurrPerfEntry 24 }

    zxAnPonOltIfRxAvgBwUtilization OBJECT-TYPE
        SYNTAX       Unsigned32
        UNITS        "0.1 percent"
        MAX-ACCESS   read-only
        STATUS       current
        DESCRIPTION
            "Received average bandwidth utilization."
        ::= {zxAnPonOltIfCurrPerfEntry 25 }
        
    zxAnPonOltIfRxFragments  OBJECT-TYPE
        SYNTAX      Counter64
        MAX-ACCESS  read-only
        STATUS      current
        DESCRIPTION
            "The total number of packets received that were less than
         64 octets in length (excluding framing bits but including
         FCS octets) and had either a bad Frame Check Sequence
         (FCS) with an integral number of octets (FCS Error) or a
         bad FCS with a non-integral number of octets (Alignment
         Error).

         Note that it is entirely normal for zxAnPonOltIfRxFragments
          to increment.  This is because it counts both runts (which are
         normal occurrences due to collisions) and noise hits."
        ::= { zxAnPonOltIfCurrPerfEntry 26}
        
    zxAnPonOltIfRxJabbers OBJECT-TYPE
        SYNTAX      Counter64
        MAX-ACCESS  read-only
        STATUS      current
        DESCRIPTION
            "The total number of packets received that were
         longer than 1518 octets (excluding framing bits,
         but including FCS octets), and had either a bad
         Frame Check Sequence (FCS) with an integral number
         of octets (FCS Error) or a bad FCS with a non-integral
         number of octets (Alignment Error).

         Note that this definition of jabber is different
         than the definition in IEEE-802.3 section 8.2.1.5
         (10BASE5) and section 10.3.1.4 (10BASE2).  These
         documents define jabber as the condition where any
         packet exceeds 20 ms.  The allowed range to detect
         jabber is between 20 ms and 150 ms."
        ::= { zxAnPonOltIfCurrPerfEntry 27}
		
	zxAnPonOltIfRxAvgOctetRate OBJECT-TYPE
        SYNTAX       Gauge32
        UNITS        "Bps"
        MAX-ACCESS   read-only
        STATUS       current
        DESCRIPTION
            "Received average octet rate."
        ::= {zxAnPonOltIfCurrPerfEntry 28 }
		
    zxAnPonOltIfTxOctets OBJECT-TYPE
        SYNTAX       Counter64
        MAX-ACCESS   read-only
        STATUS       current
        DESCRIPTION
            "Transmitted octets."
        ::= {zxAnPonOltIfCurrPerfEntry 44 }

    zxAnPonOltIfTxPkts OBJECT-TYPE
        SYNTAX       Counter64
        MAX-ACCESS   read-only
        STATUS       current
        DESCRIPTION
            "Transmitted packets."
        ::= {zxAnPonOltIfCurrPerfEntry 45 }

    zxAnPonOltIfTxOctetRate OBJECT-TYPE
        SYNTAX       Gauge32
        UNITS        "Bps"
        MAX-ACCESS   read-only
        STATUS       current
        DESCRIPTION
            "Transmitted rate of octets."
        ::= {zxAnPonOltIfCurrPerfEntry 46 }

    zxAnPonOltIfTxPktRate OBJECT-TYPE
        SYNTAX       Gauge32
        UNITS        "pps"
        MAX-ACCESS   read-only
        STATUS       current
        DESCRIPTION
            "Transmitted rate of packets."
        ::= {zxAnPonOltIfCurrPerfEntry 47 }

    zxAnPonOltIfTxOctetPeakRate OBJECT-TYPE
        SYNTAX       Gauge32
        UNITS        "Bps"
        MAX-ACCESS   read-only
        STATUS       current
        DESCRIPTION
            "Transmitted peak rate of octets."
        ::= {zxAnPonOltIfCurrPerfEntry 48 }

    zxAnPonOltIfTxPktPeakRate  OBJECT-TYPE
        SYNTAX       Gauge32
        UNITS        "pps"
        MAX-ACCESS   read-only
        STATUS       current
        DESCRIPTION
            "Transmitted peak rate of packets."
        ::= {zxAnPonOltIfCurrPerfEntry 49 }

    zxAnPonOltIfTxUcastPkts OBJECT-TYPE
        SYNTAX       Counter64
        MAX-ACCESS   read-only
        STATUS       current
        DESCRIPTION
            "Transmitted unicast packets."
        ::= {zxAnPonOltIfCurrPerfEntry 50 }

    zxAnPonOltIfTxNUcastPkts OBJECT-TYPE
        SYNTAX       Counter64
        MAX-ACCESS   read-only
        STATUS       current
        DESCRIPTION
            "Transmitted non-unicast packets."
        ::= {zxAnPonOltIfCurrPerfEntry 51 }

    zxAnPonOltIfTxMcastPkts OBJECT-TYPE
        SYNTAX       Counter64
        MAX-ACCESS   read-only
        STATUS       current
        DESCRIPTION
            "Transmitted multicast packets."
        ::= {zxAnPonOltIfCurrPerfEntry 52 }

    zxAnPonOltIfTxBcastPkts OBJECT-TYPE
        SYNTAX       Counter64
        MAX-ACCESS   read-only
        STATUS       current
        DESCRIPTION
            "Transmitted broadcast packets."
        ::= {zxAnPonOltIfCurrPerfEntry 53 }

    zxAnPonOltIfTxDiscardPkts OBJECT-TYPE
        SYNTAX       Counter64
        MAX-ACCESS   read-only
        STATUS       current
        DESCRIPTION
            "Transmitted discarded packets."
        ::= {zxAnPonOltIfCurrPerfEntry 54 }

    zxAnPonOltIfTxErrPkts OBJECT-TYPE
        SYNTAX       Counter64
        MAX-ACCESS   read-only
        STATUS       current
        DESCRIPTION
            "Transmitted error packets."
        ::= {zxAnPonOltIfCurrPerfEntry 55 }

    zxAnPonOltIfTxPdr OBJECT-TYPE
        SYNTAX       Unsigned32
        MAX-ACCESS   read-only
        STATUS       current
        DESCRIPTION
            "Transmitted packets drop ratio, in 10^-9 granularity."
        ::= {zxAnPonOltIfCurrPerfEntry 56 }

    zxAnPonOltIfTxPer OBJECT-TYPE
        SYNTAX       Unsigned32
        MAX-ACCESS   read-only
        STATUS       current
        DESCRIPTION
            "Transmitted packets error ratio, in 10^-9 granularity."
        ::= {zxAnPonOltIfCurrPerfEntry 57 }
        
    zxAnPonOltIfTxCrcAlignErrors OBJECT-TYPE
        SYNTAX      Counter64
        MAX-ACCESS  read-only
        STATUS      current
        DESCRIPTION
            "The total number of packets sent that
         had a length (excluding framing bits, but
         including FCS octets) of between 64 and 1518
         octets, inclusive, but had either a bad
         Frame Check Sequence (FCS) with an integral
         number of octets (FCS Error) or a bad FCS with
         a non-integral number of octets (Alignment Error)."
        ::= { zxAnPonOltIfCurrPerfEntry 58}

    zxAnPonOltIfTxUndersizePkts OBJECT-TYPE
        SYNTAX      Counter64
        MAX-ACCESS  read-only
        STATUS      current
        DESCRIPTION
            "The total number of packets sent that were
         less than 64 octets long (excluding framing bits,
         but including FCS octets) and were otherwise well
         formed."
        ::= { zxAnPonOltIfCurrPerfEntry 59}
            
    zxAnPonOltIfTxOversizePkts OBJECT-TYPE
        SYNTAX      Counter64
        MAX-ACCESS  read-only
        STATUS      current
        DESCRIPTION
            "The total number of packets sent that were
         longer than 1518 octets (excluding framing bits,
         but including FCS octets) and were otherwise
         well formed."
        ::= { zxAnPonOltIfCurrPerfEntry 60}
    
    zxAnPonOltIfTxPkts64Octets OBJECT-TYPE
        SYNTAX       Counter64
        MAX-ACCESS   read-only
        STATUS       current
        DESCRIPTION
            "The total number of packets (including bad
            packets) transmitted that were 64 octets in length
            excluding framing bits but including FCS octets)."
        ::= {zxAnPonOltIfCurrPerfEntry 61 }

    zxAnPonOltIfTxPkts65To127Octets OBJECT-TYPE
        SYNTAX       Counter64
        MAX-ACCESS   read-only
        STATUS       current
        DESCRIPTION
            "The total number of packets 
             transmitted that were between 65 and 127 octets in length."
        ::= {zxAnPonOltIfCurrPerfEntry 62 }

    zxAnPonOltIfTxPkts128To255Octets OBJECT-TYPE
        SYNTAX       Counter64
        MAX-ACCESS   read-only
        STATUS       current
        DESCRIPTION
            "The total number of packets 
            transmitted that were between 128 and 255 octets in length."
        ::= {zxAnPonOltIfCurrPerfEntry 63}

    zxAnPonOltIfTxPkts256To511Octets OBJECT-TYPE
        SYNTAX       Counter64
        MAX-ACCESS   read-only
        STATUS       current
        DESCRIPTION
            "The total number of packets 
            transmitted that were between 256 and 511 octets in length."
        ::= {zxAnPonOltIfCurrPerfEntry 64 }

    zxAnPonOltIfTxPkts512To1023Oct OBJECT-TYPE
        SYNTAX       Counter64
        MAX-ACCESS   read-only
        STATUS       current
        DESCRIPTION
            "The total number of packets 
            transmitted that were between 512 and 1023 octets in length."
        ::= {zxAnPonOltIfCurrPerfEntry 65 }

    zxAnPonOltIfTxPkts1024To1518Oct OBJECT-TYPE
        SYNTAX       Counter64
        MAX-ACCESS   read-only
        STATUS       current
        DESCRIPTION
            "The total number of packets 
            transmitted that were between 1024 and 1518 octets in length."
        ::= {zxAnPonOltIfCurrPerfEntry 66 }

    zxAnPonOltIfTxBwUtilization OBJECT-TYPE
        SYNTAX       Unsigned32
        UNITS        "0.1 percent"
        MAX-ACCESS   read-only
        STATUS       current
        DESCRIPTION
            "Transmitted bandwidth throughput."
        ::= {zxAnPonOltIfCurrPerfEntry 67 }

    zxAnPonOltIfTxAvgBwUtilization OBJECT-TYPE
        SYNTAX       Unsigned32
        UNITS        "0.1 percent"
        MAX-ACCESS   read-only
        STATUS       current
        DESCRIPTION
            "Transmitted average bandwidth utilization."
        ::= {zxAnPonOltIfCurrPerfEntry 68 }
        
    zxAnPonOltIfTxFragments  OBJECT-TYPE
        SYNTAX      Counter64
        MAX-ACCESS  read-only
        STATUS      current
        DESCRIPTION
            "The total number of packets sent that were less than
         64 octets in length (excluding framing bits but including
         FCS octets) and had either a bad Frame Check Sequence
         (FCS) with an integral number of octets (FCS Error) or a
         bad FCS with a non-integral number of octets (Alignment
         Error).

         Note that it is entirely normal for zxAnPonOltIfRxFragments
          to increment.  This is because it counts both runts (which are
         normal occurrences due to collisions) and noise hits."
        ::= { zxAnPonOltIfCurrPerfEntry 69}
        
    zxAnPonOltIfTxJabbers OBJECT-TYPE
        SYNTAX      Counter64
        MAX-ACCESS  read-only
        STATUS      current
        DESCRIPTION
            "The total number of packets sent that were
         longer than 1518 octets (excluding framing bits,
         but including FCS octets), and had either a bad
         Frame Check Sequence (FCS) with an integral number
         of octets (FCS Error) or a bad FCS with a non-integral
         number of octets (Alignment Error).

         Note that this definition of jabber is different
         than the definition in IEEE-802.3 section 8.2.1.5
         (10BASE5) and section 10.3.1.4 (10BASE2).  These
         documents define jabber as the condition where any
         packet exceeds 20 ms.  The allowed range to detect
         jabber is between 20 ms and 150 ms."
        ::= { zxAnPonOltIfCurrPerfEntry 70}

    zxAnPonOltIfRxCorrFecCodes OBJECT-TYPE
        SYNTAX      Counter64
        MAX-ACCESS  read-only
        STATUS      current
        DESCRIPTION
            "The correct FEC codes received."
        ::= { zxAnPonOltIfCurrPerfEntry 71}

    zxAnPonOltIfRxErrFecCodes OBJECT-TYPE
        SYNTAX      Counter64
        MAX-ACCESS  read-only
        STATUS      current
        DESCRIPTION
            "The errored FEC codes received."
        ::= { zxAnPonOltIfCurrPerfEntry 72}
        
    zxAnPonOltIfCollisions OBJECT-TYPE
        SYNTAX      Counter64
        MAX-ACCESS  read-only
        STATUS      current
        DESCRIPTION
            "The best estimate of the total number of collisions
         on this olt interface."
        ::= { zxAnPonOltIfCurrPerfEntry 88}

    zxAnPonOltIfDropEvents OBJECT-TYPE
        SYNTAX      Counter64
        MAX-ACCESS  read-only
        STATUS      current
        DESCRIPTION
            "The total number of events in which packets
         were dropped by the probe due to lack of resources.
         Note that this number is not necessarily the number of
         packets dropped; it is just the number of times this
         condition has been detected."
        ::= { zxAnPonOltIfCurrPerfEntry 89}
        
	zxAnPonOltIfTxAvgOctetRate OBJECT-TYPE
        SYNTAX       Gauge32
        UNITS        "Bps"
        MAX-ACCESS   read-only
        STATUS       current
        DESCRIPTION
            "Transmitted average octet rate."
        ::= {zxAnPonOltIfCurrPerfEntry 90 }		
		
    zxAnPonOltIfCurrPerfCapability  OBJECT-TYPE 
         SYNTAX           BITS 
           {
                zxAnPonOltIfRxOctets(0),
                zxAnPonOltIfRxPkts(1),
                zxAnPonOltIfRxOctetRate(2),
                zxAnPonOltIfRxPktRate(3),
                zxAnPonOltIfRxOctetPeakRate(4),
                zxAnPonOltIfRxPktPeakRate(5),
                zxAnPonOltIfRxUcastPkts(6),
                zxAnPonOltIfRxNUcastPkts(7),
                zxAnPonOltIfRxMcastPkts(8),
                zxAnPonOltIfRxBcastPkts(9),
                zxAnPonOltIfRxDiscardPkts(10),
                zxAnPonOltIfRxErrPkts(11),
                zxAnPonOltIfRxPdr(12),
                zxAnPonOltIfRxPer(13),
                zxAnPonOltIfRxCrcAlignErrors(14),
                zxAnPonOltIfRxUndersizePkts(15),
                zxAnPonOltIfRxOversizePkts(16),
                zxAnPonOltIfRxPkts64Octets(17),
                zxAnPonOltIfRxPkts65To127Octets(18),
                zxAnPonOltIfRxPkts128To255Octets(19),
                zxAnPonOltIfRxPkts256To511Octets(20),
                zxAnPonOltIfRxPkts512To1023Oct(21),
                zxAnPonOltIfRxPkts1024To1518Oct(22),
                zxAnPonOltIfRxBwUtilization(23),
                zxAnPonOltIfRxAvgBwUtilization(24),
                zxAnPonOltIfRxFragments(25),
                zxAnPonOltIfRxJabbers(26),
                zxAnPonOltIfTxOctets(27),
                zxAnPonOltIfTxPkts(28),
                zxAnPonOltIfTxOctetRate(29),
                zxAnPonOltIfTxPktRate(30),
                zxAnPonOltIfTxOctetPeakRate(31),
                zxAnPonOltIfTxPktPeakRate(32),
                zxAnPonOltIfTxUcastPkts(33),
                zxAnPonOltIfTxNUcastPkts(34),
                zxAnPonOltIfTxMcastPkts(35),
                zxAnPonOltIfTxBcastPkts(36),
                zxAnPonOltIfTxDiscardPkts(37),
                zxAnPonOltIfTxErrPkts(38),
                zxAnPonOltIfTxPdr(39),
                zxAnPonOltIfTxPer(40),
                zxAnPonOltIfTxCrcAlignErrors(41),
                zxAnPonOltIfTxUndersizePkts(42),
                zxAnPonOltIfTxOversizePkts(43),
                zxAnPonOltIfTxPkts64Octets(44),
                zxAnPonOltIfTxPkts65To127Octets(45),
                zxAnPonOltIfTxPkts128To255Octets(46),
                zxAnPonOltIfTxPkts256To511Octets(47),
                zxAnPonOltIfTxPkts512To1023Oct(48),
                zxAnPonOltIfTxPkts1024To1518Oct(49),
                zxAnPonOltIfTxBwUtilization(50),
                zxAnPonOltIfTxAvgBwUtilization(51),
                zxAnPonOltIfTxFragments(52),
                zxAnPonOltIfTxJabbers(53),
                zxAnPonOltIfCollisions(54),
                zxAnPonOltIfDropEvents(55),
                zxAnPonOltIfRxCorrFecCodes(56),
                zxAnPonOltIfRxErrFecCodes (57), 
				zxAnPonOltIfRxAvgOctetRate(58),
				zxAnPonOltIfTxAvgOctetRate(59)
           }             
        MAX-ACCESS  read-only
        STATUS      current
        DESCRIPTION     
            "The support capability of PON OLT current performance statistics, 
            each bit from left to right represents the support of 
            performance statistic from top to bottom in this MIB table, 
            value 1 represents support and value 0 is not support."
        ::= { zxAnPonOltIfCurrPerfEntry 99 }   
                
    zxAnPonOltIfCurrPerfReset  OBJECT-TYPE
        SYNTAX       INTEGER{
                     reset(1)
                     }
        MAX-ACCESS   read-write
        STATUS       current
        DESCRIPTION
            "Clear OLT current statistics,read invalid.
            When get this variable, always return 1."
        ::= {zxAnPonOltIfCurrPerfEntry 100 }
        
--------------------------------------------------------------------------------
--  zxAnPonOltIfCurr15MinPerfTable
--------------------------------------------------------------------------------
    zxAnPonOltIfCurr15MinPerfTable OBJECT-TYPE
        SYNTAX         SEQUENCE OF ZxAnPonOltIfCurr15MinPerfEntry
        MAX-ACCESS     not-accessible
        STATUS         current
        DESCRIPTION
            "The current 15 minutes performance data table of PON interface.
             The 'IfType' of ifIndex supports 1(physical interface) 
             and 5(PON channel)."
        ::= { zxAnPonOltPerfObjects 3 }

    zxAnPonOltIfCurr15MinPerfEntry OBJECT-TYPE
        SYNTAX         ZxAnPonOltIfCurr15MinPerfEntry
        MAX-ACCESS     not-accessible
        STATUS         current
        DESCRIPTION
            "Entry of zxAnPonOltIfCurr15MinPerfTable."
        INDEX    { ifIndex }
        ::= { zxAnPonOltIfCurr15MinPerfTable 1}

    ZxAnPonOltIfCurr15MinPerfEntry ::=
        SEQUENCE{
                zxAnPonOltIfC15MTimeElapsed            Gauge32,
                zxAnPonOltIfC15MRxOctets               Counter64,
                zxAnPonOltIfC15MRxPkts                 Counter64,
                zxAnPonOltIfC15MRxUcastPkts            Counter64,
                zxAnPonOltIfC15MRxNUcastPkts           Counter64,
                zxAnPonOltIfC15MRxMcastPkts            Counter64,
                zxAnPonOltIfC15MRxBcastPkts            Counter64,
                zxAnPonOltIfC15MRxDiscardPkts          Counter64,
                zxAnPonOltIfC15MRxErrPkts              Counter64,
                zxAnPonOltIfC15MRxCrcAlignErrors       Counter64,
                zxAnPonOltIfC15MRxUndersizePkts        Counter64,
                zxAnPonOltIfC15MRxOversizePkts         Counter64,
                zxAnPonOltIfC15MRx64Octs               Counter64,
                zxAnPonOltIfC15MRx65To127Octs          Counter64,
                zxAnPonOltIfC15MRx128To255Octs         Counter64,
                zxAnPonOltIfC15MRx256To511Octs         Counter64,
                zxAnPonOltIfC15MRx512To1023Octs        Counter64,
                zxAnPonOltIfC15MRx1024To1518Octs       Counter64,
                zxAnPonOltIfC15MRxFragments            Counter64,
                zxAnPonOltIfC15MRxJabbers              Counter64,
                zxAnPonOltIfC15MTxOctets               Counter64,
                zxAnPonOltIfC15MTxPkts                 Counter64,
                zxAnPonOltIfC15MTxUcastPkts            Counter64,
                zxAnPonOltIfC15MTxNUcastPkts           Counter64,
                zxAnPonOltIfC15MTxMcastPkts            Counter64,
                zxAnPonOltIfC15MTxBcastPkts            Counter64,
                zxAnPonOltIfC15MTxDiscardPkts          Counter64,
                zxAnPonOltIfC15MTxErrPkts              Counter64,
                zxAnPonOltIfC15MTxCrcAlignErrors       Counter64,
                zxAnPonOltIfC15MTxUndersizePkts        Counter64,
                zxAnPonOltIfC15MTxOversizePkts         Counter64,
                zxAnPonOltIfC15MTxPkts64Octets         Counter64,
                zxAnPonOltIfC15MTx65To127Octs          Counter64,
                zxAnPonOltIfC15MTx128To255Octs         Counter64,
                zxAnPonOltIfC15MTx256To511Octs         Counter64,
                zxAnPonOltIfC15MTx512To1023Octs        Counter64,
                zxAnPonOltIfC15MTx1024To1518Octs       Counter64,
                zxAnPonOltIfC15MTxFragments            Counter64,
                zxAnPonOltIfC15MTxJabbers              Counter64,
                zxAnPonOltIfC15MRxCorrFecCodes         Counter64,
                zxAnPonOltIfC15MRxErrFecCodes          Counter64,
                zxAnPonOltIfC15MCollisions             Counter64,                
                zxAnPonOltIfC15MDropEvents             Counter64,
                zxAnPonOltIfPerfCapability             BITS,
                zxAnPonOltIfC15MPerfReset              INTEGER
                }

    zxAnPonOltIfC15MTimeElapsed  OBJECT-TYPE 
        SYNTAX      Gauge32(0..899)
        UNITS       "Seconds"
        MAX-ACCESS  read-only
        STATUS      current
        DESCRIPTION     
            "Number of seconds that have elapsed since the beginning
             of the current 15 minutes interval."
        ::= { zxAnPonOltIfCurr15MinPerfEntry 1 }
        
    zxAnPonOltIfC15MRxOctets OBJECT-TYPE
        SYNTAX       Counter64
        MAX-ACCESS   read-only
        STATUS       current
        DESCRIPTION
            "The current 15 minutes interval octets of data (including
         those in bad packets) received on the
         network (excluding framing bits but including
         FCS octets)."
        ::= {zxAnPonOltIfCurr15MinPerfEntry 2 }

    zxAnPonOltIfC15MRxPkts OBJECT-TYPE
        SYNTAX       Counter64
        MAX-ACCESS   read-only
        STATUS       current
        DESCRIPTION
            "The current 15 minutes interval packets (including bad packets,
         broadcast packets, and multicast packets) received."
        ::= {zxAnPonOltIfCurr15MinPerfEntry 3 }

    zxAnPonOltIfC15MRxUcastPkts OBJECT-TYPE
        SYNTAX       Counter64
        MAX-ACCESS   read-only
        STATUS       current
        DESCRIPTION
            "The current 15 minutes interval good packets received that were
         directed to a unicast address."
        ::= {zxAnPonOltIfCurr15MinPerfEntry 4 }

    zxAnPonOltIfC15MRxNUcastPkts OBJECT-TYPE
        SYNTAX       Counter64
        MAX-ACCESS   read-only
        STATUS       current
        DESCRIPTION
            "The current 15 minutes interval good packets received that were
         directed to a non-unicast address."
        ::= {zxAnPonOltIfCurr15MinPerfEntry 5 }

    zxAnPonOltIfC15MRxMcastPkts OBJECT-TYPE
        SYNTAX       Counter64
        MAX-ACCESS   read-only
        STATUS       current
        DESCRIPTION
            "The current 15 minutes interval good packets received that were
         directed to a multicast address."
        ::= {zxAnPonOltIfCurr15MinPerfEntry 6 }

    zxAnPonOltIfC15MRxBcastPkts OBJECT-TYPE
        SYNTAX       Counter64
        MAX-ACCESS   read-only
        STATUS       current
        DESCRIPTION
            "The current 15 minutes interval good packets received that were
         directed to the broadcast address.  Note that this
         does not include multicast packets."
        ::= {zxAnPonOltIfCurr15MinPerfEntry 7 }

    zxAnPonOltIfC15MRxDiscardPkts OBJECT-TYPE
        SYNTAX       Counter64
        MAX-ACCESS   read-only
        STATUS       current
        DESCRIPTION
            "The current 15 minutes interval discarded packets received."
        ::= {zxAnPonOltIfCurr15MinPerfEntry 8 }

    zxAnPonOltIfC15MRxErrPkts OBJECT-TYPE
        SYNTAX       Counter64
        MAX-ACCESS   read-only
        STATUS       current
        DESCRIPTION
            "The current 15 minutes interval error packets received."
        ::= {zxAnPonOltIfCurr15MinPerfEntry 9 }

    zxAnPonOltIfC15MRxCrcAlignErrors OBJECT-TYPE
        SYNTAX       Counter64
        MAX-ACCESS   read-only
        STATUS       current
        DESCRIPTION
            "The current 15 minutes interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOltIfCurr15MinPerfEntry 10 }

    zxAnPonOltIfC15MRxUndersizePkts OBJECT-TYPE
        SYNTAX       Counter64
        MAX-ACCESS   read-only
        STATUS       current
        DESCRIPTION
            "The current 15 minutes interval packets received that were
         less than 64 octets long (excluding framing bits,
         but including FCS octets) and were otherwise well
         formed."
        ::= {zxAnPonOltIfCurr15MinPerfEntry 11 }

    zxAnPonOltIfC15MRxOversizePkts OBJECT-TYPE
        SYNTAX       Counter64
        MAX-ACCESS   read-only
        STATUS       current
        DESCRIPTION
            "The current 15 minutes interval packets received that were
         longer than 1518 octets (excluding framing bits,
         but including FCS octets) and were otherwise
         well formed."
        ::= {zxAnPonOltIfCurr15MinPerfEntry 12 }

    zxAnPonOltIfC15MRx64Octs      OBJECT-TYPE
        SYNTAX       Counter64
        MAX-ACCESS   read-only
        STATUS       current
        DESCRIPTION
            "The current 15 minutes interval packets (including bad
         packets) received that were 64 octets in length
         (excluding framing bits but including FCS octets)."
        ::= {zxAnPonOltIfCurr15MinPerfEntry 13 }

    zxAnPonOltIfC15MRx65To127Octs OBJECT-TYPE
        SYNTAX       Counter64
        MAX-ACCESS   read-only
        STATUS       current
        DESCRIPTION
            "The current 15 minutes interval packets (including bad
         packets) received that were between
         65 and 127 octets in length inclusive
         (excluding framing bits but including FCS octets)."
        ::= {zxAnPonOltIfCurr15MinPerfEntry 14 }

    zxAnPonOltIfC15MRx128To255Octs OBJECT-TYPE
        SYNTAX       Counter64
        MAX-ACCESS   read-only
        STATUS       current
        DESCRIPTION
            "The current 15 minutes interval packets (including bad
         packets) received that were between
         128 and 255 octets in length inclusive
         (excluding framing bits but including FCS octets)."
        ::= {zxAnPonOltIfCurr15MinPerfEntry 15 }

    zxAnPonOltIfC15MRx256To511Octs OBJECT-TYPE
        SYNTAX       Counter64
        MAX-ACCESS   read-only
        STATUS       current
        DESCRIPTION
            "The current 15 minutes interval packets (including bad
         packets) received that were between
         256 and 511 octets in length inclusive
         (excluding framing bits but including FCS octets)."
        ::= {zxAnPonOltIfCurr15MinPerfEntry 16 }

    zxAnPonOltIfC15MRx512To1023Octs OBJECT-TYPE
        SYNTAX       Counter64
        MAX-ACCESS   read-only
        STATUS       current
        DESCRIPTION
            "The current 15 minutes interval packets (including bad
         packets) received that were between
         512 and 1023 octets in length inclusive
         (excluding framing bits but including FCS octets)."
        ::= {zxAnPonOltIfCurr15MinPerfEntry 17 }

    zxAnPonOltIfC15MRx1024To1518Octs OBJECT-TYPE
        SYNTAX       Counter64
        MAX-ACCESS   read-only
        STATUS       current
        DESCRIPTION
            "The current 15 minutes interval packets (including bad
         packets) received that were between
         1024 and 1518 octets in length inclusive
         (excluding framing bits but including FCS octets)."
        ::= {zxAnPonOltIfCurr15MinPerfEntry 18 }
        
    zxAnPonOltIfC15MRxFragments  OBJECT-TYPE
        SYNTAX      Counter64
        MAX-ACCESS  read-only
        STATUS      current
        DESCRIPTION
            "The current 15 minutes interval packets received that were less 
            than 64 octets in length (excluding framing bits but including
         FCS octets) and had either a bad Frame Check Sequence
         (FCS) with an integral number of octets (FCS Error) or a
         bad FCS with a non-integral number of octets (Alignment
         Error)."
        ::= { zxAnPonOltIfCurr15MinPerfEntry 19}
        
    zxAnPonOltIfC15MRxJabbers OBJECT-TYPE
        SYNTAX      Counter64
        MAX-ACCESS  read-only
        STATUS      current
        DESCRIPTION
            "The current 15 minutes interval packets received that were
         longer than 1518 octets (excluding framing bits,
         but including FCS octets), and had either a bad
         Frame Check Sequence (FCS) with an integral number
         of octets (FCS Error) or a bad FCS with a non-integral
         number of octets (Alignment Error)."
        ::= { zxAnPonOltIfCurr15MinPerfEntry 20}

    zxAnPonOltIfC15MTxOctets OBJECT-TYPE
        SYNTAX       Counter64
        MAX-ACCESS   read-only
        STATUS       current
        DESCRIPTION
            "The current 15 minutes interval octets of data (including
         those in bad packets) sent on the
         network (excluding framing bits but including
         FCS octets)."
        ::= {zxAnPonOltIfCurr15MinPerfEntry 36 }

    zxAnPonOltIfC15MTxPkts OBJECT-TYPE
        SYNTAX       Counter64
        MAX-ACCESS   read-only
        STATUS       current
        DESCRIPTION
            "The current 15 minutes interval packets (including bad packets,
         broadcast packets, and multicast packets) transmitted."
        ::= {zxAnPonOltIfCurr15MinPerfEntry 37 }

    zxAnPonOltIfC15MTxUcastPkts OBJECT-TYPE
        SYNTAX       Counter64
        MAX-ACCESS   read-only
        STATUS       current
        DESCRIPTION
            "The current 15 minutes interval good packets transmitted that were
         directed to a unicast address."
        ::= {zxAnPonOltIfCurr15MinPerfEntry 38 }

    zxAnPonOltIfC15MTxNUcastPkts OBJECT-TYPE
        SYNTAX       Counter64
        MAX-ACCESS   read-only
        STATUS       current
        DESCRIPTION
            "The current 15 minutes interval good packets transmitted that were
         directed to a non-unicast address."
        ::= {zxAnPonOltIfCurr15MinPerfEntry 39 }

    zxAnPonOltIfC15MTxMcastPkts OBJECT-TYPE
        SYNTAX       Counter64
        MAX-ACCESS   read-only
        STATUS       current
        DESCRIPTION
            "The current 15 minutes interval good packets transmitted that were
         directed to a multicast address."
        ::= {zxAnPonOltIfCurr15MinPerfEntry 40 }

    zxAnPonOltIfC15MTxBcastPkts OBJECT-TYPE
        SYNTAX       Counter64
        MAX-ACCESS   read-only
        STATUS       current
        DESCRIPTION
            "The current 15 minutes interval good packets transmitted that were
         directed to the broadcast address.  Note that this does not include 
         multicast packets."
        ::= {zxAnPonOltIfCurr15MinPerfEntry 41 }

    zxAnPonOltIfC15MTxDiscardPkts OBJECT-TYPE
        SYNTAX       Counter64
        MAX-ACCESS   read-only
        STATUS       current
        DESCRIPTION
            "The current 15 minutes interval discarded packets transmitted."
        ::= {zxAnPonOltIfCurr15MinPerfEntry 42 }

    zxAnPonOltIfC15MTxErrPkts OBJECT-TYPE
        SYNTAX       Counter64
        MAX-ACCESS   read-only
        STATUS       current
        DESCRIPTION
            "The current 15 minutes interval error packets transmitted."
        ::= {zxAnPonOltIfCurr15MinPerfEntry 43 }
        
    zxAnPonOltIfC15MTxCrcAlignErrors OBJECT-TYPE
        SYNTAX      Counter64
        MAX-ACCESS  read-only
        STATUS      current
        DESCRIPTION
            "The current 15 minutes interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOltIfCurr15MinPerfEntry 44}

    zxAnPonOltIfC15MTxUndersizePkts OBJECT-TYPE
        SYNTAX      Counter64
        MAX-ACCESS  read-only
        STATUS      current
        DESCRIPTION
            "The current 15 minutes interval packets transmitted that were
         less than 64 octets long (excluding framing bits,but including
         FCS octets) and were otherwise well
         formed."
        ::= { zxAnPonOltIfCurr15MinPerfEntry 45}
            
    zxAnPonOltIfC15MTxOversizePkts OBJECT-TYPE
        SYNTAX      Counter64
        MAX-ACCESS  read-only
        STATUS      current
        DESCRIPTION
            "The current 15 minutes interval packets transmitted that were
         longer than 1518 octets (excluding framing bits, but including FCS
         octets) and were otherwise well formed."
        ::= { zxAnPonOltIfCurr15MinPerfEntry 46}
    
    zxAnPonOltIfC15MTxPkts64Octets OBJECT-TYPE
        SYNTAX       Counter64
        MAX-ACCESS   read-only
        STATUS       current
        DESCRIPTION
            "The current 15 minutes interval packets (including bad
         packets) transmitted that were 64 octets in length
         (excluding framing bits but including FCS octets)."
        ::= {zxAnPonOltIfCurr15MinPerfEntry 47 }

    zxAnPonOltIfC15MTx65To127Octs OBJECT-TYPE
        SYNTAX       Counter64
        MAX-ACCESS   read-only
        STATUS       current
        DESCRIPTION
            "The current 15 minutes interval packets (including bad
         packets) transmitted that were between 65 and 127 octets in
         length inclusive (excluding framing bits but including FCS octets)."
        ::= {zxAnPonOltIfCurr15MinPerfEntry 48 }

    zxAnPonOltIfC15MTx128To255Octs OBJECT-TYPE
        SYNTAX       Counter64
        MAX-ACCESS   read-only
        STATUS       current
        DESCRIPTION
            "The current 15 minutes interval packets (including bad
         packets) transmitted that were between
         128 and 255 octets in length inclusive
         (excluding framing bits but including FCS octets)."
        ::= {zxAnPonOltIfCurr15MinPerfEntry 49}

    zxAnPonOltIfC15MTx256To511Octs OBJECT-TYPE
        SYNTAX       Counter64
        MAX-ACCESS   read-only
        STATUS       current
        DESCRIPTION
            "The current 15 minutes interval packets (including bad
         packets) transmitted that were between
         256 and 511 octets in length inclusive
         (excluding framing bits but including FCS octets)."
        ::= {zxAnPonOltIfCurr15MinPerfEntry 50 }

    zxAnPonOltIfC15MTx512To1023Octs OBJECT-TYPE
        SYNTAX       Counter64
        MAX-ACCESS   read-only
        STATUS       current
        DESCRIPTION
            "The current 15 minutes interval packets (including bad
         packets) transmitted that were between
         512 and 1023 octets in length inclusive
         (excluding framing bits but including FCS octets)."
        ::= {zxAnPonOltIfCurr15MinPerfEntry 51 }

    zxAnPonOltIfC15MTx1024To1518Octs OBJECT-TYPE
        SYNTAX       Counter64
        MAX-ACCESS   read-only
        STATUS       current
        DESCRIPTION
            "The current 15 minutes interval packets (including bad
         packets) transmitted that were between
         1024 and 1518 octets in length inclusive
         (excluding framing bits but including FCS octets)."
        ::= {zxAnPonOltIfCurr15MinPerfEntry 52 }
        
    zxAnPonOltIfC15MTxFragments  OBJECT-TYPE
        SYNTAX      Counter64
        MAX-ACCESS  read-only
        STATUS      current
        DESCRIPTION
            "The current 15 minutes interval packets transmitted that were less 
            than 64 octets in length (excluding framing bits but including
         FCS octets) and had either a bad Frame Check Sequence
         (FCS) with an integral number of octets (FCS Error) or a
         bad FCS with a non-integral number of octets (Alignment
         Error)."
        ::= { zxAnPonOltIfCurr15MinPerfEntry 53}
        
    zxAnPonOltIfC15MTxJabbers OBJECT-TYPE
        SYNTAX      Counter64
        MAX-ACCESS  read-only
        STATUS      current
        DESCRIPTION
            "The current 15 minutes interval packets transmitted that were
         longer than 1518 octets (excluding framing bits,
         but including FCS octets), and had either a bad
         Frame Check Sequence (FCS) with an integral number
         of octets (FCS Error) or a bad FCS with a non-integral
         number of octets (Alignment Error)."
        ::= { zxAnPonOltIfCurr15MinPerfEntry 54}
        
    zxAnPonOltIfC15MRxCorrFecCodes OBJECT-TYPE
        SYNTAX      Counter64
        MAX-ACCESS  read-only
        STATUS      current
        DESCRIPTION
            "The current 15 minutes interval correct FEC codes received."
        ::= { zxAnPonOltIfCurr15MinPerfEntry 55}

    zxAnPonOltIfC15MRxErrFecCodes OBJECT-TYPE
        SYNTAX      Counter64
        MAX-ACCESS  read-only
        STATUS      current
        DESCRIPTION
            "The current 15 minutes interval errored FEC codes received."
        ::= { zxAnPonOltIfCurr15MinPerfEntry 56}        
        
    zxAnPonOltIfC15MCollisions OBJECT-TYPE
        SYNTAX      Counter64
        MAX-ACCESS  read-only
        STATUS      current
        DESCRIPTION
            "The current 15 minutes interval best estimate of collisions
         on this olt interface."
        ::= { zxAnPonOltIfCurr15MinPerfEntry 70}

    zxAnPonOltIfC15MDropEvents OBJECT-TYPE
        SYNTAX      Counter64
        MAX-ACCESS  read-only
        STATUS      current
        DESCRIPTION
            "The current 15 minutes interval events in which packets
         were dropped by the probe due to lack of resources."
        ::= { zxAnPonOltIfCurr15MinPerfEntry 71}    

    zxAnPonOltIfPerfCapability  OBJECT-TYPE 
         SYNTAX           BITS 
           {
                zxAnPonOltIfC15MRxOctets(0),
                zxAnPonOltIfC15MRxPkts(1),
                zxAnPonOltIfC15MRxUcastPkts(2),
                zxAnPonOltIfC15MRxNUcastPkts(3),
                zxAnPonOltIfC15MRxMcastPkts(4),
                zxAnPonOltIfC15MRxBcastPkts(5),
                zxAnPonOltIfC15MRxDiscardPkts(6),
                zxAnPonOltIfC15MRxErrPkts(7),
                zxAnPonOltIfC15MRxCrcAlignErrors(8),
                zxAnPonOltIfC15MRxUndersizePkts(9),
                zxAnPonOltIfC15MRxOversizePkts(10),
                zxAnPonOltIfC15MRx64Octs(11),
                zxAnPonOltIfC15MRx65To127Octs(12),
                zxAnPonOltIfC15MRx128To255Octs(13),
                zxAnPonOltIfC15MRx256To511Octs(14),
                zxAnPonOltIfC15MRx512To1023Octs(15),
                zxAnPonOltIfC15MRx1024To1518Octs(16),
                zxAnPonOltIfC15MRxFragments(17),
                zxAnPonOltIfC15MRxJabbers(18),
                zxAnPonOltIfC15MTxOctets(19),
                zxAnPonOltIfC15MTxPkts(20),
                zxAnPonOltIfC15MTxUcastPkts(21),
                zxAnPonOltIfC15MTxNUcastPkts(22),
                zxAnPonOltIfC15MTxMcastPkts(23),
                zxAnPonOltIfC15MTxBcastPkts(24),
                zxAnPonOltIfC15MTxDiscardPkts(25),
                zxAnPonOltIfC15MTxErrPkts(26),
                zxAnPonOltIfC15MTxCrcAlignErrors(27),
                zxAnPonOltIfC15MTxUndersizePkts(28),
                zxAnPonOltIfC15MTxOversizePkts(29),
                zxAnPonOltIfC15MTxPkts64Octets(30),
                zxAnPonOltIfC15MTx65To127Octs(31),
                zxAnPonOltIfC15MTx128To255Octs(32),
                zxAnPonOltIfC15MTx256To511Octs(33),
                zxAnPonOltIfC15MTx512To1023Octs(34),
                zxAnPonOltIfC15MTx1024To1518Octs(35),
                zxAnPonOltIfC15MTxFragments(36),
                zxAnPonOltIfC15MTxJabbers(37),
                zxAnPonOltIfC15MCollisions(38),
                zxAnPonOltIfC15MDropEvents(39),
                zxAnPonOltIfC15MRxCorrFecCodes(40),
                zxAnPonOltIfC15MRxErrFecCodes(41)
            }             
        MAX-ACCESS  read-only
        STATUS      current
        DESCRIPTION     
            "The support capability of PON OLT interface C15M, CMin, C1D, H15M, 
            HMin and H1D performance statistics, each bit from left to right 
            represents the support of performance statistic from top to 
            bottom in this MIB table, value 1 represents support and 
            value 0 is not support."
        ::= { zxAnPonOltIfCurr15MinPerfEntry 99 }   
                
    zxAnPonOltIfC15MPerfReset  OBJECT-TYPE
        SYNTAX       INTEGER{
                     reset(1)
                     }
        MAX-ACCESS   read-write
        STATUS       current
        DESCRIPTION
            "Clear all the current 15-minutes performance variables.
            When get this variable, always return 1."
        ::= {zxAnPonOltIfCurr15MinPerfEntry 100 }

--------------------------------------------------------------------------------
--  zxAnPonOltIfCurrMinPerfTable
--------------------------------------------------------------------------------
    zxAnPonOltIfCurrMinPerfTable OBJECT-TYPE
        SYNTAX         SEQUENCE OF ZxAnPonOltIfCurrMinPerfEntry
        MAX-ACCESS     not-accessible
        STATUS         current
        DESCRIPTION
            "The minutes interval performance data table of PON OLT.
             The 'IfType' of ifIndex supports 1(physical interface) 
             and 5(PON channel)."
        ::= { zxAnPonOltPerfObjects 10 }

    zxAnPonOltIfCurrMinPerfEntry OBJECT-TYPE
        SYNTAX         ZxAnPonOltIfCurrMinPerfEntry
        MAX-ACCESS     not-accessible
        STATUS         current
        DESCRIPTION
            "An entry in the OLT minutes interval performance data table."
        INDEX    { ifIndex }
        ::= { zxAnPonOltIfCurrMinPerfTable 1}

    ZxAnPonOltIfCurrMinPerfEntry ::=
        SEQUENCE {
            zxAnPonOltIfCMinTimeElapsed            HCPerfTimeElapsed,
            zxAnPonOltIfCMinRxOctets               Counter64,
            zxAnPonOltIfCMinRxPkts                 Counter64,
            zxAnPonOltIfCMinRxUcastPkts            Counter64,
            zxAnPonOltIfCMinRxNUcastPkts           Counter64,
            zxAnPonOltIfCMinRxMcastPkts            Counter64,
            zxAnPonOltIfCMinRxBcastPkts            Counter64,
            zxAnPonOltIfCMinRxDiscardPkts          Counter64,
            zxAnPonOltIfCMinRxErrPkts              Counter64,
            zxAnPonOltIfCMinRxCrcAlignErrors       Counter64,
            zxAnPonOltIfCMinRxUndersizePkts        Counter64,
            zxAnPonOltIfCMinRxOversizePkts         Counter64,
            zxAnPonOltIfCMinRx64Octs               Counter64,
            zxAnPonOltIfCMinRx65To127Octs          Counter64,
            zxAnPonOltIfCMinRx128To255Octs         Counter64,
            zxAnPonOltIfCMinRx256To511Octs         Counter64,
            zxAnPonOltIfCMinRx512To1023Octs        Counter64,
            zxAnPonOltIfCMinRx1024To1518Octs       Counter64,
            zxAnPonOltIfCMinRxFragments            Counter64,
            zxAnPonOltIfCMinRxJabbers              Counter64,
            zxAnPonOltIfCMinTxOctets               Counter64,
            zxAnPonOltIfCMinTxPkts                 Counter64,
            zxAnPonOltIfCMinTxUcastPkts            Counter64,
            zxAnPonOltIfCMinTxNUcastPkts           Counter64,
            zxAnPonOltIfCMinTxMcastPkts            Counter64,
            zxAnPonOltIfCMinTxBcastPkts            Counter64,
            zxAnPonOltIfCMinTxDiscardPkts          Counter64,
            zxAnPonOltIfCMinTxErrPkts              Counter64,
            zxAnPonOltIfCMinTxCrcAlignErrors       Counter64,
            zxAnPonOltIfCMinTxUndersizePkts        Counter64,
            zxAnPonOltIfCMinTxOversizePkts         Counter64,
            zxAnPonOltIfCMinTxPkts64Octets         Counter64,
            zxAnPonOltIfCMinTx65To127Octs          Counter64,
            zxAnPonOltIfCMinTx128To255Octs         Counter64,
            zxAnPonOltIfCMinTx256To511Octs         Counter64,
            zxAnPonOltIfCMinTx512To1023Octs        Counter64,
            zxAnPonOltIfCMinTx1024To1518Octs       Counter64,
            zxAnPonOltIfCMinTxFragments            Counter64,
            zxAnPonOltIfCMinTxJabbers              Counter64,
            zxAnPonOltIfCMinRxCorrFecCodes         Counter64,
            zxAnPonOltIfCMinRxErrFecCodes          Counter64,
            zxAnPonOltIfCMinCollisions             Counter64,
            zxAnPonOltIfCMinDropEvents             Counter64,
            zxAnPonOltIfCMinPerfReset              INTEGER
            }

    zxAnPonOltIfCMinTimeElapsed  OBJECT-TYPE 
        SYNTAX      HCPerfTimeElapsed
        UNITS       "Seconds"
        MAX-ACCESS  read-only
        STATUS      current
        DESCRIPTION     
            "Number of seconds that have elapsed since the beginning
             of the current minutes interval."
        ::= { zxAnPonOltIfCurrMinPerfEntry 1 }
        
    zxAnPonOltIfCMinRxOctets OBJECT-TYPE
        SYNTAX       Counter64
        MAX-ACCESS   read-only
        STATUS       current
        DESCRIPTION
            "The current minutes interval octets of data (including
            those in bad packets) received on the
            network (excluding framing bits but including
            FCS octets)."
        ::= {zxAnPonOltIfCurrMinPerfEntry 2 }

    zxAnPonOltIfCMinRxPkts OBJECT-TYPE
        SYNTAX       Counter64
        MAX-ACCESS   read-only
        STATUS       current
        DESCRIPTION
            "The current minutes interval packets (including bad packets,
            broadcast packets, and multicast packets) received."
        ::= {zxAnPonOltIfCurrMinPerfEntry 3 }

    zxAnPonOltIfCMinRxUcastPkts OBJECT-TYPE
        SYNTAX       Counter64
        MAX-ACCESS   read-only
        STATUS       current
        DESCRIPTION
            "The current minutes interval good packets received that were
            directed to a unicast address."
        ::= {zxAnPonOltIfCurrMinPerfEntry 4 }

    zxAnPonOltIfCMinRxNUcastPkts OBJECT-TYPE
        SYNTAX       Counter64
        MAX-ACCESS   read-only
        STATUS       current
        DESCRIPTION
            "The current minutes interval good packets received that were
            directed to a non-unicast address."
        ::= {zxAnPonOltIfCurrMinPerfEntry 5 }

    zxAnPonOltIfCMinRxMcastPkts OBJECT-TYPE
        SYNTAX       Counter64
        MAX-ACCESS   read-only
        STATUS       current
        DESCRIPTION
            "The current minutes interval good packets received that were
            directed to a multicast address."
        ::= {zxAnPonOltIfCurrMinPerfEntry 6 }

    zxAnPonOltIfCMinRxBcastPkts OBJECT-TYPE
        SYNTAX       Counter64
        MAX-ACCESS   read-only
        STATUS       current
        DESCRIPTION
            "The current minutes interval good packets received that were
            directed to the broadcast address.  Note that this
            does not include multicast packets."
        ::= {zxAnPonOltIfCurrMinPerfEntry 7 }

    zxAnPonOltIfCMinRxDiscardPkts OBJECT-TYPE
        SYNTAX       Counter64
        MAX-ACCESS   read-only
        STATUS       current
        DESCRIPTION
            "The current minutes interval discarded packets received."
        ::= {zxAnPonOltIfCurrMinPerfEntry 8 }

    zxAnPonOltIfCMinRxErrPkts OBJECT-TYPE
        SYNTAX       Counter64
        MAX-ACCESS   read-only
        STATUS       current
        DESCRIPTION
            "The current minutes interval error packets received."
        ::= {zxAnPonOltIfCurrMinPerfEntry 9 }

    zxAnPonOltIfCMinRxCrcAlignErrors OBJECT-TYPE
        SYNTAX       Counter64
        MAX-ACCESS   read-only
        STATUS       current
        DESCRIPTION
            "The current minutes interval packets received that
            had a length (excluding framing bits, but
            including FCS octets) of between 64 and 1518
            octets, inclusive, but had either a bad
            Frame Check Sequence (FCS) with an integral
            number of octets (FCS Error) or a bad FCS with
            a non-integral number of octets (Alignment Error)."
        ::= {zxAnPonOltIfCurrMinPerfEntry 10 }

    zxAnPonOltIfCMinRxUndersizePkts OBJECT-TYPE
        SYNTAX       Counter64
        MAX-ACCESS   read-only
        STATUS       current
        DESCRIPTION
            "The current minutes interval packets received that were
            less than 64 octets long (excluding framing bits,
            but including FCS octets) and were otherwise well
            formed."
        ::= {zxAnPonOltIfCurrMinPerfEntry 11 }

    zxAnPonOltIfCMinRxOversizePkts OBJECT-TYPE
        SYNTAX       Counter64
        MAX-ACCESS   read-only
        STATUS       current
        DESCRIPTION
            "The current minutes interval packets received that were
            longer than 1518 octets (excluding framing bits,
            but including FCS octets) and were otherwise
            well formed."
        ::= {zxAnPonOltIfCurrMinPerfEntry 12 }

    zxAnPonOltIfCMinRx64Octs      OBJECT-TYPE
        SYNTAX       Counter64
        MAX-ACCESS   read-only
        STATUS       current
        DESCRIPTION
            "The current minutes interval packets (including bad
            packets) received that were 64 octets in length
            (excluding framing bits but including FCS octets)."
        ::= {zxAnPonOltIfCurrMinPerfEntry 13 }

    zxAnPonOltIfCMinRx65To127Octs OBJECT-TYPE
        SYNTAX       Counter64
        MAX-ACCESS   read-only
        STATUS       current
        DESCRIPTION
            "The current minutes interval packets (including bad
            packets) received that were between
            65 and 127 octets in length inclusive
            (excluding framing bits but including FCS octets)."
        ::= {zxAnPonOltIfCurrMinPerfEntry 14 }

    zxAnPonOltIfCMinRx128To255Octs OBJECT-TYPE
        SYNTAX       Counter64
        MAX-ACCESS   read-only
        STATUS       current
        DESCRIPTION
            "The current minutes interval packets (including bad
            packets) received that were between
            128 and 255 octets in length inclusive
            (excluding framing bits but including FCS octets)."
        ::= {zxAnPonOltIfCurrMinPerfEntry 15 }

    zxAnPonOltIfCMinRx256To511Octs OBJECT-TYPE
        SYNTAX       Counter64
        MAX-ACCESS   read-only
        STATUS       current
        DESCRIPTION
            "The current minutes interval packets (including bad
            packets) received that were between
            256 and 511 octets in length inclusive
            (excluding framing bits but including FCS octets)."
        ::= {zxAnPonOltIfCurrMinPerfEntry 16 }

    zxAnPonOltIfCMinRx512To1023Octs OBJECT-TYPE
        SYNTAX       Counter64
        MAX-ACCESS   read-only
        STATUS       current
        DESCRIPTION
            "The current minutes interval packets (including bad
            packets) received that were between
            512 and 1023 octets in length inclusive
            (excluding framing bits but including FCS octets)."
        ::= {zxAnPonOltIfCurrMinPerfEntry 17 }

    zxAnPonOltIfCMinRx1024To1518Octs OBJECT-TYPE
        SYNTAX       Counter64
        MAX-ACCESS   read-only
        STATUS       current
        DESCRIPTION
            "The current minutes interval packets (including bad
            packets) received that were between
            1024 and 1518 octets in length inclusive
            (excluding framing bits but including FCS octets)."
        ::= {zxAnPonOltIfCurrMinPerfEntry 18 }
        
    zxAnPonOltIfCMinRxFragments  OBJECT-TYPE
        SYNTAX      Counter64
        MAX-ACCESS  read-only
        STATUS      current
        DESCRIPTION
            "The current minutes interval packets received that were less 
            than 64 octets in length (excluding framing bits but including
            FCS octets) and had either a bad Frame Check Sequence
            (FCS) with an integral number of octets (FCS Error) or a
            bad FCS with a non-integral number of octets (Alignment
            Error)."
        ::= { zxAnPonOltIfCurrMinPerfEntry 19}
        
    zxAnPonOltIfCMinRxJabbers OBJECT-TYPE
        SYNTAX      Counter64
        MAX-ACCESS  read-only
        STATUS      current
        DESCRIPTION
            "The current minutes interval packets received that were
            longer than 1518 octets (excluding framing bits,
            but including FCS octets), and had either a bad
            Frame Check Sequence (FCS) with an integral number
            of octets (FCS Error) or a bad FCS with a non-integral
            number of octets (Alignment Error)."
        ::= { zxAnPonOltIfCurrMinPerfEntry 20}

    zxAnPonOltIfCMinTxOctets OBJECT-TYPE
        SYNTAX       Counter64
        MAX-ACCESS   read-only
        STATUS       current
        DESCRIPTION
            "The current minutes interval octets of data (including
            those in bad packets) sent on the
            network (excluding framing bits but including
            FCS octets)."
        ::= {zxAnPonOltIfCurrMinPerfEntry 36 }

    zxAnPonOltIfCMinTxPkts OBJECT-TYPE
        SYNTAX       Counter64
        MAX-ACCESS   read-only
        STATUS       current
        DESCRIPTION
            "The current minutes interval packets (including bad packets,
            broadcast packets, and multicast packets) transmitted."
        ::= {zxAnPonOltIfCurrMinPerfEntry 37 }

    zxAnPonOltIfCMinTxUcastPkts OBJECT-TYPE
        SYNTAX       Counter64
        MAX-ACCESS   read-only
        STATUS       current
        DESCRIPTION
            "The current minutes interval good packets transmitted that were
            directed to a unicast address."
        ::= {zxAnPonOltIfCurrMinPerfEntry 38 }

    zxAnPonOltIfCMinTxNUcastPkts OBJECT-TYPE
        SYNTAX       Counter64
        MAX-ACCESS   read-only
        STATUS       current
        DESCRIPTION
            "The current minutes interval good packets transmitted that were
            directed to a non-unicast address."
        ::= {zxAnPonOltIfCurrMinPerfEntry 39 }

    zxAnPonOltIfCMinTxMcastPkts OBJECT-TYPE
        SYNTAX       Counter64
        MAX-ACCESS   read-only
        STATUS       current
        DESCRIPTION
            "The current minutes interval good packets transmitted that were
            directed to a multicast address."
        ::= {zxAnPonOltIfCurrMinPerfEntry 40 }

    zxAnPonOltIfCMinTxBcastPkts OBJECT-TYPE
        SYNTAX       Counter64
        MAX-ACCESS   read-only
        STATUS       current
        DESCRIPTION
            "The current minutes interval good packets transmitted that were
            directed to the broadcast address.  Note that this does not include 
            multicast packets."
        ::= {zxAnPonOltIfCurrMinPerfEntry 41 }

    zxAnPonOltIfCMinTxDiscardPkts OBJECT-TYPE
        SYNTAX       Counter64
        MAX-ACCESS   read-only
        STATUS       current
        DESCRIPTION
            "The current minutes interval discarded packets transmitted."
        ::= {zxAnPonOltIfCurrMinPerfEntry 42 }

    zxAnPonOltIfCMinTxErrPkts OBJECT-TYPE
        SYNTAX       Counter64
        MAX-ACCESS   read-only
        STATUS       current
        DESCRIPTION
            "The current minutes interval error packets transmitted."
        ::= {zxAnPonOltIfCurrMinPerfEntry 43 }
        
    zxAnPonOltIfCMinTxCrcAlignErrors OBJECT-TYPE
        SYNTAX      Counter64
        MAX-ACCESS  read-only
        STATUS      current
        DESCRIPTION
            "The current minutes interval packets transmitted that
            had a length (excluding framing bits, but including FCS octets)
            of between 64 and 1518 octets, inclusive, but had either a bad
            Frame Check Sequence (FCS) with an integral number of octets 
            (FCS Error) or a bad FCS with a non-integral number of octets
            (Alignment Error)."
        ::= { zxAnPonOltIfCurrMinPerfEntry 44}

    zxAnPonOltIfCMinTxUndersizePkts OBJECT-TYPE
        SYNTAX      Counter64
        MAX-ACCESS  read-only
        STATUS      current
        DESCRIPTION
            "The current minutes interval packets transmitted that were
            less than 64 octets long (excluding framing bits,but including
            FCS octets) and were otherwise well
            formed."
        ::= { zxAnPonOltIfCurrMinPerfEntry 45}
            
    zxAnPonOltIfCMinTxOversizePkts OBJECT-TYPE
        SYNTAX      Counter64
        MAX-ACCESS  read-only
        STATUS      current
        DESCRIPTION
            "The current minutes interval packets transmitted that were
            longer than 1518 octets (excluding framing bits, but including FCS
            octets) and were otherwise well formed."
        ::= { zxAnPonOltIfCurrMinPerfEntry 46}
    
    zxAnPonOltIfCMinTxPkts64Octets OBJECT-TYPE
        SYNTAX       Counter64
        MAX-ACCESS   read-only
        STATUS       current
        DESCRIPTION
            "The current minutes interval packets (including bad
            packets) transmitted that were 64 octets in length
            (excluding framing bits but including FCS octets)."
        ::= {zxAnPonOltIfCurrMinPerfEntry 47 }

    zxAnPonOltIfCMinTx65To127Octs OBJECT-TYPE
        SYNTAX       Counter64
        MAX-ACCESS   read-only
        STATUS       current
        DESCRIPTION
            "The current minutes interval packets (including bad
            packets) transmitted that were between 65 and 127 octets in
            length inclusive (excluding framing bits but including FCS octets)."
        ::= {zxAnPonOltIfCurrMinPerfEntry 48 }

    zxAnPonOltIfCMinTx128To255Octs OBJECT-TYPE
        SYNTAX       Counter64
        MAX-ACCESS   read-only
        STATUS       current
        DESCRIPTION
            "The current minutes interval packets (including bad
            packets) transmitted that were between
            128 and 255 octets in length inclusive
            (excluding framing bits but including FCS octets)."
        ::= {zxAnPonOltIfCurrMinPerfEntry 49}

    zxAnPonOltIfCMinTx256To511Octs OBJECT-TYPE
        SYNTAX       Counter64
        MAX-ACCESS   read-only
        STATUS       current
        DESCRIPTION
            "The current minutes interval packets (including bad
            packets) transmitted that were between
            256 and 511 octets in length inclusive
            (excluding framing bits but including FCS octets)."
        ::= {zxAnPonOltIfCurrMinPerfEntry 50 }

    zxAnPonOltIfCMinTx512To1023Octs OBJECT-TYPE
        SYNTAX       Counter64
        MAX-ACCESS   read-only
        STATUS       current
        DESCRIPTION
            "The current minutes interval packets (including bad
            packets) transmitted that were between
            512 and 1023 octets in length inclusive
            (excluding framing bits but including FCS octets)."
        ::= {zxAnPonOltIfCurrMinPerfEntry 51 }

    zxAnPonOltIfCMinTx1024To1518Octs OBJECT-TYPE
        SYNTAX       Counter64
        MAX-ACCESS   read-only
        STATUS       current
        DESCRIPTION
            "The current minutes interval packets (including bad
            packets) transmitted that were between
            1024 and 1518 octets in length inclusive
            (excluding framing bits but including FCS octets)."
        ::= {zxAnPonOltIfCurrMinPerfEntry 52 }
        
    zxAnPonOltIfCMinTxFragments  OBJECT-TYPE
        SYNTAX      Counter64
        MAX-ACCESS  read-only
        STATUS      current
        DESCRIPTION
            "The current minutes interval packets transmitted that were less 
            than 64 octets in length (excluding framing bits but including
            FCS octets) and had either a bad Frame Check Sequence
            (FCS) with an integral number of octets (FCS Error) or a
            bad FCS with a non-integral number of octets (Alignment
            Error)."
        ::= { zxAnPonOltIfCurrMinPerfEntry 53}
        
    zxAnPonOltIfCMinTxJabbers OBJECT-TYPE
        SYNTAX      Counter64
        MAX-ACCESS  read-only
        STATUS      current
        DESCRIPTION
            "The current minutes interval packets transmitted that were
            longer than 1518 octets (excluding framing bits,
            but including FCS octets), and had either a bad
            Frame Check Sequence (FCS) with an integral number
            of octets (FCS Error) or a bad FCS with a non-integral
            number of octets (Alignment Error)."
        ::= { zxAnPonOltIfCurrMinPerfEntry 54}
        
    zxAnPonOltIfCMinRxCorrFecCodes OBJECT-TYPE
        SYNTAX      Counter64
        MAX-ACCESS  read-only
        STATUS      current
        DESCRIPTION
            "The current minutes interval correct FEC codes received."
        ::= { zxAnPonOltIfCurrMinPerfEntry 55}

    zxAnPonOltIfCMinRxErrFecCodes OBJECT-TYPE
        SYNTAX      Counter64
        MAX-ACCESS  read-only
        STATUS      current
        DESCRIPTION
            "The current minutes interval errored FEC codes received."
        ::= { zxAnPonOltIfCurrMinPerfEntry 56}        
        
    zxAnPonOltIfCMinCollisions OBJECT-TYPE
        SYNTAX      Counter64
        MAX-ACCESS  read-only
        STATUS      current
        DESCRIPTION
            "The current minutes interval best estimate of collisions
            on this olt interface."
        ::= { zxAnPonOltIfCurrMinPerfEntry 70}

    zxAnPonOltIfCMinDropEvents OBJECT-TYPE
        SYNTAX      Counter64
        MAX-ACCESS  read-only
        STATUS      current
        DESCRIPTION
            "The current minutes interval events in which packets
            were dropped by the probe due to lack of resources."
        ::= { zxAnPonOltIfCurrMinPerfEntry 71}    

    zxAnPonOltIfCMinPerfReset  OBJECT-TYPE
        SYNTAX       INTEGER{
                     reset(1)
                     }
        MAX-ACCESS   read-write
        STATUS       current
        DESCRIPTION
            "Clear all the current minutes performance variables.
            When get this variable, always return 1."
        ::= {zxAnPonOltIfCurrMinPerfEntry 100 }

--------------------------------------------------------------------------------
--  zxAnPonOltIfCurr1DayPerfTable
--------------------------------------------------------------------------------
    zxAnPonOltIfCurr1DayPerfTable OBJECT-TYPE
        SYNTAX         SEQUENCE OF ZxAnPonOltIfCurr1DayPerfEntry
        MAX-ACCESS     not-accessible
        STATUS         current
        DESCRIPTION
            "The current 1 day performance data table of PON interface.
             The 'IfType' of ifIndex supports 1(physical interface) 
             and 5(PON channel)."
        ::= { zxAnPonOltPerfObjects 4 }

    zxAnPonOltIfCurr1DayPerfEntry OBJECT-TYPE
        SYNTAX         ZxAnPonOltIfCurr1DayPerfEntry
        MAX-ACCESS     not-accessible
        STATUS         current
        DESCRIPTION
            "Entry of zxAnPonOltIfCurr1DayPerfTable."
        INDEX    { ifIndex }
        ::= { zxAnPonOltIfCurr1DayPerfTable 1}

    ZxAnPonOltIfCurr1DayPerfEntry ::=
        SEQUENCE{
                zxAnPonOltIfC1DTimeElapsed            Gauge32,
                zxAnPonOltIfC1DRxOctets               Counter64,
                zxAnPonOltIfC1DRxPkts                 Counter64,
                zxAnPonOltIfC1DRxUcastPkts            Counter64,
                zxAnPonOltIfC1DRxNUcastPkts           Counter64,
                zxAnPonOltIfC1DRxMcastPkts            Counter64,
                zxAnPonOltIfC1DRxBcastPkts            Counter64,
                zxAnPonOltIfC1DRxDiscardPkts          Counter64,
                zxAnPonOltIfC1DRxErrPkts              Counter64,
                zxAnPonOltIfC1DRxCrcAlignErrors       Counter64,
                zxAnPonOltIfC1DRxUndersizePkts        Counter64,
                zxAnPonOltIfC1DRxOversizePkts         Counter64,
                zxAnPonOltIfC1DRx64Octs               Counter64,
                zxAnPonOltIfC1DRx65To127Octs          Counter64,
                zxAnPonOltIfC1DRx128To255Octs         Counter64,
                zxAnPonOltIfC1DRx256To511Octs         Counter64,
                zxAnPonOltIfC1DRx512To1023Octs        Counter64,
                zxAnPonOltIfC1DRx1024To1518Octs       Counter64,
                zxAnPonOltIfC1DRxFragments            Counter64,
                zxAnPonOltIfC1DRxJabbers              Counter64,
                zxAnPonOltIfC1DTxOctets               Counter64,
                zxAnPonOltIfC1DTxPkts                 Counter64,
                zxAnPonOltIfC1DTxUcastPkts            Counter64,
                zxAnPonOltIfC1DTxNUcastPkts           Counter64,
                zxAnPonOltIfC1DTxMcastPkts            Counter64,
                zxAnPonOltIfC1DTxBcastPkts            Counter64,
                zxAnPonOltIfC1DTxDiscardPkts          Counter64,
                zxAnPonOltIfC1DTxErrPkts              Counter64,
                zxAnPonOltIfC1DTxCrcAlignErrors       Counter64,
                zxAnPonOltIfC1DTxUndersizePkts        Counter64,
                zxAnPonOltIfC1DTxOversizePkts         Counter64,
                zxAnPonOltIfC1DTx64Octets             Counter64,
                zxAnPonOltIfC1DTx65To127Octs          Counter64,
                zxAnPonOltIfC1DTx128To255Octs         Counter64,
                zxAnPonOltIfC1DTx256To511Octs         Counter64,
                zxAnPonOltIfC1DTx512To1023Octs        Counter64,
                zxAnPonOltIfC1DTx1024To1518Octs       Counter64,
                zxAnPonOltIfC1DTxFragments            Counter64,
                zxAnPonOltIfC1DTxJabbers              Counter64,
                zxAnPonOltIfC1DRxCorrFecCodes         Counter64,
                zxAnPonOltIfC1DRxErrFecCodes          Counter64,
                zxAnPonOltIfC1DCollisions             Counter64,                
                zxAnPonOltIfC1DDropEvents             Counter64,
                zxAnPonOltIfC1DPerfReset              INTEGER
                }

    zxAnPonOltIfC1DTimeElapsed  OBJECT-TYPE 
        SYNTAX      Gauge32(0..86399)
        UNITS       "Seconds"
        MAX-ACCESS  read-only
        STATUS      current
        DESCRIPTION     
            "Number of seconds that have elapsed since the beginning
             of the current 1 day interval."
        ::= { zxAnPonOltIfCurr1DayPerfEntry 1 }
        
    zxAnPonOltIfC1DRxOctets OBJECT-TYPE
        SYNTAX       Counter64
        MAX-ACCESS   read-only
        STATUS       current
        DESCRIPTION
            "The current 1 day interval octets of data (including
         those in bad packets) received on the
         network (excluding framing bits but including
         FCS octets)."
        ::= {zxAnPonOltIfCurr1DayPerfEntry 2 }

    zxAnPonOltIfC1DRxPkts OBJECT-TYPE
        SYNTAX       Counter64
        MAX-ACCESS   read-only
        STATUS       current
        DESCRIPTION
            "The current 1 day interval packets (including bad packets,
         broadcast packets, and multicast packets) received."
        ::= {zxAnPonOltIfCurr1DayPerfEntry 3 }

    zxAnPonOltIfC1DRxUcastPkts OBJECT-TYPE
        SYNTAX       Counter64
        MAX-ACCESS   read-only
        STATUS       current
        DESCRIPTION
            "The current 1 day interval good packets received that were
         directed to a unicast address."
        ::= {zxAnPonOltIfCurr1DayPerfEntry 4 }

    zxAnPonOltIfC1DRxNUcastPkts OBJECT-TYPE
        SYNTAX       Counter64
        MAX-ACCESS   read-only
        STATUS       current
        DESCRIPTION
            "The current 1 day interval good packets received that were
         directed to a non-unicast address."
        ::= {zxAnPonOltIfCurr1DayPerfEntry 5 }

    zxAnPonOltIfC1DRxMcastPkts OBJECT-TYPE
        SYNTAX       Counter64
        MAX-ACCESS   read-only
        STATUS       current
        DESCRIPTION
            "The current 1 day interval good packets received that were
         directed to a multicast address."
        ::= {zxAnPonOltIfCurr1DayPerfEntry 6 }

    zxAnPonOltIfC1DRxBcastPkts OBJECT-TYPE
        SYNTAX       Counter64
        MAX-ACCESS   read-only
        STATUS       current
        DESCRIPTION
            "The current 1 day interval good packets received that were
         directed to the broadcast address.  Note that this
         does not include multicast packets."
        ::= {zxAnPonOltIfCurr1DayPerfEntry 7 }

    zxAnPonOltIfC1DRxDiscardPkts OBJECT-TYPE
        SYNTAX       Counter64
        MAX-ACCESS   read-only
        STATUS       current
        DESCRIPTION
            "The current 1 day interval discarded packets received."
        ::= {zxAnPonOltIfCurr1DayPerfEntry 8 }

    zxAnPonOltIfC1DRxErrPkts OBJECT-TYPE
        SYNTAX       Counter64
        MAX-ACCESS   read-only
        STATUS       current
        DESCRIPTION
            "The current 1 day interval error packets received."
        ::= {zxAnPonOltIfCurr1DayPerfEntry 9 }

    zxAnPonOltIfC1DRxCrcAlignErrors OBJECT-TYPE
        SYNTAX       Counter64
        MAX-ACCESS   read-only
        STATUS       current
        DESCRIPTION
            "The current 1 day interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOltIfCurr1DayPerfEntry 10 }

    zxAnPonOltIfC1DRxUndersizePkts OBJECT-TYPE
        SYNTAX       Counter64
        MAX-ACCESS   read-only
        STATUS       current
        DESCRIPTION
            "The current 1 day interval packets received that were
         less than 64 octets long (excluding framing bits,
         but including FCS octets) and were otherwise well
         formed."
        ::= {zxAnPonOltIfCurr1DayPerfEntry 11 }

    zxAnPonOltIfC1DRxOversizePkts OBJECT-TYPE
        SYNTAX       Counter64
        MAX-ACCESS   read-only
        STATUS       current
        DESCRIPTION
            "The current 1 day interval packets received that were
         longer than 1518 octets (excluding framing bits,
         but including FCS octets) and were otherwise
         well formed."
        ::= {zxAnPonOltIfCurr1DayPerfEntry 12 }

    zxAnPonOltIfC1DRx64Octs      OBJECT-TYPE
        SYNTAX       Counter64
        MAX-ACCESS   read-only
        STATUS       current
        DESCRIPTION
            "The current 1 day interval packets (including bad
         packets) received that were 64 octets in length
         (excluding framing bits but including FCS octets)."
        ::= {zxAnPonOltIfCurr1DayPerfEntry 13 }

    zxAnPonOltIfC1DRx65To127Octs OBJECT-TYPE
        SYNTAX       Counter64
        MAX-ACCESS   read-only
        STATUS       current
        DESCRIPTION
            "The current 1 day interval packets (including bad
         packets) received that were between
         65 and 127 octets in length inclusive
         (excluding framing bits but including FCS octets)."
        ::= {zxAnPonOltIfCurr1DayPerfEntry 14 }

    zxAnPonOltIfC1DRx128To255Octs OBJECT-TYPE
        SYNTAX       Counter64
        MAX-ACCESS   read-only
        STATUS       current
        DESCRIPTION
            "The current 1 day interval packets (including bad
         packets) received that were between
         128 and 255 octets in length inclusive
         (excluding framing bits but including FCS octets)."
        ::= {zxAnPonOltIfCurr1DayPerfEntry 15 }

    zxAnPonOltIfC1DRx256To511Octs OBJECT-TYPE
        SYNTAX       Counter64
        MAX-ACCESS   read-only
        STATUS       current
        DESCRIPTION
            "The current 1 day interval packets (including bad
         packets) received that were between
         256 and 511 octets in length inclusive
         (excluding framing bits but including FCS octets)."
        ::= {zxAnPonOltIfCurr1DayPerfEntry 16 }

    zxAnPonOltIfC1DRx512To1023Octs OBJECT-TYPE
        SYNTAX       Counter64
        MAX-ACCESS   read-only
        STATUS       current
        DESCRIPTION
            "The current 1 day interval packets (including bad
         packets) received that were between
         512 and 1023 octets in length inclusive
         (excluding framing bits but including FCS octets)."
        ::= {zxAnPonOltIfCurr1DayPerfEntry 17 }

    zxAnPonOltIfC1DRx1024To1518Octs OBJECT-TYPE
        SYNTAX       Counter64
        MAX-ACCESS   read-only
        STATUS       current
        DESCRIPTION
            "The current 1 day interval packets (including bad
         packets) received that were between
         1024 and 1518 octets in length inclusive
         (excluding framing bits but including FCS octets)."
        ::= {zxAnPonOltIfCurr1DayPerfEntry 18 }
        
    zxAnPonOltIfC1DRxFragments  OBJECT-TYPE
        SYNTAX      Counter64
        MAX-ACCESS  read-only
        STATUS      current
        DESCRIPTION
            "The current 1 day interval packets received that were less 
            than 64 octets in length (excluding framing bits but including
         FCS octets) and had either a bad Frame Check Sequence
         (FCS) with an integral number of octets (FCS Error) or a
         bad FCS with a non-integral number of octets (Alignment
         Error)."
        ::= { zxAnPonOltIfCurr1DayPerfEntry 19}
        
    zxAnPonOltIfC1DRxJabbers OBJECT-TYPE
        SYNTAX      Counter64
        MAX-ACCESS  read-only
        STATUS      current
        DESCRIPTION
            "The current 1 day interval packets received that were
         longer than 1518 octets (excluding framing bits,
         but including FCS octets), and had either a bad
         Frame Check Sequence (FCS) with an integral number
         of octets (FCS Error) or a bad FCS with a non-integral
         number of octets (Alignment Error)."
        ::= { zxAnPonOltIfCurr1DayPerfEntry 20}

    zxAnPonOltIfC1DTxOctets OBJECT-TYPE
        SYNTAX       Counter64
        MAX-ACCESS   read-only
        STATUS       current
        DESCRIPTION
            "The current 1 day interval octets of data (including
         those in bad packets) sent on the
         network (excluding framing bits but including
         FCS octets)."
        ::= {zxAnPonOltIfCurr1DayPerfEntry 36 }

    zxAnPonOltIfC1DTxPkts OBJECT-TYPE
        SYNTAX       Counter64
        MAX-ACCESS   read-only
        STATUS       current
        DESCRIPTION
            "The current 1 day interval packets (including bad packets,
         broadcast packets, and multicast packets) transmitted."
        ::= {zxAnPonOltIfCurr1DayPerfEntry 37 }

    zxAnPonOltIfC1DTxUcastPkts OBJECT-TYPE
        SYNTAX       Counter64
        MAX-ACCESS   read-only
        STATUS       current
        DESCRIPTION
            "The current 1 day interval good packets transmitted that were
         directed to a unicast address."
        ::= {zxAnPonOltIfCurr1DayPerfEntry 38 }

    zxAnPonOltIfC1DTxNUcastPkts OBJECT-TYPE
        SYNTAX       Counter64
        MAX-ACCESS   read-only
        STATUS       current
        DESCRIPTION
            "The current 1 day interval good packets transmitted that were
         directed to a non-unicast address."
        ::= {zxAnPonOltIfCurr1DayPerfEntry 39 }

    zxAnPonOltIfC1DTxMcastPkts OBJECT-TYPE
        SYNTAX       Counter64
        MAX-ACCESS   read-only
        STATUS       current
        DESCRIPTION
            "The current 1 day interval good packets transmitted that were
         directed to a multicast address."
        ::= {zxAnPonOltIfCurr1DayPerfEntry 40 }

    zxAnPonOltIfC1DTxBcastPkts OBJECT-TYPE
        SYNTAX       Counter64
        MAX-ACCESS   read-only
        STATUS       current
        DESCRIPTION
            "The current 1 day interval good packets transmitted that were
         directed to the broadcast address.  Note that this does not include 
         multicast packets."
        ::= {zxAnPonOltIfCurr1DayPerfEntry 41 }

    zxAnPonOltIfC1DTxDiscardPkts OBJECT-TYPE
        SYNTAX       Counter64
        MAX-ACCESS   read-only
        STATUS       current
        DESCRIPTION
            "The current 1 day interval discarded packets transmitted."
        ::= {zxAnPonOltIfCurr1DayPerfEntry 42 }

    zxAnPonOltIfC1DTxErrPkts OBJECT-TYPE
        SYNTAX       Counter64
        MAX-ACCESS   read-only
        STATUS       current
        DESCRIPTION
            "The current 1 day interval error packets transmitted."
        ::= {zxAnPonOltIfCurr1DayPerfEntry 43 }
        
    zxAnPonOltIfC1DTxCrcAlignErrors OBJECT-TYPE
        SYNTAX      Counter64
        MAX-ACCESS  read-only
        STATUS      current
        DESCRIPTION
            "The current 1 day interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOltIfCurr1DayPerfEntry 44}

    zxAnPonOltIfC1DTxUndersizePkts OBJECT-TYPE
        SYNTAX      Counter64
        MAX-ACCESS  read-only
        STATUS      current
        DESCRIPTION
            "The current 1 day interval packets transmitted that were
         less than 64 octets long (excluding framing bits,but including
         FCS octets) and were otherwise well
         formed."
        ::= { zxAnPonOltIfCurr1DayPerfEntry 45}
            
    zxAnPonOltIfC1DTxOversizePkts OBJECT-TYPE
        SYNTAX      Counter64
        MAX-ACCESS  read-only
        STATUS      current
        DESCRIPTION
            "The current 1 day interval packets transmitted that were
         longer than 1518 octets (excluding framing bits, but including FCS
         octets) and were otherwise well formed."
        ::= { zxAnPonOltIfCurr1DayPerfEntry 46}
    
    zxAnPonOltIfC1DTx64Octets OBJECT-TYPE
        SYNTAX       Counter64
        MAX-ACCESS   read-only
        STATUS       current
        DESCRIPTION
            "The current 1 day interval packets (including bad
         packets) transmitted that were 64 octets in length
         (excluding framing bits but including FCS octets)."
        ::= {zxAnPonOltIfCurr1DayPerfEntry 47 }

    zxAnPonOltIfC1DTx65To127Octs OBJECT-TYPE
        SYNTAX       Counter64
        MAX-ACCESS   read-only
        STATUS       current
        DESCRIPTION
            "The current 1 day interval packets (including bad
         packets) transmitted that were between 65 and 127 octets in
         length inclusive (excluding framing bits but including FCS octets)."
        ::= {zxAnPonOltIfCurr1DayPerfEntry 48 }

    zxAnPonOltIfC1DTx128To255Octs OBJECT-TYPE
        SYNTAX       Counter64
        MAX-ACCESS   read-only
        STATUS       current
        DESCRIPTION
            "The current 1 day interval packets (including bad
         packets) transmitted that were between
         128 and 255 octets in length inclusive
         (excluding framing bits but including FCS octets)."
        ::= {zxAnPonOltIfCurr1DayPerfEntry 49}

    zxAnPonOltIfC1DTx256To511Octs OBJECT-TYPE
        SYNTAX       Counter64
        MAX-ACCESS   read-only
        STATUS       current
        DESCRIPTION
            "The current 1 day interval packets (including bad
         packets) transmitted that were between
         256 and 511 octets in length inclusive
         (excluding framing bits but including FCS octets)."
        ::= {zxAnPonOltIfCurr1DayPerfEntry 50 }

    zxAnPonOltIfC1DTx512To1023Octs OBJECT-TYPE
        SYNTAX       Counter64
        MAX-ACCESS   read-only
        STATUS       current
        DESCRIPTION
            "The current 1 day interval packets (including bad
         packets) transmitted that were between
         512 and 1023 octets in length inclusive
         (excluding framing bits but including FCS octets)."
        ::= {zxAnPonOltIfCurr1DayPerfEntry 51 }

    zxAnPonOltIfC1DTx1024To1518Octs OBJECT-TYPE
        SYNTAX       Counter64
        MAX-ACCESS   read-only
        STATUS       current
        DESCRIPTION
            "The current 1 day interval packets (including bad
         packets) transmitted that were between
         1024 and 1518 octets in length inclusive
         (excluding framing bits but including FCS octets)."
        ::= {zxAnPonOltIfCurr1DayPerfEntry 52 }
        
    zxAnPonOltIfC1DTxFragments  OBJECT-TYPE
        SYNTAX      Counter64
        MAX-ACCESS  read-only
        STATUS      current
        DESCRIPTION
            "The current 1 day interval packets transmitted that were less 
            than 64 octets in length (excluding framing bits but including
         FCS octets) and had either a bad Frame Check Sequence
         (FCS) with an integral number of octets (FCS Error) or a
         bad FCS with a non-integral number of octets (Alignment
         Error)."
        ::= { zxAnPonOltIfCurr1DayPerfEntry 53}
        
    zxAnPonOltIfC1DTxJabbers OBJECT-TYPE
        SYNTAX      Counter64
        MAX-ACCESS  read-only
        STATUS      current
        DESCRIPTION
            "The current 1 day interval packets transmitted that were
         longer than 1518 octets (excluding framing bits,
         but including FCS octets), and had either a bad
         Frame Check Sequence (FCS) with an integral number
         of octets (FCS Error) or a bad FCS with a non-integral
         number of octets (Alignment Error)."
        ::= { zxAnPonOltIfCurr1DayPerfEntry 54}
        
    zxAnPonOltIfC1DRxCorrFecCodes OBJECT-TYPE
        SYNTAX      Counter64
        MAX-ACCESS  read-only
        STATUS      current
        DESCRIPTION
            "The current 1 day interval correct FEC codes received."
        ::= { zxAnPonOltIfCurr1DayPerfEntry 55}

    zxAnPonOltIfC1DRxErrFecCodes OBJECT-TYPE
        SYNTAX      Counter64
        MAX-ACCESS  read-only
        STATUS      current
        DESCRIPTION
            "The current 1 day interval errored FEC codes received."
        ::= { zxAnPonOltIfCurr1DayPerfEntry 56}    
        
    zxAnPonOltIfC1DCollisions OBJECT-TYPE
        SYNTAX      Counter64
        MAX-ACCESS  read-only
        STATUS      current
        DESCRIPTION
            "The current 1 day interval best estimate of collisions
         on this olt interface."
        ::= { zxAnPonOltIfCurr1DayPerfEntry 70}

    zxAnPonOltIfC1DDropEvents OBJECT-TYPE
        SYNTAX      Counter64
        MAX-ACCESS  read-only
        STATUS      current
        DESCRIPTION
            "The current 1 day interval events in which packets
         were dropped by the probe due to lack of resources."
        ::= { zxAnPonOltIfCurr1DayPerfEntry 71}
           
    zxAnPonOltIfC1DPerfReset  OBJECT-TYPE
        SYNTAX       INTEGER{
                     reset(1)
                     }
        MAX-ACCESS   read-write
        STATUS       current
        DESCRIPTION
            "Clear all the current 1 day performance variables.
            When get this variable, always return 1."
        ::= {zxAnPonOltIfCurr1DayPerfEntry 100 }
        
--------------------------------------------------------------------------------
--  zxAnPonOltIfHis15MinPerfTable
--------------------------------------------------------------------------------
    zxAnPonOltIfHis15MinPerfTable OBJECT-TYPE
        SYNTAX         SEQUENCE OF ZxAnPonOltIfHis15MinPerfEntry
        MAX-ACCESS     not-accessible
        STATUS         current
        DESCRIPTION
            "The 15 minutes interval performance data table of PON OLT.
             The 'IfType' of ifIndex supports 1(physical interface) 
             and 5(PON channel)."
        ::= { zxAnPonOltPerfObjects 5 }

    zxAnPonOltIfHis15MinPerfEntry OBJECT-TYPE
        SYNTAX         ZxAnPonOltIfHis15MinPerfEntry
        MAX-ACCESS     not-accessible
        STATUS         current
        DESCRIPTION
            "An entry in the OLT 15 minutes interval performance data table."
        INDEX    { ifIndex,zxAnPonOltIfH15MIntervalNo}
        ::= { zxAnPonOltIfHis15MinPerfTable 1}

    ZxAnPonOltIfHis15MinPerfEntry ::=
        SEQUENCE{
                zxAnPonOltIfH15MIntervalNo             Integer32,              
                zxAnPonOltIfH15MValidData              TruthValue,
                zxAnPonOltIfH15MDateAndTime            DateAndTime,
                zxAnPonOltIfH15MRxOctets               Counter64,
                zxAnPonOltIfH15MRxPkts                 Counter64,
                zxAnPonOltIfH15MRxUcastPkts            Counter64,
                zxAnPonOltIfH15MRxNUcastPkts           Counter64,
                zxAnPonOltIfH15MRxMcastPkts            Counter64,
                zxAnPonOltIfH15MRxBcastPkts            Counter64,
                zxAnPonOltIfH15MRxDiscardPkts          Counter64,
                zxAnPonOltIfH15MRxErrPkts              Counter64,
                zxAnPonOltIfH15MRxCrcAlignErrors       Counter64,
                zxAnPonOltIfH15MRxUndersizePkts        Counter64,
                zxAnPonOltIfH15MRxOversizePkts         Counter64,
                zxAnPonOltIfH15MRx64Octs               Counter64,
                zxAnPonOltIfH15MRx65To127Octs          Counter64,
                zxAnPonOltIfH15MRx128To255Octs         Counter64,
                zxAnPonOltIfH15MRx256To511Octs         Counter64,
                zxAnPonOltIfH15MRx512To1023Octs        Counter64,
                zxAnPonOltIfH15MRx1024To1518Octs       Counter64,
                zxAnPonOltIfH15MRxFragments            Counter64,
                zxAnPonOltIfH15MRxJabbers              Counter64,
				zxAnPonOltIfH15MRxAvgOctetRate         Gauge32,
                zxAnPonOltIfH15MTxOctets               Counter64,
                zxAnPonOltIfH15MTxPkts                 Counter64,
                zxAnPonOltIfH15MTxUcastPkts            Counter64,
                zxAnPonOltIfH15MTxNUcastPkts           Counter64,
                zxAnPonOltIfH15MTxMcastPkts            Counter64,
                zxAnPonOltIfH15MTxBcastPkts            Counter64,
                zxAnPonOltIfH15MTxDiscardPkts          Counter64,
                zxAnPonOltIfH15MTxErrPkts              Counter64,
                zxAnPonOltIfH15MTxCrcAlignErrors       Counter64,
                zxAnPonOltIfH15MTxUndersizePkts        Counter64,
                zxAnPonOltIfH15MTxOversizePkts         Counter64,
                zxAnPonOltIfH15MTxPkts64Octets         Counter64,
                zxAnPonOltIfH15MTx65To127Octs          Counter64,
                zxAnPonOltIfH15MTx128To255Octs         Counter64,
                zxAnPonOltIfH15MTx256To511Octs         Counter64,
                zxAnPonOltIfH15MTx512To1023Octs        Counter64,
                zxAnPonOltIfH15MTx1024To1518Octs       Counter64,
                zxAnPonOltIfH15MTxFragments            Counter64,
                zxAnPonOltIfH15MTxJabbers              Counter64,
                zxAnPonOltIfH15MRxCorrFecCodes         Counter64,
                zxAnPonOltIfH15MRxErrFecCodes          Counter64,
                zxAnPonOltIfH15MCollisions             Counter64,                
                zxAnPonOltIfH15MDropEvents             Counter64,
				zxAnPonOltIfH15MTxAvgOctetRate         Gauge32
                }

    zxAnPonOltIfH15MIntervalNo  OBJECT-TYPE 
        SYNTAX      Integer32(1..96)
        MAX-ACCESS  not-accessible
        STATUS      current
        DESCRIPTION     
             "Performance Data Interval.
              
              Interval 1 is the the most recent previous interval; 
              Interval 96 is 24 hours ago.
              Intervals from 2 to 96 are optional."
        ::= { zxAnPonOltIfHis15MinPerfEntry 1 }
        
    zxAnPonOltIfH15MValidData OBJECT-TYPE
        SYNTAX      TruthValue
        MAX-ACCESS  read-only
        STATUS      current
        DESCRIPTION     
             "Performance data valid flag.
              true(1) means valid.
              false(2) means invalid and the performace data is useless."
        ::= { zxAnPonOltIfHis15MinPerfEntry 2} 
        
    zxAnPonOltIfH15MDateAndTime     OBJECT-TYPE   
        SYNTAX      DateAndTime
        MAX-ACCESS  read-only
        STATUS      current
        DESCRIPTION     
             "15min performace data interval create time."
        ::= { zxAnPonOltIfHis15MinPerfEntry 3 }
        
    zxAnPonOltIfH15MRxOctets OBJECT-TYPE
        SYNTAX       Counter64
        MAX-ACCESS   read-only
        STATUS       current
        DESCRIPTION
            "The 15 minutes interval octets of data (including
         those in bad packets) received on the
         network (excluding framing bits but including
         FCS octets)."
        ::= {zxAnPonOltIfHis15MinPerfEntry 4 }

    zxAnPonOltIfH15MRxPkts OBJECT-TYPE
        SYNTAX       Counter64
        MAX-ACCESS   read-only
        STATUS       current
        DESCRIPTION
            "The 15 minutes interval packets (including bad packets,
         broadcast packets, and multicast packets) received."
        ::= {zxAnPonOltIfHis15MinPerfEntry 5 }

    zxAnPonOltIfH15MRxUcastPkts OBJECT-TYPE
        SYNTAX       Counter64
        MAX-ACCESS   read-only
        STATUS       current
        DESCRIPTION
            "The 15 minutes interval good packets received that were
         directed to a unicast address."
        ::= {zxAnPonOltIfHis15MinPerfEntry 6 }

    zxAnPonOltIfH15MRxNUcastPkts OBJECT-TYPE
        SYNTAX       Counter64
        MAX-ACCESS   read-only
        STATUS       current
        DESCRIPTION
            "The 15 minutes interval good packets received that were
         directed to a non-unicast address."
        ::= {zxAnPonOltIfHis15MinPerfEntry 7 }

    zxAnPonOltIfH15MRxMcastPkts OBJECT-TYPE
        SYNTAX       Counter64
        MAX-ACCESS   read-only
        STATUS       current
        DESCRIPTION
            "The 15 minutes interval good packets received that were
         directed to a multicast address."
        ::= {zxAnPonOltIfHis15MinPerfEntry 8 }

    zxAnPonOltIfH15MRxBcastPkts OBJECT-TYPE
        SYNTAX       Counter64
        MAX-ACCESS   read-only
        STATUS       current
        DESCRIPTION
            "The 15 minutes interval good packets received that were
         directed to the broadcast address.  Note that this
         does not include multicast packets."
        ::= {zxAnPonOltIfHis15MinPerfEntry 9 }

    zxAnPonOltIfH15MRxDiscardPkts OBJECT-TYPE
        SYNTAX       Counter64
        MAX-ACCESS   read-only
        STATUS       current
        DESCRIPTION
            "The 15 minutes interval discarded packets received."
        ::= {zxAnPonOltIfHis15MinPerfEntry 10 }

    zxAnPonOltIfH15MRxErrPkts OBJECT-TYPE
        SYNTAX       Counter64
        MAX-ACCESS   read-only
        STATUS       current
        DESCRIPTION
            "The 15 minutes interval error packets received."
        ::= {zxAnPonOltIfHis15MinPerfEntry 11 }

    zxAnPonOltIfH15MRxCrcAlignErrors OBJECT-TYPE
        SYNTAX       Counter64
        MAX-ACCESS   read-only
        STATUS       current
        DESCRIPTION
            "The 15 minutes interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOltIfHis15MinPerfEntry 12 }

    zxAnPonOltIfH15MRxUndersizePkts OBJECT-TYPE
        SYNTAX       Counter64
        MAX-ACCESS   read-only
        STATUS       current
        DESCRIPTION
            "The 15 minutes interval packets received that were
         less than 64 octets long (excluding framing bits,
         but including FCS octets) and were otherwise well
         formed."
        ::= {zxAnPonOltIfHis15MinPerfEntry 13 }

    zxAnPonOltIfH15MRxOversizePkts OBJECT-TYPE
        SYNTAX       Counter64
        MAX-ACCESS   read-only
        STATUS       current
        DESCRIPTION
            "The 15 minutes interval packets received that were
         longer than 1518 octets (excluding framing bits,
         but including FCS octets) and were otherwise
         well formed."
        ::= {zxAnPonOltIfHis15MinPerfEntry 14 }

    zxAnPonOltIfH15MRx64Octs      OBJECT-TYPE
        SYNTAX       Counter64
        MAX-ACCESS   read-only
        STATUS       current
        DESCRIPTION
            "The 15 minutes interval packets (including bad
         packets) received that were 64 octets in length
         (excluding framing bits but including FCS octets)."
        ::= {zxAnPonOltIfHis15MinPerfEntry 15 }

    zxAnPonOltIfH15MRx65To127Octs OBJECT-TYPE
        SYNTAX       Counter64
        MAX-ACCESS   read-only
        STATUS       current
        DESCRIPTION
            "The 15 minutes interval packets (including bad
         packets) received that were between
         65 and 127 octets in length inclusive
         (excluding framing bits but including FCS octets)."
        ::= {zxAnPonOltIfHis15MinPerfEntry 16 }

    zxAnPonOltIfH15MRx128To255Octs OBJECT-TYPE
        SYNTAX       Counter64
        MAX-ACCESS   read-only
        STATUS       current
        DESCRIPTION
            "The 15 minutes interval packets (including bad
         packets) received that were between
         128 and 255 octets in length inclusive
         (excluding framing bits but including FCS octets)."
        ::= {zxAnPonOltIfHis15MinPerfEntry 17 }

    zxAnPonOltIfH15MRx256To511Octs OBJECT-TYPE
        SYNTAX       Counter64
        MAX-ACCESS   read-only
        STATUS       current
        DESCRIPTION
            "The 15 minutes interval packets (including bad
         packets) received that were between
         256 and 511 octets in length inclusive
         (excluding framing bits but including FCS octets)."
        ::= {zxAnPonOltIfHis15MinPerfEntry 18 }

    zxAnPonOltIfH15MRx512To1023Octs OBJECT-TYPE
        SYNTAX       Counter64
        MAX-ACCESS   read-only
        STATUS       current
        DESCRIPTION
            "The 15 minutes interval packets (including bad
         packets) received that were between
         512 and 1023 octets in length inclusive
         (excluding framing bits but including FCS octets)."
        ::= {zxAnPonOltIfHis15MinPerfEntry 19 }

    zxAnPonOltIfH15MRx1024To1518Octs OBJECT-TYPE
        SYNTAX       Counter64
        MAX-ACCESS   read-only
        STATUS       current
        DESCRIPTION
            "The 15 minutes interval packets (including bad
         packets) received that were between
         1024 and 1518 octets in length inclusive
         (excluding framing bits but including FCS octets)."
        ::= {zxAnPonOltIfHis15MinPerfEntry 20 }
        
    zxAnPonOltIfH15MRxFragments  OBJECT-TYPE
        SYNTAX      Counter64
        MAX-ACCESS  read-only
        STATUS      current
        DESCRIPTION
            "The 15 minutes interval packets received that were less 
            than 64 octets in length (excluding framing bits but including
         FCS octets) and had either a bad Frame Check Sequence
         (FCS) with an integral number of octets (FCS Error) or a
         bad FCS with a non-integral number of octets (Alignment
         Error)."
        ::= { zxAnPonOltIfHis15MinPerfEntry 21}
        
    zxAnPonOltIfH15MRxJabbers OBJECT-TYPE
        SYNTAX      Counter64
        MAX-ACCESS  read-only
        STATUS      current
        DESCRIPTION
            "The 15 minutes interval packets received that were
         longer than 1518 octets (excluding framing bits,
         but including FCS octets), and had either a bad
         Frame Check Sequence (FCS) with an integral number
         of octets (FCS Error) or a bad FCS with a non-integral
         number of octets (Alignment Error)."
        ::= { zxAnPonOltIfHis15MinPerfEntry 22}
		
	zxAnPonOltIfH15MRxAvgOctetRate OBJECT-TYPE
        SYNTAX       Gauge32
        UNITS        "Bps"
        MAX-ACCESS   read-only
        STATUS       current
        DESCRIPTION
            "The 15 minutes interval received average octet rate."
        ::= {zxAnPonOltIfHis15MinPerfEntry 23 }

    zxAnPonOltIfH15MTxOctets OBJECT-TYPE
        SYNTAX       Counter64
        MAX-ACCESS   read-only
        STATUS       current
        DESCRIPTION
            "The 15 minutes interval octets of data (including
         those in bad packets) sent on the
         network (excluding framing bits but including
         FCS octets)."
        ::= {zxAnPonOltIfHis15MinPerfEntry 36 }

    zxAnPonOltIfH15MTxPkts OBJECT-TYPE
        SYNTAX       Counter64
        MAX-ACCESS   read-only
        STATUS       current
        DESCRIPTION
            "The 15 minutes interval packets (including bad packets,
         broadcast packets, and multicast packets) transmitted."
        ::= {zxAnPonOltIfHis15MinPerfEntry 37 }

    zxAnPonOltIfH15MTxUcastPkts OBJECT-TYPE
        SYNTAX       Counter64
        MAX-ACCESS   read-only
        STATUS       current
        DESCRIPTION
            "The 15 minutes interval good packets transmitted that were
         directed to a unicast address."
        ::= {zxAnPonOltIfHis15MinPerfEntry 38 }

    zxAnPonOltIfH15MTxNUcastPkts OBJECT-TYPE
        SYNTAX       Counter64
        MAX-ACCESS   read-only
        STATUS       current
        DESCRIPTION
            "The 15 minutes interval good packets transmitted that were
         directed to a non-unicast address."
        ::= {zxAnPonOltIfHis15MinPerfEntry 39 }

    zxAnPonOltIfH15MTxMcastPkts OBJECT-TYPE
        SYNTAX       Counter64
        MAX-ACCESS   read-only
        STATUS       current
        DESCRIPTION
            "The 15 minutes interval good packets transmitted that were
         directed to a multicast address."
        ::= {zxAnPonOltIfHis15MinPerfEntry 40 }

    zxAnPonOltIfH15MTxBcastPkts OBJECT-TYPE
        SYNTAX       Counter64
        MAX-ACCESS   read-only
        STATUS       current
        DESCRIPTION
            "The 15 minutes interval good packets transmitted that were
         directed to the broadcast address.Note that this does not include 
         multicast packets."
        ::= {zxAnPonOltIfHis15MinPerfEntry 41 }

    zxAnPonOltIfH15MTxDiscardPkts OBJECT-TYPE
        SYNTAX       Counter64
        MAX-ACCESS   read-only
        STATUS       current
        DESCRIPTION
            "The 15 minutes interval discarded packets transmitted."
        ::= {zxAnPonOltIfHis15MinPerfEntry 42 }

    zxAnPonOltIfH15MTxErrPkts OBJECT-TYPE
        SYNTAX       Counter64
        MAX-ACCESS   read-only
        STATUS       current
        DESCRIPTION
            "The 15 minutes interval error packets transmitted."
        ::= {zxAnPonOltIfHis15MinPerfEntry 43 }
        
    zxAnPonOltIfH15MTxCrcAlignErrors OBJECT-TYPE
        SYNTAX      Counter64
        MAX-ACCESS  read-only
        STATUS      current
        DESCRIPTION
            "The 15 minutes interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOltIfHis15MinPerfEntry 44}

    zxAnPonOltIfH15MTxUndersizePkts OBJECT-TYPE
        SYNTAX      Counter64
        MAX-ACCESS  read-only
        STATUS      current
        DESCRIPTION
            "The 15 minutes interval packets transmitted that were
         less than 64 octets long (excluding framing bits,but including
         FCS octets) and were otherwise well
         formed."
        ::= { zxAnPonOltIfHis15MinPerfEntry 45}
            
    zxAnPonOltIfH15MTxOversizePkts OBJECT-TYPE
        SYNTAX      Counter64
        MAX-ACCESS  read-only
        STATUS      current
        DESCRIPTION
            "The 15 minutes interval packets transmitted that were
         longer than 1518 octets (excluding framing bits, but including FCS
         octets) and were otherwise well formed."
        ::= { zxAnPonOltIfHis15MinPerfEntry 46}
    
    zxAnPonOltIfH15MTxPkts64Octets OBJECT-TYPE
        SYNTAX       Counter64
        MAX-ACCESS   read-only
        STATUS       current
        DESCRIPTION
            "The 15 minutes interval packets (including bad
         packets) transmitted that were 64 octets in length
         (excluding framing bits but including FCS octets)."
        ::= {zxAnPonOltIfHis15MinPerfEntry 47 }

    zxAnPonOltIfH15MTx65To127Octs OBJECT-TYPE
        SYNTAX       Counter64
        MAX-ACCESS   read-only
        STATUS       current
        DESCRIPTION
            "The 15 minutes interval packets (including bad
         packets) transmitted that were between 65 and 127 octets in
         length inclusive (excluding framing bits but including FCS octets)."
        ::= {zxAnPonOltIfHis15MinPerfEntry 48 }

    zxAnPonOltIfH15MTx128To255Octs OBJECT-TYPE
        SYNTAX       Counter64
        MAX-ACCESS   read-only
        STATUS       current
        DESCRIPTION
            "The 15 minutes interval packets (including bad
         packets) transmitted that were between
         128 and 255 octets in length inclusive
         (excluding framing bits but including FCS octets)."
        ::= {zxAnPonOltIfHis15MinPerfEntry 49}

    zxAnPonOltIfH15MTx256To511Octs OBJECT-TYPE
        SYNTAX       Counter64
        MAX-ACCESS   read-only
        STATUS       current
        DESCRIPTION
            "The 15 minutes interval packets (including bad
         packets) transmitted that were between
         256 and 511 octets in length inclusive
         (excluding framing bits but including FCS octets)."
        ::= {zxAnPonOltIfHis15MinPerfEntry 50 }

    zxAnPonOltIfH15MTx512To1023Octs OBJECT-TYPE
        SYNTAX       Counter64
        MAX-ACCESS   read-only
        STATUS       current
        DESCRIPTION
            "The 15 minutes interval packets (including bad
         packets) transmitted that were between
         512 and 1023 octets in length inclusive
         (excluding framing bits but including FCS octets)."
        ::= {zxAnPonOltIfHis15MinPerfEntry 51 }

    zxAnPonOltIfH15MTx1024To1518Octs OBJECT-TYPE
        SYNTAX       Counter64
        MAX-ACCESS   read-only
        STATUS       current
        DESCRIPTION
            "The 15 minutes interval packets (including bad
         packets) transmitted that were between
         1024 and 1518 octets in length inclusive
         (excluding framing bits but including FCS octets)."
        ::= {zxAnPonOltIfHis15MinPerfEntry 52 }
        
    zxAnPonOltIfH15MTxFragments  OBJECT-TYPE
        SYNTAX      Counter64
        MAX-ACCESS  read-only
        STATUS      current
        DESCRIPTION
            "The 15 minutes interval packets transmitted that were less 
            than 64 octets in length (excluding framing bits but including
         FCS octets) and had either a bad Frame Check Sequence
         (FCS) with an integral number of octets (FCS Error) or a
         bad FCS with a non-integral number of octets (Alignment
         Error)."
        ::= { zxAnPonOltIfHis15MinPerfEntry 53}
        
    zxAnPonOltIfH15MTxJabbers OBJECT-TYPE
        SYNTAX      Counter64
        MAX-ACCESS  read-only
        STATUS      current
        DESCRIPTION
            "The 15 minutes interval packets transmitted that were
         longer than 1518 octets (excluding framing bits,
         but including FCS octets), and had either a bad
         Frame Check Sequence (FCS) with an integral number
         of octets (FCS Error) or a bad FCS with a non-integral
         number of octets (Alignment Error)."
        ::= { zxAnPonOltIfHis15MinPerfEntry 54}
        
    zxAnPonOltIfH15MRxCorrFecCodes OBJECT-TYPE
        SYNTAX      Counter64
        MAX-ACCESS  read-only
        STATUS      current
        DESCRIPTION
            "The 15 minutes interval correct FEC codes received."
        ::= { zxAnPonOltIfHis15MinPerfEntry 55}

    zxAnPonOltIfH15MRxErrFecCodes OBJECT-TYPE
        SYNTAX      Counter64
        MAX-ACCESS  read-only
        STATUS      current
        DESCRIPTION
            "The 15 minutes interval errored FEC codes received."
        ::= { zxAnPonOltIfHis15MinPerfEntry 56}
            
    zxAnPonOltIfH15MCollisions OBJECT-TYPE
        SYNTAX      Counter64
        MAX-ACCESS  read-only
        STATUS      current
        DESCRIPTION
            "The 15 minutes interval best estimate of collisions
         on this olt interface."
        ::= { zxAnPonOltIfHis15MinPerfEntry 70}

    zxAnPonOltIfH15MDropEvents OBJECT-TYPE
        SYNTAX      Counter64
        MAX-ACCESS  read-only
        STATUS      current
        DESCRIPTION
            "The 15 minutes interval events in which packets
         were dropped by the probe due to lack of resources."
        ::= { zxAnPonOltIfHis15MinPerfEntry 71}
		
	zxAnPonOltIfH15MTxAvgOctetRate OBJECT-TYPE
        SYNTAX       Gauge32
        UNITS        "Bps"
        MAX-ACCESS   read-only
        STATUS       current
        DESCRIPTION
            "The 15 minutes interval transmitted average octet rate."
        ::= {zxAnPonOltIfHis15MinPerfEntry 72 }

--------------------------------------------------------------------------------
--  zxAnPonOltIfHisMinPerfTable
--------------------------------------------------------------------------------
    zxAnPonOltIfHisMinPerfTable OBJECT-TYPE
        SYNTAX         SEQUENCE OF ZxAnPonOltIfHisMinPerfEntry
        MAX-ACCESS     not-accessible
        STATUS         current
        DESCRIPTION
            "The minutes interval history performance data table of PON OLT.
            The 'IfType' of ifIndex supports 1(physical interface) 
            and 5(PON channel)."
        ::= { zxAnPonOltPerfObjects 11 }

    zxAnPonOltIfHisMinPerfEntry OBJECT-TYPE
        SYNTAX         ZxAnPonOltIfHisMinPerfEntry
        MAX-ACCESS     not-accessible
        STATUS         current
        DESCRIPTION
            "An entry in the OLT minutes interval history performance data table."
        INDEX    { ifIndex,zxAnPonOltIfHMinIntervalNo}
        ::= { zxAnPonOltIfHisMinPerfTable 1}

    ZxAnPonOltIfHisMinPerfEntry ::=
        SEQUENCE {
            zxAnPonOltIfHMinIntervalNo             Integer32,              
            zxAnPonOltIfHMinValidData              TruthValue,
            zxAnPonOltIfHMinDateAndTime            DateAndTime,
            zxAnPonOltIfHMinRxOctets               Counter64,
            zxAnPonOltIfHMinRxPkts                 Counter64,
            zxAnPonOltIfHMinRxUcastPkts            Counter64,
            zxAnPonOltIfHMinRxNUcastPkts           Counter64,
            zxAnPonOltIfHMinRxMcastPkts            Counter64,
            zxAnPonOltIfHMinRxBcastPkts            Counter64,
            zxAnPonOltIfHMinRxDiscardPkts          Counter64,
            zxAnPonOltIfHMinRxErrPkts              Counter64,
            zxAnPonOltIfHMinRxCrcAlignErrors       Counter64,
            zxAnPonOltIfHMinRxUndersizePkts        Counter64,
            zxAnPonOltIfHMinRxOversizePkts         Counter64,
            zxAnPonOltIfHMinRx64Octs               Counter64,
            zxAnPonOltIfHMinRx65To127Octs          Counter64,
            zxAnPonOltIfHMinRx128To255Octs         Counter64,
            zxAnPonOltIfHMinRx256To511Octs         Counter64,
            zxAnPonOltIfHMinRx512To1023Octs        Counter64,
            zxAnPonOltIfHMinRx1024To1518Octs       Counter64,
            zxAnPonOltIfHMinRxFragments            Counter64,
            zxAnPonOltIfHMinRxJabbers              Counter64,
			zxAnPonOltIfHMinRxAvgOctetRate         Gauge32,
            zxAnPonOltIfHMinTxOctets               Counter64,
            zxAnPonOltIfHMinTxPkts                 Counter64,
            zxAnPonOltIfHMinTxUcastPkts            Counter64,
            zxAnPonOltIfHMinTxNUcastPkts           Counter64,
            zxAnPonOltIfHMinTxMcastPkts            Counter64,
            zxAnPonOltIfHMinTxBcastPkts            Counter64,
            zxAnPonOltIfHMinTxDiscardPkts          Counter64,
            zxAnPonOltIfHMinTxErrPkts              Counter64,
            zxAnPonOltIfHMinTxCrcAlignErrors       Counter64,
            zxAnPonOltIfHMinTxUndersizePkts        Counter64,
            zxAnPonOltIfHMinTxOversizePkts         Counter64,
            zxAnPonOltIfHMinTxPkts64Octets         Counter64,
            zxAnPonOltIfHMinTx65To127Octs          Counter64,
            zxAnPonOltIfHMinTx128To255Octs         Counter64,
            zxAnPonOltIfHMinTx256To511Octs         Counter64,
            zxAnPonOltIfHMinTx512To1023Octs        Counter64,
            zxAnPonOltIfHMinTx1024To1518Octs       Counter64,
            zxAnPonOltIfHMinTxFragments            Counter64,
            zxAnPonOltIfHMinTxJabbers              Counter64,
            zxAnPonOltIfHMinRxCorrFecCodes         Counter64,
            zxAnPonOltIfHMinRxErrFecCodes          Counter64,
            zxAnPonOltIfHMinCollisions             Counter64,
            zxAnPonOltIfHMinDropEvents             Counter64,
			zxAnPonOltIfHMinTxAvgOctetRate         Gauge32
            }

    zxAnPonOltIfHMinIntervalNo  OBJECT-TYPE 
        SYNTAX      Integer32
        MAX-ACCESS  not-accessible
        STATUS      current
        DESCRIPTION     
            "Performance data interval number."
        ::= { zxAnPonOltIfHisMinPerfEntry 1 }
        
    zxAnPonOltIfHMinValidData OBJECT-TYPE
        SYNTAX      TruthValue
        MAX-ACCESS  read-only
        STATUS      current
        DESCRIPTION     
            "Performance data valid flag.
            true(1) means valid.
            false(2) means invalid and the performace data is useless."
        ::= { zxAnPonOltIfHisMinPerfEntry 2} 
        
    zxAnPonOltIfHMinDateAndTime     OBJECT-TYPE   
        SYNTAX      DateAndTime
        MAX-ACCESS  read-only
        STATUS      current
        DESCRIPTION     
            "The minutes interval performance data generation time."
        ::= { zxAnPonOltIfHisMinPerfEntry 3 }
        
    zxAnPonOltIfHMinRxOctets OBJECT-TYPE
        SYNTAX       Counter64
        MAX-ACCESS   read-only
        STATUS       current
        DESCRIPTION
            "The minutes interval octets of data (including
            those in bad packets) received on the
            network (excluding framing bits but including
            FCS octets)."
        ::= {zxAnPonOltIfHisMinPerfEntry 4 }

    zxAnPonOltIfHMinRxPkts OBJECT-TYPE
        SYNTAX       Counter64
        MAX-ACCESS   read-only
        STATUS       current
        DESCRIPTION
            "The minutes interval packets (including bad packets,
            broadcast packets, and multicast packets) received."
        ::= {zxAnPonOltIfHisMinPerfEntry 5 }

    zxAnPonOltIfHMinRxUcastPkts OBJECT-TYPE
        SYNTAX       Counter64
        MAX-ACCESS   read-only
        STATUS       current
        DESCRIPTION
            "The minutes interval good packets received that were
            directed to a unicast address."
        ::= {zxAnPonOltIfHisMinPerfEntry 6 }

    zxAnPonOltIfHMinRxNUcastPkts OBJECT-TYPE
        SYNTAX       Counter64
        MAX-ACCESS   read-only
        STATUS       current
        DESCRIPTION
            "The minutes interval good packets received that were
            directed to a non-unicast address."
        ::= {zxAnPonOltIfHisMinPerfEntry 7 }

    zxAnPonOltIfHMinRxMcastPkts OBJECT-TYPE
        SYNTAX       Counter64
        MAX-ACCESS   read-only
        STATUS       current
        DESCRIPTION
            "The minutes interval good packets received that were
            directed to a multicast address."
        ::= {zxAnPonOltIfHisMinPerfEntry 8 }

    zxAnPonOltIfHMinRxBcastPkts OBJECT-TYPE
        SYNTAX       Counter64
        MAX-ACCESS   read-only
        STATUS       current
        DESCRIPTION
            "The minutes interval good packets received that were
            directed to the broadcast address.  Note that this
            does not include multicast packets."
        ::= {zxAnPonOltIfHisMinPerfEntry 9 }

    zxAnPonOltIfHMinRxDiscardPkts OBJECT-TYPE
        SYNTAX       Counter64
        MAX-ACCESS   read-only
        STATUS       current
        DESCRIPTION
            "The minutes interval discarded packets received."
        ::= {zxAnPonOltIfHisMinPerfEntry 10 }

    zxAnPonOltIfHMinRxErrPkts OBJECT-TYPE
        SYNTAX       Counter64
        MAX-ACCESS   read-only
        STATUS       current
        DESCRIPTION
            "The minutes interval error packets received."
        ::= {zxAnPonOltIfHisMinPerfEntry 11 }

    zxAnPonOltIfHMinRxCrcAlignErrors OBJECT-TYPE
        SYNTAX       Counter64
        MAX-ACCESS   read-only
        STATUS       current
        DESCRIPTION
            "The minutes interval packets received that
            had a length (excluding framing bits, but
            including FCS octets) of between 64 and 1518
            octets, inclusive, but had either a bad
            Frame Check Sequence (FCS) with an integral
            number of octets (FCS Error) or a bad FCS with
            a non-integral number of octets (Alignment Error)."
        ::= {zxAnPonOltIfHisMinPerfEntry 12 }

    zxAnPonOltIfHMinRxUndersizePkts OBJECT-TYPE
        SYNTAX       Counter64
        MAX-ACCESS   read-only
        STATUS       current
        DESCRIPTION
            "The minutes interval packets received that were
            less than 64 octets long (excluding framing bits,
            but including FCS octets) and were otherwise well
            formed."
        ::= {zxAnPonOltIfHisMinPerfEntry 13 }

    zxAnPonOltIfHMinRxOversizePkts OBJECT-TYPE
        SYNTAX       Counter64
        MAX-ACCESS   read-only
        STATUS       current
        DESCRIPTION
            "The minutes interval packets received that were
            longer than 1518 octets (excluding framing bits,
            but including FCS octets) and were otherwise
            well formed."
        ::= {zxAnPonOltIfHisMinPerfEntry 14 }

    zxAnPonOltIfHMinRx64Octs      OBJECT-TYPE
        SYNTAX       Counter64
        MAX-ACCESS   read-only
        STATUS       current
        DESCRIPTION
            "The minutes interval packets (including bad
            packets) received that were 64 octets in length
            (excluding framing bits but including FCS octets)."
        ::= {zxAnPonOltIfHisMinPerfEntry 15 }

    zxAnPonOltIfHMinRx65To127Octs OBJECT-TYPE
        SYNTAX       Counter64
        MAX-ACCESS   read-only
        STATUS       current
        DESCRIPTION
            "The minutes interval packets (including bad
            packets) received that were between
            65 and 127 octets in length inclusive
            (excluding framing bits but including FCS octets)."
        ::= {zxAnPonOltIfHisMinPerfEntry 16 }

    zxAnPonOltIfHMinRx128To255Octs OBJECT-TYPE
        SYNTAX       Counter64
        MAX-ACCESS   read-only
        STATUS       current
        DESCRIPTION
            "The minutes interval packets (including bad
            packets) received that were between
            128 and 255 octets in length inclusive
            (excluding framing bits but including FCS octets)."
        ::= {zxAnPonOltIfHisMinPerfEntry 17 }

    zxAnPonOltIfHMinRx256To511Octs OBJECT-TYPE
        SYNTAX       Counter64
        MAX-ACCESS   read-only
        STATUS       current
        DESCRIPTION
            "The minutes interval packets (including bad
            packets) received that were between
            256 and 511 octets in length inclusive
            (excluding framing bits but including FCS octets)."
        ::= {zxAnPonOltIfHisMinPerfEntry 18 }

    zxAnPonOltIfHMinRx512To1023Octs OBJECT-TYPE
        SYNTAX       Counter64
        MAX-ACCESS   read-only
        STATUS       current
        DESCRIPTION
            "The minutes interval packets (including bad
            packets) received that were between
            512 and 1023 octets in length inclusive
            (excluding framing bits but including FCS octets)."
        ::= {zxAnPonOltIfHisMinPerfEntry 19 }

    zxAnPonOltIfHMinRx1024To1518Octs OBJECT-TYPE
        SYNTAX       Counter64
        MAX-ACCESS   read-only
        STATUS       current
        DESCRIPTION
            "The minutes interval packets (including bad
            packets) received that were between
            1024 and 1518 octets in length inclusive
            (excluding framing bits but including FCS octets)."
        ::= {zxAnPonOltIfHisMinPerfEntry 20 }
        
    zxAnPonOltIfHMinRxFragments  OBJECT-TYPE
        SYNTAX      Counter64
        MAX-ACCESS  read-only
        STATUS      current
        DESCRIPTION
            "The minutes interval packets received that were less 
            than 64 octets in length (excluding framing bits but including
            FCS octets) and had either a bad Frame Check Sequence
            (FCS) with an integral number of octets (FCS Error) or a
            bad FCS with a non-integral number of octets (Alignment
            Error)."
        ::= { zxAnPonOltIfHisMinPerfEntry 21}
        
    zxAnPonOltIfHMinRxJabbers OBJECT-TYPE
        SYNTAX      Counter64
        MAX-ACCESS  read-only
        STATUS      current
        DESCRIPTION
            "The minutes interval packets received that were
            longer than 1518 octets (excluding framing bits,
            but including FCS octets), and had either a bad
            Frame Check Sequence (FCS) with an integral number
            of octets (FCS Error) or a bad FCS with a non-integral
            number of octets (Alignment Error)."
        ::= { zxAnPonOltIfHisMinPerfEntry 22}
		
	zxAnPonOltIfHMinRxAvgOctetRate OBJECT-TYPE
        SYNTAX       Gauge32
        UNITS        "Bps"
        MAX-ACCESS   read-only
        STATUS       current
        DESCRIPTION
            "The minutes interval received average octet rate."
        ::= {zxAnPonOltIfHisMinPerfEntry 23 }	

    zxAnPonOltIfHMinTxOctets OBJECT-TYPE
        SYNTAX       Counter64
        MAX-ACCESS   read-only
        STATUS       current
        DESCRIPTION
            "The minutes interval octets of data (including
            those in bad packets) sent on the
            network (excluding framing bits but including
            FCS octets)."
        ::= {zxAnPonOltIfHisMinPerfEntry 36 }

    zxAnPonOltIfHMinTxPkts OBJECT-TYPE
        SYNTAX       Counter64
        MAX-ACCESS   read-only
        STATUS       current
        DESCRIPTION
            "The minutes interval packets (including bad packets,
            broadcast packets, and multicast packets) transmitted."
        ::= {zxAnPonOltIfHisMinPerfEntry 37 }

    zxAnPonOltIfHMinTxUcastPkts OBJECT-TYPE
        SYNTAX       Counter64
        MAX-ACCESS   read-only
        STATUS       current
        DESCRIPTION
            "The minutes interval good packets transmitted that were
            directed to a unicast address."
        ::= {zxAnPonOltIfHisMinPerfEntry 38 }

    zxAnPonOltIfHMinTxNUcastPkts OBJECT-TYPE
        SYNTAX       Counter64
        MAX-ACCESS   read-only
        STATUS       current
        DESCRIPTION
            "The minutes interval good packets transmitted that were
            directed to a non-unicast address."
        ::= {zxAnPonOltIfHisMinPerfEntry 39 }

    zxAnPonOltIfHMinTxMcastPkts OBJECT-TYPE
        SYNTAX       Counter64
        MAX-ACCESS   read-only
        STATUS       current
        DESCRIPTION
            "The minutes interval good packets transmitted that were
            directed to a multicast address."
        ::= {zxAnPonOltIfHisMinPerfEntry 40 }

    zxAnPonOltIfHMinTxBcastPkts OBJECT-TYPE
        SYNTAX       Counter64
        MAX-ACCESS   read-only
        STATUS       current
        DESCRIPTION
            "The minutes interval good packets transmitted that were
            directed to the broadcast address.Note that this does not include 
            multicast packets."
        ::= {zxAnPonOltIfHisMinPerfEntry 41 }

    zxAnPonOltIfHMinTxDiscardPkts OBJECT-TYPE
        SYNTAX       Counter64
        MAX-ACCESS   read-only
        STATUS       current
        DESCRIPTION
            "The minutes interval discarded packets transmitted."
        ::= {zxAnPonOltIfHisMinPerfEntry 42 }

    zxAnPonOltIfHMinTxErrPkts OBJECT-TYPE
        SYNTAX       Counter64
        MAX-ACCESS   read-only
        STATUS       current
        DESCRIPTION
            "The minutes interval error packets transmitted."
        ::= {zxAnPonOltIfHisMinPerfEntry 43 }
        
    zxAnPonOltIfHMinTxCrcAlignErrors OBJECT-TYPE
        SYNTAX      Counter64
        MAX-ACCESS  read-only
        STATUS      current
        DESCRIPTION
            "The minutes interval packets transmitted that
            had a length (excluding framing bits, but including FCS octets)
            of between 64 and 1518 octets, inclusive, but had either a bad
            Frame Check Sequence (FCS) with an integral number of octets 
            (FCS Error) or a bad FCS with a non-integral number of octets
            (Alignment Error)."
        ::= { zxAnPonOltIfHisMinPerfEntry 44}

    zxAnPonOltIfHMinTxUndersizePkts OBJECT-TYPE
        SYNTAX      Counter64
        MAX-ACCESS  read-only
        STATUS      current
        DESCRIPTION
            "The minutes interval packets transmitted that were
            less than 64 octets long (excluding framing bits,but including
            FCS octets) and were otherwise well
            formed."
        ::= { zxAnPonOltIfHisMinPerfEntry 45}
            
    zxAnPonOltIfHMinTxOversizePkts OBJECT-TYPE
        SYNTAX      Counter64
        MAX-ACCESS  read-only
        STATUS      current
        DESCRIPTION
            "The minutes interval packets transmitted that were
            longer than 1518 octets (excluding framing bits, but including FCS
            octets) and were otherwise well formed."
        ::= { zxAnPonOltIfHisMinPerfEntry 46}
    
    zxAnPonOltIfHMinTxPkts64Octets OBJECT-TYPE
        SYNTAX       Counter64
        MAX-ACCESS   read-only
        STATUS       current
        DESCRIPTION
            "The minutes interval packets (including bad
            packets) transmitted that were 64 octets in length
            (excluding framing bits but including FCS octets)."
        ::= {zxAnPonOltIfHisMinPerfEntry 47 }

    zxAnPonOltIfHMinTx65To127Octs OBJECT-TYPE
        SYNTAX       Counter64
        MAX-ACCESS   read-only
        STATUS       current
        DESCRIPTION
            "The minutes interval packets (including bad
            packets) transmitted that were between 65 and 127 octets in
            length inclusive (excluding framing bits but including FCS octets)."
        ::= {zxAnPonOltIfHisMinPerfEntry 48 }

    zxAnPonOltIfHMinTx128To255Octs OBJECT-TYPE
        SYNTAX       Counter64
        MAX-ACCESS   read-only
        STATUS       current
        DESCRIPTION
            "The minutes interval packets (including bad
            packets) transmitted that were between
            128 and 255 octets in length inclusive
            (excluding framing bits but including FCS octets)."
        ::= {zxAnPonOltIfHisMinPerfEntry 49}

    zxAnPonOltIfHMinTx256To511Octs OBJECT-TYPE
        SYNTAX       Counter64
        MAX-ACCESS   read-only
        STATUS       current
        DESCRIPTION
            "The minutes interval packets (including bad
            packets) transmitted that were between
            256 and 511 octets in length inclusive
            (excluding framing bits but including FCS octets)."
        ::= {zxAnPonOltIfHisMinPerfEntry 50 }

    zxAnPonOltIfHMinTx512To1023Octs OBJECT-TYPE
        SYNTAX       Counter64
        MAX-ACCESS   read-only
        STATUS       current
        DESCRIPTION
            "The minutes interval packets (including bad
            packets) transmitted that were between
            512 and 1023 octets in length inclusive
            (excluding framing bits but including FCS octets)."
        ::= {zxAnPonOltIfHisMinPerfEntry 51 }

    zxAnPonOltIfHMinTx1024To1518Octs OBJECT-TYPE
        SYNTAX       Counter64
        MAX-ACCESS   read-only
        STATUS       current
        DESCRIPTION
            "The minutes interval packets (including bad
            packets) transmitted that were between
            1024 and 1518 octets in length inclusive
            (excluding framing bits but including FCS octets)."
        ::= {zxAnPonOltIfHisMinPerfEntry 52 }
        
    zxAnPonOltIfHMinTxFragments  OBJECT-TYPE
        SYNTAX      Counter64
        MAX-ACCESS  read-only
        STATUS      current
        DESCRIPTION
            "The minutes interval packets transmitted that were less 
            than 64 octets in length (excluding framing bits but including
            FCS octets) and had either a bad Frame Check Sequence
            (FCS) with an integral number of octets (FCS Error) or a
            bad FCS with a non-integral number of octets (Alignment
            Error)."
        ::= { zxAnPonOltIfHisMinPerfEntry 53}
        
    zxAnPonOltIfHMinTxJabbers OBJECT-TYPE
        SYNTAX      Counter64
        MAX-ACCESS  read-only
        STATUS      current
        DESCRIPTION
            "The minutes interval packets transmitted that were
            longer than 1518 octets (excluding framing bits,
            but including FCS octets), and had either a bad
            Frame Check Sequence (FCS) with an integral number
            of octets (FCS Error) or a bad FCS with a non-integral
            number of octets (Alignment Error)."
        ::= { zxAnPonOltIfHisMinPerfEntry 54}
        
    zxAnPonOltIfHMinRxCorrFecCodes OBJECT-TYPE
        SYNTAX      Counter64
        MAX-ACCESS  read-only
        STATUS      current
        DESCRIPTION
            "The minutes interval correct FEC codes received."
        ::= { zxAnPonOltIfHisMinPerfEntry 55}

    zxAnPonOltIfHMinRxErrFecCodes OBJECT-TYPE
        SYNTAX      Counter64
        MAX-ACCESS  read-only
        STATUS      current
        DESCRIPTION
            "The minutes interval errored FEC codes received."
        ::= { zxAnPonOltIfHisMinPerfEntry 56}
            
    zxAnPonOltIfHMinCollisions OBJECT-TYPE
        SYNTAX      Counter64
        MAX-ACCESS  read-only
        STATUS      current
        DESCRIPTION
            "The minutes interval best estimate of collisions
            on this olt interface."
        ::= { zxAnPonOltIfHisMinPerfEntry 70}

    zxAnPonOltIfHMinDropEvents OBJECT-TYPE
        SYNTAX      Counter64
        MAX-ACCESS  read-only
        STATUS      current
        DESCRIPTION
            "The minutes interval events in which packets
            were dropped by the probe due to lack of resources."
        ::= { zxAnPonOltIfHisMinPerfEntry 71}
		
	zxAnPonOltIfHMinTxAvgOctetRate OBJECT-TYPE
        SYNTAX       Gauge32
        UNITS        "Bps"
        MAX-ACCESS   read-only
        STATUS       current
        DESCRIPTION
            "The minutes interval transmitted average octet rate."
        ::= {zxAnPonOltIfHisMinPerfEntry 72 }

--------------------------------------------------------------------------------
--  zxAnPonOltIfHis1DayPerfTable
--------------------------------------------------------------------------------
    zxAnPonOltIfHis1DayPerfTable OBJECT-TYPE
        SYNTAX         SEQUENCE OF ZxAnPonOltIfHis1DayPerfEntry
        MAX-ACCESS     not-accessible
        STATUS         current
        DESCRIPTION
            "The 1 day interval performance data table of PON OLT.
             The 'IfType' of ifIndex supports 1(physical interface) 
             and 5(PON channel)."
        ::= { zxAnPonOltPerfObjects 6 }

    zxAnPonOltIfHis1DayPerfEntry OBJECT-TYPE
        SYNTAX         ZxAnPonOltIfHis1DayPerfEntry
        MAX-ACCESS     not-accessible
        STATUS         current
        DESCRIPTION
            "The 1 day interval performance data entry of interfaces."
        INDEX    { ifIndex,zxAnPonOltIfH1DIntervalNo }
        ::= { zxAnPonOltIfHis1DayPerfTable 1}

    ZxAnPonOltIfHis1DayPerfEntry ::=
        SEQUENCE{
                zxAnPonOltIfH1DIntervalNo             Integer32,
                zxAnPonOltIfH1DValidData              TruthValue,
                zxAnPonOltIfH1DDateAndTime            DateAndTime,
                zxAnPonOltIfH1DRxOctets               Counter64,
                zxAnPonOltIfH1DRxPkts                 Counter64,
                zxAnPonOltIfH1DRxUcastPkts            Counter64,
                zxAnPonOltIfH1DRxNUcastPkts           Counter64,
                zxAnPonOltIfH1DRxMcastPkts            Counter64,
                zxAnPonOltIfH1DRxBcastPkts            Counter64,
                zxAnPonOltIfH1DRxDiscardPkts          Counter64,
                zxAnPonOltIfH1DRxErrPkts              Counter64,
                zxAnPonOltIfH1DRxCrcAlignErrors       Counter64,
                zxAnPonOltIfH1DRxUndersizePkts        Counter64,
                zxAnPonOltIfH1DRxOversizePkts         Counter64,
                zxAnPonOltIfH1DRx64Octs               Counter64,
                zxAnPonOltIfH1DRx65To127Octs          Counter64,
                zxAnPonOltIfH1DRx128To255Octs         Counter64,
                zxAnPonOltIfH1DRx256To511Octs         Counter64,
                zxAnPonOltIfH1DRx512To1023Octs        Counter64,
                zxAnPonOltIfH1DRx1024To1518Octs       Counter64,
                zxAnPonOltIfH1DRxFragments            Counter64,
                zxAnPonOltIfH1DRxJabbers              Counter64,
				zxAnPonOltIfH1DRxAvgOctetRate         Gauge32,
                zxAnPonOltIfH1DTxOctets               Counter64,
                zxAnPonOltIfH1DTxPkts                 Counter64,
                zxAnPonOltIfH1DTxUcastPkts            Counter64,
                zxAnPonOltIfH1DTxNUcastPkts           Counter64,
                zxAnPonOltIfH1DTxMcastPkts            Counter64,
                zxAnPonOltIfH1DTxBcastPkts            Counter64,
                zxAnPonOltIfH1DTxDiscardPkts          Counter64,
                zxAnPonOltIfH1DTxErrPkts              Counter64,
                zxAnPonOltIfH1DTxCrcAlignErrors       Counter64,
                zxAnPonOltIfH1DTxUndersizePkts        Counter64,
                zxAnPonOltIfH1DTxOversizePkts         Counter64,
                zxAnPonOltIfH1DTxPkts64Octets         Counter64,
                zxAnPonOltIfH1DTx65To127Octs          Counter64,
                zxAnPonOltIfH1DTx128To255Octs         Counter64,
                zxAnPonOltIfH1DTx256To511Octs         Counter64,
                zxAnPonOltIfH1DTx512To1023Octs        Counter64,
                zxAnPonOltIfH1DTx1024To1518Octs       Counter64,
                zxAnPonOltIfH1DTxFragments            Counter64,
                zxAnPonOltIfH1DTxJabbers              Counter64,
                zxAnPonOltIfH1DRxCorrFecCodes         Counter64,
                zxAnPonOltIfH1DRxErrFecCodes          Counter64,
                zxAnPonOltIfH1DCollisions             Counter64,                
                zxAnPonOltIfH1DDropEvents             Counter64,
				zxAnPonOltIfH1DTxAvgOctetRate         Gauge32
                }

    zxAnPonOltIfH1DIntervalNo  OBJECT-TYPE 
        SYNTAX      Integer32(1..7)
        MAX-ACCESS  not-accessible
        STATUS      current
        DESCRIPTION     
             "Performance Data 
               
               Interval 1 is the the most recent previous interval
               Interval 7 is 1 week ago.
               Intervals from 2 to 7 are optional."
        ::= { zxAnPonOltIfHis1DayPerfEntry 1 }
        
   zxAnPonOltIfH1DValidData OBJECT-TYPE
        SYNTAX      TruthValue
        MAX-ACCESS  read-only
        STATUS      current
        DESCRIPTION     
             "Performance data valid flag.
              true(1) means valid.
              false(2) means invalid and the performace data is useless."
        ::= { zxAnPonOltIfHis1DayPerfEntry 2}
        
    zxAnPonOltIfH1DDateAndTime     OBJECT-TYPE
        SYNTAX      DateAndTime
        MAX-ACCESS  read-only
        STATUS      current
        DESCRIPTION     
             "1 day performace data interval create time."
        ::= { zxAnPonOltIfHis1DayPerfEntry 3 }
        
    zxAnPonOltIfH1DRxOctets OBJECT-TYPE
        SYNTAX       Counter64
        MAX-ACCESS   read-only
        STATUS       current
        DESCRIPTION
            "The 1 day interval octets of data (including
         those in bad packets) received on the
         network (excluding framing bits but including
         FCS octets)."
        ::= {zxAnPonOltIfHis1DayPerfEntry 4 }

    zxAnPonOltIfH1DRxPkts OBJECT-TYPE
        SYNTAX       Counter64
        MAX-ACCESS   read-only
        STATUS       current
        DESCRIPTION
            "The 1 day interval packets (including bad packets,
         broadcast packets, and multicast packets) received."
        ::= {zxAnPonOltIfHis1DayPerfEntry 5 }

    zxAnPonOltIfH1DRxUcastPkts OBJECT-TYPE
        SYNTAX       Counter64
        MAX-ACCESS   read-only
        STATUS       current
        DESCRIPTION
            "The 1 day interval good packets received that were
         directed to a unicast address."
        ::= {zxAnPonOltIfHis1DayPerfEntry 6 }

    zxAnPonOltIfH1DRxNUcastPkts OBJECT-TYPE
        SYNTAX       Counter64
        MAX-ACCESS   read-only
        STATUS       current
        DESCRIPTION
            "The 1 day interval good packets received that were
         directed to a non-unicast address."
        ::= {zxAnPonOltIfHis1DayPerfEntry 7 }

    zxAnPonOltIfH1DRxMcastPkts OBJECT-TYPE
        SYNTAX       Counter64
        MAX-ACCESS   read-only
        STATUS       current
        DESCRIPTION
            "The 1 day interval good packets received that were
         directed to a multicast address."
        ::= {zxAnPonOltIfHis1DayPerfEntry 8 }

    zxAnPonOltIfH1DRxBcastPkts OBJECT-TYPE
        SYNTAX       Counter64
        MAX-ACCESS   read-only
        STATUS       current
        DESCRIPTION
            "The 1 day interval good packets received that were
         directed to the broadcast address.  Note that this
         does not include multicast packets."
        ::= {zxAnPonOltIfHis1DayPerfEntry 9 }

    zxAnPonOltIfH1DRxDiscardPkts OBJECT-TYPE
        SYNTAX       Counter64
        MAX-ACCESS   read-only
        STATUS       current
        DESCRIPTION
            "The 1 day interval discarded packets received."
        ::= {zxAnPonOltIfHis1DayPerfEntry 10 }

    zxAnPonOltIfH1DRxErrPkts OBJECT-TYPE
        SYNTAX       Counter64
        MAX-ACCESS   read-only
        STATUS       current
        DESCRIPTION
            "The 1 day interval error packets received."
        ::= {zxAnPonOltIfHis1DayPerfEntry 11 }

    zxAnPonOltIfH1DRxCrcAlignErrors OBJECT-TYPE
        SYNTAX       Counter64
        MAX-ACCESS   read-only
        STATUS       current
        DESCRIPTION
            "The 1 day interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOltIfHis1DayPerfEntry 12 }

    zxAnPonOltIfH1DRxUndersizePkts OBJECT-TYPE
        SYNTAX       Counter64
        MAX-ACCESS   read-only
        STATUS       current
        DESCRIPTION
            "The 1 day interval packets received that were
         less than 64 octets long (excluding framing bits,
         but including FCS octets) and were otherwise well
         formed."
        ::= {zxAnPonOltIfHis1DayPerfEntry 13 }

    zxAnPonOltIfH1DRxOversizePkts OBJECT-TYPE
        SYNTAX       Counter64
        MAX-ACCESS   read-only
        STATUS       current
        DESCRIPTION
            "The 1 day interval packets received that were
         longer than 1518 octets (excluding framing bits,
         but including FCS octets) and were otherwise
         well formed."
        ::= {zxAnPonOltIfHis1DayPerfEntry 14 }

    zxAnPonOltIfH1DRx64Octs      OBJECT-TYPE
        SYNTAX       Counter64
        MAX-ACCESS   read-only
        STATUS       current
        DESCRIPTION
            "The 1 day interval packets (including bad
         packets) received that were 64 octets in length
         (excluding framing bits but including FCS octets)."
        ::= {zxAnPonOltIfHis1DayPerfEntry 15 }

    zxAnPonOltIfH1DRx65To127Octs OBJECT-TYPE
        SYNTAX       Counter64
        MAX-ACCESS   read-only
        STATUS       current
        DESCRIPTION
            "The 1 day interval packets (including bad
         packets) received that were between
         65 and 127 octets in length inclusive
         (excluding framing bits but including FCS octets)."
        ::= {zxAnPonOltIfHis1DayPerfEntry 16 }

    zxAnPonOltIfH1DRx128To255Octs OBJECT-TYPE
        SYNTAX       Counter64
        MAX-ACCESS   read-only
        STATUS       current
        DESCRIPTION
            "The 1 day interval packets (including bad
         packets) received that were between
         128 and 255 octets in length inclusive
         (excluding framing bits but including FCS octets)."
        ::= {zxAnPonOltIfHis1DayPerfEntry 17 }

    zxAnPonOltIfH1DRx256To511Octs OBJECT-TYPE
        SYNTAX       Counter64
        MAX-ACCESS   read-only
        STATUS       current
        DESCRIPTION
            "The 1 day interval packets (including bad
         packets) received that were between
         256 and 511 octets in length inclusive
         (excluding framing bits but including FCS octets)."
        ::= {zxAnPonOltIfHis1DayPerfEntry 18 }

    zxAnPonOltIfH1DRx512To1023Octs OBJECT-TYPE
        SYNTAX       Counter64
        MAX-ACCESS   read-only
        STATUS       current
        DESCRIPTION
            "The 1 day interval packets (including bad
         packets) received that were between
         512 and 1023 octets in length inclusive
         (excluding framing bits but including FCS octets)."
        ::= {zxAnPonOltIfHis1DayPerfEntry 19 }

    zxAnPonOltIfH1DRx1024To1518Octs OBJECT-TYPE
        SYNTAX       Counter64
        MAX-ACCESS   read-only
        STATUS       current
        DESCRIPTION
            "The 1 day interval packets (including bad
         packets) received that were between
         1024 and 1518 octets in length inclusive
         (excluding framing bits but including FCS octets)."
        ::= {zxAnPonOltIfHis1DayPerfEntry 20 }
        
    zxAnPonOltIfH1DRxFragments  OBJECT-TYPE
        SYNTAX      Counter64
        MAX-ACCESS  read-only
        STATUS      current
        DESCRIPTION
            "The 1 day interval packets received that were less 
            than 64 octets in length (excluding framing bits but including
         FCS octets) and had either a bad Frame Check Sequence
         (FCS) with an integral number of octets (FCS Error) or a
         bad FCS with a non-integral number of octets (Alignment
         Error)."
        ::= { zxAnPonOltIfHis1DayPerfEntry 21}
        
    zxAnPonOltIfH1DRxJabbers OBJECT-TYPE
        SYNTAX      Counter64
        MAX-ACCESS  read-only
        STATUS      current
        DESCRIPTION
            "The 1 day interval packets received that were
         longer than 1518 octets (excluding framing bits,
         but including FCS octets), and had either a bad
         Frame Check Sequence (FCS) with an integral number
         of octets (FCS Error) or a bad FCS with a non-integral
         number of octets (Alignment Error)."
        ::= { zxAnPonOltIfHis1DayPerfEntry 22}
		
	zxAnPonOltIfH1DRxAvgOctetRate OBJECT-TYPE
        SYNTAX       Gauge32
        UNITS        "Bps"
        MAX-ACCESS   read-only
        STATUS       current
        DESCRIPTION
            "The 1 day interval received average octet rate."
        ::= {zxAnPonOltIfHis1DayPerfEntry 23 }

    zxAnPonOltIfH1DTxOctets OBJECT-TYPE
        SYNTAX       Counter64
        MAX-ACCESS   read-only
        STATUS       current
        DESCRIPTION
            "The 1 day interval octets of data (including
         those in bad packets) sent on the
         network (excluding framing bits but including
         FCS octets)."
        ::= {zxAnPonOltIfHis1DayPerfEntry 36 }

    zxAnPonOltIfH1DTxPkts OBJECT-TYPE
        SYNTAX       Counter64
        MAX-ACCESS   read-only
        STATUS       current
        DESCRIPTION
            "The 1 day interval packets (including bad packets,
         broadcast packets, and multicast packets) transmitted."
        ::= {zxAnPonOltIfHis1DayPerfEntry 37 }

    zxAnPonOltIfH1DTxUcastPkts OBJECT-TYPE
        SYNTAX       Counter64
        MAX-ACCESS   read-only
        STATUS       current
        DESCRIPTION
            "The 1 day interval good packets transmitted that were
         directed to a unicast address."
        ::= {zxAnPonOltIfHis1DayPerfEntry 38 }

    zxAnPonOltIfH1DTxNUcastPkts OBJECT-TYPE
        SYNTAX       Counter64
        MAX-ACCESS   read-only
        STATUS       current
        DESCRIPTION
            "The 1 day interval good packets transmitted that were
         directed to a non-unicast address."
        ::= {zxAnPonOltIfHis1DayPerfEntry 39 }

    zxAnPonOltIfH1DTxMcastPkts OBJECT-TYPE
        SYNTAX       Counter64
        MAX-ACCESS   read-only
        STATUS       current
        DESCRIPTION
            "The 1 day interval good packets transmitted that were
         directed to a multicast address."
        ::= {zxAnPonOltIfHis1DayPerfEntry 40 }

    zxAnPonOltIfH1DTxBcastPkts OBJECT-TYPE
        SYNTAX       Counter64
        MAX-ACCESS   read-only
        STATUS       current
        DESCRIPTION
            "The 1 day interval good packets transmitted that were
         directed to the broadcast address.  Note that this does not include 
         multicast packets."
        ::= {zxAnPonOltIfHis1DayPerfEntry 41 }

    zxAnPonOltIfH1DTxDiscardPkts OBJECT-TYPE
        SYNTAX       Counter64
        MAX-ACCESS   read-only
        STATUS       current
        DESCRIPTION
            "The 1 day interval discarded packets transmitted."
        ::= {zxAnPonOltIfHis1DayPerfEntry 42 }

    zxAnPonOltIfH1DTxErrPkts OBJECT-TYPE
        SYNTAX       Counter64
        MAX-ACCESS   read-only
        STATUS       current
        DESCRIPTION
            "The 1 day interval error packets transmitted."
        ::= {zxAnPonOltIfHis1DayPerfEntry 43 }
        
    zxAnPonOltIfH1DTxCrcAlignErrors OBJECT-TYPE
        SYNTAX      Counter64
        MAX-ACCESS  read-only
        STATUS      current
        DESCRIPTION
            "The 1 day interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOltIfHis1DayPerfEntry 44}

    zxAnPonOltIfH1DTxUndersizePkts OBJECT-TYPE
        SYNTAX      Counter64
        MAX-ACCESS  read-only
        STATUS      current
        DESCRIPTION
            "The 1 day interval packets transmitted that were
         less than 64 octets long (excluding framing bits,but including
         FCS octets) and were otherwise well
         formed."
        ::= { zxAnPonOltIfHis1DayPerfEntry 45}
            
    zxAnPonOltIfH1DTxOversizePkts OBJECT-TYPE
        SYNTAX      Counter64
        MAX-ACCESS  read-only
        STATUS      current
        DESCRIPTION
            "The 1 day interval packets transmitted that were
         longer than 1518 octets (excluding framing bits, but including FCS
         octets) and were otherwise well formed."
        ::= { zxAnPonOltIfHis1DayPerfEntry 46}
    
    zxAnPonOltIfH1DTxPkts64Octets OBJECT-TYPE
        SYNTAX       Counter64
        MAX-ACCESS   read-only
        STATUS       current
        DESCRIPTION
            "The 1 day interval packets (including bad
         packets) transmitted that were 64 octets in length
         (excluding framing bits but including FCS octets)."
        ::= {zxAnPonOltIfHis1DayPerfEntry 47 }

    zxAnPonOltIfH1DTx65To127Octs OBJECT-TYPE
        SYNTAX       Counter64
        MAX-ACCESS   read-only
        STATUS       current
        DESCRIPTION
            "The 1 day interval packets (including bad
         packets) transmitted that were between 65 and 127 octets in
         length inclusive (excluding framing bits but including FCS octets)."
        ::= {zxAnPonOltIfHis1DayPerfEntry 48 }

    zxAnPonOltIfH1DTx128To255Octs OBJECT-TYPE
        SYNTAX       Counter64
        MAX-ACCESS   read-only
        STATUS       current
        DESCRIPTION
            "The 1 day interval packets (including bad
         packets) transmitted that were between
         128 and 255 octets in length inclusive
         (excluding framing bits but including FCS octets)."
        ::= {zxAnPonOltIfHis1DayPerfEntry 49}

    zxAnPonOltIfH1DTx256To511Octs OBJECT-TYPE
        SYNTAX       Counter64
        MAX-ACCESS   read-only
        STATUS       current
        DESCRIPTION
            "The 1 day interval packets (including bad
         packets) transmitted that were between
         256 and 511 octets in length inclusive
         (excluding framing bits but including FCS octets)."
        ::= {zxAnPonOltIfHis1DayPerfEntry 50 }

    zxAnPonOltIfH1DTx512To1023Octs OBJECT-TYPE
        SYNTAX       Counter64
        MAX-ACCESS   read-only
        STATUS       current
        DESCRIPTION
            "The 1 day interval packets (including bad
         packets) transmitted that were between
         512 and 1023 octets in length inclusive
         (excluding framing bits but including FCS octets)."
        ::= {zxAnPonOltIfHis1DayPerfEntry 51 }

    zxAnPonOltIfH1DTx1024To1518Octs OBJECT-TYPE
        SYNTAX       Counter64
        MAX-ACCESS   read-only
        STATUS       current
        DESCRIPTION
            "The 1 day interval packets (including bad
         packets) transmitted that were between
         1024 and 1518 octets in length inclusive
         (excluding framing bits but including FCS octets)."
        ::= {zxAnPonOltIfHis1DayPerfEntry 52 }
        
    zxAnPonOltIfH1DTxFragments  OBJECT-TYPE
        SYNTAX      Counter64
        MAX-ACCESS  read-only
        STATUS      current
        DESCRIPTION
            "The 1 day interval packets transmitted that were less 
            than 64 octets in length (excluding framing bits but including
         FCS octets) and had either a bad Frame Check Sequence
         (FCS) with an integral number of octets (FCS Error) or a
         bad FCS with a non-integral number of octets (Alignment
         Error)."
        ::= { zxAnPonOltIfHis1DayPerfEntry 53}
        
    zxAnPonOltIfH1DTxJabbers OBJECT-TYPE
        SYNTAX      Counter64
        MAX-ACCESS  read-only
        STATUS      current
        DESCRIPTION
            "The 1 day interval packets transmitted that were
         longer than 1518 octets (excluding framing bits,
         but including FCS octets), and had either a bad
         Frame Check Sequence (FCS) with an integral number
         of octets (FCS Error) or a bad FCS with a non-integral
         number of octets (Alignment Error)."
        ::= { zxAnPonOltIfHis1DayPerfEntry 54}
        
    zxAnPonOltIfH1DRxCorrFecCodes OBJECT-TYPE
        SYNTAX      Counter64
        MAX-ACCESS  read-only
        STATUS      current
        DESCRIPTION
            "The 1 day interval correct FEC codes received."
        ::= { zxAnPonOltIfHis1DayPerfEntry 55}

    zxAnPonOltIfH1DRxErrFecCodes OBJECT-TYPE
        SYNTAX      Counter64
        MAX-ACCESS  read-only
        STATUS      current
        DESCRIPTION
            "The 1 day interval errored FEC codes received."
        ::= { zxAnPonOltIfHis1DayPerfEntry 56}
                
    zxAnPonOltIfH1DCollisions OBJECT-TYPE
        SYNTAX      Counter64
        MAX-ACCESS  read-only
        STATUS      current
        DESCRIPTION
            "The 1 day interval best estimate of collisions
         on this olt interface."
        ::= { zxAnPonOltIfHis1DayPerfEntry 70}
        
    zxAnPonOltIfH1DDropEvents OBJECT-TYPE
        SYNTAX      Counter64
        MAX-ACCESS  read-only
        STATUS      current
        DESCRIPTION
            "The 1 day interval events in which packets
         were dropped by the probe due to lack of resources."
        ::= { zxAnPonOltIfHis1DayPerfEntry 71}
		
	zxAnPonOltIfH1DTxAvgOctetRate OBJECT-TYPE
        SYNTAX       Gauge32
        UNITS        "Bps"
        MAX-ACCESS   read-only
        STATUS       current
        DESCRIPTION
            "The 1 day interval transmitted average octet rate."
        ::= {zxAnPonOltIfHis1DayPerfEntry 72 }
            
--------------------------------------------------------------------------------
-- zxAnPonOltPerfAlmPrfTable
--------------------------------------------------------------------------------

    zxAnPonOltPerfAlmPrfTable   OBJECT-TYPE
        SYNTAX      SEQUENCE OF ZxAnPonOltPerfAlmPrfEntry
        MAX-ACCESS  not-accessible
        STATUS      current
        DESCRIPTION 
             "The performance alarm threshold profile 
             list table of interfaces."
        ::= { zxAnPonOltPerfObjects 7 }

    zxAnPonOltPerfAlmPrfEntry   OBJECT-TYPE
        SYNTAX      ZxAnPonOltPerfAlmPrfEntry
        MAX-ACCESS  not-accessible
        STATUS      current
        DESCRIPTION 
            "The performance alarm threshold profile 
            applying entry of interfaces."
        INDEX   { zxAnPonOltPerfAlmPrfName }
        ::= { zxAnPonOltPerfAlmPrfTable 1 }

    ZxAnPonOltPerfAlmPrfEntry ::= SEQUENCE {
        zxAnPonOltPerfAlmPrfName           DisplayString,
        zxAnPonOltPerfAlmPrfRowStatus      RowStatus
        }
        
    zxAnPonOltPerfAlmPrfName  OBJECT-TYPE 
        SYNTAX      DisplayString(SIZE (1 .. 32))
        MAX-ACCESS  not-accessible
        STATUS      current
        DESCRIPTION     
            "The performance alarm threshold profile name."
        ::= { zxAnPonOltPerfAlmPrfEntry 1 }
               
    zxAnPonOltPerfAlmPrfRowStatus  OBJECT-TYPE 
        SYNTAX      RowStatus                     
        MAX-ACCESS  read-create                   
        STATUS      current                       
        DESCRIPTION                               
            "The status of this conceptual row.   
                                                  
             The supported actions of this conceptual row only include:
             'createAndGo' and 'destroy'.         
                                              
             To create a row in this table, a manager must
             set this object to createAndGo(4).                                              
                                                                                             
             To delete a row in this table, a manager must                                   
             set this object to destroy(6).                                                  
                                                                                             
             To query this object, always return 1."                                         
        ::= { zxAnPonOltPerfAlmPrfEntry 50 }                                                

--------------------------------------------------------------------------------
-- zxAnPonOltPerfAlmPrfConfTable
--------------------------------------------------------------------------------
    zxAnPonOltPerfAlmPrfConfTable   OBJECT-TYPE
        SYNTAX      SEQUENCE OF ZxAnPonOltPerfAlmPrfConfEntry
        MAX-ACCESS  not-accessible
        STATUS      current
        DESCRIPTION 
             "The performance alarm threshold profile table of interfaces."
        ::= { zxAnPonOltPerfObjects 8 }

    zxAnPonOltPerfAlmPrfConfEntry   OBJECT-TYPE
        SYNTAX      ZxAnPonOltPerfAlmPrfConfEntry
        MAX-ACCESS  not-accessible
        STATUS      current
        DESCRIPTION 
            "An entry in zxAnPonOltPerfAlmPrfConfTable.
            When a manager wants to create or modify an OLT performance 
            alarm threshold item,it must comply with the multi-variables 
            usage rule that all the mib variables related to same 
            fuction must be in one snmp set operation, the variables have
            only one type: mandatory.
            
            Mandatory variables must be in the one snmp set operation.
                   
            To create an OLT performance alarm threshold item on
            different level, alarm threshold ,restore threshold and 
            zxAnPonOltPerfAlmConfRowStatus should be in one snmp set operation.
            The alarm threshold and restore threshold variables in the 
            one snmp set operationshould be on same level.
            Such as:
            zxAnPonOltPerfRiseAlmThresh and zxAnPonOltPerfRiseAlmClrThresh,
            zxAnPonOltPerfRiseWarnThresh and zxAnPonOltPerfRiseWarnClrThresh,
            zxAnPonOltPerfFallWarnThresh and zxAnPonOltPerfFallWarnClrThresh,
            zxAnPonOltPerfFallAlmThresh and zxAnPonOltPerfFallAlmClrThresh.
            
            To modify an OLT performance alarm threshold item on
            different level,alarm threshold and restore threshold
            should be also in the one snmp set 
            operation regardless of modifying alarm or restore threshold 
            value alone.
            The alarm threshold and restore threshold variables in the 
            one snmp set operationshould be on same level.
            Such as:
            zxAnPonOltPerfRiseAlmThresh and zxAnPonOltPerfRiseAlmClrThresh,
            zxAnPonOltPerfRiseWarnThresh and zxAnPonOltPerfRiseWarnClrThresh,
            zxAnPonOltPerfFallWarnThresh and zxAnPonOltPerfFallWarnClrThresh,
            zxAnPonOltPerfFallAlmThresh and zxAnPonOltPerfFallAlmClrThresh.
            
            To remove an OLT performance alarm threshold item, only 
            zxAnPonOltPerfAlmConfRowStatus should be set to destroy(6) while 
            all levels of this ONU performance alarm threshold item will be 
            removed."
        INDEX   { zxAnPonOltPerfAlmPrfName, zxAnPonOltPerfVariable }
        ::= { zxAnPonOltPerfAlmPrfConfTable 1 }

    ZxAnPonOltPerfAlmPrfConfEntry ::= SEQUENCE {
        zxAnPonOltPerfVariable                OBJECT IDENTIFIER,
        zxAnPonOltPerfRiseAlmThresh           HCPerfCurrentCount,
        zxAnPonOltPerfRiseAlmClrThresh        HCPerfCurrentCount,
        zxAnPonOltPerfRiseWarnThresh          HCPerfCurrentCount,
        zxAnPonOltPerfRiseWarnClrThresh       HCPerfCurrentCount,
        zxAnPonOltPerfFallWarnThresh          HCPerfCurrentCount,
        zxAnPonOltPerfFallWarnClrThresh       HCPerfCurrentCount,
        zxAnPonOltPerfFallAlmThresh           HCPerfCurrentCount,
        zxAnPonOltPerfFallAlmClrThresh        HCPerfCurrentCount,
        zxAnPonOltPerfThreshUsed              BITS,
        zxAnPonOltPerfAlmConfRowStatus        RowStatus
        }

    zxAnPonOltPerfVariable  OBJECT-TYPE 
        SYNTAX      OBJECT IDENTIFIER
        MAX-ACCESS  not-accessible
        STATUS      current
        DESCRIPTION     
            "The object identifier of performance variables."
        ::= { zxAnPonOltPerfAlmPrfConfEntry 1 }
        
    zxAnPonOltPerfRiseAlmThresh  OBJECT-TYPE 
        SYNTAX      HCPerfCurrentCount
        MAX-ACCESS  read-create
        STATUS      current
        DESCRIPTION     
            "The threshold for rising alarm."
        ::= { zxAnPonOltPerfAlmPrfConfEntry 2 }

    zxAnPonOltPerfRiseAlmClrThresh  OBJECT-TYPE 
        SYNTAX      HCPerfCurrentCount
        MAX-ACCESS  read-create
        STATUS      current
        DESCRIPTION     
            "The threshold for rising alarm restore."
        ::= { zxAnPonOltPerfAlmPrfConfEntry 3 }

    zxAnPonOltPerfRiseWarnThresh  OBJECT-TYPE 
        SYNTAX      HCPerfCurrentCount
        MAX-ACCESS  read-create
        STATUS      current
        DESCRIPTION     
            "The threshold for rising warning."
        ::= { zxAnPonOltPerfAlmPrfConfEntry 4 }

    zxAnPonOltPerfRiseWarnClrThresh  OBJECT-TYPE 
        SYNTAX      HCPerfCurrentCount
        MAX-ACCESS  read-create
        STATUS      current
        DESCRIPTION     
            "The threshold for rising warning restore."
        ::= { zxAnPonOltPerfAlmPrfConfEntry 5 }
        
    zxAnPonOltPerfFallWarnThresh  OBJECT-TYPE 
        SYNTAX      HCPerfCurrentCount
        MAX-ACCESS  read-create
        STATUS      current
        DESCRIPTION     
            "The threshold for falling warning."
        ::= { zxAnPonOltPerfAlmPrfConfEntry 6 }

    zxAnPonOltPerfFallWarnClrThresh  OBJECT-TYPE 
        SYNTAX      HCPerfCurrentCount
        MAX-ACCESS  read-create
        STATUS      current
        DESCRIPTION     
            "The threshold for falling warning restore."
        ::= { zxAnPonOltPerfAlmPrfConfEntry 7 }
        
    zxAnPonOltPerfFallAlmThresh  OBJECT-TYPE 
        SYNTAX      HCPerfCurrentCount
        MAX-ACCESS  read-create
        STATUS      current
        DESCRIPTION     
            "The threshold for falling alarm."
        ::= { zxAnPonOltPerfAlmPrfConfEntry 8 }

    zxAnPonOltPerfFallAlmClrThresh  OBJECT-TYPE 
        SYNTAX      HCPerfCurrentCount
        MAX-ACCESS  read-create
        STATUS      current
        DESCRIPTION     
            "The threshold for falling alarm restore."
        ::= { zxAnPonOltPerfAlmPrfConfEntry 9 }   
                    
    zxAnPonOltPerfThreshUsed  OBJECT-TYPE 
         SYNTAX     BITS{
                    riseAlmThresh(0),
                    riseAlmClrThresh(1),
                    riseWarnThresh(2),
                    riseWarnClrThresh(3),
                    fallWarnThresh(4),
                    fallWarnClrThresh(5),
                    fallAlmThresh(6),
                    fallAlmClrThresh(7)
                    }             
        MAX-ACCESS  read-create
        STATUS      current
        DESCRIPTION     
            "The threshold used flag for falling alarm restore."
        ::= { zxAnPonOltPerfAlmPrfConfEntry 10 }
        
    zxAnPonOltPerfAlmConfRowStatus  OBJECT-TYPE
        SYNTAX      RowStatus
        MAX-ACCESS  read-create
        STATUS      current
        DESCRIPTION     
            "The status of this conceptual row. 
            
             The supported actions of this conceptual row only include:
            'createAndGo' and 'destroy'.
             
             To create a row in this table, a manager must
             set this object to createAndGo(4).
             
             To delete a row in this table, a manager must
             set this object to destroy(6).
             
             To query this object, always return 1."
        ::= { zxAnPonOltPerfAlmPrfConfEntry 50 }
        
--------------------------------------------------------------------------------
-- zxAnPonOltPerfAlmPrfApplyTable
--------------------------------------------------------------------------------

    zxAnPonOltPerfAlmPrfApplyTable   OBJECT-TYPE
        SYNTAX      SEQUENCE OF ZxAnPonOltPerfAlmPrfApplyEntry
        MAX-ACCESS  not-accessible
        STATUS      current
        DESCRIPTION 
             "The performance alarm threshold profile applying table of 
              interfaces.
              The 'IfType' of ifIndex supports 1(physical interface) 
              and 5(PON channel)."
        ::= { zxAnPonOltPerfObjects 9 }

    zxAnPonOltPerfAlmPrfApplyEntry   OBJECT-TYPE
        SYNTAX      ZxAnPonOltPerfAlmPrfApplyEntry
        MAX-ACCESS  not-accessible
        STATUS      current
        DESCRIPTION 
            " An entry in zxAnPonOltPerfAlmPrfApplyTable.
            When a manager wants to apply an OLT performance alarm 
            profile to specificed OLT interface,it must comply with 
            the multi-variables usage rule that all the mib variables 
            related to same fuction must be in one snmp set operation, 
            the variables have only one type: mandatory.
            
            Mandatory variables must be in the one snmp set operation.
                   
            To apply an OLT performance alarm profile to specificed OLT 
            interface, 'zxAnPonOltPerfAlmPrf' and 
            'zxAnPonOltAlmPrfApplyRowStatus' should be in the one snmp set 
            operation.
            To remove the application of an OLT performance alarm profile to 
            the specificed OLT interface, only 
            'zxAnPonOltAlmPrfApplyRowStatus' should be set to destroy(6)."
        INDEX   { ifIndex}
        ::= { zxAnPonOltPerfAlmPrfApplyTable 1 }

    ZxAnPonOltPerfAlmPrfApplyEntry ::= SEQUENCE {
        zxAnPonOltPerfAlmPrf            DisplayString,
        zxAnPonOltAlmPrfApplyRowStatus  RowStatus
        }
        
    zxAnPonOltPerfAlmPrf  OBJECT-TYPE 
        SYNTAX      DisplayString(SIZE (1 .. 32))
        MAX-ACCESS  read-create
        STATUS      current
        DESCRIPTION     
            "The performance alarm threshold profile."
        ::= { zxAnPonOltPerfAlmPrfApplyEntry 1 }
               
    zxAnPonOltAlmPrfApplyRowStatus  OBJECT-TYPE 
        SYNTAX      RowStatus
        MAX-ACCESS  read-create
        STATUS      current
        DESCRIPTION     
            "The status of this conceptual row. 
              
             The supported actions of this conceptual row only include:
             'createAndGo' and 'destroy'.

             To create a row in this table, a manager must
             set this object to createAndGo(4).
            
             To delete a row in this table, a manager must
             set this object to destroy(6).
             
             To query this object, always return 1."
        ::= { zxAnPonOltPerfAlmPrfApplyEntry 50 }  

--------------------------------------------------------------------------------
-- zxAnPonOnuPerfObjects
--------------------------------------------------------------------------------                
--------------------------------------------------------------------------------
--  ONU Interface Perforamance Table
--------------------------------------------------------------------------------
    zxAnPonOnuIfCurrPerfTable OBJECT-TYPE
        SYNTAX         SEQUENCE OF ZxAnPonOnuIfCurrPerfEntry
        MAX-ACCESS     not-accessible
        STATUS         current
        DESCRIPTION
            "PON ONU interface statistics table"
        ::= { zxAnPonOnuPerfObjects 2 }

    zxAnPonOnuIfCurrPerfEntry OBJECT-TYPE
        SYNTAX         ZxAnPonOnuIfCurrPerfEntry
        MAX-ACCESS     not-accessible
        STATUS         current
        DESCRIPTION
            "Entry of zxAnPonOnuIfCurrPerfTable."
        INDEX    { ifIndex,zxAnPonOnuIndex }
        ::= { zxAnPonOnuIfCurrPerfTable 1}

    ZxAnPonOnuIfCurrPerfEntry ::=
        SEQUENCE{
                zxAnPonOnuIfRxOctets               Counter64,
                zxAnPonOnuIfRxPkts                 Counter64,
                zxAnPonOnuIfRxOctetRate            Gauge32,
                zxAnPonOnuIfRxPktRate              Gauge32,
                zxAnPonOnuIfRxOctetPeakRate        Gauge32,
                zxAnPonOnuIfRxPktPeakRate          Gauge32,
                zxAnPonOnuIfRxUcastPkts            Counter64,
                zxAnPonOnuIfRxNUcastPkts           Counter64,
                zxAnPonOnuIfRxMcastPkts            Counter64,
                zxAnPonOnuIfRxBcastPkts            Counter64,
                zxAnPonOnuIfRxDiscardPkts          Counter64,
                zxAnPonOnuIfRxErrPkts              Counter64,
                zxAnPonOnuIfRxPdr                  Unsigned32,
                zxAnPonOnuIfRxPer                  Unsigned32,
                zxAnPonOnuIfRxCrcAlignErrors       Counter64,
                zxAnPonOnuIfRxUndersizePkts        Counter64,
                zxAnPonOnuIfRxOversizePkts         Counter64,
                zxAnPonOnuIfRxPkts64Octets         Counter64,
                zxAnPonOnuIfRxPkts65To127Octets    Counter64,
                zxAnPonOnuIfRxPkts128To255Octets   Counter64,
                zxAnPonOnuIfRxPkts256To511Octets   Counter64,
                zxAnPonOnuIfRxPkts512To1023Oct     Counter64,
                zxAnPonOnuIfRxPkts1024To1518Oct    Counter64,
                zxAnPonOnuIfRxBwUtilization        Unsigned32,
                zxAnPonOnuIfRxAvgBwUtilization     Unsigned32,
                zxAnPonOnuIfRxFragments            Counter64,
                zxAnPonOnuIfRxJabbers              Counter64,
                zxAnPonOnuIfTxOctets               Counter64,
                zxAnPonOnuIfTxPkts                 Counter64,
                zxAnPonOnuIfTxOctetRate            Gauge32,
                zxAnPonOnuIfTxPktRate              Gauge32,
                zxAnPonOnuIfTxOctetPeakRate        Gauge32,
                zxAnPonOnuIfTxPktPeakRate          Gauge32,
                zxAnPonOnuIfTxUcastPkts            Counter64,
                zxAnPonOnuIfTxNUcastPkts           Counter64,
                zxAnPonOnuIfTxMcastPkts            Counter64,
                zxAnPonOnuIfTxBcastPkts            Counter64,
                zxAnPonOnuIfTxDiscardPkts          Counter64,
                zxAnPonOnuIfTxErrPkts              Counter64,
                zxAnPonOnuIfTxPdr                  Unsigned32,
                zxAnPonOnuIfTxPer                  Unsigned32,
                zxAnPonOnuIfTxCrcAlignErrors       Counter64,
                zxAnPonOnuIfTxUndersizePkts        Counter64,
                zxAnPonOnuIfTxOversizePkts         Counter64,
                zxAnPonOnuIfTxPkts64Octets         Counter64,
                zxAnPonOnuIfTxPkts65To127Octets    Counter64,
                zxAnPonOnuIfTxPkts128To255Octets   Counter64,
                zxAnPonOnuIfTxPkts256To511Octets   Counter64,
                zxAnPonOnuIfTxPkts512To1023Oct     Counter64,
                zxAnPonOnuIfTxPkts1024To1518Oct    Counter64,
                zxAnPonOnuIfTxBwUtilization        Unsigned32,
                zxAnPonOnuIfTxAvgBwUtilization     Unsigned32,
                zxAnPonOnuIfTxFragments            Counter64,
                zxAnPonOnuIfTxJabbers              Counter64,
                zxAnPonOnuIfCollisions             Counter64,
                zxAnPonOnuIfDropEvents             Counter64,
                zxAnPonOnuIfCurrPerfCapability     BITS,
                zxAnPonOnuIfCurrPerfReset          INTEGER
                }

    zxAnPonOnuIfRxOctets OBJECT-TYPE
        SYNTAX       Counter64
        MAX-ACCESS   read-only
        STATUS       current
        DESCRIPTION
            "Received octets."
        ::= {zxAnPonOnuIfCurrPerfEntry 1 }

    zxAnPonOnuIfRxPkts OBJECT-TYPE
        SYNTAX       Counter64
        MAX-ACCESS   read-only
        STATUS       current
        DESCRIPTION
            "Received packets."
        ::= {zxAnPonOnuIfCurrPerfEntry 2 }

    zxAnPonOnuIfRxOctetRate OBJECT-TYPE
        SYNTAX       Gauge32
        UNITS        "Bps"
        MAX-ACCESS   read-only
        STATUS       current
        DESCRIPTION
            "Received bytes per second."
        ::= {zxAnPonOnuIfCurrPerfEntry 3 }

    zxAnPonOnuIfRxPktRate OBJECT-TYPE
        SYNTAX       Gauge32
        UNITS        "pps"  
        MAX-ACCESS   read-only
        STATUS       current
        DESCRIPTION
            "Received packets per second."
        ::= {zxAnPonOnuIfCurrPerfEntry 4 }

    zxAnPonOnuIfRxOctetPeakRate OBJECT-TYPE
        SYNTAX       Gauge32
        UNITS        "Bps" 
        MAX-ACCESS   read-only
        STATUS       current
        DESCRIPTION
            "Peak rate of received octets."
        ::= {zxAnPonOnuIfCurrPerfEntry 5 }

    zxAnPonOnuIfRxPktPeakRate OBJECT-TYPE
        SYNTAX       Gauge32
        UNITS        "pps"  
        MAX-ACCESS   read-only
        STATUS       current
        DESCRIPTION
            "Peak rate of received packets."
        ::= {zxAnPonOnuIfCurrPerfEntry 6 }

    zxAnPonOnuIfRxUcastPkts OBJECT-TYPE
        SYNTAX       Counter64
        MAX-ACCESS   read-only
        STATUS       current
        DESCRIPTION
            "Received unicast packets."
        ::= {zxAnPonOnuIfCurrPerfEntry 7 }

    zxAnPonOnuIfRxNUcastPkts OBJECT-TYPE
        SYNTAX       Counter64
        MAX-ACCESS   read-only
        STATUS       current
        DESCRIPTION
            "Received non-unicast packets."
        ::= {zxAnPonOnuIfCurrPerfEntry 8 }

    zxAnPonOnuIfRxMcastPkts OBJECT-TYPE
        SYNTAX       Counter64
        MAX-ACCESS   read-only
        STATUS       current
        DESCRIPTION
            "Received multicast packets."
        ::= {zxAnPonOnuIfCurrPerfEntry 9 }

    zxAnPonOnuIfRxBcastPkts OBJECT-TYPE
        SYNTAX       Counter64
        MAX-ACCESS   read-only
        STATUS       current
        DESCRIPTION
            "Received broadcast packets."
        ::= {zxAnPonOnuIfCurrPerfEntry 10 }

    zxAnPonOnuIfRxDiscardPkts OBJECT-TYPE
        SYNTAX       Counter64
        MAX-ACCESS   read-only
        STATUS       current
        DESCRIPTION
            "Received discarded packets."
        ::= {zxAnPonOnuIfCurrPerfEntry 11 }

    zxAnPonOnuIfRxErrPkts OBJECT-TYPE
        SYNTAX       Counter64
        MAX-ACCESS   read-only
        STATUS       current
        DESCRIPTION
            "Received errored packets."
        ::= {zxAnPonOnuIfCurrPerfEntry 12 }

    zxAnPonOnuIfRxPdr OBJECT-TYPE
        SYNTAX       Unsigned32
        MAX-ACCESS   read-only
        STATUS       current
        DESCRIPTION
            "Received packets drop ratio, in 10^-9 granularity."
        ::= {zxAnPonOnuIfCurrPerfEntry 13 }

    zxAnPonOnuIfRxPer OBJECT-TYPE
        SYNTAX       Unsigned32
        MAX-ACCESS   read-only
        STATUS       current
        DESCRIPTION
            "Received packets error ratio, in 10^-9 granularity."
        ::= {zxAnPonOnuIfCurrPerfEntry 14 }

    zxAnPonOnuIfRxCrcAlignErrors OBJECT-TYPE
        SYNTAX       Counter64
        MAX-ACCESS   read-only
        STATUS       current
        DESCRIPTION
            "The total number of packets received that
            had a length (excluding framing bits, but
            including FCS octets) of between 64 and 1518
            octets, inclusive, but but had either a bad
            Frame Check Sequence (FCS) with an integral
            number of octets (FCS Error) or a bad FCS with
            a non-integral number of octets (Alignment Error)."
        ::= {zxAnPonOnuIfCurrPerfEntry 15 }

    zxAnPonOnuIfRxUndersizePkts OBJECT-TYPE
        SYNTAX       Counter64
        MAX-ACCESS   read-only
        STATUS       current
        DESCRIPTION
            "The total number of packets received that were
            less than 64 octets long (excluding framing bits,
            but including FCS octets) and were otherwise well
            formed."
        ::= {zxAnPonOnuIfCurrPerfEntry 16 }

    zxAnPonOnuIfRxOversizePkts OBJECT-TYPE
        SYNTAX       Counter64
        MAX-ACCESS   read-only
        STATUS       current
        DESCRIPTION
            "The total number of packets received that were
            longer than 1518 octets (excluding framing bits,
            but including FCS octets) and were otherwise
            well formed."
        ::= {zxAnPonOnuIfCurrPerfEntry 17 }     

    zxAnPonOnuIfRxPkts64Octets      OBJECT-TYPE
        SYNTAX       Counter64
        MAX-ACCESS   read-only
        STATUS       current
        DESCRIPTION
            "The total number of packets (including bad
            packets) received that were 64 octets in length
            (excluding framing bits but including FCS octets)."
        ::= {zxAnPonOnuIfCurrPerfEntry 18 }

    zxAnPonOnuIfRxPkts65To127Octets OBJECT-TYPE
        SYNTAX       Counter64
        MAX-ACCESS   read-only
        STATUS       current
        DESCRIPTION
            "The total number of packets (including bad
            packets) received that were between 65 and 127 octets 
            in length (excluding framing bits but including FCS octets)."
        ::= {zxAnPonOnuIfCurrPerfEntry 19 }

    zxAnPonOnuIfRxPkts128To255Octets OBJECT-TYPE
        SYNTAX       Counter64
        MAX-ACCESS   read-only
        STATUS       current
        DESCRIPTION
            "The total number of packets (including bad
            packets) received that were between 128 and 255 octets 
            in length (excluding framing bits but including FCS octets)."
        ::= {zxAnPonOnuIfCurrPerfEntry 20 }

    zxAnPonOnuIfRxPkts256To511Octets OBJECT-TYPE
        SYNTAX       Counter64
        MAX-ACCESS   read-only
        STATUS       current
        DESCRIPTION
            "The total number of packets (including bad
            packets) received that were between 256 and 511 octets in length
            (excluding framing bits but including FCS octets)."
        ::= {zxAnPonOnuIfCurrPerfEntry 21 }

    zxAnPonOnuIfRxPkts512To1023Oct OBJECT-TYPE
        SYNTAX       Counter64
        MAX-ACCESS   read-only
        STATUS       current
        DESCRIPTION
            "The total number of packets (including bad
            packets) received that were between 512 and 1023 octets in length
            (excluding framing bits but including FCS octets)."
        ::= {zxAnPonOnuIfCurrPerfEntry 22 }

    zxAnPonOnuIfRxPkts1024To1518Oct OBJECT-TYPE
        SYNTAX       Counter64
        MAX-ACCESS   read-only
        STATUS       current
        DESCRIPTION
             "The total number of packets (including bad
             packets) received that were between 1024 and 1518 octets in length
             (excluding framing bits but including FCS octets)."
        ::= {zxAnPonOnuIfCurrPerfEntry 23 }

    zxAnPonOnuIfRxBwUtilization OBJECT-TYPE
        SYNTAX       Unsigned32
        UNITS        "0.1 percent"
        MAX-ACCESS   read-only
        STATUS       current
        DESCRIPTION
            "Received bandwidth throughput."
        ::= {zxAnPonOnuIfCurrPerfEntry 24 }

    zxAnPonOnuIfRxAvgBwUtilization OBJECT-TYPE
        SYNTAX       Unsigned32
        UNITS        "0.1 percent"
        MAX-ACCESS   read-only
        STATUS       current
        DESCRIPTION
            "Received average bandwidth utilization."
        ::= {zxAnPonOnuIfCurrPerfEntry 25 }
        
    zxAnPonOnuIfRxFragments  OBJECT-TYPE
        SYNTAX      Counter64
        MAX-ACCESS  read-only
        STATUS      current
        DESCRIPTION
            "The total number of packets received that were less than
         64 octets in length (excluding framing bits but including
         FCS octets) and had either a bad Frame Check Sequence
         (FCS) with an integral number of octets (FCS Error) or a
         bad FCS with a non-integral number of octets (Alignment
         Error).

         Note that it is entirely normal for zxAnPonOnuIfRxFragments
          to increment.  This is because it counts both runts (which are
         normal occurrences due to collisions) and noise hits."
        ::= { zxAnPonOnuIfCurrPerfEntry 26}
        
    zxAnPonOnuIfRxJabbers OBJECT-TYPE
        SYNTAX      Counter64
        MAX-ACCESS  read-only
        STATUS      current
        DESCRIPTION
            "The total number of packets received that were
         longer than 1518 octets (excluding framing bits,
         but including FCS octets), and had either a bad
         Frame Check Sequence (FCS) with an integral number
         of octets (FCS Error) or a bad FCS with a non-integral
         number of octets (Alignment Error).

         Note that this definition of jabber is different
         than the definition in IEEE-802.3 section 8.2.1.5
         (10BASE5) and section 10.3.1.4 (10BASE2).  These
         documents define jabber as the condition where any
         packet exceeds 20 ms.  The allowed range to detect
         jabber is between 20 ms and 150 ms."
        ::= { zxAnPonOnuIfCurrPerfEntry 27}

    zxAnPonOnuIfTxOctets OBJECT-TYPE
        SYNTAX       Counter64
        MAX-ACCESS   read-only
        STATUS       current
        DESCRIPTION
            "Transmitted octets."
        ::= {zxAnPonOnuIfCurrPerfEntry 44 }

    zxAnPonOnuIfTxPkts OBJECT-TYPE
        SYNTAX       Counter64
        MAX-ACCESS   read-only
        STATUS       current
        DESCRIPTION
            "Transmitted packets."
        ::= {zxAnPonOnuIfCurrPerfEntry 45 }

    zxAnPonOnuIfTxOctetRate OBJECT-TYPE
        SYNTAX       Gauge32
        UNITS        "Bps"
        MAX-ACCESS   read-only
        STATUS       current
        DESCRIPTION
            "Transmitted rate of octets."
        ::= {zxAnPonOnuIfCurrPerfEntry 46 }

    zxAnPonOnuIfTxPktRate OBJECT-TYPE
        SYNTAX       Gauge32
        UNITS        "pps"
        MAX-ACCESS   read-only
        STATUS       current
        DESCRIPTION
            "Transmitted rate of packets."
        ::= {zxAnPonOnuIfCurrPerfEntry 47 }

    zxAnPonOnuIfTxOctetPeakRate OBJECT-TYPE
        SYNTAX       Gauge32
        UNITS        "Bps"
        MAX-ACCESS   read-only
        STATUS       current
        DESCRIPTION
            "Transmitted peak rate of octets."
        ::= {zxAnPonOnuIfCurrPerfEntry 48 }

    zxAnPonOnuIfTxPktPeakRate  OBJECT-TYPE
        SYNTAX       Gauge32
        UNITS        "pps"
        MAX-ACCESS   read-only
        STATUS       current
        DESCRIPTION
            "Transmitted peak rate of packets."
        ::= {zxAnPonOnuIfCurrPerfEntry 49 }

    zxAnPonOnuIfTxUcastPkts OBJECT-TYPE
        SYNTAX       Counter64
        MAX-ACCESS   read-only
        STATUS       current
        DESCRIPTION
            "Transmitted unicast packets."
        ::= {zxAnPonOnuIfCurrPerfEntry 50 }

    zxAnPonOnuIfTxNUcastPkts OBJECT-TYPE
        SYNTAX       Counter64
        MAX-ACCESS   read-only
        STATUS       current
        DESCRIPTION
            "Transmitted non-unicast packets."
        ::= {zxAnPonOnuIfCurrPerfEntry 51 }

    zxAnPonOnuIfTxMcastPkts OBJECT-TYPE
        SYNTAX       Counter64
        MAX-ACCESS   read-only
        STATUS       current
        DESCRIPTION
            "Transmitted multicast packets."
        ::= {zxAnPonOnuIfCurrPerfEntry 52 }

    zxAnPonOnuIfTxBcastPkts OBJECT-TYPE
        SYNTAX       Counter64
        MAX-ACCESS   read-only
        STATUS       current
        DESCRIPTION
            "Transmitted broadcast packets."
        ::= {zxAnPonOnuIfCurrPerfEntry 53 }

    zxAnPonOnuIfTxDiscardPkts OBJECT-TYPE
        SYNTAX       Counter64
        MAX-ACCESS   read-only
        STATUS       current
        DESCRIPTION
            "Transmitted discarded packets."
        ::= {zxAnPonOnuIfCurrPerfEntry 54 }

    zxAnPonOnuIfTxErrPkts OBJECT-TYPE
        SYNTAX       Counter64
        MAX-ACCESS   read-only
        STATUS       current
        DESCRIPTION
            "Transmitted error packets."
        ::= {zxAnPonOnuIfCurrPerfEntry 55 }

    zxAnPonOnuIfTxPdr OBJECT-TYPE
        SYNTAX       Unsigned32
        MAX-ACCESS   read-only
        STATUS       current
        DESCRIPTION
            "Transmitted packets drop ratio, in 10^-9 granularity."
        ::= {zxAnPonOnuIfCurrPerfEntry 56 }

    zxAnPonOnuIfTxPer OBJECT-TYPE
        SYNTAX       Unsigned32
        MAX-ACCESS   read-only
        STATUS       current
        DESCRIPTION
            "Transmitted packets error ratio, in 10^-9 granularity."
        ::= {zxAnPonOnuIfCurrPerfEntry 57 }
        
    zxAnPonOnuIfTxCrcAlignErrors OBJECT-TYPE
        SYNTAX      Counter64
        MAX-ACCESS  read-only
        STATUS      current
        DESCRIPTION
            "The total number of packets sent that
         had a length (excluding framing bits, but
         including FCS octets) of between 64 and 1518
         octets, inclusive, but had either a bad
         Frame Check Sequence (FCS) with an integral
         number of octets (FCS Error) or a bad FCS with
         a non-integral number of octets (Alignment Error)."
        ::= { zxAnPonOnuIfCurrPerfEntry 58}

    zxAnPonOnuIfTxUndersizePkts OBJECT-TYPE
        SYNTAX      Counter64
        MAX-ACCESS  read-only
        STATUS      current
        DESCRIPTION
            "The total number of packets sent that were
         less than 64 octets long (excluding framing bits,
         but including FCS octets) and were otherwise well
         formed."
        ::= { zxAnPonOnuIfCurrPerfEntry 59}
            
    zxAnPonOnuIfTxOversizePkts OBJECT-TYPE
        SYNTAX      Counter64
        MAX-ACCESS  read-only
        STATUS      current
        DESCRIPTION
            "The total number of packets sent that were
         longer than 1518 octets (excluding framing bits,
         but including FCS octets) and were otherwise
         well formed."
        ::= { zxAnPonOnuIfCurrPerfEntry 60}
    
    zxAnPonOnuIfTxPkts64Octets OBJECT-TYPE
        SYNTAX       Counter64
        MAX-ACCESS   read-only
        STATUS       current
        DESCRIPTION
            "The total number of packets (including bad
            packets) transmitted that were 64 octets in length
            excluding framing bits but including FCS octets)."
        ::= {zxAnPonOnuIfCurrPerfEntry 61 }

    zxAnPonOnuIfTxPkts65To127Octets OBJECT-TYPE
        SYNTAX       Counter64
        MAX-ACCESS   read-only
        STATUS       current
        DESCRIPTION
            "The total number of packets 
             transmitted that were between 65 and 127 octets in length."
        ::= {zxAnPonOnuIfCurrPerfEntry 62 }

    zxAnPonOnuIfTxPkts128To255Octets OBJECT-TYPE
        SYNTAX       Counter64
        MAX-ACCESS   read-only
        STATUS       current
        DESCRIPTION
            "The total number of packets 
            transmitted that were between 128 and 255 octets in length."
        ::= {zxAnPonOnuIfCurrPerfEntry 63}

    zxAnPonOnuIfTxPkts256To511Octets OBJECT-TYPE
        SYNTAX       Counter64
        MAX-ACCESS   read-only
        STATUS       current
        DESCRIPTION
            "The total number of packets 
            transmitted that were between 256 and 511 octets in length."
        ::= {zxAnPonOnuIfCurrPerfEntry 64 }

    zxAnPonOnuIfTxPkts512To1023Oct OBJECT-TYPE
        SYNTAX       Counter64
        MAX-ACCESS   read-only
        STATUS       current
        DESCRIPTION
            "The total number of packets 
            transmitted that were between 512 and 1023 octets in length."
        ::= {zxAnPonOnuIfCurrPerfEntry 65 }

    zxAnPonOnuIfTxPkts1024To1518Oct OBJECT-TYPE
        SYNTAX       Counter64
        MAX-ACCESS   read-only
        STATUS       current
        DESCRIPTION
            "The total number of packets 
            transmitted that were between 1024 and 1518 octets in length."
        ::= {zxAnPonOnuIfCurrPerfEntry 66 }

    zxAnPonOnuIfTxBwUtilization OBJECT-TYPE
        SYNTAX       Unsigned32
        UNITS        "0.1 percent"
        MAX-ACCESS   read-only
        STATUS       current
        DESCRIPTION
            "Transmitted bandwidth throughput."
        ::= {zxAnPonOnuIfCurrPerfEntry 67 }

    zxAnPonOnuIfTxAvgBwUtilization OBJECT-TYPE
        SYNTAX       Unsigned32
        UNITS        "0.1 percent"
        MAX-ACCESS   read-only
        STATUS       current
        DESCRIPTION
            "Transmitted average bandwidth utilization."
        ::= {zxAnPonOnuIfCurrPerfEntry 68 }
        
    zxAnPonOnuIfTxFragments  OBJECT-TYPE
        SYNTAX      Counter64
        MAX-ACCESS  read-only
        STATUS      current
        DESCRIPTION
            "The total number of packets sent that were less than
         64 octets in length (excluding framing bits but including
         FCS octets) and had either a bad Frame Check Sequence
         (FCS) with an integral number of octets (FCS Error) or a
         bad FCS with a non-integral number of octets (Alignment
         Error).

         Note that it is entirely normal for zxAnPonOnuIfRxFragments
          to increment.  This is because it counts both runts (which are
         normal occurrences due to collisions) and noise hits."
        ::= { zxAnPonOnuIfCurrPerfEntry 69}
        
    zxAnPonOnuIfTxJabbers OBJECT-TYPE
        SYNTAX      Counter64
        MAX-ACCESS  read-only
        STATUS      current
        DESCRIPTION
            "The total number of packets sent that were
         longer than 1518 octets (excluding framing bits,
         but including FCS octets), and had either a bad
         Frame Check Sequence (FCS) with an integral number
         of octets (FCS Error) or a bad FCS with a non-integral
         number of octets (Alignment Error).

         Note that this definition of jabber is different
         than the definition in IEEE-802.3 section 8.2.1.5
         (10BASE5) and section 10.3.1.4 (10BASE2).  These
         documents define jabber as the condition where any
         packet exceeds 20 ms.  The allowed range to detect
         jabber is between 20 ms and 150 ms."
        ::= { zxAnPonOnuIfCurrPerfEntry 70}   
        
    zxAnPonOnuIfCollisions OBJECT-TYPE
        SYNTAX      Counter64
        MAX-ACCESS  read-only
        STATUS      current
        DESCRIPTION
            "The best estimate of the total number of collisions
         on this olt interface."
        ::= { zxAnPonOnuIfCurrPerfEntry 88}

    zxAnPonOnuIfDropEvents OBJECT-TYPE
        SYNTAX      Counter64
        MAX-ACCESS  read-only
        STATUS      current
        DESCRIPTION
            "The total number of events in which packets
         were dropped by the probe due to lack of resources.
         Note that this number is not necessarily the number of
         packets dropped; it is just the number of times this
         condition has been detected."
        ::= { zxAnPonOnuIfCurrPerfEntry 89}  

    zxAnPonOnuIfCurrPerfCapability  OBJECT-TYPE 
         SYNTAX           BITS 
           {
                zxAnPonOnuIfRxOctets(0),
                zxAnPonOnuIfRxPkts(1),
                zxAnPonOnuIfRxOctetRate(2),
                zxAnPonOnuIfRxPktRate(3),
                zxAnPonOnuIfRxOctetPeakRate(4),
                zxAnPonOnuIfRxPktPeakRate(5),
                zxAnPonOnuIfRxUcastPkts(6),
                zxAnPonOnuIfRxNUcastPkts(7),
                zxAnPonOnuIfRxMcastPkts(8),
                zxAnPonOnuIfRxBcastPkts(9),
                zxAnPonOnuIfRxDiscardPkts(10),
                zxAnPonOnuIfRxErrPkts(11),
                zxAnPonOnuIfRxPdr(12),
                zxAnPonOnuIfRxPer(13),
                zxAnPonOnuIfRxCrcAlignErrors(14),
                zxAnPonOnuIfRxUndersizePkts(15),
                zxAnPonOnuIfRxOversizePkts(16),
                zxAnPonOnuIfRxPkts64Octets(17),
                zxAnPonOnuIfRxPkts65To127Octets(18),
                zxAnPonOnuIfRxPkts128To255Octets(19),
                zxAnPonOnuIfRxPkts256To511Octets(20),
                zxAnPonOnuIfRxPkts512To1023Oct(21),
                zxAnPonOnuIfRxPkts1024To1518Oct(22),
                zxAnPonOnuIfRxBwUtilization(23),
                zxAnPonOnuIfRxAvgBwUtilization(24),
                zxAnPonOnuIfRxFragments(25),
                zxAnPonOnuIfRxJabbers(26),
                zxAnPonOnuIfTxOctets(27),
                zxAnPonOnuIfTxPkts(28),
                zxAnPonOnuIfTxOctetRate(29),
                zxAnPonOnuIfTxPktRate(30),
                zxAnPonOnuIfTxOctetPeakRate(31),
                zxAnPonOnuIfTxPktPeakRate(32),
                zxAnPonOnuIfTxUcastPkts(33),
                zxAnPonOnuIfTxNUcastPkts(34),
                zxAnPonOnuIfTxMcastPkts(35),
                zxAnPonOnuIfTxBcastPkts(36),
                zxAnPonOnuIfTxDiscardPkts(37),
                zxAnPonOnuIfTxErrPkts(38),
                zxAnPonOnuIfTxPdr(39),
                zxAnPonOnuIfTxPer(40),
                zxAnPonOnuIfTxCrcAlignErrors(41),
                zxAnPonOnuIfTxUndersizePkts(42),
                zxAnPonOnuIfTxOversizePkts(43),
                zxAnPonOnuIfTxPkts64Octets(44),
                zxAnPonOnuIfTxPkts65To127Octets(45),
                zxAnPonOnuIfTxPkts128To255Octets(46),
                zxAnPonOnuIfTxPkts256To511Octets(47),
                zxAnPonOnuIfTxPkts512To1023Oct(48),
                zxAnPonOnuIfTxPkts1024To1518Oct(49),
                zxAnPonOnuIfTxBwUtilization(50),
                zxAnPonOnuIfTxAvgBwUtilization(51),
                zxAnPonOnuIfTxFragments(52),
                zxAnPonOnuIfTxJabbers(53),
                zxAnPonOnuIfCollisions(54),
                zxAnPonOnuIfDropEvents(55)
           }             
        MAX-ACCESS  read-only
        STATUS      current
        DESCRIPTION     
            "The support capability of PON ONU current performance statistics, 
            each bit from left to right represents the support of 
            performance statistic from top to bottom in this MIB table, 
            value 1 represents support and value 0 is not support."
        ::= { zxAnPonOnuIfCurrPerfEntry 99 }   
                
    zxAnPonOnuIfCurrPerfReset  OBJECT-TYPE
        SYNTAX       INTEGER{
                     reset(1)
                     }
        MAX-ACCESS   read-write
        STATUS       current
        DESCRIPTION
            "Clear ONU current statistics,read invalid.
            When get this variable, always return 1."
        ::= {zxAnPonOnuIfCurrPerfEntry 100 }

--------------------------------------------------------------------------------
--  zxAnPonOnuIfCurr15MinPerfTable
--------------------------------------------------------------------------------
    zxAnPonOnuIfCurr15MinPerfTable OBJECT-TYPE
        SYNTAX         SEQUENCE OF ZxAnPonOnuIfCurr15MinPerfEntry
        MAX-ACCESS     not-accessible
        STATUS         current
        DESCRIPTION
            "The current 15 minutes performance data table of PON ONU 
            interface."
        ::= { zxAnPonOnuPerfObjects 3 }

    zxAnPonOnuIfCurr15MinPerfEntry OBJECT-TYPE
        SYNTAX         ZxAnPonOnuIfCurr15MinPerfEntry
        MAX-ACCESS     not-accessible
        STATUS         current
        DESCRIPTION
            "Entry of zxAnPonOnuIfCurr15MinPerfTable."
        INDEX    { ifIndex,zxAnPonOnuIndex }
        ::= { zxAnPonOnuIfCurr15MinPerfTable 1}

    ZxAnPonOnuIfCurr15MinPerfEntry ::=
        SEQUENCE{
                zxAnPonOnuIfC15MTimeElapsed            Gauge32,
                zxAnPonOnuIfC15MRxOctets               Counter64,
                zxAnPonOnuIfC15MRxPkts                 Counter64,
                zxAnPonOnuIfC15MRxUcastPkts            Counter64,
                zxAnPonOnuIfC15MRxNUcastPkts           Counter64,
                zxAnPonOnuIfC15MRxMcastPkts            Counter64,
                zxAnPonOnuIfC15MRxBcastPkts            Counter64,
                zxAnPonOnuIfC15MRxDiscardPkts          Counter64,
                zxAnPonOnuIfC15MRxErrPkts              Counter64,
                zxAnPonOnuIfC15MRxCrcAlignErrors       Counter64,
                zxAnPonOnuIfC15MRxUndersizePkts        Counter64,
                zxAnPonOnuIfC15MRxOversizePkts         Counter64,
                zxAnPonOnuIfC15MRx64Octs               Counter64,
                zxAnPonOnuIfC15MRx65To127Octs          Counter64,
                zxAnPonOnuIfC15MRx128To255Octs         Counter64,
                zxAnPonOnuIfC15MRx256To511Octs         Counter64,
                zxAnPonOnuIfC15MRx512To1023Octs        Counter64,
                zxAnPonOnuIfC15MRx1024To1518Octs       Counter64,
                zxAnPonOnuIfC15MRxFragments            Counter64,
                zxAnPonOnuIfC15MRxJabbers              Counter64,
                zxAnPonOnuIfC15MTxOctets               Counter64,
                zxAnPonOnuIfC15MTxPkts                 Counter64,
                zxAnPonOnuIfC15MTxUcastPkts            Counter64,
                zxAnPonOnuIfC15MTxNUcastPkts           Counter64,
                zxAnPonOnuIfC15MTxMcastPkts            Counter64,
                zxAnPonOnuIfC15MTxBcastPkts            Counter64,
                zxAnPonOnuIfC15MTxDiscardPkts          Counter64,
                zxAnPonOnuIfC15MTxErrPkts              Counter64,
                zxAnPonOnuIfC15MTxCrcAlignErrors       Counter64,
                zxAnPonOnuIfC15MTxUndersizePkts        Counter64,
                zxAnPonOnuIfC15MTxOversizePkts         Counter64,
                zxAnPonOnuIfC15MTxPkts64Octets         Counter64,
                zxAnPonOnuIfC15MTx65To127Octs          Counter64,
                zxAnPonOnuIfC15MTx128To255Octs         Counter64,
                zxAnPonOnuIfC15MTx256To511Octs         Counter64,
                zxAnPonOnuIfC15MTx512To1023Octs        Counter64,
                zxAnPonOnuIfC15MTx1024To1518Octs       Counter64,
                zxAnPonOnuIfC15MTxFragments            Counter64,
                zxAnPonOnuIfC15MTxJabbers              Counter64,
                zxAnPonOnuIfC15MCollisions             Counter64,
                zxAnPonOnuIfC15MDropEvents             Counter64,
                zxAnPonOnuIfPerfCapability             BITS,
                zxAnPonOnuIfC15MPerfReset              INTEGER
                }

    zxAnPonOnuIfC15MTimeElapsed  OBJECT-TYPE 
        SYNTAX      Gauge32(0..899)
        UNITS       "Seconds"
        MAX-ACCESS  read-only
        STATUS      current
        DESCRIPTION     
            "Number of seconds that have elapsed since the beginning
             of the current 15 minutes interval."
        ::= { zxAnPonOnuIfCurr15MinPerfEntry 1 }
        
    zxAnPonOnuIfC15MRxOctets OBJECT-TYPE
        SYNTAX       Counter64
        MAX-ACCESS   read-only
        STATUS       current
        DESCRIPTION
            "The current 15 minutes interval octets of data (including
         those in bad packets) received on the
         network (excluding framing bits but including
         FCS octets)."
        ::= {zxAnPonOnuIfCurr15MinPerfEntry 2 }

    zxAnPonOnuIfC15MRxPkts OBJECT-TYPE
        SYNTAX       Counter64
        MAX-ACCESS   read-only
        STATUS       current
        DESCRIPTION
            "The current 15 minutes interval packets (including bad packets,
         broadcast packets, and multicast packets) received."
        ::= {zxAnPonOnuIfCurr15MinPerfEntry 3 }

    zxAnPonOnuIfC15MRxUcastPkts OBJECT-TYPE
        SYNTAX       Counter64
        MAX-ACCESS   read-only
        STATUS       current
        DESCRIPTION
            "The current 15 minutes interval good packets received that were
         directed to a unicast address."
        ::= {zxAnPonOnuIfCurr15MinPerfEntry 4 }

    zxAnPonOnuIfC15MRxNUcastPkts OBJECT-TYPE
        SYNTAX       Counter64
        MAX-ACCESS   read-only
        STATUS       current
        DESCRIPTION
            "The current 15 minutes interval good packets received that were
         directed to a non-unicast address."
        ::= {zxAnPonOnuIfCurr15MinPerfEntry 5 }

    zxAnPonOnuIfC15MRxMcastPkts OBJECT-TYPE
        SYNTAX       Counter64
        MAX-ACCESS   read-only
        STATUS       current
        DESCRIPTION
            "The current 15 minutes interval good packets received that were
         directed to a multicast address."
        ::= {zxAnPonOnuIfCurr15MinPerfEntry 6 }

    zxAnPonOnuIfC15MRxBcastPkts OBJECT-TYPE
        SYNTAX       Counter64
        MAX-ACCESS   read-only
        STATUS       current
        DESCRIPTION
            "The current 15 minutes interval good packets received that were
         directed to the broadcast address.  Note that this
         does not include multicast packets."
        ::= {zxAnPonOnuIfCurr15MinPerfEntry 7 }

    zxAnPonOnuIfC15MRxDiscardPkts OBJECT-TYPE
        SYNTAX       Counter64
        MAX-ACCESS   read-only
        STATUS       current
        DESCRIPTION
            "The current 15 minutes interval discarded packets received."
        ::= {zxAnPonOnuIfCurr15MinPerfEntry 8 }

    zxAnPonOnuIfC15MRxErrPkts OBJECT-TYPE
        SYNTAX       Counter64
        MAX-ACCESS   read-only
        STATUS       current
        DESCRIPTION
            "The current 15 minutes interval error packets received."
        ::= {zxAnPonOnuIfCurr15MinPerfEntry 9 }

    zxAnPonOnuIfC15MRxCrcAlignErrors OBJECT-TYPE
        SYNTAX       Counter64
        MAX-ACCESS   read-only
        STATUS       current
        DESCRIPTION
            "The current 15 minutes interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOnuIfCurr15MinPerfEntry 10 }

    zxAnPonOnuIfC15MRxUndersizePkts OBJECT-TYPE
        SYNTAX       Counter64
        MAX-ACCESS   read-only
        STATUS       current
        DESCRIPTION
            "The current 15 minutes interval packets received that were
         less than 64 octets long (excluding framing bits,
         but including FCS octets) and were otherwise well
         formed."
        ::= {zxAnPonOnuIfCurr15MinPerfEntry 11 }

    zxAnPonOnuIfC15MRxOversizePkts OBJECT-TYPE
        SYNTAX       Counter64
        MAX-ACCESS   read-only
        STATUS       current
        DESCRIPTION
            "The current 15 minutes interval packets received that were
         longer than 1518 octets (excluding framing bits,
         but including FCS octets) and were otherwise
         well formed."
        ::= {zxAnPonOnuIfCurr15MinPerfEntry 12 }

    zxAnPonOnuIfC15MRx64Octs      OBJECT-TYPE
        SYNTAX       Counter64
        MAX-ACCESS   read-only
        STATUS       current
        DESCRIPTION
            "The current 15 minutes interval packets (including bad
         packets) received that were 64 octets in length
         (excluding framing bits but including FCS octets)."
        ::= {zxAnPonOnuIfCurr15MinPerfEntry 13 }

    zxAnPonOnuIfC15MRx65To127Octs OBJECT-TYPE
        SYNTAX       Counter64
        MAX-ACCESS   read-only
        STATUS       current
        DESCRIPTION
            "The current 15 minutes interval packets (including bad
         packets) received that were between
         65 and 127 octets in length inclusive
         (excluding framing bits but including FCS octets)."
        ::= {zxAnPonOnuIfCurr15MinPerfEntry 14 }

    zxAnPonOnuIfC15MRx128To255Octs OBJECT-TYPE
        SYNTAX       Counter64
        MAX-ACCESS   read-only
        STATUS       current
        DESCRIPTION
            "The current 15 minutes interval packets (including bad
         packets) received that were between
         128 and 255 octets in length inclusive
         (excluding framing bits but including FCS octets)."
        ::= {zxAnPonOnuIfCurr15MinPerfEntry 15 }

    zxAnPonOnuIfC15MRx256To511Octs OBJECT-TYPE
        SYNTAX       Counter64
        MAX-ACCESS   read-only
        STATUS       current
        DESCRIPTION
            "The current 15 minutes interval packets (including bad
         packets) received that were between
         256 and 511 octets in length inclusive
         (excluding framing bits but including FCS octets)."
        ::= {zxAnPonOnuIfCurr15MinPerfEntry 16 }

    zxAnPonOnuIfC15MRx512To1023Octs OBJECT-TYPE
        SYNTAX       Counter64
        MAX-ACCESS   read-only
        STATUS       current
        DESCRIPTION
            "The current 15 minutes interval packets (including bad
         packets) received that were between
         512 and 1023 octets in length inclusive
         (excluding framing bits but including FCS octets)."
        ::= {zxAnPonOnuIfCurr15MinPerfEntry 17 }

    zxAnPonOnuIfC15MRx1024To1518Octs OBJECT-TYPE
        SYNTAX       Counter64
        MAX-ACCESS   read-only
        STATUS       current
        DESCRIPTION
            "The current 15 minutes interval packets (including bad
         packets) received that were between
         1024 and 1518 octets in length inclusive
         (excluding framing bits but including FCS octets)."
        ::= {zxAnPonOnuIfCurr15MinPerfEntry 18 }
        
    zxAnPonOnuIfC15MRxFragments  OBJECT-TYPE
        SYNTAX      Counter64
        MAX-ACCESS  read-only
        STATUS      current
        DESCRIPTION
            "The current 15 minutes interval packets received that were less 
            than 64 octets in length (excluding framing bits but including
         FCS octets) and had either a bad Frame Check Sequence
         (FCS) with an integral number of octets (FCS Error) or a
         bad FCS with a non-integral number of octets (Alignment
         Error)."
        ::= { zxAnPonOnuIfCurr15MinPerfEntry 19}
        
    zxAnPonOnuIfC15MRxJabbers OBJECT-TYPE
        SYNTAX      Counter64
        MAX-ACCESS  read-only
        STATUS      current
        DESCRIPTION
            "The current 15 minutes interval packets received that were
         longer than 1518 octets (excluding framing bits,
         but including FCS octets), and had either a bad
         Frame Check Sequence (FCS) with an integral number
         of octets (FCS Error) or a bad FCS with a non-integral
         number of octets (Alignment Error)."
        ::= { zxAnPonOnuIfCurr15MinPerfEntry 20}

    zxAnPonOnuIfC15MTxOctets OBJECT-TYPE
        SYNTAX       Counter64
        MAX-ACCESS   read-only
        STATUS       current
        DESCRIPTION
            "The current 15 minutes interval octets of data (including
         those in bad packets) sent on the
         network (excluding framing bits but including
         FCS octets)."
        ::= {zxAnPonOnuIfCurr15MinPerfEntry 36 }

    zxAnPonOnuIfC15MTxPkts OBJECT-TYPE
        SYNTAX       Counter64
        MAX-ACCESS   read-only
        STATUS       current
        DESCRIPTION
            "The current 15 minutes interval packets (including bad packets,
         broadcast packets, and multicast packets) transmitted."
        ::= {zxAnPonOnuIfCurr15MinPerfEntry 37 }

    zxAnPonOnuIfC15MTxUcastPkts OBJECT-TYPE
        SYNTAX       Counter64
        MAX-ACCESS   read-only
        STATUS       current
        DESCRIPTION
            "The current 15 minutes interval good packets transmitted that were
         directed to a unicast address."
        ::= {zxAnPonOnuIfCurr15MinPerfEntry 38 }

    zxAnPonOnuIfC15MTxNUcastPkts OBJECT-TYPE
        SYNTAX       Counter64
        MAX-ACCESS   read-only
        STATUS       current
        DESCRIPTION
            "The current 15 minutes interval good packets transmitted that were
         directed to a non-unicast address."
        ::= {zxAnPonOnuIfCurr15MinPerfEntry 39 }

    zxAnPonOnuIfC15MTxMcastPkts OBJECT-TYPE
        SYNTAX       Counter64
        MAX-ACCESS   read-only
        STATUS       current
        DESCRIPTION
            "The current 15 minutes interval good packets transmitted that were
         directed to a multicast address."
        ::= {zxAnPonOnuIfCurr15MinPerfEntry 40 }

    zxAnPonOnuIfC15MTxBcastPkts OBJECT-TYPE
        SYNTAX       Counter64
        MAX-ACCESS   read-only
        STATUS       current
        DESCRIPTION
            "The current 15 minutes interval good packets transmitted that were
         directed to the broadcast address.  Note that this does not include 
         multicast packets."
        ::= {zxAnPonOnuIfCurr15MinPerfEntry 41 }

    zxAnPonOnuIfC15MTxDiscardPkts OBJECT-TYPE
        SYNTAX       Counter64
        MAX-ACCESS   read-only
        STATUS       current
        DESCRIPTION
            "The current 15 minutes interval discarded packets transmitted."
        ::= {zxAnPonOnuIfCurr15MinPerfEntry 42 }

    zxAnPonOnuIfC15MTxErrPkts OBJECT-TYPE
        SYNTAX       Counter64
        MAX-ACCESS   read-only
        STATUS       current
        DESCRIPTION
            "The current 15 minutes interval error packets transmitted."
        ::= {zxAnPonOnuIfCurr15MinPerfEntry 43 }
        
    zxAnPonOnuIfC15MTxCrcAlignErrors OBJECT-TYPE
        SYNTAX      Counter64
        MAX-ACCESS  read-only
        STATUS      current
        DESCRIPTION
            "The current 15 minutes interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOnuIfCurr15MinPerfEntry 44}

    zxAnPonOnuIfC15MTxUndersizePkts OBJECT-TYPE
        SYNTAX      Counter64
        MAX-ACCESS  read-only
        STATUS      current
        DESCRIPTION
            "The current 15 minutes interval packets transmitted that were
         less than 64 octets long (excluding framing bits,but including
         FCS octets) and were otherwise well
         formed."
        ::= { zxAnPonOnuIfCurr15MinPerfEntry 45}
            
    zxAnPonOnuIfC15MTxOversizePkts OBJECT-TYPE
        SYNTAX      Counter64
        MAX-ACCESS  read-only
        STATUS      current
        DESCRIPTION
            "The current 15 minutes interval packets transmitted that were
         longer than 1518 octets (excluding framing bits, but including FCS
         octets) and were otherwise well formed."
        ::= { zxAnPonOnuIfCurr15MinPerfEntry 46}
    
    zxAnPonOnuIfC15MTxPkts64Octets OBJECT-TYPE
        SYNTAX       Counter64
        MAX-ACCESS   read-only
        STATUS       current
        DESCRIPTION
            "The current 15 minutes interval packets (including bad
         packets) transmitted that were 64 octets in length
         (excluding framing bits but including FCS octets)."
        ::= {zxAnPonOnuIfCurr15MinPerfEntry 47 }

    zxAnPonOnuIfC15MTx65To127Octs OBJECT-TYPE
        SYNTAX       Counter64
        MAX-ACCESS   read-only
        STATUS       current
        DESCRIPTION
            "The current 15 minutes interval packets (including bad
         packets) transmitted that were between 65 and 127 octets in
         length inclusive (excluding framing bits but including FCS octets)."
        ::= {zxAnPonOnuIfCurr15MinPerfEntry 48 }

    zxAnPonOnuIfC15MTx128To255Octs OBJECT-TYPE
        SYNTAX       Counter64
        MAX-ACCESS   read-only
        STATUS       current
        DESCRIPTION
            "The current 15 minutes interval packets (including bad
         packets) transmitted that were between
         128 and 255 octets in length inclusive
         (excluding framing bits but including FCS octets)."
        ::= {zxAnPonOnuIfCurr15MinPerfEntry 49}

    zxAnPonOnuIfC15MTx256To511Octs OBJECT-TYPE
        SYNTAX       Counter64
        MAX-ACCESS   read-only
        STATUS       current
        DESCRIPTION
            "The current 15 minutes interval packets (including bad
         packets) transmitted that were between
         256 and 511 octets in length inclusive
         (excluding framing bits but including FCS octets)."
        ::= {zxAnPonOnuIfCurr15MinPerfEntry 50 }

    zxAnPonOnuIfC15MTx512To1023Octs OBJECT-TYPE
        SYNTAX       Counter64
        MAX-ACCESS   read-only
        STATUS       current
        DESCRIPTION
            "The current 15 minutes interval packets (including bad
         packets) transmitted that were between
         512 and 1023 octets in length inclusive
         (excluding framing bits but including FCS octets)."
        ::= {zxAnPonOnuIfCurr15MinPerfEntry 51 }

    zxAnPonOnuIfC15MTx1024To1518Octs OBJECT-TYPE
        SYNTAX       Counter64
        MAX-ACCESS   read-only
        STATUS       current
        DESCRIPTION
            "The current 15 minutes interval packets (including bad
         packets) transmitted that were between
         1024 and 1518 octets in length inclusive
         (excluding framing bits but including FCS octets)."
        ::= {zxAnPonOnuIfCurr15MinPerfEntry 52 }
        
    zxAnPonOnuIfC15MTxFragments  OBJECT-TYPE
        SYNTAX      Counter64
        MAX-ACCESS  read-only
        STATUS      current
        DESCRIPTION
            "The current 15 minutes interval packets transmitted that were less 
            than 64 octets in length (excluding framing bits but including
         FCS octets) and had either a bad Frame Check Sequence
         (FCS) with an integral number of octets (FCS Error) or a
         bad FCS with a non-integral number of octets (Alignment
         Error)."
        ::= { zxAnPonOnuIfCurr15MinPerfEntry 53}
        
    zxAnPonOnuIfC15MTxJabbers OBJECT-TYPE
        SYNTAX      Counter64
        MAX-ACCESS  read-only
        STATUS      current
        DESCRIPTION
            "The current 15 minutes interval packets transmitted that were
         longer than 1518 octets (excluding framing bits,
         but including FCS octets), and had either a bad
         Frame Check Sequence (FCS) with an integral number
         of octets (FCS Error) or a bad FCS with a non-integral
         number of octets (Alignment Error)."
        ::= { zxAnPonOnuIfCurr15MinPerfEntry 54}
        
    zxAnPonOnuIfC15MCollisions OBJECT-TYPE
        SYNTAX      Counter64
        MAX-ACCESS  read-only
        STATUS      current
        DESCRIPTION
            "The current 15 minutes interval best estimate of collisions
         on this onu interface."
        ::= { zxAnPonOnuIfCurr15MinPerfEntry 70}

    zxAnPonOnuIfC15MDropEvents OBJECT-TYPE
        SYNTAX      Counter64
        MAX-ACCESS  read-only
        STATUS      current
        DESCRIPTION
            "The current 15 minutes interval events in which packets
         were dropped by the probe due to lack of resources."
        ::= { zxAnPonOnuIfCurr15MinPerfEntry 71}

    zxAnPonOnuIfPerfCapability  OBJECT-TYPE 
         SYNTAX           BITS 
           {
                zxAnPonOnuIfC15MRxOctets(0),
                zxAnPonOnuIfC15MRxPkts(1),
                zxAnPonOnuIfC15MRxUcastPkts(2),
                zxAnPonOnuIfC15MRxNUcastPkts(3),
                zxAnPonOnuIfC15MRxMcastPkts(4),
                zxAnPonOnuIfC15MRxBcastPkts(5),
                zxAnPonOnuIfC15MRxDiscardPkts(6),
                zxAnPonOnuIfC15MRxErrPkts(7),
                zxAnPonOnuIfC15MRxCrcAlignErrors(8),
                zxAnPonOnuIfC15MRxUndersizePkts(9),
                zxAnPonOnuIfC15MRxOversizePkts(10),
                zxAnPonOnuIfC15MRx64Octs(11),
                zxAnPonOnuIfC15MRx65To127Octs(12),
                zxAnPonOnuIfC15MRx128To255Octs(13),
                zxAnPonOnuIfC15MRx256To511Octs(14),
                zxAnPonOnuIfC15MRx512To1023Octs(15),
                zxAnPonOnuIfC15MRx1024To1518Octs(16),
                zxAnPonOnuIfC15MRxFragments(17),
                zxAnPonOnuIfC15MRxJabbers(18),
                zxAnPonOnuIfC15MTxOctets(19),
                zxAnPonOnuIfC15MTxPkts(20),
                zxAnPonOnuIfC15MTxUcastPkts(21),
                zxAnPonOnuIfC15MTxNUcastPkts(22),
                zxAnPonOnuIfC15MTxMcastPkts(23),
                zxAnPonOnuIfC15MTxBcastPkts(24),
                zxAnPonOnuIfC15MTxDiscardPkts(25),
                zxAnPonOnuIfC15MTxErrPkts(26),
                zxAnPonOnuIfC15MTxCrcAlignErrors(27),
                zxAnPonOnuIfC15MTxUndersizePkts(28),
                zxAnPonOnuIfC15MTxOversizePkts(29),
                zxAnPonOnuIfC15MTxPkts64Octets(30),
                zxAnPonOnuIfC15MTx65To127Octs(31),
                zxAnPonOnuIfC15MTx128To255Octs(32),
                zxAnPonOnuIfC15MTx256To511Octs(33),
                zxAnPonOnuIfC15MTx512To1023Octs(34),
                zxAnPonOnuIfC15MTx1024To1518Octs(35),
                zxAnPonOnuIfC15MTxFragments(36),
                zxAnPonOnuIfC15MTxJabbers(37),
                zxAnPonOnuIfC15MCollisions(38),
                zxAnPonOnuIfC15MDropEvents(39)
            }             
        MAX-ACCESS  read-only
        STATUS      current
        DESCRIPTION  
            "The support capability of PON ONU interface C15M, CMin, C1D, H15M, 
            HMin and H1D performance statistics, each bit from left to right 
            represents the support of performance statistic from top to 
            bottom in this MIB table, value 1 represents support and 
            value 0 is not support."
        ::= { zxAnPonOnuIfCurr15MinPerfEntry 99 }   
        
    zxAnPonOnuIfC15MPerfReset  OBJECT-TYPE
        SYNTAX       INTEGER{
                     reset(1)
                     }
        MAX-ACCESS   read-write
        STATUS       current
        DESCRIPTION
            "Clear all the current 15-minutes performance variables.
            When get this variable, always return 1."
        ::= {zxAnPonOnuIfCurr15MinPerfEntry 100 }

--------------------------------------------------------------------------------
--  zxAnPonOnuIfCurrMinPerfTable
--------------------------------------------------------------------------------
    zxAnPonOnuIfCurrMinPerfTable OBJECT-TYPE
        SYNTAX         SEQUENCE OF ZxAnPonOnuIfCurrMinPerfEntry
        MAX-ACCESS     not-accessible
        STATUS         current
        DESCRIPTION
            "The minutes interval performance data table of PON ONU 
            interface."
        ::= { zxAnPonOnuPerfObjects 10 }

    zxAnPonOnuIfCurrMinPerfEntry OBJECT-TYPE
        SYNTAX         ZxAnPonOnuIfCurrMinPerfEntry
        MAX-ACCESS     not-accessible
        STATUS         current
        DESCRIPTION
            "An entry in the ONU minutes interval performance data table."
        INDEX    { ifIndex,zxAnPonOnuIndex }
        ::= { zxAnPonOnuIfCurrMinPerfTable 1}

    ZxAnPonOnuIfCurrMinPerfEntry ::=
        SEQUENCE {
            zxAnPonOnuIfCMinTimeElapsed            HCPerfTimeElapsed,
            zxAnPonOnuIfCMinRxOctets               Counter64,
            zxAnPonOnuIfCMinRxPkts                 Counter64,
            zxAnPonOnuIfCMinRxUcastPkts            Counter64,
            zxAnPonOnuIfCMinRxNUcastPkts           Counter64,
            zxAnPonOnuIfCMinRxMcastPkts            Counter64,
            zxAnPonOnuIfCMinRxBcastPkts            Counter64,
            zxAnPonOnuIfCMinRxDiscardPkts          Counter64,
            zxAnPonOnuIfCMinRxErrPkts              Counter64,
            zxAnPonOnuIfCMinRxCrcAlignErrors       Counter64,
            zxAnPonOnuIfCMinRxUndersizePkts        Counter64,
            zxAnPonOnuIfCMinRxOversizePkts         Counter64,
            zxAnPonOnuIfCMinRx64Octs               Counter64,
            zxAnPonOnuIfCMinRx65To127Octs          Counter64,
            zxAnPonOnuIfCMinRx128To255Octs         Counter64,
            zxAnPonOnuIfCMinRx256To511Octs         Counter64,
            zxAnPonOnuIfCMinRx512To1023Octs        Counter64,
            zxAnPonOnuIfCMinRx1024To1518Octs       Counter64,
            zxAnPonOnuIfCMinRxFragments            Counter64,
            zxAnPonOnuIfCMinRxJabbers              Counter64,
            zxAnPonOnuIfCMinTxOctets               Counter64,
            zxAnPonOnuIfCMinTxPkts                 Counter64,
            zxAnPonOnuIfCMinTxUcastPkts            Counter64,
            zxAnPonOnuIfCMinTxNUcastPkts           Counter64,
            zxAnPonOnuIfCMinTxMcastPkts            Counter64,
            zxAnPonOnuIfCMinTxBcastPkts            Counter64,
            zxAnPonOnuIfCMinTxDiscardPkts          Counter64,
            zxAnPonOnuIfCMinTxErrPkts              Counter64,
            zxAnPonOnuIfCMinTxCrcAlignErrors       Counter64,
            zxAnPonOnuIfCMinTxUndersizePkts        Counter64,
            zxAnPonOnuIfCMinTxOversizePkts         Counter64,
            zxAnPonOnuIfCMinTxPkts64Octets         Counter64,
            zxAnPonOnuIfCMinTx65To127Octs          Counter64,
            zxAnPonOnuIfCMinTx128To255Octs         Counter64,
            zxAnPonOnuIfCMinTx256To511Octs         Counter64,
            zxAnPonOnuIfCMinTx512To1023Octs        Counter64,
            zxAnPonOnuIfCMinTx1024To1518Octs       Counter64,
            zxAnPonOnuIfCMinTxFragments            Counter64,
            zxAnPonOnuIfCMinTxJabbers              Counter64,
            zxAnPonOnuIfCMinCollisions             Counter64,
            zxAnPonOnuIfCMinDropEvents             Counter64,
            zxAnPonOnuIfCMinPerfReset              INTEGER
            }

    zxAnPonOnuIfCMinTimeElapsed  OBJECT-TYPE 
        SYNTAX      HCPerfTimeElapsed
        UNITS       "Seconds"
        MAX-ACCESS  read-only
        STATUS      current
        DESCRIPTION     
            "Number of seconds that have elapsed since the beginning
            of the current minutes interval."
        ::= { zxAnPonOnuIfCurrMinPerfEntry 1 }
        
    zxAnPonOnuIfCMinRxOctets OBJECT-TYPE
        SYNTAX       Counter64
        MAX-ACCESS   read-only
        STATUS       current
        DESCRIPTION
            "The current minutes interval octets of data (including
            those in bad packets) received on the
            network (excluding framing bits but including
            FCS octets)."
        ::= {zxAnPonOnuIfCurrMinPerfEntry 2 }

    zxAnPonOnuIfCMinRxPkts OBJECT-TYPE
        SYNTAX       Counter64
        MAX-ACCESS   read-only
        STATUS       current
        DESCRIPTION
            "The current minutes interval packets (including bad packets,
            broadcast packets, and multicast packets) received."
        ::= {zxAnPonOnuIfCurrMinPerfEntry 3 }

    zxAnPonOnuIfCMinRxUcastPkts OBJECT-TYPE
        SYNTAX       Counter64
        MAX-ACCESS   read-only
        STATUS       current
        DESCRIPTION
            "The current minutes interval good packets received that were
            directed to a unicast address."
        ::= {zxAnPonOnuIfCurrMinPerfEntry 4 }

    zxAnPonOnuIfCMinRxNUcastPkts OBJECT-TYPE
        SYNTAX       Counter64
        MAX-ACCESS   read-only
        STATUS       current
        DESCRIPTION
            "The current minutes interval good packets received that were
            directed to a non-unicast address."
        ::= {zxAnPonOnuIfCurrMinPerfEntry 5 }

    zxAnPonOnuIfCMinRxMcastPkts OBJECT-TYPE
        SYNTAX       Counter64
        MAX-ACCESS   read-only
        STATUS       current
        DESCRIPTION
            "The current minutes interval good packets received that were
            directed to a multicast address."
        ::= {zxAnPonOnuIfCurrMinPerfEntry 6 }

    zxAnPonOnuIfCMinRxBcastPkts OBJECT-TYPE
        SYNTAX       Counter64
        MAX-ACCESS   read-only
        STATUS       current
        DESCRIPTION
            "The current minutes interval good packets received that were
            directed to the broadcast address.  Note that this
            does not include multicast packets."
        ::= {zxAnPonOnuIfCurrMinPerfEntry 7 }

    zxAnPonOnuIfCMinRxDiscardPkts OBJECT-TYPE
        SYNTAX       Counter64
        MAX-ACCESS   read-only
        STATUS       current
        DESCRIPTION
            "The current minutes interval discarded packets received."
        ::= {zxAnPonOnuIfCurrMinPerfEntry 8 }

    zxAnPonOnuIfCMinRxErrPkts OBJECT-TYPE
        SYNTAX       Counter64
        MAX-ACCESS   read-only
        STATUS       current
        DESCRIPTION
            "The current minutes interval error packets received."
        ::= {zxAnPonOnuIfCurrMinPerfEntry 9 }

    zxAnPonOnuIfCMinRxCrcAlignErrors OBJECT-TYPE
        SYNTAX       Counter64
        MAX-ACCESS   read-only
        STATUS       current
        DESCRIPTION
            "The current minutes interval packets received that
            had a length (excluding framing bits, but
            including FCS octets) of between 64 and 1518
            octets, inclusive, but had either a bad
            Frame Check Sequence (FCS) with an integral
            number of octets (FCS Error) or a bad FCS with
            a non-integral number of octets (Alignment Error)."
        ::= {zxAnPonOnuIfCurrMinPerfEntry 10 }

    zxAnPonOnuIfCMinRxUndersizePkts OBJECT-TYPE
        SYNTAX       Counter64
        MAX-ACCESS   read-only
        STATUS       current
        DESCRIPTION
            "The current minutes interval packets received that were
            less than 64 octets long (excluding framing bits,
            but including FCS octets) and were otherwise well
            formed."
        ::= {zxAnPonOnuIfCurrMinPerfEntry 11 }

    zxAnPonOnuIfCMinRxOversizePkts OBJECT-TYPE
        SYNTAX       Counter64
        MAX-ACCESS   read-only
        STATUS       current
        DESCRIPTION
            "The current minutes interval packets received that were
            longer than 1518 octets (excluding framing bits,
            but including FCS octets) and were otherwise
            well formed."
        ::= {zxAnPonOnuIfCurrMinPerfEntry 12 }

    zxAnPonOnuIfCMinRx64Octs      OBJECT-TYPE
        SYNTAX       Counter64
        MAX-ACCESS   read-only
        STATUS       current
        DESCRIPTION
            "The current minutes interval packets (including bad
            packets) received that were 64 octets in length
            (excluding framing bits but including FCS octets)."
        ::= {zxAnPonOnuIfCurrMinPerfEntry 13 }

    zxAnPonOnuIfCMinRx65To127Octs OBJECT-TYPE
        SYNTAX       Counter64
        MAX-ACCESS   read-only
        STATUS       current
        DESCRIPTION
            "The current minutes interval packets (including bad
            packets) received that were between
            65 and 127 octets in length inclusive
            (excluding framing bits but including FCS octets)."
        ::= {zxAnPonOnuIfCurrMinPerfEntry 14 }

    zxAnPonOnuIfCMinRx128To255Octs OBJECT-TYPE
        SYNTAX       Counter64
        MAX-ACCESS   read-only
        STATUS       current
        DESCRIPTION
            "The current minutes interval packets (including bad
            packets) received that were between
            128 and 255 octets in length inclusive
            (excluding framing bits but including FCS octets)."
        ::= {zxAnPonOnuIfCurrMinPerfEntry 15 }

    zxAnPonOnuIfCMinRx256To511Octs OBJECT-TYPE
        SYNTAX       Counter64
        MAX-ACCESS   read-only
        STATUS       current
        DESCRIPTION
            "The current minutes interval packets (including bad
            packets) received that were between
            256 and 511 octets in length inclusive
            (excluding framing bits but including FCS octets)."
        ::= {zxAnPonOnuIfCurrMinPerfEntry 16 }

    zxAnPonOnuIfCMinRx512To1023Octs OBJECT-TYPE
        SYNTAX       Counter64
        MAX-ACCESS   read-only
        STATUS       current
        DESCRIPTION
            "The current minutes interval packets (including bad
            packets) received that were between
            512 and 1023 octets in length inclusive
            (excluding framing bits but including FCS octets)."
        ::= {zxAnPonOnuIfCurrMinPerfEntry 17 }

    zxAnPonOnuIfCMinRx1024To1518Octs OBJECT-TYPE
        SYNTAX       Counter64
        MAX-ACCESS   read-only
        STATUS       current
        DESCRIPTION
            "The current minutes interval packets (including bad
            packets) received that were between
            1024 and 1518 octets in length inclusive
            (excluding framing bits but including FCS octets)."
        ::= {zxAnPonOnuIfCurrMinPerfEntry 18 }
        
    zxAnPonOnuIfCMinRxFragments  OBJECT-TYPE
        SYNTAX      Counter64
        MAX-ACCESS  read-only
        STATUS      current
        DESCRIPTION
            "The current minutes interval packets received that were less 
            than 64 octets in length (excluding framing bits but including
            FCS octets) and had either a bad Frame Check Sequence
            (FCS) with an integral number of octets (FCS Error) or a
            bad FCS with a non-integral number of octets (Alignment
            Error)."
        ::= { zxAnPonOnuIfCurrMinPerfEntry 19}
        
    zxAnPonOnuIfCMinRxJabbers OBJECT-TYPE
        SYNTAX      Counter64
        MAX-ACCESS  read-only
        STATUS      current
        DESCRIPTION
            "The current minutes interval packets received that were
            longer than 1518 octets (excluding framing bits,
            but including FCS octets), and had either a bad
            Frame Check Sequence (FCS) with an integral number
            of octets (FCS Error) or a bad FCS with a non-integral
            number of octets (Alignment Error)."
        ::= { zxAnPonOnuIfCurrMinPerfEntry 20}

    zxAnPonOnuIfCMinTxOctets OBJECT-TYPE
        SYNTAX       Counter64
        MAX-ACCESS   read-only
        STATUS       current
        DESCRIPTION
            "The current minutes interval octets of data (including
            those in bad packets) sent on the
            network (excluding framing bits but including
            FCS octets)."
        ::= {zxAnPonOnuIfCurrMinPerfEntry 36 }

    zxAnPonOnuIfCMinTxPkts OBJECT-TYPE
        SYNTAX       Counter64
        MAX-ACCESS   read-only
        STATUS       current
        DESCRIPTION
            "The current minutes interval packets (including bad packets,
            broadcast packets, and multicast packets) transmitted."
        ::= {zxAnPonOnuIfCurrMinPerfEntry 37 }

    zxAnPonOnuIfCMinTxUcastPkts OBJECT-TYPE
        SYNTAX       Counter64
        MAX-ACCESS   read-only
        STATUS       current
        DESCRIPTION
            "The current minutes interval good packets transmitted that were
            directed to a unicast address."
        ::= {zxAnPonOnuIfCurrMinPerfEntry 38 }

    zxAnPonOnuIfCMinTxNUcastPkts OBJECT-TYPE
        SYNTAX       Counter64
        MAX-ACCESS   read-only
        STATUS       current
        DESCRIPTION
            "The current minutes interval good packets transmitted that were
            directed to a non-unicast address."
        ::= {zxAnPonOnuIfCurrMinPerfEntry 39 }

    zxAnPonOnuIfCMinTxMcastPkts OBJECT-TYPE
        SYNTAX       Counter64
        MAX-ACCESS   read-only
        STATUS       current
        DESCRIPTION
            "The current minutes interval good packets transmitted that were
            directed to a multicast address."
        ::= {zxAnPonOnuIfCurrMinPerfEntry 40 }

    zxAnPonOnuIfCMinTxBcastPkts OBJECT-TYPE
        SYNTAX       Counter64
        MAX-ACCESS   read-only
        STATUS       current
        DESCRIPTION
            "The current minutes interval good packets transmitted that were
            directed to the broadcast address.  Note that this does not include 
            multicast packets."
        ::= {zxAnPonOnuIfCurrMinPerfEntry 41 }

    zxAnPonOnuIfCMinTxDiscardPkts OBJECT-TYPE
        SYNTAX       Counter64
        MAX-ACCESS   read-only
        STATUS       current
        DESCRIPTION
            "The current minutes interval discarded packets transmitted."
        ::= {zxAnPonOnuIfCurrMinPerfEntry 42 }

    zxAnPonOnuIfCMinTxErrPkts OBJECT-TYPE
        SYNTAX       Counter64
        MAX-ACCESS   read-only
        STATUS       current
        DESCRIPTION
            "The current minutes interval error packets transmitted."
        ::= {zxAnPonOnuIfCurrMinPerfEntry 43 }
        
    zxAnPonOnuIfCMinTxCrcAlignErrors OBJECT-TYPE
        SYNTAX      Counter64
        MAX-ACCESS  read-only
        STATUS      current
        DESCRIPTION
            "The current minutes interval packets transmitted that
            had a length (excluding framing bits, but including FCS octets)
            of between 64 and 1518 octets, inclusive, but had either a bad
            Frame Check Sequence (FCS) with an integral number of octets 
            (FCS Error) or a bad FCS with a non-integral number of octets
            (Alignment Error)."
        ::= { zxAnPonOnuIfCurrMinPerfEntry 44}

    zxAnPonOnuIfCMinTxUndersizePkts OBJECT-TYPE
        SYNTAX      Counter64
        MAX-ACCESS  read-only
        STATUS      current
        DESCRIPTION
            "The current minutes interval packets transmitted that were
            less than 64 octets long (excluding framing bits,but including
            FCS octets) and were otherwise well
            formed."
        ::= { zxAnPonOnuIfCurrMinPerfEntry 45}
            
    zxAnPonOnuIfCMinTxOversizePkts OBJECT-TYPE
        SYNTAX      Counter64
        MAX-ACCESS  read-only
        STATUS      current
        DESCRIPTION
            "The current minutes interval packets transmitted that were
            longer than 1518 octets (excluding framing bits, but including FCS
            octets) and were otherwise well formed."
        ::= { zxAnPonOnuIfCurrMinPerfEntry 46}
    
    zxAnPonOnuIfCMinTxPkts64Octets OBJECT-TYPE
        SYNTAX       Counter64
        MAX-ACCESS   read-only
        STATUS       current
        DESCRIPTION
            "The current minutes interval packets (including bad
            packets) transmitted that were 64 octets in length
            (excluding framing bits but including FCS octets)."
        ::= {zxAnPonOnuIfCurrMinPerfEntry 47 }

    zxAnPonOnuIfCMinTx65To127Octs OBJECT-TYPE
        SYNTAX       Counter64
        MAX-ACCESS   read-only
        STATUS       current
        DESCRIPTION
            "The current minutes interval packets (including bad
            packets) transmitted that were between 65 and 127 octets in
            length inclusive (excluding framing bits but including FCS octets)."
        ::= {zxAnPonOnuIfCurrMinPerfEntry 48 }

    zxAnPonOnuIfCMinTx128To255Octs OBJECT-TYPE
        SYNTAX       Counter64
        MAX-ACCESS   read-only
        STATUS       current
        DESCRIPTION
            "The current minutes interval packets (including bad
            packets) transmitted that were between
            128 and 255 octets in length inclusive
            (excluding framing bits but including FCS octets)."
        ::= {zxAnPonOnuIfCurrMinPerfEntry 49}

    zxAnPonOnuIfCMinTx256To511Octs OBJECT-TYPE
        SYNTAX       Counter64
        MAX-ACCESS   read-only
        STATUS       current
        DESCRIPTION
            "The current minutes interval packets (including bad
            packets) transmitted that were between
            256 and 511 octets in length inclusive
            (excluding framing bits but including FCS octets)."
        ::= {zxAnPonOnuIfCurrMinPerfEntry 50 }

    zxAnPonOnuIfCMinTx512To1023Octs OBJECT-TYPE
        SYNTAX       Counter64
        MAX-ACCESS   read-only
        STATUS       current
        DESCRIPTION
            "The current minutes interval packets (including bad
            packets) transmitted that were between
            512 and 1023 octets in length inclusive
            (excluding framing bits but including FCS octets)."
        ::= {zxAnPonOnuIfCurrMinPerfEntry 51 }

    zxAnPonOnuIfCMinTx1024To1518Octs OBJECT-TYPE
        SYNTAX       Counter64
        MAX-ACCESS   read-only
        STATUS       current
        DESCRIPTION
            "The current minutes interval packets (including bad
            packets) transmitted that were between
            1024 and 1518 octets in length inclusive
            (excluding framing bits but including FCS octets)."
        ::= {zxAnPonOnuIfCurrMinPerfEntry 52 }
        
    zxAnPonOnuIfCMinTxFragments  OBJECT-TYPE
        SYNTAX      Counter64
        MAX-ACCESS  read-only
        STATUS      current
        DESCRIPTION
            "The current minutes interval packets transmitted that were less 
            than 64 octets in length (excluding framing bits but including
            FCS octets) and had either a bad Frame Check Sequence
            (FCS) with an integral number of octets (FCS Error) or a
            bad FCS with a non-integral number of octets (Alignment
            Error)."
        ::= { zxAnPonOnuIfCurrMinPerfEntry 53}
        
    zxAnPonOnuIfCMinTxJabbers OBJECT-TYPE
        SYNTAX      Counter64
        MAX-ACCESS  read-only
        STATUS      current
        DESCRIPTION
            "The current minutes interval packets transmitted that were
            longer than 1518 octets (excluding framing bits,
            but including FCS octets), and had either a bad
            Frame Check Sequence (FCS) with an integral number
            of octets (FCS Error) or a bad FCS with a non-integral
            number of octets (Alignment Error)."
        ::= { zxAnPonOnuIfCurrMinPerfEntry 54}
        
    zxAnPonOnuIfCMinCollisions OBJECT-TYPE
        SYNTAX      Counter64
        MAX-ACCESS  read-only
        STATUS      current
        DESCRIPTION
            "The current minutes interval best estimate of collisions
            on this onu interface."
        ::= { zxAnPonOnuIfCurrMinPerfEntry 70}

    zxAnPonOnuIfCMinDropEvents OBJECT-TYPE
        SYNTAX      Counter64
        MAX-ACCESS  read-only
        STATUS      current
        DESCRIPTION
            "The current minutes interval events in which packets
            were dropped by the probe due to lack of resources."
        ::= { zxAnPonOnuIfCurrMinPerfEntry 71}

    zxAnPonOnuIfCMinPerfReset  OBJECT-TYPE
        SYNTAX       INTEGER{
                     reset(1)
                     }
        MAX-ACCESS   read-write
        STATUS       current
        DESCRIPTION
            "Clear all the current minutes interval performance variables.
            When get this variable, always return 1."
        ::= {zxAnPonOnuIfCurrMinPerfEntry 100 }

--------------------------------------------------------------------------------
--  zxAnPonOnuIfCurr1DayPerfTable
--------------------------------------------------------------------------------
    zxAnPonOnuIfCurr1DayPerfTable OBJECT-TYPE
        SYNTAX         SEQUENCE OF ZxAnPonOnuIfCurr1DayPerfEntry
        MAX-ACCESS     not-accessible
        STATUS         current
        DESCRIPTION
            "The current 1 day performance data table of PON ONU interface."
        ::= { zxAnPonOnuPerfObjects 4 }

    zxAnPonOnuIfCurr1DayPerfEntry OBJECT-TYPE
        SYNTAX         ZxAnPonOnuIfCurr1DayPerfEntry
        MAX-ACCESS     not-accessible
        STATUS         current
        DESCRIPTION
            "Entry of zxAnPonOnuIfCurr1DayPerfTable."
        INDEX    { ifIndex,zxAnPonOnuIndex }
        ::= { zxAnPonOnuIfCurr1DayPerfTable 1}

    ZxAnPonOnuIfCurr1DayPerfEntry ::=
        SEQUENCE{
                zxAnPonOnuIfC1DTimeElapsed            Gauge32,
                zxAnPonOnuIfC1DRxOctets               Counter64,
                zxAnPonOnuIfC1DRxPkts                 Counter64,
                zxAnPonOnuIfC1DRxUcastPkts            Counter64,
                zxAnPonOnuIfC1DRxNUcastPkts           Counter64,
                zxAnPonOnuIfC1DRxMcastPkts            Counter64,
                zxAnPonOnuIfC1DRxBcastPkts            Counter64,
                zxAnPonOnuIfC1DRxDiscardPkts          Counter64,
                zxAnPonOnuIfC1DRxErrPkts              Counter64,
                zxAnPonOnuIfC1DRxCrcAlignErrors       Counter64,
                zxAnPonOnuIfC1DRxUndersizePkts        Counter64,
                zxAnPonOnuIfC1DRxOversizePkts         Counter64,
                zxAnPonOnuIfC1DRx64Octs               Counter64,
                zxAnPonOnuIfC1DRx65To127Octs          Counter64,
                zxAnPonOnuIfC1DRx128To255Octs         Counter64,
                zxAnPonOnuIfC1DRx256To511Octs         Counter64,
                zxAnPonOnuIfC1DRx512To1023Octs        Counter64,
                zxAnPonOnuIfC1DRx1024To1518Octs       Counter64,
                zxAnPonOnuIfC1DRxFragments            Counter64,
                zxAnPonOnuIfC1DRxJabbers              Counter64,
                zxAnPonOnuIfC1DTxOctets               Counter64,
                zxAnPonOnuIfC1DTxPkts                 Counter64,
                zxAnPonOnuIfC1DTxUcastPkts            Counter64,
                zxAnPonOnuIfC1DTxNUcastPkts           Counter64,
                zxAnPonOnuIfC1DTxMcastPkts            Counter64,
                zxAnPonOnuIfC1DTxBcastPkts            Counter64,
                zxAnPonOnuIfC1DTxDiscardPkts          Counter64,
                zxAnPonOnuIfC1DTxErrPkts              Counter64,
                zxAnPonOnuIfC1DTxCrcAlignErrors       Counter64,
                zxAnPonOnuIfC1DTxUndersizePkts        Counter64,
                zxAnPonOnuIfC1DTxOversizePkts         Counter64,
                zxAnPonOnuIfC1DTx64Octets             Counter64,
                zxAnPonOnuIfC1DTx65To127Octs          Counter64,
                zxAnPonOnuIfC1DTx128To255Octs         Counter64,
                zxAnPonOnuIfC1DTx256To511Octs         Counter64,
                zxAnPonOnuIfC1DTx512To1023Octs        Counter64,
                zxAnPonOnuIfC1DTx1024To1518Octs       Counter64,
                zxAnPonOnuIfC1DTxFragments            Counter64,
                zxAnPonOnuIfC1DTxJabbers              Counter64,
                zxAnPonOnuIfC1DCollisions             Counter64,
                zxAnPonOnuIfC1DDropEvents             Counter64,
                zxAnPonOnuIfC1DPerfReset              INTEGER
                }

    zxAnPonOnuIfC1DTimeElapsed  OBJECT-TYPE 
        SYNTAX      Gauge32(0..86399)
        UNITS       "Seconds"
        MAX-ACCESS  read-only
        STATUS      current
        DESCRIPTION     
            "Number of seconds that have elapsed since the beginning
             of the current 1 day interval."
        ::= { zxAnPonOnuIfCurr1DayPerfEntry 1 }
        
    zxAnPonOnuIfC1DRxOctets OBJECT-TYPE
        SYNTAX       Counter64
        MAX-ACCESS   read-only
        STATUS       current
        DESCRIPTION
            "The current 1 day interval octets of data (including
         those in bad packets) received on the
         network (excluding framing bits but including
         FCS octets)."
        ::= {zxAnPonOnuIfCurr1DayPerfEntry 2 }

    zxAnPonOnuIfC1DRxPkts OBJECT-TYPE
        SYNTAX       Counter64
        MAX-ACCESS   read-only
        STATUS       current
        DESCRIPTION
            "The current 1 day interval packets (including bad packets,
         broadcast packets, and multicast packets) received."
        ::= {zxAnPonOnuIfCurr1DayPerfEntry 3 }

    zxAnPonOnuIfC1DRxUcastPkts OBJECT-TYPE
        SYNTAX       Counter64
        MAX-ACCESS   read-only
        STATUS       current
        DESCRIPTION
            "The current 1 day interval good packets received that were
         directed to a unicast address."
        ::= {zxAnPonOnuIfCurr1DayPerfEntry 4 }

    zxAnPonOnuIfC1DRxNUcastPkts OBJECT-TYPE
        SYNTAX       Counter64
        MAX-ACCESS   read-only
        STATUS       current
        DESCRIPTION
            "The current 1 day interval good packets received that were
         directed to a non-unicast address."
        ::= {zxAnPonOnuIfCurr1DayPerfEntry 5 }

    zxAnPonOnuIfC1DRxMcastPkts OBJECT-TYPE
        SYNTAX       Counter64
        MAX-ACCESS   read-only
        STATUS       current
        DESCRIPTION
            "The current 1 day interval good packets received that were
         directed to a multicast address."
        ::= {zxAnPonOnuIfCurr1DayPerfEntry 6 }

    zxAnPonOnuIfC1DRxBcastPkts OBJECT-TYPE
        SYNTAX       Counter64
        MAX-ACCESS   read-only
        STATUS       current
        DESCRIPTION
            "The current 1 day interval good packets received that were
         directed to the broadcast address.  Note that this
         does not include multicast packets."
        ::= {zxAnPonOnuIfCurr1DayPerfEntry 7 }

    zxAnPonOnuIfC1DRxDiscardPkts OBJECT-TYPE
        SYNTAX       Counter64
        MAX-ACCESS   read-only
        STATUS       current
        DESCRIPTION
            "The current 1 day interval discarded packets received."
        ::= {zxAnPonOnuIfCurr1DayPerfEntry 8 }

    zxAnPonOnuIfC1DRxErrPkts OBJECT-TYPE
        SYNTAX       Counter64
        MAX-ACCESS   read-only
        STATUS       current
        DESCRIPTION
            "The current 1 day interval error packets received."
        ::= {zxAnPonOnuIfCurr1DayPerfEntry 9 }

    zxAnPonOnuIfC1DRxCrcAlignErrors OBJECT-TYPE
        SYNTAX       Counter64
        MAX-ACCESS   read-only
        STATUS       current
        DESCRIPTION
            "The current 1 day interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOnuIfCurr1DayPerfEntry 10 }

    zxAnPonOnuIfC1DRxUndersizePkts OBJECT-TYPE
        SYNTAX       Counter64
        MAX-ACCESS   read-only
        STATUS       current
        DESCRIPTION
            "The current 1 day interval packets received that were
         less than 64 octets long (excluding framing bits,
         but including FCS octets) and were otherwise well
         formed."
        ::= {zxAnPonOnuIfCurr1DayPerfEntry 11 }

    zxAnPonOnuIfC1DRxOversizePkts OBJECT-TYPE
        SYNTAX       Counter64
        MAX-ACCESS   read-only
        STATUS       current
        DESCRIPTION
            "The current 1 day interval packets received that were
         longer than 1518 octets (excluding framing bits,
         but including FCS octets) and were otherwise
         well formed."
        ::= {zxAnPonOnuIfCurr1DayPerfEntry 12 }

    zxAnPonOnuIfC1DRx64Octs      OBJECT-TYPE
        SYNTAX       Counter64
        MAX-ACCESS   read-only
        STATUS       current
        DESCRIPTION
            "The current 1 day interval packets (including bad
         packets) received that were 64 octets in length
         (excluding framing bits but including FCS octets)."
        ::= {zxAnPonOnuIfCurr1DayPerfEntry 13 }

    zxAnPonOnuIfC1DRx65To127Octs OBJECT-TYPE
        SYNTAX       Counter64
        MAX-ACCESS   read-only
        STATUS       current
        DESCRIPTION
            "The current 1 day interval packets (including bad
         packets) received that were between
         65 and 127 octets in length inclusive
         (excluding framing bits but including FCS octets)."
        ::= {zxAnPonOnuIfCurr1DayPerfEntry 14 }

    zxAnPonOnuIfC1DRx128To255Octs OBJECT-TYPE
        SYNTAX       Counter64
        MAX-ACCESS   read-only
        STATUS       current
        DESCRIPTION
            "The current 1 day interval packets (including bad
         packets) received that were between
         128 and 255 octets in length inclusive
         (excluding framing bits but including FCS octets)."
        ::= {zxAnPonOnuIfCurr1DayPerfEntry 15 }

    zxAnPonOnuIfC1DRx256To511Octs OBJECT-TYPE
        SYNTAX       Counter64
        MAX-ACCESS   read-only
        STATUS       current
        DESCRIPTION
            "The current 1 day interval packets (including bad
         packets) received that were between
         256 and 511 octets in length inclusive
         (excluding framing bits but including FCS octets)."
        ::= {zxAnPonOnuIfCurr1DayPerfEntry 16 }

    zxAnPonOnuIfC1DRx512To1023Octs OBJECT-TYPE
        SYNTAX       Counter64
        MAX-ACCESS   read-only
        STATUS       current
        DESCRIPTION
            "The current 1 day interval packets (including bad
         packets) received that were between
         512 and 1023 octets in length inclusive
         (excluding framing bits but including FCS octets)."
        ::= {zxAnPonOnuIfCurr1DayPerfEntry 17 }

    zxAnPonOnuIfC1DRx1024To1518Octs OBJECT-TYPE
        SYNTAX       Counter64
        MAX-ACCESS   read-only
        STATUS       current
        DESCRIPTION
            "The current 1 day interval packets (including bad
         packets) received that were between
         1024 and 1518 octets in length inclusive
         (excluding framing bits but including FCS octets)."
        ::= {zxAnPonOnuIfCurr1DayPerfEntry 18 }
        
    zxAnPonOnuIfC1DRxFragments  OBJECT-TYPE
        SYNTAX      Counter64
        MAX-ACCESS  read-only
        STATUS      current
        DESCRIPTION
            "The current 1 day interval packets received that were less 
            than 64 octets in length (excluding framing bits but including
         FCS octets) and had either a bad Frame Check Sequence
         (FCS) with an integral number of octets (FCS Error) or a
         bad FCS with a non-integral number of octets (Alignment
         Error)."
        ::= { zxAnPonOnuIfCurr1DayPerfEntry 19}
        
    zxAnPonOnuIfC1DRxJabbers OBJECT-TYPE
        SYNTAX      Counter64
        MAX-ACCESS  read-only
        STATUS      current
        DESCRIPTION
            "The current 1 day interval packets received that were
         longer than 1518 octets (excluding framing bits,
         but including FCS octets), and had either a bad
         Frame Check Sequence (FCS) with an integral number
         of octets (FCS Error) or a bad FCS with a non-integral
         number of octets (Alignment Error)."
        ::= { zxAnPonOnuIfCurr1DayPerfEntry 20}

    zxAnPonOnuIfC1DTxOctets OBJECT-TYPE
        SYNTAX       Counter64
        MAX-ACCESS   read-only
        STATUS       current
        DESCRIPTION
            "The current 1 day interval octets of data (including
         those in bad packets) sent on the
         network (excluding framing bits but including
         FCS octets)."
        ::= {zxAnPonOnuIfCurr1DayPerfEntry 36 }

    zxAnPonOnuIfC1DTxPkts OBJECT-TYPE
        SYNTAX       Counter64
        MAX-ACCESS   read-only
        STATUS       current
        DESCRIPTION
            "The current 1 day interval packets (including bad packets,
         broadcast packets, and multicast packets) transmitted."
        ::= {zxAnPonOnuIfCurr1DayPerfEntry 37 }

    zxAnPonOnuIfC1DTxUcastPkts OBJECT-TYPE
        SYNTAX       Counter64
        MAX-ACCESS   read-only
        STATUS       current
        DESCRIPTION
            "The current 1 day interval good packets transmitted that were
         directed to a unicast address."
        ::= {zxAnPonOnuIfCurr1DayPerfEntry 38 }

    zxAnPonOnuIfC1DTxNUcastPkts OBJECT-TYPE
        SYNTAX       Counter64
        MAX-ACCESS   read-only
        STATUS       current
        DESCRIPTION
            "The current 1 day interval good packets transmitted that were
         directed to a non-unicast address."
        ::= {zxAnPonOnuIfCurr1DayPerfEntry 39 }

    zxAnPonOnuIfC1DTxMcastPkts OBJECT-TYPE
        SYNTAX       Counter64
        MAX-ACCESS   read-only
        STATUS       current
        DESCRIPTION
            "The current 1 day interval good packets transmitted that were
         directed to a multicast address."
        ::= {zxAnPonOnuIfCurr1DayPerfEntry 40 }

    zxAnPonOnuIfC1DTxBcastPkts OBJECT-TYPE
        SYNTAX       Counter64
        MAX-ACCESS   read-only
        STATUS       current
        DESCRIPTION
            "The current 1 day interval good packets transmitted that were
         directed to the broadcast address.  Note that this does not include 
         multicast packets."
        ::= {zxAnPonOnuIfCurr1DayPerfEntry 41 }

    zxAnPonOnuIfC1DTxDiscardPkts OBJECT-TYPE
        SYNTAX       Counter64
        MAX-ACCESS   read-only
        STATUS       current
        DESCRIPTION
            "The current 1 day interval discarded packets transmitted."
        ::= {zxAnPonOnuIfCurr1DayPerfEntry 42 }

    zxAnPonOnuIfC1DTxErrPkts OBJECT-TYPE
        SYNTAX       Counter64
        MAX-ACCESS   read-only
        STATUS       current
        DESCRIPTION
            "The current 1 day interval error packets transmitted."
        ::= {zxAnPonOnuIfCurr1DayPerfEntry 43 }
        
    zxAnPonOnuIfC1DTxCrcAlignErrors OBJECT-TYPE
        SYNTAX      Counter64
        MAX-ACCESS  read-only
        STATUS      current
        DESCRIPTION
            "The current 1 day interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOnuIfCurr1DayPerfEntry 44}

    zxAnPonOnuIfC1DTxUndersizePkts OBJECT-TYPE
        SYNTAX      Counter64
        MAX-ACCESS  read-only
        STATUS      current
        DESCRIPTION
            "The current 1 day interval packets transmitted that were
         less than 64 octets long (excluding framing bits,but including
         FCS octets) and were otherwise well
         formed."
        ::= { zxAnPonOnuIfCurr1DayPerfEntry 45}
            
    zxAnPonOnuIfC1DTxOversizePkts OBJECT-TYPE
        SYNTAX      Counter64
        MAX-ACCESS  read-only
        STATUS      current
        DESCRIPTION
            "The current 1 day interval packets transmitted that were
         longer than 1518 octets (excluding framing bits, but including FCS
         octets) and were otherwise well formed."
        ::= { zxAnPonOnuIfCurr1DayPerfEntry 46}
    
    zxAnPonOnuIfC1DTx64Octets OBJECT-TYPE
        SYNTAX       Counter64
        MAX-ACCESS   read-only
        STATUS       current
        DESCRIPTION
            "The current 1 day interval packets (including bad
         packets) transmitted that were 64 octets in length
         (excluding framing bits but including FCS octets)."
        ::= {zxAnPonOnuIfCurr1DayPerfEntry 47 }

    zxAnPonOnuIfC1DTx65To127Octs OBJECT-TYPE
        SYNTAX       Counter64
        MAX-ACCESS   read-only
        STATUS       current
        DESCRIPTION
            "The current 1 day interval packets (including bad
         packets) transmitted that were between 65 and 127 octets in
         length inclusive (excluding framing bits but including FCS octets)."
        ::= {zxAnPonOnuIfCurr1DayPerfEntry 48 }

    zxAnPonOnuIfC1DTx128To255Octs OBJECT-TYPE
        SYNTAX       Counter64
        MAX-ACCESS   read-only
        STATUS       current
        DESCRIPTION
            "The current 1 day interval packets (including bad
         packets) transmitted that were between
         128 and 255 octets in length inclusive
         (excluding framing bits but including FCS octets)."
        ::= {zxAnPonOnuIfCurr1DayPerfEntry 49}

    zxAnPonOnuIfC1DTx256To511Octs OBJECT-TYPE
        SYNTAX       Counter64
        MAX-ACCESS   read-only
        STATUS       current
        DESCRIPTION
            "The current 1 day interval packets (including bad
         packets) transmitted that were between
         256 and 511 octets in length inclusive
         (excluding framing bits but including FCS octets)."
        ::= {zxAnPonOnuIfCurr1DayPerfEntry 50 }

    zxAnPonOnuIfC1DTx512To1023Octs OBJECT-TYPE
        SYNTAX       Counter64
        MAX-ACCESS   read-only
        STATUS       current
        DESCRIPTION
            "The current 1 day interval packets (including bad
         packets) transmitted that were between
         512 and 1023 octets in length inclusive
         (excluding framing bits but including FCS octets)."
        ::= {zxAnPonOnuIfCurr1DayPerfEntry 51 }

    zxAnPonOnuIfC1DTx1024To1518Octs OBJECT-TYPE
        SYNTAX       Counter64
        MAX-ACCESS   read-only
        STATUS       current
        DESCRIPTION
            "The current 1 day interval packets (including bad
         packets) transmitted that were between
         1024 and 1518 octets in length inclusive
         (excluding framing bits but including FCS octets)."
        ::= {zxAnPonOnuIfCurr1DayPerfEntry 52 }
        
    zxAnPonOnuIfC1DTxFragments  OBJECT-TYPE
        SYNTAX      Counter64
        MAX-ACCESS  read-only
        STATUS      current
        DESCRIPTION
            "The current 1 day interval packets transmitted that were less 
            than 64 octets in length (excluding framing bits but including
         FCS octets) and had either a bad Frame Check Sequence
         (FCS) with an integral number of octets (FCS Error) or a
         bad FCS with a non-integral number of octets (Alignment
         Error)."
        ::= { zxAnPonOnuIfCurr1DayPerfEntry 53}
        
    zxAnPonOnuIfC1DTxJabbers OBJECT-TYPE
        SYNTAX      Counter64
        MAX-ACCESS  read-only
        STATUS      current
        DESCRIPTION
            "The current 1 day interval packets transmitted that were
         longer than 1518 octets (excluding framing bits,
         but including FCS octets), and had either a bad
         Frame Check Sequence (FCS) with an integral number
         of octets (FCS Error) or a bad FCS with a non-integral
         number of octets (Alignment Error)."
        ::= { zxAnPonOnuIfCurr1DayPerfEntry 54}
        
    zxAnPonOnuIfC1DCollisions OBJECT-TYPE
        SYNTAX      Counter64
        MAX-ACCESS  read-only
        STATUS      current
        DESCRIPTION
            "The current 1 day interval best estimate of collisions
         on this onu interface."
        ::= { zxAnPonOnuIfCurr1DayPerfEntry 70}

    zxAnPonOnuIfC1DDropEvents OBJECT-TYPE
        SYNTAX      Counter64
        MAX-ACCESS  read-only
        STATUS      current
        DESCRIPTION
            "The current 1 day interval events in which packets
         were dropped by the probe due to lack of resources."
        ::= { zxAnPonOnuIfCurr1DayPerfEntry 71}
        
    zxAnPonOnuIfC1DPerfReset  OBJECT-TYPE
        SYNTAX       INTEGER{
                     reset(1)
                     }
        MAX-ACCESS   read-write
        STATUS       current
        DESCRIPTION
            "Clear all the current 1 day performance variables.
            When get this variable, always return 1."
        ::= {zxAnPonOnuIfCurr1DayPerfEntry 100 }
        
--------------------------------------------------------------------------------
--  zxAnPonOnuIfHis15MinPerfTable
--------------------------------------------------------------------------------
    zxAnPonOnuIfHis15MinPerfTable OBJECT-TYPE
        SYNTAX         SEQUENCE OF ZxAnPonOnuIfHis15MinPerfEntry
        MAX-ACCESS     not-accessible
        STATUS         current
        DESCRIPTION
            "The 15 minutes interval performance data table of PON ONU."
        ::= { zxAnPonOnuPerfObjects 5 }

    zxAnPonOnuIfHis15MinPerfEntry OBJECT-TYPE
        SYNTAX         ZxAnPonOnuIfHis15MinPerfEntry
        MAX-ACCESS     not-accessible
        STATUS         current
        DESCRIPTION
            "An entry in the ONU 15 minutes interval performance data table."
        INDEX    { ifIndex,zxAnPonOnuIndex,zxAnPonOnuIfH15MIntervalNo}
        ::= { zxAnPonOnuIfHis15MinPerfTable 1}

    ZxAnPonOnuIfHis15MinPerfEntry ::=
        SEQUENCE{
                zxAnPonOnuIfH15MIntervalNo             Integer32,
                zxAnPonOnuIfH15MValidData              TruthValue,
                zxAnPonOnuIfH15MDateAndTime            DateAndTime,
                zxAnPonOnuIfH15MRxOctets               Counter64,
                zxAnPonOnuIfH15MRxPkts                 Counter64,
                zxAnPonOnuIfH15MRxUcastPkts            Counter64,
                zxAnPonOnuIfH15MRxNUcastPkts           Counter64,
                zxAnPonOnuIfH15MRxMcastPkts            Counter64,
                zxAnPonOnuIfH15MRxBcastPkts            Counter64,
                zxAnPonOnuIfH15MRxDiscardPkts          Counter64,
                zxAnPonOnuIfH15MRxErrPkts              Counter64,
                zxAnPonOnuIfH15MRxCrcAlignErrors       Counter64,
                zxAnPonOnuIfH15MRxUndersizePkts        Counter64,
                zxAnPonOnuIfH15MRxOversizePkts         Counter64,
                zxAnPonOnuIfH15MRx64Octs               Counter64,
                zxAnPonOnuIfH15MRx65To127Octs          Counter64,
                zxAnPonOnuIfH15MRx128To255Octs         Counter64,
                zxAnPonOnuIfH15MRx256To511Octs         Counter64,
                zxAnPonOnuIfH15MRx512To1023Octs        Counter64,
                zxAnPonOnuIfH15MRx1024To1518Octs       Counter64,
                zxAnPonOnuIfH15MRxFragments            Counter64,
                zxAnPonOnuIfH15MRxJabbers              Counter64,
                zxAnPonOnuIfH15MTxOctets               Counter64,
                zxAnPonOnuIfH15MTxPkts                 Counter64,
                zxAnPonOnuIfH15MTxUcastPkts            Counter64,
                zxAnPonOnuIfH15MTxNUcastPkts           Counter64,
                zxAnPonOnuIfH15MTxMcastPkts            Counter64,
                zxAnPonOnuIfH15MTxBcastPkts            Counter64,
                zxAnPonOnuIfH15MTxDiscardPkts          Counter64,
                zxAnPonOnuIfH15MTxErrPkts              Counter64,
                zxAnPonOnuIfH15MTxCrcAlignErrors       Counter64,
                zxAnPonOnuIfH15MTxUndersizePkts        Counter64,
                zxAnPonOnuIfH15MTxOversizePkts         Counter64,
                zxAnPonOnuIfH15MTxPkts64Octets         Counter64,
                zxAnPonOnuIfH15MTx65To127Octs          Counter64,
                zxAnPonOnuIfH15MTx128To255Octs         Counter64,
                zxAnPonOnuIfH15MTx256To511Octs         Counter64,
                zxAnPonOnuIfH15MTx512To1023Octs        Counter64,
                zxAnPonOnuIfH15MTx1024To1518Octs       Counter64,
                zxAnPonOnuIfH15MTxFragments            Counter64,
                zxAnPonOnuIfH15MTxJabbers              Counter64,
                zxAnPonOnuIfH15MCollisions             Counter64,
                zxAnPonOnuIfH15MDropEvents             Counter64
                }

    zxAnPonOnuIfH15MIntervalNo  OBJECT-TYPE 
        SYNTAX      Integer32(1..96)
        MAX-ACCESS  not-accessible
        STATUS      current
        DESCRIPTION     
             "Performance Data Interval.
              
              Interval 1 is the the most recent previous interval; 
              Interval 96 is 24 hours ago.  
              Intervals from 2 to 96 are optional."       
        ::= { zxAnPonOnuIfHis15MinPerfEntry 1 }  
        
   zxAnPonOnuIfH15MValidData OBJECT-TYPE
        SYNTAX      TruthValue
        MAX-ACCESS  read-only
        STATUS      current
        DESCRIPTION     
             "Performance data valid flag.
              true(1) means valid.
              false(2) means invalid and the performace data is useless."
        ::= { zxAnPonOnuIfHis15MinPerfEntry 2}       
        
    zxAnPonOnuIfH15MDateAndTime     OBJECT-TYPE   
        SYNTAX      DateAndTime
        MAX-ACCESS  read-only
        STATUS      current
        DESCRIPTION     
             "15min performace data interval create time."       
        ::= { zxAnPonOnuIfHis15MinPerfEntry 3 }   
        
    zxAnPonOnuIfH15MRxOctets OBJECT-TYPE
        SYNTAX       Counter64
        MAX-ACCESS   read-only
        STATUS       current
        DESCRIPTION
            "The 15 minutes interval octets of data (including
         those in bad packets) received on the
         network (excluding framing bits but including
         FCS octets)."
        ::= {zxAnPonOnuIfHis15MinPerfEntry 4 }

    zxAnPonOnuIfH15MRxPkts OBJECT-TYPE
        SYNTAX       Counter64
        MAX-ACCESS   read-only
        STATUS       current
        DESCRIPTION
            "The 15 minutes interval packets (including bad packets,
         broadcast packets, and multicast packets) received."
        ::= {zxAnPonOnuIfHis15MinPerfEntry 5 }

    zxAnPonOnuIfH15MRxUcastPkts OBJECT-TYPE
        SYNTAX       Counter64
        MAX-ACCESS   read-only
        STATUS       current
        DESCRIPTION
            "The 15 minutes interval good packets received that were
         directed to a unicast address."
        ::= {zxAnPonOnuIfHis15MinPerfEntry 6 }

    zxAnPonOnuIfH15MRxNUcastPkts OBJECT-TYPE
        SYNTAX       Counter64
        MAX-ACCESS   read-only
        STATUS       current
        DESCRIPTION
            "The 15 minutes interval good packets received that were
         directed to a non-unicast address."
        ::= {zxAnPonOnuIfHis15MinPerfEntry 7 }

    zxAnPonOnuIfH15MRxMcastPkts OBJECT-TYPE
        SYNTAX       Counter64
        MAX-ACCESS   read-only
        STATUS       current
        DESCRIPTION
            "The 15 minutes interval good packets received that were
         directed to a multicast address."
        ::= {zxAnPonOnuIfHis15MinPerfEntry 8 }

    zxAnPonOnuIfH15MRxBcastPkts OBJECT-TYPE
        SYNTAX       Counter64
        MAX-ACCESS   read-only
        STATUS       current
        DESCRIPTION
            "The 15 minutes interval good packets received that were
         directed to the broadcast address.  Note that this
         does not include multicast packets."
        ::= {zxAnPonOnuIfHis15MinPerfEntry 9 }

    zxAnPonOnuIfH15MRxDiscardPkts OBJECT-TYPE
        SYNTAX       Counter64
        MAX-ACCESS   read-only
        STATUS       current
        DESCRIPTION
            "The 15 minutes interval discarded packets received."
        ::= {zxAnPonOnuIfHis15MinPerfEntry 10 }

    zxAnPonOnuIfH15MRxErrPkts OBJECT-TYPE
        SYNTAX       Counter64
        MAX-ACCESS   read-only
        STATUS       current
        DESCRIPTION
            "The 15 minutes interval error packets received."
        ::= {zxAnPonOnuIfHis15MinPerfEntry 11 }

    zxAnPonOnuIfH15MRxCrcAlignErrors OBJECT-TYPE
        SYNTAX       Counter64
        MAX-ACCESS   read-only
        STATUS       current
        DESCRIPTION
            "The 15 minutes interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOnuIfHis15MinPerfEntry 12 }

    zxAnPonOnuIfH15MRxUndersizePkts OBJECT-TYPE
        SYNTAX       Counter64
        MAX-ACCESS   read-only
        STATUS       current
        DESCRIPTION
            "The 15 minutes interval packets received that were
         less than 64 octets long (excluding framing bits,
         but including FCS octets) and were otherwise well
         formed."
        ::= {zxAnPonOnuIfHis15MinPerfEntry 13 }

    zxAnPonOnuIfH15MRxOversizePkts OBJECT-TYPE
        SYNTAX       Counter64
        MAX-ACCESS   read-only
        STATUS       current
        DESCRIPTION
            "The 15 minutes interval packets received that were
         longer than 1518 octets (excluding framing bits,
         but including FCS octets) and were otherwise
         well formed."
        ::= {zxAnPonOnuIfHis15MinPerfEntry 14 }     

    zxAnPonOnuIfH15MRx64Octs      OBJECT-TYPE
        SYNTAX       Counter64
        MAX-ACCESS   read-only
        STATUS       current
        DESCRIPTION
            "The 15 minutes interval packets (including bad
         packets) received that were 64 octets in length
         (excluding framing bits but including FCS octets)."
        ::= {zxAnPonOnuIfHis15MinPerfEntry 15 }

    zxAnPonOnuIfH15MRx65To127Octs OBJECT-TYPE
        SYNTAX       Counter64
        MAX-ACCESS   read-only
        STATUS       current
        DESCRIPTION
            "The 15 minutes interval packets (including bad
         packets) received that were between
         65 and 127 octets in length inclusive
         (excluding framing bits but including FCS octets)."
        ::= {zxAnPonOnuIfHis15MinPerfEntry 16 }

    zxAnPonOnuIfH15MRx128To255Octs OBJECT-TYPE
        SYNTAX       Counter64
        MAX-ACCESS   read-only
        STATUS       current
        DESCRIPTION
            "The 15 minutes interval packets (including bad
         packets) received that were between
         128 and 255 octets in length inclusive
         (excluding framing bits but including FCS octets)."
        ::= {zxAnPonOnuIfHis15MinPerfEntry 17 }

    zxAnPonOnuIfH15MRx256To511Octs OBJECT-TYPE
        SYNTAX       Counter64
        MAX-ACCESS   read-only
        STATUS       current
        DESCRIPTION
            "The 15 minutes interval packets (including bad
         packets) received that were between
         256 and 511 octets in length inclusive
         (excluding framing bits but including FCS octets)."
        ::= {zxAnPonOnuIfHis15MinPerfEntry 18 }

    zxAnPonOnuIfH15MRx512To1023Octs OBJECT-TYPE
        SYNTAX       Counter64
        MAX-ACCESS   read-only
        STATUS       current
        DESCRIPTION
            "The 15 minutes interval packets (including bad
         packets) received that were between
         512 and 1023 octets in length inclusive
         (excluding framing bits but including FCS octets)."
        ::= {zxAnPonOnuIfHis15MinPerfEntry 19 }

    zxAnPonOnuIfH15MRx1024To1518Octs OBJECT-TYPE
        SYNTAX       Counter64
        MAX-ACCESS   read-only
        STATUS       current
        DESCRIPTION
            "The 15 minutes interval packets (including bad
         packets) received that were between
         1024 and 1518 octets in length inclusive
         (excluding framing bits but including FCS octets)."
        ::= {zxAnPonOnuIfHis15MinPerfEntry 20 }
        
    zxAnPonOnuIfH15MRxFragments  OBJECT-TYPE
        SYNTAX      Counter64
        MAX-ACCESS  read-only
        STATUS      current
        DESCRIPTION
            "The 15 minutes interval packets received that were less 
            than 64 octets in length (excluding framing bits but including
         FCS octets) and had either a bad Frame Check Sequence
         (FCS) with an integral number of octets (FCS Error) or a
         bad FCS with a non-integral number of octets (Alignment
         Error)."
        ::= { zxAnPonOnuIfHis15MinPerfEntry 21}
        
    zxAnPonOnuIfH15MRxJabbers OBJECT-TYPE
        SYNTAX      Counter64
        MAX-ACCESS  read-only
        STATUS      current
        DESCRIPTION
            "The 15 minutes interval packets received that were
         longer than 1518 octets (excluding framing bits,
         but including FCS octets), and had either a bad
         Frame Check Sequence (FCS) with an integral number
         of octets (FCS Error) or a bad FCS with a non-integral
         number of octets (Alignment Error)."
        ::= { zxAnPonOnuIfHis15MinPerfEntry 22}

    zxAnPonOnuIfH15MTxOctets OBJECT-TYPE
        SYNTAX       Counter64
        MAX-ACCESS   read-only
        STATUS       current
        DESCRIPTION
            "The 15 minutes interval octets of data (including
         those in bad packets) sent on the
         network (excluding framing bits but including
         FCS octets)."
        ::= {zxAnPonOnuIfHis15MinPerfEntry 36 }

    zxAnPonOnuIfH15MTxPkts OBJECT-TYPE
        SYNTAX       Counter64
        MAX-ACCESS   read-only
        STATUS       current
        DESCRIPTION
            "The 15 minutes interval packets (including bad packets,
         broadcast packets, and multicast packets) transmitted."
        ::= {zxAnPonOnuIfHis15MinPerfEntry 37 }

    zxAnPonOnuIfH15MTxUcastPkts OBJECT-TYPE
        SYNTAX       Counter64
        MAX-ACCESS   read-only
        STATUS       current
        DESCRIPTION
            "The 15 minutes interval good packets transmitted that were
         directed to a unicast address."
        ::= {zxAnPonOnuIfHis15MinPerfEntry 38 }

    zxAnPonOnuIfH15MTxNUcastPkts OBJECT-TYPE
        SYNTAX       Counter64
        MAX-ACCESS   read-only
        STATUS       current
        DESCRIPTION
            "The 15 minutes interval good packets transmitted that were
         directed to a non-unicast address."
        ::= {zxAnPonOnuIfHis15MinPerfEntry 39 }

    zxAnPonOnuIfH15MTxMcastPkts OBJECT-TYPE
        SYNTAX       Counter64
        MAX-ACCESS   read-only
        STATUS       current
        DESCRIPTION
            "The 15 minutes interval good packets transmitted that were
         directed to a multicast address."
        ::= {zxAnPonOnuIfHis15MinPerfEntry 40 }

    zxAnPonOnuIfH15MTxBcastPkts OBJECT-TYPE
        SYNTAX       Counter64
        MAX-ACCESS   read-only
        STATUS       current
        DESCRIPTION
            "The 15 minutes interval good packets transmitted that were
         directed to the broadcast address.  Note that this does not include 
         multicast packets."
        ::= {zxAnPonOnuIfHis15MinPerfEntry 41 }

    zxAnPonOnuIfH15MTxDiscardPkts OBJECT-TYPE
        SYNTAX       Counter64
        MAX-ACCESS   read-only
        STATUS       current
        DESCRIPTION
            "The 15 minutes interval discarded packets transmitted."
        ::= {zxAnPonOnuIfHis15MinPerfEntry 42 }

    zxAnPonOnuIfH15MTxErrPkts OBJECT-TYPE
        SYNTAX       Counter64
        MAX-ACCESS   read-only
        STATUS       current
        DESCRIPTION
            "The 15 minutes interval error packets transmitted."
        ::= {zxAnPonOnuIfHis15MinPerfEntry 43 }
        
    zxAnPonOnuIfH15MTxCrcAlignErrors OBJECT-TYPE
        SYNTAX      Counter64
        MAX-ACCESS  read-only
        STATUS      current
        DESCRIPTION
            "The 15 minutes interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOnuIfHis15MinPerfEntry 44}

    zxAnPonOnuIfH15MTxUndersizePkts OBJECT-TYPE
        SYNTAX      Counter64
        MAX-ACCESS  read-only
        STATUS      current
        DESCRIPTION
            "The 15 minutes interval packets transmitted that were
         less than 64 octets long (excluding framing bits,but including
         FCS octets) and were otherwise well
         formed."
        ::= { zxAnPonOnuIfHis15MinPerfEntry 45}
            
    zxAnPonOnuIfH15MTxOversizePkts OBJECT-TYPE
        SYNTAX      Counter64
        MAX-ACCESS  read-only
        STATUS      current
        DESCRIPTION
            "The 15 minutes interval packets transmitted that were
         longer than 1518 octets (excluding framing bits, but including FCS
         octets) and were otherwise well formed."
        ::= { zxAnPonOnuIfHis15MinPerfEntry 46}
    
    zxAnPonOnuIfH15MTxPkts64Octets OBJECT-TYPE
        SYNTAX       Counter64
        MAX-ACCESS   read-only
        STATUS       current
        DESCRIPTION
            "The 15 minutes interval packets (including bad
         packets) transmitted that were 64 octets in length
         (excluding framing bits but including FCS octets)."
        ::= {zxAnPonOnuIfHis15MinPerfEntry 47 }

    zxAnPonOnuIfH15MTx65To127Octs OBJECT-TYPE
        SYNTAX       Counter64
        MAX-ACCESS   read-only
        STATUS       current
        DESCRIPTION
            "The 15 minutes interval packets (including bad
         packets) transmitted that were between 65 and 127 octets in
         length inclusive (excluding framing bits but including FCS octets)."
        ::= {zxAnPonOnuIfHis15MinPerfEntry 48 }

    zxAnPonOnuIfH15MTx128To255Octs OBJECT-TYPE
        SYNTAX       Counter64
        MAX-ACCESS   read-only
        STATUS       current
        DESCRIPTION
            "The 15 minutes interval packets (including bad
         packets) transmitted that were between
         128 and 255 octets in length inclusive
         (excluding framing bits but including FCS octets)."
        ::= {zxAnPonOnuIfHis15MinPerfEntry 49}

    zxAnPonOnuIfH15MTx256To511Octs OBJECT-TYPE
        SYNTAX       Counter64
        MAX-ACCESS   read-only
        STATUS       current
        DESCRIPTION
            "The 15 minutes interval packets (including bad
         packets) transmitted that were between
         256 and 511 octets in length inclusive
         (excluding framing bits but including FCS octets)."
        ::= {zxAnPonOnuIfHis15MinPerfEntry 50 }

    zxAnPonOnuIfH15MTx512To1023Octs OBJECT-TYPE
        SYNTAX       Counter64
        MAX-ACCESS   read-only
        STATUS       current
        DESCRIPTION
            "The 15 minutes interval packets (including bad
         packets) transmitted that were between
         512 and 1023 octets in length inclusive
         (excluding framing bits but including FCS octets)."
        ::= {zxAnPonOnuIfHis15MinPerfEntry 51 }

    zxAnPonOnuIfH15MTx1024To1518Octs OBJECT-TYPE
        SYNTAX       Counter64
        MAX-ACCESS   read-only
        STATUS       current
        DESCRIPTION
            "The 15 minutes interval packets (including bad
         packets) transmitted that were between
         1024 and 1518 octets in length inclusive
         (excluding framing bits but including FCS octets)."
        ::= {zxAnPonOnuIfHis15MinPerfEntry 52 }
        
    zxAnPonOnuIfH15MTxFragments  OBJECT-TYPE
        SYNTAX      Counter64
        MAX-ACCESS  read-only
        STATUS      current
        DESCRIPTION
            "The 15 minutes interval packets transmitted that were less 
            than 64 octets in length (excluding framing bits but including
         FCS octets) and had either a bad Frame Check Sequence
         (FCS) with an integral number of octets (FCS Error) or a
         bad FCS with a non-integral number of octets (Alignment
         Error)."
        ::= { zxAnPonOnuIfHis15MinPerfEntry 53}
        
    zxAnPonOnuIfH15MTxJabbers OBJECT-TYPE
        SYNTAX      Counter64
        MAX-ACCESS  read-only
        STATUS      current
        DESCRIPTION
            "The 15 minutes interval packets transmitted that were
         longer than 1518 octets (excluding framing bits,
         but including FCS octets), and had either a bad
         Frame Check Sequence (FCS) with an integral number
         of octets (FCS Error) or a bad FCS with a non-integral
         number of octets (Alignment Error)."
        ::= { zxAnPonOnuIfHis15MinPerfEntry 54}   
        
    zxAnPonOnuIfH15MCollisions OBJECT-TYPE
        SYNTAX      Counter64
        MAX-ACCESS  read-only
        STATUS      current
        DESCRIPTION
            "The 15 minutes interval best estimate of collisions
         on this onu interface."
        ::= { zxAnPonOnuIfHis15MinPerfEntry 70}

    zxAnPonOnuIfH15MDropEvents OBJECT-TYPE
        SYNTAX      Counter64
        MAX-ACCESS  read-only
        STATUS      current
        DESCRIPTION
            "The 15 minutes interval events in which packets
         were dropped by the probe due to lack of resources."
        ::= { zxAnPonOnuIfHis15MinPerfEntry 71}

--------------------------------------------------------------------------------
--  zxAnPonOnuIfHisMinPerfTable
--------------------------------------------------------------------------------
    zxAnPonOnuIfHisMinPerfTable OBJECT-TYPE
        SYNTAX         SEQUENCE OF ZxAnPonOnuIfHisMinPerfEntry
        MAX-ACCESS     not-accessible
        STATUS         current
        DESCRIPTION
            "The minutes interval history performance data table of PON ONU."
        ::= { zxAnPonOnuPerfObjects 11 }

    zxAnPonOnuIfHisMinPerfEntry OBJECT-TYPE
        SYNTAX         ZxAnPonOnuIfHisMinPerfEntry
        MAX-ACCESS     not-accessible
        STATUS         current
        DESCRIPTION
            "An entry in the ONU minutes interval history performance data table."
        INDEX    { ifIndex,zxAnPonOnuIndex,zxAnPonOnuIfHMinIntervalNo}
        ::= { zxAnPonOnuIfHisMinPerfTable 1}

    ZxAnPonOnuIfHisMinPerfEntry ::=
        SEQUENCE {
            zxAnPonOnuIfHMinIntervalNo             Integer32,
            zxAnPonOnuIfHMinValidData              TruthValue,
            zxAnPonOnuIfHMinDateAndTime            DateAndTime,
            zxAnPonOnuIfHMinRxOctets               Counter64,
            zxAnPonOnuIfHMinRxPkts                 Counter64,
            zxAnPonOnuIfHMinRxUcastPkts            Counter64,
            zxAnPonOnuIfHMinRxNUcastPkts           Counter64,
            zxAnPonOnuIfHMinRxMcastPkts            Counter64,
            zxAnPonOnuIfHMinRxBcastPkts            Counter64,
            zxAnPonOnuIfHMinRxDiscardPkts          Counter64,
            zxAnPonOnuIfHMinRxErrPkts              Counter64,
            zxAnPonOnuIfHMinRxCrcAlignErrors       Counter64,
            zxAnPonOnuIfHMinRxUndersizePkts        Counter64,
            zxAnPonOnuIfHMinRxOversizePkts         Counter64,
            zxAnPonOnuIfHMinRx64Octs               Counter64,
            zxAnPonOnuIfHMinRx65To127Octs          Counter64,
            zxAnPonOnuIfHMinRx128To255Octs         Counter64,
            zxAnPonOnuIfHMinRx256To511Octs         Counter64,
            zxAnPonOnuIfHMinRx512To1023Octs        Counter64,
            zxAnPonOnuIfHMinRx1024To1518Octs       Counter64,
            zxAnPonOnuIfHMinRxFragments            Counter64,
            zxAnPonOnuIfHMinRxJabbers              Counter64,
            zxAnPonOnuIfHMinTxOctets               Counter64,
            zxAnPonOnuIfHMinTxPkts                 Counter64,
            zxAnPonOnuIfHMinTxUcastPkts            Counter64,
            zxAnPonOnuIfHMinTxNUcastPkts           Counter64,
            zxAnPonOnuIfHMinTxMcastPkts            Counter64,
            zxAnPonOnuIfHMinTxBcastPkts            Counter64,
            zxAnPonOnuIfHMinTxDiscardPkts          Counter64,
            zxAnPonOnuIfHMinTxErrPkts              Counter64,
            zxAnPonOnuIfHMinTxCrcAlignErrors       Counter64,
            zxAnPonOnuIfHMinTxUndersizePkts        Counter64,
            zxAnPonOnuIfHMinTxOversizePkts         Counter64,
            zxAnPonOnuIfHMinTxPkts64Octets         Counter64,
            zxAnPonOnuIfHMinTx65To127Octs          Counter64,
            zxAnPonOnuIfHMinTx128To255Octs         Counter64,
            zxAnPonOnuIfHMinTx256To511Octs         Counter64,
            zxAnPonOnuIfHMinTx512To1023Octs        Counter64,
            zxAnPonOnuIfHMinTx1024To1518Octs       Counter64,
            zxAnPonOnuIfHMinTxFragments            Counter64,
            zxAnPonOnuIfHMinTxJabbers              Counter64,
            zxAnPonOnuIfHMinCollisions             Counter64,
            zxAnPonOnuIfHMinDropEvents             Counter64
            }

    zxAnPonOnuIfHMinIntervalNo  OBJECT-TYPE 
        SYNTAX      Integer32
        MAX-ACCESS  not-accessible
        STATUS      current
        DESCRIPTION     
            "Performance data interval number."       
        ::= { zxAnPonOnuIfHisMinPerfEntry 1 }  
        
   zxAnPonOnuIfHMinValidData OBJECT-TYPE
        SYNTAX      TruthValue
        MAX-ACCESS  read-only
        STATUS      current
        DESCRIPTION     
            "Performance data valid flag.
            true(1) means valid.
            false(2) means invalid and the performace data is useless."
        ::= { zxAnPonOnuIfHisMinPerfEntry 2}       
        
    zxAnPonOnuIfHMinDateAndTime     OBJECT-TYPE   
        SYNTAX      DateAndTime
        MAX-ACCESS  read-only
        STATUS      current
        DESCRIPTION     
            "The minutes interval performance data generation time."       
        ::= { zxAnPonOnuIfHisMinPerfEntry 3 }   
        
    zxAnPonOnuIfHMinRxOctets OBJECT-TYPE
        SYNTAX       Counter64
        MAX-ACCESS   read-only
        STATUS       current
        DESCRIPTION
            "The minutes interval octets of data (including
            those in bad packets) received on the
            network (excluding framing bits but including
            FCS octets)."
        ::= {zxAnPonOnuIfHisMinPerfEntry 4 }

    zxAnPonOnuIfHMinRxPkts OBJECT-TYPE
        SYNTAX       Counter64
        MAX-ACCESS   read-only
        STATUS       current
        DESCRIPTION
            "The minutes interval packets (including bad packets,
            broadcast packets, and multicast packets) received."
        ::= {zxAnPonOnuIfHisMinPerfEntry 5 }

    zxAnPonOnuIfHMinRxUcastPkts OBJECT-TYPE
        SYNTAX       Counter64
        MAX-ACCESS   read-only
        STATUS       current
        DESCRIPTION
            "The minutes interval good packets received that were
            directed to a unicast address."
        ::= {zxAnPonOnuIfHisMinPerfEntry 6 }

    zxAnPonOnuIfHMinRxNUcastPkts OBJECT-TYPE
        SYNTAX       Counter64
        MAX-ACCESS   read-only
        STATUS       current
        DESCRIPTION
            "The minutes interval good packets received that were
            directed to a non-unicast address."
        ::= {zxAnPonOnuIfHisMinPerfEntry 7 }

    zxAnPonOnuIfHMinRxMcastPkts OBJECT-TYPE
        SYNTAX       Counter64
        MAX-ACCESS   read-only
        STATUS       current
        DESCRIPTION
            "The minutes interval good packets received that were
            directed to a multicast address."
        ::= {zxAnPonOnuIfHisMinPerfEntry 8 }

    zxAnPonOnuIfHMinRxBcastPkts OBJECT-TYPE
        SYNTAX       Counter64
        MAX-ACCESS   read-only
        STATUS       current
        DESCRIPTION
            "The minutes interval good packets received that were
            directed to the broadcast address.  Note that this
            does not include multicast packets."
        ::= {zxAnPonOnuIfHisMinPerfEntry 9 }

    zxAnPonOnuIfHMinRxDiscardPkts OBJECT-TYPE
        SYNTAX       Counter64
        MAX-ACCESS   read-only
        STATUS       current
        DESCRIPTION
            "The minutes interval discarded packets received."
        ::= {zxAnPonOnuIfHisMinPerfEntry 10 }

    zxAnPonOnuIfHMinRxErrPkts OBJECT-TYPE
        SYNTAX       Counter64
        MAX-ACCESS   read-only
        STATUS       current
        DESCRIPTION
            "The minutes interval error packets received."
        ::= {zxAnPonOnuIfHisMinPerfEntry 11 }

    zxAnPonOnuIfHMinRxCrcAlignErrors OBJECT-TYPE
        SYNTAX       Counter64
        MAX-ACCESS   read-only
        STATUS       current
        DESCRIPTION
            "The minutes interval packets received that
            had a length (excluding framing bits, but
            including FCS octets) of between 64 and 1518
            octets, inclusive, but had either a bad
            Frame Check Sequence (FCS) with an integral
            number of octets (FCS Error) or a bad FCS with
            a non-integral number of octets (Alignment Error)."
        ::= {zxAnPonOnuIfHisMinPerfEntry 12 }

    zxAnPonOnuIfHMinRxUndersizePkts OBJECT-TYPE
        SYNTAX       Counter64
        MAX-ACCESS   read-only
        STATUS       current
        DESCRIPTION
            "The minutes interval packets received that were
            less than 64 octets long (excluding framing bits,
            but including FCS octets) and were otherwise well
            formed."
        ::= {zxAnPonOnuIfHisMinPerfEntry 13 }

    zxAnPonOnuIfHMinRxOversizePkts OBJECT-TYPE
        SYNTAX       Counter64
        MAX-ACCESS   read-only
        STATUS       current
        DESCRIPTION
            "The minutes interval packets received that were
            longer than 1518 octets (excluding framing bits,
            but including FCS octets) and were otherwise
            well formed."
        ::= {zxAnPonOnuIfHisMinPerfEntry 14 }     

    zxAnPonOnuIfHMinRx64Octs      OBJECT-TYPE
        SYNTAX       Counter64
        MAX-ACCESS   read-only
        STATUS       current
        DESCRIPTION
            "The minutes interval packets (including bad
            packets) received that were 64 octets in length
            (excluding framing bits but including FCS octets)."
        ::= {zxAnPonOnuIfHisMinPerfEntry 15 }

    zxAnPonOnuIfHMinRx65To127Octs OBJECT-TYPE
        SYNTAX       Counter64
        MAX-ACCESS   read-only
        STATUS       current
        DESCRIPTION
            "The minutes interval packets (including bad
            packets) received that were between
            65 and 127 octets in length inclusive
            (excluding framing bits but including FCS octets)."
        ::= {zxAnPonOnuIfHisMinPerfEntry 16 }

    zxAnPonOnuIfHMinRx128To255Octs OBJECT-TYPE
        SYNTAX       Counter64
        MAX-ACCESS   read-only
        STATUS       current
        DESCRIPTION
            "The minutes interval packets (including bad
            packets) received that were between
            128 and 255 octets in length inclusive
            (excluding framing bits but including FCS octets)."
        ::= {zxAnPonOnuIfHisMinPerfEntry 17 }

    zxAnPonOnuIfHMinRx256To511Octs OBJECT-TYPE
        SYNTAX       Counter64
        MAX-ACCESS   read-only
        STATUS       current
        DESCRIPTION
            "The minutes interval packets (including bad
            packets) received that were between
            256 and 511 octets in length inclusive
            (excluding framing bits but including FCS octets)."
        ::= {zxAnPonOnuIfHisMinPerfEntry 18 }

    zxAnPonOnuIfHMinRx512To1023Octs OBJECT-TYPE
        SYNTAX       Counter64
        MAX-ACCESS   read-only
        STATUS       current
        DESCRIPTION
            "The minutes interval packets (including bad
            packets) received that were between
            512 and 1023 octets in length inclusive
            (excluding framing bits but including FCS octets)."
        ::= {zxAnPonOnuIfHisMinPerfEntry 19 }

    zxAnPonOnuIfHMinRx1024To1518Octs OBJECT-TYPE
        SYNTAX       Counter64
        MAX-ACCESS   read-only
        STATUS       current
        DESCRIPTION
            "The minutes interval packets (including bad
            packets) received that were between
            1024 and 1518 octets in length inclusive
            (excluding framing bits but including FCS octets)."
        ::= {zxAnPonOnuIfHisMinPerfEntry 20 }
        
    zxAnPonOnuIfHMinRxFragments  OBJECT-TYPE
        SYNTAX      Counter64
        MAX-ACCESS  read-only
        STATUS      current
        DESCRIPTION
            "The minutes interval packets received that were less 
            than 64 octets in length (excluding framing bits but including
            FCS octets) and had either a bad Frame Check Sequence
            (FCS) with an integral number of octets (FCS Error) or a
            bad FCS with a non-integral number of octets (Alignment
            Error)."
        ::= { zxAnPonOnuIfHisMinPerfEntry 21}
        
    zxAnPonOnuIfHMinRxJabbers OBJECT-TYPE
        SYNTAX      Counter64
        MAX-ACCESS  read-only
        STATUS      current
        DESCRIPTION
            "The minutes interval packets received that were
            longer than 1518 octets (excluding framing bits,
            but including FCS octets), and had either a bad
            Frame Check Sequence (FCS) with an integral number
            of octets (FCS Error) or a bad FCS with a non-integral
            number of octets (Alignment Error)."
        ::= { zxAnPonOnuIfHisMinPerfEntry 22}

    zxAnPonOnuIfHMinTxOctets OBJECT-TYPE
        SYNTAX       Counter64
        MAX-ACCESS   read-only
        STATUS       current
        DESCRIPTION
            "The minutes interval octets of data (including
            those in bad packets) sent on the
            network (excluding framing bits but including
            FCS octets)."
        ::= {zxAnPonOnuIfHisMinPerfEntry 36 }

    zxAnPonOnuIfHMinTxPkts OBJECT-TYPE
        SYNTAX       Counter64
        MAX-ACCESS   read-only
        STATUS       current
        DESCRIPTION
            "The minutes interval packets (including bad packets,
            broadcast packets, and multicast packets) transmitted."
        ::= {zxAnPonOnuIfHisMinPerfEntry 37 }

    zxAnPonOnuIfHMinTxUcastPkts OBJECT-TYPE
        SYNTAX       Counter64
        MAX-ACCESS   read-only
        STATUS       current
        DESCRIPTION
            "The minutes interval good packets transmitted that were
            directed to a unicast address."
        ::= {zxAnPonOnuIfHisMinPerfEntry 38 }

    zxAnPonOnuIfHMinTxNUcastPkts OBJECT-TYPE
        SYNTAX       Counter64
        MAX-ACCESS   read-only
        STATUS       current
        DESCRIPTION
            "The minutes interval good packets transmitted that were
            directed to a non-unicast address."
        ::= {zxAnPonOnuIfHisMinPerfEntry 39 }

    zxAnPonOnuIfHMinTxMcastPkts OBJECT-TYPE
        SYNTAX       Counter64
        MAX-ACCESS   read-only
        STATUS       current
        DESCRIPTION
            "The minutes interval good packets transmitted that were
            directed to a multicast address."
        ::= {zxAnPonOnuIfHisMinPerfEntry 40 }

    zxAnPonOnuIfHMinTxBcastPkts OBJECT-TYPE
        SYNTAX       Counter64
        MAX-ACCESS   read-only
        STATUS       current
        DESCRIPTION
            "The minutes interval good packets transmitted that were
            directed to the broadcast address.  Note that this does not include 
            multicast packets."
        ::= {zxAnPonOnuIfHisMinPerfEntry 41 }

    zxAnPonOnuIfHMinTxDiscardPkts OBJECT-TYPE
        SYNTAX       Counter64
        MAX-ACCESS   read-only
        STATUS       current
        DESCRIPTION
            "The minutes interval discarded packets transmitted."
        ::= {zxAnPonOnuIfHisMinPerfEntry 42 }

    zxAnPonOnuIfHMinTxErrPkts OBJECT-TYPE
        SYNTAX       Counter64
        MAX-ACCESS   read-only
        STATUS       current
        DESCRIPTION
            "The minutes interval error packets transmitted."
        ::= {zxAnPonOnuIfHisMinPerfEntry 43 }
        
    zxAnPonOnuIfHMinTxCrcAlignErrors OBJECT-TYPE
        SYNTAX      Counter64
        MAX-ACCESS  read-only
        STATUS      current
        DESCRIPTION
            "The minutes interval packets transmitted that
            had a length (excluding framing bits, but including FCS octets)
            of between 64 and 1518 octets, inclusive, but had either a bad
            Frame Check Sequence (FCS) with an integral number of octets 
            (FCS Error) or a bad FCS with a non-integral number of octets
            (Alignment Error)."
        ::= { zxAnPonOnuIfHisMinPerfEntry 44}

    zxAnPonOnuIfHMinTxUndersizePkts OBJECT-TYPE
        SYNTAX      Counter64
        MAX-ACCESS  read-only
        STATUS      current
        DESCRIPTION
            "The minutes interval packets transmitted that were
            less than 64 octets long (excluding framing bits,but including
            FCS octets) and were otherwise well
            formed."
        ::= { zxAnPonOnuIfHisMinPerfEntry 45}
            
    zxAnPonOnuIfHMinTxOversizePkts OBJECT-TYPE
        SYNTAX      Counter64
        MAX-ACCESS  read-only
        STATUS      current
        DESCRIPTION
            "The minutes interval packets transmitted that were
            longer than 1518 octets (excluding framing bits, but including FCS
            octets) and were otherwise well formed."
        ::= { zxAnPonOnuIfHisMinPerfEntry 46}
    
    zxAnPonOnuIfHMinTxPkts64Octets OBJECT-TYPE
        SYNTAX       Counter64
        MAX-ACCESS   read-only
        STATUS       current
        DESCRIPTION
            "The minutes interval packets (including bad
            packets) transmitted that were 64 octets in length
            (excluding framing bits but including FCS octets)."
        ::= {zxAnPonOnuIfHisMinPerfEntry 47 }

    zxAnPonOnuIfHMinTx65To127Octs OBJECT-TYPE
        SYNTAX       Counter64
        MAX-ACCESS   read-only
        STATUS       current
        DESCRIPTION
            "The minutes interval packets (including bad
            packets) transmitted that were between 65 and 127 octets in
            length inclusive (excluding framing bits but including FCS octets)."
        ::= {zxAnPonOnuIfHisMinPerfEntry 48 }

    zxAnPonOnuIfHMinTx128To255Octs OBJECT-TYPE
        SYNTAX       Counter64
        MAX-ACCESS   read-only
        STATUS       current
        DESCRIPTION
            "The minutes interval packets (including bad
            packets) transmitted that were between
            128 and 255 octets in length inclusive
            (excluding framing bits but including FCS octets)."
        ::= {zxAnPonOnuIfHisMinPerfEntry 49}

    zxAnPonOnuIfHMinTx256To511Octs OBJECT-TYPE
        SYNTAX       Counter64
        MAX-ACCESS   read-only
        STATUS       current
        DESCRIPTION
            "The minutes interval packets (including bad
            packets) transmitted that were between
            256 and 511 octets in length inclusive
            (excluding framing bits but including FCS octets)."
        ::= {zxAnPonOnuIfHisMinPerfEntry 50 }

    zxAnPonOnuIfHMinTx512To1023Octs OBJECT-TYPE
        SYNTAX       Counter64
        MAX-ACCESS   read-only
        STATUS       current
        DESCRIPTION
            "The minutes interval packets (including bad
            packets) transmitted that were between
            512 and 1023 octets in length inclusive
            (excluding framing bits but including FCS octets)."
        ::= {zxAnPonOnuIfHisMinPerfEntry 51 }

    zxAnPonOnuIfHMinTx1024To1518Octs OBJECT-TYPE
        SYNTAX       Counter64
        MAX-ACCESS   read-only
        STATUS       current
        DESCRIPTION
            "The minutes interval packets (including bad
            packets) transmitted that were between
            1024 and 1518 octets in length inclusive
            (excluding framing bits but including FCS octets)."
        ::= {zxAnPonOnuIfHisMinPerfEntry 52 }
        
    zxAnPonOnuIfHMinTxFragments  OBJECT-TYPE
        SYNTAX      Counter64
        MAX-ACCESS  read-only
        STATUS      current
        DESCRIPTION
            "The minutes interval packets transmitted that were less 
            than 64 octets in length (excluding framing bits but including
            FCS octets) and had either a bad Frame Check Sequence
            (FCS) with an integral number of octets (FCS Error) or a
            bad FCS with a non-integral number of octets (Alignment
            Error)."
        ::= { zxAnPonOnuIfHisMinPerfEntry 53}
        
    zxAnPonOnuIfHMinTxJabbers OBJECT-TYPE
        SYNTAX      Counter64
        MAX-ACCESS  read-only
        STATUS      current
        DESCRIPTION
            "The minutes interval packets transmitted that were
            longer than 1518 octets (excluding framing bits,
            but including FCS octets), and had either a bad
            Frame Check Sequence (FCS) with an integral number
            of octets (FCS Error) or a bad FCS with a non-integral
            number of octets (Alignment Error)."
        ::= { zxAnPonOnuIfHisMinPerfEntry 54}   
        
    zxAnPonOnuIfHMinCollisions OBJECT-TYPE
        SYNTAX      Counter64
        MAX-ACCESS  read-only
        STATUS      current
        DESCRIPTION
            "The minutes interval best estimate of collisions
            on this onu interface."
        ::= { zxAnPonOnuIfHisMinPerfEntry 70}

    zxAnPonOnuIfHMinDropEvents OBJECT-TYPE
        SYNTAX      Counter64
        MAX-ACCESS  read-only
        STATUS      current
        DESCRIPTION
            "The minutes interval events in which packets
            were dropped by the probe due to lack of resources."
        ::= { zxAnPonOnuIfHisMinPerfEntry 71}
        
--------------------------------------------------------------------------------
--  zxAnPonOnuIfHis1DayPerfTable
--------------------------------------------------------------------------------
    zxAnPonOnuIfHis1DayPerfTable OBJECT-TYPE
        SYNTAX         SEQUENCE OF ZxAnPonOnuIfHis1DayPerfEntry
        MAX-ACCESS     not-accessible
        STATUS         current
        DESCRIPTION
            "The 1 day interval performance data table of PON ONU."
        ::= { zxAnPonOnuPerfObjects 6 }

    zxAnPonOnuIfHis1DayPerfEntry OBJECT-TYPE
        SYNTAX         ZxAnPonOnuIfHis1DayPerfEntry
        MAX-ACCESS     not-accessible
        STATUS         current
        DESCRIPTION
            "The 1 day interval performance data entry of interfaces."
        INDEX    { ifIndex,zxAnPonOnuIndex,zxAnPonOnuIfH1DIntervalNo}
        ::= { zxAnPonOnuIfHis1DayPerfTable 1}

    ZxAnPonOnuIfHis1DayPerfEntry ::=
        SEQUENCE{
                zxAnPonOnuIfH1DIntervalNo             Integer32,
                zxAnPonOnuIfH1DValidData              TruthValue,
                zxAnPonOnuIfH1DDateAndTime            DateAndTime,
                zxAnPonOnuIfH1DRxOctets               Counter64,
                zxAnPonOnuIfH1DRxPkts                 Counter64,
                zxAnPonOnuIfH1DRxUcastPkts            Counter64,
                zxAnPonOnuIfH1DRxNUcastPkts           Counter64,
                zxAnPonOnuIfH1DRxMcastPkts            Counter64,
                zxAnPonOnuIfH1DRxBcastPkts            Counter64,
                zxAnPonOnuIfH1DRxDiscardPkts          Counter64,
                zxAnPonOnuIfH1DRxErrPkts              Counter64,
                zxAnPonOnuIfH1DRxCrcAlignErrors       Counter64,
                zxAnPonOnuIfH1DRxUndersizePkts        Counter64,
                zxAnPonOnuIfH1DRxOversizePkts         Counter64,
                zxAnPonOnuIfH1DRx64Octs               Counter64,
                zxAnPonOnuIfH1DRx65To127Octs          Counter64,
                zxAnPonOnuIfH1DRx128To255Octs         Counter64,
                zxAnPonOnuIfH1DRx256To511Octs         Counter64,
                zxAnPonOnuIfH1DRx512To1023Octs        Counter64,
                zxAnPonOnuIfH1DRx1024To1518Octs       Counter64,
                zxAnPonOnuIfH1DRxFragments            Counter64,
                zxAnPonOnuIfH1DRxJabbers              Counter64,
                zxAnPonOnuIfH1DTxOctets               Counter64,
                zxAnPonOnuIfH1DTxPkts                 Counter64,
                zxAnPonOnuIfH1DTxUcastPkts            Counter64,
                zxAnPonOnuIfH1DTxNUcastPkts           Counter64,
                zxAnPonOnuIfH1DTxMcastPkts            Counter64,
                zxAnPonOnuIfH1DTxBcastPkts            Counter64,
                zxAnPonOnuIfH1DTxDiscardPkts          Counter64,
                zxAnPonOnuIfH1DTxErrPkts              Counter64,
                zxAnPonOnuIfH1DTxCrcAlignErrors       Counter64,
                zxAnPonOnuIfH1DTxUndersizePkts        Counter64,
                zxAnPonOnuIfH1DTxOversizePkts         Counter64,
                zxAnPonOnuIfH1DTxPkts64Octets         Counter64,
                zxAnPonOnuIfH1DTx65To127Octs          Counter64,
                zxAnPonOnuIfH1DTx128To255Octs         Counter64,
                zxAnPonOnuIfH1DTx256To511Octs         Counter64,
                zxAnPonOnuIfH1DTx512To1023Octs        Counter64,
                zxAnPonOnuIfH1DTx1024To1518Octs       Counter64,
                zxAnPonOnuIfH1DTxFragments            Counter64,
                zxAnPonOnuIfH1DTxJabbers              Counter64,
                zxAnPonOnuIfH1DCollisions             Counter64,
                zxAnPonOnuIfH1DDropEvents             Counter64
                }

    zxAnPonOnuIfH1DIntervalNo  OBJECT-TYPE 
        SYNTAX      Integer32(1..7)
        MAX-ACCESS  not-accessible
        STATUS      current
        DESCRIPTION     
             "Performance Data 
               
               Interval  1 is the the most recent previous interval
               Interval 7 is 1 week ago.
               Intervals from 2 to 7 are optional."
        ::= { zxAnPonOnuIfHis1DayPerfEntry 1 }
        
   zxAnPonOnuIfH1DValidData OBJECT-TYPE
        SYNTAX      TruthValue
        MAX-ACCESS  read-only
        STATUS      current
        DESCRIPTION     
             "Performance data valid flag.
              true(1) means valid.
              false(2) means invalid and the performace data is useless."
        ::= { zxAnPonOnuIfHis1DayPerfEntry 2} 
        
    zxAnPonOnuIfH1DDateAndTime     OBJECT-TYPE   
        SYNTAX      DateAndTime
        MAX-ACCESS  read-only
        STATUS      current
        DESCRIPTION     
             "1 day performace data interval create time."
        ::= { zxAnPonOnuIfHis1DayPerfEntry 3 }
        
    zxAnPonOnuIfH1DRxOctets OBJECT-TYPE
        SYNTAX       Counter64
        MAX-ACCESS   read-only
        STATUS       current
        DESCRIPTION
            "The 1 day interval octets of data (including
         those in bad packets) received on the
         network (excluding framing bits but including
         FCS octets)."
        ::= {zxAnPonOnuIfHis1DayPerfEntry 4 }

    zxAnPonOnuIfH1DRxPkts OBJECT-TYPE
        SYNTAX       Counter64
        MAX-ACCESS   read-only
        STATUS       current
        DESCRIPTION
            "The 1 day interval packets (including bad packets,
         broadcast packets, and multicast packets) received."
        ::= {zxAnPonOnuIfHis1DayPerfEntry 5 }

    zxAnPonOnuIfH1DRxUcastPkts OBJECT-TYPE
        SYNTAX       Counter64
        MAX-ACCESS   read-only
        STATUS       current
        DESCRIPTION
            "The 1 day interval good packets received that were
         directed to a unicast address."
        ::= {zxAnPonOnuIfHis1DayPerfEntry 6 }

    zxAnPonOnuIfH1DRxNUcastPkts OBJECT-TYPE
        SYNTAX       Counter64
        MAX-ACCESS   read-only
        STATUS       current
        DESCRIPTION
            "The 1 day interval good packets received that were
         directed to a non-unicast address."
        ::= {zxAnPonOnuIfHis1DayPerfEntry 7 }

    zxAnPonOnuIfH1DRxMcastPkts OBJECT-TYPE
        SYNTAX       Counter64
        MAX-ACCESS   read-only
        STATUS       current
        DESCRIPTION
            "The 1 day interval good packets received that were
         directed to a multicast address."
        ::= {zxAnPonOnuIfHis1DayPerfEntry 8 }

    zxAnPonOnuIfH1DRxBcastPkts OBJECT-TYPE
        SYNTAX       Counter64
        MAX-ACCESS   read-only
        STATUS       current
        DESCRIPTION
            "The 1 day interval good packets received that were
         directed to the broadcast address.  Note that this
         does not include multicast packets."
        ::= {zxAnPonOnuIfHis1DayPerfEntry 9 }

    zxAnPonOnuIfH1DRxDiscardPkts OBJECT-TYPE
        SYNTAX       Counter64
        MAX-ACCESS   read-only
        STATUS       current
        DESCRIPTION
            "The 1 day interval discarded packets received."
        ::= {zxAnPonOnuIfHis1DayPerfEntry 10 }

    zxAnPonOnuIfH1DRxErrPkts OBJECT-TYPE
        SYNTAX       Counter64
        MAX-ACCESS   read-only
        STATUS       current
        DESCRIPTION
            "The 1 day interval error packets received."
        ::= {zxAnPonOnuIfHis1DayPerfEntry 11 }

    zxAnPonOnuIfH1DRxCrcAlignErrors OBJECT-TYPE
        SYNTAX       Counter64
        MAX-ACCESS   read-only
        STATUS       current
        DESCRIPTION
            "The 1 day interval packets received that
         had a length (excluding framing bits, but
         including FCS octets) of between 64 and 1518
         octets, inclusive, but had either a bad
         Frame Check Sequence (FCS) with an integral
         number of octets (FCS Error) or a bad FCS with
         a non-integral number of octets (Alignment Error)."
        ::= {zxAnPonOnuIfHis1DayPerfEntry 12 }

    zxAnPonOnuIfH1DRxUndersizePkts OBJECT-TYPE
        SYNTAX       Counter64
        MAX-ACCESS   read-only
        STATUS       current
        DESCRIPTION
            "The 1 day interval packets received that were
         less than 64 octets long (excluding framing bits,
         but including FCS octets) and were otherwise well
         formed."
        ::= {zxAnPonOnuIfHis1DayPerfEntry 13 }

    zxAnPonOnuIfH1DRxOversizePkts OBJECT-TYPE
        SYNTAX       Counter64
        MAX-ACCESS   read-only
        STATUS       current
        DESCRIPTION
            "The 1 day interval packets received that were
         longer than 1518 octets (excluding framing bits,
         but including FCS octets) and were otherwise
         well formed."
        ::= {zxAnPonOnuIfHis1DayPerfEntry 14 }     

    zxAnPonOnuIfH1DRx64Octs      OBJECT-TYPE
        SYNTAX       Counter64
        MAX-ACCESS   read-only
        STATUS       current
        DESCRIPTION
            "The 1 day interval packets (including bad
         packets) received that were 64 octets in length
         (excluding framing bits but including FCS octets)."
        ::= {zxAnPonOnuIfHis1DayPerfEntry 15 }

    zxAnPonOnuIfH1DRx65To127Octs OBJECT-TYPE
        SYNTAX       Counter64
        MAX-ACCESS   read-only
        STATUS       current
        DESCRIPTION
            "The 1 day interval packets (including bad
         packets) received that were between
         65 and 127 octets in length inclusive
         (excluding framing bits but including FCS octets)."
        ::= {zxAnPonOnuIfHis1DayPerfEntry 16 }

    zxAnPonOnuIfH1DRx128To255Octs OBJECT-TYPE
        SYNTAX       Counter64
        MAX-ACCESS   read-only
        STATUS       current
        DESCRIPTION
            "The 1 day interval packets (including bad
         packets) received that were between
         128 and 255 octets in length inclusive
         (excluding framing bits but including FCS octets)."
        ::= {zxAnPonOnuIfHis1DayPerfEntry 17 }

    zxAnPonOnuIfH1DRx256To511Octs OBJECT-TYPE
        SYNTAX       Counter64
        MAX-ACCESS   read-only
        STATUS       current
        DESCRIPTION
            "The 1 day interval packets (including bad
         packets) received that were between
         256 and 511 octets in length inclusive
         (excluding framing bits but including FCS octets)."
        ::= {zxAnPonOnuIfHis1DayPerfEntry 18 }

    zxAnPonOnuIfH1DRx512To1023Octs OBJECT-TYPE
        SYNTAX       Counter64
        MAX-ACCESS   read-only
        STATUS       current
        DESCRIPTION
            "The 1 day interval packets (including bad
         packets) received that were between
         512 and 1023 octets in length inclusive
         (excluding framing bits but including FCS octets)."
        ::= {zxAnPonOnuIfHis1DayPerfEntry 19 }

    zxAnPonOnuIfH1DRx1024To1518Octs OBJECT-TYPE
        SYNTAX       Counter64
        MAX-ACCESS   read-only
        STATUS       current
        DESCRIPTION
            "The 1 day interval packets (including bad
         packets) received that were between
         1024 and 1518 octets in length inclusive
         (excluding framing bits but including FCS octets)."
        ::= {zxAnPonOnuIfHis1DayPerfEntry 20 }
        
    zxAnPonOnuIfH1DRxFragments  OBJECT-TYPE
        SYNTAX      Counter64
        MAX-ACCESS  read-only
        STATUS      current
        DESCRIPTION
            "The 1 day interval packets received that were less 
            than 64 octets in length (excluding framing bits but including
         FCS octets) and had either a bad Frame Check Sequence
         (FCS) with an integral number of octets (FCS Error) or a
         bad FCS with a non-integral number of octets (Alignment
         Error)."
        ::= { zxAnPonOnuIfHis1DayPerfEntry 21}
        
    zxAnPonOnuIfH1DRxJabbers OBJECT-TYPE
        SYNTAX      Counter64
        MAX-ACCESS  read-only
        STATUS      current
        DESCRIPTION
            "The 1 day interval packets received that were
         longer than 1518 octets (excluding framing bits,
         but including FCS octets), and had either a bad
         Frame Check Sequence (FCS) with an integral number
         of octets (FCS Error) or a bad FCS with a non-integral
         number of octets (Alignment Error)."
        ::= { zxAnPonOnuIfHis1DayPerfEntry 22}

    zxAnPonOnuIfH1DTxOctets OBJECT-TYPE
        SYNTAX       Counter64
        MAX-ACCESS   read-only
        STATUS       current
        DESCRIPTION
            "The 1 day interval octets of data (including
         those in bad packets) sent on the
         network (excluding framing bits but including
         FCS octets)."
        ::= {zxAnPonOnuIfHis1DayPerfEntry 36 }

    zxAnPonOnuIfH1DTxPkts OBJECT-TYPE
        SYNTAX       Counter64
        MAX-ACCESS   read-only
        STATUS       current
        DESCRIPTION
            "The 1 day interval packets (including bad packets,
         broadcast packets, and multicast packets) transmitted."
        ::= {zxAnPonOnuIfHis1DayPerfEntry 37 }

    zxAnPonOnuIfH1DTxUcastPkts OBJECT-TYPE
        SYNTAX       Counter64
        MAX-ACCESS   read-only
        STATUS       current
        DESCRIPTION
            "The 1 day interval good packets transmitted that were
         directed to a unicast address."
        ::= {zxAnPonOnuIfHis1DayPerfEntry 38 }

    zxAnPonOnuIfH1DTxNUcastPkts OBJECT-TYPE
        SYNTAX       Counter64
        MAX-ACCESS   read-only
        STATUS       current
        DESCRIPTION
            "The 1 day interval good packets transmitted that were
         directed to a non-unicast address."
        ::= {zxAnPonOnuIfHis1DayPerfEntry 39 }

    zxAnPonOnuIfH1DTxMcastPkts OBJECT-TYPE
        SYNTAX       Counter64
        MAX-ACCESS   read-only
        STATUS       current
        DESCRIPTION
            "The 1 day interval good packets transmitted that were
         directed to a multicast address."
        ::= {zxAnPonOnuIfHis1DayPerfEntry 40 }

    zxAnPonOnuIfH1DTxBcastPkts OBJECT-TYPE
        SYNTAX       Counter64
        MAX-ACCESS   read-only
        STATUS       current
        DESCRIPTION
            "The 1 day interval good packets transmitted that were
         directed to the broadcast address.  Note that this does not include 
         multicast packets."
        ::= {zxAnPonOnuIfHis1DayPerfEntry 41 }

    zxAnPonOnuIfH1DTxDiscardPkts OBJECT-TYPE
        SYNTAX       Counter64
        MAX-ACCESS   read-only
        STATUS       current
        DESCRIPTION
            "The 1 day interval discarded packets transmitted."
        ::= {zxAnPonOnuIfHis1DayPerfEntry 42 }

    zxAnPonOnuIfH1DTxErrPkts OBJECT-TYPE
        SYNTAX       Counter64
        MAX-ACCESS   read-only
        STATUS       current
        DESCRIPTION
            "The 1 day interval error packets transmitted."
        ::= {zxAnPonOnuIfHis1DayPerfEntry 43 }
        
    zxAnPonOnuIfH1DTxCrcAlignErrors OBJECT-TYPE
        SYNTAX      Counter64
        MAX-ACCESS  read-only
        STATUS      current
        DESCRIPTION
            "The 1 day interval packets transmitted that
         had a length (excluding framing bits, but including FCS octets)
         of between 64 and 1518 octets, inclusive, but had either a bad
         Frame Check Sequence (FCS) with an integral number of octets 
         (FCS Error) or a bad FCS with a non-integral number of octets
         (Alignment Error)."
        ::= { zxAnPonOnuIfHis1DayPerfEntry 44}

    zxAnPonOnuIfH1DTxUndersizePkts OBJECT-TYPE
        SYNTAX      Counter64
        MAX-ACCESS  read-only
        STATUS      current
        DESCRIPTION
            "The 1 day interval packets transmitted that were
         less than 64 octets long (excluding framing bits,but including
         FCS octets) and were otherwise well
         formed."
        ::= { zxAnPonOnuIfHis1DayPerfEntry 45}
            
    zxAnPonOnuIfH1DTxOversizePkts OBJECT-TYPE
        SYNTAX      Counter64
        MAX-ACCESS  read-only
        STATUS      current
        DESCRIPTION
            "The 1 day interval packets transmitted that were
         longer than 1518 octets (excluding framing bits, but including FCS
         octets) and were otherwise well formed."
        ::= { zxAnPonOnuIfHis1DayPerfEntry 46}
    
    zxAnPonOnuIfH1DTxPkts64Octets OBJECT-TYPE
        SYNTAX       Counter64
        MAX-ACCESS   read-only
        STATUS       current
        DESCRIPTION
            "The 1 day interval packets (including bad
         packets) transmitted that were 64 octets in length
         (excluding framing bits but including FCS octets)."
        ::= {zxAnPonOnuIfHis1DayPerfEntry 47 }

    zxAnPonOnuIfH1DTx65To127Octs OBJECT-TYPE
        SYNTAX       Counter64
        MAX-ACCESS   read-only
        STATUS       current
        DESCRIPTION
            "The 1 day interval packets (including bad
         packets) transmitted that were between 65 and 127 octets in
         length inclusive (excluding framing bits but including FCS octets)."
        ::= {zxAnPonOnuIfHis1DayPerfEntry 48 }

    zxAnPonOnuIfH1DTx128To255Octs OBJECT-TYPE
        SYNTAX       Counter64
        MAX-ACCESS   read-only
        STATUS       current
        DESCRIPTION
            "The 1 day interval packets (including bad
         packets) transmitted that were between
         128 and 255 octets in length inclusive
         (excluding framing bits but including FCS octets)."
        ::= {zxAnPonOnuIfHis1DayPerfEntry 49}

    zxAnPonOnuIfH1DTx256To511Octs OBJECT-TYPE
        SYNTAX       Counter64
        MAX-ACCESS   read-only
        STATUS       current
        DESCRIPTION
            "The 1 day interval packets (including bad
         packets) transmitted that were between
         256 and 511 octets in length inclusive
         (excluding framing bits but including FCS octets)."
        ::= {zxAnPonOnuIfHis1DayPerfEntry 50 }

    zxAnPonOnuIfH1DTx512To1023Octs OBJECT-TYPE
        SYNTAX       Counter64
        MAX-ACCESS   read-only
        STATUS       current
        DESCRIPTION
            "The 1 day interval packets (including bad
         packets) transmitted that were between
         512 and 1023 octets in length inclusive
         (excluding framing bits but including FCS octets)."
        ::= {zxAnPonOnuIfHis1DayPerfEntry 51 }

    zxAnPonOnuIfH1DTx1024To1518Octs OBJECT-TYPE
        SYNTAX       Counter64
        MAX-ACCESS   read-only
        STATUS       current
        DESCRIPTION
            "The 1 day interval packets (including bad
         packets) transmitted that were between
         1024 and 1518 octets in length inclusive
         (excluding framing bits but including FCS octets)."
        ::= {zxAnPonOnuIfHis1DayPerfEntry 52 }
        
    zxAnPonOnuIfH1DTxFragments  OBJECT-TYPE
        SYNTAX      Counter64
        MAX-ACCESS  read-only
        STATUS      current
        DESCRIPTION
            "The 1 day interval packets transmitted that were less 
            than 64 octets in length (excluding framing bits but including
         FCS octets) and had either a bad Frame Check Sequence
         (FCS) with an integral number of octets (FCS Error) or a
         bad FCS with a non-integral number of octets (Alignment
         Error)."
        ::= { zxAnPonOnuIfHis1DayPerfEntry 53}
        
    zxAnPonOnuIfH1DTxJabbers OBJECT-TYPE
        SYNTAX      Counter64
        MAX-ACCESS  read-only
        STATUS      current
        DESCRIPTION
            "The 1 day interval packets transmitted that were
         longer than 1518 octets (excluding framing bits,
         but including FCS octets), and had either a bad
         Frame Check Sequence (FCS) with an integral number
         of octets (FCS Error) or a bad FCS with a non-integral
         number of octets (Alignment Error)."
        ::= { zxAnPonOnuIfHis1DayPerfEntry 54}
        
    zxAnPonOnuIfH1DCollisions OBJECT-TYPE
        SYNTAX      Counter64
        MAX-ACCESS  read-only
        STATUS      current
        DESCRIPTION
            "The 1 day interval best estimate of collisions
         on this onu interface."
        ::= { zxAnPonOnuIfHis1DayPerfEntry 70}

    zxAnPonOnuIfH1DDropEvents OBJECT-TYPE
        SYNTAX      Counter64
        MAX-ACCESS  read-only
        STATUS      current
        DESCRIPTION
            "The 1 day interval events in which packets
         were dropped by the probe due to lack of resources."
        ::= { zxAnPonOnuIfHis1DayPerfEntry 71}
--------------------------------------------------------------------------------
-- zxAnPonOnuPerfAlmPrfTable                  
--------------------------------------------------------------------------------                                               
    zxAnPonOnuPerfAlmPrfTable   OBJECT-TYPE   
        SYNTAX      SEQUENCE OF ZxAnPonOnuPerfAlmPrfEntry
        MAX-ACCESS  not-accessible             
        STATUS      current                    
        DESCRIPTION                            
             "The performance alarm threshold profile 
             list table of interfaces."
        ::= { zxAnPonOnuPerfObjects 7 }

    zxAnPonOnuPerfAlmPrfEntry   OBJECT-TYPE
        SYNTAX      ZxAnPonOnuPerfAlmPrfEntry
        MAX-ACCESS  not-accessible
        STATUS      current
        DESCRIPTION 
            "The performance alarm threshold profile 
            applying entry of interfaces."
        INDEX   { zxAnPonOnuPerfAlmPrfName }
        ::= { zxAnPonOnuPerfAlmPrfTable 1 }

    ZxAnPonOnuPerfAlmPrfEntry ::= SEQUENCE {
        zxAnPonOnuPerfAlmPrfName           DisplayString,
        zxAnPonOnuPerfAlmPrfRowStatus      RowStatus
        }
        
    zxAnPonOnuPerfAlmPrfName  OBJECT-TYPE 
        SYNTAX      DisplayString(SIZE (1 .. 32))
        MAX-ACCESS  not-accessible
        STATUS      current
        DESCRIPTION     
            "The performance alarm threshold profile name."
        ::= { zxAnPonOnuPerfAlmPrfEntry 1 }
               
    zxAnPonOnuPerfAlmPrfRowStatus  OBJECT-TYPE 
        SYNTAX      RowStatus
        MAX-ACCESS  read-create
        STATUS      current
        DESCRIPTION     
            "The status of this conceptual row.
             
             The supported actions of this conceptual row only include:
             'createAndGo' and 'destroy'.

             To create a row in this table, a manager must
             set this object to createAndGo(4).
            
             To delete a row in this table, a manager must
             set this object to destroy(6). 
             
             To query this object, always return 1."
        ::= { zxAnPonOnuPerfAlmPrfEntry 50 }

--------------------------------------------------------------------------------
-- zxAnPonOnuPerfAlmPrfConfTable
--------------------------------------------------------------------------------

    zxAnPonOnuPerfAlmPrfConfTable   OBJECT-TYPE
        SYNTAX      SEQUENCE OF ZxAnPonOnuPerfAlmPrfConfEntry
        MAX-ACCESS  not-accessible
        STATUS      current
        DESCRIPTION 
             "The performance alarm threshold profile table of interfaces."
        ::= { zxAnPonOnuPerfObjects 8 }

    zxAnPonOnuPerfAlmPrfConfEntry   OBJECT-TYPE
        SYNTAX      ZxAnPonOnuPerfAlmPrfConfEntry
        MAX-ACCESS  not-accessible
        STATUS      current
        DESCRIPTION 
            "An entry in zxAnPonOnuPerfAlmPrfConfTable.
            When a manager wants to create or modify an ONU performance 
            alarm threshold item,it must comply with the multi-variables 
            usage rule that all the mib variables related to same 
            fuction must be in one snmp set operation, the variables have
            only one type: mandatory.
            
            Mandatory variables must be in the one snmp set operation.
                   
            To create an ONU performance alarm threshold item on
            different level, alarm threshold ,restore threshold and 
            zxAnPonOnuPerfAlmConfRowStatus should be in one snmp set operation.
            The alarm threshold and restore threshold variables in the 
            one snmp set operationshould be on same level.
            Such as:
            zxAnPonOnuPerfRiseAlmThresh and zxAnPonOnuPerfRiseAlmClrThresh,
            zxAnPonOnuPerfRiseWarnThresh and zxAnPonOnuPerfRiseWarnClrThresh,
            zxAnPonOnuPerfFallWarnThresh and zxAnPonOnuPerfFallWarnClrThresh,
            zxAnPonOnuPerfFallAlmThresh and zxAnPonOnuPerfFallAlmClrThresh.
                          
            To modify an ONU performance alarm threshold item on
            different level,alarm threshold and restore threshold
            should be also in the one snmp set 
            operation regardless of modifying alarm or restore threshold 
            value alone.
            The alarm threshold and restore threshold variables in the 
            one snmp set operationshould be on same level.
            Such as:
            zxAnPonOnuPerfRiseAlmThresh and zxAnPonOnuPerfRiseAlmClrThresh,
            zxAnPonOnuPerfRiseWarnThresh and zxAnPonOnuPerfRiseWarnClrThresh,
            zxAnPonOnuPerfFallWarnThresh and zxAnPonOnuPerfFallWarnClrThresh,
            zxAnPonOnuPerfFallAlmThresh and zxAnPonOnuPerfFallAlmClrThresh.
            
            To remove an ONU performance alarm threshold item, only 
            zxAnPonOnuPerfAlmConfRowStatus should be set to destroy(6) while
            all levels of this ONU performance alarm threshold item will be 
            removed."
        INDEX   { zxAnPonOnuPerfAlmPrfName, zxAnPonOnuPerfVariable }
        ::= { zxAnPonOnuPerfAlmPrfConfTable 1 }

    ZxAnPonOnuPerfAlmPrfConfEntry ::= SEQUENCE {
        zxAnPonOnuPerfVariable                OBJECT IDENTIFIER,
        zxAnPonOnuPerfRiseAlmThresh           HCPerfCurrentCount,
        zxAnPonOnuPerfRiseAlmClrThresh        HCPerfCurrentCount,
        zxAnPonOnuPerfRiseWarnThresh          HCPerfCurrentCount,
        zxAnPonOnuPerfRiseWarnClrThresh       HCPerfCurrentCount,
        zxAnPonOnuPerfFallWarnThresh          HCPerfCurrentCount, 
        zxAnPonOnuPerfFallWarnClrThresh       HCPerfCurrentCount, 
        zxAnPonOnuPerfFallAlmThresh           HCPerfCurrentCount,
        zxAnPonOnuPerfFallAlmClrThresh        HCPerfCurrentCount,
        zxAnPonOnuPerfThreshUsed              BITS,
        zxAnPonOnuPerfAlmConfRowStatus        RowStatus
        }

    zxAnPonOnuPerfVariable  OBJECT-TYPE 
        SYNTAX      OBJECT IDENTIFIER
        MAX-ACCESS  not-accessible
        STATUS      current
        DESCRIPTION     
            "The object identifier of performance variables."
        ::= { zxAnPonOnuPerfAlmPrfConfEntry 1 }
        
    zxAnPonOnuPerfRiseAlmThresh  OBJECT-TYPE 
        SYNTAX      HCPerfCurrentCount
        MAX-ACCESS  read-create
        STATUS      current
        DESCRIPTION     
            "The threshold for rising alarm."
        ::= { zxAnPonOnuPerfAlmPrfConfEntry 2 }

    zxAnPonOnuPerfRiseAlmClrThresh  OBJECT-TYPE 
        SYNTAX      HCPerfCurrentCount
        MAX-ACCESS  read-create
        STATUS      current
        DESCRIPTION     
            "The threshold for rising alarm restore."
        ::= { zxAnPonOnuPerfAlmPrfConfEntry 3 }

    zxAnPonOnuPerfRiseWarnThresh  OBJECT-TYPE 
        SYNTAX      HCPerfCurrentCount
        MAX-ACCESS  read-create
        STATUS      current
        DESCRIPTION     
            "The threshold for rising warning."
        ::= { zxAnPonOnuPerfAlmPrfConfEntry 4 }

    zxAnPonOnuPerfRiseWarnClrThresh  OBJECT-TYPE 
        SYNTAX      HCPerfCurrentCount
        MAX-ACCESS  read-create
        STATUS      current
        DESCRIPTION     
            "The threshold for rising warning restore."
        ::= { zxAnPonOnuPerfAlmPrfConfEntry 5 }
        
    zxAnPonOnuPerfFallWarnThresh  OBJECT-TYPE 
        SYNTAX      HCPerfCurrentCount
        MAX-ACCESS  read-create
        STATUS      current
        DESCRIPTION     
            "The threshold for falling warning."
        ::= { zxAnPonOnuPerfAlmPrfConfEntry 6 }

    zxAnPonOnuPerfFallWarnClrThresh  OBJECT-TYPE 
        SYNTAX      HCPerfCurrentCount
        MAX-ACCESS  read-create
        STATUS      current
        DESCRIPTION     
            "The threshold for falling warning restore."
        ::= { zxAnPonOnuPerfAlmPrfConfEntry 7 }
        
    zxAnPonOnuPerfFallAlmThresh  OBJECT-TYPE 
        SYNTAX      HCPerfCurrentCount
        MAX-ACCESS  read-create
        STATUS      current
        DESCRIPTION     
            "The threshold for falling alarm."
        ::= { zxAnPonOnuPerfAlmPrfConfEntry 8 }

    zxAnPonOnuPerfFallAlmClrThresh  OBJECT-TYPE 
        SYNTAX      HCPerfCurrentCount
        MAX-ACCESS  read-create
        STATUS      current
        DESCRIPTION     
            "The threshold for falling alarm restore."
        ::= { zxAnPonOnuPerfAlmPrfConfEntry 9 }
        
    zxAnPonOnuPerfThreshUsed  OBJECT-TYPE 
         SYNTAX     BITS{
                    riseAlmThresh(0),
                    riseAlmClrThresh(1),
                    riseWarnThresh(2),
                    riseWarnClrThresh(3),
                    fallWarnThresh(4),
                    fallWarnClrThresh(5),
                    fallAlmThresh(6),
                    fallAlmClrThresh(7)
                    }
        MAX-ACCESS  read-create
        STATUS      current
        DESCRIPTION     
            "The threshold used flag for falling alarm restore."
        ::= { zxAnPonOnuPerfAlmPrfConfEntry 10 }

    zxAnPonOnuPerfAlmConfRowStatus  OBJECT-TYPE
        SYNTAX      RowStatus
        MAX-ACCESS  read-create
        STATUS      current
        DESCRIPTION     
            "The status of this conceptual row. 
             
             The supported actions of this conceptual row only include:
             'createAndGo' and 'destroy'.

             To create a row in this table, a manager must
             set this object to createAndGo(4).
             
             To delete a row in this table, a manager must
             set this object to destroy(6). 
             
             To query this object, always return 1."
        ::= { zxAnPonOnuPerfAlmPrfConfEntry 50 }
        
--------------------------------------------------------------------------------
-- zxAnPonOnuPerfAlmPrfApplyTable
--------------------------------------------------------------------------------

    zxAnPonOnuPerfAlmPrfApplyTable   OBJECT-TYPE
        SYNTAX      SEQUENCE OF ZxAnPonOnuPerfAlmPrfApplyEntry
        MAX-ACCESS  not-accessible
        STATUS      current
        DESCRIPTION 
             "The performance alarm threshold profile 
             applying table of interfaces."
        ::= { zxAnPonOnuPerfObjects 9 }

    zxAnPonOnuPerfAlmPrfApplyEntry   OBJECT-TYPE
        SYNTAX      ZxAnPonOnuPerfAlmPrfApplyEntry
        MAX-ACCESS  not-accessible
        STATUS      current
        DESCRIPTION 
            "An entry in zxAnPonOnuPerfAlmPrfApplyTable.
            The index 'zxAnPonOnuIndex' represents the normal ONU index.
            When a manager wants to apply an ONU performance alarm 
            profile to specificed ONU interface,it must comply with 
            the multi-variables usage rule that all the mib variables 
            related to same fuction must be in one snmp set operation, 
            the variables have only one type: mandatory.
            
            Mandatory variables must be in the one snmp set operation.
                   
            To apply an ONU performance alarm profile to the specificed ONU 
            interface, 'zxAnPonOnuPerfAlmPrf' and 
            'zxAnPonOnuAlmPrfApplyRowStatus' should be in the one snmp set 
            operation.
            
            To remove the application of an ONU performance alarm profile 
            to the specificed ONU interface, 
            only 'zxAnPonOnuAlmPrfApplyRowStatus' should be set to destroy(6)."
        INDEX   { ifIndex, zxAnPonOnuIndex }
        ::= { zxAnPonOnuPerfAlmPrfApplyTable 1 }

    ZxAnPonOnuPerfAlmPrfApplyEntry ::= SEQUENCE {
        zxAnPonOnuPerfAlmPrf            DisplayString,
        zxAnPonOnuAlmPrfApplyRowStatus  RowStatus
        }
        
    zxAnPonOnuPerfAlmPrf  OBJECT-TYPE 
        SYNTAX      DisplayString(SIZE (1 .. 32))
        MAX-ACCESS  read-create
        STATUS      current
        DESCRIPTION     
            "The performance alarm threshold profile."
        ::= { zxAnPonOnuPerfAlmPrfApplyEntry 1 }
               
    zxAnPonOnuAlmPrfApplyRowStatus  OBJECT-TYPE 
        SYNTAX      RowStatus
        MAX-ACCESS  read-create
        STATUS      current
        DESCRIPTION     
            "The status of this conceptual row.
             
             The supported actions of this conceptual row only include:
             'createAndGo' and 'destroy'.

             To create a row in this table, a manager must
             set this object to createAndGo(4).
            
             To delete a row in this table, a manager must
             set this object to destroy(6). 
             
             To query this object, always return 1."
        ::= { zxAnPonOnuPerfAlmPrfApplyEntry 50 }

-------------------------------------------------------------------------------
--  zxAnPonPerfConformance
------------------------------------------------------------------------------- 
zxAnPonPerfConformance         OBJECT IDENTIFIER ::= { zxAnPonPerfMib 4}

zxAnPonPerfCompliances         OBJECT IDENTIFIER ::= {zxAnPonPerfConformance 1}
zxAnPonPerfGroups              OBJECT IDENTIFIER ::= {zxAnPonPerfConformance 2}

zxAnPonPerfObjectConformance MODULE-COMPLIANCE
    STATUS current
    DESCRIPTION
        "The compliance statement for entities which implement the
         ZTE-AN-PON-PERF-MIB."
    MODULE
    MANDATORY-GROUPS{
                    zxAnPonIfPerfGroup
                    }
    ::= { zxAnPonPerfCompliances 1 }

--------------------------------------------------------------------------------
-- Units of Conformance
--------------------------------------------------------------------------------
zxAnPonIfPerfGroup OBJECT-GROUP
    OBJECTS         {
                    zxAnPonOltIfRxOctets,
                    zxAnPonOltIfRxPkts,
                    zxAnPonOltIfRxOctetRate,
                    zxAnPonOltIfRxPktRate,
                    zxAnPonOltIfRxOctetPeakRate,
                    zxAnPonOltIfRxPktPeakRate,
                    zxAnPonOltIfRxUcastPkts,
                    zxAnPonOltIfRxNUcastPkts,
                    zxAnPonOltIfRxMcastPkts,
                    zxAnPonOltIfRxBcastPkts,
                    zxAnPonOltIfRxDiscardPkts,
                    zxAnPonOltIfRxErrPkts,
                    zxAnPonOltIfRxPdr,
                    zxAnPonOltIfRxPer,
                    zxAnPonOltIfRxCrcAlignErrors,
                    zxAnPonOltIfRxUndersizePkts,
                    zxAnPonOltIfRxOversizePkts,          
                    zxAnPonOltIfRxPkts64Octets,
                    zxAnPonOltIfRxPkts65To127Octets,
                    zxAnPonOltIfRxPkts128To255Octets,
                    zxAnPonOltIfRxPkts256To511Octets,
                    zxAnPonOltIfRxPkts512To1023Oct,
                    zxAnPonOltIfRxPkts1024To1518Oct,
                    zxAnPonOltIfRxBwUtilization,
                    zxAnPonOltIfRxAvgBwUtilization,
                    zxAnPonOltIfRxFragments,
                    zxAnPonOltIfRxJabbers, 
                    zxAnPonOltIfTxOctets,
                    zxAnPonOltIfTxPkts,
                    zxAnPonOltIfTxOctetRate,
                    zxAnPonOltIfTxPktRate,
                    zxAnPonOltIfTxOctetPeakRate,
                    zxAnPonOltIfTxPktPeakRate,
                    zxAnPonOltIfTxUcastPkts,
                    zxAnPonOltIfTxNUcastPkts,
                    zxAnPonOltIfTxMcastPkts,
                    zxAnPonOltIfTxBcastPkts,
                    zxAnPonOltIfTxDiscardPkts,
                    zxAnPonOltIfTxErrPkts,
                    zxAnPonOltIfTxPdr,
                    zxAnPonOltIfTxPer,       
                    zxAnPonOltIfTxCrcAlignErrors,
                    zxAnPonOltIfTxUndersizePkts,                    
                    zxAnPonOltIfTxOversizePkts,
                    zxAnPonOltIfTxPkts64Octets,
                    zxAnPonOltIfTxPkts65To127Octets,
                    zxAnPonOltIfTxPkts128To255Octets,
                    zxAnPonOltIfTxPkts256To511Octets,
                    zxAnPonOltIfTxPkts512To1023Oct,
                    zxAnPonOltIfTxPkts1024To1518Oct,
                    zxAnPonOltIfTxBwUtilization,
                    zxAnPonOltIfTxAvgBwUtilization,
                    zxAnPonOltIfTxFragments,
                    zxAnPonOltIfTxJabbers,
                    zxAnPonOltIfRxCorrFecCodes,
                    zxAnPonOltIfRxErrFecCodes,
                    zxAnPonOltIfCollisions, 
                    zxAnPonOltIfDropEvents,      
                    zxAnPonOltIfCurrPerfReset,
                    zxAnPonOltIfC15MTimeElapsed,                                
                    zxAnPonOltIfC15MRxOctets,                                
                    zxAnPonOltIfC15MRxPkts,                                
                    zxAnPonOltIfC15MRxUcastPkts,                                
                    zxAnPonOltIfC15MRxNUcastPkts,                                
                    zxAnPonOltIfC15MRxMcastPkts,                                
                    zxAnPonOltIfC15MRxBcastPkts,                                
                    zxAnPonOltIfC15MRxDiscardPkts,                                
                    zxAnPonOltIfC15MRxErrPkts,                                
                    zxAnPonOltIfC15MRxCrcAlignErrors,                                
                    zxAnPonOltIfC15MRxUndersizePkts,                                
                    zxAnPonOltIfC15MRxOversizePkts,                                
                    zxAnPonOltIfC15MRx64Octs,                                
                    zxAnPonOltIfC15MRx65To127Octs,                                
                    zxAnPonOltIfC15MRx128To255Octs,                                
                    zxAnPonOltIfC15MRx256To511Octs,                                
                    zxAnPonOltIfC15MRx512To1023Octs,                                
                    zxAnPonOltIfC15MRx1024To1518Octs,                                
                    zxAnPonOltIfC15MRxFragments,                                
                    zxAnPonOltIfC15MRxJabbers,                                
                    zxAnPonOltIfC15MTxOctets,                                
                    zxAnPonOltIfC15MTxPkts,                                
                    zxAnPonOltIfC15MTxUcastPkts,                                
                    zxAnPonOltIfC15MTxNUcastPkts,                                
                    zxAnPonOltIfC15MTxMcastPkts,                                
                    zxAnPonOltIfC15MTxBcastPkts,                                
                    zxAnPonOltIfC15MTxDiscardPkts,                                
                    zxAnPonOltIfC15MTxErrPkts,                                
                    zxAnPonOltIfC15MTxCrcAlignErrors,                                
                    zxAnPonOltIfC15MTxUndersizePkts,                                
                    zxAnPonOltIfC15MTxOversizePkts,                                
                    zxAnPonOltIfC15MTxPkts64Octets,                                
                    zxAnPonOltIfC15MTx65To127Octs,                                
                    zxAnPonOltIfC15MTx128To255Octs,                                
                    zxAnPonOltIfC15MTx256To511Octs,                                
                    zxAnPonOltIfC15MTx512To1023Octs,                                
                    zxAnPonOltIfC15MTx1024To1518Octs,                                
                    zxAnPonOltIfC15MTxFragments,                                
                    zxAnPonOltIfC15MTxJabbers,                                
                    zxAnPonOltIfC15MCollisions,                                
                    zxAnPonOltIfC15MRxCorrFecCodes,                                
                    zxAnPonOltIfC15MRxErrFecCodes,                                
                    zxAnPonOltIfC15MDropEvents,                                
                    zxAnPonOltIfC15MPerfReset,
                    zxAnPonOltIfC1DTimeElapsed,
                    zxAnPonOltIfC1DRxOctets,                                
                    zxAnPonOltIfC1DRxPkts,                                
                    zxAnPonOltIfC1DRxUcastPkts,                                
                    zxAnPonOltIfC1DRxNUcastPkts,                                
                    zxAnPonOltIfC1DRxMcastPkts,                                
                    zxAnPonOltIfC1DRxBcastPkts,                                
                    zxAnPonOltIfC1DRxDiscardPkts,                                
                    zxAnPonOltIfC1DRxErrPkts,                                
                    zxAnPonOltIfC1DRxCrcAlignErrors,                                
                    zxAnPonOltIfC1DRxUndersizePkts,                                
                    zxAnPonOltIfC1DRxOversizePkts,                                
                    zxAnPonOltIfC1DRx64Octs,                                
                    zxAnPonOltIfC1DRx65To127Octs,                                
                    zxAnPonOltIfC1DRx128To255Octs,                                
                    zxAnPonOltIfC1DRx256To511Octs,                                
                    zxAnPonOltIfC1DRx512To1023Octs,                                
                    zxAnPonOltIfC1DRx1024To1518Octs,                                
                    zxAnPonOltIfC1DRxFragments,                                
                    zxAnPonOltIfC1DRxJabbers,                                
                    zxAnPonOltIfC1DTxOctets,                                
                    zxAnPonOltIfC1DTxPkts,                                
                    zxAnPonOltIfC1DTxUcastPkts,                                
                    zxAnPonOltIfC1DTxNUcastPkts,                                
                    zxAnPonOltIfC1DTxMcastPkts,                                
                    zxAnPonOltIfC1DTxBcastPkts,                                
                    zxAnPonOltIfC1DTxDiscardPkts,                                
                    zxAnPonOltIfC1DTxErrPkts,                                
                    zxAnPonOltIfC1DTxCrcAlignErrors,                                
                    zxAnPonOltIfC1DTxUndersizePkts,                                
                    zxAnPonOltIfC1DTxOversizePkts,                                
                    zxAnPonOltIfC1DTx64Octets,                                
                    zxAnPonOltIfC1DTx65To127Octs,                                
                    zxAnPonOltIfC1DTx128To255Octs,                                
                    zxAnPonOltIfC1DTx256To511Octs,                                
                    zxAnPonOltIfC1DTx512To1023Octs,                                
                    zxAnPonOltIfC1DTx1024To1518Octs,                                
                    zxAnPonOltIfC1DTxFragments,                                
                    zxAnPonOltIfC1DTxJabbers,                                
                    zxAnPonOltIfC1DCollisions,                                
                    zxAnPonOltIfC1DRxCorrFecCodes,                                
                    zxAnPonOltIfC1DRxErrFecCodes,                                
                    zxAnPonOltIfC1DDropEvents,                                
                    zxAnPonOltIfC1DPerfReset,
                    zxAnPonOltIfH15MDateAndTime,
                    zxAnPonOltIfH15MRxOctets,                                
                    zxAnPonOltIfH15MRxPkts,                                
                    zxAnPonOltIfH15MRxUcastPkts,                                
                    zxAnPonOltIfH15MRxNUcastPkts,                                
                    zxAnPonOltIfH15MRxMcastPkts,                                
                    zxAnPonOltIfH15MRxBcastPkts,                                
                    zxAnPonOltIfH15MRxDiscardPkts,                                
                    zxAnPonOltIfH15MRxErrPkts,                                
                    zxAnPonOltIfH15MRxCrcAlignErrors,                                
                    zxAnPonOltIfH15MRxUndersizePkts,                                
                    zxAnPonOltIfH15MRxOversizePkts,                                
                    zxAnPonOltIfH15MRx64Octs,                                
                    zxAnPonOltIfH15MRx65To127Octs,                                
                    zxAnPonOltIfH15MRx128To255Octs,                                
                    zxAnPonOltIfH15MRx256To511Octs,                                
                    zxAnPonOltIfH15MRx512To1023Octs,                                
                    zxAnPonOltIfH15MRx1024To1518Octs,                                
                    zxAnPonOltIfH15MRxFragments,                                
                    zxAnPonOltIfH15MRxJabbers,                                
                    zxAnPonOltIfH15MTxOctets,                                
                    zxAnPonOltIfH15MTxPkts,                                
                    zxAnPonOltIfH15MTxUcastPkts,                                
                    zxAnPonOltIfH15MTxNUcastPkts,                                
                    zxAnPonOltIfH15MTxMcastPkts,                                
                    zxAnPonOltIfH15MTxBcastPkts,                                
                    zxAnPonOltIfH15MTxDiscardPkts,                                
                    zxAnPonOltIfH15MTxErrPkts,                                
                    zxAnPonOltIfH15MTxCrcAlignErrors,                                
                    zxAnPonOltIfH15MTxUndersizePkts,                                
                    zxAnPonOltIfH15MTxOversizePkts,                                
                    zxAnPonOltIfH15MTxPkts64Octets,                                
                    zxAnPonOltIfH15MTx65To127Octs,                                
                    zxAnPonOltIfH15MTx128To255Octs,                                
                    zxAnPonOltIfH15MTx256To511Octs,                                
                    zxAnPonOltIfH15MTx512To1023Octs,                                
                    zxAnPonOltIfH15MTx1024To1518Octs,                                
                    zxAnPonOltIfH15MTxFragments,                                
                    zxAnPonOltIfH15MTxJabbers,                                 
                    zxAnPonOltIfH15MCollisions,                                
                    zxAnPonOltIfH15MRxCorrFecCodes,                                
                    zxAnPonOltIfH15MRxErrFecCodes,                                
                    zxAnPonOltIfH15MDropEvents,
                    zxAnPonOltIfH15MValidData, 
                    zxAnPonOltIfH1DDateAndTime,
                    zxAnPonOltIfH1DRxOctets,                                
                    zxAnPonOltIfH1DRxPkts,                                
                    zxAnPonOltIfH1DRxUcastPkts,                                
                    zxAnPonOltIfH1DRxNUcastPkts,                                
                    zxAnPonOltIfH1DRxMcastPkts,                                
                    zxAnPonOltIfH1DRxBcastPkts,                                
                    zxAnPonOltIfH1DRxDiscardPkts,                                
                    zxAnPonOltIfH1DRxErrPkts,                                
                    zxAnPonOltIfH1DRxCrcAlignErrors,                                
                    zxAnPonOltIfH1DRxUndersizePkts,                                
                    zxAnPonOltIfH1DRxOversizePkts,                                
                    zxAnPonOltIfH1DRx64Octs,                                
                    zxAnPonOltIfH1DRx65To127Octs,                                
                    zxAnPonOltIfH1DRx128To255Octs,                                
                    zxAnPonOltIfH1DRx256To511Octs,                                
                    zxAnPonOltIfH1DRx512To1023Octs,                                
                    zxAnPonOltIfH1DRx1024To1518Octs,                                
                    zxAnPonOltIfH1DRxFragments,                                
                    zxAnPonOltIfH1DRxJabbers,                                
                    zxAnPonOltIfH1DTxOctets,                                
                    zxAnPonOltIfH1DTxPkts,                                
                    zxAnPonOltIfH1DTxUcastPkts,                                
                    zxAnPonOltIfH1DTxNUcastPkts,                                
                    zxAnPonOltIfH1DTxMcastPkts,                                
                    zxAnPonOltIfH1DTxBcastPkts,                                
                    zxAnPonOltIfH1DTxDiscardPkts,                                
                    zxAnPonOltIfH1DTxErrPkts,                                
                    zxAnPonOltIfH1DTxCrcAlignErrors,                                
                    zxAnPonOltIfH1DTxUndersizePkts,                                
                    zxAnPonOltIfH1DTxOversizePkts,                                
                    zxAnPonOltIfH1DTxPkts64Octets,                                
                    zxAnPonOltIfH1DTx65To127Octs,                                
                    zxAnPonOltIfH1DTx128To255Octs,                                
                    zxAnPonOltIfH1DTx256To511Octs,                                
                    zxAnPonOltIfH1DTx512To1023Octs,                                
                    zxAnPonOltIfH1DTx1024To1518Octs,                                
                    zxAnPonOltIfH1DTxFragments,                                
                    zxAnPonOltIfH1DTxJabbers,                                 
                    zxAnPonOltIfH1DCollisions,                                
                    zxAnPonOltIfH1DRxCorrFecCodes,                                
                    zxAnPonOltIfH1DRxErrFecCodes,                                
                    zxAnPonOltIfH1DDropEvents,
                    zxAnPonOltIfH1DValidData,
                    zxAnPonOnuIfRxOctets,
                    zxAnPonOnuIfRxPkts,
                    zxAnPonOnuIfRxOctetRate,
                    zxAnPonOnuIfRxPktRate,
                    zxAnPonOnuIfRxOctetPeakRate,
                    zxAnPonOnuIfRxPktPeakRate,
                    zxAnPonOnuIfRxUcastPkts,
                    zxAnPonOnuIfRxNUcastPkts,
                    zxAnPonOnuIfRxMcastPkts,
                    zxAnPonOnuIfRxBcastPkts,
                    zxAnPonOnuIfRxDiscardPkts,
                    zxAnPonOnuIfRxErrPkts,
                    zxAnPonOnuIfRxPdr,
                    zxAnPonOnuIfRxPer,
                    zxAnPonOnuIfRxCrcAlignErrors,
                    zxAnPonOnuIfRxUndersizePkts ,
                    zxAnPonOnuIfRxOversizePkts,          
                    zxAnPonOnuIfRxPkts64Octets,
                    zxAnPonOnuIfRxPkts65To127Octets,
                    zxAnPonOnuIfRxPkts128To255Octets,
                    zxAnPonOnuIfRxPkts256To511Octets,
                    zxAnPonOnuIfRxPkts512To1023Oct,
                    zxAnPonOnuIfRxPkts1024To1518Oct,
                    zxAnPonOnuIfRxBwUtilization,
                    zxAnPonOnuIfRxAvgBwUtilization,
                    zxAnPonOnuIfRxFragments,
                    zxAnPonOnuIfRxJabbers,                                
                    zxAnPonOnuIfTxOctets,
                    zxAnPonOnuIfTxPkts,
                    zxAnPonOnuIfTxOctetRate,
                    zxAnPonOnuIfTxPktRate,
                    zxAnPonOnuIfTxOctetPeakRate,
                    zxAnPonOnuIfTxPktPeakRate,
                    zxAnPonOnuIfTxUcastPkts,
                    zxAnPonOnuIfTxNUcastPkts,
                    zxAnPonOnuIfTxMcastPkts,
                    zxAnPonOnuIfTxBcastPkts,
                    zxAnPonOnuIfTxDiscardPkts,
                    zxAnPonOnuIfTxErrPkts,
                    zxAnPonOnuIfTxPdr,
                    zxAnPonOnuIfTxPer,
                    zxAnPonOnuIfTxCrcAlignErrors,
                    zxAnPonOnuIfTxUndersizePkts,
                    zxAnPonOnuIfTxOversizePkts, 
                    zxAnPonOnuIfTxPkts64Octets,
                    zxAnPonOnuIfTxPkts65To127Octets,
                    zxAnPonOnuIfTxPkts128To255Octets,
                    zxAnPonOnuIfTxPkts256To511Octets, 
                    zxAnPonOnuIfTxPkts512To1023Oct,
                    zxAnPonOnuIfTxPkts1024To1518Oct,
                    zxAnPonOnuIfTxBwUtilization,
                    zxAnPonOnuIfTxAvgBwUtilization,
                    zxAnPonOnuIfTxFragments,
                    zxAnPonOnuIfTxJabbers,
                    zxAnPonOnuIfCollisions,                
                    zxAnPonOnuIfDropEvents,                
                    zxAnPonOnuIfCurrPerfReset,
                    zxAnPonOnuIfC15MTimeElapsed,                                
                    zxAnPonOnuIfC15MRxOctets,                                
                    zxAnPonOnuIfC15MRxPkts,                                
                    zxAnPonOnuIfC15MRxUcastPkts,                                
                    zxAnPonOnuIfC15MRxNUcastPkts,                                
                    zxAnPonOnuIfC15MRxMcastPkts,                                
                    zxAnPonOnuIfC15MRxBcastPkts,                                
                    zxAnPonOnuIfC15MRxDiscardPkts,                                
                    zxAnPonOnuIfC15MRxErrPkts,                                
                    zxAnPonOnuIfC15MRxCrcAlignErrors,                                
                    zxAnPonOnuIfC15MRxUndersizePkts,                                
                    zxAnPonOnuIfC15MRxOversizePkts,                                
                    zxAnPonOnuIfC15MRx64Octs,                                
                    zxAnPonOnuIfC15MRx65To127Octs,                                
                    zxAnPonOnuIfC15MRx128To255Octs,                                
                    zxAnPonOnuIfC15MRx256To511Octs,                                
                    zxAnPonOnuIfC15MRx512To1023Octs,                                
                    zxAnPonOnuIfC15MRx1024To1518Octs,                                
                    zxAnPonOnuIfC15MRxFragments,                                
                    zxAnPonOnuIfC15MRxJabbers,                                
                    zxAnPonOnuIfC15MTxOctets,                                
                    zxAnPonOnuIfC15MTxPkts,                                
                    zxAnPonOnuIfC15MTxUcastPkts,                                
                    zxAnPonOnuIfC15MTxNUcastPkts,                                
                    zxAnPonOnuIfC15MTxMcastPkts,                                
                    zxAnPonOnuIfC15MTxBcastPkts,                                
                    zxAnPonOnuIfC15MTxDiscardPkts,                                
                    zxAnPonOnuIfC15MTxErrPkts,                                
                    zxAnPonOnuIfC15MTxCrcAlignErrors,                                
                    zxAnPonOnuIfC15MTxUndersizePkts,                                
                    zxAnPonOnuIfC15MTxOversizePkts,                                
                    zxAnPonOnuIfC15MTxPkts64Octets,                                
                    zxAnPonOnuIfC15MTx65To127Octs,                                
                    zxAnPonOnuIfC15MTx128To255Octs,                                
                    zxAnPonOnuIfC15MTx256To511Octs,                                
                    zxAnPonOnuIfC15MTx512To1023Octs,                                
                    zxAnPonOnuIfC15MTx1024To1518Octs,                                
                    zxAnPonOnuIfC15MTxFragments,                                
                    zxAnPonOnuIfC15MTxJabbers,                                
                    zxAnPonOnuIfC15MCollisions,                                
                    zxAnPonOnuIfC15MDropEvents,                                
                    zxAnPonOnuIfC15MPerfReset,
                    zxAnPonOnuIfC1DTimeElapsed,
                    zxAnPonOnuIfC1DRxOctets,                                
                    zxAnPonOnuIfC1DRxPkts,                                
                    zxAnPonOnuIfC1DRxUcastPkts,                                
                    zxAnPonOnuIfC1DRxNUcastPkts,                                
                    zxAnPonOnuIfC1DRxMcastPkts,                                
                    zxAnPonOnuIfC1DRxBcastPkts,                                
                    zxAnPonOnuIfC1DRxDiscardPkts,                                
                    zxAnPonOnuIfC1DRxErrPkts,                                
                    zxAnPonOnuIfC1DRxCrcAlignErrors,                                
                    zxAnPonOnuIfC1DRxUndersizePkts,                                
                    zxAnPonOnuIfC1DRxOversizePkts,                                
                    zxAnPonOnuIfC1DRx64Octs,                                
                    zxAnPonOnuIfC1DRx65To127Octs,                                
                    zxAnPonOnuIfC1DRx128To255Octs,                                
                    zxAnPonOnuIfC1DRx256To511Octs,                                
                    zxAnPonOnuIfC1DRx512To1023Octs,                                
                    zxAnPonOnuIfC1DRx1024To1518Octs,                                
                    zxAnPonOnuIfC1DRxFragments,                                
                    zxAnPonOnuIfC1DRxJabbers,                                
                    zxAnPonOnuIfC1DTxOctets,                                
                    zxAnPonOnuIfC1DTxPkts,                                
                    zxAnPonOnuIfC1DTxUcastPkts,                                
                    zxAnPonOnuIfC1DTxNUcastPkts,                                
                    zxAnPonOnuIfC1DTxMcastPkts,                                
                    zxAnPonOnuIfC1DTxBcastPkts,                                
                    zxAnPonOnuIfC1DTxDiscardPkts,                                
                    zxAnPonOnuIfC1DTxErrPkts,                                
                    zxAnPonOnuIfC1DTxCrcAlignErrors,                                
                    zxAnPonOnuIfC1DTxUndersizePkts,                                
                    zxAnPonOnuIfC1DTxOversizePkts,                                
                    zxAnPonOnuIfC1DTx64Octets,                                
                    zxAnPonOnuIfC1DTx65To127Octs,                                
                    zxAnPonOnuIfC1DTx128To255Octs,                                
                    zxAnPonOnuIfC1DTx256To511Octs,                                
                    zxAnPonOnuIfC1DTx512To1023Octs,                                
                    zxAnPonOnuIfC1DTx1024To1518Octs,                                
                    zxAnPonOnuIfC1DTxFragments,                                
                    zxAnPonOnuIfC1DTxJabbers,                                
                    zxAnPonOnuIfC1DCollisions,                                
                    zxAnPonOnuIfC1DDropEvents,                                
                    zxAnPonOnuIfC1DPerfReset,
                    zxAnPonOnuIfH15MDateAndTime,
                    zxAnPonOnuIfH15MRxOctets,                                
                    zxAnPonOnuIfH15MRxPkts,                                
                    zxAnPonOnuIfH15MRxUcastPkts,                                
                    zxAnPonOnuIfH15MRxNUcastPkts,                                
                    zxAnPonOnuIfH15MRxMcastPkts,                                
                    zxAnPonOnuIfH15MRxBcastPkts,                                
                    zxAnPonOnuIfH15MRxDiscardPkts,                                
                    zxAnPonOnuIfH15MRxErrPkts,                                
                    zxAnPonOnuIfH15MRxCrcAlignErrors,                                
                    zxAnPonOnuIfH15MRxUndersizePkts,                                
                    zxAnPonOnuIfH15MRxOversizePkts,                                
                    zxAnPonOnuIfH15MRx64Octs,                                
                    zxAnPonOnuIfH15MRx65To127Octs,                                
                    zxAnPonOnuIfH15MRx128To255Octs,                                
                    zxAnPonOnuIfH15MRx256To511Octs,                                
                    zxAnPonOnuIfH15MRx512To1023Octs,                                
                    zxAnPonOnuIfH15MRx1024To1518Octs,                                
                    zxAnPonOnuIfH15MRxFragments,                                
                    zxAnPonOnuIfH15MRxJabbers,                                
                    zxAnPonOnuIfH15MTxOctets,                                
                    zxAnPonOnuIfH15MTxPkts,                                
                    zxAnPonOnuIfH15MTxUcastPkts,                                
                    zxAnPonOnuIfH15MTxNUcastPkts,                                
                    zxAnPonOnuIfH15MTxMcastPkts,                                
                    zxAnPonOnuIfH15MTxBcastPkts,                                
                    zxAnPonOnuIfH15MTxDiscardPkts,                                
                    zxAnPonOnuIfH15MTxErrPkts,                                
                    zxAnPonOnuIfH15MTxCrcAlignErrors,                                
                    zxAnPonOnuIfH15MTxUndersizePkts,                                
                    zxAnPonOnuIfH15MTxOversizePkts,                                
                    zxAnPonOnuIfH15MTxPkts64Octets,                                
                    zxAnPonOnuIfH15MTx65To127Octs,                                
                    zxAnPonOnuIfH15MTx128To255Octs,                                
                    zxAnPonOnuIfH15MTx256To511Octs,                                
                    zxAnPonOnuIfH15MTx512To1023Octs,                                
                    zxAnPonOnuIfH15MTx1024To1518Octs,                                
                    zxAnPonOnuIfH15MTxFragments,                                
                    zxAnPonOnuIfH15MTxJabbers,                                 
                    zxAnPonOnuIfH15MCollisions,                               
                    zxAnPonOnuIfH15MDropEvents,
                    zxAnPonOnuIfH15MValidData,
                    zxAnPonOnuIfH1DDateAndTime,
                    zxAnPonOnuIfH1DRxOctets,                                
                    zxAnPonOnuIfH1DRxPkts,                                
                    zxAnPonOnuIfH1DRxUcastPkts,                                
                    zxAnPonOnuIfH1DRxNUcastPkts,                                
                    zxAnPonOnuIfH1DRxMcastPkts,                                
                    zxAnPonOnuIfH1DRxBcastPkts,                                
                    zxAnPonOnuIfH1DRxDiscardPkts,                                
                    zxAnPonOnuIfH1DRxErrPkts,                                
                    zxAnPonOnuIfH1DRxCrcAlignErrors,                                
                    zxAnPonOnuIfH1DRxUndersizePkts,                                
                    zxAnPonOnuIfH1DRxOversizePkts,                                
                    zxAnPonOnuIfH1DRx64Octs,                                
                    zxAnPonOnuIfH1DRx65To127Octs,                                
                    zxAnPonOnuIfH1DRx128To255Octs,                                
                    zxAnPonOnuIfH1DRx256To511Octs,                                
                    zxAnPonOnuIfH1DRx512To1023Octs,                                
                    zxAnPonOnuIfH1DRx1024To1518Octs,                                
                    zxAnPonOnuIfH1DRxFragments,                                
                    zxAnPonOnuIfH1DRxJabbers,                                
                    zxAnPonOnuIfH1DTxOctets,                                
                    zxAnPonOnuIfH1DTxPkts,                                
                    zxAnPonOnuIfH1DTxUcastPkts,                                
                    zxAnPonOnuIfH1DTxNUcastPkts,                                
                    zxAnPonOnuIfH1DTxMcastPkts,                                
                    zxAnPonOnuIfH1DTxBcastPkts,                                
                    zxAnPonOnuIfH1DTxDiscardPkts,                                
                    zxAnPonOnuIfH1DTxErrPkts,                                
                    zxAnPonOnuIfH1DTxCrcAlignErrors,                                
                    zxAnPonOnuIfH1DTxUndersizePkts,                                
                    zxAnPonOnuIfH1DTxOversizePkts,                                
                    zxAnPonOnuIfH1DTxPkts64Octets,                                
                    zxAnPonOnuIfH1DTx65To127Octs,                                
                    zxAnPonOnuIfH1DTx128To255Octs,                                
                    zxAnPonOnuIfH1DTx256To511Octs,                                
                    zxAnPonOnuIfH1DTx512To1023Octs,                                
                    zxAnPonOnuIfH1DTx1024To1518Octs,                                
                    zxAnPonOnuIfH1DTxFragments,                                
                    zxAnPonOnuIfH1DTxJabbers,                                 
                    zxAnPonOnuIfH1DCollisions,                               
                    zxAnPonOnuIfH1DDropEvents,
                    zxAnPonOnuIfH1DValidData,
                    zxAnPonOltPerfAlmPrfRowStatus,
                    zxAnPonOltPerfRiseAlmThresh,
                    zxAnPonOltPerfRiseAlmClrThresh,
                    zxAnPonOltPerfRiseWarnThresh,
                    zxAnPonOltPerfRiseWarnClrThresh,
                    zxAnPonOltPerfFallWarnThresh,
                    zxAnPonOltPerfFallWarnClrThresh,
                    zxAnPonOltPerfFallAlmThresh,
                    zxAnPonOltPerfFallAlmClrThresh,
                    zxAnPonOltPerfThreshUsed,
                    zxAnPonOltPerfAlmConfRowStatus,
                    zxAnPonOltPerfAlmPrf,
                    zxAnPonOltAlmPrfApplyRowStatus,
                    zxAnPonOnuPerfAlmPrfRowStatus,
                    zxAnPonOnuPerfRiseAlmThresh,
                    zxAnPonOnuPerfRiseAlmClrThresh,
                    zxAnPonOnuPerfRiseWarnThresh,
                    zxAnPonOnuPerfRiseWarnClrThresh,
                    zxAnPonOnuPerfFallWarnThresh,
                    zxAnPonOnuPerfFallWarnClrThresh,
                    zxAnPonOnuPerfFallAlmThresh,
                    zxAnPonOnuPerfFallAlmClrThresh,
                    zxAnPonOnuPerfThreshUsed,
                    zxAnPonOnuPerfAlmConfRowStatus,
                    zxAnPonOnuPerfAlmPrf,
                    zxAnPonOnuAlmPrfApplyRowStatus                                                                                                                                                         
                    }
    STATUS          current
    DESCRIPTION     
        "A collection of objects for interface 
        statistic configuration."
    ::= { zxAnPonPerfGroups 1 }
        
END
