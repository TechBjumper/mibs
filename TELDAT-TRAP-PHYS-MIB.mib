-- file automatically created


TELDAT-TRAP-PHYS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


physTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the PHYS event subsystem."
    REVISION "201401200930Z"
    DESCRIPTION "Initial implementation"
        ::= { telEventTraps 193 }


physEventsGroup	OBJECT IDENTIFIER	::= { physTrapsMIB 1 }

physNotifications	OBJECT IDENTIFIER	::= { physTrapsMIB 2 }
physNotificationsPrefix	OBJECT IDENTIFIER	::= { physNotifications 0 }

physEventObjects1 OBJECT-IDENTITY
    STATUS current
    DESCRIPTION
        "Event PHYS.1
        Notify physical state changed"
    ::= { physEventsGroup 1 }

phys1-state OBJECT-TYPE
    SYNTAX DisplayString
    MAX-ACCESS accessible-for-notify
    STATUS current
    DESCRIPTION
        "Parameter 'state' in event PHYS.1"
    ::= { physEventObjects1 1 }

phys1-interface OBJECT-TYPE
    SYNTAX DisplayString
    MAX-ACCESS accessible-for-notify
    STATUS current
    DESCRIPTION
        "Parameter 'interface' in event PHYS.1"
    ::= { physEventObjects1 2 }

physEventObjects2 OBJECT-IDENTITY
    STATUS current
    DESCRIPTION
        "Event PHYS.2
        Notify physical event proccessing"
    ::= { physEventsGroup 2 }

phys2-proccessing-info OBJECT-TYPE
    SYNTAX DisplayString
    MAX-ACCESS accessible-for-notify
    STATUS current
    DESCRIPTION
        "Parameter 'proccessing-info' in event PHYS.2"
    ::= { physEventObjects2 1 }

phys2-interface OBJECT-TYPE
    SYNTAX DisplayString
    MAX-ACCESS accessible-for-notify
    STATUS current
    DESCRIPTION
        "Parameter 'interface' in event PHYS.2"
    ::= { physEventObjects2 2 }

physEventObjects3 OBJECT-IDENTITY
    STATUS current
    DESCRIPTION
        "Event PHYS.3
        Notify request to the BRI interface"
    ::= { physEventsGroup 3 }

phys3-request-info OBJECT-TYPE
    SYNTAX DisplayString
    MAX-ACCESS accessible-for-notify
    STATUS current
    DESCRIPTION
        "Parameter 'request-info' in event PHYS.3"
    ::= { physEventObjects3 1 }

phys3-interface OBJECT-TYPE
    SYNTAX DisplayString
    MAX-ACCESS accessible-for-notify
    STATUS current
    DESCRIPTION
        "Parameter 'interface' in event PHYS.3"
    ::= { physEventObjects3 2 }

physEventObjects4 OBJECT-IDENTITY
    STATUS current
    DESCRIPTION
        "Event PHYS.4
        Informational. Physical error  error detectec according Q.921."
    ::= { physEventsGroup 4 }

phys4-error-text OBJECT-TYPE
    SYNTAX DisplayString
    MAX-ACCESS accessible-for-notify
    STATUS current
    DESCRIPTION
        "Parameter 'error-text' in event PHYS.4"
    ::= { physEventObjects4 1 }

phys4-interface OBJECT-TYPE
    SYNTAX DisplayString
    MAX-ACCESS accessible-for-notify
    STATUS current
    DESCRIPTION
        "Parameter 'interface' in event PHYS.4"
    ::= { physEventObjects4 2 }


physNotification1 NOTIFICATION-TYPE
    OBJECTS { 
              phys1-state, 
              phys1-interface 
            }
    STATUS current
    DESCRIPTION
        "Notification of Event PHYS.1

        Message: 'State changed to $1 interface $2'

        Parameters list:
              $1: phys1-state
              $2: phys1-interface

        Notify physical state changed"
    ::= { physNotificationsPrefix 1 }

physNotification2 NOTIFICATION-TYPE
    OBJECTS { 
              phys2-proccessing-info, 
              phys2-interface 
            }
    STATUS current
    DESCRIPTION
        "Notification of Event PHYS.2

        Message: 'Processing $1 event on interface $2'

        Parameters list:
              $1: phys2-proccessing-info
              $2: phys2-interface

        Notify physical event proccessing"
    ::= { physNotificationsPrefix 2 }

physNotification3 NOTIFICATION-TYPE
    OBJECTS { 
              phys3-request-info, 
              phys3-interface 
            }
    STATUS current
    DESCRIPTION
        "Notification of Event PHYS.3

        Message: 'Request $1 to interface $2'

        Parameters list:
              $1: phys3-request-info
              $2: phys3-interface

        Notify request to the BRI interface"
    ::= { physNotificationsPrefix 3 }

physNotification4 NOTIFICATION-TYPE
    OBJECTS { 
              phys4-error-text, 
              phys4-interface 
            }
    STATUS current
    DESCRIPTION
        "Notification of Event PHYS.4

        Message: 'ERROR $1 interface $2'

        Parameters list:
              $1: phys4-error-text
              $2: phys4-interface

        Informational. Physical error  error detectec according Q.921."
    ::= { physNotificationsPrefix 4 }


END
