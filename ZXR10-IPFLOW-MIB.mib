ZXR10-IPFLOW-MIB DEFINITIONS ::= BEGIN    

IMPORTS
    MODULE-IDENTITY,
    OBJECT-TYPE,
    enterprises,
    Unsigned32
        FROM SNMPv2-SMI 
        
     DisplayString
        FROM SNMPv2-TC
    
     IpAddress
         FROM SNMPv2-SMI;
 
        

 -- netflow node identity  
 
 zxr10Ipflow MODULE-IDENTITY
    LAST-UPDATED "201506050900Z"  
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "IP FLOW MIB."

    REVISION "201506050900Z"  
    DESCRIPTION
       "Add dot1qVlanId(243) for ipflowRcdType SYNTAX"
        
    REVISION "201402131700Z"  
    DESCRIPTION
       "Import Unsigned32 and change the type of ipflowCacheEntryNum SYNTAX to Unsigned32;
       replace RFC1155-SMI by SNMPv2-SMI;
       change zxr10-Ipflow to zxr10Ipflow;
       add range for INTEGER;
       change DisplayString(SIZE (1..32)) to DisplayString(SIZE (1..31)) for ipflowAclName SYNTAX;
       change DisplayString(SIZE (1..32)) to DisplayString(SIZE (1..31)) for ipflowIfName SYNTAX;
       add paddingOctets(210) for ipflowRcdType SYNTAX"
       
    REVISION "200504120000Z"  
    DESCRIPTION
       "IP FLOW MIB."
    ::= { zxr10 67 }       
 
 zte   OBJECT IDENTIFIER ::= { enterprises 3902} 
 zxr10 OBJECT IDENTIFIER ::= { zte 3}
  

 -- sample table identity
   
 ipflowSampleTable OBJECT-TYPE
     SYNTAX       SEQUENCE OF IpflowSampleEntry
     MAX-ACCESS   not-accessible
     STATUS       current
     DESCRIPTION
         "Netflow sample table. "
     ::= { zxr10Ipflow 1}

 ipflowSampleEntry OBJECT-TYPE
     SYNTAX       IpflowSampleEntry
     MAX-ACCESS   not-accessible
     STATUS       current
     DESCRIPTION
         "Netflow sample."
     INDEX    { ipflowSampleName }
     ::= { ipflowSampleTable 1 }

 IpflowSampleEntry ::=
     SEQUENCE {
         ipflowSampleName
             DisplayString,
         ipflowSampleMethod
             INTEGER,
         ipflowSampleRate
             INTEGER
 }                
 
 ipflowSampleName OBJECT-TYPE
     SYNTAX       DisplayString(SIZE (1..32))
     MAX-ACCESS   read-only
     STATUS       current
     DESCRIPTION
         "Sample name."
     ::= { ipflowSampleEntry 1 }
     
 ipflowSampleMethod OBJECT-TYPE
     SYNTAX          INTEGER {
                      deterministic(1)                      
                   }
     MAX-ACCESS   read-only
     STATUS       current
     DESCRIPTION   
          "Sample method."
     ::= { ipflowSampleEntry 2 }

 ipflowSampleRate OBJECT-TYPE
     SYNTAX       INTEGER(1..65535)
     MAX-ACCESS   read-only
     STATUS       current
     DESCRIPTION   
         "Sample rate."
     ::= { ipflowSampleEntry 3 }


 -- exporter table identity 
      
 ipflowExporterTable OBJECT-TYPE
     SYNTAX       SEQUENCE OF IpflowExporterEntry
     MAX-ACCESS   not-accessible
     STATUS       current
     DESCRIPTION
         "Netflow Exporter table. "
     ::= { zxr10Ipflow 2}

 ipflowExporterEntry OBJECT-TYPE
     SYNTAX       IpflowExporterEntry
     MAX-ACCESS   not-accessible
     STATUS       current
     DESCRIPTION
         "Netflow Exporter."
     INDEX    { ipflowExptName }
     ::= { ipflowExporterTable 1 }

 IpflowExporterEntry ::=
     SEQUENCE {
         ipflowExptName
             DisplayString,
         ipflowExptDestIp
             IpAddress,    
         ipflowExptDestVrf
             DisplayString,  
         ipflowExptProto
             INTEGER,
         ipflowExptTplTimeout
             INTEGER, 
         ipflowExptTplRefresh
             INTEGER, 
         ipflowExptTransProto
             INTEGER,
         ipflowExptTransPort
             INTEGER,            
         ipflowExptSrcIp
             IpAddress,            
         ipflowExptSrcIpv6
             DisplayString,            
         ipflowExptDscp
             INTEGER,            
         ipflowExptDestIpv6
             DisplayString            
 }     
     
 ipflowExptName OBJECT-TYPE
     SYNTAX       DisplayString(SIZE (1..32))
     MAX-ACCESS   read-only
     STATUS       current
     DESCRIPTION
         "Exporter name."
     ::= { ipflowExporterEntry 1 }

 ipflowExptDestIp OBJECT-TYPE
     SYNTAX       IpAddress
     MAX-ACCESS   read-only
     STATUS       current
     DESCRIPTION
         "Exporter destination IP address."
     ::= { ipflowExporterEntry 2 }  
                         
 ipflowExptDestVrf OBJECT-TYPE
     SYNTAX       DisplayString(SIZE (1..32))
     MAX-ACCESS   read-only
     STATUS       current
     DESCRIPTION
         "Exporter destination vrf name."
     ::= { ipflowExporterEntry 3 }  
      
 ipflowExptProto OBJECT-TYPE
     SYNTAX       INTEGER {
                      v5(5),
                      v8(8),
                      v9(9),
                      ipfix(10)
                   }
     MAX-ACCESS   read-only
     STATUS       current
     DESCRIPTION
         "Exporter protocol."
     ::= { ipflowExporterEntry 4 }
                   
 ipflowExptTplTimeout OBJECT-TYPE
     SYNTAX       INTEGER(1..86400)
     MAX-ACCESS   read-only
     STATUS       current
     DESCRIPTION
         "Exporter template timeout."
     ::= { ipflowExporterEntry 5 }   
   
  ipflowExptTplRefresh OBJECT-TYPE
     SYNTAX       INTEGER(1..600)
     MAX-ACCESS   read-only
     STATUS       current
     DESCRIPTION
         "Exporter template refresh rate."
     ::= { ipflowExporterEntry 6 }   
  
 ipflowExptTransProto OBJECT-TYPE
     SYNTAX       INTEGER{
                      udp(1)
                  } 
     MAX-ACCESS   read-only
     STATUS       current
     DESCRIPTION
         "Exporter transport protocol."
     ::= { ipflowExporterEntry 7 } 
  
 ipflowExptTransPort OBJECT-TYPE
     SYNTAX       INTEGER(1..65535)
     MAX-ACCESS   read-only
     STATUS       current
     DESCRIPTION
         "Exporter transport port number."
     ::= { ipflowExporterEntry 8 } 

ipflowExptSrcIp OBJECT-TYPE
     SYNTAX       IpAddress
     MAX-ACCESS   read-only
     STATUS       current
     DESCRIPTION
         "Exporter source IP address."
     ::= { ipflowExporterEntry 9 } 

ipflowExptSrcIpv6 OBJECT-TYPE
     SYNTAX       DisplayString
     MAX-ACCESS   read-only
     STATUS       current
     DESCRIPTION
         "Exporter source IPv6 address."
     ::= { ipflowExporterEntry 10 } 

ipflowExptDscp OBJECT-TYPE
     SYNTAX       INTEGER(0..63)
     MAX-ACCESS   read-only
     STATUS       current
     DESCRIPTION
         "Exporter dscp."
     ::= { ipflowExporterEntry 11 } 

ipflowExptDestIpv6 OBJECT-TYPE
     SYNTAX       DisplayString
     MAX-ACCESS   read-only
     STATUS       current
     DESCRIPTION
         "Exporter destination IPv6 address."
     ::= { ipflowExporterEntry 12 } 


 -- record counting table identity 
 ipflowRcdCountTable OBJECT-TYPE
     SYNTAX       SEQUENCE OF IpflowRcdCountEntry
     MAX-ACCESS   not-accessible
     STATUS       current
     DESCRIPTION
         "Netflow Record counting table. "
     ::= { zxr10Ipflow 3}

 ipflowRcdCountEntry OBJECT-TYPE
     SYNTAX       IpflowRcdCountEntry
     MAX-ACCESS   not-accessible
     STATUS       current
     DESCRIPTION
         "Netflow Record counting."
     INDEX    { ipflowRcdctName }
     ::= { ipflowRcdCountTable 1 }

 IpflowRcdCountEntry ::=
     SEQUENCE {
         ipflowRcdctName
             DisplayString,
         ipflowRcdMatchNum
             INTEGER,
         ipflowRcdCollectNum
             INTEGER
 }     
     
 ipflowRcdctName OBJECT-TYPE
     SYNTAX       DisplayString(SIZE (1..32))
     MAX-ACCESS   read-only
     STATUS       current
     DESCRIPTION
         "Record name."
     ::= { ipflowRcdCountEntry 1 }
     
 ipflowRcdMatchNum OBJECT-TYPE
     SYNTAX       INTEGER(0..65535)
     MAX-ACCESS   read-only
     STATUS       current
     DESCRIPTION
         "Record key field number."
     ::= { ipflowRcdCountEntry 2 }
     
 ipflowRcdCollectNum OBJECT-TYPE
     SYNTAX       INTEGER(0..65535)
     MAX-ACCESS   read-only
     STATUS       current
     DESCRIPTION
         "Record non key field number."
     ::= { ipflowRcdCountEntry 3 }


-- record table identity 
 ipflowRecordTable OBJECT-TYPE
     SYNTAX       SEQUENCE OF IpflowRecordEntry
     MAX-ACCESS   not-accessible
     STATUS       current
     DESCRIPTION
         "Netflow Record table. "
     ::= { zxr10Ipflow 4}

 ipflowRecordEntry OBJECT-TYPE
     SYNTAX       IpflowRecordEntry
     MAX-ACCESS   not-accessible
     STATUS       current
     DESCRIPTION
         "Netflow Record."
     INDEX    { ipflowRecordName,ipflowRcdType }
     ::= { ipflowRecordTable 1 }

 IpflowRecordEntry ::=
     SEQUENCE {
         ipflowRecordName
             DisplayString,
         ipflowRcdType
             INTEGER,
         ipflowRcdAtt
             INTEGER,
         ipflowRcdSize
             INTEGER
 }     
 
 ipflowRecordName OBJECT-TYPE
     SYNTAX       DisplayString(SIZE (1..32))
     MAX-ACCESS   read-only
     STATUS       current
     DESCRIPTION
         "Record name."
     ::= { ipflowRecordEntry 1 }
     
 ipflowRcdType OBJECT-TYPE
     SYNTAX       INTEGER{
                    flowDirection(61),
                    flowSamplerId(48),
                    destinationMacAddress(57),
                    sourceMacAddress(56),
                    ingressInterface(10),
                    egressInterface(14),
                    flowStartSysUpTime(22),
                    flowEndSysUpTime(21),
                    destinationTransportPort(11),
                    sourceTransportPort(7),
                    icmpTypeCodeIPv4(32),
                    tcpControlBits(6),
                    igmpType(33),
                    ipClassOfService(5),
                    ipVersion(60),
                    protocolIdentifier(4),
                    destinationIPv4Address(12),
                    destinationIPv4PrefixLength(13),
                    sourceIPv4Address(8),
                    sourceIPv4PrefixLength(9),
                    ipNextHopIPv4Address(15),
                    octetDeltaCount(1),
                    packetDeltaCount(2),
                    flows(3),
                    bgpSourceAsNumber(16),
                    bgpDestinationAsNumber(17), 
                    bgpNextHopIPv4Address(18),
                    sourceIPv4Prefix(44),
                    destinationIPv4Prefix(45),
                    mplsTopLabelStackSection(70),
                    mplsLabelStackSection2(71),
                    mplsLableStackSection3(72),
                    mplsLableStackSection4(73),
                    mplsLableStackSection5(74),
                    samplingInverval(34),
                    sourceIPv6Address(27),
                    destinationIPv6Address(28),
                    sourceIPv6PrefixLength(29),
                    destinationIPv6PrefixLength(30),
                    flowLabelIPv6(31),
                    ipNextHopIPv6Address(62),
                    bgpNextHopIPv6Address(63),
                    bgpNextAdjacentAsNumber(128),
                    bgpPrevAdjacentAsNumber(129),
                    flowStartMilliseconds(152),
                    flowEndMilliseconds(153),
                    destinationIPv6Prefix(169),
                    sourceIPv6Prefix(170),
                    icmpTypeIPv4(176),
                    icmpCodeIPv4(177),
                    icmpTypeIPv6(178),
                    icmpCodeIPv6(179),
                    paddingOctets(210),
                    ingressVRFID(234),
                    egressVRFID(235),
                    dot1qVlanId(243)
                  }      
     MAX-ACCESS   read-only
     STATUS       current
     DESCRIPTION
         "Record type."
     ::= { ipflowRecordEntry 2 }
  
 ipflowRcdAtt OBJECT-TYPE
     SYNTAX       INTEGER{
                      noused(0),
                      match(1),
                      collect(2)
                  }      
     MAX-ACCESS   read-only
     STATUS       current
     DESCRIPTION
         "Record type attribute."
     ::= { ipflowRecordEntry 3 }
 
 ipflowRcdSize OBJECT-TYPE
     SYNTAX       INTEGER(0..65535)
     MAX-ACCESS   read-only
     STATUS       current
     DESCRIPTION
         "Record type size."
     ::= { ipflowRecordEntry 4 }   

 -- monitor table identity 
      
 ipflowMonitorTable OBJECT-TYPE
     SYNTAX       SEQUENCE OF IpflowMonitorEntry
     MAX-ACCESS   not-accessible
     STATUS       current
     DESCRIPTION
         "Netflow monitor table. "
     ::= { zxr10Ipflow 5}

 ipflowMonitorEntry OBJECT-TYPE
     SYNTAX       IpflowMonitorEntry
     MAX-ACCESS   not-accessible
     STATUS       current
     DESCRIPTION
         "Netflow monitor."
     INDEX    { ipflowMonitorName }
     ::= { ipflowMonitorTable 1 }

 IpflowMonitorEntry ::=
     SEQUENCE {
         ipflowMonitorName
             DisplayString,
         ipflowRcdName
             DisplayString,    
         ipflowPreDRcd
             INTEGER,    
         ipflowExporterName1
             DisplayString,   
         ipflowExporterName2
             DisplayString,  
         ipflowCacheEntryNum
             Unsigned32,
         ipflowCacheInactiveTit
             INTEGER, 
         ipflowCacheActiveTit
             INTEGER 
 }     
     
 ipflowMonitorName OBJECT-TYPE
     SYNTAX       DisplayString(SIZE (1..32))
     MAX-ACCESS   read-only
     STATUS       current
     DESCRIPTION
         "Monitor name."
     ::= { ipflowMonitorEntry 1 }
     
 ipflowRcdName OBJECT-TYPE
     SYNTAX       DisplayString(SIZE (1..32))
     MAX-ACCESS   read-only
     STATUS       current
     DESCRIPTION
         "Monitor record name."
     ::= { ipflowMonitorEntry 2 }
  
 ipflowPreDRcd OBJECT-TYPE
     SYNTAX       INTEGER{
                   nfOrgRcd(1),
                   nfIpv4ProtPortRcd(2)
                  }
     MAX-ACCESS   read-only
     STATUS       current
     DESCRIPTION
         "Monitor predefined record."
     ::= { ipflowMonitorEntry 3 }
 
 ipflowExporterName1 OBJECT-TYPE
     SYNTAX       DisplayString(SIZE (1..32))
     MAX-ACCESS   read-only
     STATUS       current
     DESCRIPTION
         "Monitor exporter1 name."
     ::= { ipflowMonitorEntry 4 }
     
 ipflowExporterName2 OBJECT-TYPE
     SYNTAX       DisplayString(SIZE (1..32))
     MAX-ACCESS   read-only
     STATUS       current
     DESCRIPTION
         "Monitor exproter2 name."
     ::= { ipflowMonitorEntry 5 }

 ipflowCacheEntryNum OBJECT-TYPE
     SYNTAX       Unsigned32(16..4294967295)
     MAX-ACCESS   read-only
     STATUS       current
     DESCRIPTION
         "Monitor cache entry number."
     ::= { ipflowMonitorEntry 6 }
                   
 ipflowCacheInactiveTit OBJECT-TYPE
     SYNTAX       INTEGER(10..604800)
     MAX-ACCESS   read-only
     STATUS       current
     DESCRIPTION
         "Monitor cache inactive timeout."
     ::= { ipflowMonitorEntry 7 } 
  
 ipflowCacheActiveTit OBJECT-TYPE
     SYNTAX       INTEGER(10..604800)
     MAX-ACCESS   read-only
     STATUS       current
     DESCRIPTION
         "Monitor cache active timeout."
     ::= { ipflowMonitorEntry 8 } 

 -- ifflow table identity 
      
 ipflowIfflowTable OBJECT-TYPE
     SYNTAX       SEQUENCE OF IpflowIfflowEntry
     MAX-ACCESS   not-accessible
     STATUS       current
     DESCRIPTION
         "Interface ipflow table. "
     ::= { zxr10Ipflow 6}

 ipflowIfflowEntry OBJECT-TYPE
     SYNTAX       IpflowIfflowEntry
     MAX-ACCESS   not-accessible
     STATUS       current
     DESCRIPTION
         "Interface ipflow."
     INDEX    { ipflowIfName, 
                ipflowSampleCastType,
                ipflowAclName,
                ipflowSampleDirect,
                ipflowSamplePktPro}
     ::= { ipflowIfflowTable 1 }

 IpflowIfflowEntry ::=
     SEQUENCE {
         ipflowIfName
             DisplayString, 
         ipflowSampleCastType
             INTEGER, 
         ipflowAclName
             DisplayString, 
         ipflowSampleDirect
             INTEGER,    
         ipflowSamplePktPro
             INTEGER,
         ipflowSmpName
             DisplayString,    
         ipflowMntName
             DisplayString       
 }     
     
 ipflowIfName OBJECT-TYPE
     SYNTAX       DisplayString(SIZE (1..31))
     MAX-ACCESS   read-only
     STATUS       current
     DESCRIPTION
         "Interface name."
     ::= { ipflowIfflowEntry 1 }
     
 ipflowSampleCastType OBJECT-TYPE
     SYNTAX       INTEGER{
                    muticast(0),
                    unicast(1),
                    allcast(2),
                    acl(3)
                    }
     MAX-ACCESS   read-only
     STATUS       current
     DESCRIPTION
         "Interface ipflow sample cast type."
     ::= { ipflowIfflowEntry 2 }
                   
  ipflowAclName OBJECT-TYPE
     SYNTAX       DisplayString(SIZE (1..31))
     MAX-ACCESS   read-only
     STATUS       current
     DESCRIPTION
         "Interface ipflow acl name."
     ::= { ipflowIfflowEntry 3 }
                  
 ipflowSampleDirect OBJECT-TYPE
     SYNTAX       INTEGER{
                      ingress(0),
                      egress(1)
                      }
     MAX-ACCESS   read-only
     STATUS       current
     DESCRIPTION
         "Interface ipflow sample direction."
     ::= { ipflowIfflowEntry 4 }  
     
 ipflowSamplePktPro OBJECT-TYPE
     SYNTAX       INTEGER{
                    ipv4(4),
                    ipv6(6),
                    mpls(7)
                    }
     MAX-ACCESS   read-only
     STATUS       current
     DESCRIPTION
         "Interface ipflow sample packet protocol."
     ::= { ipflowIfflowEntry 5 }

 ipflowSmpName OBJECT-TYPE
     SYNTAX       DisplayString(SIZE (1..32))
     MAX-ACCESS   read-only
     STATUS       current
     DESCRIPTION
         "Interface ipflow sampler name."
     ::= { ipflowIfflowEntry 6 }
  
 ipflowMntName OBJECT-TYPE
     SYNTAX       DisplayString(SIZE (1..32))
     MAX-ACCESS   read-only
     STATUS       current
     DESCRIPTION
         "Interface ipflow monitor name."
     ::= { ipflowIfflowEntry 7 }
     
     
     
END
