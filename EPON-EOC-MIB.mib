--
-- EPON-EOC-MIB.my
-- MIB generated by MG-SOFT Visual MIB Builder Version 3.0 Build 253
-- Wednesday, June 15, 2011 at 18:05:47
--

	EPON-EOC-MIB DEFINITIONS ::= BEGIN
 
		IMPORTS
			enterprises, MODULE-IDENTITY, OBJECT-IDENTITY			
				FROM SNMPv2-SMI			
			TEXTUAL-CONVENTION			
				FROM SNMPv2-TC;
	
	
		eponeoc MODULE-IDENTITY 
			LAST-UPDATED "201005271056Z"		-- May 27, 2010 at 10:56 GMT
			ORGANIZATION 
				"epon eoc factory."
			CONTACT-INFO 
				""
			DESCRIPTION 
				"epon eoc common mib module"
			::= { enterprises 34592 }
		
	
--
-- Textual conventions
--
	
		OperSwitch ::= TEXTUAL-CONVENTION
			STATUS current
			DESCRIPTION 
				"Device function operation switch type"
			SYNTAX INTEGER
				{
				enable(1),
				disable(2)
				}
			
		DeviceStatus ::= TEXTUAL-CONVENTION
			STATUS current
			DESCRIPTION 
				"Device work status type. One device or dummy device may
				have following five work status:
				notPresent(1): the device is not present (not installed)
				offline(2):the device is present,but can not be communicated (or failed to get its info)
				online(3):the device is present and can be communicated
				normal(4):the device is online and work well
				abnormal(5): the device is online but work abnormal for some reason"
			SYNTAX INTEGER
				{
				notPresent(1),
				offline(2),
				online(3),
				normal(4),
				abnormal(5)
				}
			
		DataDirection ::= TEXTUAL-CONVENTION
			STATUS current
			DESCRIPTION 
				"A data channel normally have two direction, up and down"
			SYNTAX INTEGER
				{
				upstream(1),
				downstream(2)
				}
			
		DeviceOperation ::= TEXTUAL-CONVENTION
			STATUS current
			DESCRIPTION 
				"This type defines an operate action aggregate"
			SYNTAX INTEGER
				{
				reset(2),
				default(3),
				saveConfig(4),
				restore(5),
				delete(6)
				}
			
		LedStatus ::= TEXTUAL-CONVENTION
			STATUS current
			DESCRIPTION 
				"Led status"
			SYNTAX INTEGER
				{
				on(1),
				off(2),
				blink(3)
				}
			
		DeviceType ::= TEXTUAL-CONVENTION
			STATUS current
			DESCRIPTION 
				"Device type convention. Define all PBB device type value.
				
				----------------------------------
				| family | series | class | type |
				----------------------------------
				   8b        8b      8b      8b
				
				refer to document <pducuct type defines>"
			SYNTAX INTEGER
				{
				system(16842752),
				epon-2u8p(16843009),
				olt(16843265),
				pon(16843521),
				pon(16909057),
				
				epon-1u2p(17105153),
				olt(17105409),
				pon(17105665),
				
				epon-1u4p(17236225),
				olt(17236481),
				pon(17236737),
				pon(17235968),			
				
				epon-1u8p(17170689),
				olt(17170945),
				pon(17171201),
				pon(17171202),
				
				onu4d-b(16974081),
				onu4d-b(16974082),
				onu4d-b(16974083),
				onu1d-g(16974087),
				onu2d-gm(16974095),
				onu4d-gm(16974094),
				onu4d-p(16974089),
				onu3d-m(16974090),
				onu2d-m(16974092),
				onu4d2p(16974337),
				onu4d2p-p(16974338),
				onu4d1r-p(16974594),
				onu4d2p1r(16974849),
				onu4d2p1r(17040129),
				onu4d2p1r-p(16974850),
				onu24d(17039617),
				onu1ge(825307496),
				onu2ge(825307757),
				onu4geb(825308258),
				onu4ge(825308269),
				onu1ge1fe1p(825307464),
				onu4fe1rf(858797160),
				
				onu1fe(16974086),
                onu1fe1ge(16974088),   
                onu4fe(16974085),    
                onu4fe(16974091),
                onu8feb(16974084),
                onu4fe1tv-wdm(16974593),

                onu1fec(825241683),   
                onu1gec(825241671),
                onu4fec(875573331),
                onu4geb(875573314),
                onu2gem(842018893),
                onu4gem(875573325),
                onu4few(875573335),
                onu4fe1tvc-wdm(875647827),
                onu4fe1tvca(875643987),
                onu4fe1tvw-wdm(875647831),
                onu4fe1tvw(875643991),

                onu4fe2p(1),
                onu4fe2pa(16974337),
                onu4fe2p1tv(2),
                onu24feb(3),
                onu4fe2pw(4),
                onu2fe1p(5),
                onu1feca(825241960),
                onu1geca(825307496),
                onu4feca(825242728),
                onu1gem (825241674),
                onu16feb(8),
                onu4ge(16974097)
				}
			
	
--
-- Node definitions
--
	
		-- 1.3.6.1.4.1.34592.1
		ipProduct OBJECT-IDENTITY
			STATUS current
			DESCRIPTION 
				"Defines the base identifier containing the definition of ip products line.
				"
			::= { eponeoc 1 }
		
		-- 1.3.6.1.4.1.34592.1.1
		mediaConverter OBJECT-IDENTITY
			STATUS current
			DESCRIPTION 
				"Defines the base identifier for the subtree
				supported by media converter line products.
				"
			::= { ipProduct 1 }
		
		-- 1.3.6.1.4.1.34592.1.2
		switch OBJECT-IDENTITY
			STATUS current
			DESCRIPTION 
				"Defines the base identifier for the subtree
				supported by smartCPE Switch line products.
				"
			::= { ipProduct 2 }
		
		-- 1.3.6.1.4.1.34592.1.3
		epon OBJECT-IDENTITY
			STATUS current
			DESCRIPTION 
			""
			::= { ipProduct 3 }
		
		-- 1.3.6.1.4.1.34592.1.4
		eoc OBJECT-IDENTITY
			STATUS current
			DESCRIPTION 
			""
			::= { ipProduct 4 }
		
	
	END

--
-- EPON-EOC-MIB.my
--
