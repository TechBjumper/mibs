--  =======================================================================
--  File        : oaSubscr.mib
--  Description : Private MIB for Linux Router: Subscriber's features.
--  By          : 
--              :
--  Log         : $Log: oaSubscr.mib,v $
--  Log         : Revision 1.3  2003/04/08 12:21:30  pavel
--  Log         : Added: Bytes counters 64 bits.
--  Log         :
--  Log         : Revision 1.2  2003/03/23 10:19:22  pavel
--  Log         : Add oaSubscr.mib.
--  Log         :
--  Log         : Revision 1.1.2.1  2003/03/23 08:30:39  pavel
--  Log         : Support for Subscriber accounting (susbcr-name table).
--  Log         :
--
--
-- Copyright (c) 1999 NBase-Xyplex.  All Rights Reserved.
--
--
-- Reproduction of this document is authorized on condition that this
-- copyright notice is included.  This NBase-Xyplex SNMP MIB Specification
-- embodies NBase-Xyplex's proprietary intellectual property.  NBase-Xyplex
-- retains all title and ownership in the specification, including any
-- revisions.
--
-- It is NBase-Xyplex's intent to encourage the widespread use of this
-- specification in connection with the management of NBase-Xyplex's
-- products. NBase-Xyplex grants vendor, end-users, and other interested
-- parties a non-exclusive license to use this specification in
-- connection with the management of NBase-Xyplex's products.
--
-- This specification is supplied "AS IS," and NBase-Xyplex makes no
-- warranty, either express or implied, as to the use, operation,
-- condition, or performance of the specification.
--
-- Copyright text courtesy of NBase-Xyplex
--
-- If you have any questions about this MIB, please call NBase-Xyplex
-- Technical Support Center at 1-800-858-7815 from inside USA or
-- 1-818-773-0900 from outside USA.
--
--
-- NBase-Xyplex retains the right to change this MIB without notification.
--

OASUBSCR-CFG-MIB DEFINITIONS ::= BEGIN

        IMPORTS
                enterprises, Counter32, Counter64         FROM RFC1155-SMI
                DisplayString       FROM RFC1213-MIB
                OBJECT-TYPE         FROM RFC-1212
                TRAP-TYPE           FROM RFC-1215;


        SubscriberName ::=  DisplayString(SIZE(2..35))

        DirectionType ::= INTEGER
            {
            other       (1),
            ingress     (2),
            egress      (3)
            }

        AccountCouter ::= Counter32
        AccountCounter64 ::= Counter64

-- ************************************************************
-- NBase Object Identifier Definition
-- ************************************************************

nbase              OBJECT IDENTIFIER ::= { enterprises 629 }
nbSwitchG1         OBJECT IDENTIFIER ::= { nbase 1 }
nbSwitchG1Il       OBJECT IDENTIFIER ::= { nbSwitchG1 50}

oaSubscriberConfig OBJECT IDENTIFIER ::= { nbSwitchG1Il 15}
oaSubscrConfigGen  OBJECT IDENTIFIER ::= { oaSubscriberConfig 1 }


-- ***********************************************************************
-- Subscriber Accounting Group
-- ***********************************************************************

oaSubscrAccounting      OBJECT IDENTIFIER ::= { oaSubscriberConfig 6 }

-- ***********************************************************************
-- Subscriber Accounting Table
-- ***********************************************************************

oaSubscrAccNameTable OBJECT-TYPE
                SYNTAX  SEQUENCE OF OaSubscrAccNameEntry
                ACCESS  not-accessible
                STATUS  mandatory
                DESCRIPTION
                "."
                ::= { oaSubscrAccounting 10 }

oaSubscrAccNameEntry OBJECT-TYPE
                SYNTAX  OaSubscrAccNameEntry
                ACCESS  not-accessible
                STATUS  mandatory
                DESCRIPTION
                "The Entries (records)."
                INDEX { oaSubscrName,
                        oaSubscrDirection }

                ::= { oaSubscrAccNameTable 1 }

OaSubscrAccNameEntry ::= SEQUENCE {
                oaSubscrName                       SubscriberName,
                oaSubscrDirection                  DirectionType,
                oaSubscrAccNmAdminStatus           INTEGER,
                oaSubscrAccNmOperStatus            INTEGER,
                oaSubscrAccNmConformingBytes       AccountCouter,
                oaSubscrAccNmHighConformingBytes   Counter32,
                oaSubscrAccNmLowConformingBytes    Counter32,
                oaSubscrAccNmExceedingBytes        AccountCouter,
                oaSubscrAccNmHighExceedingBytes    Counter32,
                oaSubscrAccNmLowExceedingBytes     Counter32,
                oaSubscrAccNmConformingPackets     AccountCouter,
                oaSubscrAccNmHighConformingPackets Counter32,
                oaSubscrAccNmLowConformingPackets  Counter32,
                oaSubscrAccNmExceedingPackets      AccountCouter,
                oaSubscrAccNmHighExceedingPackets  Counter32,
                oaSubscrAccNmLowExceedingPackets   Counter32,
                oaSubscrAccNm64ConformingBytes     AccountCounter64,
                oaSubscrAccNm64ExceedingBytes      AccountCounter64
                }

oaSubscrName    OBJECT-TYPE
                SYNTAX SubscriberName
                ACCESS read-only
                STATUS mandatory
                DESCRIPTION
                "The subscriber name."
                ::= { oaSubscrAccNameEntry 1 }

oaSubscrDirection    OBJECT-TYPE
                SYNTAX DirectionType
                ACCESS read-only
                STATUS mandatory
                DESCRIPTION
                "The ingress/egress direction."
                ::= { oaSubscrAccNameEntry 2 }

oaSubscrAccNmAdminStatus    OBJECT-TYPE
                SYNTAX INTEGER
                {
                 other      (1),
                 enable     (2),
                 disable    (3),
                 pause      (4),
                 resume     (5),
                 clear      (6)
                }
                ACCESS read-write
                STATUS mandatory
                DESCRIPTION
                "Accounting Admin Status."
                ::= { oaSubscrAccNameEntry 3 }

oaSubscrAccNmOperStatus    OBJECT-TYPE
                SYNTAX INTEGER
                {
                 other      (1),
                 active     (2),
                 paused     (3),
                 disabled   (4)
                }
                ACCESS read-only
                STATUS mandatory
                DESCRIPTION
                "Accounting Oper Status."
                ::= { oaSubscrAccNameEntry 4 }

oaSubscrAccNmConformingBytes   OBJECT-TYPE
                SYNTAX  AccountCouter
                ACCESS  read-only
                STATUS  mandatory
                DESCRIPTION
                "The Conforming Bytes Counter in blocks (1 block = 64k bytes) for Subscriber."
                ::= { oaSubscrAccNameEntry 6 }

oaSubscrAccNmHighConformingBytes   OBJECT-TYPE
                SYNTAX  Counter32
                ACCESS  read-only
                STATUS  mandatory
                DESCRIPTION
                "The Conforming Bytes Counter (High part) for Subscriber."
                ::= { oaSubscrAccNameEntry 7 }

oaSubscrAccNmLowConformingBytes   OBJECT-TYPE
                SYNTAX  Counter32
                ACCESS  read-only
                STATUS  mandatory
                DESCRIPTION
                "The Conforming Bytes Counter (Low part) for Subscriber."
                ::= { oaSubscrAccNameEntry 8 }

oaSubscrAccNmExceedingBytes   OBJECT-TYPE
                SYNTAX  AccountCouter
                ACCESS  read-only
                STATUS  mandatory
                DESCRIPTION
                "The Exceeding Bytes Counter in blocks (1 block = 64k bytes) for Subscriber."
                ::= { oaSubscrAccNameEntry 9 }

oaSubscrAccNmHighExceedingBytes   OBJECT-TYPE
                SYNTAX  Counter32
                ACCESS  read-only
                STATUS  mandatory
                DESCRIPTION
                "The Exceeding Bytes Counter (High part) for Subscriber."
                ::= { oaSubscrAccNameEntry 10 }

oaSubscrAccNmLowExceedingBytes   OBJECT-TYPE
                SYNTAX  Counter32
                ACCESS  read-only
                STATUS  mandatory
                DESCRIPTION
                "The Exceeding Bytes Counter (Low part) for Subscriber."
                ::= { oaSubscrAccNameEntry 11 }

oaSubscrAccNmConformingPackets   OBJECT-TYPE
                SYNTAX  AccountCouter
                ACCESS  read-only
                STATUS  mandatory
                DESCRIPTION
                "The Conforming Packets Counter in blocks (1 block = 64k bytes) for Subscriber."
                ::= { oaSubscrAccNameEntry 12 }

oaSubscrAccNmHighConformingPackets   OBJECT-TYPE
                SYNTAX  Counter32
                ACCESS  read-only
                STATUS  mandatory
                DESCRIPTION
                "The Conforming Packets Counter (High part) for Subscriber."
                ::= { oaSubscrAccNameEntry 13 }

oaSubscrAccNmLowConformingPackets   OBJECT-TYPE
                SYNTAX  Counter32
                ACCESS  read-only
                STATUS  mandatory
                DESCRIPTION
                "The Conforming Packets Counter (Low part) for Subscriber."
                ::= { oaSubscrAccNameEntry 14 }

oaSubscrAccNmExceedingPackets   OBJECT-TYPE
                SYNTAX  AccountCouter
                ACCESS  read-only
                STATUS  mandatory
                DESCRIPTION
                "The Exceeding Packets Counter in blocks (1 block = 64k bytes) for Subscriber."
                ::= { oaSubscrAccNameEntry 15 }


oaSubscrAccNmHighExceedingPackets   OBJECT-TYPE
                SYNTAX  Counter32
                ACCESS  read-only
                STATUS  mandatory
                DESCRIPTION
                "The Exceeding Packets Counter (High part) for Subscriber."
                ::= { oaSubscrAccNameEntry 16 }

oaSubscrAccNmLowExceedingPackets   OBJECT-TYPE
                SYNTAX  Counter32
                ACCESS  read-only
                STATUS  mandatory
                DESCRIPTION
                "The Exceeding Packets Counter (Low part) for Subscriber."
                ::= { oaSubscrAccNameEntry 17 }

oaSubscrAccNm64ConformingBytes   OBJECT-TYPE
                SYNTAX  AccountCounter64
                ACCESS  read-only
                STATUS  mandatory
                DESCRIPTION
                "The Conforming Bytes Counter (64 bits) for VIF."
                ::= { oaSubscrAccNameEntry 18 }

oaSubscrAccNm64ExceedingBytes   OBJECT-TYPE
                SYNTAX  AccountCounter64
                ACCESS  read-only
                STATUS  mandatory
                DESCRIPTION
                "The Exceeding Bytes Counter (64 bits) for VIF."
                ::= { oaSubscrAccNameEntry 19 }

-- ***********************************************************************
-- Subscriber per Port & Tag Accounting Table
-- ***********************************************************************

-- ***********************************************************************
--              T R A P s   D e f i n i t i o n s
-- ***********************************************************************


END
