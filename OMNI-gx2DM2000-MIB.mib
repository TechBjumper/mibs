OMNI-gx2DM2000-MIB DEFINITIONS ::= BEGIN

    IMPORTS
	IpAddress, TimeTicks, Counter            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Dm2000
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.
		
		   --REVISION	"0" Aug 18, 2011
		   --REVISION	"1" May 22, 2012

		   --DESCRIPTION
		   --			Added revision and description comment section


		--    OMNISTAR Directly Modulated Laser Module (Forward Path Transmetter)  MIB MODULE

	-- This MIB module defines information for management of HFC networks
		-- 
		-- The MIB module assumes that all generic (static) network element
		-- information is defined in a different module such as the HFC module
		-- The MIB consists of two groups:
		-- the device type descriptor subgroup and 
		-- gx2Dm2000 Network Elements subgroup.
		-- The device type descriptor subgroup is used to define 
		-- parameters specific to gx2Dm2000 device type.
		-- These parameters are common across all network elements
		-- from gx2Dm2000 device type.
		--
		-- The gx2Dm2000 Network Elements subgroup is
		-- a list of gx2Dm2000 type elements in the
		-- current network topology with nominal
		-- and current parameter values for the
		-- individual network elements; the individual
		-- network elements are identified by  
		-- index from hfcCommonTable.
		-- That implies what hfcCommonTableIndex and
		-- gx2Dm2000TableIndex are equal for each individual
		-- network element.
		-- This table is an extension of the hfcCommonTable
		-- for all elements of gx2Dm2000 type.
		--
		-- Both groups are mandatory for management of gx2Dm2000 devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Dm2000 Device Descriptor subgroup.

		-- The device type descriptor subgroup is used to define 
		-- parameters specific to gx2Dm2000 device type.
		-- These parameters are common across all network elements
		-- from gx2Dm2000 device type.


		gx2dm2000Descriptor OBJECT IDENTIFIER ::= {gx2Dm2000 1}



--*****************************************************************************
		--              gx2Dm2000 Table
		
		-- Contains a list of all gx2Dm2000 type devices in
		-- the network. Each device is characterized with
		-- current network topology information, with nominal
		-- and current parameter values for the
		-- individual network elements;
		--
		-- The individual network elements indentified by  
		-- index from hfcCommonTable.
		-- That implies what hfcCommonTableIndex and
		-- gx2dm2000TableIndex are equal for each individual
		-- nettwork element.
		-- This table should be used as an extension of the hfcCommonTable
		-- for all elements of gx2Dm2000 type.


	       gx2dm2000AnalogTable                    OBJECT-TYPE
			 SYNTAX             SEQUENCE OF Gx2dm2000AnalogEntry
			 ACCESS             not-accessible
			 STATUS             mandatory
			 DESCRIPTION
			 "This table contains gx2Dm2000 specific parameters with
			  nominal and current values."
			 ::= { gx2Dm2000 2 }


	       gx2dm2000AnalogEntry               OBJECT-TYPE
			 SYNTAX             Gx2dm2000AnalogEntry
			 ACCESS             not-accessible
			 STATUS             mandatory
			 DESCRIPTION
			 "This list contains the analog parameters and descriptions."
			 INDEX { gx2dm2000AnalogTableIndex }
			 ::= { gx2dm2000AnalogTable  1}

--***********************************************************************
	       gx2dm2000DigitalTable                    OBJECT-TYPE
			 SYNTAX             SEQUENCE OF Gx2dm2000DigitalEntry
			 ACCESS             not-accessible
			 STATUS             mandatory
			 DESCRIPTION
			 "This table contains gx2Dm2000 specific parameters with
			  nominal and current values."
			 ::= { gx2Dm2000 3 }

	       gx2dm2000DigitalEntry               OBJECT-TYPE
			 SYNTAX             Gx2dm2000DigitalEntry
			 ACCESS             not-accessible
			 STATUS             mandatory
			 DESCRIPTION
			 "This list contains digital parameters and descriptions."
			 INDEX { gx2dm2000DigitalTableIndex }
			 ::= { gx2dm2000DigitalTable  2}

--***********************************************************************
	       gx2dm2000StatusTable                    OBJECT-TYPE
			 SYNTAX             SEQUENCE OF Gx2dm2000StatusEntry
			 ACCESS             not-accessible
			 STATUS             mandatory
			 DESCRIPTION
			 "This table contains gx2Dm2000 specific parameters with
			  nominal and current values."
			 ::= { gx2Dm2000 4 }

	       gx2dm2000StatusEntry               OBJECT-TYPE
			 SYNTAX             Gx2dm2000StatusEntry
			 ACCESS             not-accessible
			 STATUS             mandatory
			 DESCRIPTION
			 "This list contains Status parameters and descriptions."
			 INDEX { gx2dm2000StatusTableIndex }
			 ::= { gx2dm2000StatusTable  3}

--***********************************************************************
	       gx2dm2000FactoryTable                    OBJECT-TYPE
			 SYNTAX             SEQUENCE OF Gx2dm2000FactoryEntry
			 ACCESS             not-accessible
			 STATUS             mandatory
			 DESCRIPTION
			 "This table contains gx2Dm2000 specific parameters with
			  nominal and current values."
			 ::= { gx2Dm2000 5 }

	       gx2dm2000FactoryEntry               OBJECT-TYPE
			 SYNTAX             Gx2dm2000FactoryEntry
			 ACCESS             not-accessible
			 STATUS             mandatory
			 DESCRIPTION
			 "This list contains Factory parameters and descriptions."
			 INDEX { gx2dm2000FactoryTableIndex }
			 ::= { gx2dm2000FactoryTable  4}

--***********************************************************************

	       gx2Dm2000HoldTimeTable                    OBJECT-TYPE
			 SYNTAX             SEQUENCE OF Gx2Dm2000HoldTimeEntry
			 ACCESS             not-accessible
			 STATUS             mandatory
			 DESCRIPTION
			 "This table contains gx2Dm2000 specific parameters with
			  nominal and current values."
			 ::= { gx2Dm2000 6 }

	       gx2Dm2000HoldTimeEntry               OBJECT-TYPE
			 SYNTAX             Gx2Dm2000HoldTimeEntry
			 ACCESS             not-accessible
			 STATUS             mandatory
			 DESCRIPTION
			 "This list contains digital product class and the
			  associated RF channel parameters and descriptions."
			 INDEX { gx2Dm2000HoldTimeTableIndex, gx2Dm2000HoldTimeSpecIndex }
			 ::= { gx2Dm2000HoldTimeTable  5}



	      Gx2dm2000AnalogEntry    ::= SEQUENCE  
	       {
		gx2dm2000AnalogTableIndex         INTEGER,
		
		--           Analog Parameters

		dm2000labelOffsetNomMonitor 		DisplayString (SIZE (0..80)),
		dm2000uomOffsetNomMonitor		DisplayString (SIZE (0..80)),
		dm2000majorHighOffsetNomMonitor	Float, 
		dm2000majorLowOffsetNomMonitor	Float, 
		dm2000minorHighOffsetNomMonitor	Float,
		dm2000minorLowOffsetNomMonitor	Float, 
		dm2000currentValueOffsetNomMonitor	Float, 
		dm2000stateFlagOffsetNomMonitor	INTEGER,
		dm2000minValueOffsetNomMonitor	Float,
		dm2000maxValueOffsetNomMonitor 	Float,
		dm2000alarmStateOffsetNomMonitor	INTEGER,

		dm2000labelOffsetNomCnt 		DisplayString (SIZE (0..80)),
		dm2000uomOffsetNomCnt			DisplayString (SIZE (0..80)),
		dm2000majorHighOffsetNomCnt		Float, 
		dm2000majorLowOffsetNomCnt		Float, 
		dm2000minorHighOffsetNomCnt		Float,
		dm2000minorLowOffsetNomCnt		Float, 
		dm2000currentValueOffsetNomCnt	Float, 
		dm2000stateFlagOffsetNomCnt		INTEGER,
		dm2000minValueOffsetNomCnt		Float,
		dm2000maxValueOffsetNomCnt 		Float,
		dm2000alarmStateOffsetNomCnt		INTEGER,

		dm2000labelRelAttenSetting 		DisplayString (SIZE (0..80)),
		dm2000uomRelAttenSetting		DisplayString (SIZE (0..80)),
		dm2000majorHighRelAttenSetting	Float, 
		dm2000majorLowRelAttenSetting		Float, 
		dm2000minorHighRelAttenSetting	Float,
		dm2000minorLowRelAttenSetting		Float, 
		dm2000currentValueRelAttenSetting	Float, 
		dm2000stateFlagRelAttenSetting	INTEGER,
		dm2000minValueRelAttenSetting		Float,
		dm2000maxValueRelAttenSetting 	Float,
		dm2000alarmStateRelAttenSetting	INTEGER,

		dm2000labelOptPower			DisplayString (SIZE (0..80)),
		dm2000uomOptPower				DisplayString (SIZE (0..80)),
		dm2000majorHighOptPower			Float, 
		dm2000majorLowOptPower			Float, 
		dm2000minorHighOptPower			Float,
		dm2000minorLowOptPower			Float, 
		dm2000currentValueOptPower		Float, 
		dm2000stateFlagOptPower			INTEGER,
		dm2000minValueOptPower			Float,
		dm2000maxValueOptPower 			Float,
		dm2000alarmStateOptPower		INTEGER,

		dm2000labelLaserBias			DisplayString (SIZE (0..80)),
		dm2000uomLaserBias			DisplayString (SIZE (0..80)),
		dm2000majorHighLaserBias		Float, 
		dm2000majorLowLaserBias			Float, 
		dm2000minorHighLaserBias		Float,
		dm2000minorLowLaserBias			Float, 
		dm2000currentValueLaserBias		Float, 
		dm2000stateFlagLaserBias		INTEGER,
		dm2000minValueLaserBias			Float,
		dm2000maxValueLaserBias 		Float,
		dm2000alarmStateLaserBias		INTEGER,

		dm2000labelTecCurrent			DisplayString (SIZE (0..80)),
		dm2000uomTecCurrent			DisplayString (SIZE (0..80)),
		dm2000majorHighTecCurrent		Float, 
		dm2000majorLowTecCurrent		Float, 
		dm2000minorHighTecCurrent		Float,
		dm2000minorLowTecCurrent		Float, 
		dm2000currentValueTecCurrent		Float, 
		dm2000stateFlagTecCurrent		INTEGER,
		dm2000minValueTecCurrent		Float,
		dm2000maxValueTecCurrent 		Float,
		dm2000alarmStateTecCurrent		INTEGER,

		dm2000labelLaserTemp			DisplayString (SIZE (0..80)),
		dm2000uomLaserTemp			DisplayString (SIZE (0..80)),
		dm2000majorHighLaserTemp		Float, 
		dm2000majorLowLaserTemp			Float, 
		dm2000minorHighLaserTemp		Float,
		dm2000minorLowLaserTemp			Float, 
		dm2000currentValueLaserTemp		Float, 
		dm2000stateFlagLaserTemp		INTEGER,
		dm2000minValueLaserTemp			Float,
		dm2000maxValueLaserTemp			Float,
		dm2000alarmStateLaserTemp		INTEGER,

		dm2000labelModuleTemp			DisplayString (SIZE (0..80)),
		dm2000uomModuleTemp				DisplayString (SIZE (0..80)),
		dm2000majorHighModuleTemp			Float, 
		dm2000majorLowModuleTemp			Float, 
		dm2000minorHighModuleTemp			Float,
		dm2000minorLowModuleTemp			Float, 
		dm2000currentValueModuleTemp		Float, 
		dm2000stateFlagModuleTemp			INTEGER,
		dm2000minValueModuleTemp			Float,
		dm2000maxValueModuleTemp			Float,
		dm2000alarmStateModuleTemp			INTEGER,

		dm2000labelFanCurrent			DisplayString (SIZE (0..80)),
		dm2000uomFanCurrent			DisplayString (SIZE (0..80)),
		dm2000majorHighFanCurrent		Float, 
		dm2000majorLowFanCurrent		Float, 
		dm2000minorHighFanCurrent		Float,
		dm2000minorLowFanCurrent		Float, 
		dm2000currentValueFanCurrent		Float, 
		dm2000stateFlagFanCurrent		INTEGER,
		dm2000minValueFanCurrent		Float,
		dm2000maxValueFanCurrent 		Float,
		dm2000alarmStateFanCurrent		INTEGER,

		dm2000label12Volt				DisplayString (SIZE (0..80)),
		dm2000uom12Volt			DisplayString (SIZE (0..80)),
		dm2000majorHigh12Volt			Float, 
		dm2000majorLow12Volt			Float, 
		dm2000minorHigh12Volt			Float,
		dm2000minorLow12Volt			Float, 
		dm2000currentValue12Volt		Float, 
		dm2000stateFlag12Volt			INTEGER,
		dm2000minValue12Volt			Float,
		dm2000maxValue12Volt			Float,
		dm2000alarmState12Volt			INTEGER
		}

		-- ****************  Digital Parameters ***********************
      Gx2dm2000DigitalEntry    ::= SEQUENCE  
      {
		gx2dm2000DigitalTableIndex         INTEGER,

		dm2000labelRfInput			DisplayString (SIZE (0..80)),
		dm2000enumRfInput					DisplayString (SIZE (0..80)),
		dm2000valueRfInput			INTEGER,
		dm2000stateflagRfInput  		INTEGER,

		dm2000labelOptOutput			DisplayString (SIZE (0..80)),
		dm2000enumOptOutput				DisplayString (SIZE (0..80)),
		dm2000valueOptOutput			INTEGER,
		dm2000stateflagOptOutput         	INTEGER,

		dm2000labelLaserMode			DisplayString (SIZE (0..80)),
		dm2000enumLaserMode				DisplayString (SIZE (0..80)),
		dm2000valueLaserMode			INTEGER,
		dm2000stateflagLaserMode         	INTEGER,

		dm2000labelLaserSecMode			DisplayString (SIZE (0..80)),
		dm2000enumLaserSecMode				DisplayString (SIZE (0..80)),
		dm2000valueLaserSecMode			INTEGER,
		dm2000stateflagLaserSecMode     	INTEGER,

		dm2000labelVideoOffset			DisplayString (SIZE (0..80)),
		dm2000enumVideoOffset				DisplayString (SIZE (0..80)),
		dm2000valueVideoOffset			INTEGER,
		dm2000stateflagVideoOffset         	INTEGER,

		dm2000labelFactoryDefault		DisplayString (SIZE (0..80)),
		dm2000enumFactoryDefault				DisplayString (SIZE (0..80)),
		dm2000valueFactoryDefault		INTEGER,
		dm2000stateflagFactoryDefault   	INTEGER,

		dm2000labelFiberLength			DisplayString (SIZE (0..80)),
		dm2000enumFiberLength			DisplayString (SIZE (0..80)),
		dm2000valueFiberLength			INTEGER,
		dm2000stateflagFiberLength   	INTEGER,
        
		dm2000labelWavelengthOffset	DisplayString (SIZE (0..80)),
		dm2000enumWavelengthOffset		DisplayString (SIZE (0..80)),
		dm2000valueWavelengthOffset	INTEGER,
		dm2000stateflagWavelengthOffset	INTEGER
         
		}

		-- ****************  Status Parameters ************************************
      Gx2dm2000StatusEntry    ::= SEQUENCE  
      {
		gx2dm2000StatusTableIndex         INTEGER,

		dm2000labelBoot				DisplayString (SIZE (0..80)),
		dm2000valueBoot				INTEGER,
		dm2000stateflagBoot			INTEGER,
		
		dm2000labelFlash				DisplayString (SIZE (0..80)),
		dm2000valueFlash				INTEGER,
		dm2000stateflagFlash			INTEGER,

		dm2000labelFactoryDataCRC 		DisplayString (SIZE (0..80)),
		dm2000valueFactoryDataCRC		INTEGER,
		dm2000stateflagFactoryDataCRC		INTEGER,

		dm2000labelLaserDataCRC 		DisplayString (SIZE (0..80)),
		dm2000valueLaserDataCRC 		INTEGER,
		dm2000stateflagLaserDataCRC 		INTEGER,

		dm2000labelAlarmDataCrc			DisplayString (SIZE (0..80)),
		dm2000valueAlarmDataCrc			INTEGER,
		dm2000stateflagAlarmDataCrc		INTEGER,

		dm2000labelHWStatus			DisplayString (SIZE (0..80)),
		dm2000valueHWStatus			INTEGER,
		dm2000stateflagHWStatus			INTEGER,

		dm2000labelRFInputStatus			DisplayString (SIZE (0..80)),
		dm2000valueRFInputStatus			INTEGER,
		dm2000stateflagRFInputStatus			INTEGER
		}


		-- ****************  Factory Parameters *************************************
      Gx2dm2000FactoryEntry   ::= SEQUENCE  
      {
		gx2dm2000FactoryTableIndex         INTEGER,
		dm2000bootControlByteValue  			INTEGER,
		dm2000bootStatusByteValue   			INTEGER,
		dm2000bank1CRCValue    			INTEGER,
		dm2000bank2CRCValue    			INTEGER,
		dm2000prgEEPROMByteValue    			INTEGER,
		dm2000factoryCRCValue    			INTEGER,
		dm2000calculateCRCValue    			INTEGER,
		dm2000hourMeterValue    			INTEGER,
		dm2000flashPrgCntAValue    			INTEGER,
		dm2000flashPrgCntBValue    			INTEGER,
		dm2000flashBankARevValue    			DisplayString (SIZE (0..80)),
		dm2000flashBankBRevValue    			DisplayString (SIZE (0..80))
		}

		-- ****************  Hold Time Parameters *************************************
	    Gx2Dm2000HoldTimeEntry    ::= SEQUENCE  
	    {
		gx2Dm2000HoldTimeTableIndex        INTEGER,
		gx2Dm2000HoldTimeSpecIndex         INTEGER,   
		gx2Dm2000HoldTimeData  			 INTEGER
		}



            -- ************** Analog Parameters ****************************
		gx2dm2000AnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2dm2000AnalogEntry 1}
-- New Parameter

		dm2000labelOffsetNomMonitor     OBJECT-TYPE
			   SYNTAX           DisplayString (SIZE (0..80))
			   ACCESS           read-only
			   STATUS           optional
			   DESCRIPTION
			   "The value of this object provides the label of the
			    Offset Monitor Analog parameter."
			   ::= { gx2dm2000AnalogEntry 2}

		dm2000uomOffsetNomMonitor       OBJECT-TYPE
			   SYNTAX           DisplayString (SIZE (0..80))
			   ACCESS           read-only
			   STATUS           optional
			   DESCRIPTION
			   "The value of this object provides the Unit of Measure of the
			    Offset Monitor Analog parameter."
			   ::= { gx2dm2000AnalogEntry 3}

		dm2000majorHighOffsetNomMonitor OBJECT-TYPE
			   SYNTAX           Float 
			   ACCESS           read-only
			   STATUS           mandatory
			   DESCRIPTION
			   "The value of this object provides the Major High alarm value
			    of the Offset Monitor Analog parameter.
			   This value is a floating point number that is represented as an IEEE 32 bit number."
			   ::= { gx2dm2000AnalogEntry 4}


		dm2000majorLowOffsetNomMonitor  OBJECT-TYPE
			   SYNTAX           Float 
			   ACCESS           read-only
			   STATUS           mandatory
			   DESCRIPTION
			   "The value of this object provides the Major Low alarm value
			    of the Offset Monitor Analog parameter.
			    This value is a floating point number that is represented as an IEEE 32 bit number."
			   ::= { gx2dm2000AnalogEntry 5}

		dm2000minorHighOffsetNomMonitor OBJECT-TYPE
			   SYNTAX           Float
			   ACCESS           read-only
			   STATUS           mandatory
			   DESCRIPTION
			   "The value of this object provides the Minor High alarm value
			    of the Offset Monitor Analog parameter.
			   This value is a float and is represented as an IEEE 32 bit number."
			   ::= { gx2dm2000AnalogEntry 6}

		dm2000minorLowOffsetNomMonitor  OBJECT-TYPE
			   SYNTAX           Float 
			   ACCESS           read-only
			   STATUS           mandatory
			   DESCRIPTION
			   "The value of this object provides the Minor Low alarm value
			    of the Offset Monitor Analog parameter.
			   This value is a float and is represented as an IEEE 32 bit number."
			   ::= { gx2dm2000AnalogEntry 7}

		dm2000currentValueOffsetNomMonitor  OBJECT-TYPE
			   SYNTAX           Float 
			   ACCESS           read-only
			   STATUS           mandatory
			   DESCRIPTION
			   "The value of this object provides the Current value
			    of the Offset Monitor Analog parameter.
			   This value is a float and is represented as an IEEE 32 bit number."
			   ::= { gx2dm2000AnalogEntry 8}

		dm2000stateFlagOffsetNomMonitor  OBJECT-TYPE
			   SYNTAX           INTEGER
								{
								hidden(1),
								read-only(2),
								updateable(3)
								}
			   ACCESS           read-only
			   STATUS           mandatory
			   DESCRIPTION
			   "The value of this object provides the state
			    of the Offset Monitor Analog parameter. (0-Hidden	
			          1-Read-Only, 2-Updateable)"
			   ::= { gx2dm2000AnalogEntry 9}

		dm2000minValueOffsetNomMonitor  OBJECT-TYPE
			   SYNTAX           Float
			   ACCESS           read-only
			   STATUS           mandatory
			   DESCRIPTION
			   "The value of this object provides the minimum value
			    the Offset Monitor Analog parameter can achive.
			   This value is a float and is represented as an IEEE 32 bit number."
			   ::= { gx2dm2000AnalogEntry 10}

		dm2000maxValueOffsetNomMonitor  OBJECT-TYPE
			   SYNTAX           Float
			   ACCESS           read-only
			   STATUS           mandatory
			   DESCRIPTION
			   "The value of this object provides the maximum value
			    the Offset Monitor Analog parameter can achive.
			   This value is a float and is represented as an IEEE 32 bit number."
			   ::= { gx2dm2000AnalogEntry 11}

		dm2000alarmStateOffsetNomMonitor  OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Monitor Analog parameter."
			   ::= { gx2dm2000AnalogEntry 12}

-- New Parameter

		dm2000labelOffsetNomCnt         OBJECT-TYPE
			   SYNTAX           DisplayString (SIZE (0..80))
			   ACCESS           read-only
			   STATUS           optional
			   DESCRIPTION
			   "The value of this object provides the label of the
			    Offset Control Analog parameter."
			   ::= { gx2dm2000AnalogEntry 13}

		dm2000uomOffsetNomCnt           OBJECT-TYPE
			   SYNTAX           DisplayString (SIZE (0..80))
			   ACCESS           read-only
			   STATUS           optional
			   DESCRIPTION
			   "The value of this object provides the label of the
			    Offset Control Analog parameter."
			   ::= { gx2dm2000AnalogEntry 14}

		dm2000majorHighOffsetNomCnt     OBJECT-TYPE
			   SYNTAX           Float 
			   ACCESS           read-only
			   STATUS           mandatory
			   DESCRIPTION
			   "The value of this object provides the Major High alarm value
			    of the Offset Control Analog parameter.
			   This value is a float and is represented as an IEEE 32 bit number."
			   ::= { gx2dm2000AnalogEntry 15}


		dm2000majorLowOffsetNomCnt      OBJECT-TYPE
			   SYNTAX           Float 
			   ACCESS           read-only
			   STATUS           mandatory
			   DESCRIPTION
			   "The value of this object provides the Major Low alarm value
			    of the Offset Control Analog parameter.
			   This value is a float and is represented as an IEEE 32 bit number."
			   ::= { gx2dm2000AnalogEntry 16}

		dm2000minorHighOffsetNomCnt     OBJECT-TYPE
			   SYNTAX           Float
			   ACCESS           read-only
			   STATUS           mandatory
			   DESCRIPTION
			   "The value of this object provides the Minor High alarm value
			    of the Offset Control Analog parameter.
			   This value is a floating point number that is represented as an IEEE 32 bit number."
			   ::= { gx2dm2000AnalogEntry 17}

		dm2000minorLowOffsetNomCnt      OBJECT-TYPE
			   SYNTAX           Float 
			   ACCESS           read-only
			   STATUS           mandatory
			   DESCRIPTION
			   "The value of this object provides the Minor Low alarm value
			    of the Offset Control Analog parameter.
			   This value is a floating point number that is represented as an IEEE 32 bit number."
			   ::= { gx2dm2000AnalogEntry 18}

		dm2000currentValueOffsetNomCnt  OBJECT-TYPE
			   SYNTAX			Float
			   ACCESS           read-write
			   STATUS           mandatory
			   DESCRIPTION
			   "The value of this object provides the Current value
			    of the Offset Control Analog parameter.
			   This value is a floating point number that is represented as an IEEE 32 bit number."
			   ::= { gx2dm2000AnalogEntry 19}

		dm2000stateFlagOffsetNomCnt     OBJECT-TYPE
			   SYNTAX           INTEGER
								{
								hidden(1),
								read-only(2),
								updateable(3)
								}
			   ACCESS           read-only
			   STATUS           mandatory
			   DESCRIPTION
			   "The value of this object provides the state
			    of the Offset Control Analog parameter. (0-Hidden	
			          1-Read-Only, 2-Updateable)"
			   ::= { gx2dm2000AnalogEntry 20}

		dm2000minValueOffsetNomCnt      OBJECT-TYPE
			   SYNTAX           Float
			   ACCESS           read-only
			   STATUS           mandatory
			   DESCRIPTION
			   "The value of this object provides the minimum value
			    the Offset Control Analog parameter can achive.
			   This value is a floating point number that is represented as an IEEE 32 bit number."
			   ::= { gx2dm2000AnalogEntry 21}

		dm2000maxValueOffsetNomCnt      OBJECT-TYPE
			   SYNTAX           Float
			   ACCESS           read-only
			   STATUS           mandatory
			   DESCRIPTION
			   "The value of this object provides the maximum value
			    the Offset Control Analog parameter can achive.
			   This value is a floating point number that is represented as an IEEE 32 bit number."
			   ::= { gx2dm2000AnalogEntry 22}

		dm2000alarmStateOffsetNomCnt    OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Control Analog parameter."
			   ::= { gx2dm2000AnalogEntry 23}
-- New Parameter

		dm2000labelRelAttenSetting      OBJECT-TYPE
			   SYNTAX           DisplayString (SIZE (0..80))
			   ACCESS           read-only
			   STATUS           optional
			   DESCRIPTION
			   "The value of this object provides the label of the
			    Attenuator Setting Analog parameter."
			   ::= { gx2dm2000AnalogEntry 24}

		dm2000uomRelAttenSetting        OBJECT-TYPE
			   SYNTAX           DisplayString (SIZE (0..80))
			   ACCESS           read-only
			   STATUS           optional
			   DESCRIPTION
			   "The value of this object provides the Unit of Measure of the
			    Attenuator Setting Analog parameter."
			   ::= { gx2dm2000AnalogEntry 25}

		dm2000majorHighRelAttenSetting  OBJECT-TYPE
			   SYNTAX           Float 
			   ACCESS           read-only
			   STATUS           mandatory
			   DESCRIPTION
			   "The value of this object provides the Major High alarm value
			    of the Attenuator Setting Analog parameter.
			   This value is a floating point number that is represented as an IEEE 32 bit number."
			   ::= { gx2dm2000AnalogEntry 26}


		dm2000majorLowRelAttenSetting   OBJECT-TYPE
			   SYNTAX           Float 
			   ACCESS           read-only
			   STATUS           mandatory
			   DESCRIPTION
			   "The value of this object provides the Major Low alarm value
			    of the Attenuator Setting Analog parameter.
			   This value is a floating point number that is represented as an IEEE 32 bit number."
			   ::= { gx2dm2000AnalogEntry 27}

		dm2000minorHighRelAttenSetting  OBJECT-TYPE
			   SYNTAX           Float
			   ACCESS           read-only
			   STATUS           mandatory
			   DESCRIPTION
			   "The value of this object provides the Minor High alarm value
			    of the Attenuator Setting Analog parameter.
   			   This value is a floating point number that is represented as an IEEE 32 bit number."
			   ::= { gx2dm2000AnalogEntry 28}

		dm2000minorLowRelAttenSetting   OBJECT-TYPE
			   SYNTAX           Float 
			   ACCESS           read-only
			   STATUS           mandatory
			   DESCRIPTION
			   "The value of this object provides the Minor Low alarm value
			    of the Attenuator Setting Analog parameter.
			   This value is a floating point number that is represented as an IEEE 32 bit number."
			   ::= { gx2dm2000AnalogEntry 29}

		dm2000currentValueRelAttenSetting   OBJECT-TYPE
			   SYNTAX           Float 
			   ACCESS           read-write
			   STATUS           mandatory
			   DESCRIPTION
			   "The value of this object provides the Current value
			    of the Attenuator Setting Analog parameter.
			   This value is a floating point number that is represented as an IEEE 32 bit number."
			   ::= { gx2dm2000AnalogEntry 30}

		dm2000stateFlagRelAttenSetting  OBJECT-TYPE
			   SYNTAX           INTEGER
								{
								hidden(1),
								read-only(2),
								updateable(3)
								}
			   ACCESS           read-only
			   STATUS           mandatory
			   DESCRIPTION
			   "The value of this object provides the state
			    of the Attenuator Setting Analog parameter. (0-Hidden	
			          1-Read-Only, 2-Updateable)."
			   ::= { gx2dm2000AnalogEntry 31}

		dm2000minValueRelAttenSetting   OBJECT-TYPE
			   SYNTAX           Float
			   ACCESS           read-only
			   STATUS           mandatory
			   DESCRIPTION
			   "The value of this object provides the minimum value
			    the Attenuator Setting Analog parameter can achive.
			   This value is a floating point number that is represented as an IEEE 32 bit number."
			   ::= { gx2dm2000AnalogEntry 32}

		dm2000maxValueRelAttenSetting   OBJECT-TYPE
			   SYNTAX           Float
			   ACCESS           read-only
			   STATUS           mandatory
			   DESCRIPTION
			   "The value of this object provides the maximum value
			    the Attenuator Setting Analog parameter can achive.
			   This value is a floating point number that is represented as an IEEE 32 bit number."
			   ::= { gx2dm2000AnalogEntry 33}

		dm2000alarmStateRelAttenSetting OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Attenuator Setting Analog parameter."
			   ::= { gx2dm2000AnalogEntry 34}
-- New Parameter

		dm2000labelOptPower             OBJECT-TYPE
			   SYNTAX           DisplayString (SIZE (0..80))
			   ACCESS           read-only
			   STATUS           optional
			   DESCRIPTION
			   "The value of this object provides the label of the
			    Optical Power Analog parameter."
			   ::= { gx2dm2000AnalogEntry 35}

		dm2000uomOptPower               OBJECT-TYPE
			   SYNTAX           DisplayString (SIZE (0..80))
			   ACCESS           read-only
			   STATUS           optional
			   DESCRIPTION
			   "The value of this object provides the Unit of Measure of the
			    Optical Power Analog parameter."
			   ::= { gx2dm2000AnalogEntry 36}

		dm2000majorHighOptPower         OBJECT-TYPE
			   SYNTAX           Float 
			   ACCESS           read-only
			   STATUS           mandatory
			   DESCRIPTION
			   "The value of this object provides the Major High alarm value
			    of the Optical Power Analog parameter.
			   This value is a floating point number that is represented as an IEEE 32 bit number."
			   ::= { gx2dm2000AnalogEntry 37}


		dm2000majorLowOptPower          OBJECT-TYPE
			   SYNTAX           Float 
			   ACCESS           read-only
			   STATUS           mandatory
			   DESCRIPTION
			   "The value of this object provides the Major Low alarm value
			    of the Optical Power Analog parameter.
			   This value is a floating point number that is represented as an IEEE 32 bit number."
			   ::= { gx2dm2000AnalogEntry 38}

		dm2000minorHighOptPower         OBJECT-TYPE
			   SYNTAX           Float
			   ACCESS           read-only
			   STATUS           mandatory
			   DESCRIPTION
			   "The value of this object provides the Minor High alarm value
			    of the Optical Power Analog parameter.
			   This value is a floating point number that is represented as an IEEE 32 bit number."
			   ::= { gx2dm2000AnalogEntry 39}

		dm2000minorLowOptPower          OBJECT-TYPE
			   SYNTAX           Float 
			   ACCESS           read-only
			   STATUS           mandatory
			   DESCRIPTION
			   "The value of this object provides the Minor Low alarm value
			    of the Optical Power Analog parameter.
			   This value is a floating point number that is represented as an IEEE 32 bit number."
			   ::= { gx2dm2000AnalogEntry 40}

		dm2000currentValueOptPower      OBJECT-TYPE
			   SYNTAX           Float 
			   ACCESS           read-only
			   STATUS           mandatory
			   DESCRIPTION
			   "The value of this object provides the Current value
			    of the Optical Power Analog parameter.
			   This value is a floating point number that is represented as an IEEE 32 bit number."
			   ::= { gx2dm2000AnalogEntry 41}

		dm2000stateFlagOptPower         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2dm2000AnalogEntry 42}

		dm2000minValueOptPower          OBJECT-TYPE
			   SYNTAX           Float
			   ACCESS           read-only
			   STATUS           mandatory
			   DESCRIPTION
			   "The value of this object provides the minimum value
			    the Optical Power Analog parameter can achive.
			   This value is a floating point number that is represented as an IEEE 32 bit number."
			   ::= { gx2dm2000AnalogEntry 43}

		dm2000maxValueOptPower          OBJECT-TYPE
			   SYNTAX           Float
			   ACCESS           read-only
			   STATUS           mandatory
			   DESCRIPTION
			   "The value of this object provides the maximum value
			    the Optical Power Analog parameter can achive.
			   This value is a floating point number that is represented as an IEEE 32 bit number."
			   ::= { gx2dm2000AnalogEntry 44}

		dm2000alarmStateOptPower        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2dm2000AnalogEntry 45}
-- New Parameter

		dm2000labelLaserBias            OBJECT-TYPE
			   SYNTAX           DisplayString (SIZE (0..80))
			   ACCESS           read-only
			   STATUS           optional
			   DESCRIPTION
			   "The value of this object provides the label of the
			    Laser Bias Current Analog parameter."
			   ::= { gx2dm2000AnalogEntry 46}

		dm2000uomLaserBias              OBJECT-TYPE
			   SYNTAX           DisplayString (SIZE (0..80))
			   ACCESS           read-only
			   STATUS           optional
			   DESCRIPTION
			   "The value of this object provides the Unit of Measure of the
			    Laser Bias Analog parameter."
			   ::= { gx2dm2000AnalogEntry 47}

		dm2000majorHighLaserBias        OBJECT-TYPE
			   SYNTAX           Float 
			   ACCESS           read-only
			   STATUS           mandatory
			   DESCRIPTION
			   "The value of this object provides the Major High alarm value
			    of the Laser Bias Analog parameter.
			   This value is a floating point number that is represented as an IEEE 32 bit number."
			   ::= { gx2dm2000AnalogEntry 48}


		dm2000majorLowLaserBias         OBJECT-TYPE
			   SYNTAX           Float 
			   ACCESS           read-only
			   STATUS           mandatory
			   DESCRIPTION
			   "The value of this object provides the Major Low alarm value
			    of the Laser Bias Analog parameter.
			   This value is a floating point number that is represented as an IEEE 32 bit number."
			   ::= { gx2dm2000AnalogEntry 49}

		dm2000minorHighLaserBias        OBJECT-TYPE
			   SYNTAX           Float
			   ACCESS           read-only
			   STATUS           mandatory
			   DESCRIPTION
			   "The value of this object provides the Minor High alarm value
			    of the Laser Bias Analog parameter.
			   This value is a floating point number that is represented as an IEEE 32 bit number."
			   ::= { gx2dm2000AnalogEntry 50}

		dm2000minorLowLaserBias         OBJECT-TYPE
			   SYNTAX           Float 
			   ACCESS           read-only
			   STATUS           mandatory
			   DESCRIPTION
			   "The value of this object provides the Minor Low alarm value
			    of the Laser Bias Analog parameter.
			   This value is a floating point number that is represented as an IEEE 32 bit number."
			   ::= { gx2dm2000AnalogEntry 51}

		dm2000currentValueLaserBias     OBJECT-TYPE
			   SYNTAX           Float 
			   ACCESS           read-only
			   STATUS           mandatory
			   DESCRIPTION
			   "The value of this object provides the Current value
			    of the Laser Bias Analog parameter.
			   This value is a floating point number that is represented as an IEEE 32 bit number."
			   ::= { gx2dm2000AnalogEntry 52}

		dm2000stateFlagLaserBias        OBJECT-TYPE
			   SYNTAX           INTEGER
								{
								hidden(1),
								read-only(2),
								updateable(3)
								}
			   ACCESS           read-only
			   STATUS           mandatory
			   DESCRIPTION
			   "The value of this object provides the state
			    of the Laser Bias Analog parameter. (0-Hidden	
			          1-Read-Only, 2-Updateable)."
			   ::= { gx2dm2000AnalogEntry 53}

		dm2000minValueLaserBias         OBJECT-TYPE
			   SYNTAX           Float
			   ACCESS           read-only
			   STATUS           mandatory
			   DESCRIPTION
			   "The value of this object provides the minimum value
			    the Laser Bias Analog parameter can achive.
			   This value is a floating point number that is represented as an IEEE 32 bit number."
			   ::= { gx2dm2000AnalogEntry 54}

		dm2000maxValueLaserBias         OBJECT-TYPE
			   SYNTAX           Float
			   ACCESS           read-only
			   STATUS           mandatory
			   DESCRIPTION
			   "The value of this object provides the maximum value
			    the Laser Bias Analog parameter can achive.
   			   This value is a floating point number that is represented as an IEEE 32 bit number."
			   ::= { gx2dm2000AnalogEntry 55}

		dm2000alarmStateLaserBias       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Analog parameter."
			   ::= { gx2dm2000AnalogEntry 56}
-- New Parameter

		dm2000labelTecCurrent           OBJECT-TYPE
			   SYNTAX           DisplayString (SIZE (0..80))
			   ACCESS           read-only
			   STATUS           optional
			   DESCRIPTION
			   "The value of this object provides the label of the
			    TEC Current Analog parameter."
			   ::= { gx2dm2000AnalogEntry 57}

		dm2000uomTecCurrent             OBJECT-TYPE
			   SYNTAX           DisplayString (SIZE (0..80))
			   ACCESS           read-only
			   STATUS           optional
			   DESCRIPTION
			   "The value of this object provides the Unit of Measure of the
			    TEC Current Analog parameter.."
			   ::= { gx2dm2000AnalogEntry 58}

		dm2000majorHighTecCurrent       OBJECT-TYPE
			   SYNTAX           Float 
			   ACCESS           read-only
			   STATUS           mandatory
			   DESCRIPTION
			   "The value of this object provides the Major High alarm value
			    of the TEC Current Analog parameter.
			   This value is a floating point number that is represented as an IEEE 32 bit number."
			   ::= { gx2dm2000AnalogEntry 59}


		dm2000majorLowTecCurrent        OBJECT-TYPE
			   SYNTAX           Float 
			   ACCESS           read-only
			   STATUS           mandatory
			   DESCRIPTION
			   "The value of this object provides the Major Low alarm value
			    of the TEC Current Analog parameter.
			   This value is a floating point number that is represented as an IEEE 32 bit number."
			   ::= { gx2dm2000AnalogEntry 60}

		dm2000minorHighTecCurrent       OBJECT-TYPE
			   SYNTAX           Float
			   ACCESS           read-only
			   STATUS           mandatory
			   DESCRIPTION
			   "The value of this object provides the Minor High alarm value
			    of the TEC Current Analog parameter.
			   This value is a floating point number that is represented as an IEEE 32 bit number."
			   ::= { gx2dm2000AnalogEntry 61}

		dm2000minorLowTecCurrent        OBJECT-TYPE
			   SYNTAX           Float 
			   ACCESS           read-only
			   STATUS           mandatory
			   DESCRIPTION
			   "The value of this object provides the Minor Low alarm value
			    of the TEC Current Analog parameter.
			   This value is a floating point number that is represented as an IEEE 32 bit number."
			   ::= { gx2dm2000AnalogEntry 62}

		dm2000currentValueTecCurrent    OBJECT-TYPE
			   SYNTAX           Float 
			   ACCESS           read-only
			   STATUS           mandatory
			   DESCRIPTION
			   "The value of this object provides the Current value
			    of the TEC Current Analog parameter.
			   This value is a floating point number that is represented as an IEEE 32 bit number."
			   ::= { gx2dm2000AnalogEntry 63}

		dm2000stateFlagTecCurrent       OBJECT-TYPE
			   SYNTAX           INTEGER
								{
								hidden(1),
								read-only(2),
								updateable(3)
								}
			   ACCESS           read-only
			   STATUS           mandatory
			   DESCRIPTION
			   "The value of this object provides the state
			    of the TEC Current Analog parameter. (0-Hidden	
			          1-Read-Only, 2-Updateable)."
			   ::= { gx2dm2000AnalogEntry 64}

		dm2000minValueTecCurrent        OBJECT-TYPE
			   SYNTAX           Float
			   ACCESS           read-only
			   STATUS           mandatory
			   DESCRIPTION
			   "The value of this object provides the minimum value
			    the TEC Current Analog parameter can achive.
	   		   This value is a floating point number that is represented as an IEEE 32 bit number."
			   ::= { gx2dm2000AnalogEntry 65}

		dm2000maxValueTecCurrent        OBJECT-TYPE
			   SYNTAX           Float
			   ACCESS           read-only
			   STATUS           mandatory
			   DESCRIPTION
			   "The value of this object provides the maximum value
			    the TEC Current Analog parameter can achive.
			   This value is a floating point number that is represented as an IEEE 32 bit number."
			   ::= { gx2dm2000AnalogEntry 66}

		dm2000alarmStateTecCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Current Analog parameter."
			   ::= { gx2dm2000AnalogEntry 67}
-- New Parameter

		dm2000labelLaserTemp            OBJECT-TYPE
			   SYNTAX           DisplayString (SIZE (0..80))
			   ACCESS           read-only
			   STATUS           optional
			   DESCRIPTION
			   "The value of this object provides the label of the
			    Laser Temperature Analog parameter."
			   ::= { gx2dm2000AnalogEntry 68}

		dm2000uomLaserTemp              OBJECT-TYPE
			   SYNTAX           DisplayString (SIZE (0..80))
			   ACCESS           read-only
			   STATUS           optional
			   DESCRIPTION
			   "The value of this object provides the Unit of Measure of the
			    Laser Temperature Analog parameter."
			   ::= { gx2dm2000AnalogEntry 69}

		dm2000majorHighLaserTemp        OBJECT-TYPE
			   SYNTAX           Float 
			   ACCESS           read-only
			   STATUS           mandatory
			   DESCRIPTION
			   "The value of this object provides the Major High alarm value
			    of the Laser Temperature Analog parameter.
			   This value is a floating point number that is represented as an IEEE 32 bit number."
			   ::= { gx2dm2000AnalogEntry 70}


		dm2000majorLowLaserTemp         OBJECT-TYPE
			   SYNTAX           Float 
			   ACCESS           read-only
			   STATUS           mandatory
			   DESCRIPTION
			   "The value of this object provides the Major Low alarm value
			    of the Laser Temperature Analog parameter.
			   This value is a floating point number that is represented as an IEEE 32 bit number."
			   ::= { gx2dm2000AnalogEntry 71}

		dm2000minorHighLaserTemp        OBJECT-TYPE
			   SYNTAX           Float
			   ACCESS           read-only
			   STATUS           mandatory
			   DESCRIPTION
			   "The value of this object provides the Minor High alarm value
			    of the Laser Temperature Analog parameter.
			   This value is a floating point number that is represented as an IEEE 32 bit number."
			   ::= { gx2dm2000AnalogEntry 72}

		dm2000minorLowLaserTemp         OBJECT-TYPE
			   SYNTAX           Float 
			   ACCESS           read-only
			   STATUS           mandatory
			   DESCRIPTION
			   "The value of this object provides the Minor Low alarm value
			    of the Laser Temperature Analog parameter.
			   This value is a floating point number that is represented as an IEEE 32 bit number."
			   ::= { gx2dm2000AnalogEntry 73}

		dm2000currentValueLaserTemp     OBJECT-TYPE
			   SYNTAX           Float 
			   ACCESS           read-only
			   STATUS           mandatory
			   DESCRIPTION
			   "The value of this object provides the Current value
			    of the Laser Temperature Analog parameter.
			   This value is a floating point number that is represented as an IEEE 32 bit number."
			   ::= { gx2dm2000AnalogEntry 74}

		dm2000stateFlagLaserTemp        OBJECT-TYPE
			   SYNTAX           INTEGER
								{
								hidden(1),
								read-only(2),
								updateable(3)
								}
			   ACCESS           read-only
			   STATUS           mandatory
			   DESCRIPTION
			   "The value of this object provides the state
			    of the Laser Temperature Analog parameter. (0-Hidden	
			          1-Read-Only, 2-Updateable)."
			   ::= { gx2dm2000AnalogEntry 75}

		dm2000minValueLaserTemp         OBJECT-TYPE
			   SYNTAX           Float
			   ACCESS           read-only
			   STATUS           mandatory
			   DESCRIPTION
			   "The value of this object provides the minimum value
			    the Laser Temperature Analog parameter can achive.
			   This value is a floating point number that is represented as an IEEE 32 bit number."
			   ::= { gx2dm2000AnalogEntry 76}

		dm2000maxValueLaserTemp         OBJECT-TYPE
			   SYNTAX           Float
			   ACCESS           read-only
			   STATUS           mandatory
			   DESCRIPTION
			   "The value of this object provides the maximum value
			    the Laser Temperature Analog parameter can achive.
			   This value is a floating point number that is represented as an IEEE 32 bit number."
			   ::= { gx2dm2000AnalogEntry 77}

		dm2000alarmStateLaserTemp       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Temperature Analog parameter."
			   ::= { gx2dm2000AnalogEntry 78}

-- New Parameter

		dm2000labelModuleTemp              OBJECT-TYPE
			   SYNTAX           DisplayString (SIZE (0..80))
			   ACCESS           read-only
			   STATUS           optional
			   DESCRIPTION
			   "The value of this object provides the label of the
			    Module Temperature Analog parameter."
			   ::= { gx2dm2000AnalogEntry 79}

		dm2000uomModuleTemp                OBJECT-TYPE
			   SYNTAX           DisplayString (SIZE (0..80))
			   ACCESS           read-only
			   STATUS           optional
			   DESCRIPTION
			   "The value of this object provides the Unit of Measure of the
			    Module Temperature Analog parameter."
			   ::= { gx2dm2000AnalogEntry 80}

		dm2000majorHighModuleTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2dm2000AnalogEntry 81}


		dm2000majorLowModuleTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2dm2000AnalogEntry 82}

		dm2000minorHighModuleTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2dm2000AnalogEntry 83}

		dm2000minorLowModuleTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2dm2000AnalogEntry 84}

		dm2000currentValueModuleTemp       OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2dm2000AnalogEntry 85}

		dm2000stateFlagModuleTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2dm2000AnalogEntry 86}

		dm2000minValueModuleTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2dm2000AnalogEntry 87}

		dm2000maxValueModuleTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2dm2000AnalogEntry 88}

		dm2000alarmStateModuleTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2dm2000AnalogEntry 89}
-- New Parameter

		dm2000labelFanCurrent           OBJECT-TYPE
			   SYNTAX           DisplayString (SIZE (0..80))
			   ACCESS           read-only
			   STATUS           optional
			   DESCRIPTION
			   "The value of this object provides the label of the
			    Fan Current Analog parameter."
			   ::= { gx2dm2000AnalogEntry 90}

		dm2000uomFanCurrent             OBJECT-TYPE
			   SYNTAX           DisplayString (SIZE (0..80))
			   ACCESS           read-only
			   STATUS           optional
			   DESCRIPTION
			   "The value of this object provides the Unit of Measure of the
			    Fan Current Analog parameter."
			   ::= { gx2dm2000AnalogEntry 91}

		dm2000majorHighFanCurrent       OBJECT-TYPE
			   SYNTAX           Float 
			   ACCESS           read-only
			   STATUS           mandatory
			   DESCRIPTION
			   "The value of this object provides the Major High alarm value
			    of the Fan Current Analog parameter.
			   This value is a floating point number that is represented as an IEEE 32 bit number."
			   ::= { gx2dm2000AnalogEntry 92}


		dm2000majorLowFanCurrent        OBJECT-TYPE
			   SYNTAX           Float 
			   ACCESS           read-only
			   STATUS           mandatory
			   DESCRIPTION
			   "The value of this object provides the Major Low alarm value
			    of the Fan Current Analog parameter.
			   This value is a floating point number that is represented as an IEEE 32 bit number."
			   ::= { gx2dm2000AnalogEntry 93}

		dm2000minorHighFanCurrent       OBJECT-TYPE
			   SYNTAX           Float
			   ACCESS           read-only
			   STATUS           mandatory
			   DESCRIPTION
			   "The value of this object provides the Minor High alarm value
			    of the Fan Current Analog parameter.
			   This value is a floating point number that is represented as an IEEE 32 bit number."
			   ::= { gx2dm2000AnalogEntry 94}

		dm2000minorLowFanCurrent        OBJECT-TYPE
			   SYNTAX           Float 
			   ACCESS           read-only
			   STATUS           mandatory
			   DESCRIPTION
			   "The value of this object provides the Minor Low alarm value
			    of the Fan Current Analog parameter.
			   This value is a floating point number that is represented as an IEEE 32 bit number."
			   ::= { gx2dm2000AnalogEntry 95}

		dm2000currentValueFanCurrent    OBJECT-TYPE
			   SYNTAX           Float 
			   ACCESS           read-only
			   STATUS           mandatory
			   DESCRIPTION
			   "The value of this object provides the Current value
			    of the Fan Current Analog parameter.
			   This value is a floating point number that is represented as an IEEE 32 bit number."
			   ::= { gx2dm2000AnalogEntry 96}

		dm2000stateFlagFanCurrent       OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2dm2000AnalogEntry 97}

		dm2000minValueFanCurrent        OBJECT-TYPE
			   SYNTAX           Float
			   ACCESS           read-only
			   STATUS           mandatory
			   DESCRIPTION
			   "The value of this object provides the minimum value
			    the Fan Current Analog parameter can achive.
			   This value is a floating point number that is represented as an IEEE 32 bit number."
			   ::= { gx2dm2000AnalogEntry 98}

		dm2000maxValueFanCurrent        OBJECT-TYPE
			   SYNTAX           Float
			   ACCESS           read-only
			   STATUS           mandatory
			   DESCRIPTION
			   "The value of this object provides the maximum value
			    the Fan Current Analog parameter can achive.
			   This value is a floating point number that is represented as an IEEE 32 bit number."
			   ::= { gx2dm2000AnalogEntry 99}

		dm2000alarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2dm2000AnalogEntry 100}
-- New Parameter

		dm2000label12Volt               OBJECT-TYPE
			   SYNTAX           DisplayString (SIZE (0..80))
			   ACCESS           read-only
			   STATUS           optional
			   DESCRIPTION
			   "The value of this object provides the label of the
			    12v Current Analog parameter."
			   ::= { gx2dm2000AnalogEntry 101}

		dm2000uom12Volt                 OBJECT-TYPE
			   SYNTAX           DisplayString (SIZE (0..80))
			   ACCESS           read-only
			   STATUS           optional
			   DESCRIPTION
			   "The value of this object provides the Unit of Measure of the
			    12v Current Analog parameter."
			   ::= { gx2dm2000AnalogEntry 102}

		dm2000majorHigh12Volt           OBJECT-TYPE
			   SYNTAX           Float 
			   ACCESS           read-only
			   STATUS           mandatory
			   DESCRIPTION
			   "The value of this object provides the Major High alarm value
			    of the 12v Current Analog parameter.
			   This value is a floating point number that is represented as an IEEE 32 bit number."
			   ::= { gx2dm2000AnalogEntry 103}


		dm2000majorLow12Volt            OBJECT-TYPE
			   SYNTAX           Float 
			   ACCESS           read-only
			   STATUS           mandatory
			   DESCRIPTION
			   "The value of this object provides the Major Low alarm value
			    of the 12v Current Analog parameter.
			   This value is a floating point number that is represented as an IEEE 32 bit number."
			   ::= { gx2dm2000AnalogEntry 104}

		dm2000minorHigh12Volt           OBJECT-TYPE
			   SYNTAX           Float
			   ACCESS           read-only
			   STATUS           mandatory
			   DESCRIPTION
			   "The value of this object provides the Minor High alarm value
			    of the 12v Current Analog parameter.
			   This value is a floating point number that is represented as an IEEE 32 bit number."
			   ::= { gx2dm2000AnalogEntry 105}

		dm2000minorLow12Volt            OBJECT-TYPE
			   SYNTAX           Float 
			   ACCESS           read-only
			   STATUS           mandatory
			   DESCRIPTION
			   "The value of this object provides the Minor Low alarm value
			    of the 12v Current Analog parameter.
			   This value is a floating point number that is represented as an IEEE 32 bit number."
			   ::= { gx2dm2000AnalogEntry 106}

		dm2000currentValue12Volt        OBJECT-TYPE
			   SYNTAX           Float 
			   ACCESS           read-only
			   STATUS           mandatory
			   DESCRIPTION
			   "The value of this object provides the Current value
			    of the 12v Current Analog parameter.
			   This value is a floating point number that is represented as an IEEE 32 bit number."
			   ::= { gx2dm2000AnalogEntry 107}

		dm2000stateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2dm2000AnalogEntry 108}

		dm2000minValue12Volt            OBJECT-TYPE
			   SYNTAX           Float
			   ACCESS           read-only
			   STATUS           mandatory
			   DESCRIPTION
			   "The value of this object provides the minimum value
			    the 12v Current Analog parameter can achive.
			   This value is a floating point number that is represented as an IEEE 32 bit number."
			   ::= { gx2dm2000AnalogEntry 109}

		dm2000maxValue12Volt            OBJECT-TYPE
			   SYNTAX           Float
			   ACCESS           read-only
			   STATUS           mandatory
			   DESCRIPTION
			   "The value of this object provides the maximum value
			    the 12v Current Analog parameter can achive.
			   This value is a floating point number that is represented as an IEEE 32 bit number."
			   ::= { gx2dm2000AnalogEntry 110}

		dm2000alarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2dm2000AnalogEntry 111}

-- ************************ Digital parameters **********************************
		gx2dm2000DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2dm2000DigitalEntry 1}

-- New parameter
		dm2000labelRfInput                	OBJECT-TYPE
			   SYNTAX       		DisplayString (SIZE (0..80))         
			   ACCESS           	read-only
			   STATUS           	optional
			   DESCRIPTION
			   "The value of this object provides the label of the
			    RF Input Control  Digital parameter."
			   ::= { gx2dm2000DigitalEntry 2}

		dm2000enumRfInput               		OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2dm2000DigitalEntry 3}

		dm2000valueRfInput                	OBJECT-TYPE
			   SYNTAX       		INTEGER
					    		{
							off(1),
							on(2)
					    		}
			   ACCESS           	read-write
			   STATUS           	mandatory
			   DESCRIPTION
			   "The value of this object is the current value of the parameter."
			   ::= { gx2dm2000DigitalEntry 4}

		dm2000stateflagRfInput              OBJECT-TYPE
			   SYNTAX       		INTEGER
								{
								hidden(1),
								read-only(2),
								updateable(3)
								}
			   ACCESS           	read-only
			   STATUS           	mandatory
			   DESCRIPTION
			   "The value of this object provides the state
			    of the RF Input Control  Digital parameter. (0-Hidden	
			          1-Read-Only, 2-Updateable)."
			   ::= { gx2dm2000DigitalEntry 5}

-- New parameter
		dm2000labelOptOutput                OBJECT-TYPE
			   SYNTAX       		DisplayString (SIZE (0..80))         
			   ACCESS           	read-only
			   STATUS           	optional
			   DESCRIPTION
			   "The value of this object provides the label of the
			    Optical Output Control  Digital parameter."
			   ::= { gx2dm2000DigitalEntry 6}

		dm2000enumOptOutput               	      OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2dm2000DigitalEntry 7}

		dm2000valueOptOutput                OBJECT-TYPE
			   SYNTAX       		INTEGER
					    		{
							off(1),
							on(2)
					    		}
			   ACCESS           	read-write
			   STATUS           	mandatory
			   DESCRIPTION
			   "The value of this object is the current value of the parameter."
			   ::= { gx2dm2000DigitalEntry 8}

		dm2000stateflagOptOutput            OBJECT-TYPE
			   SYNTAX      		INTEGER
								{
								hidden(1),
								read-only(2),
								updateable(3)
								}
			   ACCESS           	read-only
			   STATUS           	mandatory
			   DESCRIPTION
			   "The value of this object provides the dm2000state
			    of the the parameter. (0-Hidden 1-Read-Only, 2-Updateable)."
			   ::= { gx2dm2000DigitalEntry 9}
-- New parameter
		dm2000labelLaserMode                OBJECT-TYPE
			   SYNTAX         	DisplayString (SIZE (0..80))         
			   ACCESS           	read-only
			   STATUS           	optional
			   DESCRIPTION
			   "The value of this object provides the label of the
			    Laser Mode  Digital parameter."
			   ::= { gx2dm2000DigitalEntry 10}

		dm2000enumLaserMode               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2dm2000DigitalEntry 11}

		dm2000valueLaserMode                OBJECT-TYPE
			   SYNTAX       		INTEGER
					    		{
							preset(1),
							set(2),
							setEquate(3),
							manual(4),
							manualEquate(5)
					    		}
			   ACCESS           	read-write
			   STATUS           	mandatory
			   DESCRIPTION
			   "The value of this object is the current value of the parameter."
			   ::= { gx2dm2000DigitalEntry 12}

		dm2000stateflagLaserMode            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000DigitalEntry 13}
-- New parameter
		dm2000labelLaserSecMode             OBJECT-TYPE
			   SYNTAX         	DisplayString (SIZE (0..80))         
			   ACCESS           	read-only
			   STATUS           	optional
			   DESCRIPTION
			   "The value of this object provides the label of the
			    Laser Secondary Mode Digital parameter."
			   ::= { gx2dm2000DigitalEntry 14}

		dm2000enumLaserSecMode               	OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2dm2000DigitalEntry 15}

		dm2000valueLaserSecMode           	OBJECT-TYPE
			   SYNTAX       		INTEGER
					    		{
							cw(1),
							video(2)
					    		}
			   ACCESS           	read-write
			   STATUS           	mandatory
			   DESCRIPTION
			   "The value of this object is the current value of the parameter."
			   ::= { gx2dm2000DigitalEntry 16}

		dm2000stateflagLaserSecMode         OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000DigitalEntry 17}

-- New parameter
		dm2000labelVideoOffset            	OBJECT-TYPE
			   SYNTAX       	      DisplayString (SIZE (0..80))         
			   ACCESS           	read-only
			   STATUS           	optional
			   DESCRIPTION
			   "The value of this object provides the label of the
			    Video Offset  Digital parameter."
			   ::= { gx2dm2000DigitalEntry 18}

		dm2000enumVideoOffset               	OBJECT-TYPE
			   SYNTAX       	      DisplayString (SIZE (0..80))         
			   ACCESS           	read-only
			   STATUS           	optional
			   DESCRIPTION
			   "The value of this object represents the Enumeration values
			    possible for the Digital parameter. Each Enumerated values is
			    separated by a common. The first value has a enumerated value of 1.."
			   ::= { gx2dm2000DigitalEntry 19}

		dm2000valueVideoOffset              OBJECT-TYPE
			   SYNTAX       		INTEGER
					    		{
							minus2dB(1),
							minus3dB(2),
 							minus4dB(3),
							minus5dB(4)
					    		}
			   ACCESS           	read-write
			   STATUS           	mandatory
			   DESCRIPTION
			   "The value of this object is the current value of the parameter."
			   ::= { gx2dm2000DigitalEntry 20}

		dm2000stateflagVideoOffset        	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000DigitalEntry 21}        
			   
-- New parameter        

		dm2000labelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2dm2000DigitalEntry 22}

		dm2000enumFactoryDefault               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2dm2000DigitalEntry 23}


		dm2000valueFactoryDefault         	OBJECT-TYPE
			   SYNTAX       		INTEGER
					    		{
							off(1),
							on(2)
					    		}
			   ACCESS           	read-write
			   STATUS           	mandatory
			   DESCRIPTION
			   "The value of this object is the current value of the parameter."
			   ::= { gx2dm2000DigitalEntry 24}

		dm2000stateflagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000DigitalEntry 25}

-- New Parameter  
 
		dm2000labelFiberLength           OBJECT-TYPE
			   SYNTAX       		DisplayString (SIZE (0..80))         
			   ACCESS           	read-only
			   STATUS           	optional
			   DESCRIPTION
			    "The value of this object provides the label for the
			    Fiber Length Digital parameter ."
			   ::= { gx2dm2000DigitalEntry 26}

		dm2000enumFiberLength          OBJECT-TYPE
			   SYNTAX       		DisplayString (SIZE (0..80))         
			   ACCESS           	read-only
			   STATUS           	optional
			   DESCRIPTION
			    "The value of this object represents the Enumeration values
			    possible for the Digital parameter. 
				The range for fiber length selection is from 0 to 60km,
				where 0km is represented with a 1, and 60 with a 61."
			   ::= { gx2dm2000DigitalEntry 27}

		dm2000valueFiberLength         OBJECT-TYPE
			   SYNTAX       		INTEGER

			   ACCESS           	read-write
			   STATUS           	mandatory
			   DESCRIPTION
			   "The value of this object is the current value of the parameter.
			   It is used to set fiber length. The value range for this object is: 1 to 61.
			   Where 1 = 0Km and 61 = 60Km"
			   ::= { gx2dm2000DigitalEntry 28}
 
		dm2000stateflagFiberLength     OBJECT-TYPE
			   SYNTAX       		INTEGER
									{
										hidden(1),
										read-only(2),
										updateable(3)
									}
			   ACCESS           	read-only
			   STATUS           	mandatory
			   DESCRIPTION
			   "The value of this object provides the state
			    of the the parameter. (0-Hidden 1-Read-Only, 2-Updateable)."
			   ::= { gx2dm2000DigitalEntry 29}

 

-- THE OBJECTS FOR "WAVELENGTH OFFSET" ARE ONLY USED FOR CERTAIN UNITS IN THE DM2000 DEVICE FAMILY

		dm2000labelWavelengthOffset           OBJECT-TYPE
			   SYNTAX       		DisplayString (SIZE (0..80))         
			   ACCESS           	read-only
			   STATUS           	optional
			   DESCRIPTION
			   "The value of this object provides the label for the
			    Wavelength Offset Digital parameter ."
			   ::= { gx2dm2000DigitalEntry 30}

		dm2000enumWavelengthOffset          OBJECT-TYPE
			   SYNTAX       		DisplayString (SIZE (0..80))         
			   ACCESS           	read-only
			   STATUS           	optional
			   DESCRIPTION
			   "The value of this object represents the Enumeration values
			    possible for this Digital parameter. "
			   ::= { gx2dm2000DigitalEntry 31}

		dm2000valueWavelengthOffset         OBJECT-TYPE
			   SYNTAX       		INTEGER
			   {
							narrowcast(1),
							fullSpectrum(2)
					    		}
			   ACCESS           	read-write
			   STATUS           	mandatory
			   DESCRIPTION
			   "The value of this object is the current value of the parameter.
			   It is used to select a Narrowcast or Full Spectrum application."
			   ::= { gx2dm2000DigitalEntry 32}


		dm2000stateflagWavelengthOffset     OBJECT-TYPE
			   SYNTAX       		INTEGER
									{
										hidden(1),
										read-only(2),
										updateable(3)
									}
			   ACCESS           	read-only
			   STATUS           	mandatory
			   DESCRIPTION
			   "The value of this object provides the state
			    of the the Wavelength Offset parameter. (0-Hidden 1-Read-Only, 2-Updateable)."
			   ::= { gx2dm2000DigitalEntry 33}

 
		--*********** STATUS *****************
		gx2dm2000StatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2dm2000StatusEntry 1}

--New Parameter
		dm2000labelBoot               	OBJECT-TYPE
			   SYNTAX       		DisplayString (SIZE (0..80))         
			   ACCESS           	read-only
			   STATUS           	optional
			   DESCRIPTION
			   "The value of this object provides the label of the
			    Boot Status  Status parameter."
			   ::= { gx2dm2000StatusEntry 2}

		dm2000valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 3}

		dm2000stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  4}



--New Parameter
		dm2000labelFlash               	OBJECT-TYPE
			   SYNTAX       		DisplayString (SIZE (0..80))         
			   ACCESS           	read-only
			   STATUS           	optional
			   DESCRIPTION
			   "The value of this object provides the label of the
			    Flash Status  Status parameter."
			   ::= { gx2dm2000StatusEntry 5}

		dm2000valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 6}

		dm2000stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  7}

--New Parameter
		dm2000labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2dm2000StatusEntry 8}

		dm2000valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 9}

		dm2000stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  10}


--New Parameter
		dm2000labelLaserDataCRC             OBJECT-TYPE
			   SYNTAX       		DisplayString (SIZE (0..80))         
			   ACCESS           	read-only
			   STATUS           	optional
			   DESCRIPTION
			   "The value of this object provides the label of the
			    Laser Data CRC Status parameter."
			   ::= { gx2dm2000StatusEntry 11}

		dm2000valueLaserDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 12}

		dm2000stateflagLaserDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  13}

--New Parameter
		dm2000labelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2dm2000StatusEntry 14}

		dm2000valueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 15}

		dm2000stateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  16}

--New Parameter
		dm2000labelHWStatus              OBJECT-TYPE
			   SYNTAX       		DisplayString (SIZE (0..80))         
			   ACCESS           	read-only
			   STATUS           	optional
			   DESCRIPTION
			   "The value of this object provides the label of the
			    Laser Drive Level Status parameter."
			   ::= { gx2dm2000StatusEntry 17}

		dm2000valueHWStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 18}

		dm2000stateflagHWStatus     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  19}

--New Parameter
		dm2000labelRFInputStatus              OBJECT-TYPE
			   SYNTAX       		DisplayString (SIZE (0..80))         
			   ACCESS           	read-only
			   STATUS           	optional
			   DESCRIPTION
			   "The value of this object provides the label of the
			    RF Input Status parameter."
			   ::= { gx2dm2000StatusEntry 20}

		dm2000valueRFInputStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2dm2000StatusEntry 21}

		dm2000stateflagRFInputStatus     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2dm2000StatusEntry  22}



            -- ************ FACTORY DATA ****************
		gx2dm2000FactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2dm2000FactoryEntry 1}

		dm2000bootControlByteValue          	OBJECT-TYPE
			   SYNTAX       		INTEGER
			   ACCESS           	read-only
			   STATUS           	mandatory
			   DESCRIPTION
			   "The value of this object indicates which bank the firmware
			    is currently being boot from."
			   ::= { gx2dm2000FactoryEntry 2}

		dm2000bootStatusByteValue          	OBJECT-TYPE
			   SYNTAX       		INTEGER
			   ACCESS           	read-only
			   STATUS           	mandatory
			   DESCRIPTION
			   "This object indicates the status of the last boot"
			   ::= { gx2dm2000FactoryEntry 3}

		dm2000bank1CRCValue          		OBJECT-TYPE
			   SYNTAX       		INTEGER
			   ACCESS           	read-only
			   STATUS           	mandatory
			   DESCRIPTION
			   "This object provides the CRC code of bank 0."
			   ::= { gx2dm2000FactoryEntry 4}

		dm2000bank2CRCValue          		OBJECT-TYPE
			   SYNTAX       		INTEGER
			   ACCESS           	read-only
			   STATUS           	mandatory
			   DESCRIPTION
			   "This object provides the CRC code of bank 1."
			   ::= { gx2dm2000FactoryEntry 5}

		dm2000prgEEPROMByteValue          		OBJECT-TYPE
			   SYNTAX       		INTEGER
			   ACCESS           	read-only
			   STATUS           	mandatory
			   DESCRIPTION
			   "This object indicates if the EEPROM has been programmed"
			   ::= { gx2dm2000FactoryEntry 6}

		dm2000factoryCRCValue          		OBJECT-TYPE
			   SYNTAX       		INTEGER
			   ACCESS           	read-only
			   STATUS           	mandatory
			   DESCRIPTION
			   "This object provides the CRC code for the Factory data."
			   ::= { gx2dm2000FactoryEntry 7}

		dm2000calculateCRCValue          		OBJECT-TYPE
			   SYNTAX       		INTEGER
					    		{
							factory(1),
							laserData(2),
							alarm(3)
					    		}
			   ACCESS           	read-only
			   STATUS           	mandatory
			   DESCRIPTION
			   "This object indicates which of the Emnums will have the CRC calculated."
			   ::= { gx2dm2000FactoryEntry 8}

		dm2000hourMeterValue          		OBJECT-TYPE
			   SYNTAX       		INTEGER
			   ACCESS           	read-only
			   STATUS           	mandatory
			   DESCRIPTION
			   "This object provides the hour meter reading of the module."
			   ::= { gx2dm2000FactoryEntry 9}

		dm2000flashPrgCntAValue          		OBJECT-TYPE
			   SYNTAX       		INTEGER
			   ACCESS           	read-only
			   STATUS           	mandatory
			   DESCRIPTION
			   "This object provides the number of times Bank 1 flash has been 
                      programmed."
			   ::= { gx2dm2000FactoryEntry 10}

		dm2000flashPrgCntBValue          		OBJECT-TYPE
			   SYNTAX       		INTEGER
			   ACCESS           	read-only
			   STATUS           	mandatory
			   DESCRIPTION
			   "This object provides the number of times Bank 1 flash has been 
                      programmed."
			   ::= { gx2dm2000FactoryEntry 11}

		dm2000flashBankARevValue          		OBJECT-TYPE
			   SYNTAX       		DisplayString (SIZE (0..80))
			   ACCESS           	read-only
			   STATUS           	mandatory
			   DESCRIPTION
			   "This object provides the revision of flash bank 0."
			   ::= { gx2dm2000FactoryEntry 12}

		dm2000flashBankBRevValue          		OBJECT-TYPE
			   SYNTAX       		DisplayString (SIZE (0..80))
			   ACCESS           	read-only
			   STATUS           	mandatory
			   DESCRIPTION
			   "This object provides the revision of flash bank 1."
			   ::= { gx2dm2000FactoryEntry 13}


            -- ************ Hold Time DATA ****************
		gx2Dm2000HoldTimeTableIndex              OBJECT-TYPE
			   SYNTAX           INTEGER (1..4294967295)
			   ACCESS           read-only
			   STATUS           mandatory
			   DESCRIPTION
			   "The value of this object is the index of the data object."
			   ::= { gx2Dm2000HoldTimeEntry 1}

		gx2Dm2000HoldTimeSpecIndex              OBJECT-TYPE
			   SYNTAX           INTEGER (1..4294967295)
			   ACCESS           read-only
			   STATUS           mandatory
			   DESCRIPTION
			   "The value of this object identifies the index of the alarm object to be modified."
			   ::= { gx2Dm2000HoldTimeEntry 2}

		gx2Dm2000HoldTimeData          	OBJECT-TYPE
			   SYNTAX       		INTEGER
			   ACCESS           	read-write
			   STATUS           	mandatory
			   DESCRIPTION
			   "The value of this object provides access to the hold timers used 
			   to suppress nose on analog objects. This object is a 32 bit object. 
			   Validation data is entered into bytes zero and one of the object. 
			   Bytes three and four are used to entering the hold time for the 
			   specified alarm object. The Hold timer data ranges from 0 to 1300 seconds.
			   The index of this object corresponds to the alarm object to be modified. 
			   Alarm Hold timers correspond to the index of this object as follows:  
			   Index 1 = xxx, index 2 = xxxx, Index 3 = xxxx, 
			   The hold time is represented in seconds."
			   ::= { gx2Dm2000HoldTimeEntry 3}


-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                              Laser Module traps
-- **************************************************************************
   trapDM2000ConfigChangeInteger TRAP-TYPE
       ENTERPRISE gx2Dm2000
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapDM2000ConfigChangeDisplayString TRAP-TYPE
       ENTERPRISE gx2Dm2000
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapDM2000RFInputAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF input parameter 
	 goes out of range.
	 trapAdditionalInfoInteger variable contains current reading of 
	 the this parameter."
  ::= 3
  
  trapDM2000RFOverloadAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF overload parameter 
	 goes out of range.
	 trapAdditionalInfoInteger variable contains current reading of 
	 the this parameter."
  ::= 4

  trapDM2000RFOffsetAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF Offset parameter 
	 goes out of range.
	 trapAdditionalInfoInteger variable contains current reading of 
	 the this parameter."
  ::= 5

  trapDM2000OpticalPowerAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Optical Power parameter 
	 goes out of range.
	 trapAdditionalInfoInteger variable contains current reading of 
	 the this parameter."
  ::= 6

  trapDM2000LaserBiasAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Bias parameter goes out of range.
	 trapAdditionalInfoInteger variable contains current reading of 
	 the this parameter."
  ::= 7
     
  trapDM2000LaserTempAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Temperature parameter 
	 goes out of range.
	 trapAdditionalInfoInteger variable contains current reading of 
	 the this parameter."
  ::= 8

  trapDM2000TECCurrentAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules TEC Current parameter 
	 goes out of range.
	 trapAdditionalInfoInteger variable contains current reading of 
	 the this parameter."
  ::= 9

  trapDM2000FanCurrentAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Fan Current 
	 parameter goes out of range.
	 trapAdditionalInfoInteger variable contains current reading of 
	 the this parameter."
  ::= 10

  trapDM200012vAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules 12 Volt parameter goes out of range.
	 trapAdditionalInfoInteger variable contains current reading of 
	 the this parameter."
  ::= 11

  trapDM2000ModuleTempAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Module Temperature goes out of range."
  ::= 12

  trapDM2000FlashAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 13

  trapDM2000LaserBiasCntLoopAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error in its Laser Bias control loop
       operation."
  ::= 14

  trapDM2000BankBootAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 15

	trapDM2000LaserBiasCntLoopInitAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Bias Control loop init fails."
  ::= 16

	trapDM2000RFParamInitAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RF parameter Init fails."
  ::= 17

	trapDM2000TECParamInitAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Parameter Init fails."
  ::= 18

	trapDM2000AttnTableInitAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Attenuator Table Init fails."
  ::= 19

	trapDM2000PowerMeterTableInitAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Power Meter Table Init fails."
  ::= 20

	trapDM2000LaserDataCRCAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Data CRC is incorrect."
  ::= 21

	trapDM2000AlarmDataCRCAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 22

	trapDM2000FactoryDataCRCAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 23

	trapDM2000UserRFOffAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the the User RF is turned off."
  ::= 24

	trapDM2000UserOpticalOffAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User Optical Power is turned off."
  ::= 25

	trapDM2000ResetFactoryDefaultAlarm TRAP-TYPE
	ENTERPRISE gx2Dm2000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 26

  END
