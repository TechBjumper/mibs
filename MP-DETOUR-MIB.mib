-- ***************************************************************************
-- FileName    :mpDetourMib.my
-- Description :Detour Private MIB
-- Revision History     :
--   Ver.     mark   date      
--   01.01    @001   08/14/2001
-- ***************************************************************************

MP-DETOUR-MIB DEFINITIONS ::= BEGIN

   IMPORTS
      mgmt, NetworkAddress, IpAddress, Counter, Gauge, TimeTicks
      FROM RFC1155-SMI

      ifIndex
      FROM RFC1213-MIB

      OBJECT-TYPE
      FROM RFC-1212

      TRAP-TYPE
      FROM RFC-1215;

   DisplayString ::= OCTET STRING


-- The following definition is privately defined for IX5000 Private MIB

   org               OBJECT IDENTIFIER ::= { iso 3 }
   dod               OBJECT IDENTIFIER ::= { org 6 }
   internet          OBJECT IDENTIFIER ::= { dod 1 }
   private           OBJECT IDENTIFIER ::= { internet 4 }
   enterprises       OBJECT IDENTIFIER ::= { private 1 }
   nec               OBJECT IDENTIFIER ::= { enterprises 119}

   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }

   nec-mib           OBJECT IDENTIFIER ::= { nec 2 }
   necProductDepend  OBJECT IDENTIFIER ::= { nec-mib 3 }
   datax-mib         OBJECT IDENTIFIER ::= { necProductDepend 3 }
   mmpf-mib          OBJECT IDENTIFIER ::= { datax-mib 13 }

   mpDetour                 OBJECT IDENTIFIER ::= { mmpf-mib 130 }


-- Detour Private MIB


--
--
--

       mpDetourTable OBJECT-TYPE
               SYNTAX  SEQUENCE OF MpDetourEntry
               ACCESS  not-accessible
               STATUS  mandatory
               DESCRIPTION 
			"This is the table type object of Detour infomation" 
               ::= { mpDetour 1 }

       mpDetourEntry OBJECT-TYPE
               SYNTAX  MpDetourEntry
               ACCESS  not-accessible
               STATUS  mandatory
               DESCRIPTION 
			"This is the table entry of mpDetourTable."
               INDEX   { mpDetourID }
               ::= { mpDetourTable 1 }


       MpDetourEntry ::=
               SEQUENCE {
                   mpDetourID
                       INTEGER,
                   mpObservationIfindex
                       INTEGER,
                   mpObservationIfType
                       INTEGER,
                   mpObservationIfNumber
                       INTEGER,
                   mpDetourIfindex
                       INTEGER,
                   mpDetourIfType
                       INTEGER,
                   mpDetourIfNumber
                       INTEGER,
                   mpObservationAdminStatus
                       INTEGER,
                   mpObservationOperStatus
                       INTEGER,
                   mpDiscardIfindex
                       INTEGER, 
                   mpDiscardIfType
                       INTEGER,
                   mpDiscardIfNumber
                       INTEGER,
                   mpDetourAdminStatus
                       INTEGER,
                   mpDetourOperStatus
                       INTEGER,
                   mpDiscardAdminStatus
                       INTEGER,
                   mpDiscardOperStatus
                       INTEGER,
                   mpRouteStatus
                       INTEGER,
                   mpInhibitMode
                       INTEGER,
                   mpWatchMode
                       INTEGER 
               }

--Detour ID
mpDetourID OBJECT-TYPE
	SYNTAX	INTEGER
	ACCESS	read-only
	STATUS	mandatory
	DESCRIPTION
		"This object is ifIndex of observation route."
--
	::= { mpDetourEntry 1 }

--
mpObservationIfindex OBJECT-TYPE
	SYNTAX	INTEGER
	ACCESS	read-only
	STATUS	mandatory
	DESCRIPTION
		"This object is ifIndex of observation route."
	::= { mpDetourEntry 2 }

--
mpObservationIfType OBJECT-TYPE
	SYNTAX  INTEGER {
			atmpp(1),
			vlan(2),
			lis(3),
			outband(4),
			trunk(5),
			ppp(6),
			frpp(7),
			vlantrap(8),
			mplspp(9)
			}
	ACCESS  read-only
	STATUS  mandatory
	DESCRIPTION
		"This object is interface type of observation route."
	::= { mpDetourEntry 3 }

--
mpObservationIfNumber   OBJECT-TYPE
	SYNTAX  INTEGER
	ACCESS  read-only
	STATUS  mandatory
	DESCRIPTION
		"This object is interface number of observation route."
	::= { mpDetourEntry 4 }

--
mpDetourIfindex OBJECT-TYPE
	SYNTAX	INTEGER
	ACCESS	read-only
	STATUS	mandatory
	DESCRIPTION
		"This object is ifIndex of detour route."
	::= { mpDetourEntry 5 }

--
mpDetourIfType OBJECT-TYPE
	SYNTAX  INTEGER {
			atmpp(1),
			vlan(2),
			lis(3),
			outband(4),
			trunk(5),
			ppp(6),
			frpp(7),
			vlantrap(8),
			mplspp(9)
			}
	ACCESS  read-only
	STATUS  mandatory
	DESCRIPTION
		"This object is interface type of detour route."
	::= { mpDetourEntry 6 }

--
mpDetourIfNumber   OBJECT-TYPE
	SYNTAX  INTEGER
	ACCESS  read-only
	STATUS  mandatory
	DESCRIPTION
		"This object is interface number of detour route."
	::= { mpDetourEntry 7 }

--
mpObservationAdminStatus  OBJECT-TYPE
	SYNTAX  INTEGER {
			up(1),
			down(2)
			}
	ACCESS	read-write
	STATUS  mandatory
	DESCRIPTION
		"The value of this object identifies the desired
                 administer status of this observation route."
	::= { mpDetourEntry 8 }

--
mpObservationOperStatus  OBJECT-TYPE
	SYNTAX  INTEGER {
			up(1),
			down(2)
			}
	ACCESS  read-only
	STATUS  mandatory
	DESCRIPTION
		"The value of this object identifies the desired
                 operational status of this observation route."
	::= { mpDetourEntry 9 }

--
mpDiscardIfindex OBJECT-TYPE
	SYNTAX	INTEGER
	ACCESS	read-only
	STATUS	mandatory
	DESCRIPTION
		"This object is ifIndex of discard route."
	::= { mpDetourEntry 10 }

--
mpDiscardIfType OBJECT-TYPE
	SYNTAX  INTEGER {
			atmpp(1),
			vlan(2),
			lis(3),
			outband(4),
			trunk(5),
			ppp(6),
			frpp(7),
			vlantrap(8),
			mplspp(9)
			}
	ACCESS  read-only
	STATUS  mandatory
	DESCRIPTION
		"This object is interface type of discard route."
	::= { mpDetourEntry 11 }

--
mpDiscardIfNumber   OBJECT-TYPE
	SYNTAX  INTEGER
	ACCESS  read-only
	STATUS  mandatory
	DESCRIPTION
		"This object is interface number of discard route."
	::= { mpDetourEntry 12 }

--
mpDetourAdminStatus  OBJECT-TYPE
	SYNTAX  INTEGER {
			up(1),
			down(2)
			}
	ACCESS	read-write
	STATUS  mandatory
	DESCRIPTION
		"The value of this object identifies the desired
                 administer status of this detour route."
	::= { mpDetourEntry 13 }

--
mpDetourOperStatus  OBJECT-TYPE
	SYNTAX  INTEGER {
			up(1),
			down(2)
			}
	ACCESS  read-only
	STATUS  mandatory
	DESCRIPTION
		"The value of this object identifies the desired
                 operational status of this detour route."
	::= { mpDetourEntry 14 }

--
mpDiscardAdminStatus  OBJECT-TYPE
	SYNTAX  INTEGER {
			up(1),
			down(2)
			}
	ACCESS	read-write
	STATUS  mandatory
	DESCRIPTION
		"The value of this object identifies the desired
                 administer status of this discard route."
	::= { mpDetourEntry 15 }

--
mpDiscardOperStatus  OBJECT-TYPE
	SYNTAX  INTEGER {
			up(1),
			down(2)
			}
	ACCESS  read-only
	STATUS  mandatory
	DESCRIPTION
		"The value of this object identifies the desired
                 operational status of this discard route."
	::= { mpDetourEntry 16 }

--
mpRouteStatus  OBJECT-TYPE
	SYNTAX  INTEGER {
			up(1),
			down(2)
			}
	ACCESS  read-only
	STATUS  mandatory
	DESCRIPTION
		"The value of this object identifies the desired
                 operational status of this observe route."
	::= { mpDetourEntry 17 }

--
mpInhibitMode  OBJECT-TYPE
	SYNTAX  INTEGER {
			on(1),
			off(2)
			}
	ACCESS  read-write
	STATUS  mandatory
	DESCRIPTION
		"This object is inhibit mode data."
	::= { mpDetourEntry 18 }

--
mpWatchMode  OBJECT-TYPE
	SYNTAX  INTEGER {
			on(1),
			off(2)
			}
	ACCESS  read-only
	STATUS  mandatory
	DESCRIPTION
		"This object is watch mode data."
	::= { mpDetourEntry 19 }

--
--
--
mpDetourConfigChangeTimeStamp  OBJECT IDENTIFIER ::= { mpDetour 2 }

mpDetourConfigLastChange   OBJECT-TYPE
     SYNTAX       TimeTicks
     ACCESS       read-only
     STATUS       mandatory
     DESCRIPTION   "This object indicates the the time which configuration of the Detour data
                    is changed."
--
--
--

	::= { mpDetourConfigChangeTimeStamp 1 }

--
--
--
mpDetourStatusTimeStamp  OBJECT IDENTIFIER ::= { mpDetour 3 }

mpDetourStatusLastChange    OBJECT-TYPE
     SYNTAX       TimeTicks
     ACCESS       read-only
     STATUS       mandatory
     DESCRIPTION   "This object indicates the the time which configuration of 
                    the operational status is changed."
--
--

 	::= { mpDetourStatusTimeStamp 1 }


END
