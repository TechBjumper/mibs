GBNL2Switch-MIB DEFINITIONS ::= BEGIN

    IMPORTS
        MODULE-IDENTITY, OBJECT-TYPE,
        Integer32, IpAddress,
        NOTIFICATION-TYPE                       FROM SNMPv2-SMI

        DisplayString, MacAddress,
        RowStatus, TruthValue                   FROM SNMPv2-TC

        MODULE-COMPLIANCE, OBJECT-GROUP         FROM SNMPv2-CONF

        gbnL2                                   FROM GREENTECH-MASTER-MIB

        SnmpAdminString                         FROM SNMP-FRAMEWORK-MIB

        PortList, dot1qStaticMulticastEntry     FROM Q-BRIDGE-MIB;

    gbnL2Switch MODULE-IDENTITY
        LAST-UPDATED    "0011020000Z"  -- November 2, 2000
        ORGANIZATION    "Greentech"
        CONTACT-INFO    "Adam Armstrong
                         E-mail: adama@observium.org"

        DESCRIPTION     "Gbn Common Enterprise MIB definition."

        REVISION        "0011020000Z"  -- November 2, 2000
        DESCRIPTION     "Initial MIB creation."

        ::= { gbnL2 1 }

------------------------------------------------------------------------------
--  define groups in GBN-COMMON-MIB
------------------------------------------------------------------------------
    gbnL2SwitchPacket            OBJECT IDENTIFIER ::= { gbnL2Switch 1 }
    gbnL2SwitchMac               OBJECT IDENTIFIER ::= { gbnL2Switch 2 }
    gbnL2SwitchMulticast         OBJECT IDENTIFIER ::= { gbnL2Switch 3 }
    gbnL2SwitchVLAN              OBJECT IDENTIFIER ::= { gbnL2Switch 4 }
    gbnL2SwitchLacpGroup         OBJECT IDENTIFIER ::= { gbnL2Switch 5 }
    gbnL2SwitchLacpPort          OBJECT IDENTIFIER ::= { gbnL2Switch 6 }
    gbnL2SwitchMLD               OBJECT IDENTIFIER ::= { gbnL2Switch 7 }
------------------------------------------------------------------------------
--
--  gbnL2SwitchPacket - Packet Group
--
------------------------------------------------------------------------------
    broadcastSuppress OBJECT-TYPE
        SYNTAX INTEGER (0..200000)
        MAX-ACCESS read-write
        STATUS current
        DESCRIPTION
            "Rate limit Value, the maximum number of packets per second the switch should allow to receive ."
        ::= { gbnL2SwitchPacket 1 }

   dlfForward OBJECT-TYPE
       SYNTAX      INTEGER (0..3)
       MAX-ACCESS  read-write
       STATUS      current
       DESCRIPTION
           "Control the flooding of dlf packets."
           ::= { gbnL2SwitchPacket 2 }

   dlfForwardPortTable OBJECT-TYPE
        SYNTAX SEQUENCE OF DlfForwardPortEntry
        MAX-ACCESS not-accessible
        STATUS current
        DESCRIPTION
            "A table of dlf packets port control."
        ::= { gbnL2SwitchPacket 3 }

   dlfForwardPortEntry OBJECT-TYPE
        SYNTAX DlfForwardPortEntry
        MAX-ACCESS not-accessible
        STATUS current
        DESCRIPTION
            "Table entry for dlf packets control."
        INDEX { dlfForwardPort }
        ::= { dlfForwardPortTable 1 }

   DlfForwardPortEntry ::= SEQUENCE {
        dlfForwardPort     INTEGER,
        dlfForwardStatus   INTEGER
      }

   dlfForwardPort OBJECT-TYPE
        SYNTAX      INTEGER
        MAX-ACCESS  read-only
        STATUS      current
        DESCRIPTION
            "The port number in dlf packets table Item."
        ::= { dlfForwardPortEntry 1 }

   dlfForwardStatus OBJECT-TYPE
        SYNTAX      INTEGER (0..3)
        MAX-ACCESS  read-write
        STATUS      current
        DESCRIPTION
            "The dlf packets flag Item."
        ::= { dlfForwardPortEntry 2 }

------------------------------------------------------------------------------
--
--  gbnL2SwitchMac - MAC Group
--
------------------------------------------------------------------------------
    macAddressTable OBJECT-TYPE
        SYNTAX SEQUENCE OF MacAddressEntry
        MAX-ACCESS not-accessible
        STATUS current
        DESCRIPTION
            "A table of mac address ."
        ::= { gbnL2SwitchMac 1 }

    macAddressEntry OBJECT-TYPE
        SYNTAX MacAddressEntry
        MAX-ACCESS not-accessible
        STATUS current
        DESCRIPTION
            "Table entry for mac address ."
        INDEX { macAddressMac, macAddressVID, macAddressPort }
        ::= { macAddressTable 1 }

    MacAddressEntry ::= SEQUENCE {
        macAddressMac        MacAddress,
        macAddressVID        INTEGER,
        macAddressPort       INTEGER,
        macAddressStatus     INTEGER
      }

    macAddressMac OBJECT-TYPE
        SYNTAX      MacAddress
        MAX-ACCESS  read-only
        STATUS      current
        DESCRIPTION
            "The MAC address in arl table Item."
        ::= { macAddressEntry 1 }

    macAddressVID OBJECT-TYPE
        SYNTAX      INTEGER
        MAX-ACCESS  read-only
        STATUS      current
        DESCRIPTION
            "The vlan ID in arl table Item."
        ::= { macAddressEntry 2 }

    macAddressPort OBJECT-TYPE
        SYNTAX      INTEGER
        MAX-ACCESS  read-only
        STATUS      current
        DESCRIPTION
            "The port number in arl table Item."
        ::= { macAddressEntry 3 }

    macAddressStatus OBJECT-TYPE
        SYNTAX      INTEGER
        {
           dynamic(1),
           static(2),
           permanent(3),
           backhole(4),
           delete(5)
        }
        MAX-ACCESS  read-write
        STATUS      current
        DESCRIPTION
            " "
        ::= { macAddressEntry 4 }



    macLearningPortTable OBJECT-TYPE
        SYNTAX SEQUENCE OF MacLearningPortEntry
        MAX-ACCESS not-accessible
        STATUS current
        DESCRIPTION
            "A table of mac address learning port control."
        ::= { gbnL2SwitchMac 2 }

    macLearningPortEntry OBJECT-TYPE
        SYNTAX MacLearningPortEntry
        MAX-ACCESS not-accessible
        STATUS current
        DESCRIPTION
            "Table entry for mac address  learning control."
        INDEX { macAddressLearningPort }
        ::= { macLearningPortTable 1 }

    MacLearningPortEntry ::= SEQUENCE {
        macAddressLearningPort     INTEGER,
        macAddressLearningStatus  INTEGER,
        macAddressMaxCount        INTEGER
      }

    macAddressLearningPort OBJECT-TYPE
        SYNTAX      INTEGER
        MAX-ACCESS  read-only
        STATUS      current
        DESCRIPTION
            "The port number in mac address learning table Item."
        ::= { macLearningPortEntry 1 }

    macAddressLearningStatus OBJECT-TYPE
        SYNTAX      INTEGER
        {
            enable(1),
        disable(2)
        }
        MAX-ACCESS  read-write
        STATUS      current
        DESCRIPTION
            "The mac address learning flag Item."
        ::= { macLearningPortEntry 2 }

     macAddressMaxCount OBJECT-TYPE
        SYNTAX      INTEGER (0..1000)
        MAX-ACCESS  read-write
        STATUS      current
        DESCRIPTION
            "the max mac address number of port."
        ::= { macLearningPortEntry 3 }

------------------------------------------------------------------------------
--
--  gbnL2SwitchMulticast - Multicast Group
--
------------------------------------------------------------------------------
    igmpSnoopEnabled  OBJECT-TYPE
        SYNTAX TruthValue
        MAX-ACCESS read-write
        STATUS current
        DESCRIPTION
            "DURABLE: { false }
             Setting this object to true(1) enables IGMP Snooping.  Setting
             it to false(2) disables IGMP Snooping.

             Note that IGMP Snooping can function with or without GVRP and
             GMRP enabled."
        ::= { gbnL2SwitchMulticast 1 }


    igmpSnoopAlerts  OBJECT-TYPE
        SYNTAX TruthValue
        MAX-ACCESS read-write
        STATUS current
        DESCRIPTION
            "DURABLE: { false }
             Setting this object to true(1) enables the IP Router Alert
             Option (as defined in RFC2113) for transmitted IGMP packets.
             Setting it to false(2) disables this option."
        ::= { gbnL2SwitchMulticast 2 }

    igmpSnoopAging  OBJECT-TYPE
        SYNTAX Integer32 (10..1000000)
        MAX-ACCESS read-write
        STATUS current
        DESCRIPTION
            "DURABLE: { 300 }
             The timeout period in seconds for aging out Multicast Groups
             dynamically learned with IGMP Snooping.  Note that aging operates
             on a per interface per VLAN per multicast group basis."
        ::= { gbnL2SwitchMulticast 3 }

    igmpSnoopTable OBJECT-TYPE
        SYNTAX SEQUENCE OF IgmpSnoopEntry
        MAX-ACCESS not-accessible
        STATUS current
        DESCRIPTION
            "This table, which provides IGMP Snooping information, augments
             the 'dot1qStaticMulticastTable' in the Q-MIB (RFC2674)."
        ::= { gbnL2SwitchMulticast 4 }

    igmpSnoopEntry OBJECT-TYPE
        SYNTAX IgmpSnoopEntry
        MAX-ACCESS not-accessible
        STATUS current
        DESCRIPTION
            "Displays by VLAN, Multicast Group, and Multicast receive port
             the set of ports enabled to forward Multicast Group traffic as
             determined by the IGMP Snooping task."
        AUGMENTS { dot1qStaticMulticastEntry }
        ::= { igmpSnoopTable 1 }

    IgmpSnoopEntry ::= SEQUENCE {
        igmpSnoopEgressPorts   PortList
    }

    igmpSnoopEgressPorts  OBJECT-TYPE
        SYNTAX PortList
        MAX-ACCESS read-only
        STATUS current
        DESCRIPTION
            "This read-only object displays the set of ports enabled to
             forward specific Multicast Group traffic as determined by the
             IGMP Snooping task.

             It should be noted that the IGMP Snooping task generates a pseudo-
             static (i.e., not saved in NVM) port list similar to the RFC2674
             Q-MIB 'dot1qStaticMulticastStaticEgressPorts' object. Consequently,
             a port will not be a member of 'gbnCommonIgmpSnoopEgressPorts' if
             it is a member of 'dot1qStaticMulticastForbiddenEgressPorts'."
        ::= { igmpSnoopEntry 1 }

    igmpSnoopDefaultGroupPolicy OBJECT-TYPE
        SYNTAX INTEGER {
            deny(0),
            permit(1)
        }
        MAX-ACCESS read-write
        STATUS current
        DESCRIPTION
            "The default group learning policy when a group address is not found in
            IGMP Snooping white-list and black-list"
        ::= { gbnL2SwitchMulticast 5 }

    igmpSnoopMaxResponseTime OBJECT-TYPE
        SYNTAX Integer32 (1..100)
        MAX-ACCESS read-write
        STATUS current
        DESCRIPTION
            "The timeout period in seconds waited before determinating whether
            a group port should be deleted or not after received a leave packet"
        ::= { gbnL2SwitchMulticast 6 }

    igmpSnoopPortTable OBJECT-TYPE
        SYNTAX SEQUENCE OF IgmpSnoopPortEntry
        MAX-ACCESS not-accessible
        STATUS current
        DESCRIPTION
            "Used to config IGMP Snooping port options,such as group-limit and
             fast-leave."
        ::= { gbnL2SwitchMulticast 7 }

    igmpSnoopPortEntry OBJECT-TYPE
        SYNTAX IgmpSnoopPortEntry
        MAX-ACCESS not-accessible
        STATUS current
        DESCRIPTION
            "Entries of igmpSnoopPortTable."
        INDEX { igmpSnoopPort }
        ::= { igmpSnoopPortTable 1 }

    IgmpSnoopPortEntry ::= SEQUENCE {
        igmpSnoopPort            INTEGER,
        igmpSnoopPortFastLeave   INTEGER,
        igmpSnoopPortGroupLimit  INTEGER,
        igmpSnoopPortMcastVlan   INTEGER
    }

    igmpSnoopPort OBJECT-TYPE
        SYNTAX INTEGER
        MAX-ACCESS read-only
        STATUS current
        DESCRIPTION
            "Index that uniquely identifies a Ap port within igmpSnoopPortTable."
        ::= { igmpSnoopPortEntry 1 }

    igmpSnoopPortFastLeave OBJECT-TYPE
        SYNTAX INTEGER {
            enable(1),
            disable(2)
        }
        MAX-ACCESS read-write
        STATUS current
        DESCRIPTION
            "The fast-leave option of a IGMP Snooping port,when set
             a group port is deleted immediately on receiving a leave
             packet, otherwise a max-response-time should be waited
             before deleting the port."
        ::= { igmpSnoopPortEntry 2 }

    igmpSnoopPortGroupLimit OBJECT-TYPE
        SYNTAX INTEGER (0..991)
        MAX-ACCESS read-write
        STATUS current
        DESCRIPTION
            "The max number of Multicast groups a port can learn."
        ::= { igmpSnoopPortEntry 3 }

    igmpSnoopPortMcastVlan OBJECT-TYPE
        SYNTAX INTEGER (0..4094)
        MAX-ACCESS read-write
        STATUS current
        DESCRIPTION
             "Specify a multicast vlan for a port.IGMP report groups received
              on the port will be add to the multicast vlan, regardless of the
              vlan id indicated by the report packets, a zero vlan means no multicast
              vlan is used."
        ::= { igmpSnoopPortEntry 4 }

    igmpSnoopGroupTable OBJECT-TYPE
        SYNTAX SEQUENCE OF IgmpSnoopGroupEntry
        MAX-ACCESS not-accessible
        STATUS current
        DESCRIPTION
            "This table is used to config IGMP Snooping white-list and
             black-list."
        ::= { gbnL2SwitchMulticast 8 }

    igmpSnoopGroupEntry OBJECT-TYPE
        SYNTAX IgmpSnoopGroupEntry
        MAX-ACCESS not-accessible
        STATUS current
        DESCRIPTION
            "Entries of igmpSnoopGroupTable."
        INDEX { igmpSnoopGroupAddress, igmpSnoopGroupPort , igmpSnoopGroupVLAN }
        ::= { igmpSnoopGroupTable 1 }

    IgmpSnoopGroupEntry ::= SEQUENCE {
        igmpSnoopGroupAddress    MacAddress,
        igmpSnoopGroupPort       INTEGER,
        igmpSnoopGroupVLAN       INTEGER,
        igmpSnoopGroupPolicy     INTEGER
    }

    igmpSnoopGroupAddress OBJECT-TYPE
        SYNTAX MacAddress
        MAX-ACCESS not-accessible
        STATUS current
        DESCRIPTION
            "An index that uniquely identifies a multicast mac-address
             within igmpSnoopGroupTable."
        ::= { igmpSnoopGroupEntry 1 }

    igmpSnoopGroupPort OBJECT-TYPE
        SYNTAX INTEGER
        MAX-ACCESS not-accessible
        STATUS current
        DESCRIPTION
            "An index that uniquely identifies a Ap port within igmpSnoopGroupTable."
        ::= { igmpSnoopGroupEntry 2 }

    igmpSnoopGroupVLAN OBJECT-TYPE
        SYNTAX INTEGER (1..4094)
        MAX-ACCESS not-accessible
        STATUS current
        DESCRIPTION
            "An index that uniquely identifies a VLAN ID within igmpSnoopGroupTable."
        ::= { igmpSnoopGroupEntry 3 }

    igmpSnoopGroupPolicy OBJECT-TYPE
        SYNTAX INTEGER {
              permit(3),
              deny(4),
              del(5)
        }
        MAX-ACCESS read-write
        STATUS current
        DESCRIPTION
            "This entry is used to config IGMP Snooping white-list and
            black-list.Policies defined in white-list and black-list are
            superior to that has beed defined by igmpSnoopDefaultGroupPolicy.
            If group is not found in white-list or black-list then
            'igmpSnoopDefaultGroupPolicy' takes effect"
        ::= { igmpSnoopGroupEntry 4 }


    crossVlanMulticastEnabled  OBJECT-TYPE
        SYNTAX TruthValue
        MAX-ACCESS read-write
        STATUS current
        DESCRIPTION
            "Setting this object to true(1) enables cross-vlan multicast.  Setting
             it to false(2) disables cross-vlan multicast."
        ::= { gbnL2SwitchMulticast 9 }

    crossVlanMulticastTable OBJECT-TYPE
        SYNTAX SEQUENCE OF CrossVlanMulticastEntry
        MAX-ACCESS not-accessible
        STATUS current
        DESCRIPTION
            "Used to config port info of cross-vlan multicast,such as tag/untag and vlanid of tag."
        ::= { gbnL2SwitchMulticast 10 }

    crossVlanMulticastEntry OBJECT-TYPE
        SYNTAX CrossVlanMulticastEntry
        MAX-ACCESS not-accessible
        STATUS current
        DESCRIPTION
            "Entries of crossVlanMulticastPortTable."
        INDEX { crossVlanPort }
        ::= { crossVlanMulticastTable 1 }

    CrossVlanMulticastEntry ::= SEQUENCE {
            crossVlanPort            Integer32,
            crossVlanPortTag       TruthValue,
            crossVlanPortVid        Integer32
        }
    crossVlanPort OBJECT-TYPE
        SYNTAX Integer32
        MAX-ACCESS not-accessible
        STATUS current
        DESCRIPTION
            "The port number."
        ::= { crossVlanMulticastEntry 1 }

    crossVlanPortTag OBJECT-TYPE
        SYNTAX TruthValue
        MAX-ACCESS read-write
        STATUS current
        DESCRIPTION
            "Setting this object to true(1) of tag.  Setting
             it to false(2) of untag."
        ::= { crossVlanMulticastEntry 2 }


    crossVlanPortVid OBJECT-TYPE
        SYNTAX Integer32 (1..4095)
        MAX-ACCESS read-write
        STATUS current
        DESCRIPTION
            "The vlanid of tag port."
        ::= { crossVlanMulticastEntry 3 }

    igmpSnoopRoutePortForward OBJECT-TYPE
        SYNTAX      INTEGER
        {
            enabled(1),
            disabled(2)
        }
        MAX-ACCESS  read-write
        STATUS      current
        DESCRIPTION
            "If the status is enabled, the route port can be added into the group automatically
             when an igmp snooping group is created . If the status is disabled, it will be not."
        ::= { gbnL2SwitchMulticast 11 }

------------------------------------------------------------------------------
--
--  gbnL2SwitchVLAN - VLAN Group
--
------------------------------------------------------------------------------
    portModeTable OBJECT-TYPE
        SYNTAX SEQUENCE OF PortModeEntry
        MAX-ACCESS not-accessible
        STATUS current
        DESCRIPTION
            "A Table of port mode."
        ::= { gbnL2SwitchVLAN 1 }

    portModeEntry OBJECT-TYPE
        SYNTAX PortModeEntry
        MAX-ACCESS not-accessible
        STATUS current
        DESCRIPTION
            "A list of portmode parameters."
        INDEX { portNumber }
        ::= { portModeTable 1 }

    PortModeEntry ::= SEQUENCE {
            portNumber     Integer32,
            portMode       INTEGER
        }

    portNumber OBJECT-TYPE
        SYNTAX Integer32
        MAX-ACCESS read-only
        STATUS current
        DESCRIPTION
            "port number'."
        ::= { portModeEntry 1 }

    portMode OBJECT-TYPE
        SYNTAX INTEGER {
                    trunk-port(1),
                    access-port(2),
                    hybrid-port(3)
        }
        MAX-ACCESS read-write
        STATUS current
        DESCRIPTION
            "type of mode"
        ::= { portModeEntry 2 }
------------------------------------------------------------------------------
--
--  gbnL2SwitchLacpGroup - Lacp Channel Group
--
------------------------------------------------------------------------------
    channelGroupCreate OBJECT-TYPE
        SYNTAX INTEGER
        MAX-ACCESS read-write
        STATUS current
        DESCRIPTION
            "Create a channel group ."
        ::= { gbnL2SwitchLacpGroup 1 }

    channelGroupDelete OBJECT-TYPE
        SYNTAX INTEGER
        MAX-ACCESS read-write
        STATUS current
        DESCRIPTION
            "Delete a channel group. Make sure there is no member in this group ."
        ::= { gbnL2SwitchLacpGroup 2 }

    channelGroupTable OBJECT-TYPE
        SYNTAX SEQUENCE OF ChannelGroupEntry
        MAX-ACCESS not-accessible
        STATUS current
        DESCRIPTION
            "A table that contains information about every
            Lacp channel group that is associated with this System."
        ::= { gbnL2SwitchLacpGroup 3 }

    channelGroupEntry OBJECT-TYPE
        SYNTAX ChannelGroupEntry
        MAX-ACCESS not-accessible
        STATUS current
        DESCRIPTION
            "A list of the Lacp channel group parameters. This is indexed
            by the group index."
        --INDEX { ChannelGroupIndex }
        ::= { channelGroupTable 1 }

   ChannelGroupEntry ::=
    SEQUENCE {
        channelGroupIndex
           INTEGER,
        channelGroupPortList
           PortList,
        channelGroupRule
           INTEGER,
        channelGroupRowstatus
           RowStatus
    }

    channelGroupIndex OBJECT-TYPE
        SYNTAX       INTEGER
        MAX-ACCESS   read-only
        STATUS       current
        DESCRIPTION
            "The Index of the Lacp Channel group."
        ::= { channelGroupEntry 1 }

    channelGroupPortList OBJECT-TYPE
        SYNTAX      PortList
        MAX-ACCESS  read-write
        STATUS      current
        DESCRIPTION
            "The complete set of ports currently associated with
             this Group.  Each bit set in this list represents
             an Actor Port member of this Group."

        ::= { channelGroupEntry 2 }

    channelGroupRule OBJECT-TYPE
    SYNTAX INTEGER {
        srcMAC(1),
        destMAC(2),
        srcXORDestMAC(3),
        srcIP(4),
        destIP(5),
        srcXORDestIP(6)
    }
    ACCESS read-write
    STATUS mandatory
    DESCRIPTION
        " The Rule to be applied to this Link Aggregator's Trunk Group
        Table. The rules are based on the following selections SrcMAC (1),
        means that the last three bits of the Source MAC Address are used to
        index the Trunk Group to get the destination port. DestMAC (2), means
        the last three bits of the Destination MAC Address are used to index
        into the Trunk Group to get the destination port. SrcXORDestMAC (3),
        means that the last three bits of the Source MAC Address are logically
        XORed with the last three bits of the Destination MAC Address and used
        to index into the Trunk Group to get the destination port. SrcIP (4),
        means the last three bits of the Source IP Address are used to index
        into the Trunk Group to get the destination port. DestIP (5), means
        the last three bits of the Destination IP Address are used to index
        into the Trunk Group to get the destination port. SrcXORDestIP (6),
        means the last three bits of the Source IP Address are logically XORed
        with the last three bits of the Destination IP Address and used to
        index into the Trunk Group to get the destination port. This rule
        defines the distribution algorithm applied to the aggregated link."

    ::= { channelGroupEntry 3 }


    channelGroupRowstatus OBJECT-TYPE
        SYNTAX       TruthValue
        MAX-ACCESS   read-write
        STATUS       current
        DESCRIPTION
            "rowstatus of channel group."
        ::= { channelGroupEntry 4 }

------------------------------------------------------------------------------
--
--  gbnL2SwitchLacpPort - Lacp port
--
------------------------------------------------------------------------------
    lacpPortModeTable OBJECT-TYPE
        SYNTAX      SEQUENCE OF LacpPortModeEntry
        MAX-ACCESS  not-accessible
        STATUS      current
        DESCRIPTION
            "A table that contains information about every
            Lacp channel group that is associated with this System."
        ::= { gbnL2SwitchLacpPort 1 }

    lacpPortModeEntry OBJECT-TYPE
        SYNTAX      LacpPortModeEntry
        MAX-ACCESS  not-accessible
        STATUS      current
        DESCRIPTION
            "The port mode of lacp. This is indexed
            by the port number."
        INDEX { portIndex }
        ::= { lacpPortModeTable 1 }

    LacpPortModeEntry ::=
    SEQUENCE {
        portIndex
           INTEGER,
        portLacpMode
           INTEGER,
        portLacpRowstatus
           RowStatus
    }

    portIndex OBJECT-TYPE
        SYNTAX       INTEGER
        MAX-ACCESS   read-only
        STATUS       current
        DESCRIPTION
            "The Index of the port."
        ::= { lacpPortModeEntry 1 }

    portLacpMode OBJECT-TYPE
        SYNTAX INTEGER {
        static(1),
        active(2),
        passive(3)
    }
    MAX-ACCESS   read-write
    STATUS       current
    DESCRIPTION
        "The mode of the Lacp Channel group.Static:link aggregation is
        static configguration,and lacp protocol do not run. Active:the port
        in this mode can send lacp pdu active.Passive:the port in this mode
        just send pdu when needed."
    ::= { lacpPortModeEntry 2 }

    portLacpRowstatus OBJECT-TYPE
        SYNTAX       TruthValue
        MAX-ACCESS   read-only
        STATUS       current
        DESCRIPTION
            "rowstatus of port."
        ::= { lacpPortModeEntry 3 }
------------------------------------------------------------------------------
--
--  gbnL2SwitchMLD - MLD Group
--
------------------------------------------------------------------------------
    mldSnoopEnabled  OBJECT-TYPE
        SYNTAX TruthValue
        MAX-ACCESS read-write
        STATUS current
        DESCRIPTION
            "DURABLE: { false }
             Setting this object to true(1) enables MLD Snooping.  Setting
             it to false(2) disables MLD Snooping.

             Note that MLD Snooping can function with or without GVRP and
             GMRP enabled."
        ::= { gbnL2SwitchMLD 1 }


    mldSnoopAlerts  OBJECT-TYPE
        SYNTAX TruthValue
        MAX-ACCESS read-write
        STATUS current
        DESCRIPTION
            "DURABLE: { false }
             Setting this object to true(1) enables the IP Router Alert
             Option (as defined in RFC2113) for transmitted MLD packets.
             Setting it to false(2) disables this option."
        ::= { gbnL2SwitchMLD 2 }

    mldSnoopAging  OBJECT-TYPE
        SYNTAX Integer32 (10..1000000)
        MAX-ACCESS read-write
        STATUS current
        DESCRIPTION
            "DURABLE: { 300 }
             The timeout period in seconds for aging out MLD Groups
             dynamically learned with MLD Snooping.  Note that aging operates
             on a per interface per VLAN per multicast group basis."
        ::= { gbnL2SwitchMLD 3 }

    mldSnoopTable OBJECT-TYPE
        SYNTAX SEQUENCE OF MldSnoopEntry
        MAX-ACCESS not-accessible
        STATUS current
        DESCRIPTION
            "This table, which provides MLD Snooping information, augments
             the 'dot1qStaticMulticastTable' in the Q-MIB (RFC2674)."
        ::= { gbnL2SwitchMLD 4 }

    mldSnoopEntry OBJECT-TYPE
        SYNTAX MldSnoopEntry
        MAX-ACCESS not-accessible
        STATUS current
        DESCRIPTION
            "Displays by VLAN, MLD Group, and MLD receive port
             the set of ports enabled to forward MLD Group traffic as
             determined by the MLD Snooping task."
        AUGMENTS { dot1qStaticMulticastEntry }
        ::= { mldSnoopTable 1 }

    MldSnoopEntry ::=
    SEQUENCE {
        mldSnoopEgressPorts  PortList
    }

    mldSnoopEgressPorts  OBJECT-TYPE
        SYNTAX PortList
        MAX-ACCESS read-only
        STATUS current
        DESCRIPTION
            "This read-only object displays the set of ports enabled to
             forward specific MLD Group traffic as determined by the
             MLD Snooping task.

             It should be noted that the MLD Snooping task generates a pseudo-
             static (i.e., not saved in NVM) port list similar to the RFC2674
             Q-MIB 'dot1qStaticMulticastStaticEgressPorts' object. Consequently,
             a port will not be a member of 'gbnCommonIgmpSnoopEgressPorts' if
             it is a member of 'dot1qStaticMulticastForbiddenEgressPorts'."
        ::= { mldSnoopEntry 1 }

    mldSnoopDefaultGroupPolicy OBJECT-TYPE
        SYNTAX INTEGER {
            deny(0),
            permit(1)
        }
        MAX-ACCESS read-write
        STATUS current
        DESCRIPTION
            "The default group learning policy when a group address is not found in
            MLD Snooping white-list and black-list"
        ::= { gbnL2SwitchMLD 5 }

    mldSnoopMaxResponseTime OBJECT-TYPE
        SYNTAX Integer32 (1..100)
        MAX-ACCESS read-write
        STATUS current
        DESCRIPTION
            "The timeout period in seconds waited before determinating whether
            a group port should be deleted or not after received a leave packet"
        ::= { gbnL2SwitchMLD 6 }

    mldSnoopPortTable OBJECT-TYPE
        SYNTAX SEQUENCE OF MldSnoopPortEntry
        MAX-ACCESS not-accessible
        STATUS current
        DESCRIPTION
            "Used to config MLD Snooping port options,such as group-limit and
             fast-leave."
        ::= { gbnL2SwitchMLD 7 }

    mldSnoopPortEntry OBJECT-TYPE
        SYNTAX MldSnoopPortEntry
        MAX-ACCESS not-accessible
        STATUS current
        DESCRIPTION
            "Entries of mldSnoopPortTable."
        INDEX { mldSnoopPort }
        ::= { mldSnoopPortTable 1 }

    MldSnoopPortEntry ::= SEQUENCE {
        mldSnoopPort            INTEGER,
        mldSnoopPortFastLeave   INTEGER,
        mldSnoopPortGroupLimit  INTEGER,
        mldSnoopPortMcastVlan   INTEGER
    }

    mldSnoopPort OBJECT-TYPE
        SYNTAX INTEGER
        MAX-ACCESS read-only
        STATUS current
        DESCRIPTION
            "Index that uniquely identifies a Ap port within mldSnoopPortTable."
        ::= { mldSnoopPortEntry 1 }

    mldSnoopPortFastLeave OBJECT-TYPE
        SYNTAX INTEGER {
            enable(1),
            disable(2)
        }
        MAX-ACCESS read-write
        STATUS current
        DESCRIPTION
            "The fast-leave option of a MLD Snooping port,when set
             a group port is deleted immediately on receiving a leave
             packet, otherwise a max-response-time should be waited
             before deleting the port."
        ::= { mldSnoopPortEntry 2 }

    mldSnoopPortGroupLimit OBJECT-TYPE
        SYNTAX INTEGER (0..128)
        MAX-ACCESS read-write
        STATUS current
        DESCRIPTION
            "The max number of MLD groups a port can learn."
        ::= { mldSnoopPortEntry 3 }

    mldSnoopPortMcastVlan OBJECT-TYPE
        SYNTAX INTEGER (0..4094)
        MAX-ACCESS read-write
        STATUS current
        DESCRIPTION
             "Specify a multicast vlan for a port.MLD report groups received
              on the port will be add to the multicast vlan, regardless of the
              vlan id indicated by the report packets, a zero vlan means no multicast
              vlan is used."
        ::= { mldSnoopPortEntry 4 }

    mldSnoopGroupTable OBJECT-TYPE
        SYNTAX SEQUENCE OF MldSnoopGroupEntry
        MAX-ACCESS not-accessible
        STATUS current
        DESCRIPTION
            "This table is used to config MLD Snooping white-list and
             black-list."
        ::= { gbnL2SwitchMLD 8 }

    mldSnoopGroupEntry OBJECT-TYPE
        SYNTAX MldSnoopGroupEntry
        MAX-ACCESS not-accessible
        STATUS current
        DESCRIPTION
            "Entries of mldSnoopGroupTable."
        INDEX { mldSnoopGroupAddress, mldSnoopGroupPort, mldSnoopGroupVLAN }
        ::= { mldSnoopGroupTable 1 }

    MldSnoopGroupEntry ::= SEQUENCE {
        mldSnoopGroupAddress    MacAddress,
        mldSnoopGroupPort       INTEGER,
        mldSnoopGroupVLAN       INTEGER,
        mldSnoopGroupPolicy     INTEGER
    }

    mldSnoopGroupAddress OBJECT-TYPE
        SYNTAX MacAddress
        MAX-ACCESS not-accessible
        STATUS current
        DESCRIPTION
            "An index that uniquely identifies a multicast mac-address
             within mldSnoopGroupTable."
        ::= { mldSnoopGroupEntry 1 }

    mldSnoopGroupPort OBJECT-TYPE
        SYNTAX INTEGER
        MAX-ACCESS not-accessible
        STATUS current
        DESCRIPTION
            "An index that uniquely identifies a Ap port within mldSnoopGroupTable."
        ::= { mldSnoopGroupEntry 2 }

    mldSnoopGroupVLAN OBJECT-TYPE
        SYNTAX INTEGER (1..4094)
        MAX-ACCESS not-accessible
        STATUS current
        DESCRIPTION
            "An index that uniquely identifies a VLAN ID within mldSnoopGroupTable."
        ::= { mldSnoopGroupEntry 3 }

    mldSnoopGroupPolicy OBJECT-TYPE
        SYNTAX INTEGER {
              permit(3),
              deny(4),
              del(5)
        }
        MAX-ACCESS read-write
        STATUS current
        DESCRIPTION
            "This entry is used to config MLD Snooping white-list and
            black-list.Policies defined in white-list and black-list are
            superior to that has beed defined by mldSnoopDefaultGroupPolicy.
            If group is not found in white-list or black-list then
            'mldSnoopDefaultGroupPolicy' takes effect"
        ::= { mldSnoopGroupEntry 4 }

    mldSnoopRoutePortForward OBJECT-TYPE
        SYNTAX      INTEGER
        {
            enabled(1),
            disabled(2)
        }
        MAX-ACCESS  read-write
        STATUS      current
        DESCRIPTION
            "If the status is enabled, the route port can be added into the group automatically
             when an mld snooping group is created . If the status is disabled, it will be not."
        ::= { gbnL2SwitchMLD 9 }

--
-- END of GBN-COMMON-MIB
--

END
