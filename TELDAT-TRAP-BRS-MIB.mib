-- file automatically created


TELDAT-TRAP-BRS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


brsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BRS event subsystem."
    REVISION "201401200930Z"
    DESCRIPTION "Initial implementation"
        ::= { telEventTraps 3 }


brsEventsGroup	OBJECT IDENTIFIER	::= { brsTrapsMIB 1 }

brsNotifications	OBJECT IDENTIFIER	::= { brsTrapsMIB 2 }
brsNotificationsPrefix	OBJECT IDENTIFIER	::= { brsNotifications 0 }

brsEventObjects1 OBJECT-IDENTITY
    STATUS current
    DESCRIPTION
        "Event BRS.1
        A packet is placed in the class based on its protocol."
    ::= { brsEventsGroup 1 }

brs1-msg-prot-type OBJECT-TYPE
    SYNTAX DisplayString
    MAX-ACCESS accessible-for-notify
    STATUS current
    DESCRIPTION
        "Parameter 'msg prot type' in event BRS.1"
    ::= { brsEventObjects1 1 }

brs1-class-name OBJECT-TYPE
    SYNTAX DisplayString
    MAX-ACCESS accessible-for-notify
    STATUS current
    DESCRIPTION
        "Parameter 'class name' in event BRS.1"
    ::= { brsEventObjects1 2 }

brs1-interface OBJECT-TYPE
    SYNTAX DisplayString
    MAX-ACCESS accessible-for-notify
    STATUS current
    DESCRIPTION
        "Parameter 'interface' in event BRS.1"
    ::= { brsEventObjects1 3 }

brsEventObjects2 OBJECT-IDENTITY
    STATUS current
    DESCRIPTION
        "Event BRS.2
        Notifies on all packet overflows."
    ::= { brsEventsGroup 2 }

brs2-msg-prot-type OBJECT-TYPE
    SYNTAX DisplayString
    MAX-ACCESS accessible-for-notify
    STATUS current
    DESCRIPTION
        "Parameter 'msg prot type' in event BRS.2"
    ::= { brsEventObjects2 1 }

brs2-interface OBJECT-TYPE
    SYNTAX DisplayString
    MAX-ACCESS accessible-for-notify
    STATUS current
    DESCRIPTION
        "Parameter 'interface' in event BRS.2"
    ::= { brsEventObjects2 2 }

brsEventObjects3 OBJECT-IDENTITY
    STATUS current
    DESCRIPTION
        "Event BRS.3
        Message showed when zero length packets are dumped."
    ::= { brsEventsGroup 3 }

brs3-msg-prot-type OBJECT-TYPE
    SYNTAX DisplayString
    MAX-ACCESS accessible-for-notify
    STATUS current
    DESCRIPTION
        "Parameter 'msg prot type' in event BRS.3"
    ::= { brsEventObjects3 1 }

brs3-interface OBJECT-TYPE
    SYNTAX DisplayString
    MAX-ACCESS accessible-for-notify
    STATUS current
    DESCRIPTION
        "Parameter 'interface' in event BRS.3"
    ::= { brsEventObjects3 2 }

brsEventObjects4 OBJECT-IDENTITY
    STATUS current
    DESCRIPTION
        "Event BRS.4
        A packet is placed from handler struct to driver queue
        to be transmitted."
    ::= { brsEventsGroup 4 }

brs4-class-name OBJECT-TYPE
    SYNTAX DisplayString
    MAX-ACCESS accessible-for-notify
    STATUS current
    DESCRIPTION
        "Parameter 'class name' in event BRS.4"
    ::= { brsEventObjects4 1 }

brs4-interface OBJECT-TYPE
    SYNTAX DisplayString
    MAX-ACCESS accessible-for-notify
    STATUS current
    DESCRIPTION
        "Parameter 'interface' in event BRS.4"
    ::= { brsEventObjects4 2 }

brsEventObjects5 OBJECT-IDENTITY
    STATUS current
    DESCRIPTION
        "Event BRS.5
        No traffic-shape-group can transmit due to congestion."
    ::= { brsEventsGroup 5 }

brs5-class OBJECT-TYPE
    SYNTAX DisplayString
    MAX-ACCESS accessible-for-notify
    STATUS current
    DESCRIPTION
        "Parameter 'class' in event BRS.5"
    ::= { brsEventObjects5 1 }

brs5-interface OBJECT-TYPE
    SYNTAX DisplayString
    MAX-ACCESS accessible-for-notify
    STATUS current
    DESCRIPTION
        "Parameter 'interface' in event BRS.5"
    ::= { brsEventObjects5 2 }

brs5-ticks-left OBJECT-TYPE
    SYNTAX Integer32
    MAX-ACCESS accessible-for-notify
    STATUS current
    DESCRIPTION
        "Parameter 'ticks-left' in event BRS.5"
    ::= { brsEventObjects5 3 }

brsEventObjects6 OBJECT-IDENTITY
    STATUS current
    DESCRIPTION
        "Event BRS.6
        A timer is launch to check for de-congestion of any class."
    ::= { brsEventsGroup 6 }

brs6-interface OBJECT-TYPE
    SYNTAX DisplayString
    MAX-ACCESS accessible-for-notify
    STATUS current
    DESCRIPTION
        "Parameter 'interface' in event BRS.6"
    ::= { brsEventObjects6 1 }

brs6-class OBJECT-TYPE
    SYNTAX DisplayString
    MAX-ACCESS accessible-for-notify
    STATUS current
    DESCRIPTION
        "Parameter 'class' in event BRS.6"
    ::= { brsEventObjects6 2 }

brs6-new-time OBJECT-TYPE
    SYNTAX Integer32
    MAX-ACCESS accessible-for-notify
    STATUS current
    DESCRIPTION
        "Parameter 'new time' in event BRS.6"
    ::= { brsEventObjects6 3 }

brs6-new-time-out OBJECT-TYPE
    SYNTAX Integer32
    MAX-ACCESS accessible-for-notify
    STATUS current
    DESCRIPTION
        "Parameter 'new time-out' in event BRS.6"
    ::= { brsEventObjects6 4 }

brs6-old-time OBJECT-TYPE
    SYNTAX Integer32
    MAX-ACCESS accessible-for-notify
    STATUS current
    DESCRIPTION
        "Parameter 'old time' in event BRS.6"
    ::= { brsEventObjects6 5 }

brs6-old-time-out OBJECT-TYPE
    SYNTAX Integer32
    MAX-ACCESS accessible-for-notify
    STATUS current
    DESCRIPTION
        "Parameter 'old time-out' in event BRS.6"
    ::= { brsEventObjects6 6 }

brsEventObjects7 OBJECT-IDENTITY
    STATUS current
    DESCRIPTION
        "Event BRS.7
        A timer has expired."
    ::= { brsEventsGroup 7 }

brs7-interface OBJECT-TYPE
    SYNTAX DisplayString
    MAX-ACCESS accessible-for-notify
    STATUS current
    DESCRIPTION
        "Parameter 'interface' in event BRS.7"
    ::= { brsEventObjects7 1 }

brsEventObjects8 OBJECT-IDENTITY
    STATUS current
    DESCRIPTION
        "Event BRS.8
        A packet has been tagged with a new dscp value."
    ::= { brsEventsGroup 8 }

brs8-source-IP OBJECT-TYPE
    SYNTAX IpAddress
    MAX-ACCESS accessible-for-notify
    STATUS current
    DESCRIPTION
        "Parameter 'source IP' in event BRS.8"
    ::= { brsEventObjects8 1 }

brs8-destination-IP OBJECT-TYPE
    SYNTAX IpAddress
    MAX-ACCESS accessible-for-notify
    STATUS current
    DESCRIPTION
        "Parameter 'destination IP' in event BRS.8"
    ::= { brsEventObjects8 2 }

brs8-class OBJECT-TYPE
    SYNTAX DisplayString
    MAX-ACCESS accessible-for-notify
    STATUS current
    DESCRIPTION
        "Parameter 'class' in event BRS.8"
    ::= { brsEventObjects8 3 }

brs8-new-dscp-value OBJECT-TYPE
    SYNTAX Integer32
    MAX-ACCESS accessible-for-notify
    STATUS current
    DESCRIPTION
        "Parameter 'new dscp value' in event BRS.8"
    ::= { brsEventObjects8 4 }

brsEventObjects9 OBJECT-IDENTITY
    STATUS current
    DESCRIPTION
        "Event BRS.9
        A packet has been tagged with a new cos value."
    ::= { brsEventsGroup 9 }

brs9-source-IP OBJECT-TYPE
    SYNTAX IpAddress
    MAX-ACCESS accessible-for-notify
    STATUS current
    DESCRIPTION
        "Parameter 'source IP' in event BRS.9"
    ::= { brsEventObjects9 1 }

brs9-destination-IP OBJECT-TYPE
    SYNTAX IpAddress
    MAX-ACCESS accessible-for-notify
    STATUS current
    DESCRIPTION
        "Parameter 'destination IP' in event BRS.9"
    ::= { brsEventObjects9 2 }

brs9-class OBJECT-TYPE
    SYNTAX DisplayString
    MAX-ACCESS accessible-for-notify
    STATUS current
    DESCRIPTION
        "Parameter 'class' in event BRS.9"
    ::= { brsEventObjects9 3 }

brs9-new-cos-value OBJECT-TYPE
    SYNTAX Integer32
    MAX-ACCESS accessible-for-notify
    STATUS current
    DESCRIPTION
        "Parameter 'new cos value' in event BRS.9"
    ::= { brsEventObjects9 4 }

brsEventObjects10 OBJECT-IDENTITY
    STATUS current
    DESCRIPTION
        "Event BRS.10
        A packet has been tagged with ATM CLP."
    ::= { brsEventsGroup 10 }

brs10-source-IP OBJECT-TYPE
    SYNTAX IpAddress
    MAX-ACCESS accessible-for-notify
    STATUS current
    DESCRIPTION
        "Parameter 'source IP' in event BRS.10"
    ::= { brsEventObjects10 1 }

brs10-destination-IP OBJECT-TYPE
    SYNTAX IpAddress
    MAX-ACCESS accessible-for-notify
    STATUS current
    DESCRIPTION
        "Parameter 'destination IP' in event BRS.10"
    ::= { brsEventObjects10 2 }

brs10-class OBJECT-TYPE
    SYNTAX DisplayString
    MAX-ACCESS accessible-for-notify
    STATUS current
    DESCRIPTION
        "Parameter 'class' in event BRS.10"
    ::= { brsEventObjects10 3 }

brsEventObjects11 OBJECT-IDENTITY
    STATUS current
    DESCRIPTION
        "Event BRS.11
        A preclassified packet has been tagged with a new dscp value."
    ::= { brsEventsGroup 11 }

brs11-source-IP OBJECT-TYPE
    SYNTAX IpAddress
    MAX-ACCESS accessible-for-notify
    STATUS current
    DESCRIPTION
        "Parameter 'source IP' in event BRS.11"
    ::= { brsEventObjects11 1 }

brs11-destination-IP OBJECT-TYPE
    SYNTAX IpAddress
    MAX-ACCESS accessible-for-notify
    STATUS current
    DESCRIPTION
        "Parameter 'destination IP' in event BRS.11"
    ::= { brsEventObjects11 2 }

brs11-class OBJECT-TYPE
    SYNTAX DisplayString
    MAX-ACCESS accessible-for-notify
    STATUS current
    DESCRIPTION
        "Parameter 'class' in event BRS.11"
    ::= { brsEventObjects11 3 }

brs11-new-dscp-value OBJECT-TYPE
    SYNTAX Integer32
    MAX-ACCESS accessible-for-notify
    STATUS current
    DESCRIPTION
        "Parameter 'new dscp value' in event BRS.11"
    ::= { brsEventObjects11 4 }

brsEventObjects12 OBJECT-IDENTITY
    STATUS current
    DESCRIPTION
        "Event BRS.12
        A packet has been tagged with PTM low/high latency or low/high priority transmission preferred."
    ::= { brsEventsGroup 12 }

brs12-source-IP OBJECT-TYPE
    SYNTAX IpAddress
    MAX-ACCESS accessible-for-notify
    STATUS current
    DESCRIPTION
        "Parameter 'source IP' in event BRS.12"
    ::= { brsEventObjects12 1 }

brs12-destination-IP OBJECT-TYPE
    SYNTAX IpAddress
    MAX-ACCESS accessible-for-notify
    STATUS current
    DESCRIPTION
        "Parameter 'destination IP' in event BRS.12"
    ::= { brsEventObjects12 2 }

brs12-class OBJECT-TYPE
    SYNTAX DisplayString
    MAX-ACCESS accessible-for-notify
    STATUS current
    DESCRIPTION
        "Parameter 'class' in event BRS.12"
    ::= { brsEventObjects12 3 }

brs12-latency-priority OBJECT-TYPE
    SYNTAX DisplayString
    MAX-ACCESS accessible-for-notify
    STATUS current
    DESCRIPTION
        "Parameter 'latency/priority' in event BRS.12"
    ::= { brsEventObjects12 4 }

brsEventObjects13 OBJECT-IDENTITY
    STATUS current
    DESCRIPTION
        "Event BRS.13
        A level-indicator has been updated because a rate has been exceeded in a class"
    ::= { brsEventsGroup 13 }

brs13-levindid OBJECT-TYPE
    SYNTAX Integer32
    MAX-ACCESS accessible-for-notify
    STATUS current
    DESCRIPTION
        "Parameter 'levindid' in event BRS.13"
    ::= { brsEventObjects13 1 }

brs13-class OBJECT-TYPE
    SYNTAX DisplayString
    MAX-ACCESS accessible-for-notify
    STATUS current
    DESCRIPTION
        "Parameter 'class' in event BRS.13"
    ::= { brsEventObjects13 2 }

brs13-operation OBJECT-TYPE
    SYNTAX DisplayString
    MAX-ACCESS accessible-for-notify
    STATUS current
    DESCRIPTION
        "Parameter 'operation' in event BRS.13"
    ::= { brsEventObjects13 3 }

brs13-value OBJECT-TYPE
    SYNTAX Integer32
    MAX-ACCESS accessible-for-notify
    STATUS current
    DESCRIPTION
        "Parameter 'value' in event BRS.13"
    ::= { brsEventObjects13 4 }

brsEventObjects14 OBJECT-IDENTITY
    STATUS current
    DESCRIPTION
        "Event BRS.14
        A rate limit configured as percentage of available bandwidth of a interface
        has been recalculated for a traffic class."
    ::= { brsEventsGroup 14 }

brs14-rate OBJECT-TYPE
    SYNTAX Integer32
    MAX-ACCESS accessible-for-notify
    STATUS current
    DESCRIPTION
        "Parameter 'rate' in event BRS.14"
    ::= { brsEventObjects14 1 }

brs14-class OBJECT-TYPE
    SYNTAX DisplayString
    MAX-ACCESS accessible-for-notify
    STATUS current
    DESCRIPTION
        "Parameter 'class' in event BRS.14"
    ::= { brsEventObjects14 2 }

brs14-interface OBJECT-TYPE
    SYNTAX DisplayString
    MAX-ACCESS accessible-for-notify
    STATUS current
    DESCRIPTION
        "Parameter 'interface' in event BRS.14"
    ::= { brsEventObjects14 3 }

brsEventObjects15 OBJECT-IDENTITY
    STATUS current
    DESCRIPTION
        "Event BRS.15
        A rate limit configured as percentage of available bandwidth of a interface
        has been recalculated."
    ::= { brsEventsGroup 15 }

brs15-rate OBJECT-TYPE
    SYNTAX Integer32
    MAX-ACCESS accessible-for-notify
    STATUS current
    DESCRIPTION
        "Parameter 'rate' in event BRS.15"
    ::= { brsEventObjects15 1 }

brs15-interface OBJECT-TYPE
    SYNTAX DisplayString
    MAX-ACCESS accessible-for-notify
    STATUS current
    DESCRIPTION
        "Parameter 'interface' in event BRS.15"
    ::= { brsEventObjects15 2 }

brsEventObjects16 OBJECT-IDENTITY
    STATUS current
    DESCRIPTION
        "Event BRS.16
        Notifies on packet discarded because of class queue overflow."
    ::= { brsEventsGroup 16 }

brs16-msg-prot-type OBJECT-TYPE
    SYNTAX DisplayString
    MAX-ACCESS accessible-for-notify
    STATUS current
    DESCRIPTION
        "Parameter 'msg prot type' in event BRS.16"
    ::= { brsEventObjects16 1 }

brs16-class OBJECT-TYPE
    SYNTAX DisplayString
    MAX-ACCESS accessible-for-notify
    STATUS current
    DESCRIPTION
        "Parameter 'class' in event BRS.16"
    ::= { brsEventObjects16 2 }

brs16-queue-length OBJECT-TYPE
    SYNTAX Integer32
    MAX-ACCESS accessible-for-notify
    STATUS current
    DESCRIPTION
        "Parameter 'queue length' in event BRS.16"
    ::= { brsEventObjects16 3 }

brs16-interface OBJECT-TYPE
    SYNTAX DisplayString
    MAX-ACCESS accessible-for-notify
    STATUS current
    DESCRIPTION
        "Parameter 'interface' in event BRS.16"
    ::= { brsEventObjects16 4 }

brsEventObjects17 OBJECT-IDENTITY
    STATUS current
    DESCRIPTION
        "Event BRS.17
        A rate limit has been enabled or disabled for a class by a cellular link advisor"
    ::= { brsEventsGroup 17 }

brs17-technology OBJECT-TYPE
    SYNTAX Integer32
    MAX-ACCESS accessible-for-notify
    STATUS current
    DESCRIPTION
        "Parameter 'technology' in event BRS.17"
    ::= { brsEventObjects17 1 }

brs17-new-state OBJECT-TYPE
    SYNTAX DisplayString
    MAX-ACCESS accessible-for-notify
    STATUS current
    DESCRIPTION
        "Parameter 'new state' in event BRS.17"
    ::= { brsEventObjects17 2 }

brs17-class OBJECT-TYPE
    SYNTAX DisplayString
    MAX-ACCESS accessible-for-notify
    STATUS current
    DESCRIPTION
        "Parameter 'class' in event BRS.17"
    ::= { brsEventObjects17 3 }

brs17-interface OBJECT-TYPE
    SYNTAX DisplayString
    MAX-ACCESS accessible-for-notify
    STATUS current
    DESCRIPTION
        "Parameter 'interface' in event BRS.17"
    ::= { brsEventObjects17 4 }

brsEventObjects18 OBJECT-IDENTITY
    STATUS current
    DESCRIPTION
        "Event BRS.18
        Global rate limit has been enabled or disabled by a cellular link advisor"
    ::= { brsEventsGroup 18 }

brs18-technology OBJECT-TYPE
    SYNTAX Integer32
    MAX-ACCESS accessible-for-notify
    STATUS current
    DESCRIPTION
        "Parameter 'technology' in event BRS.18"
    ::= { brsEventObjects18 1 }

brs18-new-state OBJECT-TYPE
    SYNTAX DisplayString
    MAX-ACCESS accessible-for-notify
    STATUS current
    DESCRIPTION
        "Parameter 'new state' in event BRS.18"
    ::= { brsEventObjects18 2 }

brs18-interface OBJECT-TYPE
    SYNTAX DisplayString
    MAX-ACCESS accessible-for-notify
    STATUS current
    DESCRIPTION
        "Parameter 'interface' in event BRS.18"
    ::= { brsEventObjects18 3 }

brsEventObjects19 OBJECT-IDENTITY
    STATUS current
    DESCRIPTION
        "Event BRS.19
        Error has occurred when registering or unregistering a cellular advisor upcall"
    ::= { brsEventsGroup 19 }

brs19-register-action OBJECT-TYPE
    SYNTAX DisplayString
    MAX-ACCESS accessible-for-notify
    STATUS current
    DESCRIPTION
        "Parameter 'register action' in event BRS.19"
    ::= { brsEventObjects19 1 }

brs19-interface OBJECT-TYPE
    SYNTAX DisplayString
    MAX-ACCESS accessible-for-notify
    STATUS current
    DESCRIPTION
        "Parameter 'interface' in event BRS.19"
    ::= { brsEventObjects19 2 }


brsNotification1 NOTIFICATION-TYPE
    OBJECTS { 
              brs1-msg-prot-type, 
              brs1-class-name,
              brs1-interface 
            }
    STATUS current
    DESCRIPTION
        "Notification of Event BRS.1

        Message: 'protocol $1 is placed in class $2 interface $3'

        Parameters list:
              $1: brs1-msg-prot-type
              $2: brs1-class-name
              $3: brs1-interface

        A packet is placed in the class based on its protocol."
    ::= { brsNotificationsPrefix 1 }

brsNotification2 NOTIFICATION-TYPE
    OBJECTS { 
              brs2-msg-prot-type, 
              brs2-interface 
            }
    STATUS current
    DESCRIPTION
        "Notification of Event BRS.2

        Message: 'a packet of protocol $1 is discarded because of queue overflow on interface $2'

        Parameters list:
              $1: brs2-msg-prot-type
              $2: brs2-interface

        Notifies on all packet overflows."
    ::= { brsNotificationsPrefix 2 }

brsNotification3 NOTIFICATION-TYPE
    OBJECTS { 
              brs3-msg-prot-type, 
              brs3-interface 
            }
    STATUS current
    DESCRIPTION
        "Notification of Event BRS.3

        Message: 'a zero length packet of protocol $1 is discarded interface $2'

        Parameters list:
              $1: brs3-msg-prot-type
              $2: brs3-interface

        Message showed when zero length packets are dumped."
    ::= { brsNotificationsPrefix 3 }

brsNotification4 NOTIFICATION-TYPE
    OBJECTS { 
              brs4-class-name, 
              brs4-interface 
            }
    STATUS current
    DESCRIPTION
        "Notification of Event BRS.4

        Message: 'packet transmitted from class $1 interface $2'

        Parameters list:
              $1: brs4-class-name
              $2: brs4-interface

        A packet is placed from handler struct to driver queue
        to be transmitted."
    ::= { brsNotificationsPrefix 4 }

brsNotification5 NOTIFICATION-TYPE
    OBJECTS { 
              brs5-class, 
              brs5-interface,
              brs5-ticks-left 
            }
    STATUS current
    DESCRIPTION
        "Notification of Event BRS.5

        Message: 'class $1 congested interface $2 ticks to transmit $3'

        Parameters list:
              $1: brs5-class
              $2: brs5-interface
              $3: brs5-ticks-left

        No traffic-shape-group can transmit due to congestion."
    ::= { brsNotificationsPrefix 5 }

brsNotification6 NOTIFICATION-TYPE
    OBJECTS { 
              brs6-interface, 
              brs6-class,
              brs6-new-time,
              brs6-new-time-out,
              brs6-old-time,
              brs6-old-time-out 
            }
    STATUS current
    DESCRIPTION
        "Notification of Event BRS.6

        Message: 'timer launch interface $1 class $2 new time $3 new time-out $4 old time $5 old time-out $6'

        Parameters list:
              $1: brs6-interface
              $2: brs6-class
              $3: brs6-new-time
              $4: brs6-new-time-out
              $5: brs6-old-time
              $6: brs6-old-time-out

        A timer is launch to check for de-congestion of any class."
    ::= { brsNotificationsPrefix 6 }

brsNotification7 NOTIFICATION-TYPE
    OBJECTS { 
              brs7-interface 
            }
    STATUS current
    DESCRIPTION
        "Notification of Event BRS.7

        Message: 'time-out interface $1'

        Parameters list:
              $1: brs7-interface

        A timer has expired."
    ::= { brsNotificationsPrefix 7 }

brsNotification8 NOTIFICATION-TYPE
    OBJECTS { 
              brs8-source-IP, 
              brs8-destination-IP,
              brs8-class,
              brs8-new-dscp-value 
            }
    STATUS current
    DESCRIPTION
        "Notification of Event BRS.8

        Message: 'Packet from $1 to $2 class $3 tagged with $4'

        Parameters list:
              $1: brs8-source-IP
              $2: brs8-destination-IP
              $3: brs8-class
              $4: brs8-new-dscp-value

        A packet has been tagged with a new dscp value."
    ::= { brsNotificationsPrefix 8 }

brsNotification9 NOTIFICATION-TYPE
    OBJECTS { 
              brs9-source-IP, 
              brs9-destination-IP,
              brs9-class,
              brs9-new-cos-value 
            }
    STATUS current
    DESCRIPTION
        "Notification of Event BRS.9

        Message: 'Packet from $1 to $2 class $3 cos tagged with $4'

        Parameters list:
              $1: brs9-source-IP
              $2: brs9-destination-IP
              $3: brs9-class
              $4: brs9-new-cos-value

        A packet has been tagged with a new cos value."
    ::= { brsNotificationsPrefix 9 }

brsNotification10 NOTIFICATION-TYPE
    OBJECTS { 
              brs10-source-IP, 
              brs10-destination-IP,
              brs10-class 
            }
    STATUS current
    DESCRIPTION
        "Notification of Event BRS.10

        Message: 'Packet from $1 to $2 class $3 atm clp set'

        Parameters list:
              $1: brs10-source-IP
              $2: brs10-destination-IP
              $3: brs10-class

        A packet has been tagged with ATM CLP."
    ::= { brsNotificationsPrefix 10 }

brsNotification11 NOTIFICATION-TYPE
    OBJECTS { 
              brs11-source-IP, 
              brs11-destination-IP,
              brs11-class,
              brs11-new-dscp-value 
            }
    STATUS current
    DESCRIPTION
        "Notification of Event BRS.11

        Message: 'Preclassified packet from $1 to $2 class $3 tagged with $4'

        Parameters list:
              $1: brs11-source-IP
              $2: brs11-destination-IP
              $3: brs11-class
              $4: brs11-new-dscp-value

        A preclassified packet has been tagged with a new dscp value."
    ::= { brsNotificationsPrefix 11 }

brsNotification12 NOTIFICATION-TYPE
    OBJECTS { 
              brs12-source-IP, 
              brs12-destination-IP,
              brs12-class,
              brs12-latency-priority 
            }
    STATUS current
    DESCRIPTION
        "Notification of Event BRS.12

        Message: 'Packet from $1 to $2 class $3 ptm $4 set'

        Parameters list:
              $1: brs12-source-IP
              $2: brs12-destination-IP
              $3: brs12-class
              $4: brs12-latency-priority

        A packet has been tagged with PTM low/high latency or low/high priority transmission preferred."
    ::= { brsNotificationsPrefix 12 }

brsNotification13 NOTIFICATION-TYPE
    OBJECTS { 
              brs13-levindid, 
              brs13-class,
              brs13-operation,
              brs13-value 
            }
    STATUS current
    DESCRIPTION
        "Notification of Event BRS.13

        Message: 'Level-indicator id $1 associated to class $2 has been updated $3 $4'

        Parameters list:
              $1: brs13-levindid
              $2: brs13-class
              $3: brs13-operation
              $4: brs13-value

        A level-indicator has been updated because a rate has been exceeded in a class"
    ::= { brsNotificationsPrefix 13 }

brsNotification14 NOTIFICATION-TYPE
    OBJECTS { 
              brs14-rate, 
              brs14-class,
              brs14-interface 
            }
    STATUS current
    DESCRIPTION
        "Notification of Event BRS.14

        Message: 'new rate limit $1 kbps for class $2 in interface $3'

        Parameters list:
              $1: brs14-rate
              $2: brs14-class
              $3: brs14-interface

        A rate limit configured as percentage of available bandwidth of a interface
        has been recalculated for a traffic class."
    ::= { brsNotificationsPrefix 14 }

brsNotification15 NOTIFICATION-TYPE
    OBJECTS { 
              brs15-rate, 
              brs15-interface 
            }
    STATUS current
    DESCRIPTION
        "Notification of Event BRS.15

        Message: 'new global rate limit $1 kbps for interface $2'

        Parameters list:
              $1: brs15-rate
              $2: brs15-interface

        A rate limit configured as percentage of available bandwidth of a interface
        has been recalculated."
    ::= { brsNotificationsPrefix 15 }

brsNotification16 NOTIFICATION-TYPE
    OBJECTS { 
              brs16-msg-prot-type, 
              brs16-class,
              brs16-queue-length,
              brs16-interface 
            }
    STATUS current
    DESCRIPTION
        "Notification of Event BRS.16

        Message: 'discarded packet of protocol $1 in class $2 with queue length $3 because of overflow on interface $4'

        Parameters list:
              $1: brs16-msg-prot-type
              $2: brs16-class
              $3: brs16-queue-length
              $4: brs16-interface

        Notifies on packet discarded because of class queue overflow."
    ::= { brsNotificationsPrefix 16 }

brsNotification17 NOTIFICATION-TYPE
    OBJECTS { 
              brs17-technology, 
              brs17-new-state,
              brs17-class,
              brs17-interface 
            }
    STATUS current
    DESCRIPTION
        "Notification of Event BRS.17

        Message: 'cellualr technology $1 $2 rate limit for class $3 on interface $4'

        Parameters list:
              $1: brs17-technology
              $2: brs17-new-state
              $3: brs17-class
              $4: brs17-interface

        A rate limit has been enabled or disabled for a class by a cellular link advisor"
    ::= { brsNotificationsPrefix 17 }

brsNotification18 NOTIFICATION-TYPE
    OBJECTS { 
              brs18-technology, 
              brs18-new-state,
              brs18-interface 
            }
    STATUS current
    DESCRIPTION
        "Notification of Event BRS.18

        Message: 'cellular technology $1 $2 global rate limit on interface $3'

        Parameters list:
              $1: brs18-technology
              $2: brs18-new-state
              $3: brs18-interface

        Global rate limit has been enabled or disabled by a cellular link advisor"
    ::= { brsNotificationsPrefix 18 }

brsNotification19 NOTIFICATION-TYPE
    OBJECTS { 
              brs19-register-action, 
              brs19-interface 
            }
    STATUS current
    DESCRIPTION
        "Notification of Event BRS.19

        Message: 'cellular advisor upcall not $1 on base interface $2'

        Parameters list:
              $1: brs19-register-action
              $2: brs19-interface

        Error has occurred when registering or unregistering a cellular advisor upcall"
    ::= { brsNotificationsPrefix 19 }


END
