XYLAN-BASE-MIB DEFINITIONS ::= BEGIN

	--  RCSID information

	--  $RCSfile: xylan.mib,v $
	--  $Revision: 1.2 $		$State: Exp $
	--  $Date: 1999/04/08 17:23:42 $
	--  $Author: eszajner $


	--  Xylan.mib
	--  Revision: 1.00
	--  Date: June 9, 1994
        --  April 13 2000, bkesner added xylanASAArch PR 30988

	--  Alcatel Internetworking, Inc.
	--  26801 W. Agoura Road
	--  Calabasas, CA 91301
	--  (818) 880-3500
	--  support@ind.alcatel.com

	--  This module provides authoritative definitions for Alcatel Internetworking, Inc.
	--  Base MIB definitions

	--  This module will be extended, as needed.


	--  Alcatel Internetworking, Inc. reserves the right to make changes in
	--  specification and oher information contained in this document
	--  without prior notice.  The reader should consult Alcatel Internetworking,
	--  Inc. to determine whether any such changes have been made.
	--  Current MIBs are availible from the following URLs:
	--		ftp://ftp.ind.alcatel.com/pub/products/mibs
	--		http://www.ind.alcatel.com

	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1996, Alcatel Internetworking, Inc. All Rights Reserved.


	IMPORTS
		enterprises
			FROM RFC1155-SMI
			;


	-- EXPORTS
		-- xylan, xylanMgmt, xylanArch, xylanMib, xylanChassis,
		-- xylanVlanArch;


	xylan			OBJECT IDENTIFIER ::= { enterprises 800 }
	xylanMgmt		OBJECT IDENTIFIER ::= { xylan 1 }
	xylanArch		OBJECT IDENTIFIER ::= { xylan 2 }
	xylanProduct		OBJECT IDENTIFIER ::= { xylan 3 }
	xylanMib		OBJECT IDENTIFIER ::= { xylanMgmt 1 }
	xylanChassis		OBJECT IDENTIFIER ::= { xylanArch 1 }
	xylanVlanArch		OBJECT IDENTIFIER ::= { xylanArch 2 }
	xylanVportArch		OBJECT IDENTIFIER ::= { xylanArch 3 }
	xylanAtmArch		OBJECT IDENTIFIER ::= { xylanArch 4 }
	xylanTrapArch		OBJECT IDENTIFIER ::= { xylanArch 5 }
	xylanIpxArch		OBJECT IDENTIFIER ::= { xylanArch 6 }
	xylanWsmArch		OBJECT IDENTIFIER ::= { xylanArch 7 }
	xylanFrArch		OBJECT IDENTIFIER ::= { xylanArch 8 }
	xylanCsmArch		OBJECT IDENTIFIER ::= { xylanArch 9 }
	xylanVapArch		OBJECT IDENTIFIER ::= { xylanArch 10}
	xylanPportArch		OBJECT IDENTIFIER ::= { xylanArch 11}
	xylanFwArch		OBJECT IDENTIFIER ::= { xylanArch 12}
	xylanIpArch		OBJECT IDENTIFIER ::= { xylanArch 13}
	xylanIpmsArch		OBJECT IDENTIFIER ::= { xylanArch 14}
	xylanAVLArch 		OBJECT IDENTIFIER ::= { xylanArch 15}
	xylanBackupArch		OBJECT IDENTIFIER ::= { xylanArch 16}
	xylanPppArch		OBJECT IDENTIFIER ::= { xylanArch 17}
	xylanHealthArch		OBJECT IDENTIFIER ::= { xylanArch 18}
	xylanTsmArch		OBJECT IDENTIFIER ::= { xylanArch 19}
	xylanXIPArch		OBJECT IDENTIFIER ::= { xylanArch 20}
	xylanAscCArch		OBJECT IDENTIFIER ::= { xylanArch 21}
	xylanFltArch		OBJECT IDENTIFIER ::= { xylanArch 22}
	xylanSonetArch		OBJECT IDENTIFIER ::= { xylanArch 23}
	xylanSrtbArch		OBJECT IDENTIFIER ::= { xylanArch 24}
        xylanM013Arch           OBJECT IDENTIFIER ::= { xylanArch 25}
	xylanVsmArch            OBJECT IDENTIFIER ::= { xylanArch 26}
	xylanNtpArch            OBJECT IDENTIFIER ::= { xylanArch 27}
	xylanOamArch            OBJECT IDENTIFIER ::= { xylanArch 28}
	xylanMplsArch           OBJECT IDENTIFIER ::= { xylanArch 29}
	xylanRdArch             OBJECT IDENTIFIER ::= { xylanArch 30}
	xylanHrexArch           OBJECT IDENTIFIER ::= { xylanArch 31}
	xylanASAArch 		OBJECT IDENTIFIER ::= { xylanArch 32}
	xylanFrAtmArch          OBJECT IDENTIFIER ::= { xylanArch 33}
	
	xylanHardware		OBJECT IDENTIFIER ::= { xylanProduct 1 }
	
	xylanSwitchDevice	OBJECT IDENTIFIER ::= { xylanHardware 1 }
	xylanSwitchDevice2	OBJECT IDENTIFIER ::= { xylanHardware 2 }
	
	omniswitch5		OBJECT IDENTIFIER ::= { xylanSwitchDevice 1 }
	omniswitch9		OBJECT IDENTIFIER ::= { xylanSwitchDevice 2 }
	pizzaSwitch		OBJECT IDENTIFIER ::= { xylanSwitchDevice 3 }
	microSwitch		OBJECT IDENTIFIER ::= { xylanSwitchDevice 4 }
	omnicell5		OBJECT IDENTIFIER ::= { xylanSwitchDevice 5 }
	omnicell9		OBJECT IDENTIFIER ::= { xylanSwitchDevice 6 }
	pizzaPort		OBJECT IDENTIFIER ::= { xylanSwitchDevice 7 }
	omniStack1024		OBJECT IDENTIFIER ::= { xylanSwitchDevice 8 }
	omniStack6024		OBJECT IDENTIFIER ::= { xylanSwitchDevice 9 }
	omnicore13 		OBJECT IDENTIFIER ::= { xylanSwitchDevice 10 }
	omniAccess408		OBJECT IDENTIFIER ::= { xylanSwitchDevice 11 }
	omniAccess512		OBJECT IDENTIFIER ::= { xylanSwitchDevice 12 }
	omniStack8008		OBJECT IDENTIFIER ::= { xylanSwitchDevice 13 }
	omniStack6124		OBJECT IDENTIFIER ::= { xylanSwitchDevice 14 }
	omniStack6148		OBJECT IDENTIFIER ::= { xylanSwitchDevice 15 }
	omniStack5024		OBJECT IDENTIFIER ::= { xylanSwitchDevice 16 }
	omniStack4024		OBJECT IDENTIFIER ::= { xylanSwitchDevice 17 }
	
	xylanSoftware		OBJECT IDENTIFIER ::= { xylanProduct 2 }
	
	xylanPnni		OBJECT IDENTIFIER ::= { xylanSoftware 1 }
	xylanGated	  	OBJECT IDENTIFIER ::= { xylanSoftware 2 }
	xylanMrouted		OBJECT IDENTIFIER ::= { xylanSoftware 3 }
	xylanNHRP               OBJECT IDENTIFIER ::= { xylanSoftware 4 }
	xylanPolicy             OBJECT IDENTIFIER ::= { xylanSoftware 5 }

-- I needed to get the ATM Forum OIDs into xylan_mib.c
        atmForum 		OBJECT IDENTIFIER ::= { enterprises 353 }
	
-- for mpoa mpc dynamically binding. SPeng
        atmForumNetworkManagement OBJECT IDENTIFIER ::= { atmForum 5 }
        atmfLanEmulation	OBJECT IDENTIFIER ::= { atmForumNetworkManagement 3 }
	atmfPnni                OBJECT IDENTIFIER ::= { atmForumNetworkManagement 4 }	
        atmfMpoa 		OBJECT IDENTIFIER ::= { atmForumNetworkManagement 8 }
	mpoaMIB 		OBJECT IDENTIFIER ::= { atmfMpoa 1 }
	mpoaMIBObjects		OBJECT IDENTIFIER ::= { mpoaMIB 1 }
	mpoaCommonObjects	OBJECT IDENTIFIER ::= { mpoaMIBObjects 1 }
	mpcObjects		OBJECT IDENTIFIER ::= { mpoaMIBObjects 2 }
	mpsObjects		OBJECT IDENTIFIER ::= { mpoaMIBObjects 3 }

END
