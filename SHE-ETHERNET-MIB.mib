--
-- she-ethernet-mib.mib
-- MIB generated by MG-SOFT Visual MIB Builder Version 6.0  Build 88
-- Monday,  July 14,  2008 at 10:54:03
--

-- Start of ClearCase branch-information of current release:
-- she-ethernet-mib.mib   /main/she_main_grf/5
-- End of ClearCase branch-information.

	SHE-ETHERNET-MIB DEFINITIONS ::= BEGIN
 
		IMPORTS
			she			
				FROM AN-MIB			
			ifNumber,  ifIndex			
				FROM IF-MIB			
			SheControlStatusType,  SheEnableType			
				FROM SHE-TC-MIB			
			OBJECT-GROUP,  MODULE-COMPLIANCE,  NOTIFICATION-GROUP			
				FROM SNMPv2-CONF			
			Integer32,  Unsigned32,  Gauge32,  Counter32,  OBJECT-TYPE,  
			MODULE-IDENTITY,  NOTIFICATION-TYPE			
				FROM SNMPv2-SMI			
			TruthValue			
				FROM SNMPv2-TC;
	
	
--  1.3.6.1.4.1.231.7.1.2.2.1.5
		sheEthernetMib MODULE-IDENTITY 
			LAST-UPDATED "200807141000Z"		-- July 14,  2008 at 10:00 GMT
			ORGANIZATION 
				"Nokia Siemens Networks"
			CONTACT-INFO 
				"Gerd Barchmann
				COO BBA DSLAM RD SDE HW1
				
				+49 3834 555654
				gerd.barchmann@nsn.com"
			DESCRIPTION 
				"This MIB contains all ethernet specific configurations and informations.
				Some statistic counters from the Etherlike MIB are included."
			REVISION "200410151540Z"		-- October 15,  2004 at 15:40 GMT
			DESCRIPTION 
				"Add SheEthernetPortStandbyLaserOff and SheEthernetPortControlLaserOff"
			REVISION "200411091250Z"		-- November 09,  2004 at 12:50 GMT
			DESCRIPTION 
				"IUS_Release1"
			REVISION "200501101311Z"		-- January 10,  2005 at 13:11 GMT
			DESCRIPTION 
				"New Type SheEtnernetControlRequestResultType defined.
				Used for ReqResult in control group."
			REVISION "200501241140Z"		-- January 24,  2005 at 11:40 GMT
			DESCRIPTION 
				"Change Size-values for sheEthernetPortPhysicalRemoteChassis and
				sheEthernetPortPhysicalRemoteSlot and equivalent controlgroup-values."
			REVISION "200504211009Z"		-- April 21,  2005 at 10:09 GMT
			DESCRIPTION 
				"Correct typo in flowControl description.
				Change syntax for ...ControlTimeStamp."
			REVISION "200504271523Z"		-- April 27,  2005 at 15:23 GMT
			DESCRIPTION 
				"Restrict configuration of sheEthernetPortControlDuplexMode to full only.
				Add operstate down alarm trap."
			REVISION "200510130833Z"		-- October 13,  2005 at 08:33 GMT
			DESCRIPTION 
				"Delete not longer needed items:
				AlarmSeverity and OperStateDown-Alarm.
				Both will be handled by she-physical-mib."
			REVISION "200512011537Z"		-- December 01,  2005 at 15:37 GMT
			DESCRIPTION 
				"Correct ranges for sfp-data - could be empty if no sfp is plugged."
			REVISION "200602271326Z"		-- February 27,  2006 at 13:26 GMT
			DESCRIPTION 
				"Correct description for sheEthernetPortNegotiationMode."
			REVISION "200608221349Z"		-- August 22,  2006 at 13:49 GMT
			DESCRIPTION 
				"Take over by Gerd Barchmann for R2.5."
			REVISION "200611230816Z"		-- November 23,  2006 at 08:16 GMT
			DESCRIPTION 
				"Take corrections from SHE MIB release 155 for R2.0/R2.3."
			REVISION "200704261135Z"		-- April 26,  2007 at 11:35 GMT
			DESCRIPTION 
				"Correct usage of predefined type TruthValue."
			REVISION "200709191354Z"		-- September 19,  2007 at 13:54 GMT
			DESCRIPTION 
				"Add status attributes for SFP diagnostic values.
				Correct description for sheEthernetPortNegotiationMode."
			REVISION "200807141030Z"		-- July 14,  2008 at 10:30 GMT
			DESCRIPTION 
				"Modify possible range for Rate configuration."
			::= { she 5 }

		
	
--
-- Type definitions
--
	
-- This will descripe the used transeiver on the ethernet interface.
		SheEthernetPortType ::= INTEGER
			{
			unknown(0), 
			electrical(1), 
			optical(2)
			}

		SheEthernetDuplexType ::= INTEGER
			{
			full(1), 
			half(2), 
			notAvailable(3)
			}

		SheEthernetFlowControlType ::= INTEGER
			{
			notAvailable(0), 
			disabled(1), 
			enabledBoth(2), 
			enabledSymetrical(4), 
			enabledAsymetrical(8)
			}

		SheEthernetNegotiationModeType ::= INTEGER
			{
			auto(1), 
			force(2), 
			notAvailable(3)
			}

		SheEthernetTranseiverType ::= INTEGER
			{
			unknown(0), 
			electrical(1), 
			electricalCoaxial(2), 
			opticalLongHaul(3), 
			opticalShortHaul(4)
			}

		SheLinkDiscoveryModeType ::= INTEGER
			{
			none(1), 
			manual(2), 
			automatic(3)
			}

-- This type specifies the user commands (control requests)
-- from the TMN-OS or LCT and the results of user commands.
		SheEthernetControlRequestType ::= INTEGER
			{
			noRequest(1), 
			setEthernetPortConfiguration(101), 
			clearEthernetDot3StatsCounters(102), 
			setEthernetPortLinkDiscoveryValues(103), 
			setEthernetPortAlarmSeverityIndex(104), 
			setEthernetPortStandbyLaserOff(105), 
			setEthernetPortSwitchoverOnLinkDown(106)
			}

		SheEthernetControlRequestResultType ::= INTEGER
			{
			noRequest(1), 
			comExecStarted(30), 
			paramFaulty(31), 
			requestBusy(32), 
			setDataFailed(34), 
			aswTimeout(35), 
			commandFailed(36), 
			commandSucceeded(37)
			}

	
	
--
-- Node definitions
--
	
-- 1.3.6.1.4.1.231.7.1.2.2.1.5.1
		sheEthernet OBJECT IDENTIFIER ::= { sheEthernetMib 1 }

		
--   
-- 1.3.6.1.4.1.231.7.1.2.2.1.5.1.1
		sheEthernetPortTable OBJECT-TYPE
			SYNTAX SEQUENCE OF SheEthernetPortEntry
			MAX-ACCESS not-accessible
			STATUS current
			DESCRIPTION
				"The ethernet port table."
			::= { sheEthernet 1 }

		
--  1.3.6.1.4.1.231.7.1.2.2.1.5.1.1.1
		sheEthernetPortEntry OBJECT-TYPE
			SYNTAX SheEthernetPortEntry
			MAX-ACCESS not-accessible
			STATUS current
			DESCRIPTION
				"Each entry represents a physical ethernet interface. Index by ifIndex."
			INDEX { ifIndex }
			::= { sheEthernetPortTable 1 }

		
		SheEthernetPortEntry ::=
			SEQUENCE { 
				sheEthernetPortType
					SheEthernetPortType, 
				sheEthernetPortTransmissionRate
					Integer32, 
				sheEthernetPortDuplexMode
					SheEthernetDuplexType, 
				sheEthernetPortFlowControl
					SheEthernetFlowControlType, 
				sheEthernetPortNegotiationMode
					SheEthernetNegotiationModeType, 
				sheEthernetPortSfpTranseiver
					SheEthernetTranseiverType, 
				sheEthernetPortSfpVendorName
					OCTET STRING, 
				sheEthernetPortSfpVendorPartNumber
					OCTET STRING, 
				sheEthernetPortSfpVendorRevision
					OCTET STRING, 
				sheEthernetPortSfpVendorSerialNumber
					OCTET STRING, 
				sheEthernetPortSfpDateCode
					OCTET STRING, 
				sheEthernetPortPhysicalRemoteChassis
					OCTET STRING, 
				sheEthernetPortPhysicalRemoteSlot
					Integer32, 
				sheEthernetPortPhysicalRemotePort
					Integer32, 
				sheEthernetPortPhysicalLinkDiscoveryMode
					SheLinkDiscoveryModeType, 
				sheEthernetPortAlarmSeverityIndex
					Integer32, 
				sheEthernetPortStandbyLaserOff
					SheEnableType, 
				sheEthernetPortSwitchoverOnLinkDown
					TruthValue, 
				sheEthernetPortSfpDiagnosticValid
					TruthValue, 
				sheEthernetPortSfpTemperature
					INTEGER, 
				sheEthernetPortSfpSupplyVoltage
					Unsigned32, 
				sheEthernetPortSfpLaserBiasCurrent
					Unsigned32, 
				sheEthernetPortSfpTxPower
					Unsigned32, 
				sheEthernetPortSfpRxPower
					Unsigned32
			 }

--  1.3.6.1.4.1.231.7.1.2.2.1.5.1.1.1.2
		sheEthernetPortType OBJECT-TYPE
			SYNTAX SheEthernetPortType
			MAX-ACCESS read-only
			STATUS current
			DESCRIPTION
				"This value must always be configured. 
				SheEthernetPortType
				0 - unknown
				1 - electrical
				2 - optical
				
				Select the type of used interface."
			DEFVAL { 1 }
			::= { sheEthernetPortEntry 2 }

		
--  1.3.6.1.4.1.231.7.1.2.2.1.5.1.1.1.3
		sheEthernetPortTransmissionRate OBJECT-TYPE
			SYNTAX Integer32 (10 | 100 | 1000)
			UNITS "MBit/s"
			MAX-ACCESS read-only
			STATUS current
			DESCRIPTION
				"The speed of port. Unit is Mbit/s. 
				A modification is only useful for electrical-interfaces. 
				Optical-interfaces will always support 1000 MBIT/s."
			DEFVAL { 1000 }
			::= { sheEthernetPortEntry 3 }

		
--  1.3.6.1.4.1.231.7.1.2.2.1.5.1.1.1.4
		sheEthernetPortDuplexMode OBJECT-TYPE
			SYNTAX SheEthernetDuplexType
			MAX-ACCESS read-only
			STATUS current
			DESCRIPTION
				"The duplex status of port. The SHE will support always full duplex.
				SheEthernetDuplexType
				1 - full
				2 - half
				3 - notAvailable
				"
			DEFVAL { 1 }
			::= { sheEthernetPortEntry 4 }

		
--  1.3.6.1.4.1.231.7.1.2.2.1.5.1.1.1.5
		sheEthernetPortFlowControl OBJECT-TYPE
			SYNTAX SheEthernetFlowControlType
			MAX-ACCESS read-only
			STATUS current
			DESCRIPTION
				"The flow-control mode of port.
				SheEthernetFlowControlType
				0 - notAvailable 
				1 - disabled 
				2 - enabledBoth 
				4 - enabledSymetrical 
				8 - enabledAsymetrical  
				
				The Symetrical types are only useful for electrical GE."
			DEFVAL { 2 }
			::= { sheEthernetPortEntry 5 }

		
--  1.3.6.1.4.1.231.7.1.2.2.1.5.1.1.1.6
		sheEthernetPortNegotiationMode OBJECT-TYPE
			SYNTAX SheEthernetNegotiationModeType
			MAX-ACCESS read-only
			STATUS current
			DESCRIPTION
				"The Auto Negotiation mode of port. Default is auto.
				Speed will not be part of the autonegotiation.
				In case of Rate = 1000 and PortType = electrical, 
				the negotiation mode is always auto (default). 
				
				SheEthernetNegotiationType
				1 - auto
				2 - force
				3 - notAvailable"
			DEFVAL { auto }
			::= { sheEthernetPortEntry 6 }

		
--  1.3.6.1.4.1.231.7.1.2.2.1.5.1.1.1.7
		sheEthernetPortSfpTranseiver OBJECT-TYPE
			SYNTAX SheEthernetTranseiverType
			MAX-ACCESS read-only
			STATUS current
			DESCRIPTION
				"Code for electrical or optical compatibility. If 0 (unknown) maybe no SFP
				module is plugged and the following table values are not valid.
				For she only optical sfp-modules are allowed.
				SheEthernetTranseiverType
				0 - unknown
				1 - electrical (1000-T)
				2 - electricalCoaxial(1000-CX)
				3 - opticalLongHaul(1000-LX)
				4 - opticalShortHaul(1000-SX)
				"
			REFERENCE
				"according SFP transceiver MultiSource Agreement (MSA) table 3.1"
			DEFVAL { 0 }
			::= { sheEthernetPortEntry 7 }

		
-- 1.3.6.1.4.1.231.7.1.2.2.1.5.1.1.1.8
		sheEthernetPortSfpVendorName OBJECT-TYPE
			SYNTAX OCTET STRING (SIZE (0..16))
			MAX-ACCESS read-only
			STATUS current
			DESCRIPTION
				"Sfp transeiver vendor name (ASCII). 16 Byte."
			REFERENCE
				"according SFP transceiver MultiSource Agreement (MSA) table 3.1"
			::= { sheEthernetPortEntry 8 }

		
--  1.3.6.1.4.1.231.7.1.2.2.1.5.1.1.1.9
		sheEthernetPortSfpVendorPartNumber OBJECT-TYPE
			SYNTAX OCTET STRING (SIZE (0..16))
			MAX-ACCESS read-only
			STATUS current
			DESCRIPTION
				"Part number provided by SFP transeiver vendor (ASCII). 16 Byte."
			REFERENCE
				"according SFP transceiver MultiSource Agreement (MSA) table 3.1"
			::= { sheEthernetPortEntry 9 }

		
--  1.3.6.1.4.1.231.7.1.2.2.1.5.1.1.1.10
		sheEthernetPortSfpVendorRevision OBJECT-TYPE
			SYNTAX OCTET STRING (SIZE (0..4))
			MAX-ACCESS read-only
			STATUS current
			DESCRIPTION
				"Revision level for part number provided by vendor (ASCII). 4 Byte."
			REFERENCE
				"according SFP transceiver MultiSource Agreement (MSA) table 3.1"
			::= { sheEthernetPortEntry 10 }

		
--  1.3.6.1.4.1.231.7.1.2.2.1.5.1.1.1.11
		sheEthernetPortSfpVendorSerialNumber OBJECT-TYPE
			SYNTAX OCTET STRING (SIZE (0..16))
			MAX-ACCESS read-only
			STATUS current
			DESCRIPTION
				"Serial number provided by vendor (ASCII). 16 Byte."
			REFERENCE
				"according SFP transceiver MultiSource Agreement (MSA) table 3.1"
			::= { sheEthernetPortEntry 11 }

		
--  1.3.6.1.4.1.231.7.1.2.2.1.5.1.1.1.12
		sheEthernetPortSfpDateCode OBJECT-TYPE
			SYNTAX OCTET STRING (SIZE (0..8))
			MAX-ACCESS read-only
			STATUS current
			DESCRIPTION
				"Vendor's manufacturing date code (ASCII).
				2 Byte low order digit's for year (00=2000)
				2 Byte digits of month's (01=Jan ... 12=Dec)
				2 Byte day of month's (01..31)
				2 Byte vendor specific lot-code,  may be blank"
			REFERENCE
				"according SFP transceiver MultiSource Agreement (MSA) table 3.1"
			::= { sheEthernetPortEntry 12 }

		
--  1.3.6.1.4.1.231.7.1.2.2.1.5.1.1.1.13
		sheEthernetPortPhysicalRemoteChassis OBJECT-TYPE
			SYNTAX OCTET STRING (SIZE (0..4))
			MAX-ACCESS read-only
			STATUS current
			DESCRIPTION
				"Only used for Link Discovery. Set by operator. 
				No further meaning for the NE. IP Address of the remote NE."
			::= { sheEthernetPortEntry 13 }

		
--  1.3.6.1.4.1.231.7.1.2.2.1.5.1.1.1.14
		sheEthernetPortPhysicalRemoteSlot OBJECT-TYPE
			SYNTAX Integer32
			MAX-ACCESS read-only
			STATUS current
			DESCRIPTION
				"Only used for Link Discovery. Set by operator. 
				No further meaning for the NE."
			::= { sheEthernetPortEntry 14 }

		
--  1.3.6.1.4.1.231.7.1.2.2.1.5.1.1.1.15
		sheEthernetPortPhysicalRemotePort OBJECT-TYPE
			SYNTAX Integer32
			MAX-ACCESS read-only
			STATUS current
			DESCRIPTION
				"Only used for Link Discovery. Set by operator. 
				No further meaning for the NE."
			::= { sheEthernetPortEntry 15 }

		
--  1.3.6.1.4.1.231.7.1.2.2.1.5.1.1.1.16
		sheEthernetPortPhysicalLinkDiscoveryMode OBJECT-TYPE
			SYNTAX SheLinkDiscoveryModeType
			MAX-ACCESS read-only
			STATUS current
			DESCRIPTION
				"Only used for Link Discovery. Set by operator. 
				No further meaning for the NE. Automatic mode is not supported 
				by release 1.0."
			::= { sheEthernetPortEntry 16 }

		
--  1.3.6.1.4.1.231.7.1.2.2.1.5.1.1.1.17
		sheEthernetPortAlarmSeverityIndex OBJECT-TYPE
			SYNTAX Integer32 (1..10)
			MAX-ACCESS read-only
			STATUS current
			DESCRIPTION
				"Used alarm severity for this portentry."
			DEFVAL { 1 }
			::= { sheEthernetPortEntry 17 }

		
--  1.3.6.1.4.1.231.7.1.2.2.1.5.1.1.1.18
		sheEthernetPortStandbyLaserOff OBJECT-TYPE
			SYNTAX SheEnableType
			MAX-ACCESS read-only
			STATUS current
			DESCRIPTION
				"0 disable
				1 enable"
			DEFVAL { disable }
			::= { sheEthernetPortEntry 18 }

		
--  1.3.6.1.4.1.231.7.1.2.2.1.5.1.1.1.19
		sheEthernetPortSwitchoverOnLinkDown OBJECT-TYPE
			SYNTAX TruthValue
			MAX-ACCESS read-only
			STATUS current
			DESCRIPTION
				"A given port's link status is monitored. When link down for the port
				is detected,  switchover from an active board to a standby board is performed."
			DEFVAL { false }
			::= { sheEthernetPortEntry 19 }

		
-- 1.3.6.1.4.1.231.7.1.2.2.1.5.1.1.1.20
		sheEthernetPortSfpDiagnosticValid OBJECT-TYPE
			SYNTAX TruthValue
			MAX-ACCESS read-only
			STATUS current
			DESCRIPTION
				"If set,  the following corresponding status parameters are valid."
			DEFVAL { false }
			::= { sheEthernetPortEntry 20 }

		
--  1.3.6.1.4.1.231.7.1.2.2.1.5.1.1.1.21
		sheEthernetPortSfpTemperature OBJECT-TYPE
			SYNTAX INTEGER (-32767..32767)
			UNITS "1/256 oC"
			MAX-ACCESS read-only
			STATUS current
			DESCRIPTION
				"Internally measured transceiver temperature. Represented as a 16 bit signed twos
				complement value in increments of 1/256 degrees Celsius,  yielding a total range of -128C
				to +128C. Temperature accuracy is vendor specific but must be better than +/-3 degrees
				Celsius over specified operating temperature and voltage.The temperature in degrees Celsius
				is given by the signed twos complement value with LSB equal to 1/256 C.
				
				Coding examples:
				DECIMAL    HIGH BYTE    LOW BYTE
				+127.996   7F           FF
				+1.000     01           00
				+0.004     00           01
				-0.004     FF           FF
				-1.000     FF           00
				-127.996   80           01
				-128.000   80           00
				
				Only valid if sheEthernetPortSfpDiagnosticValid entry is true."
			REFERENCE
				"SFF 8472 table 3.17"
			::= { sheEthernetPortEntry 21 }

		
--  1.3.6.1.4.1.231.7.1.2.2.1.5.1.1.1.22
		sheEthernetPortSfpSupplyVoltage OBJECT-TYPE
			SYNTAX Unsigned32 (0..65535)
			UNITS "100 uV"
			MAX-ACCESS read-only
			STATUS current
			DESCRIPTION
				"Internally measured transceiver supply voltage. Represented as a 16 bit unsigned integer
				with the voltage defined as the full 16 bit value (0 .. 65535) with LSB equal to 100 uVolt, 
				yielding a total range of 0 to +6.55 Volts. Practical considerations to be defined by
				transceiver manufacturer will tend to limit the actual bounds of the supply voltage
				measurement. Accuracy is vendor specific but must be better than +/-3% of the
				manufacturer's nominal value over specified operating temperature and voltage. Note that
				in some transceivers,  transmitter supply voltage and receiver supply voltage are isolated.
				In that case,  only one supply is monitored.
				
				Only valid if sheEthernetPortSfpDiagnosticValid entry is true."
			REFERENCE
				"SFF 8472 table 3.17"
			::= { sheEthernetPortEntry 22 }

		
--  1.3.6.1.4.1.231.7.1.2.2.1.5.1.1.1.23
		sheEthernetPortSfpLaserBiasCurrent OBJECT-TYPE
			SYNTAX Unsigned32 (0..65535)
			UNITS "2 uA"
			MAX-ACCESS read-only
			STATUS current
			DESCRIPTION
				"Measured TX bias current in uA. Represented as a 16 bit unsigned integer with the current
				defined as the full 16 bit value (0 .. 65535) with LSB equal to 2 uA,  yielding a total range of
				0 to 131 mA. Accuracy is vendor specific but must be better than +/-10% of the
				manufacturer's nominal value over specified operating temperature and voltage.
				
				Only valid if sheEthernetPortSfpDiagnosticValid entry is true."
			REFERENCE
				"SFF 8472 table 3.17"
			::= { sheEthernetPortEntry 23 }

		
--  1.3.6.1.4.1.231.7.1.2.2.1.5.1.1.1.24
		sheEthernetPortSfpTxPower OBJECT-TYPE
			SYNTAX Unsigned32 (0..65535)
			UNITS "0.1 uW"
			MAX-ACCESS read-only
			STATUS current
			DESCRIPTION
				"Measured TX output power. Represented as a 16 bit unsigned integer with
				the power defined as the full 16 bit value (0 .. 65535) with LSB equal to 0.1 uW, 
				yielding a total range of 0 to 6.5535 mW (~ -40 to +8.2 dBm). Data is assumed to be
				based on measurement of laser monitor photodiode current. It is factory calibrated to
				absolute units using the most representative fiber output type. Accuracy is vendor
				specific but must be better than +/-3dB over specified temperature and voltage. Data
				is not valid when the transmitter is disabled.
				
				Only valid if sheEthernetPortSfpDiagnosticValid entry is true.
				"
			REFERENCE
				"SFF 8472 table 3.17"
			::= { sheEthernetPortEntry 24 }

		
--  1.3.6.1.4.1.231.7.1.2.2.1.5.1.1.1.25
		sheEthernetPortSfpRxPower OBJECT-TYPE
			SYNTAX Unsigned32 (0..65535)
			UNITS "0.1 uW"
			MAX-ACCESS read-only
			STATUS current
			DESCRIPTION
				"Measured RX received optical power.
				Represented as a 16 bit unsigned integer with the power defined as the full 16 bit
				value (0 .. 65535) with LSB equal to 0.1 uW,  yielding a total range of 0 to 6.5535
				mW (~ -40 to +8.2 dBm). Absolute accuracy is dependent upon the exact optical
				wavelength. For the vendor specified wavelength,  accuracy shall be better than
				+/-3dB over specified temperature and voltage. This accuracy shall be maintained for
				input power levels up to the lesser of maximum transmitted or maximum received
				optical power per the appropriate standard. It shall be maintained down to the
				minimum transmitted power minus cable plant loss (insertion loss or passive loss)
				per the appropriate standard. Absolute accuracy beyond this minimum required
				received input optical power range is vendor specific.
				
				Only valid if sheEthernetPortSfpDiagnosticValid entry is true."
			REFERENCE
				"SFF 8472 table 3.17"
			::= { sheEthernetPortEntry 25 }

		
--  1.3.6.1.4.1.231.7.1.2.2.1.5.1.3
		sheEthernetPortControl OBJECT IDENTIFIER ::= { sheEthernet 3 }

		
--  1.3.6.1.4.1.231.7.1.2.2.1.5.1.3.1
		sheEthernetPortControlRequest OBJECT-TYPE
			SYNTAX SheEthernetControlRequestType
			MAX-ACCESS read-write
			STATUS current
			DESCRIPTION
				"setEthernetPortConfiguration:
				sheEthernetPortControlIndex
				sheEthernetPortControlType
				sheEthernetPortControlRate
				sheEthernetPortControlDuplexMode
				sheEthernetPortControlFlowControl
				sheEthernetPortControlNegotiationMode
				
				clearEthernetDot3StatsCounters:
				sheEthernetPortControlIndex
				
				setEthernetPortLinkDiscoveryValues:
				sheEthernetPortControlIndex
				sheEthernetPortControlPhysicalRemoteChassis
				sheEthernetPortControlPhysicalRemoteSlot
				sheEthernetPortControlPhysicalRemotePort
				sheEthernetPortControlPhysicalLinkDiscoveryMode
				
				setEthernetPortStandbyLaserOff:
				sheEthernetPortControlIndex
				sheEthernetPortControlStandbyLaserOff
				
				setEthernetPortSwitchoverOnLinkDown:
				sheEthernetPortControlIndex
				sheEthernetPortControlSwitchoverOnLinkDown
				
				setEthernetPortAlarmSeverityIndex:
				sheEthernetPortControlIndex
				sheEthernetPortControlAlarmSeverityIndex"
			::= { sheEthernetPortControl 1 }

		
--  1.3.6.1.4.1.231.7.1.2.2.1.5.1.3.2
		sheEthernetPortControlIndex OBJECT-TYPE
			SYNTAX Integer32
			MAX-ACCESS read-write
			STATUS current
			DESCRIPTION
				"The index if the interface to be configured."
			::= { sheEthernetPortControl 2 }

		
--  1.3.6.1.4.1.231.7.1.2.2.1.5.1.3.3
		sheEthernetPortControlStatus OBJECT-TYPE
			SYNTAX SheControlStatusType
			MAX-ACCESS read-only
			STATUS current
			DESCRIPTION
				"Status of the user command"
			::= { sheEthernetPortControl 3 }

		
--  1.3.6.1.4.1.231.7.1.2.2.1.5.1.3.4
		sheEthernetPortControlTimer OBJECT-TYPE
			SYNTAX Gauge32
			MAX-ACCESS read-only
			STATUS current
			DESCRIPTION
				"The maximum wait time for the manager for a long running user command. 
				"
			::= { sheEthernetPortControl 4 }

		
--  1.3.6.1.4.1.231.7.1.2.2.1.5.1.3.5
		sheEthernetPortControlTimestamp OBJECT-TYPE
			SYNTAX Unsigned32
			UNITS "sec"
			MAX-ACCESS read-only
			STATUS current
			DESCRIPTION
				"Time stamp attribute set at the end of a command."
			::= { sheEthernetPortControl 5 }

		
--  1.3.6.1.4.1.231.7.1.2.2.1.5.1.3.6
		sheEthernetPortControlReqResult OBJECT-TYPE
			SYNTAX SheEthernetControlRequestResultType
			MAX-ACCESS read-only
			STATUS current
			DESCRIPTION
				"The result of the last user command."
			::= { sheEthernetPortControl 6 }

		
--  1.3.6.1.4.1.231.7.1.2.2.1.5.1.3.7
		sheEthernetPortControlType OBJECT-TYPE
			SYNTAX SheEthernetPortType (1 | 2)
			MAX-ACCESS read-write
			STATUS current
			DESCRIPTION
				"Select the type of used interface.
				SheEthernetPortType
				1 - electrical
				2 - optical"
			::= { sheEthernetPortControl 7 }

		
--  1.3.6.1.4.1.231.7.1.2.2.1.5.1.3.8
		sheEthernetPortControlRate OBJECT-TYPE
			SYNTAX Integer32 (10 | 100 | 1000)
			MAX-ACCESS read-write
			STATUS current
			DESCRIPTION
				"Used Datarate.
				This configuration is only useful for electrical-interfaces. 
				Optical-interfaces will always support 1000 MBIT/s."
			::= { sheEthernetPortControl 8 }

		
--   
-- 1.3.6.1.4.1.231.7.1.2.2.1.5.1.3.9
		sheEthernetPortControlDuplexMode OBJECT-TYPE
			SYNTAX SheEthernetDuplexType (1)
			MAX-ACCESS read-write
			STATUS current
			DESCRIPTION
				"Used DuplexMode."
			::= { sheEthernetPortControl 9 }

		
--  1.3.6.1.4.1.231.7.1.2.2.1.5.1.3.10
		sheEthernetPortControlFlowControl OBJECT-TYPE
			SYNTAX SheEthernetFlowControlType (1 | 2)
			MAX-ACCESS read-write
			STATUS current
			DESCRIPTION
				"Used FlowControl-value."
			::= { sheEthernetPortControl 10 }

		
--  1.3.6.1.4.1.231.7.1.2.2.1.5.1.3.11
		sheEthernetPortControlNegotiationMode OBJECT-TYPE
			SYNTAX SheEthernetNegotiationModeType (1 | 2)
			MAX-ACCESS read-write
			STATUS current
			DESCRIPTION
				"Used Negotiation mode."
			::= { sheEthernetPortControl 11 }

		
--  1.3.6.1.4.1.231.7.1.2.2.1.5.1.3.12
		sheEthernetPortControlPhysicalRemoteChassis OBJECT-TYPE
			SYNTAX OCTET STRING (SIZE (4))
			MAX-ACCESS read-write
			STATUS current
			DESCRIPTION
				"Set RemoteCassis-Information."
			::= { sheEthernetPortControl 12 }

		
--  1.3.6.1.4.1.231.7.1.2.2.1.5.1.3.13
		sheEthernetPortControlPhysicalRemoteSlot OBJECT-TYPE
			SYNTAX Integer32
			MAX-ACCESS read-write
			STATUS current
			DESCRIPTION
				"Set RemoteSlot-Information."
			::= { sheEthernetPortControl 13 }

		
--  1.3.6.1.4.1.231.7.1.2.2.1.5.1.3.14
		sheEthernetPortControlPhysicalRemotePort OBJECT-TYPE
			SYNTAX Integer32
			MAX-ACCESS read-write
			STATUS current
			DESCRIPTION
				"Set RemotePort-Information."
			::= { sheEthernetPortControl 14 }

		
--  1.3.6.1.4.1.231.7.1.2.2.1.5.1.3.15
		sheEthernetPortControlPhysicalLinkDiscoveryMode OBJECT-TYPE
			SYNTAX SheLinkDiscoveryModeType
			MAX-ACCESS read-write
			STATUS current
			DESCRIPTION
				"Set mode of Remote-Information retrieval."
			::= { sheEthernetPortControl 15 }

		
--  1.3.6.1.4.1.231.7.1.2.2.1.5.1.3.16
		sheEthernetPortControlAlarmSeverityIndex OBJECT-TYPE
			SYNTAX Integer32 (1..10)
			MAX-ACCESS read-write
			STATUS current
			DESCRIPTION
				"Set alarm severity for this portentry."
			::= { sheEthernetPortControl 16 }

		
--  1.3.6.1.4.1.231.7.1.2.2.1.5.1.3.17
		sheEthernetPortControlStandbyLaserOff OBJECT-TYPE
			SYNTAX SheEnableType
			MAX-ACCESS read-write
			STATUS current
			DESCRIPTION
				"."
			::= { sheEthernetPortControl 17 }

		
--  1.3.6.1.4.1.231.7.1.2.2.1.5.1.3.18
		sheEthernetPortControlSwitchoverOnLinkDown OBJECT-TYPE
			SYNTAX TruthValue
			MAX-ACCESS read-write
			STATUS current
			DESCRIPTION
				"A given port's link status is monitored. When link down for the port
				is detected,  switchover from an active board to a standby board is performed."
			::= { sheEthernetPortControl 18 }

		
--  1.3.6.1.4.1.231.7.1.2.2.1.5.1.4
		sheDot3StatsTable OBJECT-TYPE
			SYNTAX SEQUENCE OF SheDot3StatsEntry
			MAX-ACCESS not-accessible
			STATUS current
			DESCRIPTION
				"From the Etherlike-Mib."
			::= { sheEthernet 4 }

		
--  1.3.6.1.4.1.231.7.1.2.2.1.5.1.4.1
		sheDot3StatsEntry OBJECT-TYPE
			SYNTAX SheDot3StatsEntry
			MAX-ACCESS not-accessible
			STATUS current
			DESCRIPTION
				"One entry per physical ethernet interface. Index is ifIndex."
			INDEX { ifIndex }
			::= { sheDot3StatsTable 1 }

		
		SheDot3StatsEntry ::=
			SEQUENCE { 
				sheDot3StatsAlignmentErrors
					Counter32, 
				sheDot3StatsFCSErrors
					Counter32, 
				sheDot3StatsSingleCollisionFrames
					Counter32, 
				sheDot3StatsMultipleCollisionFrames
					Counter32, 
				sheDot3StatsSQETestErrors
					Counter32, 
				sheDot3StatsDeferredTransmissions
					Counter32, 
				sheDot3StatsLateCollisions
					Counter32, 
				sheDot3StatsExcessiveCollisions
					Counter32, 
				sheDot3StatsInternalMacTransmitErrors
					Counter32, 
				sheDot3StatsCarrierSenseErrors
					Counter32, 
				sheDot3StatsFrameTooLongs
					Counter32, 
				sheDot3StatsInternalMacReceiveErrors
					Counter32, 
				sheDot3StatsSymbolErrors
					Counter32
			 }

--  1.3.6.1.4.1.231.7.1.2.2.1.5.1.4.1.2
		sheDot3StatsAlignmentErrors OBJECT-TYPE
			SYNTAX Counter32
			MAX-ACCESS read-only
			STATUS current
			DESCRIPTION
				"A count of frames received on a particular
				interface that are not an integral number of
				octets in length and do not pass the FCS check.
				
				The count represented by an instance of this
				object is incremented when the alignmentError
				status is returned by the MAC service to the
				LLC (or other MAC user). Received frames for
				which multiple error conditions obtain are, 
				according to the conventions of IEEE 802.3
				Layer Management,  counted exclusively according
				to the error status presented to the LLC."
			::= { sheDot3StatsEntry 2 }

		
--  1.3.6.1.4.1.231.7.1.2.2.1.5.1.4.1.3
		sheDot3StatsFCSErrors OBJECT-TYPE
			SYNTAX Counter32
			MAX-ACCESS read-only
			STATUS current
			DESCRIPTION
				"A count of frames received on a particular
				interface that are an integral number of octets
				in length but do not pass the FCS check.
				
				The count represented by an instance of this
				object is incremented when the frameCheckError
				status is returned by the MAC service to the
				LLC (or other MAC user). Received frames for
				which multiple error conditions obtain are, 
				according to the conventions of IEEE 802.3
				Layer Management,  counted exclusively according
				to the error status presented to the LLC."
			::= { sheDot3StatsEntry 3 }

		
--  1.3.6.1.4.1.231.7.1.2.2.1.5.1.4.1.4
		sheDot3StatsSingleCollisionFrames OBJECT-TYPE
			SYNTAX Counter32
			MAX-ACCESS read-only
			STATUS current
			DESCRIPTION
				"A count of successfully transmitted frames on
				a particular interface for which transmission
				is inhibited by exactly one collision.
				
				A frame that is counted by an instance of this
				object is also counted by the corresponding
				instance of either the ifOutUcastPkts, 
				ifOutMulticastPkts,  or ifOutBroadcastPkts, 
				and is not counted by the corresponding
				instance of the dot3StatsMultipleCollisionFrames
				object."
			::= { sheDot3StatsEntry 4 }

		
--  1.3.6.1.4.1.231.7.1.2.2.1.5.1.4.1.5
		sheDot3StatsMultipleCollisionFrames OBJECT-TYPE
			SYNTAX Counter32
			MAX-ACCESS read-only
			STATUS current
			DESCRIPTION
				"A count of successfully transmitted frames on
				a particular interface for which transmission
				 is inhibited by more than one collision.
				
				A frame that is counted by an instance of this
				object is also counted by the corresponding
				instance of either the ifOutUcastPkts, 
				ifOutMulticastPkts,  or ifOutBroadcastPkts, 
				and is not counted by the corresponding
				instance of the dot3StatsSingleCollisionFrames
				object."
			::= { sheDot3StatsEntry 5 }

		
--  1.3.6.1.4.1.231.7.1.2.2.1.5.1.4.1.6
		sheDot3StatsSQETestErrors OBJECT-TYPE
			SYNTAX Counter32
			MAX-ACCESS read-only
			STATUS current
			DESCRIPTION
				"A count of times that the SQE TEST ERROR
				message is generated by the PLS sublayer for a
				particular interface. The SQE TEST ERROR
				message is defined in section 7.2.2.2.4 of
				ANSI/IEEE 802.3-1985 and its generation is
				described in section 7.2.4.6 of the same
				document."
			::= { sheDot3StatsEntry 6 }

		
--  1.3.6.1.4.1.231.7.1.2.2.1.5.1.4.1.7
		sheDot3StatsDeferredTransmissions OBJECT-TYPE
			SYNTAX Counter32
			MAX-ACCESS read-only
			STATUS current
			DESCRIPTION
				"A count of frames for which the first
				transmission attempt on a particular interface
				is delayed because the medium is busy.
				
				The count represented by an instance of this
				object does not include frames involved in
				collisions."
			::= { sheDot3StatsEntry 7 }

		
--  1.3.6.1.4.1.231.7.1.2.2.1.5.1.4.1.8
		sheDot3StatsLateCollisions OBJECT-TYPE
			SYNTAX Counter32
			MAX-ACCESS read-only
			STATUS current
			DESCRIPTION
				"The number of times that a collision is
				detected on a particular interface later than
				512 bit-times into the transmission of a
				packet.
				
				Five hundred and twelve bit-times corresponds
				to 51.2 microseconds on a 10 Mbit/s system. A
				(late) collision included in a count
				represented by an instance of this object is
				also considered as a (generic) collision for
				purposes of other collision-related
				statistics."
			::= { sheDot3StatsEntry 8 }

		
--  1.3.6.1.4.1.231.7.1.2.2.1.5.1.4.1.9
		sheDot3StatsExcessiveCollisions OBJECT-TYPE
			SYNTAX Counter32
			MAX-ACCESS read-only
			STATUS current
			DESCRIPTION
				"A count of frames for which transmission on a
				particular interface fails due to excessive
				collisions."
			::= { sheDot3StatsEntry 9 }

		
--  1.3.6.1.4.1.231.7.1.2.2.1.5.1.4.1.10
		sheDot3StatsInternalMacTransmitErrors OBJECT-TYPE
			SYNTAX Counter32
			MAX-ACCESS read-only
			STATUS current
			DESCRIPTION
				"A count of frames for which transmission on a
				particular interface fails due to an internal
				MAC sublayer transmit error. A frame is only
				counted by an instance of this object if it is
				not counted by the corresponding instance of
				either the dot3StatsLateCollisions object,  the
				dot3StatsExcessiveCollisions object,  or the
				dot3StatsCarrierSenseErrors object.
				
				The precise meaning of the count represented by
				an instance of this object is implementation-
				specific.  In particular,  an instance of this
				object may represent a count of transmission
				errors on a particular interface that are not
				otherwise counted."
			::= { sheDot3StatsEntry 10 }

		
--  1.3.6.1.4.1.231.7.1.2.2.1.5.1.4.1.11
		sheDot3StatsCarrierSenseErrors OBJECT-TYPE
			SYNTAX Counter32
			MAX-ACCESS read-only
			STATUS current
			DESCRIPTION
				"The number of times that the carrier sense
				condition was lost or never asserted when
				attempting to transmit a frame on a particular
				interface.
				
				The count represented by an instance of this
				object is incremented at most once per
				transmission attempt,  even if the carrier sense
				condition fluctuates during a transmission
				attempt."
			::= { sheDot3StatsEntry 11 }

		
--  1.3.6.1.4.1.231.7.1.2.2.1.5.1.4.1.12
		sheDot3StatsFrameTooLongs OBJECT-TYPE
			SYNTAX Counter32
			MAX-ACCESS read-only
			STATUS current
			DESCRIPTION
				"A count of frames received on a particular
				interface that exceed the maximum permitted
				frame size.
				
				The count represented by an instance of this
				object is incremented when the frameTooLong
				status is returned by the MAC service to the
				LLC (or other MAC user). Received frames for
				which multiple error conditions obtain are, 
				according to the conventions of IEEE 802.3
				Layer Management,  counted exclusively according
				to the error status presented to the LLC."
			::= { sheDot3StatsEntry 12 }

		
--  1.3.6.1.4.1.231.7.1.2.2.1.5.1.4.1.13
		sheDot3StatsInternalMacReceiveErrors OBJECT-TYPE
			SYNTAX Counter32
			MAX-ACCESS read-only
			STATUS current
			DESCRIPTION
				"A count of frames for which reception on a
				particular interface fails due to an internal
				MAC sublayer receive error. A frame is only
				counted by an instance of this object if it is
				not counted by the corresponding instance of
				either the dot3StatsFrameTooLongs object,  the
				dot3StatsAlignmentErrors object,  or the
				dot3StatsFCSErrors object.
				
				The precise meaning of the count represented by
				an instance of this object is implementation-
				specific.  In particular,  an instance of this
				object may represent a count of receive errors
				on a particular interface that are not
				otherwise counted."
			::= { sheDot3StatsEntry 13 }

		
--   
-- 1.3.6.1.4.1.231.7.1.2.2.1.5.1.4.1.14
		sheDot3StatsSymbolErrors OBJECT-TYPE
			SYNTAX Counter32
			MAX-ACCESS read-only
			STATUS current
			DESCRIPTION
				"Symbol error."
			::= { sheDot3StatsEntry 14 }

		
--   
-- 1.3.6.1.4.1.231.7.1.2.2.1.5.1.5
		sheEthernetNotifications OBJECT IDENTIFIER ::= { sheEthernet 5 }

		
--  1.3.6.1.4.1.231.7.1.2.2.1.5.1.5.1
		sheEthernetPortConfigurationChanged NOTIFICATION-TYPE
			OBJECTS { sheEthernetPortControlIndex,  sheEthernetPortControlTimestamp,  sheEthernetPortControlType,  sheEthernetPortControlRate,  sheEthernetPortControlDuplexMode,  
				sheEthernetPortControlFlowControl,  sheEthernetPortControlNegotiationMode,  sheEthernetPortControlAlarmSeverityIndex }
			STATUS current
			DESCRIPTION 
				"Port configuration notification."
			::= { sheEthernetNotifications 1 }

		
--  1.3.6.1.4.1.231.7.1.2.2.1.5.1.5.2
		sheEthernetPortSfpDataChanged NOTIFICATION-TYPE
			OBJECTS { ifIndex,  sheEthernetPortSfpTranseiver,  sheEthernetPortSfpVendorName,  sheEthernetPortSfpVendorPartNumber,  sheEthernetPortSfpVendorRevision,  
				sheEthernetPortSfpVendorSerialNumber,  sheEthernetPortSfpDateCode }
			STATUS current
			DESCRIPTION 
				"Port data change notification."
			::= { sheEthernetNotifications 2 }

		
--  1.3.6.1.4.1.231.7.1.2.2.1.5.1.5.3
		sheEthernetDot3StatsCountersCleared NOTIFICATION-TYPE
			OBJECTS { ifNumber }
			STATUS current
			DESCRIPTION 
				"Command execution notification."
			::= { sheEthernetNotifications 3 }

		
--  1.3.6.1.4.1.231.7.1.2.2.1.5.1.5.4
		sheEthernetPortLinkDiscoveryValuesChanged NOTIFICATION-TYPE
			OBJECTS { sheEthernetPortControlIndex,  sheEthernetPortControlTimestamp,  sheEthernetPortControlPhysicalRemoteChassis,  sheEthernetPortControlPhysicalRemoteSlot,  sheEthernetPortControlPhysicalRemotePort,  
				sheEthernetPortControlPhysicalLinkDiscoveryMode }
			STATUS current
			DESCRIPTION 
				"Port configuration notification."
			::= { sheEthernetNotifications 4 }

		
--  1.3.6.1.4.1.231.7.1.2.2.1.5.1.5.6
		sheEthernetPortStandbyLaserOffChanged NOTIFICATION-TYPE
			OBJECTS { sheEthernetPortControlIndex,  sheEthernetPortControlTimestamp,  sheEthernetPortControlStandbyLaserOff }
			STATUS current
			DESCRIPTION 
				"Port configuration notification."
			::= { sheEthernetNotifications 6 }

		
--  1.3.6.1.4.1.231.7.1.2.2.1.5.1.5.6
		sheEthernetPortSwitchoverOnLinkDownChanged NOTIFICATION-TYPE
			OBJECTS { sheEthernetPortControlIndex,  sheEthernetPortControlTimestamp,  sheEthernetPortControlSwitchoverOnLinkDown }
			STATUS current
			DESCRIPTION 
				"sheEthernetPortControlSwitchoverOnLinkDown has been changed."
			::= { sheEthernetNotifications 7 }

		
--  1.3.6.1.4.1.231.7.1.2.2.1.5.1.6
		sheEthernetConformance OBJECT IDENTIFIER ::= { sheEthernet 100 }

		
--   
-- 1.3.6.1.4.1.231.7.1.2.2.1.5.1.6.1
		sheEthernetCompliances OBJECT IDENTIFIER ::= { sheEthernetConformance 1 }

		
--  1.3.6.1.4.1.231.7.1.2.2.1.5.1.6.1.1
-- this module
		sheEthernetCompliance MODULE-COMPLIANCE
			STATUS current
			DESCRIPTION 
				"Description."
			MODULE -- this module
				MANDATORY-GROUPS { sheEthernetPortGroup,  sheEthernetControlGroup,  sheEthernetStatsGroup,  sheEthernetNotificationGroup }
			::= { sheEthernetCompliances 1 }

		
--  1.3.6.1.4.1.231.7.1.2.2.1.5.1.6.2
		sheEthernetGroups OBJECT IDENTIFIER ::= { sheEthernetConformance 2 }

		
--  1.3.6.1.4.1.231.7.1.2.2.1.5.1.6.2.1
		sheEthernetPortGroup OBJECT-GROUP
			OBJECTS { sheEthernetPortType,  sheEthernetPortTransmissionRate,  sheEthernetPortDuplexMode,  sheEthernetPortFlowControl,  sheEthernetPortNegotiationMode,  
				sheEthernetPortSfpTranseiver,  sheEthernetPortSfpVendorName,  sheEthernetPortSfpVendorPartNumber,  sheEthernetPortSfpVendorRevision,  sheEthernetPortSfpVendorSerialNumber,  
				sheEthernetPortPhysicalRemoteChassis,  sheEthernetPortPhysicalRemoteSlot,  sheEthernetPortPhysicalRemotePort,  sheEthernetPortStandbyLaserOff,  sheEthernetPortSwitchoverOnLinkDown,  
				sheEthernetPortAlarmSeverityIndex,  sheEthernetPortSfpTxPower,  sheEthernetPortSfpRxPower,  sheEthernetPortSfpTemperature,  sheEthernetPortSfpSupplyVoltage,  
				sheEthernetPortSfpLaserBiasCurrent,  sheEthernetPortSfpDiagnosticValid,  sheEthernetPortPhysicalLinkDiscoveryMode,  sheEthernetPortSfpDateCode }
			STATUS current
			DESCRIPTION 
				"Description."
			::= { sheEthernetGroups 1 }

		
--  1.3.6.1.4.1.231.7.1.2.2.1.5.1.6.2.2
		sheEthernetControlGroup OBJECT-GROUP
			OBJECTS { sheEthernetPortControlRequest,  sheEthernetPortControlIndex,  sheEthernetPortControlStatus,  sheEthernetPortControlType,  sheEthernetPortControlRate,  
				sheEthernetPortControlDuplexMode,  sheEthernetPortControlFlowControl,  sheEthernetPortControlPhysicalRemoteChassis,  sheEthernetPortControlPhysicalRemoteSlot,  sheEthernetPortControlPhysicalRemotePort,  
				sheEthernetPortControlPhysicalLinkDiscoveryMode,  sheEthernetPortControlTimestamp,  sheEthernetPortControlStandbyLaserOff,  sheEthernetPortControlSwitchoverOnLinkDown,  sheEthernetPortControlAlarmSeverityIndex,  
				sheEthernetPortControlNegotiationMode,  sheEthernetPortControlTimer,  sheEthernetPortControlReqResult }
			STATUS current
			DESCRIPTION 
				"Description."
			::= { sheEthernetGroups 2 }

		
--  1.3.6.1.4.1.231.7.1.2.2.1.5.1.6.2.3
		sheEthernetStatsGroup OBJECT-GROUP
			OBJECTS { sheDot3StatsAlignmentErrors,  sheDot3StatsFCSErrors,  sheDot3StatsSingleCollisionFrames,  sheDot3StatsMultipleCollisionFrames,  sheDot3StatsSQETestErrors,  
				sheDot3StatsDeferredTransmissions,  sheDot3StatsLateCollisions,  sheDot3StatsExcessiveCollisions,  sheDot3StatsInternalMacTransmitErrors,  sheDot3StatsCarrierSenseErrors,  
				sheDot3StatsFrameTooLongs,  sheDot3StatsInternalMacReceiveErrors,  sheDot3StatsSymbolErrors }
			STATUS current
			DESCRIPTION 
				"Description."
			::= { sheEthernetGroups 3 }

		
--  1.3.6.1.4.1.231.7.1.2.2.1.5.1.6.2.4
		sheEthernetNotificationGroup NOTIFICATION-GROUP
			NOTIFICATIONS { sheEthernetPortConfigurationChanged,  sheEthernetDot3StatsCountersCleared,  sheEthernetPortStandbyLaserOffChanged,  sheEthernetPortSwitchoverOnLinkDownChanged,  sheEthernetPortLinkDiscoveryValuesChanged,  
				sheEthernetPortSfpDataChanged }
			STATUS current
			DESCRIPTION 
				"Description."
			::= { sheEthernetGroups 4 }

		
	
	END

--
-- she-ethernet-mib.mib
--
