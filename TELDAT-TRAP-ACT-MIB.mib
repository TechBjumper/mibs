-- file automatically created


TELDAT-TRAP-ACT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


actTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ACT event subsystem."
    REVISION "201401200930Z"
    DESCRIPTION "Initial implementation"
        ::= { telEventTraps 245 }


actEventsGroup	OBJECT IDENTIFIER	::= { actTrapsMIB 1 }

actNotifications	OBJECT IDENTIFIER	::= { actTrapsMIB 2 }
actNotificationsPrefix	OBJECT IDENTIFIER	::= { actNotifications 0 }

actEventObjects1 OBJECT-IDENTITY
    STATUS current
    DESCRIPTION
        "Event ACT.1
        Sending custom trap to management station"
    ::= { actEventsGroup 1 }

act1-pppip OBJECT-TYPE
    SYNTAX IpAddress
    MAX-ACCESS accessible-for-notify
    STATUS current
    DESCRIPTION
        "Parameter 'pppip' in event ACT.1"
    ::= { actEventObjects1 1 }

act1-connectiondate OBJECT-TYPE
    SYNTAX DisplayString
    MAX-ACCESS accessible-for-notify
    STATUS current
    DESCRIPTION
        "Parameter 'connectiondate' in event ACT.1"
    ::= { actEventObjects1 2 }

act1-serialnumber OBJECT-TYPE
    SYNTAX DisplayString
    MAX-ACCESS accessible-for-notify
    STATUS current
    DESCRIPTION
        "Parameter 'serialnumber' in event ACT.1"
    ::= { actEventObjects1 3 }

act1-hostname OBJECT-TYPE
    SYNTAX DisplayString
    MAX-ACCESS accessible-for-notify
    STATUS current
    DESCRIPTION
        "Parameter 'hostname' in event ACT.1"
    ::= { actEventObjects1 4 }

act1-imsi OBJECT-TYPE
    SYNTAX DisplayString
    MAX-ACCESS accessible-for-notify
    STATUS current
    DESCRIPTION
        "Parameter 'imsi' in event ACT.1"
    ::= { actEventObjects1 5 }

act1-wlanstations OBJECT-TYPE
    SYNTAX Integer32
    MAX-ACCESS accessible-for-notify
    STATUS current
    DESCRIPTION
        "Parameter 'wlanstations' in event ACT.1"
    ::= { actEventObjects1 6 }

act1-startup OBJECT-TYPE
    SYNTAX DisplayString
    MAX-ACCESS accessible-for-notify
    STATUS current
    DESCRIPTION
        "Parameter 'startup' in event ACT.1"
    ::= { actEventObjects1 7 }

act1-system OBJECT-TYPE
    SYNTAX DisplayString
    MAX-ACCESS accessible-for-notify
    STATUS current
    DESCRIPTION
        "Parameter 'system' in event ACT.1"
    ::= { actEventObjects1 8 }

act1-ppprx OBJECT-TYPE
    SYNTAX Integer32
    MAX-ACCESS accessible-for-notify
    STATUS current
    DESCRIPTION
        "Parameter 'ppprx' in event ACT.1"
    ::= { actEventObjects1 9 }

act1-ppptx OBJECT-TYPE
    SYNTAX Integer32
    MAX-ACCESS accessible-for-notify
    STATUS current
    DESCRIPTION
        "Parameter 'ppptx' in event ACT.1"
    ::= { actEventObjects1 10 }

act1-wlanrx OBJECT-TYPE
    SYNTAX Integer32
    MAX-ACCESS accessible-for-notify
    STATUS current
    DESCRIPTION
        "Parameter 'wlanrx' in event ACT.1"
    ::= { actEventObjects1 11 }

act1-wlantx OBJECT-TYPE
    SYNTAX Integer32
    MAX-ACCESS accessible-for-notify
    STATUS current
    DESCRIPTION
        "Parameter 'wlantx' in event ACT.1"
    ::= { actEventObjects1 12 }

act1-pingresponse OBJECT-TYPE
    SYNTAX Integer32
    MAX-ACCESS accessible-for-notify
    STATUS current
    DESCRIPTION
        "Parameter 'pingresponse' in event ACT.1"
    ::= { actEventObjects1 13 }


actNotification1 NOTIFICATION-TYPE
    OBJECTS { 
              act1-pppip, 
              act1-connectiondate,
              act1-serialnumber,
              act1-hostname,
              act1-imsi,
              act1-wlanstations,
              act1-startup,
              act1-system,
              act1-ppprx,
              act1-ppptx,
              act1-wlanrx,
              act1-wlantx,
              act1-pingresponse 
            }
    STATUS current
    DESCRIPTION
        "Notification of Event ACT.1

        Message: 'IP:$1 CD:$2 Sr:$3 Bus:$4 IMSI:$5 Wst:$6 St:$7 Syt:$8 Prx:$9 Ptx:$10 Wrx:$11 Wtx:$12 Pg:$13'

        Parameters list:
              $1: act1-pppip
              $2: act1-connectiondate
              $3: act1-serialnumber
              $4: act1-hostname
              $5: act1-imsi
              $6: act1-wlanstations
              $7: act1-startup
              $8: act1-system
              $9: act1-ppprx
              $10: act1-ppptx
              $11: act1-wlanrx
              $12: act1-wlantx
              $13: act1-pingresponse

        Sending custom trap to management station"
    ::= { actNotificationsPrefix 1 }


END
