-- file automatically created


TELDAT-TRAP-MSDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


msdpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the MSDP event subsystem."
    REVISION "201401200930Z"
    DESCRIPTION "Initial implementation"
        ::= { telEventTraps 244 }


msdpEventsGroup	OBJECT IDENTIFIER	::= { msdpTrapsMIB 1 }

msdpNotifications	OBJECT IDENTIFIER	::= { msdpTrapsMIB 2 }
msdpNotificationsPrefix	OBJECT IDENTIFIER	::= { msdpNotifications 0 }

msdpEventObjects1 OBJECT-IDENTITY
    STATUS current
    DESCRIPTION
        "Event MSDP.1
        MSDP peering started with a remote peer."
    ::= { msdpEventsGroup 1 }

msdp1-remote-peer-addr OBJECT-TYPE
    SYNTAX IpAddress
    MAX-ACCESS accessible-for-notify
    STATUS current
    DESCRIPTION
        "Parameter 'remote-peer-addr' in event MSDP.1"
    ::= { msdpEventObjects1 1 }

msdpEventObjects2 OBJECT-IDENTITY
    STATUS current
    DESCRIPTION
        "Event MSDP.2
        Peer state changes in the MSDP state machine"
    ::= { msdpEventsGroup 2 }

msdp2-remote-peer-addr OBJECT-TYPE
    SYNTAX IpAddress
    MAX-ACCESS accessible-for-notify
    STATUS current
    DESCRIPTION
        "Parameter 'remote-peer-addr' in event MSDP.2"
    ::= { msdpEventObjects2 1 }

msdp2-actual-state OBJECT-TYPE
    SYNTAX DisplayString
    MAX-ACCESS accessible-for-notify
    STATUS current
    DESCRIPTION
        "Parameter 'actual-state' in event MSDP.2"
    ::= { msdpEventObjects2 2 }

msdp2-next-state OBJECT-TYPE
    SYNTAX DisplayString
    MAX-ACCESS accessible-for-notify
    STATUS current
    DESCRIPTION
        "Parameter 'next-state' in event MSDP.2"
    ::= { msdpEventObjects2 3 }

msdpEventObjects3 OBJECT-IDENTITY
    STATUS current
    DESCRIPTION
        "Event MSDP.3
        Any error detected when connection is established with the peer"
    ::= { msdpEventsGroup 3 }

msdp3-text-error OBJECT-TYPE
    SYNTAX DisplayString
    MAX-ACCESS accessible-for-notify
    STATUS current
    DESCRIPTION
        "Parameter 'text-error' in event MSDP.3"
    ::= { msdpEventObjects3 1 }

msdp3-remote-peer-addr OBJECT-TYPE
    SYNTAX IpAddress
    MAX-ACCESS accessible-for-notify
    STATUS current
    DESCRIPTION
        "Parameter 'remote-peer-addr' in event MSDP.3"
    ::= { msdpEventObjects3 2 }

msdp3-consequence OBJECT-TYPE
    SYNTAX DisplayString
    MAX-ACCESS accessible-for-notify
    STATUS current
    DESCRIPTION
        "Parameter 'consequence' in event MSDP.3"
    ::= { msdpEventObjects3 3 }

msdpEventObjects4 OBJECT-IDENTITY
    STATUS current
    DESCRIPTION
        "Event MSDP.4
        MSDP peering is stopped because the peer holdtimer has expired or the peer config has been deleted"
    ::= { msdpEventsGroup 4 }

msdp4-remote-peer-addr OBJECT-TYPE
    SYNTAX IpAddress
    MAX-ACCESS accessible-for-notify
    STATUS current
    DESCRIPTION
        "Parameter 'remote-peer-addr' in event MSDP.4"
    ::= { msdpEventObjects4 1 }

msdp4-cause OBJECT-TYPE
    SYNTAX DisplayString
    MAX-ACCESS accessible-for-notify
    STATUS current
    DESCRIPTION
        "Parameter 'cause' in event MSDP.4"
    ::= { msdpEventObjects4 2 }

msdpEventObjects5 OBJECT-IDENTITY
    STATUS current
    DESCRIPTION
        "Event MSDP.5
        In a MSDP peering, one peer listens for new TCP connections(passive side)
        and the other side(active side) makes an active connect."
    ::= { msdpEventsGroup 5 }

msdp5-text OBJECT-TYPE
    SYNTAX DisplayString
    MAX-ACCESS accessible-for-notify
    STATUS current
    DESCRIPTION
        "Parameter 'text' in event MSDP.5"
    ::= { msdpEventObjects5 1 }

msdpEventObjects6 OBJECT-IDENTITY
    STATUS current
    DESCRIPTION
        "Event MSDP.6
        A valid connection has been made to a configured MSDP peer. State is ESTABLISHED"
    ::= { msdpEventsGroup 6 }

msdp6-remote-peer-addr OBJECT-TYPE
    SYNTAX IpAddress
    MAX-ACCESS accessible-for-notify
    STATUS current
    DESCRIPTION
        "Parameter 'remote-peer-addr' in event MSDP.6"
    ::= { msdpEventObjects6 1 }

msdp6-port OBJECT-TYPE
    SYNTAX Integer32
    MAX-ACCESS accessible-for-notify
    STATUS current
    DESCRIPTION
        "Parameter 'port' in event MSDP.6"
    ::= { msdpEventObjects6 2 }

msdpEventObjects7 OBJECT-IDENTITY
    STATUS current
    DESCRIPTION
        "Event MSDP.7
        MSDP connection fails. Internal error"
    ::= { msdpEventsGroup 7 }

msdp7-text-error OBJECT-TYPE
    SYNTAX DisplayString
    MAX-ACCESS accessible-for-notify
    STATUS current
    DESCRIPTION
        "Parameter 'text-error' in event MSDP.7"
    ::= { msdpEventObjects7 1 }

msdpEventObjects8 OBJECT-IDENTITY
    STATUS current
    DESCRIPTION
        "Event MSDP.8
        MSDP connection fails. External error"
    ::= { msdpEventsGroup 8 }

msdp8-text-error OBJECT-TYPE
    SYNTAX DisplayString
    MAX-ACCESS accessible-for-notify
    STATUS current
    DESCRIPTION
        "Parameter 'text-error' in event MSDP.8"
    ::= { msdpEventObjects8 1 }

msdp8-remote-peer-addr OBJECT-TYPE
    SYNTAX IpAddress
    MAX-ACCESS accessible-for-notify
    STATUS current
    DESCRIPTION
        "Parameter 'remote-peer-addr' in event MSDP.8"
    ::= { msdpEventObjects8 2 }

msdpEventObjects9 OBJECT-IDENTITY
    STATUS current
    DESCRIPTION
        "Event MSDP.9
        Sending KeepAlive TLV message to remote peer."
    ::= { msdpEventsGroup 9 }

msdp9-remote-peer-addr OBJECT-TYPE
    SYNTAX IpAddress
    MAX-ACCESS accessible-for-notify
    STATUS current
    DESCRIPTION
        "Parameter 'remote-peer-addr' in event MSDP.9"
    ::= { msdpEventObjects9 1 }

msdpEventObjects10 OBJECT-IDENTITY
    STATUS current
    DESCRIPTION
        "Event MSDP.10
        Sending Source Active TLV message to remote peer."
    ::= { msdpEventsGroup 10 }

msdp10-remote-peer-addr OBJECT-TYPE
    SYNTAX IpAddress
    MAX-ACCESS accessible-for-notify
    STATUS current
    DESCRIPTION
        "Parameter 'remote-peer-addr' in event MSDP.10"
    ::= { msdpEventObjects10 1 }

msdp10-entry-count OBJECT-TYPE
    SYNTAX Integer32
    MAX-ACCESS accessible-for-notify
    STATUS current
    DESCRIPTION
        "Parameter 'entry-count' in event MSDP.10"
    ::= { msdpEventObjects10 2 }

msdp10-length OBJECT-TYPE
    SYNTAX Integer32
    MAX-ACCESS accessible-for-notify
    STATUS current
    DESCRIPTION
        "Parameter 'length' in event MSDP.10"
    ::= { msdpEventObjects10 3 }

msdpEventObjects11 OBJECT-IDENTITY
    STATUS current
    DESCRIPTION
        "Event MSDP.11
        Received MSDP KeepAlive TLV message from remote peer."
    ::= { msdpEventsGroup 11 }

msdp11-remote-peer-addr OBJECT-TYPE
    SYNTAX IpAddress
    MAX-ACCESS accessible-for-notify
    STATUS current
    DESCRIPTION
        "Parameter 'remote-peer-addr' in event MSDP.11"
    ::= { msdpEventObjects11 1 }

msdpEventObjects12 OBJECT-IDENTITY
    STATUS current
    DESCRIPTION
        "Event MSDP.12
        Received MSDP Source Active TLV message from remote peer."
    ::= { msdpEventsGroup 12 }

msdp12-remote-peer-addr OBJECT-TYPE
    SYNTAX IpAddress
    MAX-ACCESS accessible-for-notify
    STATUS current
    DESCRIPTION
        "Parameter 'remote-peer-addr' in event MSDP.12"
    ::= { msdpEventObjects12 1 }

msdp12-length OBJECT-TYPE
    SYNTAX Integer32
    MAX-ACCESS accessible-for-notify
    STATUS current
    DESCRIPTION
        "Parameter 'length' in event MSDP.12"
    ::= { msdpEventObjects12 2 }

msdp12-entrycount OBJECT-TYPE
    SYNTAX Integer32
    MAX-ACCESS accessible-for-notify
    STATUS current
    DESCRIPTION
        "Parameter 'entrycount' in event MSDP.12"
    ::= { msdpEventObjects12 3 }

msdp12-rp-address OBJECT-TYPE
    SYNTAX IpAddress
    MAX-ACCESS accessible-for-notify
    STATUS current
    DESCRIPTION
        "Parameter 'rp-address' in event MSDP.12"
    ::= { msdpEventObjects12 4 }

msdpEventObjects13 OBJECT-IDENTITY
    STATUS current
    DESCRIPTION
        "Event MSDP.13
        Event in RPF peer algorithm. One of the rules matches for the peer"
    ::= { msdpEventsGroup 13 }

msdp13-remote-peer-addr OBJECT-TYPE
    SYNTAX IpAddress
    MAX-ACCESS accessible-for-notify
    STATUS current
    DESCRIPTION
        "Parameter 'remote-peer-addr' in event MSDP.13"
    ::= { msdpEventObjects13 1 }

msdp13-rule OBJECT-TYPE
    SYNTAX DisplayString
    MAX-ACCESS accessible-for-notify
    STATUS current
    DESCRIPTION
        "Parameter 'rule' in event MSDP.13"
    ::= { msdpEventObjects13 2 }

msdpEventObjects14 OBJECT-IDENTITY
    STATUS current
    DESCRIPTION
        "Event MSDP.14
        Event in RPF peer algorithm. None of the rules match for the peer. The
        Source Active TLV message is discarded"
    ::= { msdpEventsGroup 14 }

msdp14-remote-peer-addr OBJECT-TYPE
    SYNTAX IpAddress
    MAX-ACCESS accessible-for-notify
    STATUS current
    DESCRIPTION
        "Parameter 'remote-peer-addr' in event MSDP.14"
    ::= { msdpEventObjects14 1 }

msdpEventObjects15 OBJECT-IDENTITY
    STATUS current
    DESCRIPTION
        "Event MSDP.15
        RPF peer skipped"
    ::= { msdpEventsGroup 15 }

msdp15-remote-peer-addr OBJECT-TYPE
    SYNTAX IpAddress
    MAX-ACCESS accessible-for-notify
    STATUS current
    DESCRIPTION
        "Parameter 'remote-peer-addr' in event MSDP.15"
    ::= { msdpEventObjects15 1 }

msdp15-text OBJECT-TYPE
    SYNTAX DisplayString
    MAX-ACCESS accessible-for-notify
    STATUS current
    DESCRIPTION
        "Parameter 'text' in event MSDP.15"
    ::= { msdpEventObjects15 2 }

msdpEventObjects16 OBJECT-IDENTITY
    STATUS current
    DESCRIPTION
        "Event MSDP.16
        Event in RPF peer algorithm. The algorithm is going to fail because
        there is an option missing in the MSDP peer configuration."
    ::= { msdpEventsGroup 16 }

msdp16-remote-peer OBJECT-TYPE
    SYNTAX IpAddress
    MAX-ACCESS accessible-for-notify
    STATUS current
    DESCRIPTION
        "Parameter 'remote-peer' in event MSDP.16"
    ::= { msdpEventObjects16 1 }

msdp16-text-error OBJECT-TYPE
    SYNTAX DisplayString
    MAX-ACCESS accessible-for-notify
    STATUS current
    DESCRIPTION
        "Parameter 'text-error' in event MSDP.16"
    ::= { msdpEventObjects16 2 }

msdpEventObjects18 OBJECT-IDENTITY
    STATUS current
    DESCRIPTION
        "Event MSDP.18
        The SA TLV received from the remote peer is too large. The message is accepted, but the
        additional data is ignored."
    ::= { msdpEventsGroup 18 }

msdp18-remote-peer OBJECT-TYPE
    SYNTAX IpAddress
    MAX-ACCESS accessible-for-notify
    STATUS current
    DESCRIPTION
        "Parameter 'remote-peer' in event MSDP.18"
    ::= { msdpEventObjects18 1 }

msdp18-msg-length OBJECT-TYPE
    SYNTAX Integer32
    MAX-ACCESS accessible-for-notify
    STATUS current
    DESCRIPTION
        "Parameter 'msg-length' in event MSDP.18"
    ::= { msdpEventObjects18 2 }

msdp18-max-len OBJECT-TYPE
    SYNTAX Integer32
    MAX-ACCESS accessible-for-notify
    STATUS current
    DESCRIPTION
        "Parameter 'max-len' in event MSDP.18"
    ::= { msdpEventObjects18 3 }

msdpEventObjects19 OBJECT-IDENTITY
    STATUS current
    DESCRIPTION
        "Event MSDP.19
        An entry was added or updated in the SA-cache"
    ::= { msdpEventsGroup 19 }

msdp19-src-addr OBJECT-TYPE
    SYNTAX IpAddress
    MAX-ACCESS accessible-for-notify
    STATUS current
    DESCRIPTION
        "Parameter 'src-addr' in event MSDP.19"
    ::= { msdpEventObjects19 1 }

msdp19-grp-addr OBJECT-TYPE
    SYNTAX IpAddress
    MAX-ACCESS accessible-for-notify
    STATUS current
    DESCRIPTION
        "Parameter 'grp-addr' in event MSDP.19"
    ::= { msdpEventObjects19 2 }

msdp19-rp-addr OBJECT-TYPE
    SYNTAX IpAddress
    MAX-ACCESS accessible-for-notify
    STATUS current
    DESCRIPTION
        "Parameter 'rp-addr' in event MSDP.19"
    ::= { msdpEventObjects19 3 }

msdpEventObjects20 OBJECT-IDENTITY
    STATUS current
    DESCRIPTION
        "Event MSDP.20
        Error adding a new SA-cache entry"
    ::= { msdpEventsGroup 20 }

msdp20-src-addr OBJECT-TYPE
    SYNTAX IpAddress
    MAX-ACCESS accessible-for-notify
    STATUS current
    DESCRIPTION
        "Parameter 'src-addr' in event MSDP.20"
    ::= { msdpEventObjects20 1 }

msdp20-grp-addr OBJECT-TYPE
    SYNTAX IpAddress
    MAX-ACCESS accessible-for-notify
    STATUS current
    DESCRIPTION
        "Parameter 'grp-addr' in event MSDP.20"
    ::= { msdpEventObjects20 2 }

msdp20-rp-addr OBJECT-TYPE
    SYNTAX IpAddress
    MAX-ACCESS accessible-for-notify
    STATUS current
    DESCRIPTION
        "Parameter 'rp-addr' in event MSDP.20"
    ::= { msdpEventObjects20 3 }

msdpEventObjects21 OBJECT-IDENTITY
    STATUS current
    DESCRIPTION
        "Event MSDP.21
        An entry was deleted from SA-cache"
    ::= { msdpEventsGroup 21 }

msdp21-src-addr OBJECT-TYPE
    SYNTAX IpAddress
    MAX-ACCESS accessible-for-notify
    STATUS current
    DESCRIPTION
        "Parameter 'src-addr' in event MSDP.21"
    ::= { msdpEventObjects21 1 }

msdp21-grp-addr OBJECT-TYPE
    SYNTAX IpAddress
    MAX-ACCESS accessible-for-notify
    STATUS current
    DESCRIPTION
        "Parameter 'grp-addr' in event MSDP.21"
    ::= { msdpEventObjects21 2 }

msdp21-rp-addr OBJECT-TYPE
    SYNTAX IpAddress
    MAX-ACCESS accessible-for-notify
    STATUS current
    DESCRIPTION
        "Parameter 'rp-addr' in event MSDP.21"
    ::= { msdpEventObjects21 3 }

msdpEventObjects22 OBJECT-IDENTITY
    STATUS current
    DESCRIPTION
        "Event MSDP.22
        Set connectRetry Timer for remote peer in MSDP connection"
    ::= { msdpEventsGroup 22 }

msdp22-remote-peer OBJECT-TYPE
    SYNTAX IpAddress
    MAX-ACCESS accessible-for-notify
    STATUS current
    DESCRIPTION
        "Parameter 'remote-peer' in event MSDP.22"
    ::= { msdpEventObjects22 1 }

msdp22-timer-value OBJECT-TYPE
    SYNTAX Integer32
    MAX-ACCESS accessible-for-notify
    STATUS current
    DESCRIPTION
        "Parameter 'timer-value' in event MSDP.22"
    ::= { msdpEventObjects22 2 }

msdpEventObjects23 OBJECT-IDENTITY
    STATUS current
    DESCRIPTION
        "Event MSDP.23
        ConnectRetry Timer has expired, retry the connection with the peer"
    ::= { msdpEventsGroup 23 }

msdp23-remote-peer OBJECT-TYPE
    SYNTAX IpAddress
    MAX-ACCESS accessible-for-notify
    STATUS current
    DESCRIPTION
        "Parameter 'remote-peer' in event MSDP.23"
    ::= { msdpEventObjects23 1 }

msdpEventObjects24 OBJECT-IDENTITY
    STATUS current
    DESCRIPTION
        "Event MSDP.24
        Stop ConnectRetry timer because connection is established with the peer"
    ::= { msdpEventsGroup 24 }

msdp24-remote-peer OBJECT-TYPE
    SYNTAX IpAddress
    MAX-ACCESS accessible-for-notify
    STATUS current
    DESCRIPTION
        "Parameter 'remote-peer' in event MSDP.24"
    ::= { msdpEventObjects24 1 }

msdpEventObjects26 OBJECT-IDENTITY
    STATUS current
    DESCRIPTION
        "Event MSDP.26
        PeerHold Timer has expired, the connection with the peer is closed"
    ::= { msdpEventsGroup 26 }

msdp26-remote-peer OBJECT-TYPE
    SYNTAX IpAddress
    MAX-ACCESS accessible-for-notify
    STATUS current
    DESCRIPTION
        "Parameter 'remote-peer' in event MSDP.26"
    ::= { msdpEventObjects26 1 }

msdpEventObjects28 OBJECT-IDENTITY
    STATUS current
    DESCRIPTION
        "Event MSDP.28
        I am the RP of the domain, start the SA-Adv-Timer for send periodic SA"
    ::= { msdpEventsGroup 28 }

msdp28-remote-peer OBJECT-TYPE
    SYNTAX IpAddress
    MAX-ACCESS accessible-for-notify
    STATUS current
    DESCRIPTION
        "Parameter 'remote-peer' in event MSDP.28"
    ::= { msdpEventObjects28 1 }

msdp28-timer-value OBJECT-TYPE
    SYNTAX Integer32
    MAX-ACCESS accessible-for-notify
    STATUS current
    DESCRIPTION
        "Parameter 'timer-value' in event MSDP.28"
    ::= { msdpEventObjects28 2 }

msdpEventObjects30 OBJECT-IDENTITY
    STATUS current
    DESCRIPTION
        "Event MSDP.30
        The SA-Adv-Timer has expired, and begins the advertisement of its active sources"
    ::= { msdpEventsGroup 30 }

msdp30-remote-peer OBJECT-TYPE
    SYNTAX IpAddress
    MAX-ACCESS accessible-for-notify
    STATUS current
    DESCRIPTION
        "Parameter 'remote-peer' in event MSDP.30"
    ::= { msdpEventObjects30 1 }

msdpEventObjects31 OBJECT-IDENTITY
    STATUS current
    DESCRIPTION
        "Event MSDP.31
        Every 60secs, send a SA message with the SA-cache entries to reduce storms"
    ::= { msdpEventsGroup 31 }

msdp31-remote-peer-addr OBJECT-TYPE
    SYNTAX IpAddress
    MAX-ACCESS accessible-for-notify
    STATUS current
    DESCRIPTION
        "Parameter 'remote-peer-addr' in event MSDP.31"
    ::= { msdpEventObjects31 1 }

msdpEventObjects32 OBJECT-IDENTITY
    STATUS current
    DESCRIPTION
        "Event MSDP.32
        The SA-cache timer has expired for a entry, the entry is marked for delete"
    ::= { msdpEventsGroup 32 }

msdp32-src-addr OBJECT-TYPE
    SYNTAX IpAddress
    MAX-ACCESS accessible-for-notify
    STATUS current
    DESCRIPTION
        "Parameter 'src-addr' in event MSDP.32"
    ::= { msdpEventObjects32 1 }

msdp32-grp-addr OBJECT-TYPE
    SYNTAX IpAddress
    MAX-ACCESS accessible-for-notify
    STATUS current
    DESCRIPTION
        "Parameter 'grp-addr' in event MSDP.32"
    ::= { msdpEventObjects32 2 }

msdp32-rp-addr OBJECT-TYPE
    SYNTAX IpAddress
    MAX-ACCESS accessible-for-notify
    STATUS current
    DESCRIPTION
        "Parameter 'rp-addr' in event MSDP.32"
    ::= { msdpEventObjects32 3 }

msdpEventObjects33 OBJECT-IDENTITY
    STATUS current
    DESCRIPTION
        "Event MSDP.33
        A new source active is learned"
    ::= { msdpEventsGroup 33 }

msdp33-src-addr OBJECT-TYPE
    SYNTAX IpAddress
    MAX-ACCESS accessible-for-notify
    STATUS current
    DESCRIPTION
        "Parameter 'src-addr' in event MSDP.33"
    ::= { msdpEventObjects33 1 }

msdp33-grp-addr OBJECT-TYPE
    SYNTAX IpAddress
    MAX-ACCESS accessible-for-notify
    STATUS current
    DESCRIPTION
        "Parameter 'grp-addr' in event MSDP.33"
    ::= { msdpEventObjects33 2 }

msdp33-rp-addr OBJECT-TYPE
    SYNTAX IpAddress
    MAX-ACCESS accessible-for-notify
    STATUS current
    DESCRIPTION
        "Parameter 'rp-addr' in event MSDP.33"
    ::= { msdpEventObjects33 3 }

msdpEventObjects34 OBJECT-IDENTITY
    STATUS current
    DESCRIPTION
        "Event MSDP.34
        There is no entries in MRT to send in the periodic SA message."
    ::= { msdpEventsGroup 34 }

msdp34-remote-peer-addr OBJECT-TYPE
    SYNTAX IpAddress
    MAX-ACCESS accessible-for-notify
    STATUS current
    DESCRIPTION
        "Parameter 'remote-peer-addr' in event MSDP.34"
    ::= { msdpEventObjects34 1 }

msdpEventObjects35 OBJECT-IDENTITY
    STATUS current
    DESCRIPTION
        "Event MSDP.35
        All entries sent in periodic SA message"
    ::= { msdpEventsGroup 35 }

msdp35-remote-peer-addr OBJECT-TYPE
    SYNTAX IpAddress
    MAX-ACCESS accessible-for-notify
    STATUS current
    DESCRIPTION
        "Parameter 'remote-peer-addr' in event MSDP.35"
    ::= { msdpEventObjects35 1 }

msdpEventObjects39 OBJECT-IDENTITY
    STATUS current
    DESCRIPTION
        "Event MSDP.39
        An unrecognized MSDP message has received. The message is discarded"
    ::= { msdpEventsGroup 39 }

msdp39-msg-type OBJECT-TYPE
    SYNTAX Integer32
    MAX-ACCESS accessible-for-notify
    STATUS current
    DESCRIPTION
        "Parameter 'msg-type' in event MSDP.39"
    ::= { msdpEventObjects39 1 }

msdpEventObjects40 OBJECT-IDENTITY
    STATUS current
    DESCRIPTION
        "Event MSDP.40
        Error sending an MSDP message"
    ::= { msdpEventsGroup 40 }

msdp40-text-error OBJECT-TYPE
    SYNTAX DisplayString
    MAX-ACCESS accessible-for-notify
    STATUS current
    DESCRIPTION
        "Parameter 'text-error' in event MSDP.40"
    ::= { msdpEventObjects40 1 }

msdp40-remote-peer-addr OBJECT-TYPE
    SYNTAX IpAddress
    MAX-ACCESS accessible-for-notify
    STATUS current
    DESCRIPTION
        "Parameter 'remote-peer-addr' in event MSDP.40"
    ::= { msdpEventObjects40 2 }

msdpEventObjects41 OBJECT-IDENTITY
    STATUS current
    DESCRIPTION
        "Event MSDP.41
        Error receiving an MSDP message. Format error detected"
    ::= { msdpEventsGroup 41 }

msdp41-text-error OBJECT-TYPE
    SYNTAX DisplayString
    MAX-ACCESS accessible-for-notify
    STATUS current
    DESCRIPTION
        "Parameter 'text-error' in event MSDP.41"
    ::= { msdpEventObjects41 1 }

msdp41-length OBJECT-TYPE
    SYNTAX Integer32
    MAX-ACCESS accessible-for-notify
    STATUS current
    DESCRIPTION
        "Parameter 'length' in event MSDP.41"
    ::= { msdpEventObjects41 2 }

msdp41-remote-peer-addr OBJECT-TYPE
    SYNTAX IpAddress
    MAX-ACCESS accessible-for-notify
    STATUS current
    DESCRIPTION
        "Parameter 'remote-peer-addr' in event MSDP.41"
    ::= { msdpEventObjects41 3 }

msdpEventObjects42 OBJECT-IDENTITY
    STATUS current
    DESCRIPTION
        "Event MSDP.42
        Generic internal error."
    ::= { msdpEventsGroup 42 }

msdp42-text-error OBJECT-TYPE
    SYNTAX DisplayString
    MAX-ACCESS accessible-for-notify
    STATUS current
    DESCRIPTION
        "Parameter 'text-error' in event MSDP.42"
    ::= { msdpEventObjects42 1 }


msdpNotification1 NOTIFICATION-TYPE
    OBJECTS { 
              msdp1-remote-peer-addr 
            }
    STATUS current
    DESCRIPTION
        "Notification of Event MSDP.1

        Message: 'Start MSDP peering with remote peer $1'

        Parameters list:
              $1: msdp1-remote-peer-addr

        MSDP peering started with a remote peer."
    ::= { msdpNotificationsPrefix 1 }

msdpNotification2 NOTIFICATION-TYPE
    OBJECTS { 
              msdp2-remote-peer-addr, 
              msdp2-actual-state,
              msdp2-next-state 
            }
    STATUS current
    DESCRIPTION
        "Notification of Event MSDP.2

        Message: 'Peer $1 change from state $2 to state $3 in the MSDP state machine'

        Parameters list:
              $1: msdp2-remote-peer-addr
              $2: msdp2-actual-state
              $3: msdp2-next-state

        Peer state changes in the MSDP state machine"
    ::= { msdpNotificationsPrefix 2 }

msdpNotification3 NOTIFICATION-TYPE
    OBJECTS { 
              msdp3-text-error, 
              msdp3-remote-peer-addr,
              msdp3-consequence 
            }
    STATUS current
    DESCRIPTION
        "Notification of Event MSDP.3

        Message: 'Error ($1) detected in peering with remote peer $2 -> $3'

        Parameters list:
              $1: msdp3-text-error
              $2: msdp3-remote-peer-addr
              $3: msdp3-consequence

        Any error detected when connection is established with the peer"
    ::= { msdpNotificationsPrefix 3 }

msdpNotification4 NOTIFICATION-TYPE
    OBJECTS { 
              msdp4-remote-peer-addr, 
              msdp4-cause 
            }
    STATUS current
    DESCRIPTION
        "Notification of Event MSDP.4

        Message: 'Stop MSDP peering with remote peer $1, because $2'

        Parameters list:
              $1: msdp4-remote-peer-addr
              $2: msdp4-cause

        MSDP peering is stopped because the peer holdtimer has expired or the peer config has been deleted"
    ::= { msdpNotificationsPrefix 4 }

msdpNotification5 NOTIFICATION-TYPE
    OBJECTS { 
              msdp5-text 
            }
    STATUS current
    DESCRIPTION
        "Notification of Event MSDP.5

        Message: '$1'

        Parameters list:
              $1: msdp5-text

        In a MSDP peering, one peer listens for new TCP connections(passive side)
        and the other side(active side) makes an active connect."
    ::= { msdpNotificationsPrefix 5 }

msdpNotification6 NOTIFICATION-TYPE
    OBJECTS { 
              msdp6-remote-peer-addr, 
              msdp6-port 
            }
    STATUS current
    DESCRIPTION
        "Notification of Event MSDP.6

        Message: 'The connection is ESTABLISHED with the peer $1:$2'

        Parameters list:
              $1: msdp6-remote-peer-addr
              $2: msdp6-port

        A valid connection has been made to a configured MSDP peer. State is ESTABLISHED"
    ::= { msdpNotificationsPrefix 6 }

msdpNotification7 NOTIFICATION-TYPE
    OBJECTS { 
              msdp7-text-error 
            }
    STATUS current
    DESCRIPTION
        "Notification of Event MSDP.7

        Message: '$1'

        Parameters list:
              $1: msdp7-text-error

        MSDP connection fails. Internal error"
    ::= { msdpNotificationsPrefix 7 }

msdpNotification8 NOTIFICATION-TYPE
    OBJECTS { 
              msdp8-text-error, 
              msdp8-remote-peer-addr 
            }
    STATUS current
    DESCRIPTION
        "Notification of Event MSDP.8

        Message: '$1: $2'

        Parameters list:
              $1: msdp8-text-error
              $2: msdp8-remote-peer-addr

        MSDP connection fails. External error"
    ::= { msdpNotificationsPrefix 8 }

msdpNotification9 NOTIFICATION-TYPE
    OBJECTS { 
              msdp9-remote-peer-addr 
            }
    STATUS current
    DESCRIPTION
        "Notification of Event MSDP.9

        Message: 'Send MSDP KeepAlive TLV message to peer $1'

        Parameters list:
              $1: msdp9-remote-peer-addr

        Sending KeepAlive TLV message to remote peer."
    ::= { msdpNotificationsPrefix 9 }

msdpNotification10 NOTIFICATION-TYPE
    OBJECTS { 
              msdp10-remote-peer-addr, 
              msdp10-entry-count,
              msdp10-length 
            }
    STATUS current
    DESCRIPTION
        "Notification of Event MSDP.10

        Message: 'Send MSDP Source Active TLV message to remote peer $1, $2 entries, length $3-bytes'

        Parameters list:
              $1: msdp10-remote-peer-addr
              $2: msdp10-entry-count
              $3: msdp10-length

        Sending Source Active TLV message to remote peer."
    ::= { msdpNotificationsPrefix 10 }

msdpNotification11 NOTIFICATION-TYPE
    OBJECTS { 
              msdp11-remote-peer-addr 
            }
    STATUS current
    DESCRIPTION
        "Notification of Event MSDP.11

        Message: 'Received MSDP KeepAlive TLV message from peer $1'

        Parameters list:
              $1: msdp11-remote-peer-addr

        Received MSDP KeepAlive TLV message from remote peer."
    ::= { msdpNotificationsPrefix 11 }

msdpNotification12 NOTIFICATION-TYPE
    OBJECTS { 
              msdp12-remote-peer-addr, 
              msdp12-length,
              msdp12-entrycount,
              msdp12-rp-address 
            }
    STATUS current
    DESCRIPTION
        "Notification of Event MSDP.12

        Message: 'Received MSDP Source Active TLV message from remote peer $1, len $2, entry count $3, RP address $4'

        Parameters list:
              $1: msdp12-remote-peer-addr
              $2: msdp12-length
              $3: msdp12-entrycount
              $4: msdp12-rp-address

        Received MSDP Source Active TLV message from remote peer."
    ::= { msdpNotificationsPrefix 12 }

msdpNotification13 NOTIFICATION-TYPE
    OBJECTS { 
              msdp13-remote-peer-addr, 
              msdp13-rule 
            }
    STATUS current
    DESCRIPTION
        "Notification of Event MSDP.13

        Message: 'RPF peer check passed for the peer $1, match with rule $2'

        Parameters list:
              $1: msdp13-remote-peer-addr
              $2: msdp13-rule

        Event in RPF peer algorithm. One of the rules matches for the peer"
    ::= { msdpNotificationsPrefix 13 }

msdpNotification14 NOTIFICATION-TYPE
    OBJECTS { 
              msdp14-remote-peer-addr 
            }
    STATUS current
    DESCRIPTION
        "Notification of Event MSDP.14

        Message: 'RPF peer check failed for the peer $1, MSDP SourceActive TLV discarded'

        Parameters list:
              $1: msdp14-remote-peer-addr

        Event in RPF peer algorithm. None of the rules match for the peer. The
        Source Active TLV message is discarded"
    ::= { msdpNotificationsPrefix 14 }

msdpNotification15 NOTIFICATION-TYPE
    OBJECTS { 
              msdp15-remote-peer-addr, 
              msdp15-text 
            }
    STATUS current
    DESCRIPTION
        "Notification of Event MSDP.15

        Message: 'RPF peer skipped for peer $1, because $2'

        Parameters list:
              $1: msdp15-remote-peer-addr
              $2: msdp15-text

        RPF peer skipped"
    ::= { msdpNotificationsPrefix 15 }

msdpNotification16 NOTIFICATION-TYPE
    OBJECTS { 
              msdp16-remote-peer, 
              msdp16-text-error 
            }
    STATUS current
    DESCRIPTION
        "Notification of Event MSDP.16

        Message: 'RPF peer check for peer $1 is going to fail because $2'

        Parameters list:
              $1: msdp16-remote-peer
              $2: msdp16-text-error

        Event in RPF peer algorithm. The algorithm is going to fail because
        there is an option missing in the MSDP peer configuration."
    ::= { msdpNotificationsPrefix 16 }

msdpNotification17 NOTIFICATION-TYPE
    STATUS current
    DESCRIPTION
        "Notification of Event MSDP.17

        Message: '--'

        Reserved for future use"
    ::= { msdpNotificationsPrefix 17 }

msdpNotification18 NOTIFICATION-TYPE
    OBJECTS { 
              msdp18-remote-peer, 
              msdp18-msg-length,
              msdp18-max-len 
            }
    STATUS current
    DESCRIPTION
        "Notification of Event MSDP.18

        Message: 'The SourceActive received from the peer $1 is too large, length $2 bytes, maximum length $3 bytes. The message is accepted, but the additional data is ignored.'

        Parameters list:
              $1: msdp18-remote-peer
              $2: msdp18-msg-length
              $3: msdp18-max-len

        The SA TLV received from the remote peer is too large. The message is accepted, but the
        additional data is ignored."
    ::= { msdpNotificationsPrefix 18 }

msdpNotification19 NOTIFICATION-TYPE
    OBJECTS { 
              msdp19-src-addr, 
              msdp19-grp-addr,
              msdp19-rp-addr 
            }
    STATUS current
    DESCRIPTION
        "Notification of Event MSDP.19

        Message: 'Add/Update an SourceActive cache entry: Source $1, Group $2, RP $3'

        Parameters list:
              $1: msdp19-src-addr
              $2: msdp19-grp-addr
              $3: msdp19-rp-addr

        An entry was added or updated in the SA-cache"
    ::= { msdpNotificationsPrefix 19 }

msdpNotification20 NOTIFICATION-TYPE
    OBJECTS { 
              msdp20-src-addr, 
              msdp20-grp-addr,
              msdp20-rp-addr 
            }
    STATUS current
    DESCRIPTION
        "Notification of Event MSDP.20

        Message: 'Unable to add the new entry ($1, $2) RP: $3, to the SourceActive cache'

        Parameters list:
              $1: msdp20-src-addr
              $2: msdp20-grp-addr
              $3: msdp20-rp-addr

        Error adding a new SA-cache entry"
    ::= { msdpNotificationsPrefix 20 }

msdpNotification21 NOTIFICATION-TYPE
    OBJECTS { 
              msdp21-src-addr, 
              msdp21-grp-addr,
              msdp21-rp-addr 
            }
    STATUS current
    DESCRIPTION
        "Notification of Event MSDP.21

        Message: 'Deleting a SourceActive cache entry: Source $1, Group $2, RP $3'

        Parameters list:
              $1: msdp21-src-addr
              $2: msdp21-grp-addr
              $3: msdp21-rp-addr

        An entry was deleted from SA-cache"
    ::= { msdpNotificationsPrefix 21 }

msdpNotification22 NOTIFICATION-TYPE
    OBJECTS { 
              msdp22-remote-peer, 
              msdp22-timer-value 
            }
    STATUS current
    DESCRIPTION
        "Notification of Event MSDP.22

        Message: 'Set connectRetry Timer for remote peer $1: $2secs'

        Parameters list:
              $1: msdp22-remote-peer
              $2: msdp22-timer-value

        Set connectRetry Timer for remote peer in MSDP connection"
    ::= { msdpNotificationsPrefix 22 }

msdpNotification23 NOTIFICATION-TYPE
    OBJECTS { 
              msdp23-remote-peer 
            }
    STATUS current
    DESCRIPTION
        "Notification of Event MSDP.23

        Message: 'The connectRetry timer has expired for remote peer $1, retry the connection'

        Parameters list:
              $1: msdp23-remote-peer

        ConnectRetry Timer has expired, retry the connection with the peer"
    ::= { msdpNotificationsPrefix 23 }

msdpNotification24 NOTIFICATION-TYPE
    OBJECTS { 
              msdp24-remote-peer 
            }
    STATUS current
    DESCRIPTION
        "Notification of Event MSDP.24

        Message: 'Stop the connectRetry Timer because the connection is established with the peer $1'

        Parameters list:
              $1: msdp24-remote-peer

        Stop ConnectRetry timer because connection is established with the peer"
    ::= { msdpNotificationsPrefix 24 }

msdpNotification25 NOTIFICATION-TYPE
    STATUS current
    DESCRIPTION
        "Notification of Event MSDP.25

        Message: '--'

        Reserved for future use"
    ::= { msdpNotificationsPrefix 25 }

msdpNotification26 NOTIFICATION-TYPE
    OBJECTS { 
              msdp26-remote-peer 
            }
    STATUS current
    DESCRIPTION
        "Notification of Event MSDP.26

        Message: 'The peerHold timer has expired for remote peer $1, connection is closed'

        Parameters list:
              $1: msdp26-remote-peer

        PeerHold Timer has expired, the connection with the peer is closed"
    ::= { msdpNotificationsPrefix 26 }

msdpNotification27 NOTIFICATION-TYPE
    STATUS current
    DESCRIPTION
        "Notification of Event MSDP.27

        Message: '--'

        Reserved for future use"
    ::= { msdpNotificationsPrefix 27 }

msdpNotification28 NOTIFICATION-TYPE
    OBJECTS { 
              msdp28-remote-peer, 
              msdp28-timer-value 
            }
    STATUS current
    DESCRIPTION
        "Notification of Event MSDP.28

        Message: 'I am the RP of the domain, start the SA-Advertisement Timer for peer $1: $2secs'

        Parameters list:
              $1: msdp28-remote-peer
              $2: msdp28-timer-value

        I am the RP of the domain, start the SA-Adv-Timer for send periodic SA"
    ::= { msdpNotificationsPrefix 28 }

msdpNotification29 NOTIFICATION-TYPE
    STATUS current
    DESCRIPTION
        "Notification of Event MSDP.29

        Message: '--'

        Reserved for future use"
    ::= { msdpNotificationsPrefix 29 }

msdpNotification30 NOTIFICATION-TYPE
    OBJECTS { 
              msdp30-remote-peer 
            }
    STATUS current
    DESCRIPTION
        "Notification of Event MSDP.30

        Message: 'SA-Advertisement timer has expired, start sending active sources to peer $1'

        Parameters list:
              $1: msdp30-remote-peer

        The SA-Adv-Timer has expired, and begins the advertisement of its active sources"
    ::= { msdpNotificationsPrefix 30 }

msdpNotification31 NOTIFICATION-TYPE
    OBJECTS { 
              msdp31-remote-peer-addr 
            }
    STATUS current
    DESCRIPTION
        "Notification of Event MSDP.31

        Message: 'Send a periodic SourceActive message with the SA-cache entries to the remote peer $1'

        Parameters list:
              $1: msdp31-remote-peer-addr

        Every 60secs, send a SA message with the SA-cache entries to reduce storms"
    ::= { msdpNotificationsPrefix 31 }

msdpNotification32 NOTIFICATION-TYPE
    OBJECTS { 
              msdp32-src-addr, 
              msdp32-grp-addr,
              msdp32-rp-addr 
            }
    STATUS current
    DESCRIPTION
        "Notification of Event MSDP.32

        Message: 'The SouceActive cache timer has expired for the entry ($1, $2, $3), mark entry for deletion'

        Parameters list:
              $1: msdp32-src-addr
              $2: msdp32-grp-addr
              $3: msdp32-rp-addr

        The SA-cache timer has expired for a entry, the entry is marked for delete"
    ::= { msdpNotificationsPrefix 32 }

msdpNotification33 NOTIFICATION-TYPE
    OBJECTS { 
              msdp33-src-addr, 
              msdp33-grp-addr,
              msdp33-rp-addr 
            }
    STATUS current
    DESCRIPTION
        "Notification of Event MSDP.33

        Message: 'New source active learned: Source $1, Group $2, RP $3'

        Parameters list:
              $1: msdp33-src-addr
              $2: msdp33-grp-addr
              $3: msdp33-rp-addr

        A new source active is learned"
    ::= { msdpNotificationsPrefix 33 }

msdpNotification34 NOTIFICATION-TYPE
    OBJECTS { 
              msdp34-remote-peer-addr 
            }
    STATUS current
    DESCRIPTION
        "Notification of Event MSDP.34

        Message: 'No entries found in MRT for the periodic SourceActive message to remote peer $1'

        Parameters list:
              $1: msdp34-remote-peer-addr

        There is no entries in MRT to send in the periodic SA message."
    ::= { msdpNotificationsPrefix 34 }

msdpNotification35 NOTIFICATION-TYPE
    OBJECTS { 
              msdp35-remote-peer-addr 
            }
    STATUS current
    DESCRIPTION
        "Notification of Event MSDP.35

        Message: 'All entries in MRT has sent for the periodic SourceActive message to remote peer $1'

        Parameters list:
              $1: msdp35-remote-peer-addr

        All entries sent in periodic SA message"
    ::= { msdpNotificationsPrefix 35 }

msdpNotification36 NOTIFICATION-TYPE
    STATUS current
    DESCRIPTION
        "Notification of Event MSDP.36

        Message: '--'

        Reserved for future use"
    ::= { msdpNotificationsPrefix 36 }

msdpNotification37 NOTIFICATION-TYPE
    STATUS current
    DESCRIPTION
        "Notification of Event MSDP.37

        Message: '--'

        Reserved for future use"
    ::= { msdpNotificationsPrefix 37 }

msdpNotification38 NOTIFICATION-TYPE
    STATUS current
    DESCRIPTION
        "Notification of Event MSDP.38

        Message: '--'

        Reserved for future use"
    ::= { msdpNotificationsPrefix 38 }

msdpNotification39 NOTIFICATION-TYPE
    OBJECTS { 
              msdp39-msg-type 
            }
    STATUS current
    DESCRIPTION
        "Notification of Event MSDP.39

        Message: 'Received an unrecognized MSDP message: type $1. The message is discarded'

        Parameters list:
              $1: msdp39-msg-type

        An unrecognized MSDP message has received. The message is discarded"
    ::= { msdpNotificationsPrefix 39 }

msdpNotification40 NOTIFICATION-TYPE
    OBJECTS { 
              msdp40-text-error, 
              msdp40-remote-peer-addr 
            }
    STATUS current
    DESCRIPTION
        "Notification of Event MSDP.40

        Message: '$1 to remote peer $2'

        Parameters list:
              $1: msdp40-text-error
              $2: msdp40-remote-peer-addr

        Error sending an MSDP message"
    ::= { msdpNotificationsPrefix 40 }

msdpNotification41 NOTIFICATION-TYPE
    OBJECTS { 
              msdp41-text-error, 
              msdp41-length,
              msdp41-remote-peer-addr 
            }
    STATUS current
    DESCRIPTION
        "Notification of Event MSDP.41

        Message: '$1 (length $2) from remote peer $3'

        Parameters list:
              $1: msdp41-text-error
              $2: msdp41-length
              $3: msdp41-remote-peer-addr

        Error receiving an MSDP message. Format error detected"
    ::= { msdpNotificationsPrefix 41 }

msdpNotification42 NOTIFICATION-TYPE
    OBJECTS { 
              msdp42-text-error 
            }
    STATUS current
    DESCRIPTION
        "Notification of Event MSDP.42

        Message: '$1'

        Parameters list:
              $1: msdp42-text-error

        Generic internal error."
    ::= { msdpNotificationsPrefix 42 }


END
