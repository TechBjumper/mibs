-- file automatically created


TELDAT-TRAP-ICM6-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


icm6TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ICM6 event subsystem."
    REVISION "201401200930Z"
    DESCRIPTION "Initial implementation"
        ::= { telEventTraps 234 }


icm6EventsGroup	OBJECT IDENTIFIER	::= { icm6TrapsMIB 1 }

icm6Notifications	OBJECT IDENTIFIER	::= { icm6TrapsMIB 2 }
icm6NotificationsPrefix	OBJECT IDENTIFIER	::= { icm6Notifications 0 }

icm6EventObjects1 OBJECT-IDENTITY
    STATUS current
    DESCRIPTION
        "Event ICM6.1
        This message is generated when a packet with an icmp6 header too short
        is received. The packet is discarded."
    ::= { icm6EventsGroup 1 }

icm61-source-ip6-address OBJECT-TYPE
    SYNTAX DisplayString
    MAX-ACCESS accessible-for-notify
    STATUS current
    DESCRIPTION
        "Parameter 'source-ip6-address' in event ICM6.1"
    ::= { icm6EventObjects1 1 }

icm61-destination-ip6-address OBJECT-TYPE
    SYNTAX DisplayString
    MAX-ACCESS accessible-for-notify
    STATUS current
    DESCRIPTION
        "Parameter 'destination-ip6-address' in event ICM6.1"
    ::= { icm6EventObjects1 2 }

icm61-icmp6-header-length OBJECT-TYPE
    SYNTAX Integer32
    MAX-ACCESS accessible-for-notify
    STATUS current
    DESCRIPTION
        "Parameter 'icmp6-header-length' in event ICM6.1"
    ::= { icm6EventObjects1 3 }

icm6EventObjects2 OBJECT-IDENTITY
    STATUS current
    DESCRIPTION
        "Event ICM6.2
        This message is generated when an ICMPv6 packet is discarded because its
        checksum field is wrong."
    ::= { icm6EventsGroup 2 }

icm62-source-ip6-address OBJECT-TYPE
    SYNTAX DisplayString
    MAX-ACCESS accessible-for-notify
    STATUS current
    DESCRIPTION
        "Parameter 'source-ip6-address' in event ICM6.2"
    ::= { icm6EventObjects2 1 }

icm62-destination-ip6-address OBJECT-TYPE
    SYNTAX DisplayString
    MAX-ACCESS accessible-for-notify
    STATUS current
    DESCRIPTION
        "Parameter 'destination-ip6-address' in event ICM6.2"
    ::= { icm6EventObjects2 2 }

icm6EventObjects3 OBJECT-IDENTITY
    STATUS current
    DESCRIPTION
        "Event ICM6.3
        This message is generated when an ICMPv6 packet is discarded because its
        type field is wrong."
    ::= { icm6EventsGroup 3 }

icm63-source-ip6-address OBJECT-TYPE
    SYNTAX DisplayString
    MAX-ACCESS accessible-for-notify
    STATUS current
    DESCRIPTION
        "Parameter 'source-ip6-address' in event ICM6.3"
    ::= { icm6EventObjects3 1 }

icm63-destination-ip6-address OBJECT-TYPE
    SYNTAX DisplayString
    MAX-ACCESS accessible-for-notify
    STATUS current
    DESCRIPTION
        "Parameter 'destination-ip6-address' in event ICM6.3"
    ::= { icm6EventObjects3 2 }

icm63-icmp6-packet-type OBJECT-TYPE
    SYNTAX Integer32
    MAX-ACCESS accessible-for-notify
    STATUS current
    DESCRIPTION
        "Parameter 'icmp6-packet-type' in event ICM6.3"
    ::= { icm6EventObjects3 3 }

icm6EventObjects4 OBJECT-IDENTITY
    STATUS current
    DESCRIPTION
        "Event ICM6.4
        This messsage informs about the type of the ICMPv6 packet received."
    ::= { icm6EventsGroup 4 }

icm64-icmp6-packet-type OBJECT-TYPE
    SYNTAX DisplayString
    MAX-ACCESS accessible-for-notify
    STATUS current
    DESCRIPTION
        "Parameter 'icmp6-packet-type' in event ICM6.4"
    ::= { icm6EventObjects4 1 }

icm64-source-ip6-address OBJECT-TYPE
    SYNTAX DisplayString
    MAX-ACCESS accessible-for-notify
    STATUS current
    DESCRIPTION
        "Parameter 'source-ip6-address' in event ICM6.4"
    ::= { icm6EventObjects4 2 }

icm64-destination-ip6-address OBJECT-TYPE
    SYNTAX DisplayString
    MAX-ACCESS accessible-for-notify
    STATUS current
    DESCRIPTION
        "Parameter 'destination-ip6-address' in event ICM6.4"
    ::= { icm6EventObjects4 3 }

icm6EventObjects5 OBJECT-IDENTITY
    STATUS current
    DESCRIPTION
        "Event ICM6.5
        This messsage reports on the type of the ICMPv6 packet to send."
    ::= { icm6EventsGroup 5 }

icm65-packet-type OBJECT-TYPE
    SYNTAX DisplayString
    MAX-ACCESS accessible-for-notify
    STATUS current
    DESCRIPTION
        "Parameter 'packet-type' in event ICM6.5"
    ::= { icm6EventObjects5 1 }

icm65-source-ip6-address OBJECT-TYPE
    SYNTAX DisplayString
    MAX-ACCESS accessible-for-notify
    STATUS current
    DESCRIPTION
        "Parameter 'source-ip6-address' in event ICM6.5"
    ::= { icm6EventObjects5 2 }

icm65-destination-ip6-address OBJECT-TYPE
    SYNTAX DisplayString
    MAX-ACCESS accessible-for-notify
    STATUS current
    DESCRIPTION
        "Parameter 'destination-ip6-address' in event ICM6.5"
    ::= { icm6EventObjects5 3 }


icm6Notification1 NOTIFICATION-TYPE
    OBJECTS { 
              icm61-source-ip6-address, 
              icm61-destination-ip6-address,
              icm61-icmp6-header-length 
            }
    STATUS current
    DESCRIPTION
        "Notification of Event ICM6.1

        Message: 'Discard packet from $1 to $2: ICMP6 header length $3 too short'

        Parameters list:
              $1: icm61-source-ip6-address
              $2: icm61-destination-ip6-address
              $3: icm61-icmp6-header-length

        This message is generated when a packet with an icmp6 header too short
        is received. The packet is discarded."
    ::= { icm6NotificationsPrefix 1 }

icm6Notification2 NOTIFICATION-TYPE
    OBJECTS { 
              icm62-source-ip6-address, 
              icm62-destination-ip6-address 
            }
    STATUS current
    DESCRIPTION
        "Notification of Event ICM6.2

        Message: 'Discard packet from $1 to $2: bad checksum'

        Parameters list:
              $1: icm62-source-ip6-address
              $2: icm62-destination-ip6-address

        This message is generated when an ICMPv6 packet is discarded because its
        checksum field is wrong."
    ::= { icm6NotificationsPrefix 2 }

icm6Notification3 NOTIFICATION-TYPE
    OBJECTS { 
              icm63-source-ip6-address, 
              icm63-destination-ip6-address,
              icm63-icmp6-packet-type 
            }
    STATUS current
    DESCRIPTION
        "Notification of Event ICM6.3

        Message: 'Discard packet from $1 to $2: type $3 wrong'

        Parameters list:
              $1: icm63-source-ip6-address
              $2: icm63-destination-ip6-address
              $3: icm63-icmp6-packet-type

        This message is generated when an ICMPv6 packet is discarded because its
        type field is wrong."
    ::= { icm6NotificationsPrefix 3 }

icm6Notification4 NOTIFICATION-TYPE
    OBJECTS { 
              icm64-icmp6-packet-type, 
              icm64-source-ip6-address,
              icm64-destination-ip6-address 
            }
    STATUS current
    DESCRIPTION
        "Notification of Event ICM6.4

        Message: 'Receive packet $1 from $2 to $3'

        Parameters list:
              $1: icm64-icmp6-packet-type
              $2: icm64-source-ip6-address
              $3: icm64-destination-ip6-address

        This messsage informs about the type of the ICMPv6 packet received."
    ::= { icm6NotificationsPrefix 4 }

icm6Notification5 NOTIFICATION-TYPE
    OBJECTS { 
              icm65-packet-type, 
              icm65-source-ip6-address,
              icm65-destination-ip6-address 
            }
    STATUS current
    DESCRIPTION
        "Notification of Event ICM6.5

        Message: 'Send $1 packet from $2 to $3'

        Parameters list:
              $1: icm65-packet-type
              $2: icm65-source-ip6-address
              $3: icm65-destination-ip6-address

        This messsage reports on the type of the ICMPv6 packet to send."
    ::= { icm6NotificationsPrefix 5 }

icm6Notification6 NOTIFICATION-TYPE
    STATUS current
    DESCRIPTION
        "Notification of Event ICM6.6

        Message: '---'

        ???"
    ::= { icm6NotificationsPrefix 6 }

icm6Notification7 NOTIFICATION-TYPE
    STATUS current
    DESCRIPTION
        "Notification of Event ICM6.7

        Message: '---'

        ???"
    ::= { icm6NotificationsPrefix 7 }

icm6Notification8 NOTIFICATION-TYPE
    STATUS current
    DESCRIPTION
        "Notification of Event ICM6.8

        Message: '---'

        ???"
    ::= { icm6NotificationsPrefix 8 }

icm6Notification9 NOTIFICATION-TYPE
    STATUS current
    DESCRIPTION
        "Notification of Event ICM6.9

        Message: '---'

        ???"
    ::= { icm6NotificationsPrefix 9 }

icm6Notification10 NOTIFICATION-TYPE
    STATUS current
    DESCRIPTION
        "Notification of Event ICM6.10

        Message: '---'

        ???"
    ::= { icm6NotificationsPrefix 10 }

icm6Notification11 NOTIFICATION-TYPE
    STATUS current
    DESCRIPTION
        "Notification of Event ICM6.11

        Message: '---'

        ???"
    ::= { icm6NotificationsPrefix 11 }

icm6Notification12 NOTIFICATION-TYPE
    STATUS current
    DESCRIPTION
        "Notification of Event ICM6.12

        Message: '---'

        ???"
    ::= { icm6NotificationsPrefix 12 }

icm6Notification13 NOTIFICATION-TYPE
    STATUS current
    DESCRIPTION
        "Notification of Event ICM6.13

        Message: '---'

        ???"
    ::= { icm6NotificationsPrefix 13 }

icm6Notification14 NOTIFICATION-TYPE
    STATUS current
    DESCRIPTION
        "Notification of Event ICM6.14

        Message: '---'

        ???"
    ::= { icm6NotificationsPrefix 14 }

icm6Notification15 NOTIFICATION-TYPE
    STATUS current
    DESCRIPTION
        "Notification of Event ICM6.15

        Message: '---'

        ???"
    ::= { icm6NotificationsPrefix 15 }

icm6Notification16 NOTIFICATION-TYPE
    STATUS current
    DESCRIPTION
        "Notification of Event ICM6.16

        Message: '---'

        ???"
    ::= { icm6NotificationsPrefix 16 }

icm6Notification17 NOTIFICATION-TYPE
    STATUS current
    DESCRIPTION
        "Notification of Event ICM6.17

        Message: '---'

        ???"
    ::= { icm6NotificationsPrefix 17 }

icm6Notification18 NOTIFICATION-TYPE
    STATUS current
    DESCRIPTION
        "Notification of Event ICM6.18

        Message: '---'

        ???"
    ::= { icm6NotificationsPrefix 18 }

icm6Notification19 NOTIFICATION-TYPE
    STATUS current
    DESCRIPTION
        "Notification of Event ICM6.19

        Message: '---'

        ???"
    ::= { icm6NotificationsPrefix 19 }

icm6Notification20 NOTIFICATION-TYPE
    STATUS current
    DESCRIPTION
        "Notification of Event ICM6.20

        Message: '---'

        ???"
    ::= { icm6NotificationsPrefix 20 }

icm6Notification21 NOTIFICATION-TYPE
    STATUS current
    DESCRIPTION
        "Notification of Event ICM6.21

        Message: '---'

        ???"
    ::= { icm6NotificationsPrefix 21 }

icm6Notification22 NOTIFICATION-TYPE
    STATUS current
    DESCRIPTION
        "Notification of Event ICM6.22

        Message: '---'

        ???"
    ::= { icm6NotificationsPrefix 22 }

icm6Notification23 NOTIFICATION-TYPE
    STATUS current
    DESCRIPTION
        "Notification of Event ICM6.23

        Message: '---'

        ???"
    ::= { icm6NotificationsPrefix 23 }

icm6Notification24 NOTIFICATION-TYPE
    STATUS current
    DESCRIPTION
        "Notification of Event ICM6.24

        Message: '---'

        ???"
    ::= { icm6NotificationsPrefix 24 }

icm6Notification25 NOTIFICATION-TYPE
    STATUS current
    DESCRIPTION
        "Notification of Event ICM6.25

        Message: '---'

        ???"
    ::= { icm6NotificationsPrefix 25 }

icm6Notification26 NOTIFICATION-TYPE
    STATUS current
    DESCRIPTION
        "Notification of Event ICM6.26

        Message: '---'

        ???"
    ::= { icm6NotificationsPrefix 26 }

icm6Notification27 NOTIFICATION-TYPE
    STATUS current
    DESCRIPTION
        "Notification of Event ICM6.27

        Message: '---'

        ???"
    ::= { icm6NotificationsPrefix 27 }

icm6Notification28 NOTIFICATION-TYPE
    STATUS current
    DESCRIPTION
        "Notification of Event ICM6.28

        Message: '---'

        ???"
    ::= { icm6NotificationsPrefix 28 }

icm6Notification29 NOTIFICATION-TYPE
    STATUS current
    DESCRIPTION
        "Notification of Event ICM6.29

        Message: '---'

        ???"
    ::= { icm6NotificationsPrefix 29 }

icm6Notification30 NOTIFICATION-TYPE
    STATUS current
    DESCRIPTION
        "Notification of Event ICM6.30

        Message: '---'

        ???"
    ::= { icm6NotificationsPrefix 30 }

icm6Notification31 NOTIFICATION-TYPE
    STATUS current
    DESCRIPTION
        "Notification of Event ICM6.31

        Message: '---'

        ???"
    ::= { icm6NotificationsPrefix 31 }

icm6Notification32 NOTIFICATION-TYPE
    STATUS current
    DESCRIPTION
        "Notification of Event ICM6.32

        Message: '---'

        ???"
    ::= { icm6NotificationsPrefix 32 }

icm6Notification33 NOTIFICATION-TYPE
    STATUS current
    DESCRIPTION
        "Notification of Event ICM6.33

        Message: '---'

        ???"
    ::= { icm6NotificationsPrefix 33 }

icm6Notification34 NOTIFICATION-TYPE
    STATUS current
    DESCRIPTION
        "Notification of Event ICM6.34

        Message: '---'

        ???"
    ::= { icm6NotificationsPrefix 34 }

icm6Notification35 NOTIFICATION-TYPE
    STATUS current
    DESCRIPTION
        "Notification of Event ICM6.35

        Message: '---'

        ???"
    ::= { icm6NotificationsPrefix 35 }

icm6Notification36 NOTIFICATION-TYPE
    STATUS current
    DESCRIPTION
        "Notification of Event ICM6.36

        Message: '---'

        ???"
    ::= { icm6NotificationsPrefix 36 }

icm6Notification37 NOTIFICATION-TYPE
    STATUS current
    DESCRIPTION
        "Notification of Event ICM6.37

        Message: '---'

        ???"
    ::= { icm6NotificationsPrefix 37 }

icm6Notification38 NOTIFICATION-TYPE
    STATUS current
    DESCRIPTION
        "Notification of Event ICM6.38

        Message: '---'

        ???"
    ::= { icm6NotificationsPrefix 38 }

icm6Notification39 NOTIFICATION-TYPE
    STATUS current
    DESCRIPTION
        "Notification of Event ICM6.39

        Message: '---'

        ???"
    ::= { icm6NotificationsPrefix 39 }

icm6Notification40 NOTIFICATION-TYPE
    STATUS current
    DESCRIPTION
        "Notification of Event ICM6.40

        Message: '---'

        ???"
    ::= { icm6NotificationsPrefix 40 }

icm6Notification41 NOTIFICATION-TYPE
    STATUS current
    DESCRIPTION
        "Notification of Event ICM6.41

        Message: '---'

        ???"
    ::= { icm6NotificationsPrefix 41 }

icm6Notification42 NOTIFICATION-TYPE
    STATUS current
    DESCRIPTION
        "Notification of Event ICM6.42

        Message: '---'

        ???"
    ::= { icm6NotificationsPrefix 42 }

icm6Notification43 NOTIFICATION-TYPE
    STATUS current
    DESCRIPTION
        "Notification of Event ICM6.43

        Message: '---'

        ???"
    ::= { icm6NotificationsPrefix 43 }

icm6Notification44 NOTIFICATION-TYPE
    STATUS current
    DESCRIPTION
        "Notification of Event ICM6.44

        Message: '---'

        ???"
    ::= { icm6NotificationsPrefix 44 }

icm6Notification45 NOTIFICATION-TYPE
    STATUS current
    DESCRIPTION
        "Notification of Event ICM6.45

        Message: '---'

        ???"
    ::= { icm6NotificationsPrefix 45 }

icm6Notification46 NOTIFICATION-TYPE
    STATUS current
    DESCRIPTION
        "Notification of Event ICM6.46

        Message: '---'

        ???"
    ::= { icm6NotificationsPrefix 46 }

icm6Notification47 NOTIFICATION-TYPE
    STATUS current
    DESCRIPTION
        "Notification of Event ICM6.47

        Message: '---'

        ???"
    ::= { icm6NotificationsPrefix 47 }

icm6Notification48 NOTIFICATION-TYPE
    STATUS current
    DESCRIPTION
        "Notification of Event ICM6.48

        Message: '---'

        ???"
    ::= { icm6NotificationsPrefix 48 }

icm6Notification49 NOTIFICATION-TYPE
    STATUS current
    DESCRIPTION
        "Notification of Event ICM6.49

        Message: '---'

        ???"
    ::= { icm6NotificationsPrefix 49 }

icm6Notification50 NOTIFICATION-TYPE
    STATUS current
    DESCRIPTION
        "Notification of Event ICM6.50

        Message: '---'

        ???"
    ::= { icm6NotificationsPrefix 50 }

icm6Notification51 NOTIFICATION-TYPE
    STATUS current
    DESCRIPTION
        "Notification of Event ICM6.51

        Message: '---'

        ???"
    ::= { icm6NotificationsPrefix 51 }

icm6Notification52 NOTIFICATION-TYPE
    STATUS current
    DESCRIPTION
        "Notification of Event ICM6.52

        Message: '---'

        ???"
    ::= { icm6NotificationsPrefix 52 }

icm6Notification53 NOTIFICATION-TYPE
    STATUS current
    DESCRIPTION
        "Notification of Event ICM6.53

        Message: '---'

        ???"
    ::= { icm6NotificationsPrefix 53 }

icm6Notification54 NOTIFICATION-TYPE
    STATUS current
    DESCRIPTION
        "Notification of Event ICM6.54

        Message: '---'

        ???"
    ::= { icm6NotificationsPrefix 54 }

icm6Notification55 NOTIFICATION-TYPE
    STATUS current
    DESCRIPTION
        "Notification of Event ICM6.55

        Message: '---'

        ???"
    ::= { icm6NotificationsPrefix 55 }

icm6Notification56 NOTIFICATION-TYPE
    STATUS current
    DESCRIPTION
        "Notification of Event ICM6.56

        Message: '---'

        ???"
    ::= { icm6NotificationsPrefix 56 }

icm6Notification57 NOTIFICATION-TYPE
    STATUS current
    DESCRIPTION
        "Notification of Event ICM6.57

        Message: '---'

        ???"
    ::= { icm6NotificationsPrefix 57 }

icm6Notification58 NOTIFICATION-TYPE
    STATUS current
    DESCRIPTION
        "Notification of Event ICM6.58

        Message: '---'

        ???"
    ::= { icm6NotificationsPrefix 58 }

icm6Notification59 NOTIFICATION-TYPE
    STATUS current
    DESCRIPTION
        "Notification of Event ICM6.59

        Message: '---'

        ???"
    ::= { icm6NotificationsPrefix 59 }

icm6Notification60 NOTIFICATION-TYPE
    STATUS current
    DESCRIPTION
        "Notification of Event ICM6.60

        Message: '---'

        ???"
    ::= { icm6NotificationsPrefix 60 }

icm6Notification61 NOTIFICATION-TYPE
    STATUS current
    DESCRIPTION
        "Notification of Event ICM6.61

        Message: '---'

        ???"
    ::= { icm6NotificationsPrefix 61 }

icm6Notification62 NOTIFICATION-TYPE
    STATUS current
    DESCRIPTION
        "Notification of Event ICM6.62

        Message: '---'

        ???"
    ::= { icm6NotificationsPrefix 62 }

icm6Notification63 NOTIFICATION-TYPE
    STATUS current
    DESCRIPTION
        "Notification of Event ICM6.63

        Message: '---'

        ???"
    ::= { icm6NotificationsPrefix 63 }

icm6Notification64 NOTIFICATION-TYPE
    STATUS current
    DESCRIPTION
        "Notification of Event ICM6.64

        Message: '---'

        ???"
    ::= { icm6NotificationsPrefix 64 }

icm6Notification65 NOTIFICATION-TYPE
    STATUS current
    DESCRIPTION
        "Notification of Event ICM6.65

        Message: '---'

        ???"
    ::= { icm6NotificationsPrefix 65 }

icm6Notification66 NOTIFICATION-TYPE
    STATUS current
    DESCRIPTION
        "Notification of Event ICM6.66

        Message: '---'

        ???"
    ::= { icm6NotificationsPrefix 66 }

icm6Notification67 NOTIFICATION-TYPE
    STATUS current
    DESCRIPTION
        "Notification of Event ICM6.67

        Message: '---'

        ???"
    ::= { icm6NotificationsPrefix 67 }

icm6Notification68 NOTIFICATION-TYPE
    STATUS current
    DESCRIPTION
        "Notification of Event ICM6.68

        Message: '---'

        ???"
    ::= { icm6NotificationsPrefix 68 }

icm6Notification69 NOTIFICATION-TYPE
    STATUS current
    DESCRIPTION
        "Notification of Event ICM6.69

        Message: '---'

        ???"
    ::= { icm6NotificationsPrefix 69 }

icm6Notification70 NOTIFICATION-TYPE
    STATUS current
    DESCRIPTION
        "Notification of Event ICM6.70

        Message: '---'

        ???"
    ::= { icm6NotificationsPrefix 70 }

icm6Notification71 NOTIFICATION-TYPE
    STATUS current
    DESCRIPTION
        "Notification of Event ICM6.71

        Message: '---'

        ???"
    ::= { icm6NotificationsPrefix 71 }

icm6Notification72 NOTIFICATION-TYPE
    STATUS current
    DESCRIPTION
        "Notification of Event ICM6.72

        Message: '---'

        ???"
    ::= { icm6NotificationsPrefix 72 }

icm6Notification73 NOTIFICATION-TYPE
    STATUS current
    DESCRIPTION
        "Notification of Event ICM6.73

        Message: '---'

        ???"
    ::= { icm6NotificationsPrefix 73 }

icm6Notification74 NOTIFICATION-TYPE
    STATUS current
    DESCRIPTION
        "Notification of Event ICM6.74

        Message: '---'

        ???"
    ::= { icm6NotificationsPrefix 74 }

icm6Notification75 NOTIFICATION-TYPE
    STATUS current
    DESCRIPTION
        "Notification of Event ICM6.75

        Message: '---'

        ???"
    ::= { icm6NotificationsPrefix 75 }

icm6Notification76 NOTIFICATION-TYPE
    STATUS current
    DESCRIPTION
        "Notification of Event ICM6.76

        Message: '---'

        ???"
    ::= { icm6NotificationsPrefix 76 }

icm6Notification77 NOTIFICATION-TYPE
    STATUS current
    DESCRIPTION
        "Notification of Event ICM6.77

        Message: '---'

        ???"
    ::= { icm6NotificationsPrefix 77 }

icm6Notification78 NOTIFICATION-TYPE
    STATUS current
    DESCRIPTION
        "Notification of Event ICM6.78

        Message: '---'

        ???"
    ::= { icm6NotificationsPrefix 78 }

icm6Notification79 NOTIFICATION-TYPE
    STATUS current
    DESCRIPTION
        "Notification of Event ICM6.79

        Message: '---'

        ???"
    ::= { icm6NotificationsPrefix 79 }

icm6Notification80 NOTIFICATION-TYPE
    STATUS current
    DESCRIPTION
        "Notification of Event ICM6.80

        Message: '---'

        ???"
    ::= { icm6NotificationsPrefix 80 }

icm6Notification81 NOTIFICATION-TYPE
    STATUS current
    DESCRIPTION
        "Notification of Event ICM6.81

        Message: '---'

        ???"
    ::= { icm6NotificationsPrefix 81 }

icm6Notification82 NOTIFICATION-TYPE
    STATUS current
    DESCRIPTION
        "Notification of Event ICM6.82

        Message: '---'

        ???"
    ::= { icm6NotificationsPrefix 82 }

icm6Notification83 NOTIFICATION-TYPE
    STATUS current
    DESCRIPTION
        "Notification of Event ICM6.83

        Message: '---'

        ???"
    ::= { icm6NotificationsPrefix 83 }

icm6Notification84 NOTIFICATION-TYPE
    STATUS current
    DESCRIPTION
        "Notification of Event ICM6.84

        Message: '---'

        ???"
    ::= { icm6NotificationsPrefix 84 }

icm6Notification85 NOTIFICATION-TYPE
    STATUS current
    DESCRIPTION
        "Notification of Event ICM6.85

        Message: '---'

        ???"
    ::= { icm6NotificationsPrefix 85 }

icm6Notification86 NOTIFICATION-TYPE
    STATUS current
    DESCRIPTION
        "Notification of Event ICM6.86

        Message: '---'

        ???"
    ::= { icm6NotificationsPrefix 86 }

icm6Notification87 NOTIFICATION-TYPE
    STATUS current
    DESCRIPTION
        "Notification of Event ICM6.87

        Message: '---'

        ???"
    ::= { icm6NotificationsPrefix 87 }

icm6Notification88 NOTIFICATION-TYPE
    STATUS current
    DESCRIPTION
        "Notification of Event ICM6.88

        Message: '---'

        ???"
    ::= { icm6NotificationsPrefix 88 }

icm6Notification89 NOTIFICATION-TYPE
    STATUS current
    DESCRIPTION
        "Notification of Event ICM6.89

        Message: '---'

        ???"
    ::= { icm6NotificationsPrefix 89 }

icm6Notification90 NOTIFICATION-TYPE
    STATUS current
    DESCRIPTION
        "Notification of Event ICM6.90

        Message: '---'

        ???"
    ::= { icm6NotificationsPrefix 90 }

icm6Notification91 NOTIFICATION-TYPE
    STATUS current
    DESCRIPTION
        "Notification of Event ICM6.91

        Message: '---'

        ???"
    ::= { icm6NotificationsPrefix 91 }

icm6Notification92 NOTIFICATION-TYPE
    STATUS current
    DESCRIPTION
        "Notification of Event ICM6.92

        Message: '---'

        ???"
    ::= { icm6NotificationsPrefix 92 }

icm6Notification93 NOTIFICATION-TYPE
    STATUS current
    DESCRIPTION
        "Notification of Event ICM6.93

        Message: '---'

        ???"
    ::= { icm6NotificationsPrefix 93 }

icm6Notification94 NOTIFICATION-TYPE
    STATUS current
    DESCRIPTION
        "Notification of Event ICM6.94

        Message: '---'

        ???"
    ::= { icm6NotificationsPrefix 94 }

icm6Notification95 NOTIFICATION-TYPE
    STATUS current
    DESCRIPTION
        "Notification of Event ICM6.95

        Message: '---'

        ???"
    ::= { icm6NotificationsPrefix 95 }

icm6Notification96 NOTIFICATION-TYPE
    STATUS current
    DESCRIPTION
        "Notification of Event ICM6.96

        Message: '---'

        ???"
    ::= { icm6NotificationsPrefix 96 }

icm6Notification97 NOTIFICATION-TYPE
    STATUS current
    DESCRIPTION
        "Notification of Event ICM6.97

        Message: '---'

        ???"
    ::= { icm6NotificationsPrefix 97 }

icm6Notification98 NOTIFICATION-TYPE
    STATUS current
    DESCRIPTION
        "Notification of Event ICM6.98

        Message: '---'

        ???"
    ::= { icm6NotificationsPrefix 98 }

icm6Notification99 NOTIFICATION-TYPE
    STATUS current
    DESCRIPTION
        "Notification of Event ICM6.99

        Message: '---'

        ???"
    ::= { icm6NotificationsPrefix 99 }

icm6Notification100 NOTIFICATION-TYPE
    STATUS current
    DESCRIPTION
        "Notification of Event ICM6.100

        Message: '---'

        ???"
    ::= { icm6NotificationsPrefix 100 }

icm6Notification101 NOTIFICATION-TYPE
    STATUS current
    DESCRIPTION
        "Notification of Event ICM6.101

        Message: '---'

        ???"
    ::= { icm6NotificationsPrefix 101 }

icm6Notification102 NOTIFICATION-TYPE
    STATUS current
    DESCRIPTION
        "Notification of Event ICM6.102

        Message: '---'

        ???"
    ::= { icm6NotificationsPrefix 102 }

icm6Notification103 NOTIFICATION-TYPE
    STATUS current
    DESCRIPTION
        "Notification of Event ICM6.103

        Message: '---'

        ???"
    ::= { icm6NotificationsPrefix 103 }

icm6Notification104 NOTIFICATION-TYPE
    STATUS current
    DESCRIPTION
        "Notification of Event ICM6.104

        Message: '---'

        ???"
    ::= { icm6NotificationsPrefix 104 }

icm6Notification105 NOTIFICATION-TYPE
    STATUS current
    DESCRIPTION
        "Notification of Event ICM6.105

        Message: '---'

        ???"
    ::= { icm6NotificationsPrefix 105 }

icm6Notification106 NOTIFICATION-TYPE
    STATUS current
    DESCRIPTION
        "Notification of Event ICM6.106

        Message: '---'

        ???"
    ::= { icm6NotificationsPrefix 106 }

icm6Notification107 NOTIFICATION-TYPE
    STATUS current
    DESCRIPTION
        "Notification of Event ICM6.107

        Message: '---'

        ???"
    ::= { icm6NotificationsPrefix 107 }

icm6Notification108 NOTIFICATION-TYPE
    STATUS current
    DESCRIPTION
        "Notification of Event ICM6.108

        Message: '---'

        ???"
    ::= { icm6NotificationsPrefix 108 }

icm6Notification109 NOTIFICATION-TYPE
    STATUS current
    DESCRIPTION
        "Notification of Event ICM6.109

        Message: '---'

        ???"
    ::= { icm6NotificationsPrefix 109 }

icm6Notification110 NOTIFICATION-TYPE
    STATUS current
    DESCRIPTION
        "Notification of Event ICM6.110

        Message: '---'

        ???"
    ::= { icm6NotificationsPrefix 110 }

icm6Notification111 NOTIFICATION-TYPE
    STATUS current
    DESCRIPTION
        "Notification of Event ICM6.111

        Message: '---'

        ???"
    ::= { icm6NotificationsPrefix 111 }

icm6Notification112 NOTIFICATION-TYPE
    STATUS current
    DESCRIPTION
        "Notification of Event ICM6.112

        Message: '---'

        ???"
    ::= { icm6NotificationsPrefix 112 }

icm6Notification113 NOTIFICATION-TYPE
    STATUS current
    DESCRIPTION
        "Notification of Event ICM6.113

        Message: '---'

        ???"
    ::= { icm6NotificationsPrefix 113 }

icm6Notification114 NOTIFICATION-TYPE
    STATUS current
    DESCRIPTION
        "Notification of Event ICM6.114

        Message: '---'

        ???"
    ::= { icm6NotificationsPrefix 114 }

icm6Notification115 NOTIFICATION-TYPE
    STATUS current
    DESCRIPTION
        "Notification of Event ICM6.115

        Message: '---'

        ???"
    ::= { icm6NotificationsPrefix 115 }

icm6Notification116 NOTIFICATION-TYPE
    STATUS current
    DESCRIPTION
        "Notification of Event ICM6.116

        Message: '---'

        ???"
    ::= { icm6NotificationsPrefix 116 }

icm6Notification117 NOTIFICATION-TYPE
    STATUS current
    DESCRIPTION
        "Notification of Event ICM6.117

        Message: '---'

        ???"
    ::= { icm6NotificationsPrefix 117 }

icm6Notification118 NOTIFICATION-TYPE
    STATUS current
    DESCRIPTION
        "Notification of Event ICM6.118

        Message: '---'

        ???"
    ::= { icm6NotificationsPrefix 118 }

icm6Notification119 NOTIFICATION-TYPE
    STATUS current
    DESCRIPTION
        "Notification of Event ICM6.119

        Message: '---'

        ???"
    ::= { icm6NotificationsPrefix 119 }

icm6Notification120 NOTIFICATION-TYPE
    STATUS current
    DESCRIPTION
        "Notification of Event ICM6.120

        Message: '---'

        ???"
    ::= { icm6NotificationsPrefix 120 }

icm6Notification121 NOTIFICATION-TYPE
    STATUS current
    DESCRIPTION
        "Notification of Event ICM6.121

        Message: '---'

        ???"
    ::= { icm6NotificationsPrefix 121 }

icm6Notification122 NOTIFICATION-TYPE
    STATUS current
    DESCRIPTION
        "Notification of Event ICM6.122

        Message: '---'

        ???"
    ::= { icm6NotificationsPrefix 122 }

icm6Notification123 NOTIFICATION-TYPE
    STATUS current
    DESCRIPTION
        "Notification of Event ICM6.123

        Message: '---'

        ???"
    ::= { icm6NotificationsPrefix 123 }

icm6Notification124 NOTIFICATION-TYPE
    STATUS current
    DESCRIPTION
        "Notification of Event ICM6.124

        Message: '---'

        ???"
    ::= { icm6NotificationsPrefix 124 }

icm6Notification125 NOTIFICATION-TYPE
    STATUS current
    DESCRIPTION
        "Notification of Event ICM6.125

        Message: '---'

        ???"
    ::= { icm6NotificationsPrefix 125 }

icm6Notification126 NOTIFICATION-TYPE
    STATUS current
    DESCRIPTION
        "Notification of Event ICM6.126

        Message: '---'

        ???"
    ::= { icm6NotificationsPrefix 126 }

icm6Notification127 NOTIFICATION-TYPE
    STATUS current
    DESCRIPTION
        "Notification of Event ICM6.127

        Message: '---'

        ???"
    ::= { icm6NotificationsPrefix 127 }

icm6Notification128 NOTIFICATION-TYPE
    STATUS current
    DESCRIPTION
        "Notification of Event ICM6.128

        Message: '---'

        ???"
    ::= { icm6NotificationsPrefix 128 }

icm6Notification129 NOTIFICATION-TYPE
    STATUS current
    DESCRIPTION
        "Notification of Event ICM6.129

        Message: '---'

        ???"
    ::= { icm6NotificationsPrefix 129 }

icm6Notification130 NOTIFICATION-TYPE
    STATUS current
    DESCRIPTION
        "Notification of Event ICM6.130

        Message: '---'

        ???"
    ::= { icm6NotificationsPrefix 130 }

icm6Notification131 NOTIFICATION-TYPE
    STATUS current
    DESCRIPTION
        "Notification of Event ICM6.131

        Message: '---'

        ???"
    ::= { icm6NotificationsPrefix 131 }

icm6Notification132 NOTIFICATION-TYPE
    STATUS current
    DESCRIPTION
        "Notification of Event ICM6.132

        Message: '---'

        ???"
    ::= { icm6NotificationsPrefix 132 }

icm6Notification133 NOTIFICATION-TYPE
    STATUS current
    DESCRIPTION
        "Notification of Event ICM6.133

        Message: '---'

        ???"
    ::= { icm6NotificationsPrefix 133 }

icm6Notification134 NOTIFICATION-TYPE
    STATUS current
    DESCRIPTION
        "Notification of Event ICM6.134

        Message: '---'

        ???"
    ::= { icm6NotificationsPrefix 134 }

icm6Notification135 NOTIFICATION-TYPE
    STATUS current
    DESCRIPTION
        "Notification of Event ICM6.135

        Message: '---'

        ???"
    ::= { icm6NotificationsPrefix 135 }

icm6Notification136 NOTIFICATION-TYPE
    STATUS current
    DESCRIPTION
        "Notification of Event ICM6.136

        Message: '---'

        ???"
    ::= { icm6NotificationsPrefix 136 }

icm6Notification137 NOTIFICATION-TYPE
    STATUS current
    DESCRIPTION
        "Notification of Event ICM6.137

        Message: '---'

        ???"
    ::= { icm6NotificationsPrefix 137 }

icm6Notification138 NOTIFICATION-TYPE
    STATUS current
    DESCRIPTION
        "Notification of Event ICM6.138

        Message: '---'

        ???"
    ::= { icm6NotificationsPrefix 138 }

icm6Notification139 NOTIFICATION-TYPE
    STATUS current
    DESCRIPTION
        "Notification of Event ICM6.139

        Message: '---'

        ???"
    ::= { icm6NotificationsPrefix 139 }

icm6Notification140 NOTIFICATION-TYPE
    STATUS current
    DESCRIPTION
        "Notification of Event ICM6.140

        Message: '---'

        ???"
    ::= { icm6NotificationsPrefix 140 }

icm6Notification141 NOTIFICATION-TYPE
    STATUS current
    DESCRIPTION
        "Notification of Event ICM6.141

        Message: '---'

        ???"
    ::= { icm6NotificationsPrefix 141 }

icm6Notification142 NOTIFICATION-TYPE
    STATUS current
    DESCRIPTION
        "Notification of Event ICM6.142

        Message: '---'

        ???"
    ::= { icm6NotificationsPrefix 142 }

icm6Notification143 NOTIFICATION-TYPE
    STATUS current
    DESCRIPTION
        "Notification of Event ICM6.143

        Message: '---'

        ???"
    ::= { icm6NotificationsPrefix 143 }

icm6Notification144 NOTIFICATION-TYPE
    STATUS current
    DESCRIPTION
        "Notification of Event ICM6.144

        Message: '---'

        ???"
    ::= { icm6NotificationsPrefix 144 }

icm6Notification145 NOTIFICATION-TYPE
    STATUS current
    DESCRIPTION
        "Notification of Event ICM6.145

        Message: '---'

        ???"
    ::= { icm6NotificationsPrefix 145 }

icm6Notification146 NOTIFICATION-TYPE
    STATUS current
    DESCRIPTION
        "Notification of Event ICM6.146

        Message: '---'

        ???"
    ::= { icm6NotificationsPrefix 146 }

icm6Notification147 NOTIFICATION-TYPE
    STATUS current
    DESCRIPTION
        "Notification of Event ICM6.147

        Message: '---'

        ???"
    ::= { icm6NotificationsPrefix 147 }

icm6Notification148 NOTIFICATION-TYPE
    STATUS current
    DESCRIPTION
        "Notification of Event ICM6.148

        Message: '---'

        ???"
    ::= { icm6NotificationsPrefix 148 }

icm6Notification149 NOTIFICATION-TYPE
    STATUS current
    DESCRIPTION
        "Notification of Event ICM6.149

        Message: '---'

        ???"
    ::= { icm6NotificationsPrefix 149 }

icm6Notification150 NOTIFICATION-TYPE
    STATUS current
    DESCRIPTION
        "Notification of Event ICM6.150

        Message: '---'

        ???"
    ::= { icm6NotificationsPrefix 150 }

icm6Notification151 NOTIFICATION-TYPE
    STATUS current
    DESCRIPTION
        "Notification of Event ICM6.151

        Message: '---'

        ???"
    ::= { icm6NotificationsPrefix 151 }

icm6Notification152 NOTIFICATION-TYPE
    STATUS current
    DESCRIPTION
        "Notification of Event ICM6.152

        Message: '---'

        ???"
    ::= { icm6NotificationsPrefix 152 }

icm6Notification153 NOTIFICATION-TYPE
    STATUS current
    DESCRIPTION
        "Notification of Event ICM6.153

        Message: '---'

        ???"
    ::= { icm6NotificationsPrefix 153 }

icm6Notification154 NOTIFICATION-TYPE
    STATUS current
    DESCRIPTION
        "Notification of Event ICM6.154

        Message: '---'

        ???"
    ::= { icm6NotificationsPrefix 154 }

icm6Notification155 NOTIFICATION-TYPE
    STATUS current
    DESCRIPTION
        "Notification of Event ICM6.155

        Message: '---'

        ???"
    ::= { icm6NotificationsPrefix 155 }

icm6Notification156 NOTIFICATION-TYPE
    STATUS current
    DESCRIPTION
        "Notification of Event ICM6.156

        Message: '---'

        ???"
    ::= { icm6NotificationsPrefix 156 }

icm6Notification157 NOTIFICATION-TYPE
    STATUS current
    DESCRIPTION
        "Notification of Event ICM6.157

        Message: '---'

        ???"
    ::= { icm6NotificationsPrefix 157 }

icm6Notification158 NOTIFICATION-TYPE
    STATUS current
    DESCRIPTION
        "Notification of Event ICM6.158

        Message: '---'

        ???"
    ::= { icm6NotificationsPrefix 158 }

icm6Notification159 NOTIFICATION-TYPE
    STATUS current
    DESCRIPTION
        "Notification of Event ICM6.159

        Message: '---'

        ???"
    ::= { icm6NotificationsPrefix 159 }

icm6Notification160 NOTIFICATION-TYPE
    STATUS current
    DESCRIPTION
        "Notification of Event ICM6.160

        Message: '---'

        ???"
    ::= { icm6NotificationsPrefix 160 }

icm6Notification161 NOTIFICATION-TYPE
    STATUS current
    DESCRIPTION
        "Notification of Event ICM6.161

        Message: '---'

        ???"
    ::= { icm6NotificationsPrefix 161 }

icm6Notification162 NOTIFICATION-TYPE
    STATUS current
    DESCRIPTION
        "Notification of Event ICM6.162

        Message: '---'

        ???"
    ::= { icm6NotificationsPrefix 162 }

icm6Notification163 NOTIFICATION-TYPE
    STATUS current
    DESCRIPTION
        "Notification of Event ICM6.163

        Message: '---'

        ???"
    ::= { icm6NotificationsPrefix 163 }

icm6Notification164 NOTIFICATION-TYPE
    STATUS current
    DESCRIPTION
        "Notification of Event ICM6.164

        Message: '---'

        ???"
    ::= { icm6NotificationsPrefix 164 }

icm6Notification165 NOTIFICATION-TYPE
    STATUS current
    DESCRIPTION
        "Notification of Event ICM6.165

        Message: '---'

        ???"
    ::= { icm6NotificationsPrefix 165 }

icm6Notification166 NOTIFICATION-TYPE
    STATUS current
    DESCRIPTION
        "Notification of Event ICM6.166

        Message: '---'

        ???"
    ::= { icm6NotificationsPrefix 166 }

icm6Notification167 NOTIFICATION-TYPE
    STATUS current
    DESCRIPTION
        "Notification of Event ICM6.167

        Message: '---'

        ???"
    ::= { icm6NotificationsPrefix 167 }

icm6Notification168 NOTIFICATION-TYPE
    STATUS current
    DESCRIPTION
        "Notification of Event ICM6.168

        Message: '---'

        ???"
    ::= { icm6NotificationsPrefix 168 }

icm6Notification169 NOTIFICATION-TYPE
    STATUS current
    DESCRIPTION
        "Notification of Event ICM6.169

        Message: '---'

        ???"
    ::= { icm6NotificationsPrefix 169 }

icm6Notification170 NOTIFICATION-TYPE
    STATUS current
    DESCRIPTION
        "Notification of Event ICM6.170

        Message: '---'

        ???"
    ::= { icm6NotificationsPrefix 170 }

icm6Notification171 NOTIFICATION-TYPE
    STATUS current
    DESCRIPTION
        "Notification of Event ICM6.171

        Message: '---'

        ???"
    ::= { icm6NotificationsPrefix 171 }

icm6Notification172 NOTIFICATION-TYPE
    STATUS current
    DESCRIPTION
        "Notification of Event ICM6.172

        Message: '---'

        ???"
    ::= { icm6NotificationsPrefix 172 }

icm6Notification173 NOTIFICATION-TYPE
    STATUS current
    DESCRIPTION
        "Notification of Event ICM6.173

        Message: '---'

        ???"
    ::= { icm6NotificationsPrefix 173 }

icm6Notification174 NOTIFICATION-TYPE
    STATUS current
    DESCRIPTION
        "Notification of Event ICM6.174

        Message: '---'

        ???"
    ::= { icm6NotificationsPrefix 174 }

icm6Notification175 NOTIFICATION-TYPE
    STATUS current
    DESCRIPTION
        "Notification of Event ICM6.175

        Message: '---'

        ???"
    ::= { icm6NotificationsPrefix 175 }

icm6Notification176 NOTIFICATION-TYPE
    STATUS current
    DESCRIPTION
        "Notification of Event ICM6.176

        Message: '---'

        ???"
    ::= { icm6NotificationsPrefix 176 }

icm6Notification177 NOTIFICATION-TYPE
    STATUS current
    DESCRIPTION
        "Notification of Event ICM6.177

        Message: '---'

        ???"
    ::= { icm6NotificationsPrefix 177 }

icm6Notification178 NOTIFICATION-TYPE
    STATUS current
    DESCRIPTION
        "Notification of Event ICM6.178

        Message: '---'

        ???"
    ::= { icm6NotificationsPrefix 178 }

icm6Notification179 NOTIFICATION-TYPE
    STATUS current
    DESCRIPTION
        "Notification of Event ICM6.179

        Message: '---'

        ???"
    ::= { icm6NotificationsPrefix 179 }

icm6Notification180 NOTIFICATION-TYPE
    STATUS current
    DESCRIPTION
        "Notification of Event ICM6.180

        Message: '---'

        ???"
    ::= { icm6NotificationsPrefix 180 }

icm6Notification181 NOTIFICATION-TYPE
    STATUS current
    DESCRIPTION
        "Notification of Event ICM6.181

        Message: '---'

        ???"
    ::= { icm6NotificationsPrefix 181 }

icm6Notification182 NOTIFICATION-TYPE
    STATUS current
    DESCRIPTION
        "Notification of Event ICM6.182

        Message: '---'

        ???"
    ::= { icm6NotificationsPrefix 182 }

icm6Notification183 NOTIFICATION-TYPE
    STATUS current
    DESCRIPTION
        "Notification of Event ICM6.183

        Message: '---'

        ???"
    ::= { icm6NotificationsPrefix 183 }

icm6Notification184 NOTIFICATION-TYPE
    STATUS current
    DESCRIPTION
        "Notification of Event ICM6.184

        Message: '---'

        ???"
    ::= { icm6NotificationsPrefix 184 }

icm6Notification185 NOTIFICATION-TYPE
    STATUS current
    DESCRIPTION
        "Notification of Event ICM6.185

        Message: '---'

        ???"
    ::= { icm6NotificationsPrefix 185 }

icm6Notification186 NOTIFICATION-TYPE
    STATUS current
    DESCRIPTION
        "Notification of Event ICM6.186

        Message: '---'

        ???"
    ::= { icm6NotificationsPrefix 186 }

icm6Notification187 NOTIFICATION-TYPE
    STATUS current
    DESCRIPTION
        "Notification of Event ICM6.187

        Message: '---'

        ???"
    ::= { icm6NotificationsPrefix 187 }

icm6Notification188 NOTIFICATION-TYPE
    STATUS current
    DESCRIPTION
        "Notification of Event ICM6.188

        Message: '---'

        ???"
    ::= { icm6NotificationsPrefix 188 }

icm6Notification189 NOTIFICATION-TYPE
    STATUS current
    DESCRIPTION
        "Notification of Event ICM6.189

        Message: '---'

        ???"
    ::= { icm6NotificationsPrefix 189 }

icm6Notification190 NOTIFICATION-TYPE
    STATUS current
    DESCRIPTION
        "Notification of Event ICM6.190

        Message: '---'

        ???"
    ::= { icm6NotificationsPrefix 190 }

icm6Notification191 NOTIFICATION-TYPE
    STATUS current
    DESCRIPTION
        "Notification of Event ICM6.191

        Message: '---'

        ???"
    ::= { icm6NotificationsPrefix 191 }

icm6Notification192 NOTIFICATION-TYPE
    STATUS current
    DESCRIPTION
        "Notification of Event ICM6.192

        Message: '---'

        ???"
    ::= { icm6NotificationsPrefix 192 }

icm6Notification193 NOTIFICATION-TYPE
    STATUS current
    DESCRIPTION
        "Notification of Event ICM6.193

        Message: '---'

        ???"
    ::= { icm6NotificationsPrefix 193 }

icm6Notification194 NOTIFICATION-TYPE
    STATUS current
    DESCRIPTION
        "Notification of Event ICM6.194

        Message: '---'

        ???"
    ::= { icm6NotificationsPrefix 194 }

icm6Notification195 NOTIFICATION-TYPE
    STATUS current
    DESCRIPTION
        "Notification of Event ICM6.195

        Message: '---'

        ???"
    ::= { icm6NotificationsPrefix 195 }

icm6Notification196 NOTIFICATION-TYPE
    STATUS current
    DESCRIPTION
        "Notification of Event ICM6.196

        Message: '---'

        ???"
    ::= { icm6NotificationsPrefix 196 }

icm6Notification197 NOTIFICATION-TYPE
    STATUS current
    DESCRIPTION
        "Notification of Event ICM6.197

        Message: '---'

        ???"
    ::= { icm6NotificationsPrefix 197 }

icm6Notification198 NOTIFICATION-TYPE
    STATUS current
    DESCRIPTION
        "Notification of Event ICM6.198

        Message: '---'

        ???"
    ::= { icm6NotificationsPrefix 198 }

icm6Notification199 NOTIFICATION-TYPE
    STATUS current
    DESCRIPTION
        "Notification of Event ICM6.199

        Message: '---'

        ???"
    ::= { icm6NotificationsPrefix 199 }

icm6Notification200 NOTIFICATION-TYPE
    STATUS current
    DESCRIPTION
        "Notification of Event ICM6.200

        Message: '---'

        ???"
    ::= { icm6NotificationsPrefix 200 }


END
