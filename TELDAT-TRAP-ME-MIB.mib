-- file automatically created


TELDAT-TRAP-ME-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


meTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ME event subsystem."
    REVISION "201401200930Z"
    DESCRIPTION "Initial implementation"
        ::= { telEventTraps 201 }


meEventsGroup	OBJECT IDENTIFIER	::= { meTrapsMIB 1 }

meNotifications	OBJECT IDENTIFIER	::= { meTrapsMIB 2 }
meNotificationsPrefix	OBJECT IDENTIFIER	::= { meNotifications 0 }

meEventObjects1 OBJECT-IDENTITY
    STATUS current
    DESCRIPTION
        "Event ME.1
        Data has been received from Serial Terminal."
    ::= { meEventsGroup 1 }

me1-bytes-number OBJECT-TYPE
    SYNTAX Integer32
    MAX-ACCESS accessible-for-notify
    STATUS current
    DESCRIPTION
        "Parameter 'bytes-number' in event ME.1"
    ::= { meEventObjects1 1 }

me1-interface OBJECT-TYPE
    SYNTAX DisplayString
    MAX-ACCESS accessible-for-notify
    STATUS current
    DESCRIPTION
        "Parameter 'interface' in event ME.1"
    ::= { meEventObjects1 2 }

meEventObjects2 OBJECT-IDENTITY
    STATUS current
    DESCRIPTION
        "Event ME.2
        One AT command message has been received from Serial Terminal."
    ::= { meEventsGroup 2 }

me2-coment OBJECT-TYPE
    SYNTAX DisplayString
    MAX-ACCESS accessible-for-notify
    STATUS current
    DESCRIPTION
        "Parameter 'coment' in event ME.2"
    ::= { meEventObjects2 1 }

me2-atCommand OBJECT-TYPE
    SYNTAX DisplayString
    MAX-ACCESS accessible-for-notify
    STATUS current
    DESCRIPTION
        "Parameter 'atCommand' in event ME.2"
    ::= { meEventObjects2 2 }

me2-interface OBJECT-TYPE
    SYNTAX DisplayString
    MAX-ACCESS accessible-for-notify
    STATUS current
    DESCRIPTION
        "Parameter 'interface' in event ME.2"
    ::= { meEventObjects2 3 }

me2-state OBJECT-TYPE
    SYNTAX Integer32
    MAX-ACCESS accessible-for-notify
    STATUS current
    DESCRIPTION
        "Parameter 'state' in event ME.2"
    ::= { meEventObjects2 4 }

meEventObjects3 OBJECT-IDENTITY
    STATUS current
    DESCRIPTION
        "Event ME.3
        A Message with bad address has been received from Serial Terminal."
    ::= { meEventsGroup 3 }

me3-bad-addr OBJECT-TYPE
    SYNTAX Integer32
    MAX-ACCESS accessible-for-notify
    STATUS current
    DESCRIPTION
        "Parameter 'bad-addr' in event ME.3"
    ::= { meEventObjects3 1 }

me3-interface OBJECT-TYPE
    SYNTAX DisplayString
    MAX-ACCESS accessible-for-notify
    STATUS current
    DESCRIPTION
        "Parameter 'interface' in event ME.3"
    ::= { meEventObjects3 2 }

meEventObjects4 OBJECT-IDENTITY
    STATUS current
    DESCRIPTION
        "Event ME.4
        One Bad Message has been received from Serial Terminal."
    ::= { meEventsGroup 4 }

me4-cause OBJECT-TYPE
    SYNTAX DisplayString
    MAX-ACCESS accessible-for-notify
    STATUS current
    DESCRIPTION
        "Parameter 'cause' in event ME.4"
    ::= { meEventObjects4 1 }

me4-interface OBJECT-TYPE
    SYNTAX DisplayString
    MAX-ACCESS accessible-for-notify
    STATUS current
    DESCRIPTION
        "Parameter 'interface' in event ME.4"
    ::= { meEventObjects4 2 }

me4-state OBJECT-TYPE
    SYNTAX Integer32
    MAX-ACCESS accessible-for-notify
    STATUS current
    DESCRIPTION
        "Parameter 'state' in event ME.4"
    ::= { meEventObjects4 3 }

meEventObjects5 OBJECT-IDENTITY
    STATUS current
    DESCRIPTION
        "Event ME.5
        A message with LRC/CRC error has been received from Serial Terminal."
    ::= { meEventsGroup 5 }

me5-interface OBJECT-TYPE
    SYNTAX DisplayString
    MAX-ACCESS accessible-for-notify
    STATUS current
    DESCRIPTION
        "Parameter 'interface' in event ME.5"
    ::= { meEventObjects5 1 }

me5-state OBJECT-TYPE
    SYNTAX Integer32
    MAX-ACCESS accessible-for-notify
    STATUS current
    DESCRIPTION
        "Parameter 'state' in event ME.5"
    ::= { meEventObjects5 2 }

meEventObjects6 OBJECT-IDENTITY
    STATUS current
    DESCRIPTION
        "Event ME.6
        A message with error has been received from Remote."
    ::= { meEventsGroup 6 }

me6-error-type OBJECT-TYPE
    SYNTAX DisplayString
    MAX-ACCESS accessible-for-notify
    STATUS current
    DESCRIPTION
        "Parameter 'error-type' in event ME.6"
    ::= { meEventObjects6 1 }

me6-interface OBJECT-TYPE
    SYNTAX DisplayString
    MAX-ACCESS accessible-for-notify
    STATUS current
    DESCRIPTION
        "Parameter 'interface' in event ME.6"
    ::= { meEventObjects6 2 }

me6-state OBJECT-TYPE
    SYNTAX Integer32
    MAX-ACCESS accessible-for-notify
    STATUS current
    DESCRIPTION
        "Parameter 'state' in event ME.6"
    ::= { meEventObjects6 3 }

meEventObjects7 OBJECT-IDENTITY
    STATUS current
    DESCRIPTION
        "Event ME.7
        Addres received from Serial Terminal is not included in configuration
        registers list."
    ::= { meEventsGroup 7 }

me7-serial-address OBJECT-TYPE
    SYNTAX Integer32
    MAX-ACCESS accessible-for-notify
    STATUS current
    DESCRIPTION
        "Parameter 'serial-address' in event ME.7"
    ::= { meEventObjects7 1 }

me7-interface OBJECT-TYPE
    SYNTAX DisplayString
    MAX-ACCESS accessible-for-notify
    STATUS current
    DESCRIPTION
        "Parameter 'interface' in event ME.7"
    ::= { meEventObjects7 2 }

meEventObjects8 OBJECT-IDENTITY
    STATUS current
    DESCRIPTION
        "Event ME.8
        Processed a basic AT command"
    ::= { meEventsGroup 8 }

me8-atCommand OBJECT-TYPE
    SYNTAX DisplayString
    MAX-ACCESS accessible-for-notify
    STATUS current
    DESCRIPTION
        "Parameter 'atCommand' in event ME.8"
    ::= { meEventObjects8 1 }

me8-value OBJECT-TYPE
    SYNTAX Integer32
    MAX-ACCESS accessible-for-notify
    STATUS current
    DESCRIPTION
        "Parameter 'value' in event ME.8"
    ::= { meEventObjects8 2 }

meEventObjects9 OBJECT-IDENTITY
    STATUS current
    DESCRIPTION
        "Event ME.9
        The Transfer has been completed successfully."
    ::= { meEventsGroup 9 }

me9-interface OBJECT-TYPE
    SYNTAX DisplayString
    MAX-ACCESS accessible-for-notify
    STATUS current
    DESCRIPTION
        "Parameter 'interface' in event ME.9"
    ::= { meEventObjects9 1 }

meEventObjects10 OBJECT-IDENTITY
    STATUS current
    DESCRIPTION
        "Event ME.10
        Processed an extended AT command"
    ::= { meEventsGroup 10 }

me10-atCommand OBJECT-TYPE
    SYNTAX DisplayString
    MAX-ACCESS accessible-for-notify
    STATUS current
    DESCRIPTION
        "Parameter 'atCommand' in event ME.10"
    ::= { meEventObjects10 1 }

me10-value OBJECT-TYPE
    SYNTAX Integer32
    MAX-ACCESS accessible-for-notify
    STATUS current
    DESCRIPTION
        "Parameter 'value' in event ME.10"
    ::= { meEventObjects10 2 }

meEventObjects11 OBJECT-IDENTITY
    STATUS current
    DESCRIPTION
        "Event ME.11
        Processed an extended AT command"
    ::= { meEventsGroup 11 }

me11-atCommand OBJECT-TYPE
    SYNTAX DisplayString
    MAX-ACCESS accessible-for-notify
    STATUS current
    DESCRIPTION
        "Parameter 'atCommand' in event ME.11"
    ::= { meEventObjects11 1 }

me11-value OBJECT-TYPE
    SYNTAX Integer32
    MAX-ACCESS accessible-for-notify
    STATUS current
    DESCRIPTION
        "Parameter 'value' in event ME.11"
    ::= { meEventObjects11 2 }

meEventObjects12 OBJECT-IDENTITY
    STATUS current
    DESCRIPTION
        "Event ME.12
        Processed a basic AT command Sn=x"
    ::= { meEventsGroup 12 }

me12-atCommand OBJECT-TYPE
    SYNTAX DisplayString
    MAX-ACCESS accessible-for-notify
    STATUS current
    DESCRIPTION
        "Parameter 'atCommand' in event ME.12"
    ::= { meEventObjects12 1 }

me12-sReg OBJECT-TYPE
    SYNTAX Integer32
    MAX-ACCESS accessible-for-notify
    STATUS current
    DESCRIPTION
        "Parameter 'sReg' in event ME.12"
    ::= { meEventObjects12 2 }

me12-value OBJECT-TYPE
    SYNTAX Integer32
    MAX-ACCESS accessible-for-notify
    STATUS current
    DESCRIPTION
        "Parameter 'value' in event ME.12"
    ::= { meEventObjects12 3 }

meEventObjects13 OBJECT-IDENTITY
    STATUS current
    DESCRIPTION
        "Event ME.13
        The TCP session has been closed."
    ::= { meEventsGroup 13 }

me13-foreign-host OBJECT-TYPE
    SYNTAX IpAddress
    MAX-ACCESS accessible-for-notify
    STATUS current
    DESCRIPTION
        "Parameter 'foreign-host' in event ME.13"
    ::= { meEventObjects13 1 }

me13-remote-port OBJECT-TYPE
    SYNTAX Integer32
    MAX-ACCESS accessible-for-notify
    STATUS current
    DESCRIPTION
        "Parameter 'remote-port' in event ME.13"
    ::= { meEventObjects13 2 }

meEventObjects14 OBJECT-IDENTITY
    STATUS current
    DESCRIPTION
        "Event ME.14
        The TCP session has been closed by the Remote end."
    ::= { meEventsGroup 14 }

me14-foreign-host OBJECT-TYPE
    SYNTAX IpAddress
    MAX-ACCESS accessible-for-notify
    STATUS current
    DESCRIPTION
        "Parameter 'foreign-host' in event ME.14"
    ::= { meEventObjects14 1 }

me14-remote-port OBJECT-TYPE
    SYNTAX Integer32
    MAX-ACCESS accessible-for-notify
    STATUS current
    DESCRIPTION
        "Parameter 'remote-port' in event ME.14"
    ::= { meEventObjects14 2 }

meEventObjects15 OBJECT-IDENTITY
    STATUS current
    DESCRIPTION
        "Event ME.15
        The TCP session has been opened by the Remote end."
    ::= { meEventsGroup 15 }

me15-remote-ip OBJECT-TYPE
    SYNTAX IpAddress
    MAX-ACCESS accessible-for-notify
    STATUS current
    DESCRIPTION
        "Parameter 'remote-ip' in event ME.15"
    ::= { meEventObjects15 1 }

me15-remote-port OBJECT-TYPE
    SYNTAX Integer32
    MAX-ACCESS accessible-for-notify
    STATUS current
    DESCRIPTION
        "Parameter 'remote-port' in event ME.15"
    ::= { meEventObjects15 2 }

meEventObjects16 OBJECT-IDENTITY
    STATUS current
    DESCRIPTION
        "Event ME.16
        An AT response message has been transmited to Serial Terminal."
    ::= { meEventsGroup 16 }

me16-atResponse OBJECT-TYPE
    SYNTAX DisplayString
    MAX-ACCESS accessible-for-notify
    STATUS current
    DESCRIPTION
        "Parameter 'atResponse' in event ME.16"
    ::= { meEventObjects16 1 }

me16-interface OBJECT-TYPE
    SYNTAX DisplayString
    MAX-ACCESS accessible-for-notify
    STATUS current
    DESCRIPTION
        "Parameter 'interface' in event ME.16"
    ::= { meEventObjects16 2 }

me16-state OBJECT-TYPE
    SYNTAX Integer32
    MAX-ACCESS accessible-for-notify
    STATUS current
    DESCRIPTION
        "Parameter 'state' in event ME.16"
    ::= { meEventObjects16 3 }

meEventObjects17 OBJECT-IDENTITY
    STATUS current
    DESCRIPTION
        "Event ME.17
        A change ON/OFF has been detected in Serial Control Signal Input."
    ::= { meEventsGroup 17 }

me17-message-type OBJECT-TYPE
    SYNTAX DisplayString
    MAX-ACCESS accessible-for-notify
    STATUS current
    DESCRIPTION
        "Parameter 'message-type' in event ME.17"
    ::= { meEventObjects17 1 }

me17-interface OBJECT-TYPE
    SYNTAX DisplayString
    MAX-ACCESS accessible-for-notify
    STATUS current
    DESCRIPTION
        "Parameter 'interface' in event ME.17"
    ::= { meEventObjects17 2 }

me17-state OBJECT-TYPE
    SYNTAX Integer32
    MAX-ACCESS accessible-for-notify
    STATUS current
    DESCRIPTION
        "Parameter 'state' in event ME.17"
    ::= { meEventObjects17 3 }

meEventObjects18 OBJECT-IDENTITY
    STATUS current
    DESCRIPTION
        "Event ME.18
        Timeout has occur waiting data."
    ::= { meEventsGroup 18 }

me18-site OBJECT-TYPE
    SYNTAX DisplayString
    MAX-ACCESS accessible-for-notify
    STATUS current
    DESCRIPTION
        "Parameter 'site' in event ME.18"
    ::= { meEventObjects18 1 }

me18-interface OBJECT-TYPE
    SYNTAX DisplayString
    MAX-ACCESS accessible-for-notify
    STATUS current
    DESCRIPTION
        "Parameter 'interface' in event ME.18"
    ::= { meEventObjects18 2 }

me18-state OBJECT-TYPE
    SYNTAX Integer32
    MAX-ACCESS accessible-for-notify
    STATUS current
    DESCRIPTION
        "Parameter 'state' in event ME.18"
    ::= { meEventObjects18 3 }

meEventObjects19 OBJECT-IDENTITY
    STATUS current
    DESCRIPTION
        "Event ME.19
        A packet was lost, due TCP Tx overrun error."
    ::= { meEventsGroup 19 }

me19-interface OBJECT-TYPE
    SYNTAX DisplayString
    MAX-ACCESS accessible-for-notify
    STATUS current
    DESCRIPTION
        "Parameter 'interface' in event ME.19"
    ::= { meEventObjects19 1 }

me19-state OBJECT-TYPE
    SYNTAX Integer32
    MAX-ACCESS accessible-for-notify
    STATUS current
    DESCRIPTION
        "Parameter 'state' in event ME.19"
    ::= { meEventObjects19 2 }

meEventObjects20 OBJECT-IDENTITY
    STATUS current
    DESCRIPTION
        "Event ME.20
        A packet was lost, due TCP is closed."
    ::= { meEventsGroup 20 }

me20-interface OBJECT-TYPE
    SYNTAX DisplayString
    MAX-ACCESS accessible-for-notify
    STATUS current
    DESCRIPTION
        "Parameter 'interface' in event ME.20"
    ::= { meEventObjects20 1 }

me20-state OBJECT-TYPE
    SYNTAX Integer32
    MAX-ACCESS accessible-for-notify
    STATUS current
    DESCRIPTION
        "Parameter 'state' in event ME.20"
    ::= { meEventObjects20 2 }

meEventObjects21 OBJECT-IDENTITY
    STATUS current
    DESCRIPTION
        "Event ME.21
        The transfer has been wrong against specified NA and IP addr."
    ::= { meEventsGroup 21 }

me21-na OBJECT-TYPE
    SYNTAX Integer32
    MAX-ACCESS accessible-for-notify
    STATUS current
    DESCRIPTION
        "Parameter 'na' in event ME.21"
    ::= { meEventObjects21 1 }

me21-ip-host-address OBJECT-TYPE
    SYNTAX IpAddress
    MAX-ACCESS accessible-for-notify
    STATUS current
    DESCRIPTION
        "Parameter 'ip-host-address' in event ME.21"
    ::= { meEventObjects21 2 }

me21-cause OBJECT-TYPE
    SYNTAX Integer32
    MAX-ACCESS accessible-for-notify
    STATUS current
    DESCRIPTION
        "Parameter 'cause' in event ME.21"
    ::= { meEventObjects21 3 }

me21-interface OBJECT-TYPE
    SYNTAX DisplayString
    MAX-ACCESS accessible-for-notify
    STATUS current
    DESCRIPTION
        "Parameter 'interface' in event ME.21"
    ::= { meEventObjects21 4 }

meEventObjects22 OBJECT-IDENTITY
    STATUS current
    DESCRIPTION
        "Event ME.22
        TCP generic event was occurred."
    ::= { meEventsGroup 22 }

me22-event OBJECT-TYPE
    SYNTAX DisplayString
    MAX-ACCESS accessible-for-notify
    STATUS current
    DESCRIPTION
        "Parameter 'event' in event ME.22"
    ::= { meEventObjects22 1 }

me22-ip OBJECT-TYPE
    SYNTAX IpAddress
    MAX-ACCESS accessible-for-notify
    STATUS current
    DESCRIPTION
        "Parameter 'ip' in event ME.22"
    ::= { meEventObjects22 2 }

me22-port OBJECT-TYPE
    SYNTAX Integer32
    MAX-ACCESS accessible-for-notify
    STATUS current
    DESCRIPTION
        "Parameter 'port' in event ME.22"
    ::= { meEventObjects22 3 }

meEventObjects23 OBJECT-IDENTITY
    STATUS current
    DESCRIPTION
        "Event ME.23
        A change ON/OFF has been make in Serial Control Signal Input."
    ::= { meEventsGroup 23 }

me23-message-type OBJECT-TYPE
    SYNTAX DisplayString
    MAX-ACCESS accessible-for-notify
    STATUS current
    DESCRIPTION
        "Parameter 'message-type' in event ME.23"
    ::= { meEventObjects23 1 }

me23-interface OBJECT-TYPE
    SYNTAX DisplayString
    MAX-ACCESS accessible-for-notify
    STATUS current
    DESCRIPTION
        "Parameter 'interface' in event ME.23"
    ::= { meEventObjects23 2 }

me23-state OBJECT-TYPE
    SYNTAX Integer32
    MAX-ACCESS accessible-for-notify
    STATUS current
    DESCRIPTION
        "Parameter 'state' in event ME.23"
    ::= { meEventObjects23 3 }

meEventObjects24 OBJECT-IDENTITY
    STATUS current
    DESCRIPTION
        "Event ME.24
        Data error from Serial Terminal has been received."
    ::= { meEventsGroup 24 }

me24-message-type OBJECT-TYPE
    SYNTAX DisplayString
    MAX-ACCESS accessible-for-notify
    STATUS current
    DESCRIPTION
        "Parameter 'message-type' in event ME.24"
    ::= { meEventObjects24 1 }

me24-interface OBJECT-TYPE
    SYNTAX DisplayString
    MAX-ACCESS accessible-for-notify
    STATUS current
    DESCRIPTION
        "Parameter 'interface' in event ME.24"
    ::= { meEventObjects24 2 }

me24-state OBJECT-TYPE
    SYNTAX Integer32
    MAX-ACCESS accessible-for-notify
    STATUS current
    DESCRIPTION
        "Parameter 'state' in event ME.24"
    ::= { meEventObjects24 3 }

meEventObjects25 OBJECT-IDENTITY
    STATUS current
    DESCRIPTION
        "Event ME.25
        TCP Listen has been closed, due max session number has been reached."
    ::= { meEventsGroup 25 }

me25-port OBJECT-TYPE
    SYNTAX Integer32
    MAX-ACCESS accessible-for-notify
    STATUS current
    DESCRIPTION
        "Parameter 'port' in event ME.25"
    ::= { meEventObjects25 1 }

meEventObjects26 OBJECT-IDENTITY
    STATUS current
    DESCRIPTION
        "Event ME.26
        An input TCP session has been rejet."
    ::= { meEventsGroup 26 }

me26-event OBJECT-TYPE
    SYNTAX DisplayString
    MAX-ACCESS accessible-for-notify
    STATUS current
    DESCRIPTION
        "Parameter 'event' in event ME.26"
    ::= { meEventObjects26 1 }

me26-ip OBJECT-TYPE
    SYNTAX IpAddress
    MAX-ACCESS accessible-for-notify
    STATUS current
    DESCRIPTION
        "Parameter 'ip' in event ME.26"
    ::= { meEventObjects26 2 }

me26-port OBJECT-TYPE
    SYNTAX Integer32
    MAX-ACCESS accessible-for-notify
    STATUS current
    DESCRIPTION
        "Parameter 'port' in event ME.26"
    ::= { meEventObjects26 3 }

meEventObjects27 OBJECT-IDENTITY
    STATUS current
    DESCRIPTION
        "Event ME.27
        Detailed Data send to serial interface."
    ::= { meEventsGroup 27 }

me27-interface OBJECT-TYPE
    SYNTAX DisplayString
    MAX-ACCESS accessible-for-notify
    STATUS current
    DESCRIPTION
        "Parameter 'interface' in event ME.27"
    ::= { meEventObjects27 1 }

me27-serial-address OBJECT-TYPE
    SYNTAX Integer32
    MAX-ACCESS accessible-for-notify
    STATUS current
    DESCRIPTION
        "Parameter 'serial-address' in event ME.27"
    ::= { meEventObjects27 2 }

me27-lenght OBJECT-TYPE
    SYNTAX Integer32
    MAX-ACCESS accessible-for-notify
    STATUS current
    DESCRIPTION
        "Parameter 'lenght' in event ME.27"
    ::= { meEventObjects27 3 }

me27-hex-data OBJECT-TYPE
    SYNTAX DisplayString
    MAX-ACCESS accessible-for-notify
    STATUS current
    DESCRIPTION
        "Parameter 'hex-data' in event ME.27"
    ::= { meEventObjects27 4 }

meEventObjects28 OBJECT-IDENTITY
    STATUS current
    DESCRIPTION
        "Event ME.28
        Detailed Data received from serial interface."
    ::= { meEventsGroup 28 }

me28-interface OBJECT-TYPE
    SYNTAX DisplayString
    MAX-ACCESS accessible-for-notify
    STATUS current
    DESCRIPTION
        "Parameter 'interface' in event ME.28"
    ::= { meEventObjects28 1 }

me28-serial-address OBJECT-TYPE
    SYNTAX Integer32
    MAX-ACCESS accessible-for-notify
    STATUS current
    DESCRIPTION
        "Parameter 'serial-address' in event ME.28"
    ::= { meEventObjects28 2 }

me28-lenght OBJECT-TYPE
    SYNTAX Integer32
    MAX-ACCESS accessible-for-notify
    STATUS current
    DESCRIPTION
        "Parameter 'lenght' in event ME.28"
    ::= { meEventObjects28 3 }

me28-hex-data OBJECT-TYPE
    SYNTAX DisplayString
    MAX-ACCESS accessible-for-notify
    STATUS current
    DESCRIPTION
        "Parameter 'hex-data' in event ME.28"
    ::= { meEventObjects28 4 }

meEventObjects29 OBJECT-IDENTITY
    STATUS current
    DESCRIPTION
        "Event ME.29
        Change in the speed of the Serial Terminal."
    ::= { meEventsGroup 29 }

me29-speed OBJECT-TYPE
    SYNTAX Integer32
    MAX-ACCESS accessible-for-notify
    STATUS current
    DESCRIPTION
        "Parameter 'speed' in event ME.29"
    ::= { meEventObjects29 1 }

me29-interface OBJECT-TYPE
    SYNTAX DisplayString
    MAX-ACCESS accessible-for-notify
    STATUS current
    DESCRIPTION
        "Parameter 'interface' in event ME.29"
    ::= { meEventObjects29 2 }

meEventObjects30 OBJECT-IDENTITY
    STATUS current
    DESCRIPTION
        "Event ME.30
        Change in the speed of the Serial Terminal."
    ::= { meEventsGroup 30 }

me30-interface OBJECT-TYPE
    SYNTAX DisplayString
    MAX-ACCESS accessible-for-notify
    STATUS current
    DESCRIPTION
        "Parameter 'interface' in event ME.30"
    ::= { meEventObjects30 1 }


meNotification1 NOTIFICATION-TYPE
    OBJECTS { 
              me1-bytes-number, 
              me1-interface 
            }
    STATUS current
    DESCRIPTION
        "Notification of Event ME.1

        Message: 'Rx Data from Serial Terminal $1 bytes, interface $2'

        Parameters list:
              $1: me1-bytes-number
              $2: me1-interface

        Data has been received from Serial Terminal."
    ::= { meNotificationsPrefix 1 }

meNotification2 NOTIFICATION-TYPE
    OBJECTS { 
              me2-coment, 
              me2-atCommand,
              me2-interface,
              me2-state 
            }
    STATUS current
    DESCRIPTION
        "Notification of Event ME.2

        Message: 'Rx $1 from Serial Terminal: AT$2, interface $3 state $4'

        Parameters list:
              $1: me2-coment
              $2: me2-atCommand
              $3: me2-interface
              $4: me2-state

        One AT command message has been received from Serial Terminal."
    ::= { meNotificationsPrefix 2 }

meNotification3 NOTIFICATION-TYPE
    OBJECTS { 
              me3-bad-addr, 
              me3-interface 
            }
    STATUS current
    DESCRIPTION
        "Notification of Event ME.3

        Message: 'Rx Address error from Serial Terminal $1 bytes, interface $2'

        Parameters list:
              $1: me3-bad-addr
              $2: me3-interface

        A Message with bad address has been received from Serial Terminal."
    ::= { meNotificationsPrefix 3 }

meNotification4 NOTIFICATION-TYPE
    OBJECTS { 
              me4-cause, 
              me4-interface,
              me4-state 
            }
    STATUS current
    DESCRIPTION
        "Notification of Event ME.4

        Message: 'Rx Bad Message from Serial Terminal ($1), interface $2 state $3'

        Parameters list:
              $1: me4-cause
              $2: me4-interface
              $3: me4-state

        One Bad Message has been received from Serial Terminal."
    ::= { meNotificationsPrefix 4 }

meNotification5 NOTIFICATION-TYPE
    OBJECTS { 
              me5-interface, 
              me5-state 
            }
    STATUS current
    DESCRIPTION
        "Notification of Event ME.5

        Message: 'A block with LRC/CRC error has been received from Serial Terminal, interface $1 state $2'

        Parameters list:
              $1: me5-interface
              $2: me5-state

        A message with LRC/CRC error has been received from Serial Terminal."
    ::= { meNotificationsPrefix 5 }

meNotification6 NOTIFICATION-TYPE
    OBJECTS { 
              me6-error-type, 
              me6-interface,
              me6-state 
            }
    STATUS current
    DESCRIPTION
        "Notification of Event ME.6

        Message: 'A block with $1 error has been received from Serial Terminal, interface $2 state $3'

        Parameters list:
              $1: me6-error-type
              $2: me6-interface
              $3: me6-state

        A message with error has been received from Remote."
    ::= { meNotificationsPrefix 6 }

meNotification7 NOTIFICATION-TYPE
    OBJECTS { 
              me7-serial-address, 
              me7-interface 
            }
    STATUS current
    DESCRIPTION
        "Notification of Event ME.7

        Message: 'Address $1 received from Serial Terminal is not included in configuration regiters. Interface $2'

        Parameters list:
              $1: me7-serial-address
              $2: me7-interface

        Addres received from Serial Terminal is not included in configuration
        registers list."
    ::= { meNotificationsPrefix 7 }

meNotification8 NOTIFICATION-TYPE
    OBJECTS { 
              me8-atCommand, 
              me8-value 
            }
    STATUS current
    DESCRIPTION
        "Notification of Event ME.8

        Message: 'Basic AT Command: AT$1$2'

        Parameters list:
              $1: me8-atCommand
              $2: me8-value

        Processed a basic AT command"
    ::= { meNotificationsPrefix 8 }

meNotification9 NOTIFICATION-TYPE
    OBJECTS { 
              me9-interface 
            }
    STATUS current
    DESCRIPTION
        "Notification of Event ME.9

        Message: 'The Transfer has been completed successfully. Interface $1'

        Parameters list:
              $1: me9-interface

        The Transfer has been completed successfully."
    ::= { meNotificationsPrefix 9 }

meNotification10 NOTIFICATION-TYPE
    OBJECTS { 
              me10-atCommand, 
              me10-value 
            }
    STATUS current
    DESCRIPTION
        "Notification of Event ME.10

        Message: 'Extended AT Command: AT&$1$2'

        Parameters list:
              $1: me10-atCommand
              $2: me10-value

        Processed an extended AT command"
    ::= { meNotificationsPrefix 10 }

meNotification11 NOTIFICATION-TYPE
    OBJECTS { 
              me11-atCommand, 
              me11-value 
            }
    STATUS current
    DESCRIPTION
        "Notification of Event ME.11

        Message: 'Propietary AT Command: AT$1$2'

        Parameters list:
              $1: me11-atCommand
              $2: me11-value

        Processed an extended AT command"
    ::= { meNotificationsPrefix 11 }

meNotification12 NOTIFICATION-TYPE
    OBJECTS { 
              me12-atCommand, 
              me12-sReg,
              me12-value 
            }
    STATUS current
    DESCRIPTION
        "Notification of Event ME.12

        Message: 'Basic AT Command: AT$1$2=$3'

        Parameters list:
              $1: me12-atCommand
              $2: me12-sReg
              $3: me12-value

        Processed a basic AT command Sn=x"
    ::= { meNotificationsPrefix 12 }

meNotification13 NOTIFICATION-TYPE
    OBJECTS { 
              me13-foreign-host, 
              me13-remote-port 
            }
    STATUS current
    DESCRIPTION
        "Notification of Event ME.13

        Message: 'The TCP session has been closed. rem. IP: $1, Port: $2'

        Parameters list:
              $1: me13-foreign-host
              $2: me13-remote-port

        The TCP session has been closed."
    ::= { meNotificationsPrefix 13 }

meNotification14 NOTIFICATION-TYPE
    OBJECTS { 
              me14-foreign-host, 
              me14-remote-port 
            }
    STATUS current
    DESCRIPTION
        "Notification of Event ME.14

        Message: 'The TCP session has been closed by the Remote end. rem. IP: $1, Port: $2'

        Parameters list:
              $1: me14-foreign-host
              $2: me14-remote-port

        The TCP session has been closed by the Remote end."
    ::= { meNotificationsPrefix 14 }

meNotification15 NOTIFICATION-TYPE
    OBJECTS { 
              me15-remote-ip, 
              me15-remote-port 
            }
    STATUS current
    DESCRIPTION
        "Notification of Event ME.15

        Message: 'The TCP session has been opened by the Remote end. Remote IP:$1 , Port: $2'

        Parameters list:
              $1: me15-remote-ip
              $2: me15-remote-port

        The TCP session has been opened by the Remote end."
    ::= { meNotificationsPrefix 15 }

meNotification16 NOTIFICATION-TYPE
    OBJECTS { 
              me16-atResponse, 
              me16-interface,
              me16-state 
            }
    STATUS current
    DESCRIPTION
        "Notification of Event ME.16

        Message: 'Tx Message to Serial Terminal, $1, interface $2 state $3'

        Parameters list:
              $1: me16-atResponse
              $2: me16-interface
              $3: me16-state

        An AT response message has been transmited to Serial Terminal."
    ::= { meNotificationsPrefix 16 }

meNotification17 NOTIFICATION-TYPE
    OBJECTS { 
              me17-message-type, 
              me17-interface,
              me17-state 
            }
    STATUS current
    DESCRIPTION
        "Notification of Event ME.17

        Message: 'Serial Control Signal Input change to $1, interface $2 state $3'

        Parameters list:
              $1: me17-message-type
              $2: me17-interface
              $3: me17-state

        A change ON/OFF has been detected in Serial Control Signal Input."
    ::= { meNotificationsPrefix 17 }

meNotification18 NOTIFICATION-TYPE
    OBJECTS { 
              me18-site, 
              me18-interface,
              me18-state 
            }
    STATUS current
    DESCRIPTION
        "Notification of Event ME.18

        Message: 'Timeout waiting data from $1, interface $2 state $3'

        Parameters list:
              $1: me18-site
              $2: me18-interface
              $3: me18-state

        Timeout has occur waiting data."
    ::= { meNotificationsPrefix 18 }

meNotification19 NOTIFICATION-TYPE
    OBJECTS { 
              me19-interface, 
              me19-state 
            }
    STATUS current
    DESCRIPTION
        "Notification of Event ME.19

        Message: 'Packet lost due TCP Tx overrun error. Interface $1 state $2'

        Parameters list:
              $1: me19-interface
              $2: me19-state

        A packet was lost, due TCP Tx overrun error."
    ::= { meNotificationsPrefix 19 }

meNotification20 NOTIFICATION-TYPE
    OBJECTS { 
              me20-interface, 
              me20-state 
            }
    STATUS current
    DESCRIPTION
        "Notification of Event ME.20

        Message: 'Packet lost due TCP session is closes. Interface $1 state $2'

        Parameters list:
              $1: me20-interface
              $2: me20-state

        A packet was lost, due TCP is closed."
    ::= { meNotificationsPrefix 20 }

meNotification21 NOTIFICATION-TYPE
    OBJECTS { 
              me21-na, 
              me21-ip-host-address,
              me21-cause,
              me21-interface 
            }
    STATUS current
    DESCRIPTION
        "Notification of Event ME.21

        Message: 'The transfer has been wrong, against address $1, IP $2, Cause $3, interface $4'

        Parameters list:
              $1: me21-na
              $2: me21-ip-host-address
              $3: me21-cause
              $4: me21-interface

        The transfer has been wrong against specified NA and IP addr."
    ::= { meNotificationsPrefix 21 }

meNotification22 NOTIFICATION-TYPE
    OBJECTS { 
              me22-event, 
              me22-ip,
              me22-port 
            }
    STATUS current
    DESCRIPTION
        "Notification of Event ME.22

        Message: 'The TCP event: $1 . Rem. IP: $2, rem. Port: $3'

        Parameters list:
              $1: me22-event
              $2: me22-ip
              $3: me22-port

        TCP generic event was occurred."
    ::= { meNotificationsPrefix 22 }

meNotification23 NOTIFICATION-TYPE
    OBJECTS { 
              me23-message-type, 
              me23-interface,
              me23-state 
            }
    STATUS current
    DESCRIPTION
        "Notification of Event ME.23

        Message: 'Serial Control Signal Output change to $1, interface $2 state $3'

        Parameters list:
              $1: me23-message-type
              $2: me23-interface
              $3: me23-state

        A change ON/OFF has been make in Serial Control Signal Input."
    ::= { meNotificationsPrefix 23 }

meNotification24 NOTIFICATION-TYPE
    OBJECTS { 
              me24-message-type, 
              me24-interface,
              me24-state 
            }
    STATUS current
    DESCRIPTION
        "Notification of Event ME.24

        Message: 'Data ERROR from Serial Terminal has been received type: $1. Interface $2 state $3'

        Parameters list:
              $1: me24-message-type
              $2: me24-interface
              $3: me24-state

        Data error from Serial Terminal has been received."
    ::= { meNotificationsPrefix 24 }

meNotification25 NOTIFICATION-TYPE
    OBJECTS { 
              me25-port 
            }
    STATUS current
    DESCRIPTION
        "Notification of Event ME.25

        Message: 'Max sessions number has been reached, port $1'

        Parameters list:
              $1: me25-port

        TCP Listen has been closed, due max session number has been reached."
    ::= { meNotificationsPrefix 25 }

meNotification26 NOTIFICATION-TYPE
    OBJECTS { 
              me26-event, 
              me26-ip,
              me26-port 
            }
    STATUS current
    DESCRIPTION
        "Notification of Event ME.26

        Message: 'TCP inout session rejet: $1 . Rem. IP: $2, rem. Port: $3'

        Parameters list:
              $1: me26-event
              $2: me26-ip
              $3: me26-port

        An input TCP session has been rejet."
    ::= { meNotificationsPrefix 26 }

meNotification27 NOTIFICATION-TYPE
    OBJECTS { 
              me27-interface, 
              me27-serial-address,
              me27-lenght,
              me27-hex-data 
            }
    STATUS current
    DESCRIPTION
        "Notification of Event ME.27

        Message: 'Data transmitted to serial interface $1 (addr:$2,$3 bytes):$4'

        Parameters list:
              $1: me27-interface
              $2: me27-serial-address
              $3: me27-lenght
              $4: me27-hex-data

        Detailed Data send to serial interface."
    ::= { meNotificationsPrefix 27 }

meNotification28 NOTIFICATION-TYPE
    OBJECTS { 
              me28-interface, 
              me28-serial-address,
              me28-lenght,
              me28-hex-data 
            }
    STATUS current
    DESCRIPTION
        "Notification of Event ME.28

        Message: 'Data received from serial interface $1 (addr:$2,$3 bytes):$4'

        Parameters list:
              $1: me28-interface
              $2: me28-serial-address
              $3: me28-lenght
              $4: me28-hex-data

        Detailed Data received from serial interface."
    ::= { meNotificationsPrefix 28 }

meNotification29 NOTIFICATION-TYPE
    OBJECTS { 
              me29-speed, 
              me29-interface 
            }
    STATUS current
    DESCRIPTION
        "Notification of Event ME.29

        Message: 'Change the speed of Serial Terminal to $1 in interface $2'

        Parameters list:
              $1: me29-speed
              $2: me29-interface

        Change in the speed of the Serial Terminal."
    ::= { meNotificationsPrefix 29 }

meNotification30 NOTIFICATION-TYPE
    OBJECTS { 
              me30-interface 
            }
    STATUS current
    DESCRIPTION
        "Notification of Event ME.30

        Message: 'Received the escape char through interface $1'

        Parameters list:
              $1: me30-interface

        Change in the speed of the Serial Terminal."
    ::= { meNotificationsPrefix 30 }


END
