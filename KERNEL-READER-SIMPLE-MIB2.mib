KERNEL-READER-SIMPLE-MIB2 DEFINITIONS ::= BEGIN

IMPORTS
    enterprises, MODULE-IDENTITY, Integer32, Counter64, Unsigned32
        FROM SNMPv2-SMI;

kernelReader MODULE-IDENTITY
    LAST-UPDATED "0609201255Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        ""
    ::= { modules 12 }
modules	OBJECT IDENTIFIER ::= { agent 2 }

agent	OBJECT IDENTIFIER ::= { sunsymon 2 }

sunsymon	OBJECT IDENTIFIER ::= { prod 12 }

prod	OBJECT IDENTIFIER ::= { sun 2 }

sun	OBJECT IDENTIFIER ::= { enterprises 42 }


load	OBJECT IDENTIFIER ::= { kernelReader 2 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

avg1min OBJECT-TYPE
    SYNTAX      DisplayString
    UNITS       "Jobs"
    MAX-ACCESS  read-only
    STATUS      current
    DESCRIPTION
                "Load average over the last 1 minute."
    ::= { load 1 }

avg5min OBJECT-TYPE
    SYNTAX      DisplayString
    UNITS       "Jobs"
    MAX-ACCESS  read-only
    STATUS      current
    DESCRIPTION
                "Load average over the last 5 minutes."
    ::= { load 2 }

avg15min OBJECT-TYPE
    SYNTAX      DisplayString
    UNITS       "Jobs"
    MAX-ACCESS  read-only
    STATUS      current
    DESCRIPTION
                "Load average over the last 15 minutes."
    ::= { load 3 }

cpudetail	OBJECT IDENTIFIER ::= { kernelReader 5 }

cpuUtilTable OBJECT-TYPE
    SYNTAX      SEQUENCE OF CpuUtilEntry
    MAX-ACCESS  not-accessible
    STATUS      current
    DESCRIPTION
                "MIB tree branch"
    ::= { cpudetail 1 }

cpuUtilEntry OBJECT-TYPE
    SYNTAX      CpuUtilEntry
    MAX-ACCESS  not-accessible
    STATUS      current
    DESCRIPTION
                "MIB tree branch"
    INDEX  { cpuinstance }
    ::= { cpuUtilTable 1 }

CpuUtilEntry ::=
    SEQUENCE {
        cpuinstance
            Integer32,
        cpudelta
            DisplayString,
        cpuidle
            DisplayString,
        cpuuser
            DisplayString,
        cpukernel
            DisplayString,
        cpuwait
            DisplayString,
        waitio
            DisplayString,
        waitswap
            DisplayString,
        waitpio
            DisplayString,
        idlethread
            Counter64,
        rknrd403
            DisplayString
    }

cpuinstance OBJECT-TYPE
    SYNTAX      Integer32
    MAX-ACCESS  read-only
    STATUS      current
    DESCRIPTION
                "The CPU number"
    ::= { cpuUtilEntry 1 }

cpudelta OBJECT-TYPE
    SYNTAX      DisplayString
    MAX-ACCESS  read-only
    STATUS      current
    DESCRIPTION
                "Floating point value"
    ::= { cpuUtilEntry 2 }

cpuidle OBJECT-TYPE
    SYNTAX      DisplayString
    UNITS       "%"
    MAX-ACCESS  read-only
    STATUS      current
    DESCRIPTION
                "Floating point value"
    ::= { cpuUtilEntry 3 }

cpuuser OBJECT-TYPE
    SYNTAX      DisplayString
    UNITS       "%"
    MAX-ACCESS  read-only
    STATUS      current
    DESCRIPTION
                "Floating point value"
    ::= { cpuUtilEntry 4 }

cpukernel OBJECT-TYPE
    SYNTAX      DisplayString
    UNITS       "%"
    MAX-ACCESS  read-only
    STATUS      current
    DESCRIPTION
                "Floating point value"
    ::= { cpuUtilEntry 5 }

cpuwait OBJECT-TYPE
    SYNTAX      DisplayString
    UNITS       "%"
    MAX-ACCESS  read-only
    STATUS      current
    DESCRIPTION
                "Floating point value"
    ::= { cpuUtilEntry 6 }

waitio OBJECT-TYPE
    SYNTAX      DisplayString
    UNITS       "%"
    MAX-ACCESS  read-only
    STATUS      current
    DESCRIPTION
                "Floating point value"
    ::= { cpuUtilEntry 7 }

waitswap OBJECT-TYPE
    SYNTAX      DisplayString
    UNITS       "%"
    MAX-ACCESS  read-only
    STATUS      current
    DESCRIPTION
                "Floating point value"
    ::= { cpuUtilEntry 8 }

waitpio OBJECT-TYPE
    SYNTAX      DisplayString
    UNITS       "%"
    MAX-ACCESS  read-only
    STATUS      current
    DESCRIPTION
                "Floating point value"
    ::= { cpuUtilEntry 9 }

idlethread OBJECT-TYPE
    SYNTAX      Counter64
    MAX-ACCESS  read-only
    STATUS      current
    DESCRIPTION
                "Counter64 value"
    ::= { cpuUtilEntry 10 }

rknrd403 OBJECT-TYPE
    SYNTAX      DisplayString
    MAX-ACCESS  read-only
    STATUS      current
    DESCRIPTION
                "Meta CPU Rule"
    ::= { cpuUtilEntry 11 }

overAllCpuStatistics	OBJECT IDENTIFIER ::= { cpudetail 10 }

overAllCpuStatsUtil OBJECT-TYPE
    SYNTAX      DisplayString
    UNITS       "%"
    MAX-ACCESS  read-only
    STATUS      current
    DESCRIPTION
                "Floating point value"
    ::= { overAllCpuStatistics 1 }

overAllCpuStatsIdle OBJECT-TYPE
    SYNTAX      DisplayString
    UNITS       "%"
    MAX-ACCESS  read-only
    STATUS      current
    DESCRIPTION
                "Floating point value"
    ::= { overAllCpuStatistics 2 }

memoryusage	OBJECT IDENTIFIER ::= { kernelReader 6 }

memavail OBJECT-TYPE
    SYNTAX      Integer32
    UNITS       "MB"
    MAX-ACCESS  read-only
    STATUS      current
    DESCRIPTION
                "Physical memory available"
    ::= { memoryusage 1 }

meminuse OBJECT-TYPE
    SYNTAX      Integer32
    UNITS       "MB"
    MAX-ACCESS  read-only
    STATUS      current
    DESCRIPTION
                "Physical memory in use"
    ::= { memoryusage 2 }

memPctUsed OBJECT-TYPE
    SYNTAX      DisplayString
    MAX-ACCESS  read-only
    STATUS      current
    DESCRIPTION
                "Percentage value"
    ::= { memoryusage 3 }

memfree OBJECT-TYPE
    SYNTAX      Integer32
    UNITS       "MB"
    MAX-ACCESS  read-only
    STATUS      current
    DESCRIPTION
                "Physical memory free"
    ::= { memoryusage 4 }

pctFree OBJECT-TYPE
    SYNTAX      DisplayString
    MAX-ACCESS  read-only
    STATUS      current
    DESCRIPTION
                "Percentage value"
    ::= { memoryusage 5 }

swapdetail	OBJECT IDENTIFIER ::= { kernelReader 7 }

swapavail OBJECT-TYPE
    SYNTAX      Integer32
    UNITS       "KiloBytes"
    MAX-ACCESS  read-only
    STATUS      current
    DESCRIPTION
                "Swap available(Total SWAP - RESERVED)"
    ::= { swapdetail 1 }

swapresv OBJECT-TYPE
    SYNTAX      Integer32
    UNITS       "KiloBytes"
    MAX-ACCESS  read-only
    STATUS      current
    DESCRIPTION
                "Swap reserved"
    ::= { swapdetail 2 }

swapalloc OBJECT-TYPE
    SYNTAX      Integer32
    UNITS       "KiloBytes"
    MAX-ACCESS  read-only
    STATUS      current
    DESCRIPTION
                "Swap allocated"
    ::= { swapdetail 3 }

swapused OBJECT-TYPE
    SYNTAX      Unsigned32
    UNITS       "KiloBytes"
    MAX-ACCESS  read-only
    STATUS      current
    DESCRIPTION
                "Swap Used"
    ::= { swapdetail 4 }

swaptotal OBJECT-TYPE
    SYNTAX      Integer32
    UNITS       "KiloBytes"
    MAX-ACCESS  read-only
    STATUS      current
    DESCRIPTION
                "Swap total"
    ::= { swapdetail 5 }

swapPctUsed OBJECT-TYPE
    SYNTAX      DisplayString
    UNITS       "%"
    MAX-ACCESS  read-only
    STATUS      current
    DESCRIPTION
                "Percentage value"
    ::= { swapdetail 6 }

rknrd405 OBJECT-TYPE
    SYNTAX      DisplayString
    MAX-ACCESS  read-only
    STATUS      current
    DESCRIPTION
                "Meta Swap Rule"
    ::= { swapdetail 7 }

filesystem	OBJECT IDENTIFIER ::= { kernelReader 4 }

ufsFileSystem	OBJECT IDENTIFIER ::= { filesystem 1 }

fileTable OBJECT-TYPE
    SYNTAX      SEQUENCE OF FileEntry
    MAX-ACCESS  not-accessible
    STATUS      current
    DESCRIPTION
                "MIB tree branch"
    ::= { ufsFileSystem 1 }

fileEntry OBJECT-TYPE
    SYNTAX      FileEntry
    MAX-ACCESS  not-accessible
    STATUS      current
    DESCRIPTION
                "MIB tree branch"
    INDEX  { index }
    ::= { fileTable 1 }

FileEntry ::=
    SEQUENCE {
        index
            DisplayString,
        mount
            DisplayString,
        diskname
            DisplayString,
        ksize
            Integer32,
        kfree
            Integer32,
        kavail
            Integer32,
        kpctUsed
            DisplayString,
        isize
            Integer32,
        iavail
            Integer32,
        ipctUsed
            DisplayString
    }

index OBJECT-TYPE
    SYNTAX      DisplayString
    MAX-ACCESS  read-only
    STATUS      current
    DESCRIPTION
                "The mount point index for the filesystem"
    ::= { fileEntry 1 }

mount OBJECT-TYPE
    SYNTAX      DisplayString
    MAX-ACCESS  read-only
    STATUS      current
    DESCRIPTION
                "The mount point for the filesystem"
    ::= { fileEntry 2 }

diskname OBJECT-TYPE
    SYNTAX      DisplayString
    MAX-ACCESS  read-only
    STATUS      current
    DESCRIPTION
                "The name of the device (/dev/dsk/...)"
    ::= { fileEntry 3 }

ksize OBJECT-TYPE
    SYNTAX      Integer32
    UNITS       "KB"
    MAX-ACCESS  read-only
    STATUS      current
    DESCRIPTION
                "The total size of the filesystem in KBytes"
    ::= { fileEntry 4 }

kfree OBJECT-TYPE
    SYNTAX      Integer32
    UNITS       "KB"
    MAX-ACCESS  read-only
    STATUS      current
    DESCRIPTION
                "Available disk space in KBytes"
    ::= { fileEntry 5 }

kavail OBJECT-TYPE
    SYNTAX      Integer32
    UNITS       "KB"
    MAX-ACCESS  read-only
    STATUS      current
    DESCRIPTION
                "Available disk space for non-superusers in KBytes"
    ::= { fileEntry 6 }

kpctUsed OBJECT-TYPE
    SYNTAX      DisplayString
    UNITS       "%"
    MAX-ACCESS  read-only
    STATUS      current
    DESCRIPTION
                "Percentage of Disk Space Used"
    ::= { fileEntry 7 }

isize OBJECT-TYPE
    SYNTAX      Integer32
    UNITS       "inodes"
    MAX-ACCESS  read-only
    STATUS      current
    DESCRIPTION
                "The total size of the filesystem in KBytes"
    ::= { fileEntry 8 }

iavail OBJECT-TYPE
    SYNTAX      Integer32
    UNITS       "inodes"
    MAX-ACCESS  read-only
    STATUS      current
    DESCRIPTION
                "Available disk space for the file system in KBytes"
    ::= { fileEntry 9 }

ipctUsed OBJECT-TYPE
    SYNTAX      DisplayString
    UNITS       "%"
    MAX-ACCESS  read-only
    STATUS      current
    DESCRIPTION
                "Percentage of Inodes Used"
    ::= { fileEntry 10 }

ext3FileSystem	OBJECT IDENTIFIER ::= { filesystem 31 }

otherFileSystem	OBJECT IDENTIFIER ::= { filesystem 32 }
END
