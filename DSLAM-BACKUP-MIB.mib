-- $Workfile:   pgbackup.my  $

-- $Revision:   1.0  $
-- $Date:   Apr 22 2000 17:06:02  $

-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.

     DSLAM-BACKUP-MIB DEFINITIONS ::= BEGIN

     IMPORTS

        MODULE-IDENTITY, OBJECT-TYPE
            FROM SNMPv2-SMI
        RowStatus
            FROM SNMPv2-TC
        MODULE-COMPLIANCE, OBJECT-GROUP
            FROM SNMPv2-CONF
        InterfaceIndex, ifIndex
            FROM IF-MIB
        AtmVpIdentifier, AtmVcIdentifier, AtmVorXOperStatus
            FROM ATM-TC-MIB
        pgainDSLAM
            FROM PAIRGAIN-COMMON-HD-MIB;

     pgBackupMIB MODULE-IDENTITY
		LAST-UPDATED ""
		ORGANIZATION "PairGain Technologies, Inc."
		CONTACT-INFO ""
		DESCRIPTION
			"The MIB Module for BACKUP."
		::= { pgainDSLAM 19 }

     pgBackupObjects OBJECT IDENTIFIER ::= { pgBackupMIB 1 }

     --  PairGain Backup Port Table

     -- This table contains configuration and state
     -- information of a backup port entry

     -- This table is used to restore the PVC
     -- connection back from the backup path to the primary
     -- path.

     pgBackupPortTable  OBJECT-TYPE
          SYNTAX         SEQUENCE OF PgBackupPortEntry
          MAX-ACCESS     not-accessible
          STATUS         current
          DESCRIPTION
            "This table is used to restore the PVC/PVP
            connections back from the backup path to the
            primary one. The number of the entry in this table
            depends on the number of line card in the system.
            The entries would be pre-existent. Only the MIB
            object of pgBackupPortAdminStatus is allowed
            to set."
          ::= { pgBackupObjects 1 }

     pgBackupPortEntry  OBJECT-TYPE
          SYNTAX         PgBackupPortEntry
          MAX-ACCESS     not-accessible
          STATUS         current
          DESCRIPTION
            "The entry of the pgBackupPortTable. The ifIndex
            would be the ATM interface of the line card."
          INDEX { ifIndex }
          ::= { pgBackupPortTable 1 }

     PgBackupPortEntry    ::= SEQUENCE  {
          pgBackupPortAdminStatus  	INTEGER
                }

     pgBackupPortAdminStatus  OBJECT-TYPE
          SYNTAX         INTEGER { enable(1) }
          MAX-ACCESS     read-write
          STATUS         current
          DESCRIPTION
            "This object is used to restore the PVC/PVP
            connection back from the backup path to
            the primary path."
          ::= { pgBackupPortEntry 1 }

     --  PairGain Backup VP Table

     -- This table contains configuration and state
     -- information of a backup Virtual Path.

     -- This table can be used to keep track of the relationship
     -- of the connection between the primary path and the backup
     -- path.

     pgBackupVpTable    OBJECT-TYPE
          SYNTAX         SEQUENCE OF PgBackupVpEntry
          MAX-ACCESS     not-accessible
          STATUS         current
          DESCRIPTION
            "The Backup VP table. This table is used for PVPs
	    Redirect."
          ::= { pgBackupObjects 2 }

     pgBackupVpEntry    OBJECT-TYPE
          SYNTAX         PgBackupVpEntry
          MAX-ACCESS     not-accessible
          STATUS         current
          DESCRIPTION
            "The entry of pgBackupVpTable."
          INDEX { pgBackupVpPrimaryIfIndex,
                  pgBackupVpPrimaryVpi,
                  pgBackupVpSecondaryIfIndex,
                  pgBackupVpSecondaryVpi
                }
          ::= { pgBackupVpTable  1}

     PgBackupVpEntry    ::= SEQUENCE  {
          pgBackupVpPrimaryIfIndex		InterfaceIndex,
          pgBackupVpPrimaryVpi         		AtmVpIdentifier,
          pgBackupVpSecondaryIfIndex    	InterfaceIndex,
          pgBackupVpSecondaryVpi        	AtmVpIdentifier,
          pgBackupVpRowStatus    		RowStatus,
          pgBackupVpPrimaryAdminStatus  	INTEGER,
          pgBackupVpPrimaryOperStatus           AtmVorXOperStatus,
          pgBackupVpSecondaryOperStatus         AtmVorXOperStatus,
	  pgBackupVpSwitchTimes			INTEGER
                }

     pgBackupVpPrimaryIfIndex    OBJECT-TYPE
          SYNTAX         InterfaceIndex
          MAX-ACCESS     not-accessible
          STATUS         current
          DESCRIPTION
            "The ifIndex value of the ATM interface at line
            card side for the primary PVP. This value would
            represent one of the line card in the system."
          ::= { pgBackupVpEntry 1 }

     pgBackupVpPrimaryVpi    OBJECT-TYPE
          SYNTAX         AtmVpIdentifier
          MAX-ACCESS     not-accessible
          STATUS         current
          DESCRIPTION
            "The VPI value of the primary VPL."
          ::= { pgBackupVpEntry 2 }

     pgBackupVpSecondaryIfIndex    OBJECT-TYPE
          SYNTAX         InterfaceIndex
          MAX-ACCESS     not-accessible
          STATUS  current
          DESCRIPTION
            "The ifIndex value of the ATM interface at line
            card side for the secondary PVP. This value would
            represent one of the line card in the system."
          ::= { pgBackupVpEntry 3 }

     pgBackupVpSecondaryVpi    OBJECT-TYPE
          SYNTAX         AtmVpIdentifier
          MAX-ACCESS     not-accessible
          STATUS         current
          DESCRIPTION
            "The VPI value of the secondary VPL."
          ::= { pgBackupVpEntry 4 }

     pgBackupVpRowStatus    OBJECT-TYPE
          SYNTAX         RowStatus
          MAX-ACCESS     read-create
          STATUS         current
          DESCRIPTION
            "This object is used to create, delete
            or modify a row in this table."
          DEFVAL { createAndWait }
          ::= { pgBackupVpEntry 5 }

     pgBackupVpPrimaryAdminStatus    OBJECT-TYPE
          SYNTAX         INTEGER { enable(1) }
          MAX-ACCESS     read-write
          STATUS         current
          DESCRIPTION
            "This object is used to restore the
            PVP back from the secondary PVP to
            the primary PVP."
          ::= { pgBackupVpEntry 6 }

     pgBackupVpPrimaryOperStatus    OBJECT-TYPE
          SYNTAX         AtmVorXOperStatus
          MAX-ACCESS     read-only
          STATUS         current
          DESCRIPTION
            "The current operational status of the cross-connect
            over the primary PVP."
          ::= { pgBackupVpEntry 7 }

     pgBackupVpSecondaryOperStatus    OBJECT-TYPE
          SYNTAX         AtmVorXOperStatus
          MAX-ACCESS     read-only
          STATUS         current
          DESCRIPTION
            "The current operational status of the cross-connect
            over the secondary PVP."
          ::= { pgBackupVpEntry 8 }

     pgBackupVpSwitchTimes    OBJECT-TYPE
          SYNTAX         INTEGER  (0..65535)
          MAX-ACCESS     read-only
          STATUS         current
          DESCRIPTION
            "The number of times when the PVP is
            switched from the primary PVP to the secondary
            PVP."
          ::= { pgBackupVpEntry 9 }


     --  PairGain Backup VC Table

     -- This table contains configuration and state
     -- information of a backup Virtual Connection

     -- This table can be used to keep track of the relationship
     -- of the connection between the primary path and the backup
     -- path.

     pgBackupVcTable    OBJECT-TYPE
          SYNTAX         SEQUENCE OF PgBackupVcEntry
          MAX-ACCESS     not-accessible
          STATUS         current
          DESCRIPTION
            "The Backup VC table. This table is used for PVCs
            Redirect."
          ::= { pgBackupObjects 3 }

     pgBackupVcEntry    OBJECT-TYPE
          SYNTAX         PgBackupVcEntry
          MAX-ACCESS     not-accessible
          STATUS         current
          DESCRIPTION
            "The entry of pgBackupVcTable."
          INDEX { pgBackupVcPrimaryIfIndex,
                  pgBackupVcPrimaryVpi,
                  pgBackupVcPrimaryVci,
                  pgBackupVcSecondaryIfIndex,
                  pgBackupVcSecondaryVpi,
                  pgBackupVcSecondaryVci
                }
          ::= { pgBackupVcTable 1 }

     PgBackupVcEntry    ::= SEQUENCE  {
          pgBackupVcPrimaryIfIndex		InterfaceIndex,
          pgBackupVcPrimaryVpi         		AtmVpIdentifier,
          pgBackupVcPrimaryVci           	AtmVcIdentifier,
          pgBackupVcSecondaryIfIndex    	InterfaceIndex,
          pgBackupVcSecondaryVpi        	AtmVpIdentifier,
          pgBackupVcSecondaryVci        	AtmVcIdentifier,
          pgBackupVcRowStatus    		RowStatus,
          pgBackupVcPrimaryAdminStatus  	INTEGER,
          pgBackupVcPrimaryOperStatus           AtmVorXOperStatus,
          pgBackupVcSecondaryOperStatus         AtmVorXOperStatus,
          pgBackupVcSwitchTimes                 INTEGER
                }

     pgBackupVcPrimaryIfIndex    OBJECT-TYPE
          SYNTAX         InterfaceIndex
          MAX-ACCESS     not-accessible
          STATUS         current
          DESCRIPTION
            "The ifIndex value of the ATM interface at line
            card side for the primary PVC. This value would
            represent one of the line card in the system."
          ::= { pgBackupVcEntry 1 }

     pgBackupVcPrimaryVpi    OBJECT-TYPE
          SYNTAX         AtmVpIdentifier
          MAX-ACCESS     not-accessible
          STATUS         current
          DESCRIPTION
            "The VPI value of the primary VCL."
          ::= { pgBackupVcEntry 2 }

     pgBackupVcPrimaryVci    OBJECT-TYPE
          SYNTAX         AtmVcIdentifier
          MAX-ACCESS     not-accessible
          STATUS         current
          DESCRIPTION
            "The VCI value of the primary VCL."
          ::= { pgBackupVcEntry 3 }

     pgBackupVcSecondaryIfIndex    OBJECT-TYPE
          SYNTAX         InterfaceIndex
          MAX-ACCESS     not-accessible
          STATUS  current
          DESCRIPTION
            "The ifIndex value of the ATM interface at line
            card side for the secondary PVC. This value would
            represent one of the line card in the system."
          ::= { pgBackupVcEntry 4 }

     pgBackupVcSecondaryVpi    OBJECT-TYPE
          SYNTAX         AtmVpIdentifier
          MAX-ACCESS     not-accessible
          STATUS         current
          DESCRIPTION
            "The VPI value of the secondary VCL."
          ::= { pgBackupVcEntry 5 }

     pgBackupVcSecondaryVci    OBJECT-TYPE
          SYNTAX         AtmVcIdentifier
          MAX-ACCESS     not-accessible
          STATUS         current
          DESCRIPTION
            "The VCI value of the secondary VCL."
          ::= { pgBackupVcEntry 6 }

     pgBackupVcRowStatus    OBJECT-TYPE
          SYNTAX         RowStatus
          MAX-ACCESS     read-create
          STATUS         current
          DESCRIPTION
            "This object is used to create, delete
            or modify a row in this table."
          DEFVAL { createAndWait }
          ::= { pgBackupVcEntry 7 }

     pgBackupVcPrimaryAdminStatus    OBJECT-TYPE
          SYNTAX         INTEGER { enable(1) }
          MAX-ACCESS     read-write
          STATUS         current
          DESCRIPTION
            "This object is used to restore the
            PVC back from the secondary PVC to
            the primary PVC."
          ::= { pgBackupVcEntry 8 }

     pgBackupVcPrimaryOperStatus    OBJECT-TYPE
          SYNTAX         AtmVorXOperStatus
          MAX-ACCESS     read-only
          STATUS         current
          DESCRIPTION
            "The current operational status of the cross-connect
            over the primary PVC."
          ::= { pgBackupVcEntry 9 }

     pgBackupVcSecondaryOperStatus    OBJECT-TYPE
          SYNTAX         AtmVorXOperStatus
          MAX-ACCESS     read-only
          STATUS         current
          DESCRIPTION
            "The current operational status of the cross-connect
            over the secondary PVC."
          ::= { pgBackupVcEntry 10 }

     pgBackupVcSwitchTimes    OBJECT-TYPE
          SYNTAX         INTEGER  (0..65535)
          MAX-ACCESS     read-only
          STATUS         current
          DESCRIPTION
            "The number of times when the PVC is
            switched from the primary PVC to the secondary
            PVC."
          ::= { pgBackupVcEntry 11 }

     END
