-- file automatically created


TELDAT-TRAP-WLAN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


wlanTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the WLAN event subsystem."
    REVISION "201401200930Z"
    DESCRIPTION "Initial implementation"
        ::= { telEventTraps 188 }


wlanEventsGroup	OBJECT IDENTIFIER	::= { wlanTrapsMIB 1 }

wlanNotifications	OBJECT IDENTIFIER	::= { wlanTrapsMIB 2 }
wlanNotificationsPrefix	OBJECT IDENTIFIER	::= { wlanNotifications 0 }

wlanEventObjects1 OBJECT-IDENTITY
    STATUS current
    DESCRIPTION
        "Event WLAN.1
        Generic informational event."
    ::= { wlanEventsGroup 1 }

wlan1-string OBJECT-TYPE
    SYNTAX DisplayString
    MAX-ACCESS accessible-for-notify
    STATUS current
    DESCRIPTION
        "Parameter 'string' in event WLAN.1"
    ::= { wlanEventObjects1 1 }

wlanEventObjects2 OBJECT-IDENTITY
    STATUS current
    DESCRIPTION
        "Event WLAN.2
        MLME Transmit Event."
    ::= { wlanEventsGroup 2 }

wlan2-subtype OBJECT-TYPE
    SYNTAX DisplayString
    MAX-ACCESS accessible-for-notify
    STATUS current
    DESCRIPTION
        "Parameter 'subtype' in event WLAN.2"
    ::= { wlanEventObjects2 1 }

wlan2-result OBJECT-TYPE
    SYNTAX DisplayString
    MAX-ACCESS accessible-for-notify
    STATUS current
    DESCRIPTION
        "Parameter 'result' in event WLAN.2"
    ::= { wlanEventObjects2 2 }

wlan2-mac-address OBJECT-TYPE
    SYNTAX DisplayString
    MAX-ACCESS accessible-for-notify
    STATUS current
    DESCRIPTION
        "Parameter 'mac-address' in event WLAN.2"
    ::= { wlanEventObjects2 3 }

wlan2-ifc OBJECT-TYPE
    SYNTAX DisplayString
    MAX-ACCESS accessible-for-notify
    STATUS current
    DESCRIPTION
        "Parameter 'ifc' in event WLAN.2"
    ::= { wlanEventObjects2 4 }

wlanEventObjects3 OBJECT-IDENTITY
    STATUS current
    DESCRIPTION
        "Event WLAN.3
        MLME Receive Event."
    ::= { wlanEventsGroup 3 }

wlan3-subtype OBJECT-TYPE
    SYNTAX DisplayString
    MAX-ACCESS accessible-for-notify
    STATUS current
    DESCRIPTION
        "Parameter 'subtype' in event WLAN.3"
    ::= { wlanEventObjects3 1 }

wlan3-mac-address OBJECT-TYPE
    SYNTAX DisplayString
    MAX-ACCESS accessible-for-notify
    STATUS current
    DESCRIPTION
        "Parameter 'mac-address' in event WLAN.3"
    ::= { wlanEventObjects3 2 }

wlan3-ifc OBJECT-TYPE
    SYNTAX DisplayString
    MAX-ACCESS accessible-for-notify
    STATUS current
    DESCRIPTION
        "Parameter 'ifc' in event WLAN.3"
    ::= { wlanEventObjects3 3 }

wlanEventObjects4 OBJECT-IDENTITY
    STATUS current
    DESCRIPTION
        "Event WLAN.4
        Beacon frame received."
    ::= { wlanEventsGroup 4 }

wlan4-mac-address OBJECT-TYPE
    SYNTAX DisplayString
    MAX-ACCESS accessible-for-notify
    STATUS current
    DESCRIPTION
        "Parameter 'mac-address' in event WLAN.4"
    ::= { wlanEventObjects4 1 }

wlan4-channel OBJECT-TYPE
    SYNTAX Integer32
    MAX-ACCESS accessible-for-notify
    STATUS current
    DESCRIPTION
        "Parameter 'channel' in event WLAN.4"
    ::= { wlanEventObjects4 2 }

wlan4-transState OBJECT-TYPE
    SYNTAX Integer32
    MAX-ACCESS accessible-for-notify
    STATUS current
    DESCRIPTION
        "Parameter 'transState' in event WLAN.4"
    ::= { wlanEventObjects4 3 }

wlan4-rssi OBJECT-TYPE
    SYNTAX Integer32
    MAX-ACCESS accessible-for-notify
    STATUS current
    DESCRIPTION
        "Parameter 'rssi' in event WLAN.4"
    ::= { wlanEventObjects4 4 }

wlanEventObjects5 OBJECT-IDENTITY
    STATUS current
    DESCRIPTION
        "Event WLAN.5
        Station PTK state machine."
    ::= { wlanEventsGroup 5 }

wlan5-state-machine OBJECT-TYPE
    SYNTAX DisplayString
    MAX-ACCESS accessible-for-notify
    STATUS current
    DESCRIPTION
        "Parameter 'state-machine' in event WLAN.5"
    ::= { wlanEventObjects5 1 }

wlan5-state OBJECT-TYPE
    SYNTAX DisplayString
    MAX-ACCESS accessible-for-notify
    STATUS current
    DESCRIPTION
        "Parameter 'state' in event WLAN.5"
    ::= { wlanEventObjects5 2 }

wlan5-interface OBJECT-TYPE
    SYNTAX DisplayString
    MAX-ACCESS accessible-for-notify
    STATUS current
    DESCRIPTION
        "Parameter 'interface' in event WLAN.5"
    ::= { wlanEventObjects5 3 }

wlan5-aid OBJECT-TYPE
    SYNTAX Integer32
    MAX-ACCESS accessible-for-notify
    STATUS current
    DESCRIPTION
        "Parameter 'aid' in event WLAN.5"
    ::= { wlanEventObjects5 4 }

wlanEventObjects6 OBJECT-IDENTITY
    STATUS current
    DESCRIPTION
        "Event WLAN.6
        Station GTK state machine."
    ::= { wlanEventsGroup 6 }

wlan6-state-machine OBJECT-TYPE
    SYNTAX DisplayString
    MAX-ACCESS accessible-for-notify
    STATUS current
    DESCRIPTION
        "Parameter 'state-machine' in event WLAN.6"
    ::= { wlanEventObjects6 1 }

wlan6-state OBJECT-TYPE
    SYNTAX DisplayString
    MAX-ACCESS accessible-for-notify
    STATUS current
    DESCRIPTION
        "Parameter 'state' in event WLAN.6"
    ::= { wlanEventObjects6 2 }

wlan6-interface OBJECT-TYPE
    SYNTAX DisplayString
    MAX-ACCESS accessible-for-notify
    STATUS current
    DESCRIPTION
        "Parameter 'interface' in event WLAN.6"
    ::= { wlanEventObjects6 3 }

wlan6-aid OBJECT-TYPE
    SYNTAX Integer32
    MAX-ACCESS accessible-for-notify
    STATUS current
    DESCRIPTION
        "Parameter 'aid' in event WLAN.6"
    ::= { wlanEventObjects6 4 }

wlanEventObjects7 OBJECT-IDENTITY
    STATUS current
    DESCRIPTION
        "Event WLAN.7
        Global GTK state machine."
    ::= { wlanEventsGroup 7 }

wlan7-state-machine OBJECT-TYPE
    SYNTAX DisplayString
    MAX-ACCESS accessible-for-notify
    STATUS current
    DESCRIPTION
        "Parameter 'state-machine' in event WLAN.7"
    ::= { wlanEventObjects7 1 }

wlan7-state OBJECT-TYPE
    SYNTAX DisplayString
    MAX-ACCESS accessible-for-notify
    STATUS current
    DESCRIPTION
        "Parameter 'state' in event WLAN.7"
    ::= { wlanEventObjects7 2 }

wlan7-interface OBJECT-TYPE
    SYNTAX DisplayString
    MAX-ACCESS accessible-for-notify
    STATUS current
    DESCRIPTION
        "Parameter 'interface' in event WLAN.7"
    ::= { wlanEventObjects7 3 }

wlanEventObjects8 OBJECT-IDENTITY
    STATUS current
    DESCRIPTION
        "Event WLAN.8
        Generic WLAN application informational event."
    ::= { wlanEventsGroup 8 }

wlan8-string OBJECT-TYPE
    SYNTAX DisplayString
    MAX-ACCESS accessible-for-notify
    STATUS current
    DESCRIPTION
        "Parameter 'string' in event WLAN.8"
    ::= { wlanEventObjects8 1 }

wlanEventObjects9 OBJECT-IDENTITY
    STATUS current
    DESCRIPTION
        "Event WLAN.9
        Supplicant key management state machine."
    ::= { wlanEventsGroup 9 }

wlan9-state-machine OBJECT-TYPE
    SYNTAX DisplayString
    MAX-ACCESS accessible-for-notify
    STATUS current
    DESCRIPTION
        "Parameter 'state-machine' in event WLAN.9"
    ::= { wlanEventObjects9 1 }

wlan9-state OBJECT-TYPE
    SYNTAX DisplayString
    MAX-ACCESS accessible-for-notify
    STATUS current
    DESCRIPTION
        "Parameter 'state' in event WLAN.9"
    ::= { wlanEventObjects9 2 }

wlan9-interface OBJECT-TYPE
    SYNTAX DisplayString
    MAX-ACCESS accessible-for-notify
    STATUS current
    DESCRIPTION
        "Parameter 'interface' in event WLAN.9"
    ::= { wlanEventObjects9 3 }

wlanEventObjects10 OBJECT-IDENTITY
    STATUS current
    DESCRIPTION
        "Event WLAN.10
        A WLAN multicast packet was received and it was discarded because
        it did not match registered multicast addresses on interface."
    ::= { wlanEventsGroup 10 }

wlan10-source-WLAN-address OBJECT-TYPE
    SYNTAX DisplayString
    MAX-ACCESS accessible-for-notify
    STATUS current
    DESCRIPTION
        "Parameter 'source-WLAN-address' in event WLAN.10"
    ::= { wlanEventObjects10 1 }

wlan10-destination-WLAN-address OBJECT-TYPE
    SYNTAX DisplayString
    MAX-ACCESS accessible-for-notify
    STATUS current
    DESCRIPTION
        "Parameter 'destination-WLAN-address' in event WLAN.10"
    ::= { wlanEventObjects10 2 }

wlan10-interface OBJECT-TYPE
    SYNTAX DisplayString
    MAX-ACCESS accessible-for-notify
    STATUS current
    DESCRIPTION
        "Parameter 'interface' in event WLAN.10"
    ::= { wlanEventObjects10 3 }

wlanEventObjects11 OBJECT-IDENTITY
    STATUS current
    DESCRIPTION
        "Event WLAN.11
        A WLAN unicast packet was received and it was discarded because
        it did not match local unicast addresses."
    ::= { wlanEventsGroup 11 }

wlan11-source-WLAN-address OBJECT-TYPE
    SYNTAX DisplayString
    MAX-ACCESS accessible-for-notify
    STATUS current
    DESCRIPTION
        "Parameter 'source-WLAN-address' in event WLAN.11"
    ::= { wlanEventObjects11 1 }

wlan11-destination-WLAN-address OBJECT-TYPE
    SYNTAX DisplayString
    MAX-ACCESS accessible-for-notify
    STATUS current
    DESCRIPTION
        "Parameter 'destination-WLAN-address' in event WLAN.11"
    ::= { wlanEventObjects11 2 }

wlan11-interface OBJECT-TYPE
    SYNTAX DisplayString
    MAX-ACCESS accessible-for-notify
    STATUS current
    DESCRIPTION
        "Parameter 'interface' in event WLAN.11"
    ::= { wlanEventObjects11 3 }

wlanEventObjects12 OBJECT-IDENTITY
    STATUS current
    DESCRIPTION
        "Event WLAN.12
        Generic driver informational event"
    ::= { wlanEventsGroup 12 }

wlan12-string OBJECT-TYPE
    SYNTAX DisplayString
    MAX-ACCESS accessible-for-notify
    STATUS current
    DESCRIPTION
        "Parameter 'string' in event WLAN.12"
    ::= { wlanEventObjects12 1 }


wlanNotification1 NOTIFICATION-TYPE
    OBJECTS { 
              wlan1-string 
            }
    STATUS current
    DESCRIPTION
        "Notification of Event WLAN.1

        Message: '$1'

        Parameters list:
              $1: wlan1-string

        Generic informational event."
    ::= { wlanNotificationsPrefix 1 }

wlanNotification2 NOTIFICATION-TYPE
    OBJECTS { 
              wlan2-subtype, 
              wlan2-result,
              wlan2-mac-address,
              wlan2-ifc 
            }
    STATUS current
    DESCRIPTION
        "Notification of Event WLAN.2

        Message: 'mlmeMgtTxCompletion $1 result: $2, destination address $3 in $4'

        Parameters list:
              $1: wlan2-subtype
              $2: wlan2-result
              $3: wlan2-mac-address
              $4: wlan2-ifc

        MLME Transmit Event."
    ::= { wlanNotificationsPrefix 2 }

wlanNotification3 NOTIFICATION-TYPE
    OBJECTS { 
              wlan3-subtype, 
              wlan3-mac-address,
              wlan3-ifc 
            }
    STATUS current
    DESCRIPTION
        "Notification of Event WLAN.3

        Message: 'mlmeMgtRxCompletion $1, destination address $2 in $3'

        Parameters list:
              $1: wlan3-subtype
              $2: wlan3-mac-address
              $3: wlan3-ifc

        MLME Receive Event."
    ::= { wlanNotificationsPrefix 3 }

wlanNotification4 NOTIFICATION-TYPE
    OBJECTS { 
              wlan4-mac-address, 
              wlan4-channel,
              wlan4-transState,
              wlan4-rssi 
            }
    STATUS current
    DESCRIPTION
        "Notification of Event WLAN.4

        Message: 'mlmeBeaconReceive: Beacon from $1 on channel $2, transState: $3, RSSI: $4'

        Parameters list:
              $1: wlan4-mac-address
              $2: wlan4-channel
              $3: wlan4-transState
              $4: wlan4-rssi

        Beacon frame received."
    ::= { wlanNotificationsPrefix 4 }

wlanNotification5 NOTIFICATION-TYPE
    OBJECTS { 
              wlan5-state-machine, 
              wlan5-state,
              wlan5-interface,
              wlan5-aid 
            }
    STATUS current
    DESCRIPTION
        "Notification of Event WLAN.5

        Message: 'State Machine $1 entered state $2, ifc $3 aid $4'

        Parameters list:
              $1: wlan5-state-machine
              $2: wlan5-state
              $3: wlan5-interface
              $4: wlan5-aid

        Station PTK state machine."
    ::= { wlanNotificationsPrefix 5 }

wlanNotification6 NOTIFICATION-TYPE
    OBJECTS { 
              wlan6-state-machine, 
              wlan6-state,
              wlan6-interface,
              wlan6-aid 
            }
    STATUS current
    DESCRIPTION
        "Notification of Event WLAN.6

        Message: 'State Machine $1 entered state $2, ifc $3 aid $4'

        Parameters list:
              $1: wlan6-state-machine
              $2: wlan6-state
              $3: wlan6-interface
              $4: wlan6-aid

        Station GTK state machine."
    ::= { wlanNotificationsPrefix 6 }

wlanNotification7 NOTIFICATION-TYPE
    OBJECTS { 
              wlan7-state-machine, 
              wlan7-state,
              wlan7-interface 
            }
    STATUS current
    DESCRIPTION
        "Notification of Event WLAN.7

        Message: 'State Machine $1 entered state $2, ifc $3'

        Parameters list:
              $1: wlan7-state-machine
              $2: wlan7-state
              $3: wlan7-interface

        Global GTK state machine."
    ::= { wlanNotificationsPrefix 7 }

wlanNotification8 NOTIFICATION-TYPE
    OBJECTS { 
              wlan8-string 
            }
    STATUS current
    DESCRIPTION
        "Notification of Event WLAN.8

        Message: '$1'

        Parameters list:
              $1: wlan8-string

        Generic WLAN application informational event."
    ::= { wlanNotificationsPrefix 8 }

wlanNotification9 NOTIFICATION-TYPE
    OBJECTS { 
              wlan9-state-machine, 
              wlan9-state,
              wlan9-interface 
            }
    STATUS current
    DESCRIPTION
        "Notification of Event WLAN.9

        Message: 'State Machine $1 entered state $2, ifc $3'

        Parameters list:
              $1: wlan9-state-machine
              $2: wlan9-state
              $3: wlan9-interface

        Supplicant key management state machine."
    ::= { wlanNotificationsPrefix 9 }

wlanNotification10 NOTIFICATION-TYPE
    OBJECTS { 
              wlan10-source-WLAN-address, 
              wlan10-destination-WLAN-address,
              wlan10-interface 
            }
    STATUS current
    DESCRIPTION
        "Notification of Event WLAN.10

        Message: 'WLAN multicast packet received from $1 to $2 is filtered interface $3'

        Parameters list:
              $1: wlan10-source-WLAN-address
              $2: wlan10-destination-WLAN-address
              $3: wlan10-interface

        A WLAN multicast packet was received and it was discarded because
        it did not match registered multicast addresses on interface."
    ::= { wlanNotificationsPrefix 10 }

wlanNotification11 NOTIFICATION-TYPE
    OBJECTS { 
              wlan11-source-WLAN-address, 
              wlan11-destination-WLAN-address,
              wlan11-interface 
            }
    STATUS current
    DESCRIPTION
        "Notification of Event WLAN.11

        Message: 'WLAN unicast packet received from $1 to $2 is filtered interface $3'

        Parameters list:
              $1: wlan11-source-WLAN-address
              $2: wlan11-destination-WLAN-address
              $3: wlan11-interface

        A WLAN unicast packet was received and it was discarded because
        it did not match local unicast addresses."
    ::= { wlanNotificationsPrefix 11 }

wlanNotification12 NOTIFICATION-TYPE
    OBJECTS { 
              wlan12-string 
            }
    STATUS current
    DESCRIPTION
        "Notification of Event WLAN.12

        Message: '$1'

        Parameters list:
              $1: wlan12-string

        Generic driver informational event"
    ::= { wlanNotificationsPrefix 12 }


END
