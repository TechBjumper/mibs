WebGraph-AnalogIO-57662-US-MIB DEFINITIONS ::= BEGIN
----------------------------------------------------------------
-- Revison: 1.30
----------------------------------------------------------------
-- 08.01.2010 	New: Reports
--		 
----------------------------------------------------------------
-- Revison: 1.29
----------------------------------------------------------------
-- 01.10.2009 	Webio
--		New Analog Out: 57662
----------------------------------------------------------------
-- Revison: 1.28
----------------------------------------------------------------
-- 02.12.2008 	Webio
--		New Graphics java script base parameter 
----------------------------------------------------------------
-- Revison: 1.27
----------------------------------------------------------------
-- 09.11.2006 	Webio
--		DHCP enable 
----------------------------------------------------------------
-- Revison: 1.26
----------------------------------------------------------------
-- 28.06.2006 	New: Community String Trap
--		
----------------------------------------------------------------
-- Revison: 1.25
----------------------------------------------------------------
-- 25.11.2005 	#57641, WebGraph AnalogIn
--		OID correction 
----------------------------------------------------------------
-- Revison: 1.24
----------------------------------------------------------------
-- 26.07.2005 	#57641, WebGraph AnalogIn
--		CRON timer function
----------------------------------------------------------------
-- Revison: 1.23
----------------------------------------------------------------
-- 14.07.2005 	#57641, WebGraph AnalogIn
--		FTP functions
----------------------------------------------------------------
-- Revison: 1.22
----------------------------------------------------------------
-- 17.05.2005 	#57641, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermHygroAlarmRHMin
--			wtWebGraphThermHygroAlarmRHMax
--			wtWebGraphThermHygroAlarmRHHysteresis
--			wtWebGraphThermHygroPortSensorSelect
--			wtWebGraphThermHygroAlarmDeltaTemp		
--			wtWebGraphThermHygroAlarmAHMin		
--			wtWebGraphThermHygroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalog57662  			OBJECT IDENTIFIER ::= { wtWebio 29 }
    
--  wtWebGraphAnalog57662 Tree

    wtWebGraphAnalog57662Inventory   		OBJECT IDENTIFIER ::= { wtWebGraphAnalog57662 1 }
    wtWebGraphAnalog57662SessCntrl 		OBJECT IDENTIFIER ::= { wtWebGraphAnalog57662 2 }
    wtWebGraphAnalog57662Config    		OBJECT IDENTIFIER ::= { wtWebGraphAnalog57662 3 }
    wtWebGraphAnalog57662Diag    		OBJECT IDENTIFIER ::= { wtWebGraphAnalog57662 4 }
    	
--  wtWebGraphAnalog57662Config Tree

    wtWebGraphAnalog57662Device    		OBJECT IDENTIFIER ::= { wtWebGraphAnalog57662Config 1 }
    wtWebGraphAnalog57662Ports     		OBJECT IDENTIFIER ::= { wtWebGraphAnalog57662Config 2 }	
    wtWebGraphAnalog57662Manufact  		OBJECT IDENTIFIER ::= { wtWebGraphAnalog57662Config 3 }	

--  wtWebGraphAnalog57662Device Tree

    wtWebGraphAnalog57662Text			OBJECT IDENTIFIER ::= { wtWebGraphAnalog57662Device 1 }	
    wtWebGraphAnalog57662TimeDate 		OBJECT IDENTIFIER ::= { wtWebGraphAnalog57662Device 2 }
    wtWebGraphAnalog57662Basic			OBJECT IDENTIFIER ::= { wtWebGraphAnalog57662Device 3 }	
    wtWebGraphAnalog57662Datalogger		OBJECT IDENTIFIER ::= { wtWebGraphAnalog57662Device 4 }	
    wtWebGraphAnalog57662Alarm			OBJECT IDENTIFIER ::= { wtWebGraphAnalog57662Device 5 }
    wtWebGraphAnalog57662Graphics 		OBJECT IDENTIFIER ::= { wtWebGraphAnalog57662Device 6 }
    wtWebGraphAnalog57662Report			OBJECT IDENTIFIER ::= { wtWebGraphAnalog57662Device 7 }    
    
--  wtWebGraphAnalog57662TimeDate Tree

    wtWebGraphAnalog57662TimeZone		OBJECT IDENTIFIER ::= { wtWebGraphAnalog57662TimeDate 1 }
    wtWebGraphAnalog57662TimeServer		OBJECT IDENTIFIER ::= { wtWebGraphAnalog57662TimeDate 2 }	
    wtWebGraphAnalog57662DeviceClock		OBJECT IDENTIFIER ::= { wtWebGraphAnalog57662TimeDate 3 }

--  wtWebGraphAnalog57662Basic Tree
    
    wtWebGraphAnalog57662Network		OBJECT IDENTIFIER ::= { wtWebGraphAnalog57662Basic 1 }
    wtWebGraphAnalog57662HTTP			OBJECT IDENTIFIER ::= { wtWebGraphAnalog57662Basic 2 }
    wtWebGraphAnalog57662Mail			OBJECT IDENTIFIER ::= { wtWebGraphAnalog57662Basic 3 }	
    wtWebGraphAnalog57662SNMP			OBJECT IDENTIFIER ::= { wtWebGraphAnalog57662Basic 4 }
    wtWebGraphAnalog57662UDP			OBJECT IDENTIFIER ::= { wtWebGraphAnalog57662Basic 5 }
    wtWebGraphAnalog57662Syslog			OBJECT IDENTIFIER ::= { wtWebGraphAnalog57662Basic 6 }
    wtWebGraphAnalog57662FTP			OBJECT IDENTIFIER ::= { wtWebGraphAnalog57662Basic 7 }
    wtWebGraphAnalog57662Language		OBJECT IDENTIFIER ::= { wtWebGraphAnalog57662Basic 8 }
    wtWebGraphAnalog57662Binary			OBJECT IDENTIFIER ::= { wtWebGraphAnalog57662Basic 9 }

--  wtWebGraphAnalog57662Graphics Tree
    
    wtWebGraphAnalog57662GraphicsBase 		OBJECT IDENTIFIER ::= { wtWebGraphAnalog57662Graphics 1 }
    wtWebGraphAnalog57662GraphicsSelect 	OBJECT IDENTIFIER ::= { wtWebGraphAnalog57662Graphics 2 }
    wtWebGraphAnalog57662GraphicsScale 		OBJECT IDENTIFIER ::= { wtWebGraphAnalog57662Graphics 3 }
       
-- wtWebGraphAnalog57662Inventory Group
------------------------

wtWebGraphAnalog57662Sensors OBJECT-TYPE
    SYNTAX INTEGER (1..2)
    ACCESS read-only
    STATUS mandatory
    DESCRIPTION
        "Number of sensors"
    ::= { wtWebGraphAnalog57662Inventory 1 }

-- Interface Table

wtWebGraphAnalog57662SensorTable OBJECT-TYPE
    SYNTAX SEQUENCE OF WtWebGraphAnalog57662SensorEntry
    ACCESS not-accessible
    STATUS mandatory
    DESCRIPTION
        "List of sensors."
    ::= { wtWebGraphAnalog57662Inventory 2 }

wtWebGraphAnalog57662SensorEntry OBJECT-TYPE
    SYNTAX WtWebGraphAnalog57662SensorEntry
    ACCESS not-accessible
    STATUS mandatory
    DESCRIPTION
        "List of sensor numbers."
    INDEX  { wtWebGraphAnalog57662SensorNo }
    ::= { wtWebGraphAnalog57662SensorTable 1 }

WtWebGraphAnalog57662SensorEntry ::= SEQUENCE {
    wtWebGraphAnalog57662SensorNo INTEGER
}

wtWebGraphAnalog57662SensorNo OBJECT-TYPE
    SYNTAX INTEGER (1..2)
    ACCESS read-only
    STATUS mandatory
    DESCRIPTION
        "Sensor number."
    ::= { wtWebGraphAnalog57662SensorEntry 1 }


-- wtWebGraphAnalog57662Values Table

wtWebGraphAnalog57662ValuesTable OBJECT-TYPE
    SYNTAX SEQUENCE OF WtWebGraphAnalog57662ValuesEntry
    ACCESS not-accessible
    STATUS mandatory
    DESCRIPTION
        "List of measurement values corresponding to the channel numbers."
    ::= { wtWebGraphAnalog57662Inventory 3 }

wtWebGraphAnalog57662ValuesEntry OBJECT-TYPE
    SYNTAX WtWebGraphAnalog57662ValuesEntry
    ACCESS not-accessible
    STATUS mandatory
    DESCRIPTION
        "Measurement values of the sensors."
    INDEX  { wtWebGraphAnalog57662SensorNo }
    ::= { wtWebGraphAnalog57662ValuesTable 1 }

WtWebGraphAnalog57662ValuesEntry ::= SEQUENCE{
    wtWebGraphAnalog57662Values OCTET STRING
}

wtWebGraphAnalog57662Values OBJECT-TYPE
    SYNTAX OCTET STRING (SIZE (5))
    ACCESS read-write
    STATUS mandatory
    DESCRIPTION
        "Measurement value of the sensor, ASCII.
        This value will be translated according to the ports settings
        for the read and write operations."
    ::= { wtWebGraphAnalog57662ValuesEntry 1 }

-- wtWebGraphAnalog57662BinaryValues Table

wtWebGraphAnalog57662BinaryValuesTable OBJECT-TYPE
    SYNTAX SEQUENCE OF WtWebGraphAnalog57662BinaryValuesEntry
    ACCESS not-accessible
    STATUS mandatory
    DESCRIPTION
        "List of binary measurement values corresponding to the channel numbers."
    ::= { wtWebGraphAnalog57662Inventory 4 }

wtWebGraphAnalog57662BinaryValuesEntry OBJECT-TYPE
    SYNTAX WtWebGraphAnalog57662BinaryValuesEntry
    ACCESS not-accessible
    STATUS mandatory
    DESCRIPTION
        "Binary measurement values of the sensors."
    INDEX  { wtWebGraphAnalog57662SensorNo }
    ::= { wtWebGraphAnalog57662BinaryValuesTable 1 }

WtWebGraphAnalog57662BinaryValuesEntry ::= SEQUENCE{
    wtWebGraphAnalog57662BinaryValues INTEGER
}    

wtWebGraphAnalog57662BinaryValues OBJECT-TYPE
    SYNTAX INTEGER
    ACCESS read-write
    STATUS mandatory
    DESCRIPTION
        "Binary measurement value of the sensor in 1/1000,
        signed number, 0x7FFFFFFF indicates an invalid value.
        This value will be translated according to the ports settings
        for the read and write operations."
    ::= { wtWebGraphAnalog57662BinaryValuesEntry 1 }

-- wtWebGraphAnalog57662SessCntrl Group
--------------------------------

wtWebGraphAnalog57662SessCntrlPassword OBJECT-TYPE
    SYNTAX OCTET STRING 
    ACCESS read-write
    STATUS mandatory
    DESCRIPTION
        "Entering this password opens a session which is ended by writing a 1 to 
        wtWebGraphAnalog57662SessCntrlLogout. When read this variable provides a string of
        length zero."
    ::= { wtWebGraphAnalog57662SessCntrl 1 }

wtWebGraphAnalog57662SessCntrlConfigMode OBJECT-TYPE
    SYNTAX INTEGER {
    wtWebGraphAnalog57662SessCntrl-NoSession(0),
    wtWebGraphAnalog57662SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalog57662SessCntrl 2 }

wtWebGraphAnalog57662SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphAnalog57662SessCntrl 3 }

wtWebGraphAnalog57662SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphAnalog57662SessCntrl 4 }

wtWebGraphAnalog57662SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphAnalog57662SessCntrl 5 }
    

-- wtWebGraphAnalog57662Text Group
------------------------

wtWebGraphAnalog57662DeviceName OBJECT-TYPE
    SYNTAX OCTET STRING 
    ACCESS read-write
    STATUS mandatory
    DESCRIPTION
        "Name of the Webio, which is user definable."
    ::= { wtWebGraphAnalog57662Text 1 }

wtWebGraphAnalog57662DeviceText OBJECT-TYPE
    SYNTAX OCTET STRING 
    ACCESS read-write
    STATUS mandatory
    DESCRIPTION
        "Description of the Webio, which is user definable."
    ::= { wtWebGraphAnalog57662Text 2 }

wtWebGraphAnalog57662DeviceLocation OBJECT-TYPE
    SYNTAX OCTET STRING 
    ACCESS read-write
    STATUS mandatory
    DESCRIPTION
        "Description of the location of the Webio, which is user definable."
    ::= { wtWebGraphAnalog57662Text 3 }

wtWebGraphAnalog57662DeviceContact OBJECT-TYPE
    SYNTAX OCTET STRING 
    ACCESS read-write
    STATUS mandatory
    DESCRIPTION
        "Contact address of the system operator of the Webio, which is user definable."
    ::= { wtWebGraphAnalog57662Text 4 }

-- wtWebGraphAnalog57662TimeZone Group
----------------------------

wtWebGraphAnalog57662TzOffsetHrs OBJECT-TYPE
    SYNTAX INTEGER 
    ACCESS read-write
    STATUS mandatory
    DESCRIPTION
        "Offset hours for the time zone (winter time) with respect to UTC."
    ::= { wtWebGraphAnalog57662TimeZone 1 }

wtWebGraphAnalog57662TzOffsetMin OBJECT-TYPE
    SYNTAX INTEGER 
    ACCESS read-write
    STATUS mandatory
    DESCRIPTION
        "Offset minutes for the time zone (winter time) with respect to UTC."
    ::= { wtWebGraphAnalog57662TimeZone 2 }

wtWebGraphAnalog57662TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalog57662TimeZone 3 }    
    
wtWebGraphAnalog57662StTzOffsetHrs OBJECT-TYPE
    SYNTAX INTEGER 
    ACCESS read-write
    STATUS mandatory
    DESCRIPTION
        "Offset hours of the time zone (summer time) with respect to UTC."
    ::= { wtWebGraphAnalog57662TimeZone 4 }

wtWebGraphAnalog57662StTzOffsetMin OBJECT-TYPE
    SYNTAX INTEGER 
    ACCESS read-write
    STATUS mandatory
    DESCRIPTION
        "Offset minutes of the time zone (summer time) with respect to UTC."
    ::= { wtWebGraphAnalog57662TimeZone 5 }
    
wtWebGraphAnalog57662StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalog57662TimeZone 6 }       
    
wtWebGraphAnalog57662StTzStartMonth OBJECT-TYPE
    SYNTAX INTEGER {
    	wtWebGraphAnalog57662StartMonth-January(1),
    	wtWebGraphAnalog57662StartMonth-February(2),
    	wtWebGraphAnalog57662StartMonth-March(3),
    	wtWebGraphAnalog57662StartMonth-April(4),
    	wtWebGraphAnalog57662StartMonth-May(5),
    	wtWebGraphAnalog57662StartMonth-June(6),
    	wtWebGraphAnalog57662StartMonth-July(7),
    	wtWebGraphAnalog57662StartMonth-August(8),
    	wtWebGraphAnalog57662StartMonth-September(9),
    	wtWebGraphAnalog57662StartMonth-October(10),
    	wtWebGraphAnalog57662StartMonth-November(11),
    	wtWebGraphAnalog57662StartMonth-December(12)
    	}
    	
    ACCESS read-write
    STATUS mandatory
    DESCRIPTION
        "Month in which the change is made from winter time to summer time."
    ::= { wtWebGraphAnalog57662TimeZone 7 }

wtWebGraphAnalog57662StTzStartMode OBJECT-TYPE
    SYNTAX INTEGER {
    	wtWebGraphAnalog57662StartMode-first(1),
    	wtWebGraphAnalog57662StartMode-second(2),
    	wtWebGraphAnalog57662StartMode-third(3),
    	wtWebGraphAnalog57662StartMode-fourth(4),
    	wtWebGraphAnalog57662StartMode-last(5)
    	}
    	
    ACCESS read-write
    STATUS mandatory
    DESCRIPTION
        "Mode of the day of the week for which the change is made from winter time to summer time."
    ::= { wtWebGraphAnalog57662TimeZone 8 }

wtWebGraphAnalog57662StTzStartWday OBJECT-TYPE
    SYNTAX INTEGER {
    	wtWebGraphAnalog57662StartWday-Sunday(1),
    	wtWebGraphAnalog57662StartWday-Monday(2),
    	wtWebGraphAnalog57662StartWday-Tuesday(3),
    	wtWebGraphAnalog57662StartWday-Thursday(4),
    	wtWebGraphAnalog57662StartWday-Wednesday(5),
    	wtWebGraphAnalog57662StartWday-Friday(6),
    	wtWebGraphAnalog57662StartWday-Saturday(7)
    	}
    	
    ACCESS read-write
    STATUS mandatory
    DESCRIPTION
        "Day of the week on which the change is made from winter time to summer time"
    ::= { wtWebGraphAnalog57662TimeZone 9 }
    
wtWebGraphAnalog57662StTzStartHrs OBJECT-TYPE
    SYNTAX INTEGER 
    ACCESS read-write
    STATUS mandatory
    DESCRIPTION
        "Hour in which the time zone is changed from winter to summer time with
        respect to UTC."
    ::= { wtWebGraphAnalog57662TimeZone 10 }

wtWebGraphAnalog57662StTzStartMin OBJECT-TYPE
    SYNTAX INTEGER 
    ACCESS read-write
    STATUS mandatory
    DESCRIPTION
        "Minute in which the time zone is changed from winter to summer time with
        respect to UTC."
    ::= { wtWebGraphAnalog57662TimeZone 11 }
 
wtWebGraphAnalog57662StTzStopMonth OBJECT-TYPE
    SYNTAX INTEGER {
    	wtWebGraphAnalog57662StopMonth-January(1),
    	wtWebGraphAnalog57662StopMonth-February(2),
    	wtWebGraphAnalog57662StopMonth-March(3),
    	wtWebGraphAnalog57662StopMonth-April(4),
    	wtWebGraphAnalog57662StopMonth-May(5),
    	wtWebGraphAnalog57662StopMonth-June(6),
    	wtWebGraphAnalog57662StopMonth-July(7),
    	wtWebGraphAnalog57662StopMonth-August(8),
    	wtWebGraphAnalog57662StopMonth-September(9),
    	wtWebGraphAnalog57662StopMonth-October(10),
    	wtWebGraphAnalog57662StopMonth-November(11),
    	wtWebGraphAnalog57662StopMonth-December(12)
    	}
    ACCESS read-write
    STATUS mandatory
    DESCRIPTION
        "Month in which the change is made from summer time to winter time."
   ::= { wtWebGraphAnalog57662TimeZone 12 }

wtWebGraphAnalog57662StTzStopMode OBJECT-TYPE
    SYNTAX INTEGER {
    	wtWebGraphAnalog57662StopMode-first(1),
    	wtWebGraphAnalog57662StopMode-second(2),
    	wtWebGraphAnalog57662StopMode-third(3),
    	wtWebGraphAnalog57662StopMode-fourth(4),
    	wtWebGraphAnalog57662StopMode-last(5)
    	}
    ACCESS read-write
    STATUS mandatory
    DESCRIPTION
        "Mode of the week day on which the change is made from summer time to winter time."
    ::= { wtWebGraphAnalog57662TimeZone 13 }

wtWebGraphAnalog57662StTzStopWday OBJECT-TYPE
    SYNTAX INTEGER {
    	wtWebGraphAnalog57662StopWday-Sunday(1),
    	wtWebGraphAnalog57662StopWday-Monday(2),
    	wtWebGraphAnalog57662StopWday-Tuesday(3),
    	wtWebGraphAnalog57662StopWday-Thursday(4),
    	wtWebGraphAnalog57662StopWday-Wednesday(5),
    	wtWebGraphAnalog57662StopWday-Friday(6),
    	wtWebGraphAnalog57662StopWday-Saturday(7)
    	}
    ACCESS read-write
    STATUS mandatory
    DESCRIPTION
        "Day of the week on which the change is made from summer time to winter time."
    ::= { wtWebGraphAnalog57662TimeZone 14 }
    
wtWebGraphAnalog57662StTzStopHrs OBJECT-TYPE
    SYNTAX INTEGER 
    ACCESS read-write
    STATUS mandatory
    DESCRIPTION
        "Hour at which the time zone is changed from summer to winter time with
        respect to UTC."
    ::= { wtWebGraphAnalog57662TimeZone 15 }

wtWebGraphAnalog57662StTzStopMin OBJECT-TYPE
    SYNTAX INTEGER 
    ACCESS read-write
    STATUS mandatory
    DESCRIPTION
        "Minute at which the time zone is changed from summer to winter time with
        respect to UTC."
    ::= { wtWebGraphAnalog57662TimeZone 16 }

-- wtWebGraphAnalog57662TimeServer Group
----------------------------

wtWebGraphAnalog57662TimeServer1 OBJECT-TYPE
    SYNTAX OCTET STRING 
    ACCESS read-write
    STATUS mandatory
    DESCRIPTION
        "IP address or name of the 1st time server in ASCII"
    ::= { wtWebGraphAnalog57662TimeServer 1 }

wtWebGraphAnalog57662TimeServer2 OBJECT-TYPE
    SYNTAX OCTET STRING 
    ACCESS read-write
    STATUS mandatory
    DESCRIPTION
        "IP address or name of the 2nd time server in ASCII"
    ::= { wtWebGraphAnalog57662TimeServer 2 }
    
wtWebGraphAnalog57662TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalog57662TimeServer 3 }
    
wtWebGraphAnalog57662TsSyncTime OBJECT-TYPE
    SYNTAX INTEGER 
    ACCESS read-write
    STATUS mandatory
    DESCRIPTION
        "Daily synchronisation time with the time server (hour: 0-23)."
    ::= { wtWebGraphAnalog57662TimeServer 4 } 
    
-- wtWebGraphAnalog57662DeviceClock Group
----------------------------

wtWebGraphAnalog57662ClockHrs OBJECT-TYPE
    SYNTAX INTEGER (0..23)
    ACCESS read-write
    STATUS mandatory
    DESCRIPTION
        "Clock hours taking into account the time zone settings."
    ::= { wtWebGraphAnalog57662DeviceClock 1 }

wtWebGraphAnalog57662ClockMin OBJECT-TYPE
    SYNTAX INTEGER (0..59)
    ACCESS read-write
    STATUS mandatory
    DESCRIPTION
        "Clock minutes taking into account the time zone settings."
    ::= { wtWebGraphAnalog57662DeviceClock 2 }

wtWebGraphAnalog57662ClockDay OBJECT-TYPE
    SYNTAX INTEGER (1..31)
    ACCESS read-write
    STATUS mandatory
    DESCRIPTION
        "Date: Day of the month, taking into account the time zone settings."
    ::= { wtWebGraphAnalog57662DeviceClock 3 }

wtWebGraphAnalog57662ClockMonth OBJECT-TYPE
   SYNTAX INTEGER {
    	wtWebGraphAnalog57662ClockMonth-January(1),
    	wtWebGraphAnalog57662ClockMonth-February(2),
    	wtWebGraphAnalog57662ClockMonth-March(3),
    	wtWebGraphAnalog57662ClockMonth-April(4),
    	wtWebGraphAnalog57662ClockMonth-May(5),
    	wtWebGraphAnalog57662ClockMonth-June(6),
    	wtWebGraphAnalog57662ClockMonth-July(7),
    	wtWebGraphAnalog57662ClockMonth-August(8),
    	wtWebGraphAnalog57662ClockMonth-September(9),
    	wtWebGraphAnalog57662ClockMonth-October(10),
    	wtWebGraphAnalog57662ClockMonth-November(11),
    	wtWebGraphAnalog57662ClockMonth-December(12)
    	}
    ACCESS read-write
    STATUS mandatory
    DESCRIPTION
        "Date: Month, taking into account the time zone settings."
    ::= { wtWebGraphAnalog57662DeviceClock 4 }

wtWebGraphAnalog57662ClockYear OBJECT-TYPE
    SYNTAX INTEGER (0..65535)
    ACCESS read-write
    STATUS mandatory
    DESCRIPTION
        "Date: Year, taking into account the time zone settings."
    ::= { wtWebGraphAnalog57662DeviceClock 5 }
    

-- wtWebGraphAnalog57662Network Group
------------------------

wtWebGraphAnalog57662IpAddress OBJECT-TYPE
    SYNTAX IpAddress
    ACCESS read-write
    STATUS mandatory
    DESCRIPTION
        "IP address of the Webio"
    ::= { wtWebGraphAnalog57662Network 1 }

wtWebGraphAnalog57662SubnetMask OBJECT-TYPE
    SYNTAX IpAddress
    ACCESS read-write
    STATUS mandatory
    DESCRIPTION
        "Subnet mask of the Webio"
    ::= { wtWebGraphAnalog57662Network 2 }

wtWebGraphAnalog57662Gateway OBJECT-TYPE
    SYNTAX IpAddress
    ACCESS read-write
    STATUS mandatory
    DESCRIPTION
        "Gateway of the Webio"
    ::= { wtWebGraphAnalog57662Network 3 }

wtWebGraphAnalog57662DnsServer1 OBJECT-TYPE
    SYNTAX OCTET STRING 
    ACCESS read-write
    STATUS mandatory
    DESCRIPTION
        "IP address of the 1st DNS server in ASCII"
    ::= { wtWebGraphAnalog57662Network 4 }

wtWebGraphAnalog57662DnsServer2 OBJECT-TYPE
    SYNTAX OCTET STRING 
    ACCESS read-write
    STATUS mandatory
    DESCRIPTION
        "IP address of the 2nd DNS server in ASCII"
    ::= { wtWebGraphAnalog57662Network 5 }

wtWebGraphAnalog57662AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalog57662Network 6 }

--  wtWebGraphAnalog57662HTTP Group
--------------------------------

wtWebGraphAnalog57662Startup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalog57662HTTP 1 }

wtWebGraphAnalog57662GetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalog57662HTTP 2 }  
    
wtWebGraphAnalog57662HttpPort OBJECT-TYPE
    SYNTAX INTEGER (1..65535)
    ACCESS read-write
    STATUS mandatory
    DESCRIPTION
        "Definition of the standard HTML port (Default: 80)."
    ::= { wtWebGraphAnalog57662HTTP 3 }    


-- wtWebGraphAnalog57662Mail Group
--------------------------------

wtWebGraphAnalog57662MailAdName OBJECT-TYPE
    SYNTAX OCTET STRING 
    ACCESS read-write
    STATUS mandatory
    DESCRIPTION
        "Device name for mail administration."
    ::= { wtWebGraphAnalog57662Mail 1 }
    
wtWebGraphAnalog57662MailReply OBJECT-TYPE
    SYNTAX OCTET STRING 
    ACCESS read-write
    STATUS mandatory
    DESCRIPTION
        "Reply address for the mail server."
    ::= { wtWebGraphAnalog57662Mail 2 }
    
wtWebGraphAnalog57662MailServer OBJECT-TYPE
    SYNTAX OCTET STRING 
    ACCESS read-write
    STATUS mandatory
    DESCRIPTION
        "Name or IP address of the mail server."
    ::= { wtWebGraphAnalog57662Mail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalog57662Mail 4 }
    
wtWebGraphAnalog57662MailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalog57662Mail 5 }
    
wtWebGraphAnalog57662MailAuthUser OBJECT-TYPE
    SYNTAX OCTET STRING 
    ACCESS read-write
    STATUS mandatory
    DESCRIPTION
        "Name of the user to be authenticated."
    ::= { wtWebGraphAnalog57662Mail 6 }    
    
wtWebGraphAnalog57662MailAuthPassword OBJECT-TYPE
    SYNTAX OCTET STRING 
    ACCESS read-write
    STATUS mandatory
    DESCRIPTION
        "Authentication password."
    ::= { wtWebGraphAnalog57662Mail 7 }    
    
wtWebGraphAnalog57662MailPop3Server OBJECT-TYPE
    SYNTAX OCTET STRING 
    ACCESS read-write
    STATUS mandatory
    DESCRIPTION
        "Name or Ip-address of the POP3 Servers."
    ::= { wtWebGraphAnalog57662Mail 8 }            

-- wtWebGraphAnalog57662SNMP Group
--------------------------------

wtWebGraphAnalog57662SnmpCommunityStringRead OBJECT-TYPE
    SYNTAX OCTET STRING
    ACCESS read-write
    STATUS mandatory
    DESCRIPTION
        "Community string read only"
    ::= { wtWebGraphAnalog57662SNMP 1 }

wtWebGraphAnalog57662SnmpCommunityStringReadWrite OBJECT-TYPE
    SYNTAX OCTET STRING
    ACCESS read-write
    STATUS mandatory
    DESCRIPTION
        "Community string read / write"
    ::= { wtWebGraphAnalog57662SNMP 2 }

wtWebGraphAnalog57662SystemTrapManagerIP OBJECT-TYPE
    SYNTAX OCTET STRING 
    ACCESS read-write
    STATUS mandatory
    DESCRIPTION
        "Name or IP address of the TCP server which accepts the system trap."
    ::= { wtWebGraphAnalog57662SNMP 3 }
    
wtWebGraphAnalog57662SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalog57662SNMP 4 }
    
wtWebGraphAnalog57662SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphAnalog57662SNMP 5 }
    
wtWebGraphAnalog57662SnmpCommunityStringTrap OBJECT-TYPE
    SYNTAX OCTET STRING
    ACCESS read-write
    STATUS mandatory
    DESCRIPTION
        "Community string send within traps."
    ::= { wtWebGraphAnalog57662SNMP 6 }    
            
    
-- wtWebGraphAnalog57662UDP Group
--------------------------------
    
wtWebGraphAnalog57662UdpPort OBJECT-TYPE
    SYNTAX INTEGER (1..65535)
    ACCESS read-write
    STATUS mandatory
    DESCRIPTION
        "Udp port to which the Udp queries ( short form GET requests) can be sent. This
        port number must be unique within the device."
    ::= { wtWebGraphAnalog57662UDP 1 }
    
wtWebGraphAnalog57662UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalog57662UDP 2 }
    
--  wtWebGraphAnalog57662Syslog Group
--------------------------------
    
wtWebGraphAnalog57662SyslogServerIP OBJECT-TYPE
    SYNTAX OCTET STRING 
    ACCESS read-write
    STATUS mandatory
    DESCRIPTION
        "Name or IP address of the Syslog server, which accepts the Syslog messgaes."
    ::= { wtWebGraphAnalog57662Syslog 1 }
    
wtWebGraphAnalog57662SyslogServerPort OBJECT-TYPE
    SYNTAX INTEGER
    ACCESS read-write
    STATUS mandatory
    DESCRIPTION
        "Portnumber of the Syslog servers, default 514."
    ::= { wtWebGraphAnalog57662Syslog 2 }

wtWebGraphAnalog57662SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalog57662Syslog 3 }    

wtWebGraphAnalog57662SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalog57662Syslog 4 }
    
--  wtWebGraphAnalog57662FTP Group
--------------------------------

wtWebGraphAnalog57662FTPServerIP OBJECT-TYPE
    SYNTAX OCTET STRING 
    ACCESS read-write
    STATUS mandatory
    DESCRIPTION
        "Name or IP address of the FTP server, which accepts the FTP messages."
    ::= { wtWebGraphAnalog57662FTP 1 }
    
wtWebGraphAnalog57662FTPServerControlPort OBJECT-TYPE
    SYNTAX INTEGER
    ACCESS read-write
    STATUS mandatory
    DESCRIPTION
        "Portnumber of the control port of the FTP server, default 21."
    ::= { wtWebGraphAnalog57662FTP 2 }
    
wtWebGraphAnalog57662FTPUserName OBJECT-TYPE
    SYNTAX OCTET STRING 
    ACCESS read-write
    STATUS mandatory
    DESCRIPTION
        "FTP Loggin: user name."
    ::= { wtWebGraphAnalog57662FTP 3 }
    
wtWebGraphAnalog57662FTPPassword OBJECT-TYPE
    SYNTAX OCTET STRING 
    ACCESS read-write
    STATUS mandatory
    DESCRIPTION
        "FTP Loggin: user password."
    ::= { wtWebGraphAnalog57662FTP 4 }

wtWebGraphAnalog57662FTPAccount OBJECT-TYPE
    SYNTAX OCTET STRING 
    ACCESS read-write
    STATUS mandatory
    DESCRIPTION
        "FTP Loggin: name of account."
    ::= { wtWebGraphAnalog57662FTP 5 }

wtWebGraphAnalog57662FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalog57662FTP 6 }
    
wtWebGraphAnalog57662FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalog57662FTP 7 }
    
--  wtWebGraphAnalog57662Language Group
--------------------------------

wtWebGraphAnalog57662LanguageSelect OBJECT-TYPE
    SYNTAX OCTET STRING 
    ACCESS read-write
    STATUS mandatory
    DESCRIPTION
        "Language selection:
        Octet 1: unused
        Octet 2: unused
        Octet 3: unused
        Octet 4:
        	Bit 2-7: unused
        	Bit 1  : English
                Bit 0  : German"
    ::= { wtWebGraphAnalog57662Language 1 }        
    
--  wtWebGraphAnalog57662Binary Group
--------------------------------

wtWebGraphAnalog57662BinaryModeCount OBJECT-TYPE
    SYNTAX INTEGER (1..2)
    ACCESS read-only
    STATUS mandatory
    DESCRIPTION
        "Number of independent binary channels."
    ::= { wtWebGraphAnalog57662Binary 1 }
    
-- Binary Interface Table

wtWebGraphAnalog57662BinaryIfTable OBJECT-TYPE
    SYNTAX SEQUENCE OF WtWebGraphAnalog57662BinaryIfEntry
    ACCESS not-accessible
    STATUS mandatory
    DESCRIPTION
        "Table of indices."
    ::= { wtWebGraphAnalog57662Binary 2 }

wtWebGraphAnalog57662BinaryIfEntry OBJECT-TYPE
    SYNTAX WtWebGraphAnalog57662BinaryIfEntry
    ACCESS not-accessible
    STATUS mandatory
    DESCRIPTION
        "Indices of the binary channels."
    INDEX  { wtWebGraphAnalog57662BinaryModeNo }
    ::= { wtWebGraphAnalog57662BinaryIfTable 1 }

WtWebGraphAnalog57662BinaryIfEntry ::= SEQUENCE {
    wtWebGraphAnalog57662BinaryModeNo INTEGER
}

wtWebGraphAnalog57662BinaryModeNo OBJECT-TYPE
    SYNTAX INTEGER (1..2)
    ACCESS read-only
    STATUS mandatory
    DESCRIPTION
        "Number of the binary channel."
    ::= { wtWebGraphAnalog57662BinaryIfEntry 1 }

-- Binary Table
--------------------------------

wtWebGraphAnalog57662BinaryTable OBJECT-TYPE
    SYNTAX SEQUENCE OF WtWebGraphAnalog57662BinaryEntry
    ACCESS not-accessible
    STATUS mandatory
    DESCRIPTION
        "Table of properties of the binary mode."
    ::= { wtWebGraphAnalog57662Binary 3 }

wtWebGraphAnalog57662BinaryEntry OBJECT-TYPE
    SYNTAX WtWebGraphAnalog57662BinaryEntry
    ACCESS not-accessible
    STATUS mandatory
    DESCRIPTION
        "Binary properties."
    INDEX  { wtWebGraphAnalog57662BinaryModeNo }
    ::= { wtWebGraphAnalog57662BinaryTable 1 }

WtWebGraphAnalog57662BinaryEntry ::= SEQUENCE {
    wtWebGraphAnalog57662BinaryOperationMode			OCTET STRING,
    wtWebGraphAnalog57662BinaryTcpServerLocalPort		INTEGER,
    wtWebGraphAnalog57662BinaryTcpServerInputTrigger		OCTET STRING,
    wtWebGraphAnalog57662BinaryTcpServerApplicationMode		OCTET STRING,
    wtWebGraphAnalog57662BinaryTcpClientLocalPort		INTEGER,
    wtWebGraphAnalog57662BinaryTcpClientServerPort		INTEGER,
    wtWebGraphAnalog57662BinaryTcpClientServerIpAddr		OCTET STRING,
    wtWebGraphAnalog57662BinaryTcpClientServerPassword		OCTET STRING,
    wtWebGraphAnalog57662BinaryTcpClientInactivity		INTEGER,
    wtWebGraphAnalog57662BinaryTcpClientInputTrigger		OCTET STRING,
    wtWebGraphAnalog57662BinaryTcpClientInterval		INTEGER,
    wtWebGraphAnalog57662BinaryTcpClientApplicationMode		OCTET STRING,
    wtWebGraphAnalog57662BinaryUdpPeerLocalPort			INTEGER,
    wtWebGraphAnalog57662BinaryUdpPeerRemotePort		INTEGER,
    wtWebGraphAnalog57662BinaryUdpPeerRemoteIpAddr		OCTET STRING,
    wtWebGraphAnalog57662BinaryUdpPeerInputTrigger		OCTET STRING,
    wtWebGraphAnalog57662BinaryUdpPeerInterval			INTEGER,
    wtWebGraphAnalog57662BinaryUdpPeerApplicationMode		OCTET STRING,
    wtWebGraphAnalog57662BinaryConnectedPort			INTEGER,
    wtWebGraphAnalog57662BinaryConnectedIpAddr			IpAddress,
    wtWebGraphAnalog57662BinaryTcpServerClientHttpPort		INTEGER,
    wtWebGraphAnalog57662BinaryTcpClientServerHttpPort		INTEGER,
    wtWebGraphAnalog57662BinaryTcpServerHysteresis1		OCTET STRING,
    wtWebGraphAnalog57662BinaryTcpServerHysteresis2		OCTET STRING,
    wtWebGraphAnalog57662BinaryTcpClientHysteresis1		OCTET STRING,
    wtWebGraphAnalog57662BinaryTcpClientHysteresis2		OCTET STRING,
    wtWebGraphAnalog57662BinaryUdpPeerHysteresis1		OCTET STRING,
    wtWebGraphAnalog57662BinaryUdpPeerHysteresis2		OCTET STRING
    
}

wtWebGraphAnalog57662BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebGraphAnalog57662BinaryEntry 1 }

wtWebGraphAnalog57662BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebGraphAnalog57662BinaryEntry 2 }

wtWebGraphAnalog57662BinaryTcpServerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input states.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Analog inputs 0-1"
    ::= { wtWebGraphAnalog57662BinaryEntry 3 }

wtWebGraphAnalog57662BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebGraphAnalog57662BinaryEntry 4 }
    
wtWebGraphAnalog57662BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebGraphAnalog57662BinaryEntry 5 }

wtWebGraphAnalog57662BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebGraphAnalog57662BinaryEntry 6 }

wtWebGraphAnalog57662BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebGraphAnalog57662BinaryEntry 7 }

wtWebGraphAnalog57662BinaryTcpClientServerPassword OBJECT-TYPE
    SYNTAX OCTET STRING
    ACCESS read-write
    STATUS mandatory
    DESCRIPTION
        "Building a connection may be protected by the 
        administrator password of the server. Enter the server password
        to establish the connection, if a server administrator password
        exists."
    ::= { wtWebGraphAnalog57662BinaryEntry 8 }

wtWebGraphAnalog57662BinaryTcpClientInactivity OBJECT-TYPE
    SYNTAX INTEGER 
    ACCESS read-write
    STATUS mandatory
    DESCRIPTION
        "Connection timeout in 100ms. If no data are exchanged within the specified  
        time, the device closes the connection to the server.
        The value 0 deactivates the timer. Using the Box2Box mode this function is
        disabled."
    ::= { wtWebGraphAnalog57662BinaryEntry 9 }
    
wtWebGraphAnalog57662BinaryTcpClientInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input states.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Analog inputs 0-1"
    ::= { wtWebGraphAnalog57662BinaryEntry 10 }
 
wtWebGraphAnalog57662BinaryTcpClientInterval OBJECT-TYPE
    SYNTAX INTEGER (0..65535)
    ACCESS read-write
    STATUS mandatory
    DESCRIPTION
        "Configurable interval with a 100ms base, in which the Webio device sends
        data to the configured application. A interval of zero stopps the 
        periodical sending."
    ::= { wtWebGraphAnalog57662BinaryEntry 11 }

wtWebGraphAnalog57662BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57662BinaryEntry 12 }

wtWebGraphAnalog57662BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebGraphAnalog57662BinaryEntry 13 }

wtWebGraphAnalog57662BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebGraphAnalog57662BinaryEntry 14 }

wtWebGraphAnalog57662BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebGraphAnalog57662BinaryEntry 15 }

wtWebGraphAnalog57662BinaryUdpPeerInputTrigger OBJECT-TYPE
    SYNTAX OCTET STRING (SIZE (4))
    ACCESS read-write
    STATUS mandatory
    DESCRIPTION
        "Every change on the inputs causes their state to be transmitted to the 
        remote device. To minimize data traffic, individual inputs may be exempted 
        from this rule. Nevertheless every transmission will contain all input states.
        If a bit is set (1), a change of state on the corresponding input 
        triggers a transmission. If the bit is not set (0), no transmission 
        takes place.
        The OCTETS are interpreted bit-by-bit, with each bit corresponding to an input. 
        Bit 0 corresponds to the LSB.
        OCTET 1: unused
        OCTET 2: unused
        OCTET 3: unused
        OCTET 4, Bit 0-1: Analog inputs 0-1"
    ::= { wtWebGraphAnalog57662BinaryEntry 16 }

wtWebGraphAnalog57662BinaryUdpPeerInterval OBJECT-TYPE
    SYNTAX INTEGER (0..65535)
    ACCESS read-write
    STATUS mandatory
    DESCRIPTION
        "Configurable interval with a 100ms base, in which the Webio device sends
        data to the configured remote device. A interval of zero stopps the 
        periodical sending."
    ::= { wtWebGraphAnalog57662BinaryEntry 17 }

wtWebGraphAnalog57662BinaryUdpPeerApplicationMode OBJECT-TYPE
    SYNTAX OCTET STRING (SIZE (4))
    ACCESS read-write
    STATUS mandatory
    DESCRIPTION
        "Selection of the application mode:
        The OCTETS are interpreted bit-by-bit, with each bit corresponding to an output. 
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57662BinaryEntry 18 }

wtWebGraphAnalog57662BinaryConnectedPort OBJECT-TYPE
    SYNTAX INTEGER (1..65535)
    ACCESS read-only
    STATUS mandatory
    DESCRIPTION
        "Port number of the remote device, after connection has been established.
        In case of no connection or missing port informations a zero will be read."
    ::= { wtWebGraphAnalog57662BinaryEntry 19 }

wtWebGraphAnalog57662BinaryConnectedIpAddr OBJECT-TYPE
    SYNTAX IpAddress
    ACCESS read-only
    STATUS mandatory
    DESCRIPTION
        "IP address of the remote device, after connection has been established.
        In case of no connection or missing port informations 0.0.0.0 will be read."
    ::= { wtWebGraphAnalog57662BinaryEntry 20 } 

wtWebGraphAnalog57662BinaryTcpServerClientHttpPort OBJECT-TYPE
    SYNTAX INTEGER (1..65535)
    ACCESS read-write
    STATUS mandatory
    DESCRIPTION
        "HTTP port number of the remote device at TCP Server Mode. If an mailfunction occurs 
        status informations will be send to this port. 
        Not used at mode Compatible 50xxx."
    ::= { wtWebGraphAnalog57662BinaryEntry 21 }
    
wtWebGraphAnalog57662BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebGraphAnalog57662BinaryEntry 22 }                
    
wtWebGraphAnalog57662BinaryTcpServerHysteresis1 OBJECT-TYPE
    SYNTAX OCTET STRING
    ACCESS read-write
    STATUS mandatory
    DESCRIPTION
        "A change greater than this value initiate a transmission of the corresponding input value.
        The input 1 must be selected at wtWebGraphAnalog57662BinaryTcpServerInputTrigger.
        With a hysteresis of zero any change will be transmitted."
    ::= { wtWebGraphAnalog57662BinaryEntry 23 }

wtWebGraphAnalog57662BinaryTcpServerHysteresis2 OBJECT-TYPE
    SYNTAX OCTET STRING
    ACCESS read-write
    STATUS mandatory
    DESCRIPTION
        "A change greater than this value initiate a transmission of the corresponding input value.
        The input 2 must be selected at wtWebGraphAnalog57662BinaryTcpServerInputTrigger.
        With a hysteresis of zero any change will be transmitted."
    ::= { wtWebGraphAnalog57662BinaryEntry 24 }
    
wtWebGraphAnalog57662BinaryTcpClientHysteresis1 OBJECT-TYPE
    SYNTAX OCTET STRING
    ACCESS read-write
    STATUS mandatory
    DESCRIPTION
        "A change greater than this value initiate a transmission of the corresponding input value.
        The input 1 must be selected at wtWebGraphAnalog57662BinaryTcpClientInputTrigger.
        With a hysteresis of zero any change will be transmitted."
        
      ::= { wtWebGraphAnalog57662BinaryEntry 25 }
    
wtWebGraphAnalog57662BinaryTcpClientHysteresis2 OBJECT-TYPE
    SYNTAX OCTET STRING
    ACCESS read-write
    STATUS mandatory
    DESCRIPTION
        "A change greater than this value initiate a transmission of the corresponding input value.
        The input 2 must be selected at wtWebGraphAnalog57662BinaryTcpClientInputTrigger.
        With a hysteresis of zero any change will be transmitted."
        
      ::= { wtWebGraphAnalog57662BinaryEntry 26 }

wtWebGraphAnalog57662BinaryUdpPeerHysteresis1 OBJECT-TYPE
    SYNTAX OCTET STRING
    ACCESS read-write
    STATUS mandatory
    DESCRIPTION
        "A change greater than this value initiate a transmission of the corresponding input value.
        The input 1 must be selected at wtWebGraphAnalog57662BinaryUdpPeerInputTrigger.
        With a hysteresis of zero any change will be transmitted."
    ::= { wtWebGraphAnalog57662BinaryEntry 27 }
            
wtWebGraphAnalog57662BinaryUdpPeerHysteresis2 OBJECT-TYPE
    SYNTAX OCTET STRING
    ACCESS read-write
    STATUS mandatory
    DESCRIPTION
        "A change greater than this value initiate a transmission of the corresponding input value.
        The input 2 must be selected at wtWebGraphAnalog57662BinaryUdpPeerInputTrigger.
        With a hysteresis of zero any change will be transmitted."
    ::= { wtWebGraphAnalog57662BinaryEntry 28 }
            
-- wtWebGraphAnalog57662Datalogger Group
--------------------------------

wtWebGraphAnalog57662LoggerTimebase OBJECT-TYPE
    SYNTAX INTEGER {
    wtWebGraphAnalog57662Datalogger-15Sec(1),
    wtWebGraphAnalog57662Datalogger-30Sec(2),
    wtWebGraphAnalog57662Datalogger-1Min(3),
    wtWebGraphAnalog57662Datalogger-5Min(4),
    wtWebGraphAnalog57662Datalogger-15Min(5),
    wtWebGraphAnalog57662Datalogger-60Min(6)
    }
    ACCESS read-write
    STATUS mandatory
    DESCRIPTION
        "Time base of the data logger"
    ::= { wtWebGraphAnalog57662Datalogger 1 }

wtWebGraphAnalog57662LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalog57662Datalogger 2 }

wtWebGraphAnalog57662DisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalog57662Datalogger 3 }    
    
-- Graph Sensor Color Table

wtWebGraphAnalog57662SensorColorTable OBJECT-TYPE
    SYNTAX SEQUENCE OF WtWebGraphAnalog57662SensorColorEntry
    ACCESS not-accessible
    STATUS mandatory
    DESCRIPTION
        "List of sensor colors for the praphical presentation."
    ::= { wtWebGraphAnalog57662Datalogger 4 }

wtWebGraphAnalog57662SensorColorEntry OBJECT-TYPE
    SYNTAX WtWebGraphAnalog57662SensorColorEntry
    ACCESS not-accessible
    STATUS mandatory
    DESCRIPTION
        "Index numbers of the sensors."
    INDEX  { wtWebGraphAnalog57662SensorNo }
    ::= { wtWebGraphAnalog57662SensorColorTable 1 }

WtWebGraphAnalog57662SensorColorEntry ::= SEQUENCE {
    wtWebGraphAnalog57662SensorColor OCTET STRING
}

wtWebGraphAnalog57662SensorColor OBJECT-TYPE
    SYNTAX OCTET STRING (SIZE(3))
    ACCESS read-write
    STATUS mandatory
    DESCRIPTION
        "Color of the sensors at the praphical presention."
    ::= { wtWebGraphAnalog57662SensorColorEntry 1 }
    
wtWebGraphAnalog57662AutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphAnalog57662Datalogger 5 }
    
wtWebGraphAnalog57662VerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebGraphAnalog57662Datalogger 6 }

wtWebGraphAnalog57662VerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebGraphAnalog57662Datalogger 7 }
    
wtWebGraphAnalog57662HorizontalZoom OBJECT-TYPE
    SYNTAX INTEGER {
    wtWebGraphAnalog57662Zoom-25min(1),
    wtWebGraphAnalog57662Zoom-75min(2),
    wtWebGraphAnalog57662Zoom-5hrs(3),
    wtWebGraphAnalog57662Zoom-30hrs(4),
    wtWebGraphAnalog57662Zoom-5days(5),
    wtWebGraphAnalog57662Zoom-25days(6)
    }
    ACCESS read-write
    STATUS mandatory
    DESCRIPTION
        "Defines the default zoom stage, if no auto scaling is selected."
    ::= { wtWebGraphAnalog57662Datalogger 8 }    

-- wtWebGraphAnalog57662Alarm Group
----------------------------

wtWebGraphAnalog57662AlarmCount OBJECT-TYPE
    SYNTAX INTEGER (1..8)
    ACCESS read-only
    STATUS mandatory
    DESCRIPTION
        "Number of independent alarms."
    ::= { wtWebGraphAnalog57662Alarm 1 }
    
-- Alarm Interface Table

wtWebGraphAnalog57662AlarmIfTable OBJECT-TYPE
    SYNTAX SEQUENCE OF WtWebGraphAnalog57662AlarmIfEntry
    ACCESS not-accessible
    STATUS mandatory
    DESCRIPTION
        "List of alarm indices."
    ::= { wtWebGraphAnalog57662Alarm 2 }

wtWebGraphAnalog57662AlarmIfEntry OBJECT-TYPE
    SYNTAX WtWebGraphAnalog57662AlarmIfEntry
    ACCESS not-accessible
    STATUS mandatory
    DESCRIPTION
        "Numbers of the alarms."
    INDEX  { wtWebGraphAnalog57662AlarmNo }
    ::= { wtWebGraphAnalog57662AlarmIfTable 1 }

WtWebGraphAnalog57662AlarmIfEntry ::= SEQUENCE {
    wtWebGraphAnalog57662AlarmNo INTEGER
}

wtWebGraphAnalog57662AlarmNo OBJECT-TYPE
    SYNTAX INTEGER (1..8)
    ACCESS read-only
    STATUS mandatory
    DESCRIPTION
        "Alarm number."
    ::= { wtWebGraphAnalog57662AlarmIfEntry 1 }

-- Alarm Table

wtWebGraphAnalog57662AlarmTable OBJECT-TYPE
    SYNTAX SEQUENCE OF WtWebGraphAnalog57662AlarmEntry
    ACCESS not-accessible
    STATUS mandatory
    DESCRIPTION
        "List of settings depending on the alarm number."
    ::= { wtWebGraphAnalog57662Alarm 3 }

wtWebGraphAnalog57662AlarmEntry OBJECT-TYPE
    SYNTAX WtWebGraphAnalog57662AlarmEntry
    ACCESS not-accessible
    STATUS mandatory
    DESCRIPTION
        "Alarm parameters of the individual alarms."
    INDEX  { wtWebGraphAnalog57662AlarmNo }
    ::= { wtWebGraphAnalog57662AlarmTable 1 }

WtWebGraphAnalog57662AlarmEntry ::= SEQUENCE {
    wtWebGraphAnalog57662AlarmTrigger			OCTET STRING,
    wtWebGraphAnalog57662AlarmMin1			OCTET STRING,
    wtWebGraphAnalog57662AlarmMax1			OCTET STRING,
    wtWebGraphAnalog57662AlarmHysteresis1		OCTET STRING,
    wtWebGraphAnalog57662AlarmDelay			OCTET STRING,
    wtWebGraphAnalog57662AlarmInterval			OCTET STRING,
    wtWebGraphAnalog57662AlarmEnable			OCTET STRING,
    wtWebGraphAnalog57662AlarmEMailAddr			OCTET STRING,
    wtWebGraphAnalog57662AlarmMailSubject		OCTET STRING,
    wtWebGraphAnalog57662AlarmMailText			OCTET STRING,
    wtWebGraphAnalog57662AlarmManagerIP			OCTET STRING,
    wtWebGraphAnalog57662AlarmTrapText			OCTET STRING,
    wtWebGraphAnalog57662AlarmMailOptions		OCTET STRING,
    wtWebGraphAnalog57662AlarmTcpIpAddr			OCTET STRING,
    wtWebGraphAnalog57662AlarmTcpPort			INTEGER,
    wtWebGraphAnalog57662AlarmTcpText			OCTET STRING,
    wtWebGraphAnalog57662AlarmClearMailSubject		OCTET STRING,
    wtWebGraphAnalog57662AlarmClearMailText		OCTET STRING,
    wtWebGraphAnalog57662AlarmClearTrapText		OCTET STRING,
    wtWebGraphAnalog57662AlarmClearTcpText		OCTET STRING,
    wtWebGraphAnalog57662AlarmMin2			OCTET STRING,
    wtWebGraphAnalog57662AlarmMax2			OCTET STRING,
    wtWebGraphAnalog57662AlarmHysteresis2		OCTET STRING,
    wtWebGraphAnalog57662AlarmSyslogIpAddr		OCTET STRING,
    wtWebGraphAnalog57662AlarmSyslogPort		INTEGER,
    wtWebGraphAnalog57662AlarmSyslogText		OCTET STRING,
    wtWebGraphAnalog57662AlarmSyslogClearText		OCTET STRING,
    wtWebGraphAnalog57662AlarmFtpDataPort		OCTET STRING,
    wtWebGraphAnalog57662AlarmFtpFileName		OCTET STRING,
    wtWebGraphAnalog57662AlarmFtpText			OCTET STRING,
    wtWebGraphAnalog57662AlarmFtpClearText		OCTET STRING,
    wtWebGraphAnalog57662AlarmFtpOption			OCTET STRING,
    wtWebGraphAnalog57662AlarmTimerCron			OCTET STRING

}

wtWebGraphAnalog57662AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphAnalog57662AlarmEntry 1 }

wtWebGraphAnalog57662AlarmMin1 OBJECT-TYPE
    SYNTAX OCTET STRING 
    ACCESS read-write
    STATUS mandatory
    DESCRIPTION
        "Minimum sensor 1 with maximum 3 decimal places."
    ::= { wtWebGraphAnalog57662AlarmEntry 2 }

wtWebGraphAnalog57662AlarmMax1 OBJECT-TYPE
    SYNTAX OCTET STRING 
    ACCESS read-write
    STATUS mandatory
    DESCRIPTION
        "Maximum sensor 1 with maximum 3 decimal places."
    ::= { wtWebGraphAnalog57662AlarmEntry 3 }
    
wtWebGraphAnalog57662AlarmHysteresis1 OBJECT-TYPE
    SYNTAX OCTET STRING 
    ACCESS read-write
    STATUS mandatory
    DESCRIPTION
        "Reading changes of this size clears the alarm state (MAX-hyst, MIN+hyst.)
        with maximum 3 decimal places."
    ::= { wtWebGraphAnalog57662AlarmEntry 4 }

wtWebGraphAnalog57662AlarmDelay OBJECT-TYPE
    SYNTAX OCTET STRING 
    ACCESS read-write
    STATUS mandatory
    DESCRIPTION
        "Alarm will be delayed by setting this time while stable alarm 
        condition occur (time in minutes)."
    ::= { wtWebGraphAnalog57662AlarmEntry 5 }
        

wtWebGraphAnalog57662AlarmInterval OBJECT-TYPE
    SYNTAX OCTET STRING 
    ACCESS read-write
    STATUS mandatory
    DESCRIPTION
        "Send interval for alarm messages."
    ::= { wtWebGraphAnalog57662AlarmEntry 6 }

wtWebGraphAnalog57662AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAnalog57662AlarmEntry 7 }

wtWebGraphAnalog57662AlarmEMailAddr OBJECT-TYPE
    SYNTAX OCTET STRING 
    ACCESS read-write
    STATUS mandatory
    DESCRIPTION
        "E-Mail address for sending the alarm mail to."
    ::= { wtWebGraphAnalog57662AlarmEntry 8 }

wtWebGraphAnalog57662AlarmMailSubject OBJECT-TYPE
    SYNTAX OCTET STRING 
    ACCESS read-write
    STATUS mandatory
    DESCRIPTION
        "Subject line for alarm mail."
    ::= { wtWebGraphAnalog57662AlarmEntry 9 }

wtWebGraphAnalog57662AlarmMailText OBJECT-TYPE
    SYNTAX OCTET STRING 
    ACCESS read-write
    STATUS mandatory
    DESCRIPTION
        "Alarm mail text: <Mn> provides the current temperature; n = 1..2.
        <Z> provides the current time."
    ::= { wtWebGraphAnalog57662AlarmEntry 10 }

wtWebGraphAnalog57662AlarmManagerIP OBJECT-TYPE
    SYNTAX OCTET STRING 
    ACCESS read-write
    STATUS mandatory
    DESCRIPTION
        "Name or IP address of the SNMP Manager which accepts the trap."
    ::= { wtWebGraphAnalog57662AlarmEntry 11 }

wtWebGraphAnalog57662AlarmTrapText OBJECT-TYPE
    SYNTAX OCTET STRING 
    ACCESS read-write
    STATUS mandatory
    DESCRIPTION
        "This text is sent in the trap body."
    ::= { wtWebGraphAnalog57662AlarmEntry 12 }
    
wtWebGraphAnalog57662AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalog57662AlarmEntry 13 }    
    
wtWebGraphAnalog57662AlarmTcpIpAddr OBJECT-TYPE
    SYNTAX OCTET STRING 
    ACCESS read-write
    STATUS mandatory
    DESCRIPTION
        "Name or IP address of the TCP server which accepts the trap."
    ::= { wtWebGraphAnalog57662AlarmEntry 14 }    

wtWebGraphAnalog57662AlarmTcpPort OBJECT-TYPE
    SYNTAX INTEGER (1..65535) 
    ACCESS read-write
    STATUS mandatory
    DESCRIPTION
        "Port number of the TCP server which accepts the trap."
    ::= { wtWebGraphAnalog57662AlarmEntry 15 }    

wtWebGraphAnalog57662AlarmTcpText OBJECT-TYPE
    SYNTAX OCTET STRING 
    ACCESS read-write
    STATUS mandatory
    DESCRIPTION
        "This text is sent in the TCP trap body."
    ::= { wtWebGraphAnalog57662AlarmEntry 16 }

wtWebGraphAnalog57662AlarmClearMailSubject OBJECT-TYPE
    SYNTAX OCTET STRING 
    ACCESS read-write
    STATUS mandatory
    DESCRIPTION
        "Subject line for alarm clear mail."
    ::= { wtWebGraphAnalog57662AlarmEntry 17 }

wtWebGraphAnalog57662AlarmClearMailText OBJECT-TYPE
    SYNTAX OCTET STRING 
    ACCESS read-write
    STATUS mandatory
    DESCRIPTION
        "Alarm clear mail text: <Mn> provides the current temperature; n = 1..2.
        <Z> provides the current time."
    ::= { wtWebGraphAnalog57662AlarmEntry 18 }

wtWebGraphAnalog57662AlarmClearTrapText OBJECT-TYPE
    SYNTAX OCTET STRING 
    ACCESS read-write
    STATUS mandatory
    DESCRIPTION
        "This text is sent in the trap body."
    ::= { wtWebGraphAnalog57662AlarmEntry 19 }

wtWebGraphAnalog57662AlarmClearTcpText OBJECT-TYPE
    SYNTAX OCTET STRING 
    ACCESS read-write
    STATUS mandatory
    DESCRIPTION
        "This text is sent in the TCP trap body."
    ::= { wtWebGraphAnalog57662AlarmEntry 20 }
    
wtWebGraphAnalog57662AlarmMin2 OBJECT-TYPE
    SYNTAX OCTET STRING 
    ACCESS read-write
    STATUS mandatory
    DESCRIPTION
        "Minimum sensor 2 with maximum 3 decimal places."
    ::= { wtWebGraphAnalog57662AlarmEntry 21 }

wtWebGraphAnalog57662AlarmMax2 OBJECT-TYPE
    SYNTAX OCTET STRING 
    ACCESS read-write
    STATUS mandatory
    DESCRIPTION
        "Maximum sensor 2 with maximum 2 decimal places."
    ::= { wtWebGraphAnalog57662AlarmEntry 22 }

wtWebGraphAnalog57662AlarmHysteresis2 OBJECT-TYPE
    SYNTAX OCTET STRING 
    ACCESS read-write
    STATUS mandatory
    DESCRIPTION
        "Hysterese rel. sensor 2 with maximum 3 decimal places."
    ::= { wtWebGraphAnalog57662AlarmEntry 23 }

wtWebGraphAnalog57662AlarmSyslogIpAddr OBJECT-TYPE
    SYNTAX OCTET STRING 
    ACCESS read-write
    STATUS mandatory
    DESCRIPTION
        "IP address of the syslog server to which the Webio device should send syslog messages."
    ::= { wtWebGraphAnalog57662AlarmEntry 24 }    

wtWebGraphAnalog57662AlarmSyslogPort OBJECT-TYPE
    SYNTAX INTEGER (1..65535) 
    ACCESS read-write
    STATUS mandatory
    DESCRIPTION
        "Port number of the syslog server to which the Webio device should send syslog messages."
    ::= { wtWebGraphAnalog57662AlarmEntry 25 }    

wtWebGraphAnalog57662AlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphAnalog57662AlarmEntry 26 }
    
wtWebGraphAnalog57662AlarmSyslogClearText OBJECT-TYPE
    SYNTAX OCTET STRING 
    ACCESS read-write
    STATUS mandatory
    DESCRIPTION
        "Every message starts with the priority key, a time stamp and the host ip address, according RFC3164.
        This text appears in the following syslog message body of a alarm clear message."
    ::= { wtWebGraphAnalog57662AlarmEntry 27 }
    
wtWebGraphAnalog57662AlarmFtpDataPort OBJECT-TYPE
    SYNTAX OCTET STRING 
    ACCESS read-write
    STATUS mandatory
    DESCRIPTION
        "Local data port: 1..65535 or AUTO: the next free port will be assigned."
    ::= { wtWebGraphAnalog57662AlarmEntry 28 }
    
wtWebGraphAnalog57662AlarmFtpFileName OBJECT-TYPE
    SYNTAX OCTET STRING 
    ACCESS read-write
    STATUS mandatory
    DESCRIPTION
        "Name of the file including path informations."
    ::= { wtWebGraphAnalog57662AlarmEntry 29 }
    
wtWebGraphAnalog57662AlarmFtpText OBJECT-TYPE
    SYNTAX OCTET STRING 
    ACCESS read-write
    STATUS mandatory
    DESCRIPTION
        "Message text to store on the FTP server."
    ::= { wtWebGraphAnalog57662AlarmEntry 30 }

wtWebGraphAnalog57662AlarmFtpClearText OBJECT-TYPE
    SYNTAX OCTET STRING 
    ACCESS read-write
    STATUS mandatory
    DESCRIPTION
        "Alarm clear message to store on the FTP server."
    ::= { wtWebGraphAnalog57662AlarmEntry 31 }
    
wtWebGraphAnalog57662AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphAnalog57662AlarmEntry 32 }      
    
wtWebGraphAnalog57662AlarmTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas (i.e.: 2,14,22)
         - a partition within the allowed range (i.e.: 1-5)
         - step size within a partition of the allowed range (i.e.: 0-59/2  every second minute)."
    ::= { wtWebGraphAnalog57662AlarmEntry 33 }      

-- wtWebGraphAnalog57662GraphicsBase Group
----------------------------

wtWebGraphAnalog57662GraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalog57662GraphicsBase 1 }

wtWebGraphAnalog57662GraphicsBaseWidth OBJECT-TYPE
    SYNTAX INTEGER 
    ACCESS read-write
    STATUS mandatory
    DESCRIPTION
        "Defines the width of the graphic in pixels."
    ::= { wtWebGraphAnalog57662GraphicsBase 2 }
    
wtWebGraphAnalog57662GraphicsBaseHeight OBJECT-TYPE
        SYNTAX INTEGER 
        ACCESS read-write
        STATUS mandatory
        DESCRIPTION
            "Defines the height of the graphic in pixels."
        ::= { wtWebGraphAnalog57662GraphicsBase 3 }

wtWebGraphAnalog57662GraphicsBaseFrameColor OBJECT-TYPE
    SYNTAX OCTET STRING (SIZE(3))
    ACCESS read-write
    STATUS mandatory
    DESCRIPTION
        "Frame color definition in RGB."
    ::= { wtWebGraphAnalog57662GraphicsBase 4 }

wtWebGraphAnalog57662GraphicsBaseBackgroundColor OBJECT-TYPE
    SYNTAX OCTET STRING (SIZE(3))
    ACCESS read-write
    STATUS mandatory
    DESCRIPTION
        "Background color definition in RGB."
    ::= { wtWebGraphAnalog57662GraphicsBase 5 }
    
wtWebGraphAnalog57662GraphicsBasePollingrate OBJECT-TYPE
        SYNTAX INTEGER 
        ACCESS read-write
        STATUS mandatory
        DESCRIPTION
            "Defines the pollingrate in seconds, 
            which defines the refreshing intervall of the graphic."
        ::= { wtWebGraphAnalog57662GraphicsBase 6 }
   
-- wtWebGraphAnalog57662GraphicsSelect Group
----------------------------

wtWebGraphAnalog57662GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalog57662GraphicsSelect 1 }   
    
wtWebGraphAnalog57662GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2-7: unused"
     ::= { wtWebGraphAnalog57662GraphicsSelect 2 }   

-- Graph Sensor Color Table

wtWebGraphAnalog57662SensorColor2Table OBJECT-TYPE
    SYNTAX SEQUENCE OF WtWebGraphAnalog57662SensorColor2Entry
    ACCESS not-accessible
    STATUS mandatory
    DESCRIPTION
        "List of sensor colors for the praphical presentation."
    ::= { wtWebGraphAnalog57662GraphicsSelect 3 }

wtWebGraphAnalog57662SensorColor2Entry OBJECT-TYPE
    SYNTAX WtWebGraphAnalog57662SensorColor2Entry
    ACCESS not-accessible
    STATUS mandatory
    DESCRIPTION
        "Numbers of the sensors."
    INDEX  { wtWebGraphAnalog57662SensorNo }
    ::= { wtWebGraphAnalog57662SensorColor2Table 1 }

WtWebGraphAnalog57662SensorColor2Entry ::= SEQUENCE {
    wtWebGraphAnalog57662GraphicsSensorColor OCTET STRING,
    wtWebGraphAnalog57662GraphicsSelectScale OCTET STRING
}

wtWebGraphAnalog57662GraphicsSensorColor OBJECT-TYPE
    SYNTAX OCTET STRING (SIZE(3))
    ACCESS read-write
    STATUS mandatory
    DESCRIPTION
        "Color of the sensors at the praphical presention."
    ::= { wtWebGraphAnalog57662SensorColor2Entry 1 }
    
wtWebGraphAnalog57662GraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2-7: unused"
    ::= { wtWebGraphAnalog57662SensorColor2Entry 2 }
   
-- wtWebGraphAnalog57662GraphicsScale Group
----------------------------

wtWebGraphAnalog57662GraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2-7: unused"
    ::= { wtWebGraphAnalog57662GraphicsScale 1 }


wtWebGraphAnalog57662GraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2-7: unused"
    ::= { wtWebGraphAnalog57662GraphicsScale 2 }

wtWebGraphAnalog57662GraphicsScale1Min OBJECT-TYPE
    SYNTAX INTEGER
    ACCESS read-only
    STATUS mandatory
    DESCRIPTION
        "Scale 1: Minimum."
    ::= { wtWebGraphAnalog57662GraphicsScale 3 }
   
wtWebGraphAnalog57662GraphicsScale2Min OBJECT-TYPE
    SYNTAX INTEGER
    ACCESS read-only
    STATUS mandatory
    DESCRIPTION
        "Scale 2: Minimum."
    ::= { wtWebGraphAnalog57662GraphicsScale 4 }

wtWebGraphAnalog57662GraphicsScale1Max OBJECT-TYPE
    SYNTAX INTEGER
    ACCESS read-only
    STATUS mandatory
    DESCRIPTION
        "Scale 1: Maximum."
    ::= { wtWebGraphAnalog57662GraphicsScale 7 }

wtWebGraphAnalog57662GraphicsScale2Max OBJECT-TYPE
    SYNTAX INTEGER
    ACCESS read-only
    STATUS mandatory
    DESCRIPTION
        "Scale 2: Maximum."
    ::= { wtWebGraphAnalog57662GraphicsScale 8 }

wtWebGraphAnalog57662GraphicsScale1Unit OBJECT-TYPE
    SYNTAX OCTET STRING
    ACCESS read-only
    STATUS mandatory
    DESCRIPTION
        "Scale 1: Unit."
    ::= { wtWebGraphAnalog57662GraphicsScale 11 }

wtWebGraphAnalog57662GraphicsScale2Unit OBJECT-TYPE
    SYNTAX OCTET STRING
    ACCESS read-only
    STATUS mandatory
    DESCRIPTION
        "Scale 2: Unit."
    ::= { wtWebGraphAnalog57662GraphicsScale 12 }

-- wtWebGraphAnalog57662Report Group
----------------------------

wtWebGraphAnalog57662ReportCount OBJECT-TYPE
    SYNTAX INTEGER (1..8)
    ACCESS read-only
    STATUS mandatory
    DESCRIPTION
        "Number of independent Reports."
    ::= { wtWebGraphAnalog57662Report 1 }
    
-- Report Interface Table

wtWebGraphAnalog57662ReportIfTable OBJECT-TYPE
    SYNTAX SEQUENCE OF WtWebGraphAnalog57662ReportIfEntry
    ACCESS not-accessible
    STATUS mandatory
    DESCRIPTION
        "List of Report indices."
    ::= { wtWebGraphAnalog57662Report 2 }

wtWebGraphAnalog57662ReportIfEntry OBJECT-TYPE
    SYNTAX WtWebGraphAnalog57662ReportIfEntry
    ACCESS not-accessible
    STATUS mandatory
    DESCRIPTION
        "Numbers of the Reports."
    INDEX  { wtWebGraphAnalog57662ReportNo }
    ::= { wtWebGraphAnalog57662ReportIfTable 1 }

WtWebGraphAnalog57662ReportIfEntry ::= SEQUENCE {
    wtWebGraphAnalog57662ReportNo INTEGER
}

wtWebGraphAnalog57662ReportNo OBJECT-TYPE
    SYNTAX INTEGER
    ACCESS read-only
    STATUS mandatory
    DESCRIPTION
        "Report number."
    ::= { wtWebGraphAnalog57662ReportIfEntry 1 }

-- Report Table

wtWebGraphAnalog57662ReportTable OBJECT-TYPE
    SYNTAX SEQUENCE OF WtWebGraphAnalog57662ReportEntry
    ACCESS not-accessible
    STATUS mandatory
    DESCRIPTION
        "List of settings depending on the Report number."
    ::= { wtWebGraphAnalog57662Report 3 }

wtWebGraphAnalog57662ReportEntry OBJECT-TYPE
    SYNTAX WtWebGraphAnalog57662ReportEntry
    ACCESS not-accessible
    STATUS mandatory
    DESCRIPTION
        "Report parameters of the individual Reports."
    INDEX  { wtWebGraphAnalog57662ReportNo }
    ::= { wtWebGraphAnalog57662ReportTable 1 }

WtWebGraphAnalog57662ReportEntry ::= SEQUENCE {
    wtWebGraphAnalog57662ReportEnable			OCTET STRING,
    wtWebGraphAnalog57662ReportTimerCron		OCTET STRING,
    wtWebGraphAnalog57662ReportMethodeEnable		OCTET STRING,
    wtWebGraphAnalog57662ReportEMailAddr			OCTET STRING,
    wtWebGraphAnalog57662ReportMailSubject		OCTET STRING,
    wtWebGraphAnalog57662ReportMailText			OCTET STRING,
    wtWebGraphAnalog57662ReportManagerIP		OCTET STRING,
    wtWebGraphAnalog57662ReportTrapText			OCTET STRING,
    wtWebGraphAnalog57662ReportMailOptions		OCTET STRING,
    wtWebGraphAnalog57662ReportTcpIpAddr		OCTET STRING,
    wtWebGraphAnalog57662ReportTcpPort			INTEGER,
    wtWebGraphAnalog57662ReportTcpText			OCTET STRING,
    wtWebGraphAnalog57662ReportClearMailSubject		OCTET STRING,
    wtWebGraphAnalog57662ReportClearMailText		OCTET STRING,
    wtWebGraphAnalog57662ReportClearTrapText		OCTET STRING,
    wtWebGraphAnalog57662ReportClearTcpText		OCTET STRING,
    wtWebGraphAnalog57662ReportSyslogIpAddr		OCTET STRING,
    wtWebGraphAnalog57662ReportSyslogPort		INTEGER,
    wtWebGraphAnalog57662ReportSyslogText		OCTET STRING,
    wtWebGraphAnalog57662ReportSyslogClearText		OCTET STRING,    
    wtWebGraphAnalog57662ReportFtpDataPort		OCTET STRING,
    wtWebGraphAnalog57662ReportFtpFileName		OCTET STRING,
    wtWebGraphAnalog57662ReportFtpText			OCTET STRING,
    wtWebGraphAnalog57662ReportFtpClearText		OCTET STRING,
    wtWebGraphAnalog57662ReportFtpOption		OCTET STRING    
}

wtWebGraphAnalog57662ReportEnable OBJECT-TYPE
    SYNTAX OCTET STRING (SIZE(4))
    ACCESS read-write
    STATUS mandatory
    DESCRIPTION
        "Binar kodierte Triggerbedingungen:
        Octet 1: unused
        Octet 2: unused
        Octet 3: unused
        Octet 4:
        	Bit 0: Report enable
        	Bit 1-7: unused"
    ::= { wtWebGraphAnalog57662ReportEntry 1 }
    
wtWebGraphAnalog57662ReportTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas (i.e.: 2,14,22)
         - a partition within the allowed range (i.e.: 1-5)
         - step size within a partition of the allowed range (i.e.: 0-59/2  every second minute)."
    ::= { wtWebGraphAnalog57662ReportEntry 2 } 
    
wtWebGraphAnalog57662ReportMethodeEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable
        	Bit 3:	Syslog enable
        	Bit 4:  FTP Client enable"        	
    ::= { wtWebGraphAnalog57662ReportEntry 3 }
    
wtWebGraphAnalog57662ReportEMailAddr OBJECT-TYPE
    SYNTAX OCTET STRING 
    ACCESS read-write
    STATUS mandatory
    DESCRIPTION
        "E-Mail address for sending the alarm mail to."
    ::= { wtWebGraphAnalog57662ReportEntry 8 }

wtWebGraphAnalog57662ReportMailSubject OBJECT-TYPE
    SYNTAX OCTET STRING 
    ACCESS read-write
    STATUS mandatory
    DESCRIPTION
        "Subject line for alarm mail."
    ::= { wtWebGraphAnalog57662ReportEntry 9 }

wtWebGraphAnalog57662ReportMailText OBJECT-TYPE
    SYNTAX OCTET STRING 
    ACCESS read-write
    STATUS mandatory
    DESCRIPTION
        "Report mail text: <Mn> provides the current temperature; n = 1..2.
        <Z> provides the current time."
    ::= { wtWebGraphAnalog57662ReportEntry 10 }

wtWebGraphAnalog57662ReportManagerIP OBJECT-TYPE
    SYNTAX OCTET STRING 
    ACCESS read-write
    STATUS mandatory
    DESCRIPTION
        "Name or IP address of the SNMP Manager which accepts the trap."
    ::= { wtWebGraphAnalog57662ReportEntry 11 }

wtWebGraphAnalog57662ReportTrapText OBJECT-TYPE
    SYNTAX OCTET STRING 
    ACCESS read-write
    STATUS mandatory
    DESCRIPTION
        "This text is sent in the trap body."
    ::= { wtWebGraphAnalog57662ReportEntry 12 }
    
wtWebGraphAnalog57662ReportMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalog57662ReportEntry 13 }    
    
wtWebGraphAnalog57662ReportTcpIpAddr OBJECT-TYPE
    SYNTAX OCTET STRING 
    ACCESS read-write
    STATUS mandatory
    DESCRIPTION
        "Name or IP address of the TCP server which accepts the trap."
    ::= { wtWebGraphAnalog57662ReportEntry 14 }    

wtWebGraphAnalog57662ReportTcpPort OBJECT-TYPE
    SYNTAX INTEGER (1..65535) 
    ACCESS read-write
    STATUS mandatory
    DESCRIPTION
        "Port number of the TCP server which accepts the trap."
    ::= { wtWebGraphAnalog57662ReportEntry 15 }    

wtWebGraphAnalog57662ReportTcpText OBJECT-TYPE
    SYNTAX OCTET STRING 
    ACCESS read-write
    STATUS mandatory
    DESCRIPTION
        "This text is sent in the TCP trap body."
    ::= { wtWebGraphAnalog57662ReportEntry 16 }

wtWebGraphAnalog57662ReportClearMailSubject OBJECT-TYPE
    SYNTAX OCTET STRING 
    ACCESS read-write
    STATUS mandatory
    DESCRIPTION
        "Subject line for alarm clear mail."
    ::= { wtWebGraphAnalog57662ReportEntry 17 }

wtWebGraphAnalog57662ReportClearMailText OBJECT-TYPE
    SYNTAX OCTET STRING 
    ACCESS read-write
    STATUS mandatory
    DESCRIPTION
        "Report clear mail text: <Mn> provides the current temperature; n = 1..2.
        <Z> provides the current time."
    ::= { wtWebGraphAnalog57662ReportEntry 18 }

wtWebGraphAnalog57662ReportClearTrapText OBJECT-TYPE
    SYNTAX OCTET STRING 
    ACCESS read-write
    STATUS mandatory
    DESCRIPTION
        "This text is sent in the trap body."
    ::= { wtWebGraphAnalog57662ReportEntry 19 }

wtWebGraphAnalog57662ReportClearTcpText OBJECT-TYPE
    SYNTAX OCTET STRING 
    ACCESS read-write
    STATUS mandatory
    DESCRIPTION
        "This text is sent in the TCP trap body."
    ::= { wtWebGraphAnalog57662ReportEntry 20 }
    
wtWebGraphAnalog57662ReportSyslogIpAddr OBJECT-TYPE
    SYNTAX OCTET STRING 
    ACCESS read-write
    STATUS mandatory
    DESCRIPTION
        "IP address of the syslog server to which the Webio device should send syslog messages."
    ::= { wtWebGraphAnalog57662ReportEntry 24 }    

wtWebGraphAnalog57662ReportSyslogPort OBJECT-TYPE
    SYNTAX INTEGER (1..65535) 
    ACCESS read-write
    STATUS mandatory
    DESCRIPTION
        "Port number of the syslog server to which the Webio device should send syslog messages."
    ::= { wtWebGraphAnalog57662ReportEntry 25 }    

wtWebGraphAnalog57662ReportSyslogText OBJECT-TYPE
    SYNTAX OCTET STRING 
    ACCESS read-write
    STATUS mandatory
    DESCRIPTION
        "Every message starts with the priority key, a time stamp and the host ip address, according RFC3164.
        This text appears in the following syslog message body."
    ::= { wtWebGraphAnalog57662ReportEntry 26 }
    
wtWebGraphAnalog57662ReportSyslogClearText OBJECT-TYPE
    SYNTAX OCTET STRING 
    ACCESS read-write
    STATUS mandatory
    DESCRIPTION
        "Every message starts with the priority key, a time stamp and the host ip address, according RFC3164.
        This text appears in the following syslog message body of a alarm clear message."
    ::= { wtWebGraphAnalog57662ReportEntry 27 }
    
wtWebGraphAnalog57662ReportFtpDataPort OBJECT-TYPE
    SYNTAX OCTET STRING 
    ACCESS read-write
    STATUS mandatory
    DESCRIPTION
        "Local data port: 1..65535 or AUTO: the next free port will be assigned."
    ::= { wtWebGraphAnalog57662ReportEntry 28 }
    
wtWebGraphAnalog57662ReportFtpFileName OBJECT-TYPE
    SYNTAX OCTET STRING 
    ACCESS read-write
    STATUS mandatory
    DESCRIPTION
        "Name of the file including path informations."
    ::= { wtWebGraphAnalog57662ReportEntry 29 }
    
wtWebGraphAnalog57662ReportFtpText OBJECT-TYPE
    SYNTAX OCTET STRING 
    ACCESS read-write
    STATUS mandatory
    DESCRIPTION
        "Message text to store on the FTP server."
    ::= { wtWebGraphAnalog57662ReportEntry 30 }

wtWebGraphAnalog57662ReportFtpClearText OBJECT-TYPE
    SYNTAX OCTET STRING 
    ACCESS read-write
    STATUS mandatory
    DESCRIPTION
        "Report clear message to store on the FTP server."
    ::= { wtWebGraphAnalog57662ReportEntry 31 }
    
wtWebGraphAnalog57662ReportFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphAnalog57662ReportEntry 32 }      

    
-- wtWebGraphAnalog57662Ports Group
----------------------------

-- Table

wtWebGraphAnalog57662PortTable OBJECT-TYPE
    SYNTAX SEQUENCE OF WtWebGraphAnalog57662PortEntry
    ACCESS not-accessible
    STATUS mandatory
    DESCRIPTION
        "List of settings depending on the sensor number."
    ::= { wtWebGraphAnalog57662Ports 1 }

wtWebGraphAnalog57662PortEntry OBJECT-TYPE
    SYNTAX WtWebGraphAnalog57662PortEntry
    ACCESS not-accessible
    STATUS mandatory
    DESCRIPTION
        "Sensor parameters for the individual sensors."
    INDEX  { wtWebGraphAnalog57662SensorNo }
    ::= { wtWebGraphAnalog57662PortTable 1 }

WtWebGraphAnalog57662PortEntry ::= SEQUENCE {
    wtWebGraphAnalog57662PortName		OCTET STRING,
    wtWebGraphAnalog57662PortText		OCTET STRING,
    wtWebGraphAnalog57662PortOffset1		OCTET STRING,
    wtWebGraphAnalog57662SetPoint1		OCTET STRING,
    wtWebGraphAnalog57662PortOffset2		OCTET STRING,
    wtWebGraphAnalog57662SetPoint2		OCTET STRING,
    wtWebGraphAnalog57662PortComment		OCTET STRING,
    wtWebGraphAnalog57662PortSensorSelect	OCTET STRING,
    wtWebGraphAnalog57662PortUnit		OCTET STRING,
    wtWebGraphAnalog57662PortScale0		OCTET STRING,
    wtWebGraphAnalog57662PortScale100		OCTET STRING,
    wtWebGraphAnalog57662PortOutputMode		OCTET STRING,
    wtWebGraphAnalog57662PortInputMode		OCTET STRING,
    wtWebGraphAnalog57662PortCompensationValue	OCTET STRING,
    wtWebGraphAnalog57662PortCompensationMode	OCTET STRING    
}

wtWebGraphAnalog57662PortName OBJECT-TYPE
    SYNTAX OCTET STRING 
    ACCESS read-write
    STATUS mandatory
    DESCRIPTION
        "Name of the sensor."
    ::= { wtWebGraphAnalog57662PortEntry 1 }

wtWebGraphAnalog57662PortText OBJECT-TYPE
    SYNTAX OCTET STRING 
    ACCESS read-write
    STATUS mandatory
    DESCRIPTION
        "Description of the sensor."
    ::= { wtWebGraphAnalog57662PortEntry 2 }

wtWebGraphAnalog57662PortOffset1 OBJECT-TYPE
    SYNTAX OCTET STRING 
    ACCESS read-write
    STATUS mandatory
    DESCRIPTION
        "Offset calibration: Offset in degrees with maximum 3 decimal places at set point 1."
    ::= { wtWebGraphAnalog57662PortEntry 3 }

wtWebGraphAnalog57662SetPoint1 OBJECT-TYPE
    SYNTAX OCTET STRING 
    ACCESS read-write
    STATUS mandatory
    DESCRIPTION
        "Offset calibration: Reference set point 1 in degrees with maximum 3 decimal places."
    ::= { wtWebGraphAnalog57662PortEntry 4 }

wtWebGraphAnalog57662PortOffset2 OBJECT-TYPE
    SYNTAX OCTET STRING 
    ACCESS read-write
    STATUS mandatory
    DESCRIPTION
        "Offset calibration: Offset in degrees with maximum 3 decimal places at set point 2."
    ::= { wtWebGraphAnalog57662PortEntry 5 }

wtWebGraphAnalog57662SetPoint2 OBJECT-TYPE
    SYNTAX OCTET STRING 
    ACCESS read-write
    STATUS mandatory
    DESCRIPTION
        "Offset calibration: Reference set point 2 in degrees with maximum 3 decimal places."
    ::= { wtWebGraphAnalog57662PortEntry 6 }

wtWebGraphAnalog57662PortComment OBJECT-TYPE
    SYNTAX OCTET STRING 
    ACCESS read-write
    STATUS mandatory
    DESCRIPTION
        "Offset calibration: informations of date, name of operator, reference devices."
    ::= { wtWebGraphAnalog57662PortEntry 7 }   

wtWebGraphAnalog57662PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-20mA (default)
		Bit 1  :	4-20mA
		Bit 2  :	Disconnect
        	Bit 3-7:	unused"
    ::= { wtWebGraphAnalog57662PortEntry 8 }    
    
wtWebGraphAnalog57662PortUnit OBJECT-TYPE
    SYNTAX OCTET STRING 
    ACCESS read-write
    STATUS mandatory
    DESCRIPTION
        "User scale: displayed unit."
    ::= { wtWebGraphAnalog57662PortEntry 9 }   
    
wtWebGraphAnalog57662PortScale0 OBJECT-TYPE
    SYNTAX OCTET STRING 
    ACCESS read-write
    STATUS mandatory
    DESCRIPTION
        "User scale: displayed value in 1/1000 at 0% full scale range.
        Range: -999999.999 to 999999.999"
    ::= { wtWebGraphAnalog57662PortEntry 10 }   

wtWebGraphAnalog57662PortScale100 OBJECT-TYPE
    SYNTAX OCTET STRING 
    ACCESS read-write
    STATUS mandatory
    DESCRIPTION
        "User scale: displayed value in 1/1000 at 100% full scale range.
        Range: -999999.999 to 999999.999"
    ::= { wtWebGraphAnalog57662PortEntry 11 } 
    
wtWebGraphAnalog57662PortOutputMode OBJECT-TYPE
    SYNTAX OCTET STRING (SIZE (4))
    ACCESS read-write
    STATUS mandatory
    DESCRIPTION
        "This binary coded output mode defines the individual operation mode for any
        output. More than one mode must not be selected. If an output mode is selected,
        Bit 2 in wtWebGraphAnalog57662PortInputMode will be set automatically.
        The OCTETS are interpreted bit-by-bit, Bit 0 corresponds to the LSB.
        OCTET 1: unused
        OCTET 2: unused
        OCTET 3: unused
        OCTET 4: Bit 6-7: unused
        	 Bit 5  : Output OFF
        	 Bit 4  : Binary 2
        	 Bit 3  : Binary 1
        	 Bit 2  : SNMP
        	 Bit 1  : UDP ASCII
        	 Bit 0  : HTTP"
    ::= { wtWebGraphAnalog57662PortEntry 12 }
    
wtWebGraphAnalog57662PortInputMode OBJECT-TYPE
    SYNTAX OCTET STRING (SIZE (4))
    ACCESS read-write
    STATUS mandatory
    DESCRIPTION
        "This binary coded input mode defines the individual operation mode for any
        input. More than one mode must not be selected. If an input mode is selected,
        Bit 5 in wtWebGraphAnalog57662PortOutputMode will be set automatically.
        The OCTETS are interpreted bit-by-bit,Bit 0 corresponds to the LSB.
        OCTET 1: ungenutzt
        OCTET 2: ungenutzt
        OCTET 3: ungenutzt
        OCTET 4: Bit 3-7: unused
        	 Bit 2  : I-Output
        	 Bit 1  : I-Input, active
        	 Bit 0  : I-Input, passive"
    ::= { wtWebGraphAnalog57662PortEntry 13 }     

wtWebGraphAnalog57662PortCompensationValue OBJECT-TYPE
    SYNTAX OCTET STRING 
    ACCESS read-write
    STATUS mandatory
    DESCRIPTION
        "This entry is used to optimize the step response with capcitive loads."
    ::= { wtWebGraphAnalog57662PortEntry 14 }
    
wtWebGraphAnalog57662PortCompensationMode OBJECT-TYPE
    SYNTAX OCTET STRING (SIZE (4))
    ACCESS read-write
    STATUS mandatory
    DESCRIPTION
        "This binary coded compensation mode defines the individual operation mode for any
        output. If Auto adaptive is selected, the optimal value of wtWebGraphAnalog57662PortCompensationValue
        will be determinate continuously. Set Bit 1 to start with the last saved value of
        wtWebGraphAnalog57662PortCompensationValue in this Mode.
        If Bit 0 is cleared and Auto Mode is off wtWebGraphAnalog57662PortCompensationValue
        will allways be used, regardless of the state of Bit 1.
        The OCTETS are interpreted bit-by-bit,Bit 0 corresponds to the LSB.
        OCTET 1: ungenutzt
        OCTET 2: ungenutzt
        OCTET 3: ungenutzt
        OCTET 4: Bit 2-7: unused
        	 Bit 1  : Use saved value at power on
        	 Bit 0  : Auto adaptive enable"   	 
    ::= { wtWebGraphAnalog57662PortEntry 15 }
    

-- wtWebGraphAnalog57662Manufact Group
----------------------------

wtWebGraphAnalog57662MfName OBJECT-TYPE
    SYNTAX OCTET STRING 
    ACCESS read-write
    STATUS mandatory
    DESCRIPTION
        "Manufacturer company name"
    ::= { wtWebGraphAnalog57662Manufact 1 }

wtWebGraphAnalog57662MfAddr OBJECT-TYPE
    SYNTAX OCTET STRING 
    ACCESS read-write
    STATUS mandatory
    DESCRIPTION
        "Manufacturer address."
    ::= { wtWebGraphAnalog57662Manufact 2 }

wtWebGraphAnalog57662MfHotline OBJECT-TYPE
    SYNTAX OCTET STRING 
    ACCESS read-write
    STATUS mandatory
    DESCRIPTION
        "Manufacturer hotline."
    ::= { wtWebGraphAnalog57662Manufact 3 }

wtWebGraphAnalog57662MfInternet OBJECT-TYPE
    SYNTAX OCTET STRING 
    ACCESS read-write
    STATUS mandatory
    DESCRIPTION
        "Manufacturer Internet address."
    ::= { wtWebGraphAnalog57662Manufact 4 }

wtWebGraphAnalog57662MfDeviceTyp OBJECT-TYPE
    SYNTAX OCTET STRING 
    ACCESS read-write
    STATUS mandatory
    DESCRIPTION
        "Manufacturer device name (model number)."
    ::= { wtWebGraphAnalog57662Manufact 5 }

wtWebGraphAnalog57662MfOrderNo OBJECT-TYPE
    SYNTAX OCTET STRING 
    ACCESS read-write
    STATUS mandatory
    DESCRIPTION
        "Manufacturer part number."
    ::= { wtWebGraphAnalog57662Manufact 6 }

-- wtWebGraphAnalog57662Diag Group
----------------------------

wtWebGraphAnalog57662DiagErrorCount OBJECT-TYPE
    SYNTAX INTEGER
    ACCESS read-only
    STATUS mandatory
    DESCRIPTION
        "Number of entries in the error memory."
    ::= { wtWebGraphAnalog57662Diag 1 }

wtWebGraphAnalog57662DiagBinaryError OBJECT-TYPE
    SYNTAX OCTET STRING 
    ACCESS read-only
    STATUS mandatory
    DESCRIPTION
        "Error causes coded bit-by-bit."
    ::= { wtWebGraphAnalog57662Diag 2 }

wtWebGraphAnalog57662DiagErrorIndex OBJECT-TYPE
    SYNTAX INTEGER
    ACCESS read-write
    STATUS mandatory
    DESCRIPTION
        "The value of this variable is used as an index to read 
        an error massege from wtWebGraphAnalog57662DiagErrorMessage.
        Errors are numbered from 1 to wtWebGraphAnalog57662DiagErrorCount.
        Writing a valid value into this variable, making the appropriate 
        message readable from wtWebGraphAnalog57662DiagErrorMessage."
    ::= { wtWebGraphAnalog57662Diag 3 }

wtWebGraphAnalog57662DiagErrorMessage OBJECT-TYPE
    SYNTAX OCTET STRING 
    ACCESS read-only
    STATUS mandatory
    DESCRIPTION
        "Using wtWebGraphAnalog57662DiagErrorIndex as an index, the appropriate message is available."
    ::= { wtWebGraphAnalog57662Diag 4 }
    
wtWebGraphAnalog57662DiagErrorClear OBJECT-TYPE
    SYNTAX INTEGER
    ACCESS write-only
    STATUS mandatory
    DESCRIPTION
        "Writing 1 into this variable clears all diagnosis messages."
    ::= { wtWebGraphAnalog57662Diag 5 }

-- TRAP DEFINITIONS

-- Diese SNMP-Traps werden gesendet, wenn die Alarmtriggerbedingungen zutreffen 

wtWebGraphAnalog57662Alert1 TRAP-TYPE
    ENTERPRISE  wtWebGraphAnalog57662
    VARIABLES   { wtWebGraphAnalog57662AlarmTrapText }
    DESCRIPTION
        "This SNMP trap is generated when Alarm 1 was triggered,
        SNMP trap enable is set and
        SNMP is enabled."
    -- NMS trap annotation
    --#TYPE "Web-IO Analog-InOut Alarm 1"
    --#SUMMARY "Alarm 1: %s"
    --#ARGUMENTS {0}
    --#SEVERITY INFORMATIONAL
    --#TIMEINDEX 99
    --#STATE OPERATIONAL    
    ::= 31

wtWebGraphAnalog57662Alert2 TRAP-TYPE
    ENTERPRISE  wtWebGraphAnalog57662
    VARIABLES   { wtWebGraphAnalog57662AlarmTrapText }
    DESCRIPTION
        "This SNMP trap is generated when Alarm 2 was triggered,
        SNMP trap enable is set and
        SNMP is enabled."
    -- NMS trap annotation
    --#TYPE "Web-IO Analog-InOut Alarm 2"
    --#SUMMARY "Alarm 2: %s"
    --#ARGUMENTS {0}
    --#SEVERITY INFORMATIONAL
    --#TIMEINDEX 99
    --#STATE OPERATIONAL    
    ::= 32

wtWebGraphAnalog57662Alert3 TRAP-TYPE
    ENTERPRISE  wtWebGraphAnalog57662
    VARIABLES   { wtWebGraphAnalog57662AlarmTrapText }
    DESCRIPTION
        "This SNMP trap is generated when Alarm 3 was triggered,
        SNMP trap enable is set and
        SNMP is enabled."
    -- NMS trap annotation
    --#TYPE "Web-IO Analog-InOut Alarm 3"
    --#SUMMARY "Alarm 3: %s"
    --#ARGUMENTS {0}
    --#SEVERITY INFORMATIONAL
    --#TIMEINDEX 99
    --#STATE OPERATIONAL    
    ::= 33

wtWebGraphAnalog57662Alert4 TRAP-TYPE
    ENTERPRISE  wtWebGraphAnalog57662
    VARIABLES   { wtWebGraphAnalog57662AlarmTrapText }
    DESCRIPTION
        "This SNMP trap is generated when Alarm 4 was triggered,
        SNMP trap enable is set and
        SNMP is enabled."
    -- NMS trap annotation
    --#TYPE "Web-IO Analog-InOut Alarm 4"
    --#SUMMARY "Alarm 4: %s"
    --#ARGUMENTS {0}
    --#SEVERITY INFORMATIONAL
    --#TIMEINDEX 99
    --#STATE OPERATIONAL    
    ::= 34

wtWebGraphAnalog57662Alert5 TRAP-TYPE
    ENTERPRISE  wtWebGraphAnalog57662
    VARIABLES   { wtWebGraphAnalog57662AlarmTrapText }
    DESCRIPTION
        "This SNMP trap is generated when Alarm 5 was triggered,
        SNMP trap enable is set and
        SNMP is enabled."
    -- NMS trap annotation
    --#TYPE "Web-IO Analog-InOut Alarm 5"
    --#SUMMARY "Alarm 5: %s"
    --#ARGUMENTS {0}
    --#SEVERITY INFORMATIONAL
    --#TIMEINDEX 99
    --#STATE OPERATIONAL    
    ::= 35

wtWebGraphAnalog57662Alert6 TRAP-TYPE
    ENTERPRISE  wtWebGraphAnalog57662
    VARIABLES   { wtWebGraphAnalog57662AlarmTrapText }
    DESCRIPTION
        "This SNMP trap is generated when Alarm 6 was triggered,
        SNMP trap enable is set and
        SNMP is enabled."
    -- NMS trap annotation
    --#TYPE "Web-IO Analog-InOut Alarm 6"
    --#SUMMARY "Alarm 6: %s"
    --#ARGUMENTS {0}
    --#SEVERITY INFORMATIONAL
    --#TIMEINDEX 99
    --#STATE OPERATIONAL    
    ::= 36

wtWebGraphAnalog57662Alert7 TRAP-TYPE
    ENTERPRISE  wtWebGraphAnalog57662
    VARIABLES   { wtWebGraphAnalog57662AlarmTrapText }
    DESCRIPTION
        "This SNMP trap is generated when Alarm 7 was triggered,
        SNMP trap enable is set and
        SNMP is enabled."
    -- NMS trap annotation
    --#TYPE "Web-IO Analog-InOut Alarm 7"
    --#SUMMARY "Alarm 7: %s"
    --#ARGUMENTS {0}
    --#SEVERITY INFORMATIONAL
    --#TIMEINDEX 99
    --#STATE OPERATIONAL    
    ::= 37

wtWebGraphAnalog57662Alert8 TRAP-TYPE
    ENTERPRISE  wtWebGraphAnalog57662
    VARIABLES   { wtWebGraphAnalog57662AlarmTrapText }
    DESCRIPTION
        "This SNMP trap is generated when Alarm 8 was triggered,
        SNMP trap enable is set and
        SNMP is enabled."
    -- NMS trap annotation
    --#TYPE "Web-IO Analog-InOut Alarm 8"
    --#SUMMARY "Alarm 8: %s"
    --#ARGUMENTS {0}
    --#SEVERITY INFORMATIONAL
    --#TIMEINDEX 99
    --#STATE OPERATIONAL    
    ::= 38

wtWebGraphAnalog57662Alert9 TRAP-TYPE
    ENTERPRISE  wtWebGraphAnalog57662
    VARIABLES   { wtWebGraphAnalog57662AlarmClearTrapText }
    DESCRIPTION
        "This SNMP trap is generated when Alarm 1 was cleared,
        SNMP trap enable is set and
        SNMP is enabled."
    -- NMS trap annotation
    --#TYPE "Web-IO Analog-InOut Release Alarm 1"
    --#SUMMARY "Release Alarm 1: %s"
    --#ARGUMENTS {0}
    --#SEVERITY INFORMATIONAL
    --#TIMEINDEX 99
    --#STATE OPERATIONAL    
    ::= 91

wtWebGraphAnalog57662Alert10 TRAP-TYPE
    ENTERPRISE  wtWebGraphAnalog57662
    VARIABLES   { wtWebGraphAnalog57662AlarmClearTrapText }
    DESCRIPTION
        "This SNMP trap is generated when Alarm 2 was cleared,
        SNMP trap enable is set and
        SNMP is enabled."
    -- NMS trap annotation
    --#TYPE "Web-IO Analog-InOut Release Alarm 2"
    --#SUMMARY "Release Alarm 2: %s"
    --#ARGUMENTS {0}
    --#SEVERITY INFORMATIONAL
    --#TIMEINDEX 99
    --#STATE OPERATIONAL    
    ::= 92

wtWebGraphAnalog57662Alert11 TRAP-TYPE
    ENTERPRISE  wtWebGraphAnalog57662
    VARIABLES   { wtWebGraphAnalog57662AlarmClearTrapText }
    DESCRIPTION
        "This SNMP trap is generated when Alarm 3 was cleared,
        SNMP trap enable is set and
        SNMP is enabled."
    -- NMS trap annotation
    --#TYPE "Web-IO Analog-InOut Release Alarm 3"
    --#SUMMARY "Release Alarm 3: %s"
    --#ARGUMENTS {0}
    --#SEVERITY INFORMATIONAL
    --#TIMEINDEX 99
    --#STATE OPERATIONAL    
    ::= 93

wtWebGraphAnalog57662Alert12 TRAP-TYPE
    ENTERPRISE  wtWebGraphAnalog57662
    VARIABLES   { wtWebGraphAnalog57662AlarmClearTrapText }
    DESCRIPTION
        "This SNMP trap is generated when Alarm 4 was cleared,
        SNMP trap enable is set and
        SNMP is enabled."
    -- NMS trap annotation
    --#TYPE "Web-IO Analog-InOut Release Alarm 4"
    --#SUMMARY "Release Alarm 4: %s"
    --#ARGUMENTS {0}
    --#SEVERITY INFORMATIONAL
    --#TIMEINDEX 99
    --#STATE OPERATIONAL    
    ::= 94

wtWebGraphAnalog57662Alert13 TRAP-TYPE
    ENTERPRISE  wtWebGraphAnalog57662
    VARIABLES   { wtWebGraphAnalog57662AlarmClearTrapText }
    DESCRIPTION
        "This SNMP trap is generated when Alarm 5 was cleared,
        SNMP trap enable is set and
        SNMP is enabled."
    -- NMS trap annotation
    --#TYPE "Web-IO Analog-InOut Release Alarm 5"
    --#SUMMARY "Release Alarm 5: %s"
    --#ARGUMENTS {0}
    --#SEVERITY INFORMATIONAL
    --#TIMEINDEX 99
    --#STATE OPERATIONAL    
    ::= 95

wtWebGraphAnalog57662Alert14 TRAP-TYPE
    ENTERPRISE  wtWebGraphAnalog57662
    VARIABLES   { wtWebGraphAnalog57662AlarmClearTrapText }
    DESCRIPTION
        "This SNMP trap is generated when Alarm 6 was cleared,
        SNMP trap enable is set and
        SNMP is enabled."
    -- NMS trap annotation
    --#TYPE "Web-IO Analog-InOut Release Alarm 6"
    --#SUMMARY "Release Alarm 6: %s"
    --#ARGUMENTS {0}
    --#SEVERITY INFORMATIONAL
    --#TIMEINDEX 99
    --#STATE OPERATIONAL    
    ::= 96

wtWebGraphAnalog57662Alert15 TRAP-TYPE
    ENTERPRISE  wtWebGraphAnalog57662
    VARIABLES   { wtWebGraphAnalog57662AlarmClearTrapText }
    DESCRIPTION
        "This SNMP trap is generated when Alarm 7 was cleared,
        SNMP trap enable is set and
        SNMP is enabled."
    -- NMS trap annotation
    --#TYPE "Web-IO Analog-InOut Release Alarm 7"
    --#SUMMARY "Release Alarm 7: %s"
    --#ARGUMENTS {0}
    --#SEVERITY INFORMATIONAL
    --#TIMEINDEX 99
    --#STATE OPERATIONAL    
    ::= 97

wtWebGraphAnalog57662Alert16 TRAP-TYPE
    ENTERPRISE  wtWebGraphAnalog57662
    VARIABLES   { wtWebGraphAnalog57662AlarmClearTrapText }
    DESCRIPTION
        "This SNMP trap is generated when Alarm 8 was cleared,
        SNMP trap enable is set and
        SNMP is enabled."
    -- NMS trap annotation
    --#TYPE "Web-IO Analog-InOut Release Alarm 8"
    --#SUMMARY "Release Alarm 8: %s"
    --#ARGUMENTS {0}
    --#SEVERITY INFORMATIONAL
    --#TIMEINDEX 99
    --#STATE OPERATIONAL    
    ::= 98

wtWebGraphAnalog57662AlertReport TRAP-TYPE
    ENTERPRISE  wtWebGraphAnalog57662
    VARIABLES   { wtWebGraphAnalog57662AlarmTrapText }
    DESCRIPTION
        "This SNMP trap is generated when the report was triggered,
        SNMP trap enable is set and
        SNMP is enabled."
    -- NMS trap annotation
    --#TYPE "Web-IO Analog-InOut Report"
    --#SUMMARY "Report: %s"
    --#ARGUMENTS {0}
    --#SEVERITY INFORMATIONAL
    --#TIMEINDEX 99
    --#STATE OPERATIONAL    
    ::= 39
    
wtWebGraphAnalog57662AlertDiag TRAP-TYPE
    ENTERPRISE  wtWebGraphAnalog57662
    VARIABLES   { 	
    		wtWebGraphAnalog57662DiagErrorIndex,
    	  	wtWebGraphAnalog57662DiagErrorMessage
    		}
    DESCRIPTION
        "This SNMP trap is generated when a diagnosis/error message was triggered,
        SNMP trap enable is set and
        SNMP is enabled."
    -- NMS trap annotation
    --#TYPE "Web-IO Analog-InOut Diagnose Error"
    --#SUMMARY "Diagnose error index: %d, Message: %s."
    --#ARGUMENTS {0,1}
    --#SEVERITY MAJOR
    --#TIMEINDEX 99
    --#STATE DEGRADED    
    ::= 110 
 
END
