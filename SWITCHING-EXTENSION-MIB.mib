SWITCHING-EXTENSION-MIB DEFINITIONS ::= BEGIN



IMPORTS
    MODULE-IDENTITY, OBJECT-TYPE, NOTIFICATION-TYPE, IpAddress,
    Integer32, Unsigned32, TimeTicks
                                        FROM SNMPv2-SMI
	TEXTUAL-CONVENTION,
    RowStatus,MacAddress,TimeStamp      FROM SNMPv2-TC
    quanta, switch, AgentPortMask       FROM QUANTA-SWITCH-MIB
    VlanList                            FROM SWITCHING-MIB
    DisplayString,PhysAddress           FROM RFC1213-MIB
    VlanIndex,dot1qVlanIndex,dot1qFdbId FROM Q-BRIDGE-MIB
    IANAifType                          FROM IANAifType-MIB
    ifIndex,InterfaceIndex,InterfaceIndexOrZero
                                        FROM IF-MIB
    InetAddressType, InetAddress        FROM INET-ADDRESS-MIB
    SnmpAdminString                     FROM SNMP-FRAMEWORK-MIB;

    switchingExtension MODULE-IDENTITY
        LAST-UPDATED "200803310000Z" -- 31 MAR 2008 12:00:00 GMT
        ORGANIZATION "Quanta Computer Inc."
        CONTACT-INFO
          "                      Customer Support
          Postal:                Quanta Computer Inc.
                                 No. 4, Wen Ming 1 St., Kuei Shan Hsiang,
                                 Tao Yuan Shien, Taiwan, R.O.C.
          Tel:                   +886 327 2345
          E-Mail:                Morpheus.Chang@quantatw.com"
        DESCRIPTION
          "QCI switching extension MIB"


    ::= { switch 101 }


--**************************************************************************************
--    agentInfoGroup
--**************************************************************************************

agentInfoGroupExtension                             OBJECT IDENTIFIER ::= { switchingExtension 1 }


    --**************************************************************************************
    -- agentInventoryGroupExtension
    --
    --**************************************************************************************


    agentInventoryGroupExtension        OBJECT IDENTIFIER ::= { agentInfoGroupExtension 1 }


    agentInventroyHardwareVersion OBJECT-TYPE
         SYNTAX      DisplayString
         MAX-ACCESS  read-only
         STATUS      current
         DESCRIPTION
                     "The switch's hardware version.  "
         ::= { agentInventoryGroupExtension 100 }

    agentInventoryLoaderVersion OBJECT-TYPE
         SYNTAX      DisplayString
         MAX-ACCESS  read-only
         STATUS      current
         DESCRIPTION
                     "The Switch's loader version "
         ::= { agentInventoryGroupExtension 102 }

    agentInventoryBootRomVersion OBJECT-TYPE
         SYNTAX      DisplayString
         MAX-ACCESS  read-only
         STATUS      current
         DESCRIPTION
                     "The switch's Boot Rom Version. "
         ::= { agentInventoryGroupExtension 103 }

    agentInventoryOpCodeVersion OBJECT-TYPE
         SYNTAX      DisplayString
         MAX-ACCESS  read-only
         STATUS      current
         DESCRIPTION
                     "The switch's Operation Code version."
         ::= { agentInventoryGroupExtension 104 }

   agentInventoryLabelRevNumber OBJECT-TYPE
         SYNTAX      DisplayString
         MAX-ACCESS  read-only
         STATUS      current
         DESCRIPTION
                     "The switch's Label Revision Number."
         ::= { agentInventoryGroupExtension 105 }


   --**************************************************************************************
    -- Temperature and FAN1, FAN2 status information Table
    --
    --**************************************************************************************
    agentTemperatureFanStatusTable OBJECT-TYPE
         SYNTAX      SEQUENCE OF AgentTemperatureFanStatusEntry
         MAX-ACCESS  not-accessible
         STATUS      current
         DESCRIPTION
                     "The switch's temperature and FANs information table"
         ::= { agentInventoryGroupExtension 106 }

    agentTemperatureFanStatusEntry OBJECT-TYPE
         SYNTAX      AgentTemperatureFanStatusEntry
         MAX-ACCESS  not-accessible
         STATUS      current
         DESCRIPTION
                     "entry of temperature and FANs information table"
         INDEX       { agentTemperatureFanUnitIndex }
         ::= { agentTemperatureFanStatusTable 1 }

    AgentTemperatureFanStatusEntry ::=
         SEQUENCE {
             agentTemperatureFanUnitIndex   Integer32,
             agentTemperature               DisplayString,
             agentTemperature1              DisplayString,
             agentTemperature2              DisplayString,
             agentTemperature3              DisplayString,
             agentTemperature4              DisplayString,
             agentTemperature5              DisplayString,
             agentFAN1                      INTEGER,
             agentFAN2                      INTEGER,
             agentFAN3	                    INTEGER,
             agentFAN4	                    INTEGER,
			 agentFANChipType               DisplayString
         }


    agentTemperatureFanUnitIndex OBJECT-TYPE
         SYNTAX      Integer32 (0..2147483647)
         MAX-ACCESS  read-only
         STATUS      current
         DESCRIPTION
                     "Unique index of temperature and FANs Information entry"
         ::= { agentTemperatureFanStatusEntry 1 }


     agentTemperature OBJECT-TYPE
         SYNTAX      DisplayString
         MAX-ACCESS  read-only
         STATUS      current
         DESCRIPTION
                     "temperature of the unit"
         ::= { agentTemperatureFanStatusEntry 2 }

     agentTemperature1 OBJECT-TYPE
         SYNTAX      DisplayString
         MAX-ACCESS  read-only
         STATUS      current
         DESCRIPTION
                     "temperature 1 of the unit"
         ::= { agentTemperatureFanStatusEntry 11 }

     agentTemperature2 OBJECT-TYPE
         SYNTAX      DisplayString
         MAX-ACCESS  read-only
         STATUS      current
         DESCRIPTION
                     "temperature 2 of the unit"
         ::= { agentTemperatureFanStatusEntry 12 }

     agentTemperature3 OBJECT-TYPE
         SYNTAX      DisplayString
         MAX-ACCESS  read-only
         STATUS      current
         DESCRIPTION
                     "temperature 3 of the unit"
         ::= { agentTemperatureFanStatusEntry 13 }

     agentTemperature4 OBJECT-TYPE
         SYNTAX      DisplayString
         MAX-ACCESS  read-only
         STATUS      current
         DESCRIPTION
                     "temperature 4 of the unit"
         ::= { agentTemperatureFanStatusEntry 14 }

     agentTemperature5 OBJECT-TYPE
         SYNTAX      DisplayString
         MAX-ACCESS  read-only
         STATUS      current
         DESCRIPTION
                     "temperature 5 of the unit"
         ::= { agentTemperatureFanStatusEntry 15 }


	agentFAN1 OBJECT-TYPE
         SYNTAX      INTEGER {
                     active(1),
                     inactive(2)
                  }
         MAX-ACCESS  read-only
         STATUS      current
         DESCRIPTION
                     "FAN1 status of the unit"
         ::= { agentTemperatureFanStatusEntry 21 }

    agentFAN2 OBJECT-TYPE
         SYNTAX      INTEGER {
                     active(1),
                     inactive(2)
                  }
         MAX-ACCESS  read-only
         STATUS      current
         DESCRIPTION
                     "FAN2 status of the unit"
         ::= { agentTemperatureFanStatusEntry 22 }

    agentFAN3 OBJECT-TYPE
         SYNTAX      INTEGER {
                     active(1),
                     inactive(2)
                  }
         MAX-ACCESS  read-only
         STATUS      current
         DESCRIPTION
                     "FAN3 status of the unit"
         ::= { agentTemperatureFanStatusEntry 23 }

    agentFAN4 OBJECT-TYPE
         SYNTAX      INTEGER {
                     active(1),
                     inactive(2)
                  }
         MAX-ACCESS  read-only
         STATUS      current
         DESCRIPTION
                     "FAN3 status of the unit"
         ::= { agentTemperatureFanStatusEntry 24 }

     agentFANChipType OBJECT-TYPE
         SYNTAX      DisplayString
         MAX-ACCESS  read-only
         STATUS      current
         DESCRIPTION
                     "fan chip type of the unit"
         ::= { agentTemperatureFanStatusEntry 31 }

    --**************************************************************************************
    -- Power Supply status information Table
    --
    --**************************************************************************************
    agentPowerSupplyStatusTable OBJECT-TYPE
         SYNTAX      SEQUENCE OF AgentPowerSupplyStatusEntry
         MAX-ACCESS  not-accessible
         STATUS      current
         DESCRIPTION
                     "The switch's power supplies information table"
         ::= { agentInventoryGroupExtension 107 }

    agentPowerSupplyStatusEntry OBJECT-TYPE
         SYNTAX      AgentPowerSupplyStatusEntry
         MAX-ACCESS  not-accessible
         STATUS      current
         DESCRIPTION
                     "entry of power supplies information table"
         INDEX       { agentPowerSupplyUnitIndex }
         ::= { agentPowerSupplyStatusTable 1 }

    AgentPowerSupplyStatusEntry ::=
         SEQUENCE {
         agentPowerSupplyUnitIndex
                 Integer32,
         agentPowerSupplyStatus
                 INTEGER,
         agentPowerSupplyName
                 DisplayString,
         agentPowerSupplyModel
                 DisplayString,
         agentPowerSupplyRevisionNumber
                 DisplayString,
         agentPowerSupplyManufacturerLocation
                 DisplayString,
         agentPowerSupplyManufacturingDate
                 DisplayString,
         agentPowerSupplySerialNumber
                 DisplayString,
         agentPowerSupplyTemperature1
                 DisplayString,
         agentPowerSupplyTemperature2
                 DisplayString,
         agentPowerSupplyFanSpeed
                 DisplayString,
         agentPowerSupplyFanDuty
                 Integer32,
		 agentPowerConsumption
                 DisplayString
         }

    agentPowerSupplyUnitIndex OBJECT-TYPE
         SYNTAX      Integer32 (0..2147483647)
         MAX-ACCESS  read-only
         STATUS      current
         DESCRIPTION
                     "Unique index of power supplies Information entry"
         ::= { agentPowerSupplyStatusEntry 1 }

    agentPowerSupplyStatus OBJECT-TYPE
         SYNTAX      INTEGER {
                     active(1),
                     inactive(2),
					 notpresent(3)
                  }
         MAX-ACCESS  read-only
         STATUS      current
         DESCRIPTION
                     "status of the power supply"
         ::= { agentPowerSupplyStatusEntry 2 }

    agentPowerSupplyName OBJECT-TYPE
         SYNTAX      DisplayString
         MAX-ACCESS  read-only
         STATUS      current
         DESCRIPTION
                     "name of the power supply"
         ::= { agentPowerSupplyStatusEntry 3 }

    agentPowerSupplyModel OBJECT-TYPE
         SYNTAX      DisplayString
         MAX-ACCESS  read-only
         STATUS      current
         DESCRIPTION
                     "model of the power supply"
         ::= { agentPowerSupplyStatusEntry 4 }

    agentPowerSupplyRevisionNumber OBJECT-TYPE
         SYNTAX      DisplayString
         MAX-ACCESS  read-only
         STATUS      current
         DESCRIPTION
                     "revision number of the power supply"
         ::= { agentPowerSupplyStatusEntry 5 }

    agentPowerSupplyManufacturerLocation OBJECT-TYPE
         SYNTAX      DisplayString
         MAX-ACCESS  read-only
         STATUS      current
         DESCRIPTION
                     "manufacturer location of the power supply"
         ::= { agentPowerSupplyStatusEntry 6 }

    agentPowerSupplyManufacturingDate OBJECT-TYPE
         SYNTAX      DisplayString
         MAX-ACCESS  read-only
         STATUS      current
         DESCRIPTION
                     "manufacturing date of the power supply"
         ::= { agentPowerSupplyStatusEntry 7 }

    agentPowerSupplySerialNumber OBJECT-TYPE
         SYNTAX      DisplayString
         MAX-ACCESS  read-only
         STATUS      current
         DESCRIPTION
                     "serial number of the power supply"
         ::= { agentPowerSupplyStatusEntry 8 }

    agentPowerSupplyTemperature1 OBJECT-TYPE
         SYNTAX      DisplayString
         MAX-ACCESS  read-only
         STATUS      current
         DESCRIPTION
                     "temperature 1 of the power supply"
         ::= { agentPowerSupplyStatusEntry 9 }

    agentPowerSupplyTemperature2 OBJECT-TYPE
         SYNTAX      DisplayString
         MAX-ACCESS  read-only
         STATUS      current
         DESCRIPTION
                     "temperature 2 of the power supply"
         ::= { agentPowerSupplyStatusEntry 10 }

    agentPowerSupplyFanSpeed OBJECT-TYPE
         SYNTAX      DisplayString
         MAX-ACCESS  read-only
         STATUS      current
         DESCRIPTION
                     "fan speed of the power supply"
         ::= { agentPowerSupplyStatusEntry 11 }

    agentPowerSupplyFanDuty OBJECT-TYPE
         SYNTAX      Integer32
         MAX-ACCESS  read-only
         STATUS      current
         DESCRIPTION
                     "fan duty of the power supply"
         ::= { agentPowerSupplyStatusEntry 12 }

	agentPowerConsumption OBJECT-TYPE
         SYNTAX      DisplayString
         MAX-ACCESS  read-only
         STATUS      current
         DESCRIPTION
                     "power consumption of the power supply"
         ::= { agentPowerSupplyStatusEntry 13 }

--/* Add for DOM support by KevinLee 2013/08/13*/
    --**************************************************************************************
    -- DOM information Table
    -- add by JoeLai, 2013-07-18
    --**************************************************************************************
    agentDOMTable OBJECT-TYPE
         SYNTAX      SEQUENCE OF AgentDOMEntry
         MAX-ACCESS  not-accessible
         STATUS      current
         DESCRIPTION
                     "The switch's dom information table"
         ::= { agentInventoryGroupExtension 108 }

    agentDOMEntry OBJECT-TYPE
         SYNTAX      AgentDOMEntry
         MAX-ACCESS  not-accessible
         STATUS      current
         DESCRIPTION
                     "entry of dom information table"
         INDEX       { agentDOMtransceiverIndex }
         ::= { agentDOMTable 1 }

    AgentDOMEntry ::=
         SEQUENCE {
         agentDOMtransceiverIndex
                 Integer32,
         agentDOMTemperature
                 DisplayString,
         agentDOMVoltage
                 DisplayString,
         agentDOMBias
                 DisplayString,
         agentDOMTxpower
                 DisplayString,
         agentDOMRxpower
                 DisplayString,
         agentDOMtemperatureHighAlarm
                 DisplayString,
         agentDOMtemperatureHighWarning
                 DisplayString,
         agentDOMtemperatureLowWarning
                 DisplayString,
         agentDOMtemperatureLowAlarm
                 DisplayString,
         agentDOMvotageHighAlarm
                 DisplayString,
         agentDOMvotageHighWarning
                 DisplayString,
         agentDOMvotageLowWarning
                 DisplayString,
         agentDOMvotageLowAlarm
                 DisplayString,
         agentDOMbiasHighAlarm
                 DisplayString,
         agentDOMbiasHighWarning
                 DisplayString,
         agentDOMbiasLowWarning
                 DisplayString,
         agentDOMbiasLowAlarm
                 DisplayString,
         agentDOMtxpowerHighAlarm
                 DisplayString,
         agentDOMtxpowerHighWarning
                 DisplayString,
         agentDOMtxpowerLowWarning
                 DisplayString,
         agentDOMtxpowerLowAlarm
                 DisplayString,
         agentDOMrxpowerHighAlarm
                 DisplayString,
         agentDOMrxpowerHighWarning
                 DisplayString,
         agentDOMrxpowerLowWarning
                 DisplayString,
         agentDOMrxpowerLowAlarm
                 DisplayString				 
	     }

    agentDOMtransceiverIndex OBJECT-TYPE
         SYNTAX      Integer32 (0..2147483647)
         MAX-ACCESS  read-only
         STATUS      current
         DESCRIPTION
                     "Unique index of dom Information entry"
         ::= { agentDOMEntry 1 }

    agentDOMTemperature OBJECT-TYPE
         SYNTAX      DisplayString
         MAX-ACCESS  read-only
         STATUS      current
         DESCRIPTION
                     "temperature of the transceiver module"
         ::= { agentDOMEntry 2 }

    agentDOMVoltage OBJECT-TYPE
         SYNTAX      DisplayString
         MAX-ACCESS  read-only
         STATUS      current
         DESCRIPTION
                     "votage of the transceiver module"
         ::= { agentDOMEntry 3 }		 
		  
    agentDOMBias OBJECT-TYPE
         SYNTAX      DisplayString
         MAX-ACCESS  read-only
         STATUS      current
         DESCRIPTION
                     "Bias current of the transceiver module"
         ::= { agentDOMEntry 4 }		 

	agentDOMTxpower OBJECT-TYPE
         SYNTAX      DisplayString
         MAX-ACCESS  read-only
         STATUS      current
         DESCRIPTION
                     "Tx Power of the transceiver module"
         ::= { agentDOMEntry 5 }
		 
    agentDOMRxpower OBJECT-TYPE
         SYNTAX      DisplayString
         MAX-ACCESS  read-only
         STATUS      current
         DESCRIPTION
                     "Rx Power of the transceiver module"
         ::= { agentDOMEntry 6 }		 

    agentDOMtemperatureHighAlarm OBJECT-TYPE
         SYNTAX      DisplayString
         MAX-ACCESS  read-only
         STATUS      current
         DESCRIPTION
                     "Temperature high alarm of the transceiver module"
         ::= { agentDOMEntry 7 }

    agentDOMtemperatureHighWarning OBJECT-TYPE
         SYNTAX      DisplayString
         MAX-ACCESS  read-only
         STATUS      current
         DESCRIPTION
                     "Temperature high warning of the transceiver module"
         ::= { agentDOMEntry 8 }

    agentDOMtemperatureLowWarning OBJECT-TYPE
         SYNTAX      DisplayString
         MAX-ACCESS  read-only
         STATUS      current
         DESCRIPTION
                     "Temperature low warning of the transceiver module"
         ::= { agentDOMEntry 9 }

    agentDOMtemperatureLowAlarm OBJECT-TYPE
         SYNTAX      DisplayString
         MAX-ACCESS  read-only
         STATUS      current
         DESCRIPTION
                     "Temperature low alarm of the transceiver module"
         ::= { agentDOMEntry 10 }

    agentDOMvotageHighAlarm OBJECT-TYPE
         SYNTAX      DisplayString
         MAX-ACCESS  read-only
         STATUS      current
         DESCRIPTION
                     "Votage high alarm of the transceiver module"
         ::= { agentDOMEntry 11 }

    agentDOMvotageHighWarning OBJECT-TYPE
         SYNTAX      DisplayString
         MAX-ACCESS  read-only
         STATUS      current
         DESCRIPTION
                     "Votage high warning of the transceiver module"
         ::= { agentDOMEntry 12 }

    agentDOMvotageLowWarning OBJECT-TYPE
         SYNTAX      DisplayString
         MAX-ACCESS  read-only
         STATUS      current
         DESCRIPTION
                     "Votage low warning of the transceiver module"
         ::= { agentDOMEntry 13 }

    agentDOMvotageLowAlarm OBJECT-TYPE
         SYNTAX      DisplayString
         MAX-ACCESS  read-only
         STATUS      current
         DESCRIPTION
                     "Votage low alarm of the transceiver module"
         ::= { agentDOMEntry 14 }

    agentDOMbiasHighAlarm OBJECT-TYPE
         SYNTAX      DisplayString
         MAX-ACCESS  read-only
         STATUS      current
         DESCRIPTION
                     "Bias high alarm of the transceiver module"
         ::= { agentDOMEntry 15 }

    agentDOMbiasHighWarning OBJECT-TYPE
         SYNTAX      DisplayString
         MAX-ACCESS  read-only
         STATUS      current
         DESCRIPTION
                     "Bias high warning of the transceiver module"
         ::= { agentDOMEntry 16 }

    agentDOMbiasLowWarning OBJECT-TYPE
         SYNTAX      DisplayString
         MAX-ACCESS  read-only
         STATUS      current
         DESCRIPTION
                     "Bias low warning of the transceiver module"
         ::= { agentDOMEntry 17 }

    agentDOMbiasLowAlarm OBJECT-TYPE
         SYNTAX      DisplayString
         MAX-ACCESS  read-only
         STATUS      current
         DESCRIPTION
                     "Bias low alarm of the transceiver module"
         ::= { agentDOMEntry 18 }

    agentDOMtxpowerHighAlarm OBJECT-TYPE
         SYNTAX      DisplayString
         MAX-ACCESS  read-only
         STATUS      current
         DESCRIPTION
                     "Tx Power high alarm of the transceiver module"
         ::= { agentDOMEntry 19 }

    agentDOMtxpowerHighWarning OBJECT-TYPE
         SYNTAX      DisplayString
         MAX-ACCESS  read-only
         STATUS      current
         DESCRIPTION
                     "Tx Power high warning of the transceiver module"
         ::= { agentDOMEntry 20 }

    agentDOMtxpowerLowWarning OBJECT-TYPE
         SYNTAX      DisplayString
         MAX-ACCESS  read-only
         STATUS      current
         DESCRIPTION
                     "Tx Power low warning of the transceiver module"
         ::= { agentDOMEntry 21 }

    agentDOMtxpowerLowAlarm OBJECT-TYPE
         SYNTAX      DisplayString
         MAX-ACCESS  read-only
         STATUS      current
         DESCRIPTION
                     "Tx Power low alarm of the transceiver module"
         ::= { agentDOMEntry 22 }

    agentDOMrxpowerHighAlarm OBJECT-TYPE
         SYNTAX      DisplayString
         MAX-ACCESS  read-only
         STATUS      current
         DESCRIPTION
                     "Rx Power high alarm of the transceiver module"
         ::= { agentDOMEntry 23 }

    agentDOMrxpowerHighWarning OBJECT-TYPE
         SYNTAX      DisplayString
         MAX-ACCESS  read-only
         STATUS      current
         DESCRIPTION
                     "Rx Power high warning of the transceiver module"
         ::= { agentDOMEntry 24 }

    agentDOMrxpowerLowWarning OBJECT-TYPE
         SYNTAX      DisplayString
         MAX-ACCESS  read-only
         STATUS      current
         DESCRIPTION
                     "Rx Power low warning of the transceiver module"
         ::= { agentDOMEntry 25 }

    agentDOMrxpowerLowAlarm OBJECT-TYPE
         SYNTAX      DisplayString
         MAX-ACCESS  read-only
         STATUS      current
         DESCRIPTION
                     "Rx Power low alarm of the transceiver module"
         ::= { agentDOMEntry 26 }

--/* Add by KevinLee 2014/04/17*/ /* Add SNMP for DOM */
--**************************************************************************************
--    DOM Group
--
--**************************************************************************************
agentDOMGroup                             OBJECT IDENTIFIER ::= { switchingExtension 100 }

    agentDOMAdminMode OBJECT-TYPE
         SYNTAX     INTEGER {
                    enable(1),
                    disable(2)
                    }
         MAX-ACCESS  read-write
         STATUS      current
         DESCRIPTION
                     "Enable or disable the DOM feature. The default mode is disabled."
         DEFVAL { disable }
         ::= { agentDOMGroup 1 }

    agentDOMInterval OBJECT-TYPE
         SYNTAX     INTEGER (300..1800)
         MAX-ACCESS  read-write
         STATUS      current
         DESCRIPTION
                     "Configure the interval of Digital Optical Monitor."
         DEFVAL { 600 }
         ::= { agentDOMGroup 2 }

	--**************************************************************************************
    -- agent10GInfoGroupExtension
    --
    --**************************************************************************************


    agent10GModuleInfoGroupExtension        OBJECT IDENTIFIER ::= { agentInfoGroupExtension 2 }

    --**************************************************************************************
    -- 10G modules information Table
    --
    --**************************************************************************************

   agent10GModuleTable OBJECT-TYPE
         SYNTAX      SEQUENCE OF Agent10GModuleEntry
         MAX-ACCESS  not-accessible
         STATUS      current
         DESCRIPTION
                     "The switch's 10G module information table"
         ::= { agent10GModuleInfoGroupExtension 107 }

    agent10GModuleEntry OBJECT-TYPE
         SYNTAX      Agent10GModuleEntry
         MAX-ACCESS  not-accessible
         STATUS      current
         DESCRIPTION
                     "entry of 10G module information table"
         INDEX       { agent10GModuleUnitIndex, agent10GModuleSlotIndex, agent10GModulePortIndex }
         ::= { agent10GModuleTable 1 }

    Agent10GModuleEntry ::=
         SEQUENCE {
             agent10GModuleUnitIndex           Integer32,
             agent10GModuleSlotIndex           Integer32,
             agent10GModulePortIndex           Integer32,
             agent10GModuleIndex               Integer32,
             agent10GModuleInterfaceNumber     Integer32,
             agent10GModuleType                DisplayString,
             agent10GModuleComplianceCode      DisplayString,
             agent10GModuleVendorName          DisplayString,
             agent10GModulePartNumber          DisplayString,
             agent10GModuleSerialNumber        DisplayString,
             agent10GModuleRevisionNumber      DisplayString,
             agent10GModuleManufacturingDate   DisplayString
         }

    agent10GModuleUnitIndex OBJECT-TYPE
         SYNTAX      Integer32 (0..2147483647)
         MAX-ACCESS  read-only
         STATUS      current
         DESCRIPTION
                     "The unit number associated with this unit."
         ::= { agent10GModuleEntry 1 }

    agent10GModuleSlotIndex OBJECT-TYPE
         SYNTAX      Integer32 (0..2147483647)
         MAX-ACCESS  read-only
         STATUS      current
         DESCRIPTION
                     "Unique slot index in 10G module entry."
         ::= { agent10GModuleEntry 2 }

    agent10GModulePortIndex OBJECT-TYPE
         SYNTAX      Integer32 (0..2147483647)
         MAX-ACCESS  read-only
         STATUS      current
         DESCRIPTION
                     "Unique port index of the slot in 10G module entry."
         ::= { agent10GModuleEntry 3 }

    agent10GModuleIndex OBJECT-TYPE
         SYNTAX      Integer32 (0..2147483647)
         MAX-ACCESS  read-only
         STATUS      current
         DESCRIPTION
                     "Unique index of 10G module entry."
         ::= { agent10GModuleEntry 4 }

     agent10GModuleInterfaceNumber OBJECT-TYPE
         SYNTAX      Integer32 (0..2147483647)
         MAX-ACCESS  read-only
         STATUS      current
         DESCRIPTION
                     "Interface number of the corresponding 10G module index entry."
         ::= { agent10GModuleEntry 5 }

    agent10GModuleType OBJECT-TYPE
         SYNTAX  DisplayString
         MAX-ACCESS  read-only
         STATUS      current
         DESCRIPTION
                     "10G module's types. It could be CX4 or SFP Plus."
         ::= { agent10GModuleEntry 6 }

    agent10GModuleComplianceCode OBJECT-TYPE
         SYNTAX  DisplayString
         MAX-ACCESS  read-only
         STATUS      current
         DESCRIPTION
                     "10G module's Compliance codes"
         ::= { agent10GModuleEntry 7 }

    agent10GModuleVendorName   OBJECT-TYPE
         SYNTAX  DisplayString
         MAX-ACCESS  read-only
         STATUS      current
         DESCRIPTION
                     "10G module's vendor name."
         ::= { agent10GModuleEntry 8 }

    agent10GModulePartNumber   OBJECT-TYPE
         SYNTAX  DisplayString
         MAX-ACCESS  read-only
         STATUS      current
         DESCRIPTION
                     "10G module's part number."
         ::= { agent10GModuleEntry 9 }

    agent10GModuleSerialNumber   OBJECT-TYPE
         SYNTAX  DisplayString
         MAX-ACCESS  read-only
         STATUS      current
         DESCRIPTION
                     "10G module's serial number."
         ::= { agent10GModuleEntry 10 }

    agent10GModuleRevisionNumber   OBJECT-TYPE
         SYNTAX  DisplayString
         MAX-ACCESS  read-only
         STATUS      current
         DESCRIPTION
                     "10G module's revision number."
         ::= { agent10GModuleEntry 11 }

    agent10GModuleManufacturingDate   OBJECT-TYPE
         SYNTAX  DisplayString
         MAX-ACCESS  read-only
         STATUS      current
         DESCRIPTION
                     "10G module's Manufacturing date."
         ::= { agent10GModuleEntry 12 }

    --**************************************************************************************
    -- GBIC information Table
    --
    --**************************************************************************************
    agentGBICInfoTable OBJECT-TYPE
         SYNTAX      SEQUENCE OF AgentGBICInfoEntry
         MAX-ACCESS  not-accessible
         STATUS      current
         DESCRIPTION
                     "The switch's GBIC information table"
         ::= { agentInfoGroupExtension 3 }

    agentGBICInfoEntry OBJECT-TYPE
         SYNTAX      AgentGBICInfoEntry
         MAX-ACCESS  not-accessible
         STATUS      current
         DESCRIPTION
                     "entry of GBIC information table"
         INDEX       { agentGBICInfoIndex }
         ::= { agentGBICInfoTable 1 }

    AgentGBICInfoEntry ::=
         SEQUENCE {
             agentGBICInfoIndex                Integer32,
             agentGBICInfoInterfaceNumber      Integer32,
             agentGBICInfoComplianceCode    DisplayString,
             agentGBICInfoVendorName        DisplayString,
             agentGBICInfoPartNumber        DisplayString,
             agentGBICInfoSerialNumber      DisplayString,
             agentGBICInfoRevisionNumber    DisplayString,
             agentGBICInfoManufacturingDate DisplayString
         }


    agentGBICInfoIndex OBJECT-TYPE
         SYNTAX      Integer32 (0..2147483647)
         MAX-ACCESS  read-only
         STATUS      current
         DESCRIPTION
                     "Unique index of GBIC Information entry"
         ::= { agentGBICInfoEntry 1 }


     agentGBICInfoInterfaceNumber OBJECT-TYPE
         SYNTAX      Integer32
         MAX-ACCESS  read-only
         STATUS      current
         DESCRIPTION
                     "interface number of the corresponding GBIC index entry"
         ::= { agentGBICInfoEntry 2 }


    agentGBICInfoComplianceCode OBJECT-TYPE
         SYNTAX  DisplayString
         MAX-ACCESS  read-only
         STATUS      current
         DESCRIPTION
                     "Gigabit Ethernet Compliance codes"
         ::= { agentGBICInfoEntry 3 }

    agentGBICInfoVendorName OBJECT-TYPE
         SYNTAX  DisplayString
         MAX-ACCESS  read-only
         STATUS      current
         DESCRIPTION
                     "GBIC vendor name"
         ::= { agentGBICInfoEntry 4 }


    agentGBICInfoPartNumber OBJECT-TYPE
         SYNTAX  DisplayString
         MAX-ACCESS  read-only
         STATUS      current
         DESCRIPTION
                     "GBIC part number"
         ::= { agentGBICInfoEntry 5 }


    agentGBICInfoSerialNumber OBJECT-TYPE
         SYNTAX  DisplayString
         MAX-ACCESS  read-only
         STATUS      current
         DESCRIPTION
                     "GBIC serial number"
         ::= { agentGBICInfoEntry 6 }


    agentGBICInfoRevisionNumber OBJECT-TYPE
         SYNTAX  DisplayString
         MAX-ACCESS  read-only
         STATUS      current
         DESCRIPTION
                     "GBIC revision number"
         ::= { agentGBICInfoEntry 7 }

    agentGBICInfoManufacturingDate  OBJECT-TYPE
         SYNTAX  DisplayString
         MAX-ACCESS  read-only
         STATUS      current
         DESCRIPTION
                     "GBIC manufacturing date"
         ::= { agentGBICInfoEntry 8 }


--**************************************************************************************
--    agentConfigGroupExtension
--**************************************************************************************

agentConfigGroupExtension                             OBJECT IDENTIFIER ::= { switchingExtension 2 }


    --**************************************************************************************
    -- agentCLIConfigGroupExtension
    --
    --**************************************************************************************

agentCLIConfigGroupExtension                          OBJECT IDENTIFIER ::= { agentConfigGroupExtension 1 }

agentSerialGroupExtension                             OBJECT IDENTIFIER ::= { agentCLIConfigGroupExtension 5 }

    agentSerialPasswdCnt OBJECT-TYPE
         SYNTAX      Integer32 (0..120)
         MAX-ACCESS  read-write
         STATUS      current
         DESCRIPTION
                     "The switch's serial port password count threshold.  "
         DEFVAL {3}
         ::= { agentSerialGroupExtension 100 }

    agentSerialPasswdCntSetToDefault OBJECT-TYPE
         SYNTAX      INTEGER {
                     enable(1),
                     disable(2)
                  }
         MAX-ACCESS  read-write
         STATUS      current
         DESCRIPTION
                     "Set the switch's serial port password count threshold to the default value.  "
         DEFVAL {disable}
         ::= { agentSerialGroupExtension 101 }

     agentSerialSilentTime OBJECT-TYPE
         SYNTAX      Integer32 (0..65535)
         MAX-ACCESS  read-write
         STATUS      current
         DESCRIPTION
                     "If a user fail to login into the console for agentSerialPasswdCnt times, the user cannot login again for a period of agentSerialSilentTime seconds  "
         DEFVAL {0}
         ::= { agentSerialGroupExtension 102 }

    agentSerialSilentTimeSetToDefault OBJECT-TYPE
         SYNTAX      INTEGER {
                     enable(1),
                     disable(2)
                  }
         MAX-ACCESS  read-write
         STATUS      current
         DESCRIPTION
                     "Set the switch's serial port silent time to the default value.  "
         DEFVAL {disable}
         ::= { agentSerialGroupExtension 103 }


agentVtyGroupExtension                             OBJECT IDENTIFIER ::= { agentCLIConfigGroupExtension 6 }


    agentVtyTelnetServerAdminMode OBJECT-TYPE
         SYNTAX      INTEGER {
                     enable(1),
                     disable(2)
                  }
         MAX-ACCESS  read-write
         STATUS      current
         DESCRIPTION
                     "The switch's telnet server admin mode."
         ::= { agentVtyGroupExtension 103 }

    agentVtyPasswdCnt OBJECT-TYPE
         SYNTAX      Integer32 (0..120)
         MAX-ACCESS  read-write
         STATUS      current
         DESCRIPTION
                     "The switch's password count threshold for telnet and SSH connections. System will reject
                      telnet or SSH connections if users fail the password authentication for agentVtyPasswdCnt times  "
         DEFVAL {3}
         ::= { agentVtyGroupExtension 104 }

    agentVtyPasswdCntSetToDefault OBJECT-TYPE
         SYNTAX      INTEGER {
                     enable(1),
                     disable(2)
                  }
         MAX-ACCESS  read-write
         STATUS      current
         DESCRIPTION
                     "Set the switch's password count threshold to the default value for telnet and SSH connections.  "
         DEFVAL {disable}
         ::= { agentVtyGroupExtension 105 }

    agentVtyTerminalLength OBJECT-TYPE
         SYNTAX      Integer32 (10..100)
         MAX-ACCESS  read-write
         STATUS      current
         DESCRIPTION
                     "The switch's terminal length for telnet connections."
         DEFVAL { 24 }
         ::= { agentVtyGroupExtension 106 }

    agentVtyTerminalLengthSetToDefault OBJECT-TYPE
         SYNTAX      INTEGER {
                     enable(1),
                     disable(2)
                  }
         MAX-ACCESS  read-write
         STATUS      current
         DESCRIPTION
                     "Set the switch's terminal length to the default value for telnet connections."
         DEFVAL { disable }
         ::= { agentVtyGroupExtension 107 }

    --**************************************************************************************
    -- agentNetworkConfigGroupExtension
    --
    --**************************************************************************************


    agentNetworkConfigGroupExtension        OBJECT IDENTIFIER ::= { agentConfigGroupExtension 3 }


    agentNetworkHttpPort OBJECT-TYPE
         SYNTAX      Integer32 (1..65535)
         MAX-ACCESS  read-write
         STATUS      current
         DESCRIPTION
                     "The switch's HTTP port number.  "
         ::= { agentNetworkConfigGroupExtension 100 }


    agentNetworkDhcpClientIfClientIdFormat OBJECT-TYPE
         SYNTAX      INTEGER {
                     hexformat(1),
                     textformat(2)
                  }
         MAX-ACCESS  read-write
         STATUS      current
         DESCRIPTION
                     "Set the switch's client ID agentNetworkDhcpClientIfClientId format. It could be HEX(00:00:00:00:00:00) or TEXT( which length is less or equal to 32) "
         DEFVAL { hexformat }
         ::= { agentNetworkConfigGroupExtension 101 }


    agentNetworkDhcpClientIfClientId OBJECT-TYPE
         SYNTAX      DisplayString (SIZE(1..32))
         MAX-ACCESS  read-write
         STATUS      current
         DESCRIPTION
                     "Set the switch's Client ID. The client ID is used in asking for an IP address from the DHCP server. It could be HEX(00:00:00:00:00:00) or TEXT( which length is less or equal to 32) "
         ::= { agentNetworkConfigGroupExtension 102 }



    agentNetworkDhcpSetToInventoryClientIfClientId OBJECT-TYPE
         SYNTAX      INTEGER {
                     enable(1),
                     disable(2)
                  }
         MAX-ACCESS  read-write
         STATUS      current
         DESCRIPTION
                     "If enable, set switch's Client ID to the inventory's default value "
         DEFVAL { disable }
         ::= { agentNetworkConfigGroupExtension 103 }




    agentNetworkDhcpRestart OBJECT-TYPE
         SYNTAX      INTEGER {
                     restart(1),
                     noRestart(2)
                  }
         MAX-ACCESS  read-write
         STATUS      obsolete
         DESCRIPTION
                     "If restart, release current IP address and Re-get the switch's IP address from the DHCP/BOOTP server "
         ::= { agentNetworkConfigGroupExtension 104 }


    --**************************************************************************************
    -- agentSwitchConfigExtensionGroup
    --
    --**************************************************************************************

agentSwitchConfigGroupExtension                      OBJECT IDENTIFIER ::= { agentConfigGroupExtension 8 }

    --**************************************************************************************
    -- agentIPFilterConfigGroupExtension
    --
    --**************************************************************************************
agentIPFilterConfigGroupExtension                      OBJECT IDENTIFIER ::= { agentSwitchConfigGroupExtension 10 }

agentIPFilterConfigAdminMode OBJECT-TYPE
         SYNTAX      INTEGER {
                     enable(1),
                     disable(2)
                  }
         MAX-ACCESS  read-write
         STATUS      current
         DESCRIPTION
                     "enable/disable IP filter function of the switch.  "
         DEFVAL {disable}
         ::= { agentIPFilterConfigGroupExtension 10 }
		 

    agentIpFilterConfigCreate OBJECT-TYPE
         SYNTAX      DisplayString
         MAX-ACCESS  read-write
         STATUS      current
         DESCRIPTION
                     "Creates a new IpFilter entry with name and ip mask or ipv6/prefix length.
                      Max length of ip filter name is 64.
                      Ipv4 Example:
                      IpFilterName 1.1.1.1 255.255.255.0
                      
                      Ipv6 Example:
                      IpFilterName2 1111::1/64
                      "
         ::= { agentIPFilterConfigGroupExtension 11 }		 

		 
    agentIpFilterConfigDelete OBJECT-TYPE
         SYNTAX      DisplayString
         MAX-ACCESS  read-write
         STATUS      current
         DESCRIPTION
                     "Delete a IpFilter entry by name."
         ::= { agentIPFilterConfigGroupExtension 12 }		 
 
 
    --**************************************************************************************
    -- Ip Filter Table
    --
    --**************************************************************************************
    agentIpFilterConfigTable OBJECT-TYPE
         SYNTAX      SEQUENCE OF AgentIpFilterConfigEntry
         MAX-ACCESS  not-accessible
         STATUS      current
         DESCRIPTION
                     "The switch's IP filter table"
         ::= { agentIPFilterConfigGroupExtension 30 }

    agentIpFilterConfigEntry OBJECT-TYPE
         SYNTAX      AgentIpFilterConfigEntry
         MAX-ACCESS  not-accessible
         STATUS      current
         DESCRIPTION
                     "entry of IP filter table"
         INDEX       { agentIpFilterConfigIndex }
         ::= { agentIpFilterConfigTable 1 }

    AgentIpFilterConfigEntry ::=
         SEQUENCE {
             agentIpFilterConfigIndex         Integer32,
             agentIpFilterConfigName          DisplayString,
			 agentIpFilterConfigIP            InetAddress,
			 agentIpFilterConfigMask          InetAddress
         }

    agentIpFilterConfigIndex OBJECT-TYPE
         SYNTAX      Integer32 (0..2147483647)
         MAX-ACCESS  read-only
         STATUS      current
         DESCRIPTION
                     "Unique index of IP Filter entry"
         ::= { agentIpFilterConfigEntry 1 }


    agentIpFilterConfigIP OBJECT-TYPE
         SYNTAX  InetAddress
         MAX-ACCESS  read-write
         STATUS      current
         DESCRIPTION
                     "set the IPv4/IPv6 address which are allowed to connect to DUT
					 IP should be changed with mask."
         ::= { agentIpFilterConfigEntry 2 }

	agentIpFilterConfigMask OBJECT-TYPE
         SYNTAX  InetAddress
         MAX-ACCESS  read-write
         STATUS      current
         DESCRIPTION
                     "set the IPv4/IPv6 mask for defining an IPv4/IPv6 range.
					 IP should be changed with mask."
         ::= { agentIpFilterConfigEntry 3 }
		 
    
	agentIpFilterConfigName OBJECT-TYPE
         SYNTAX  DisplayString (SIZE(1..64))
         MAX-ACCESS  read-write
         STATUS      current
         DESCRIPTION
                     "The name of IpFilter entry."
         ::= { agentIpFilterConfigEntry 4 }

    --**************************************************************************************
    -- QCI Switch Static MacFiltering Table
    --**************************************************************************************


--agentSwitchStaticMacFilteringExtensionTable OBJECT-TYPE
--         SYNTAX      SEQUENCE OF AgentSwitchStaticMacFilteringExtensionEntry
--         MAX-ACCESS  not-accessible
--         STATUS      current
--         DESCRIPTION
--                     "The switch's static Mac filtering table"
--         ::= { agentSwitchConfigGroupExtension 15 }

--    agentSwitchStaticMacFilteringExtensionEntry OBJECT-TYPE
--         SYNTAX      AgentSwitchStaticMacFilteringExtensionEntry
--         MAX-ACCESS  not-accessible
--         STATUS      current
--         DESCRIPTION
--                     "Per-port ingress/egress filter configuration based on VLAN Id and MAC address."
--         INDEX       { agentSwitchStaticMacFilteringExtensionVlanId, agentSwitchStaticMacFilteringExtensionAddress }
--         ::= { agentSwitchStaticMacFilteringExtensionTable 1 }

--    AgentSwitchStaticMacFilteringExtensionEntry ::=
--         SEQUENCE {
--             agentSwitchStaticMacFilteringExtensionVlanId
--                 Integer32,
--             agentSwitchStaticMacFilteringExtensionAddress
--                 MacAddress,
--             agentSwitchStaticMacFilteringExtensionSourcePort
--                 Integer32,
--             agentSwitchStaticMacFilteringExtensionStatus
--                 INTEGER
--         }

--    agentSwitchStaticMacFilteringExtensionVlanId OBJECT-TYPE
--         SYNTAX   Integer32
--         MAX-ACCESS  read-only
--         STATUS      current
--         DESCRIPTION
--                     "The Static MAC Filter Vlan Id"
--         ::= { agentSwitchStaticMacFilteringExtensionEntry 1 }

--    agentSwitchStaticMacFilteringExtensionAddress OBJECT-TYPE
--         SYNTAX   MacAddress
--         MAX-ACCESS  read-only
--         STATUS      current
--         DESCRIPTION
--                     "The Static MAC Filter MAC address"
--         ::= { agentSwitchStaticMacFilteringExtensionEntry 2 }

--    agentSwitchStaticMacFilteringExtensionSourcePort OBJECT-TYPE
--         SYNTAX   Integer32
--         MAX-ACCESS  read-create
--         STATUS      current
--         DESCRIPTION
--                     "The Static MAC Filter source port."

--         ::= { agentSwitchStaticMacFilteringExtensionEntry 3 }


--    agentSwitchStaticMacFilteringExtensionStatus OBJECT-TYPE
--         SYNTAX  INTEGER {
--                valid(1),
--                invalid(4)
--            }
--         MAX-ACCESS  read-create
--         STATUS      current
--         DESCRIPTION
--                     "The Static MAC Filter status.

--                     Supported values:
--                     valid(1)      - the entry is valid
--                     invalid(4)    - removes the entry"
--         ::= { agentSwitchStaticMacFilteringExtensionEntry 5 }


    --**************************************************************************************
    -- agentTransferConfigGroupExtension
    --
    --**************************************************************************************

agentTransferConfigGroupExtension                      OBJECT IDENTIFIER ::= { agentConfigGroupExtension 9 }




    --**************************************************************************************
    --  agentTransferCopyGroup
    --
    --**************************************************************************************

agentTransferCopyGroup                      OBJECT IDENTIFIER ::= { agentTransferConfigGroupExtension 3 }

    agentTransferCopyRunningConfigToSwitchDestFilename OBJECT-TYPE
         SYNTAX      DisplayString (SIZE(0..30))
         MAX-ACCESS  read-write
         STATUS      current
         DESCRIPTION
                     "The filename used to store current running config in the switch.
                     It can be up to 30 alphanumeric characters."

         ::= { agentTransferCopyGroup 1 }

    agentTransferCopyRunningConfigStart OBJECT-TYPE
         SYNTAX      INTEGER {
                     enable(1),
                     disable(2)
                  }
         MAX-ACCESS  read-write
         STATUS      current
         DESCRIPTION
                     "Copy running configure to switch, the filename is specified in
                     agentTransferCopyRunningConfigToSwitchDestFilename."

         ::= { agentTransferCopyGroup 2 }

    agentTransferCopyRunningConfigStatus OBJECT-TYPE
         SYNTAX      INTEGER {
                     success(0),
                     failure(1),
                     wrongFileType(4),
                     noPartitionTableEntry(15),
                     runByOtherUsers(16)
                  }
         MAX-ACCESS  read-only
         STATUS      current
         DESCRIPTION
                     "Indicates the current status of a copy running configure operation."
         ::= { agentTransferCopyGroup 3 }



    --**************************************************************************************
    --  agentTransferDeleteGroup
    --
    --**************************************************************************************

agentTransferDeleteGroup                      OBJECT IDENTIFIER ::= { agentTransferConfigGroupExtension 4 }

    agentTransferDeleteSwitchFilename OBJECT-TYPE
         SYNTAX      DisplayString (SIZE(0..32))
         MAX-ACCESS  read-write
         STATUS      current
         DESCRIPTION
                     "The filename of the file to be deleted from the switch.
                     It can be up to 32 alphanumeric characters."

         ::= { agentTransferDeleteGroup 1 }

    agentTransferDeleteStart OBJECT-TYPE
         SYNTAX      INTEGER {
                     enable(1),
                     disable(2)
                  }
         MAX-ACCESS  read-write
         STATUS      current
         DESCRIPTION
                     "start deleting file; the filename is specified in
                     agentTransferDeleteSwitchFilename."

         ::= { agentTransferDeleteGroup 2 }

    agentTransferDeleteStatus OBJECT-TYPE
         SYNTAX      INTEGER {
                     success(0),
                     failure(1)
                  }
         MAX-ACCESS  read-only
         STATUS      current
         DESCRIPTION
                     "Indicates the current status of the deleting operation."
         ::= { agentTransferDeleteGroup 3 }


    --**************************************************************************************
    -- Storm Control Table
    --
    --**************************************************************************************
	agentStormContorlConfigGroupExtension                      OBJECT IDENTIFIER ::= { agentSwitchConfigGroupExtension 18 }

      agentSwitchBroadcastControlMode OBJECT-TYPE
         SYNTAX      INTEGER {
                     enable(1),
                     disable(2)
                  }
         MAX-ACCESS  read-write
         STATUS      current
         DESCRIPTION
                     "The switch config broadcast allows you to enable or disable
                     broadcast storm recovery mode. When you specify Enable for Broadcast
                     Storm Recovery and the broadcast traffic on any Ethernet port exceeds
                     20 percent of the link speed, the switch blocks (discards) the broadcast
                     traffic until the broadcast traffic returns to 10 percent or less.
                     Upper limit for 10M link is 20% and lower limit is 10%.
                     For 100M link Upper limit is 5% and lower limit is 2%"
         DEFVAL { disable }
         ::= { agentStormContorlConfigGroupExtension  1 }

      agentSwitchMulticastControlMode OBJECT-TYPE
         SYNTAX      INTEGER {
                     enable(1),
                     disable(2)
                  }
         MAX-ACCESS  read-write
         STATUS      current
         DESCRIPTION
                     "The switch config multicast allows you to enable or disable
                     multicast storm recovery mode. When you specify Enable for Multicast
                     Storm Recovery and the multicast traffic on any Ethernet port exceeds
                     20 percent of the link speed, the switch blocks (discards) the multicast
                     traffic until the multicast traffic returns to 10 percent or less.
                     Upper limit for 10M link is 20% and lower limit is 10%.
                     For 100M link Upper limit is 5% and lower limit is 2%"
         DEFVAL { disable }
         ::= { agentStormContorlConfigGroupExtension  2 }
         
      agentSwitchUnicastControlMode OBJECT-TYPE
         SYNTAX      INTEGER {
                     enable(1),
                     disable(2)
                  }
         MAX-ACCESS  read-write
         STATUS      current
         DESCRIPTION
                     "The switch config unicast allows you to enable or disable
                     unicast storm recovery mode. When you specify Enable for unicast
                     Storm Recovery and the unicast traffic on any Ethernet port exceeds
                     20 percent of the link speed, the switch blocks (discards) the unicast
                     traffic until the unicast traffic returns to 10 percent or less.
                     Upper limit for 10M link is 20% and lower limit is 10%.
                     For 100M link Upper limit is 5% and lower limit is 2%"
         DEFVAL { disable }
         ::= { agentStormContorlConfigGroupExtension  3 }

      agentSwitchDot3FlowControlMode OBJECT-TYPE
           SYNTAX      INTEGER {
                       enable(1),
                       disable(2)
                    }
           MAX-ACCESS  read-write
           STATUS      current
           DESCRIPTION
                      "Config switchconfig flowcontrol allows you to enable or disable
                       802.3x flow control for the switch. This value
                       applies to only full-duplex mode ports. "
           DEFVAL { disable }
           ::= { agentStormContorlConfigGroupExtension 4 }

 
 	--**************************************************************************************
    -- Broadcast Table
    --
    --**************************************************************************************
 
  agentSwitchStormControlBroadcastTable OBJECT-TYPE
           SYNTAX      SEQUENCE OF AgentSwitchStormControlBroadcastEntry
           MAX-ACCESS  not-accessible
           STATUS      current
           DESCRIPTION
                       "The switch's storm control table"
           ::= { agentStormContorlConfigGroupExtension 10 }

      agentSwitchStormControlBroadcastEntry OBJECT-TYPE
           SYNTAX      AgentSwitchStormControlBroadcastEntry
           MAX-ACCESS  not-accessible
           STATUS      current
           DESCRIPTION
                       "storm control for a specific port."
           INDEX       { agentSwitchBcastStormIfIndex }
           ::= { agentSwitchStormControlBroadcastTable 1 }

      AgentSwitchStormControlBroadcastEntry ::=
           SEQUENCE {
               agentSwitchBcastStormIfIndex         	   Integer32,
               agentSwitchBcastStormExtensionPktRate       Unsigned32,
   			   agentSwitchBcastStormExtensionAdminMode     INTEGER
           }

      agentSwitchBcastStormIfIndex OBJECT-TYPE
           SYNTAX      Integer32 (0..2147483647)
           MAX-ACCESS  read-only
           STATUS      current
           DESCRIPTION
                       "Unique index of switch broadcast storm entry"
           ::= { agentSwitchStormControlBroadcastEntry 1 }

		   
        agentSwitchBcastStormExtensionPktRate OBJECT-TYPE
		   SYNTAX      Unsigned32 (1..14880000)
             MAX-ACCESS  read-write
             STATUS      current
             DESCRIPTION
                       "The Pkt rate, range is from 1 to 14880000."
		   DEFVAL { 4160 }
             ::= { agentSwitchStormControlBroadcastEntry 2 }


       agentSwitchBcastStormExtensionAdminMode OBJECT-TYPE
             SYNTAX  INTEGER {
                       enable(1),
                       disable(2)
                   }
             MAX-ACCESS  read-write
             STATUS      current
             DESCRIPTION
                         "enable/disable broadcast storm control"
             ::= { agentSwitchStormControlBroadcastEntry 3 }

		   
 	--**************************************************************************************
    -- Multicast Table
    --
    --**************************************************************************************


  agentSwitchStormControlMulticastTable OBJECT-TYPE
           SYNTAX      SEQUENCE OF AgentSwitchStormControlMulticastEntry
           MAX-ACCESS  not-accessible
           STATUS      current
           DESCRIPTION
                       "The switch's storm control table"
           ::= { agentStormContorlConfigGroupExtension 20 }

      agentSwitchStormControlMulticastEntry OBJECT-TYPE
           SYNTAX      AgentSwitchStormControlMulticastEntry
           MAX-ACCESS  not-accessible
           STATUS      current
           DESCRIPTION
                       "storm control for a specific port."
           INDEX       { agentSwitchMcastStormIfIndex }
           ::= { agentSwitchStormControlMulticastTable 1 }

      AgentSwitchStormControlMulticastEntry ::=
           SEQUENCE {
               agentSwitchMcastStormIfIndex                Integer32,
               agentSwitchMcastStormExtensionPktRate       Unsigned32,
   			   agentSwitchMcastStormExtensionAdminMode     INTEGER
           }

      agentSwitchMcastStormIfIndex OBJECT-TYPE
           SYNTAX      Integer32 (0..2147483647)
           MAX-ACCESS  read-only
           STATUS      current
           DESCRIPTION
                       "Unique index of switch Multicast storm entry"
           ::= { agentSwitchStormControlMulticastEntry 1 }

		   
       agentSwitchMcastStormExtensionPktRate OBJECT-TYPE
		   SYNTAX      Unsigned32 (1..14880000)
             MAX-ACCESS  read-write
             STATUS      current
             DESCRIPTION
                       "The Pkt rate, range is from 1 to 14880000."
		   DEFVAL { 4160 }
             ::= { agentSwitchStormControlMulticastEntry 2 }


       agentSwitchMcastStormExtensionAdminMode OBJECT-TYPE
             SYNTAX  INTEGER {
                       enable(1),
                       disable(2)
                   }
             MAX-ACCESS  read-write
             STATUS      current
             DESCRIPTION
                         "enable/disable Multicast storm control"
             ::= { agentSwitchStormControlMulticastEntry 3 }

		   
 	--**************************************************************************************
    -- Unicast Table
    --
    --**************************************************************************************

	agentSwitchStormControlUnicastTable OBJECT-TYPE
           SYNTAX      SEQUENCE OF AgentSwitchStormControlUnicastEntry
           MAX-ACCESS  not-accessible
           STATUS      current
           DESCRIPTION
                       "The switch's storm control table"
           ::= { agentStormContorlConfigGroupExtension 30 }

      agentSwitchStormControlUnicastEntry OBJECT-TYPE
           SYNTAX      AgentSwitchStormControlUnicastEntry
           MAX-ACCESS  not-accessible
           STATUS      current
           DESCRIPTION
                       "storm control for a specific port."
           INDEX       { agentSwitchUcastStormIfIndex }
           ::= { agentSwitchStormControlUnicastTable 1 }

      AgentSwitchStormControlUnicastEntry ::=
           SEQUENCE {
               agentSwitchUcastStormIfIndex                Integer32,
               agentSwitchUcastStormExtensionPktRate       Unsigned32,
   			   agentSwitchUcastStormExtensionAdminMode     INTEGER
           }
		   
      agentSwitchUcastStormIfIndex OBJECT-TYPE
           SYNTAX      Integer32 (0..2147483647)
           MAX-ACCESS  read-only
           STATUS      current
           DESCRIPTION
                       "Unique index of switch Unicast storm entry"
           ::= { agentSwitchStormControlUnicastEntry 1 }


       agentSwitchUcastStormExtensionPktRate OBJECT-TYPE
		   SYNTAX      Unsigned32 (1..14880000)
             MAX-ACCESS  read-write
             STATUS      current
             DESCRIPTION
                       "The Pkt rate, range is from 1 to 14880000."
		   DEFVAL { 4160 }
             ::= { agentSwitchStormControlUnicastEntry 2 }


       agentSwitchUcastStormExtensionAdminMode OBJECT-TYPE
             SYNTAX  INTEGER {
                       enable(1),
                       disable(2)
                   }
             MAX-ACCESS  read-write
             STATUS      current
             DESCRIPTION
                         "enable/disable ingress rate limit"
             ::= { agentSwitchStormControlUnicastEntry 3 }

		   
 	--**************************************************************************************
    -- FlowControl Table
    --
    --**************************************************************************************

	agentSwitchFlowControlTable OBJECT-TYPE
           SYNTAX      SEQUENCE OF AgentSwitchFlowControlEntry
           MAX-ACCESS  not-accessible
           STATUS      current
           DESCRIPTION
                       "The switch's storm control table"
           ::= { agentStormContorlConfigGroupExtension 40 }

      agentSwitchFlowControlEntry OBJECT-TYPE
           SYNTAX      AgentSwitchFlowControlEntry
           MAX-ACCESS  not-accessible
           STATUS      current
           DESCRIPTION
                       "storm control for a specific port."
           INDEX       { agentSwitchFlowControlIfIndex }
           ::= { agentSwitchFlowControlTable 1 }

      AgentSwitchFlowControlEntry ::=
           SEQUENCE {
               agentSwitchFlowControlIfIndex           Integer32,
               agentSwitchFlowControlAdminMode         INTEGER
           }

      agentSwitchFlowControlIfIndex OBJECT-TYPE
           SYNTAX      Integer32 (0..2147483647)
           MAX-ACCESS  read-only
           STATUS      current
           DESCRIPTION
                       "Unique index of switch FlowControl storm entry"
           ::= { agentSwitchFlowControlEntry 1 }
		   
   
     agentSwitchFlowControlAdminMode OBJECT-TYPE
           SYNTAX  INTEGER {
                     enable(1),
                     disable(2)
                 }
           MAX-ACCESS  read-write
           STATUS      current
           DESCRIPTION
                       "enable/disable FlowControl storm control"
           ::= { agentSwitchFlowControlEntry 2 }


 	--**************************************************************************************
    -- StormControlAction Table
    --
    --**************************************************************************************

	agentSwitchStormControlActionTable OBJECT-TYPE
           SYNTAX      SEQUENCE OF AgentSwitchStormControlActionEntry
           MAX-ACCESS  not-accessible
           STATUS      current
           DESCRIPTION
                       "The switch's storm control table"
           ::= { agentStormContorlConfigGroupExtension 50 }

      agentSwitchStormControlActionEntry OBJECT-TYPE
           SYNTAX      AgentSwitchStormControlActionEntry
           MAX-ACCESS  not-accessible
           STATUS      current
           DESCRIPTION
                       "storm control for a specific port."
           INDEX       { agentSwitchStormControlActionIfIndex }
           ::= { agentSwitchStormControlActionTable 1 }

      AgentSwitchStormControlActionEntry ::=
           SEQUENCE {
               agentSwitchStormControlActionIfIndex           Integer32,
               agentSwitchStormControlActionShutdownMode      INTEGER,
			   agentSwitchStormControlActionTrapMode          INTEGER
			   }

      agentSwitchStormControlActionIfIndex OBJECT-TYPE
           SYNTAX      Integer32 (0..2147483647)
           MAX-ACCESS  read-only
         STATUS      current
         DESCRIPTION
                       "Unique index of switch StormControlAction storm entry"
           ::= { agentSwitchStormControlActionEntry 1 }

         
    agentSwitchStormControlActionShutdownMode OBJECT-TYPE
         SYNTAX      INTEGER {
                     enable(1),
                     disable(2)
                  }
         MAX-ACCESS  read-write
         STATUS      current
         DESCRIPTION
                      "Shutdown this interface if a storm occurs."
           ::= { agentSwitchStormControlActionEntry 2 }	

		   
    agentSwitchStormControlActionTrapMode OBJECT-TYPE
         SYNTAX      INTEGER {
                     enable(1),
                     disable(2)
                  }
         MAX-ACCESS  read-write
         STATUS      current
         DESCRIPTION
                      "Send SNMP trap if a storm occurs."
           ::= { agentSwitchStormControlActionEntry 3 }	



    --**************************************************************************************
    -- errRecovery Table
    --
    --**************************************************************************************
	agentErrRecoveryConfigGroupExtension                      OBJECT IDENTIFIER ::= { agentSwitchConfigGroupExtension 28 }

      agentErrRecoveryInterval OBJECT-TYPE
         SYNTAX      Integer32 (30..86400)
         MAX-ACCESS  read-write
         STATUS      current
         DESCRIPTION
                     "Configure Recovery Timer Interval."
         DEFVAL {300}
         ::= { agentErrRecoveryConfigGroupExtension  1 }
	
      agentErrRecoveryStormCtrlCauseMode OBJECT-TYPE
         SYNTAX      INTEGER {
                     enable(1),
                     disable(2)
                  }
         MAX-ACCESS  read-write
         STATUS      current
         DESCRIPTION
                     "Enable/Disable timer to recover from storm-control error disable state."
         DEFVAL { disable }
         ::= { agentErrRecoveryConfigGroupExtension  2 }

      agentErrRecoveryUdldCauseMode OBJECT-TYPE
         SYNTAX      INTEGER {
                     enable(1),
                     disable(2)
                  }
         MAX-ACCESS  read-write
         STATUS      current
         DESCRIPTION
                     "Enable/Disable timer to recover from udld error disable state."
         DEFVAL { disable }
         ::= { agentErrRecoveryConfigGroupExtension  3 }
         
      agentErrRecoveryPortSecurityCauseMode OBJECT-TYPE
         SYNTAX      INTEGER {
                     enable(1),
                     disable(2)
                  }
         MAX-ACCESS  read-write
         STATUS      current
         DESCRIPTION
                     "Enable/Disable timer to recover from port-security error disable state."
         DEFVAL { disable }
         ::= { agentErrRecoveryConfigGroupExtension  4 }
		 
      agentErrRecoveryBpduCauseMode OBJECT-TYPE
         SYNTAX      INTEGER {
                     enable(1),
                     disable(2)
                  }
         MAX-ACCESS  read-write
         STATUS      current
         DESCRIPTION
                     "Enable/Disable timer to recover from bpdu error disable state."
         DEFVAL { disable }
         ::= { agentErrRecoveryConfigGroupExtension  5 }

      agentErrRecoveryLinkFlapCauseMode OBJECT-TYPE
         SYNTAX      INTEGER {
                     enable(1),
                     disable(2)
                  }
         MAX-ACCESS  read-write
         STATUS      current
         DESCRIPTION
                     "Enable/Disable timer to recover from link flap error disable state."
         DEFVAL { disable }
         ::= { agentErrRecoveryConfigGroupExtension  6 }

      agentErrRecoveryMacFlapCauseMode OBJECT-TYPE
         SYNTAX      INTEGER {
                     enable(1),
                     disable(2)
                  }
         MAX-ACCESS  read-write
         STATUS      current
         DESCRIPTION
                     "Enable/Disable timer to recover from MAC flap error disable state."
         DEFVAL { enable }
         ::= { agentErrRecoveryConfigGroupExtension  7 }

     agentErrDetectLinkFlapCauseMode OBJECT-TYPE
         SYNTAX      INTEGER {
                     enable(1),
                     disable(2)
                  }
         MAX-ACCESS  read-write
         STATUS      current
         DESCRIPTION
                      "Enable/Disable error disable detection for link flapping state."
         DEFVAL { enable }
         ::= { agentErrRecoveryConfigGroupExtension  8 }

      agentErrDetectMacFlapCauseMode OBJECT-TYPE
         SYNTAX      INTEGER {
                     enable(1),
                     disable(2)
                  }
         MAX-ACCESS  read-write
         STATUS      current
         DESCRIPTION
                     "Enable/Disable error disable detection for MAC flapping state."
         DEFVAL { enable }
         ::= { agentErrRecoveryConfigGroupExtension  9 }
         		 
    --**************************************************************************************
    -- Storm Control Table
    --
    --**************************************************************************************

--      agentSwitchBroadcastControlMode OBJECT-TYPE
--         SYNTAX      INTEGER {
--                     enable(1),
--                     disable(2)
--                  }
--         MAX-ACCESS  read-write
--         STATUS      current
--         DESCRIPTION
--                     "The switch config broadcast allows you to enable or disable
--                     broadcast storm recovery mode. When you specify Enable for Broadcast
--                     Storm Recovery and the broadcast traffic on any Ethernet port exceeds
--                     20 percent of the link speed, the switch blocks (discards) the broadcast
--                     traffic until the broadcast traffic returns to 10 percent or less.
--                     Upper limit for 10M link is 20% and lower limit is 10%.
--                     For 100M link Upper limit is 5% and lower limit is 2%"
--         DEFVAL { disable }
--         ::= { agentSwitchConfigGroupExtension  18 }

--      agentSwitchDot3FlowControlMode OBJECT-TYPE
--           SYNTAX      INTEGER {
--                       enable(1),
--                       disable(2)
--                    }
--           MAX-ACCESS  read-write
--           STATUS      current
--           DESCRIPTION
--                      "Config switchconfig flowcontrol allows you to enable or disable
--                       802.3x flow control for the switch. This value
--                       applies to only full-duplex mode ports. "
--           DEFVAL { disable }
--           ::= { agentSwitchConfigGroupExtension 19 }

--  agentSwitchStormControlExtensionTable OBJECT-TYPE
--           SYNTAX      SEQUENCE OF AgentSwitchStormControlExtensionEntry
--           MAX-ACCESS  not-accessible
--           STATUS      current
--           DESCRIPTION
--                       "The switch's storm control table"
--           ::= { agentSwitchConfigGroupExtension 20 }

--      agentSwitchStormControlExtensionEntry OBJECT-TYPE
--           SYNTAX      AgentSwitchStormControlExtensionEntry
--           MAX-ACCESS  not-accessible
--           STATUS      current
--           DESCRIPTION
--                       "storm control for a specific port."
--           INDEX       { agentSwitchStormControlExtensionIfIndex }
--           ::= { agentSwitchStormControlExtensionTable 1 }

--      AgentSwitchStormControlExtensionEntry ::=
--           SEQUENCE {
--               agentSwitchStormControlExtensionIfIndex         Integer32,
--               agentSwitchBcastStormExtensionPktRate           INTEGER,
--               agentSwitchBcastStormExtensionAdminMode         INTEGER,
--               agentSwitchMcastStormExtensionPktRate           INTEGER,
--               agentSwitchMcastStormExtensionAdminMode         INTEGER,
--               agentSwitchUcastStormExtensionPktRate           INTEGER,
--               agentSwitchUcastStormExtensionAdminMode         INTEGER,
--               agentSwitchFlowControlAdminMode	             INTEGER
--           }

--      agentSwitchStormControlExtensionIfIndex OBJECT-TYPE
--           SYNTAX      Integer32
--           MAX-ACCESS  read-only
--           STATUS      current
--           DESCRIPTION
--                       "Unique index of switch broadcast storm entry"
--           ::= { agentSwitchStormControlExtensionEntry 1 }


--      agentSwitchBcastStormExtensionPktRate OBJECT-TYPE
--           SYNTAX  INTEGER {
--                    level1(1),
--                    level2(2),
--                    level3(3),
--                    level4(4)
--           }
--           MAX-ACCESS  read-write
--           STATUS      current
--           DESCRIPTION
--                       "set the packet rate thresholds for broadcast storm control. Note that
--                       level1 represents 64 PPS for 10M/100M/1G interfaces, and 1042 PPS for 10G interfaces;
--                       level2 represents 128 PPS for 10M/100M/1G interfaces, and 2084 PPS for 10G interfaces;
--                       level3 represents 256 PPS for 10M/100M/1G interfaces, and 3124 PPS for 10G interfaces;
--                       level4 represents 512 PPS for 10M/100M/1G interfaces, and 4167 PPS for 10G interfaces."
--           ::= { agentSwitchStormControlExtensionEntry 2 }


--     agentSwitchBcastStormExtensionAdminMode OBJECT-TYPE
--           SYNTAX  INTEGER {
--                     enable(1),
--                     disable(2)
--                 }
--           MAX-ACCESS  read-write
--           STATUS      current
--           DESCRIPTION
--                       "enable/disable broadcast storm control"
--           ::= { agentSwitchStormControlExtensionEntry 3 }

--     agentSwitchMcastStormExtensionPktRate OBJECT-TYPE
--           SYNTAX  INTEGER {
--                    level1(1),
--                    level2(2),
--                    level3(3),
--                    level4(4)
--           }
--           MAX-ACCESS  read-write
--           STATUS      current
--           DESCRIPTION
--                       "set the packet rate thresholds for multicast storm control. Note that
--                       level1 represents 64 PPS for 10M/100M/1G interfaces, and 1042 PPS for 10G interfaces;
--                       level2 represents 128 PPS for 10M/100M/1G interfaces, and 2084 PPS for 10G interfaces;
--                       level3 represents 256 PPS for 10M/100M/1G interfaces, and 3124 PPS for 10G interfaces;
--                       level4 represents 512 PPS for 10M/100M/1G interfaces, and 4167 PPS for 10G interfaces."
--           ::= { agentSwitchStormControlExtensionEntry 4 }


--     agentSwitchMcastStormExtensionAdminMode OBJECT-TYPE
--           SYNTAX  INTEGER {
--                     enable(1),
--                     disable(2)
--                 }
--           MAX-ACCESS  read-write
--           STATUS      current
--           DESCRIPTION
--                       "enable/disable Multicast storm control"
--           ::= { agentSwitchStormControlExtensionEntry 5 }

--     agentSwitchUcastStormExtensionPktRate OBJECT-TYPE
--           SYNTAX  INTEGER {
--                    level1(1),
--                    level2(2),
--                    level3(3),
--                    level4(4)
--           }
--           MAX-ACCESS  read-write
--           STATUS      current
--           DESCRIPTION
--                       "set the packet rate thresholds for unicast storm control. Note that
--                       level1 represents 64 PPS for 10M/100M/1G interfaces, and 1042 PPS for 10G interfaces;
--                       level2 represents 128 PPS for 10M/100M/1G interfaces, and 2084 PPS for 10G interfaces;
--                       level3 represents 256 PPS for 10M/100M/1G interfaces, and 3124 PPS for 10G interfaces;
--                       level4 represents 512 PPS for 10M/100M/1G interfaces, and 4167 PPS for 10G interfaces."
--           ::= { agentSwitchStormControlExtensionEntry 6 }


--     agentSwitchUcastStormExtensionAdminMode OBJECT-TYPE
--           SYNTAX  INTEGER {
--                     enable(1),
--                     disable(2)
--                 }
--           MAX-ACCESS  read-write
--           STATUS      current
--           DESCRIPTION
--                       "enable/disable ingress rate limit"
--           ::= { agentSwitchStormControlExtensionEntry 7 }


--     agentSwitchFlowControlAdminMode OBJECT-TYPE
--           SYNTAX  INTEGER {
--                     enable(1),
--                     disable(2)
--                 }
--           MAX-ACCESS  read-write
--           STATUS      current
--           DESCRIPTION
--                       "enable/disable flow control"
--           ::= { agentSwitchStormControlExtensionEntry 8 }

--      agentSwitchMulticastControlMode OBJECT-TYPE
--         SYNTAX      INTEGER {
--                     enable(1),
--                     disable(2)
--                  }
--         MAX-ACCESS  read-write
--         STATUS      current
--         DESCRIPTION
--                     "The switch config multicast allows you to enable or disable
--                     multicast storm recovery mode. When you specify Enable for Multicast
--                     Storm Recovery and the multicast traffic on any Ethernet port exceeds
--                     20 percent of the link speed, the switch blocks (discards) the multicast
--                     traffic until the multicast traffic returns to 10 percent or less.
--                     Upper limit for 10M link is 20% and lower limit is 10%.
--                     For 100M link Upper limit is 5% and lower limit is 2%"
--         DEFVAL { disable }
--         ::= { agentSwitchConfigGroupExtension  21 }
         
--      agentSwitchUnicastControlMode OBJECT-TYPE
--         SYNTAX      INTEGER {
--                     enable(1),
--                     disable(2)
--                  }
--         MAX-ACCESS  read-write
--         STATUS      current
--         DESCRIPTION
--                     "The switch config unicast allows you to enable or disable
--                     unicast storm recovery mode. When you specify Enable for unicast
--                     Storm Recovery and the unicast traffic on any Ethernet port exceeds
--                     20 percent of the link speed, the switch blocks (discards) the unicast
--                     traffic until the unicast traffic returns to 10 percent or less.
--                     Upper limit for 10M link is 20% and lower limit is 10%.
--                     For 100M link Upper limit is 5% and lower limit is 2%"
--         DEFVAL { disable }
--         ::= { agentSwitchConfigGroupExtension  22 }		 
		   

    --**************************************************************************************
    -- Rate Limit Table
    --
    --**************************************************************************************



--agentSwitchRateLimitTable OBJECT-TYPE
--         SYNTAX      SEQUENCE OF AgentSwitchRateLimitEntry
--         MAX-ACCESS  not-accessible
--         STATUS      current
--         DESCRIPTION
--                     "The switch's Rate Limit table"
--         ::= { agentSwitchConfigGroupExtension 22 }

--    agentSwitchRateLimitEntry OBJECT-TYPE
--         SYNTAX      AgentSwitchRateLimitEntry
--         MAX-ACCESS  not-accessible
--         STATUS      current
--         DESCRIPTION
--                     "Rate Limit for a specific port."
--         INDEX       { agentSwitchRateLimitIfIndex }
--         ::= { agentSwitchRateLimitTable 1 }

--    AgentSwitchRateLimitEntry ::=
--         SEQUENCE {
--             agentSwitchRateLimitIfIndex           Integer32,
--             agentSwitchRateLimitPktRate           Integer32,
--             agentSwitchRateLimitAdminMode         INTEGER
--         }

--    agentSwitchRateLimitIfIndex OBJECT-TYPE
--         SYNTAX      Integer32
--         MAX-ACCESS  read-only
--         STATUS      current
--         DESCRIPTION
--                     "Unique index of rate limit entry"
--         ::= { agentSwitchRateLimitEntry 1 }

--    agentSwitchRateLimitPktRate OBJECT-TYPE
--         SYNTAX  Integer32(1..1000)
--         MAX-ACCESS  read-write
--         STATUS      current
--         DESCRIPTION
--                     "set the percentage thresholds for Rate Limit"
--         ::= { agentSwitchRateLimitEntry 2 }


--    agentSwitchRateLimitAdminMode OBJECT-TYPE
--         SYNTAX  INTEGER {
--                   enable(1),
--                   disable(2)
--               }
--         MAX-ACCESS  read-write
--         STATUS      current
--         DESCRIPTION
--                     "set the admin mode for Rate Limit"
--         ::= { agentSwitchRateLimitEntry 4 }

    --**************************************************************************************
    -- agentPortConfigExtensionTable
    --
    --**************************************************************************************

agentPortConfigExtensionTable OBJECT-TYPE
         SYNTAX      SEQUENCE OF AgentPortConfigExtensionEntry
         MAX-ACCESS  not-accessible
         STATUS      current
         DESCRIPTION
                     "The switch's port capability table"
         ::= { agentConfigGroupExtension 13 }

    agentPortConfigExtensionEntry OBJECT-TYPE
         SYNTAX      AgentPortConfigExtensionEntry
         MAX-ACCESS  not-accessible
         STATUS      current
         DESCRIPTION
                     "port capability setting for a specific port."
         INDEX       { agentPortConfigExtensionIfIndex }
         ::= { agentPortConfigExtensionTable 1 }

    AgentPortConfigExtensionEntry ::=
         SEQUENCE {
             agentPortConfigExtensionIfIndex                Integer32,
             agentPortConfigExtensionAdminMode              INTEGER,
             agentPortConfigExtensionLinkTrapMode           INTEGER,
             agentPortConfigExtensionClearStats             INTEGER,
             agentPortConfigExtensionMaxFrameSizeLimit      Integer32,
             agentPortConfigExtensionMaxFrameSize           Integer32
         }

    agentPortConfigExtensionIfIndex OBJECT-TYPE
         SYNTAX      Integer32 (0..2147483647)
         MAX-ACCESS  read-only
         STATUS      current
         DESCRIPTION
                     "port index used to uniquelly identify an entry of the port capability Table"
         ::= { agentPortConfigExtensionEntry 1 }

    agentPortConfigExtensionAdminMode OBJECT-TYPE
         SYNTAX      INTEGER {
                     enable(1),
                     disable(2)
                 }
         MAX-ACCESS  read-write
         STATUS      current
         DESCRIPTION
                     "The switch's Port Admin Mode"
         ::= { agentPortConfigExtensionEntry 6 }

    agentPortConfigExtensionLinkTrapMode OBJECT-TYPE
         SYNTAX      INTEGER {
                     enable(1),
                     disable(2)
                  }
         MAX-ACCESS  read-write
         STATUS      current
         DESCRIPTION
                     "If enabled, link up and link down traps will be sent for this port."
         ::= { agentPortConfigExtensionEntry 9 }

     agentPortConfigExtensionClearStats OBJECT-TYPE
         SYNTAX      INTEGER {
                     enable(1),
                     disable(2)
                  }
         MAX-ACCESS  read-write
         STATUS      current
         DESCRIPTION
                     "clear stats for this port only"
         ::= { agentPortConfigExtensionEntry 10 }

    agentPortConfigExtensionMaxFrameSizeLimit OBJECT-TYPE
         SYNTAX      Integer32 (1518..12288)
         MAX-ACCESS  read-only
         STATUS      current
         DESCRIPTION
                     "This object identifies the largest value that can be
                     configured for agentPortConfigExtensionMaxFrameSize"
         ::= { agentPortConfigExtensionEntry 18 }

    agentPortConfigExtensionMaxFrameSize OBJECT-TYPE
         SYNTAX      Integer32 (1518..12288)
         MAX-ACCESS  read-write
         STATUS      current
         DESCRIPTION
                     "This object identifies the currently configured maximum frame size
                     value for this port. The maximmum value that this object can be set
                     to is the value of agentPortConfigExtensionMaxFrameSizeLimit.  For Ethernet ports
                     which support 802.1Q vlan tagging, the minimum value that this object
                     can be set to is 1522"
         ::= { agentPortConfigExtensionEntry 19 }

    --**************************************************************************************
    -- agentClassOfServiceGroupExtension
    --
    --**************************************************************************************

--agentClassOfServiceGroupExtension                    OBJECT IDENTIFIER ::= { agentConfigGroupExtension 17 }

--agentQueueBandwidthTable OBJECT-TYPE
--         SYNTAX      SEQUENCE OF AgentQueueBandwidthEntry
--         MAX-ACCESS  not-accessible
--         STATUS      current
--         DESCRIPTION
--                     "The switch port's queue bandwidth"
--         ::= { agentClassOfServiceGroupExtension 100 }

--    agentQueueBandwidthEntry OBJECT-TYPE
--         SYNTAX      AgentQueueBandwidthEntry
--         MAX-ACCESS  not-accessible
--         STATUS      current
--         DESCRIPTION
--                     "queue bandwidth setting for a specific port."
--         INDEX       { agentQueueBandwidthIfIndex }
--         ::= { agentQueueBandwidthTable 1 }

--    AgentQueueBandwidthEntry ::=
--         SEQUENCE {
--             agentQueueBandwidthIfIndex           Integer32,
--             agentQueueBandwidthQueue1            Integer32,
--             agentQueueBandwidthQueue2            Integer32,
--             agentQueueBandwidthQueue3            Integer32,
--             agentQueueBandwidthQueue4            Integer32,
--             agentQueueBandwidthResetWeight       INTEGER
--         }

--    agentQueueBandwidthIfIndex OBJECT-TYPE
--         SYNTAX      Integer32
--         MAX-ACCESS  read-only
--         STATUS      current
--         DESCRIPTION
--                     "port index used to uniquelly identify an entry of the queue bandwidth Table"
--         ::= { agentQueueBandwidthEntry 1 }


--    agentQueueBandwidthQueue1  OBJECT-TYPE
--         SYNTAX      Integer32 (1..8)
--         MAX-ACCESS  read-write
--         STATUS      current
--         DESCRIPTION
--                     "bandwidth priority for queue 1. "
--         ::= { agentQueueBandwidthEntry 2 }

--    agentQueueBandwidthQueue2  OBJECT-TYPE
--         SYNTAX      Integer32 (1..8)
--         MAX-ACCESS  read-write
--         STATUS      current
--         DESCRIPTION
--                     "bandwidth priority for queue 2. "
--         ::= { agentQueueBandwidthEntry 3 }

--    agentQueueBandwidthQueue3  OBJECT-TYPE
--         SYNTAX      Integer32 (1..8)
--         MAX-ACCESS  read-write
--         STATUS      current
--         DESCRIPTION
--                     "bandwidth priority for queue 3. "
--         ::= { agentQueueBandwidthEntry 4 }

--    agentQueueBandwidthQueue4  OBJECT-TYPE
--         SYNTAX      Integer32 (1..8)
--         MAX-ACCESS  read-write
--         STATUS      current
--         DESCRIPTION
--                     "bandwidth priority for queue 4. "
--         ::= { agentQueueBandwidthEntry 5 }

--    agentQueueBandwidthResetWeight OBJECT-TYPE
--         SYNTAX  INTEGER {
--                   enable(1),
--                   disable(2)
--               }
--         MAX-ACCESS  read-write
--         STATUS      current
--         DESCRIPTION
--                     "Enable to reset this interface's queue bandwidth weight to the default value"
--         ::= { agentQueueBandwidthEntry 6 }



    --**************************************************************************************
    -- agentSwitchConfigGroupExtension
    --
    --**************************************************************************************


--      agentSwitchIGMPSnoopingGroupExtension  OBJECT IDENTIFIER ::= { agentSwitchConfigGroupExtension 6 }
      agentSwitchSnoopingGroupExtension  OBJECT IDENTIFIER ::= { agentSwitchConfigGroupExtension 6 }

--    agentSwitchIGMPSnoopingQuerierAdminMode OBJECT-TYPE
--         SYNTAX      INTEGER {
--                     enable(1),
--                     disable(2)
--                  }
--         MAX-ACCESS  read-write
--         STATUS      current
--         DESCRIPTION
--                     "enable/disable administration of IGMP querier. Please enable agentSwitchIGMPSnoopingAdminMode
--                     before setting agentSwitchIGMPSnoopingQuerierAdminMode to enable "
--         DEFVAL { disable }
--         ::= { agentSwitchIGMPSnoopingGroupExtension 101 }


     	-- *****************************************************************
     	-- RouterCurrentTable
     	--
     	-- *****************************************************************

--     	agentIgmpSnoopRouterCurrentTable OBJECT-TYPE
--     	  SYNTAX  SEQUENCE OF AgentIgmpSnoopRouterCurrentEntry
--     	  MAX-ACCESS  not-accessible
--     	  STATUS      current
--     	  DESCRIPTION
--     	  "Table for current router ports."
--     	::= { agentSwitchIGMPSnoopingGroupExtension 105  }
--
--
--     	agentIgmpSnoopRouterCurrentEntry OBJECT-TYPE
--     	  SYNTAX  AgentIgmpSnoopRouterCurrentEntry
--     	  MAX-ACCESS  not-accessible
--     	  STATUS      current
--     	  DESCRIPTION
--     	  "Entry for current router ports."
--     	  INDEX { agentIgmpSnoopRouterCurrentVlanIndex }
--     	::= { agentIgmpSnoopRouterCurrentTable 1  }
--
--
--     	AgentIgmpSnoopRouterCurrentEntry ::= SEQUENCE {
--     	  agentIgmpSnoopRouterCurrentVlanIndex Unsigned32,
--     	  agentIgmpSnoopRouterCurrentPorts OCTET STRING (SIZE(0..255)),
--     	  agentIgmpSnoopRouterCurrentStatus OCTET STRING (SIZE(0..255))
--     	}
--
--     	agentIgmpSnoopRouterCurrentVlanIndex OBJECT-TYPE
--     	  SYNTAX  Unsigned32
--     	  MAX-ACCESS  read-only
--     	  STATUS      current
--     	  DESCRIPTION
--     	  "This is defined as dot1qVlanIndex in the Q-BRIDGE-MIB."
--     	::= { agentIgmpSnoopRouterCurrentEntry 1  }
--
--     	agentIgmpSnoopRouterCurrentPorts OBJECT-TYPE
--     	  SYNTAX  OCTET STRING (SIZE(0..255))
--     	  MAX-ACCESS  read-only
--     	  STATUS      current
--     	  DESCRIPTION
--     	  "The set of ports which are current router ports.
--     	   Within this list, some router ports are static router ports.
--     	   Please refer to igmpSnoopRouterStaticTable."
--     	::= { agentIgmpSnoopRouterCurrentEntry 2  }
--
--     	agentIgmpSnoopRouterCurrentStatus OBJECT-TYPE
--     	  SYNTAX  OCTET STRING (SIZE(0..255))
--     	  MAX-ACCESS  read-only
--     	  STATUS      current
--     	  DESCRIPTION
--     	  "The set of ports which are static router ports."
--     	::= { agentIgmpSnoopRouterCurrentEntry 3  }


     	-- *****************************************************************
     	-- RouterStaticTable
     	--
     	-- *****************************************************************

--     	agentIgmpSnoopRouterStaticTable OBJECT-TYPE
--     	  SYNTAX  SEQUENCE OF AgentIgmpSnoopRouterStaticEntry
--     	  MAX-ACCESS  not-accessible
--     	  STATUS      current
--     	  DESCRIPTION
--     	  "Table for static router ports."
--     	::= { agentSwitchIGMPSnoopingGroupExtension 108  }
--
--
--     	agentIgmpSnoopRouterStaticEntry OBJECT-TYPE
--     	  SYNTAX  AgentIgmpSnoopRouterStaticEntry
--     	  MAX-ACCESS  not-accessible
--     	  STATUS      current
--     	  DESCRIPTION
--     	  "Entry for static router ports."
--     	  INDEX { agentIgmpSnoopRouterStaticVlanIndex }
--     	::= { agentIgmpSnoopRouterStaticTable 1  }
--
--
--     	AgentIgmpSnoopRouterStaticEntry ::= SEQUENCE {
--     	  agentIgmpSnoopRouterStaticVlanIndex Unsigned32,
--     	  agentIgmpSnoopRouterStaticPorts OCTET STRING (SIZE(0..255)),
--     	  agentIgmpSnoopRouterStaticStatus INTEGER
--     	}
--
--     	agentIgmpSnoopRouterStaticVlanIndex OBJECT-TYPE
--     	  SYNTAX  Unsigned32
--     	  MAX-ACCESS  read-only
--     	  STATUS      current
--     	  DESCRIPTION
--     	  "index of static router ports table"
--     	::= { agentIgmpSnoopRouterStaticEntry 1  }
--
--     	agentIgmpSnoopRouterStaticPorts OBJECT-TYPE
--     	  SYNTAX  OCTET STRING (SIZE(0..255))
--     	  MAX-ACCESS  read-only
--     	  STATUS      current
--     	  DESCRIPTION
--     	  "The set of ports which are static router ports."
--     	::= { agentIgmpSnoopRouterStaticEntry 2  }
--
--     	agentIgmpSnoopRouterStaticStatus OBJECT-TYPE
--     	  SYNTAX  INTEGER {
--                valid(1),
--                invalid(4)
--            }
--     	  MAX-ACCESS  read-only
--     	  STATUS      current
--     	  DESCRIPTION
--     	  "status all static router ports."
--     	::= { agentIgmpSnoopRouterStaticEntry 3  }


     	-- *****************************************************************
     	-- MulticastCurrentTable
     	--
     	-- *****************************************************************

--     	agentIgmpSnoopMulticastCurrentTable OBJECT-TYPE
--     	  SYNTAX  SEQUENCE OF AgentIgmpSnoopMulticastCurrentEntry
--     	  MAX-ACCESS  not-accessible
--     	  STATUS      current
--     	  DESCRIPTION
--     	  "Table for current multicast addresses."
--     	::= { agentSwitchIGMPSnoopingGroupExtension 110  }
--
--
--     	agentIgmpSnoopMulticastCurrentEntry OBJECT-TYPE
--     	  SYNTAX  AgentIgmpSnoopMulticastCurrentEntry
--     	  MAX-ACCESS  not-accessible
--     	  STATUS      current
--     	  DESCRIPTION
--     	  "Entry for current multicast addresses."
--     	  INDEX { agentIgmpSnoopMulticastCurrentVlanIndex, agentIgmpSnoopMulticastCurrentMacAddress }
--     	::= { agentIgmpSnoopMulticastCurrentTable 1  }
--
--
--     	AgentIgmpSnoopMulticastCurrentEntry ::= SEQUENCE {
--     	  agentIgmpSnoopMulticastCurrentVlanIndex Unsigned32,
--     	  agentIgmpSnoopMulticastCurrentMacAddress MacAddress,
--     	  agentIgmpSnoopMulticastCurrentPorts OCTET STRING (SIZE(0..255)),
--     	  agentIgmpSnoopMulticastCurrentStatus OCTET STRING (SIZE(0..255))
--     	}
--
--     	agentIgmpSnoopMulticastCurrentVlanIndex OBJECT-TYPE
--     	  SYNTAX  Unsigned32
--     	  MAX-ACCESS  read-only
--     	  STATUS      current
--     	  DESCRIPTION
--     	  "This is defined as dot1qVlanIndex in the Q-BRIDGE-MIB."
--     	::= { agentIgmpSnoopMulticastCurrentEntry 1  }
--
--     	agentIgmpSnoopMulticastCurrentMacAddress OBJECT-TYPE
--     	  SYNTAX  MacAddress
--     	  MAX-ACCESS  read-only
--     	  STATUS      current
--     	  DESCRIPTION
--     	  "IP address of multicast group."
--     	::= { agentIgmpSnoopMulticastCurrentEntry 2  }
--
--     	agentIgmpSnoopMulticastCurrentPorts OBJECT-TYPE
--     	  SYNTAX  OCTET STRING (SIZE(0..255))
--     	  MAX-ACCESS  read-only
--     	  STATUS      current
--     	  DESCRIPTION
--     	  "The set of ports which are members."
--     	::= { agentIgmpSnoopMulticastCurrentEntry 3  }
--
--     	agentIgmpSnoopMulticastCurrentStatus OBJECT-TYPE
--     	  SYNTAX  OCTET STRING (SIZE(0..255))
--     	  MAX-ACCESS  read-only
--     	  STATUS      current
--     	  DESCRIPTION
--     	  "The set of ports which are static members."
--     	::= { agentIgmpSnoopMulticastCurrentEntry 4  }


--*****************************************************************
-- For Snooping L2 Multicast Static (Integrated Version), 20080507
--*****************************************************************
     	-- *****************************************************************
     	-- IGMP L2 Multicast Static Table
     	--
     	-- *****************************************************************

     	agentIgmpSnoopL2MulticastStaticTable OBJECT-TYPE
     	  SYNTAX  SEQUENCE OF AgentIgmpSnoopL2MulticastStaticEntry
     	  MAX-ACCESS  not-accessible
     	  STATUS      current
     	  DESCRIPTION
     	              "Table for IGMP snooping static multicast addresses."
     	  ::= { agentSwitchSnoopingGroupExtension 112  }


     	agentIgmpSnoopL2MulticastStaticEntry OBJECT-TYPE
     	  SYNTAX  AgentIgmpSnoopL2MulticastStaticEntry
     	  MAX-ACCESS  not-accessible
     	  STATUS      current
     	  DESCRIPTION
     	              "Entry for static multicast addresses."
     	  INDEX { agentIgmpSnoopL2MulticastStaticIndex }
     	  ::= { agentIgmpSnoopL2MulticastStaticTable 1  }


     	AgentIgmpSnoopL2MulticastStaticEntry ::= SEQUENCE {
     	  agentIgmpSnoopL2MulticastStaticIndex Unsigned32,
     	  agentIgmpSnoopL2MulticastStaticVlanId Unsigned32,
     	  agentIgmpSnoopL2MulticastStaticMacAddress MacAddress,
          agentIgmpSnoopL2MulticastStaticMemberPortMask AgentPortMask,
          agentIgmpSnoopL2MulticastStaticActivePortMask AgentPortMask,
     	  agentIgmpSnoopL2MulticastStaticMemberPorts OCTET STRING,
     	  agentIgmpSnoopL2MulticastStaticActivePorts OCTET STRING
     	}

     	agentIgmpSnoopL2MulticastStaticIndex OBJECT-TYPE
          SYNTAX      Unsigned32
     	  MAX-ACCESS  read-only
     	  STATUS      current
     	  DESCRIPTION
     	              "Unique index of agentIgmpSnoopL2MulticastStaticEntry."
     	  ::= { agentIgmpSnoopL2MulticastStaticEntry 1  }

     	agentIgmpSnoopL2MulticastStaticVlanId OBJECT-TYPE
     	  SYNTAX  Unsigned32
     	  MAX-ACCESS  read-only
     	  STATUS      current
     	  DESCRIPTION
     	              "This is defined as dot1qVlanIndex in the Q-BRIDGE-MIB."
     	  ::= { agentIgmpSnoopL2MulticastStaticEntry 2 }

     	agentIgmpSnoopL2MulticastStaticMacAddress OBJECT-TYPE
     	  SYNTAX  MacAddress
     	  MAX-ACCESS  read-only
     	  STATUS      current
     	  DESCRIPTION
     	              "MAC address of multicast group."
     	  ::= { agentIgmpSnoopL2MulticastStaticEntry 3 }

        agentIgmpSnoopL2MulticastStaticMemberPortMask OBJECT-TYPE
          SYNTAX      AgentPortMask
          MAX-ACCESS  read-only
          STATUS      current
          DESCRIPTION
                      "IGMP Snooping L2 Multicast Static Port Mask."
          DEFVAL { '000000000000'H }
          ::= { agentIgmpSnoopL2MulticastStaticEntry 4 }

        agentIgmpSnoopL2MulticastStaticActivePortMask OBJECT-TYPE
          SYNTAX      AgentPortMask
          MAX-ACCESS  read-only
          STATUS      current
          DESCRIPTION
                      "IGMP Snooping L2 Multicast Static Active Port Mask."
          DEFVAL { '000000000000'H }
          ::= { agentIgmpSnoopL2MulticastStaticEntry 5 }

     	agentIgmpSnoopL2MulticastStaticMemberPorts OBJECT-TYPE
     	  SYNTAX  OCTET STRING (SIZE(0..255))
     	  MAX-ACCESS  read-create
     	  STATUS      current
     	  DESCRIPTION
     	              "The set of ports which are members. (2,3) means port 2 and port 3 are Multicast Static Ports."
     	  ::= { agentIgmpSnoopL2MulticastStaticEntry 6 }

     	agentIgmpSnoopL2MulticastStaticActivePorts OBJECT-TYPE
     	  SYNTAX  OCTET STRING (SIZE(0..255))
     	  MAX-ACCESS  read-only
     	  STATUS      current
     	  DESCRIPTION
     	              "The set of ports which are active. (2,3) means port 2 and port 3 are active."
     	  ::= { agentIgmpSnoopL2MulticastStaticEntry 7 }

     	-- *****************************************************************
     	-- MLD Multicast Static Table
     	--
     	-- *****************************************************************

     	agentMldSnoopL2MulticastStaticTable OBJECT-TYPE
     	  SYNTAX  SEQUENCE OF AgentMldSnoopL2MulticastStaticEntry
     	  MAX-ACCESS  not-accessible
     	  STATUS      current
     	  DESCRIPTION
     	              "Table for MLD snooping static multicast addresses."
     	  ::= { agentSwitchSnoopingGroupExtension 113  }


     	agentMldSnoopL2MulticastStaticEntry OBJECT-TYPE
     	  SYNTAX  AgentMldSnoopL2MulticastStaticEntry
     	  MAX-ACCESS  not-accessible
     	  STATUS      current
     	  DESCRIPTION
     	              "Entry for static multicast addresses."
     	  INDEX { agentMldSnoopL2MulticastStaticIndex }
     	  ::= { agentMldSnoopL2MulticastStaticTable 1  }


     	AgentMldSnoopL2MulticastStaticEntry ::= SEQUENCE {
     	  agentMldSnoopL2MulticastStaticIndex Unsigned32,
     	  agentMldSnoopL2MulticastStaticVlanId Unsigned32,
     	  agentMldSnoopL2MulticastStaticMacAddress MacAddress,
          agentMldSnoopL2MulticastStaticMemberPortMask AgentPortMask,
          agentMldSnoopL2MulticastStaticActivePortMask AgentPortMask,
     	  agentMldSnoopL2MulticastStaticMemberPorts OCTET STRING,
     	  agentMldSnoopL2MulticastStaticActivePorts OCTET STRING
     	}

     	agentMldSnoopL2MulticastStaticIndex OBJECT-TYPE
          SYNTAX      Unsigned32
     	  MAX-ACCESS  read-only
     	  STATUS      current
     	  DESCRIPTION
     	              "Unique index of agentMldSnoopL2MulticastStaticEntry."
     	  ::= { agentMldSnoopL2MulticastStaticEntry 1  }

     	agentMldSnoopL2MulticastStaticVlanId OBJECT-TYPE
     	  SYNTAX  Unsigned32
     	  MAX-ACCESS  read-only
     	  STATUS      current
     	  DESCRIPTION
     	              "This is defined as dot1qVlanIndex in the Q-BRIDGE-MIB."
     	  ::= { agentMldSnoopL2MulticastStaticEntry 2 }

     	agentMldSnoopL2MulticastStaticMacAddress OBJECT-TYPE
     	  SYNTAX  MacAddress
     	  MAX-ACCESS  read-only
     	  STATUS      current
     	  DESCRIPTION
     	              "MAC address of multicast group."
     	  ::= { agentMldSnoopL2MulticastStaticEntry 3 }

        agentMldSnoopL2MulticastStaticMemberPortMask OBJECT-TYPE
          SYNTAX      AgentPortMask
          MAX-ACCESS  read-only
          STATUS      current
          DESCRIPTION
                      "MLD Snooping L2 Multicast Static Port Mask."
          DEFVAL { '000000000000'H }
          ::= { agentMldSnoopL2MulticastStaticEntry 4 }

        agentMldSnoopL2MulticastStaticActivePortMask OBJECT-TYPE
          SYNTAX      AgentPortMask
          MAX-ACCESS  read-only
          STATUS      current
          DESCRIPTION
                      "MLD Snooping L2 Multicast Static Active Port Mask."
          DEFVAL { '000000000000'H }
          ::= { agentMldSnoopL2MulticastStaticEntry 5 }

     	agentMldSnoopL2MulticastStaticMemberPorts OBJECT-TYPE
     	  SYNTAX  OCTET STRING (SIZE(0..255))
     	  MAX-ACCESS  read-create
     	  STATUS      current
     	  DESCRIPTION
     	              "The set of ports which are members. (2,3) means port 2 and port 3 are Multicast Static Ports."
     	  ::= { agentMldSnoopL2MulticastStaticEntry 6 }

     	agentMldSnoopL2MulticastStaticActivePorts OBJECT-TYPE
     	  SYNTAX  OCTET STRING (SIZE(0..255))
     	  MAX-ACCESS  read-only
     	  STATUS      current
     	  DESCRIPTION
     	              "The set of ports which are active. (2,3) means port 2 and port 3 are active."
     	  ::= { agentMldSnoopL2MulticastStaticEntry 7 }

--***********************************************


--**************************************************************************************
--    agentSwitchCurrBootFilesGroupExtension
--**************************************************************************************

agentSwitchCurrBootFilesGroupExtension                  OBJECT IDENTIFIER ::= { switchingExtension 103 }

agentSwitchCurrBootRomFileName OBJECT-TYPE
         SYNTAX      DisplayString (SIZE(0..30))
         MAX-ACCESS  read-write
         STATUS      current
         DESCRIPTION
                     "Current BootRom Filename. This is shown on vxWorks plateforms. "
         ::= { agentSwitchCurrBootFilesGroupExtension 1 }

agentSwitchCurrBootLoaderFileName OBJECT-TYPE
         SYNTAX      DisplayString
         MAX-ACCESS  read-only
         STATUS      current
         DESCRIPTION
                     "Current Boot Loader Filename. This is shown on vxWorks plateforms. "
         ::= { agentSwitchCurrBootFilesGroupExtension 3 }

agentSwitchCurrBootConfigFileName OBJECT-TYPE
         SYNTAX      DisplayString (SIZE(0..30))
         MAX-ACCESS  read-write
         STATUS      current
         DESCRIPTION
                     "Current configuration Filename "
         ::= { agentSwitchCurrBootFilesGroupExtension 5 }

agentSwitchCurrBootOpCodeFileName OBJECT-TYPE
         SYNTAX      DisplayString (SIZE(0..30))
         MAX-ACCESS  read-write
         STATUS      current
         DESCRIPTION
                     "Current Operation Code Filename "
         ::= { agentSwitchCurrBootFilesGroupExtension 7 }

agentSwitchCurrUBootFileName OBJECT-TYPE
         SYNTAX      DisplayString
         MAX-ACCESS  read-only
         STATUS      current
         DESCRIPTION
                     "Current UBoot Filename. This is shown on linux plateforms. "
         ::= { agentSwitchCurrBootFilesGroupExtension 9 }

agentSwitchCurrKernelFileName OBJECT-TYPE
         SYNTAX      DisplayString
         MAX-ACCESS  read-only
         STATUS      current
         DESCRIPTION
                     "Current Kernel Filename. This is shown on linux plateforms. "
         ::= { agentSwitchCurrBootFilesGroupExtension 11 }

agentSwitchCurrVMTracerFileName OBJECT-TYPE
         SYNTAX      DisplayString
         MAX-ACCESS  read-only
         STATUS      current
         DESCRIPTION
                     "Current VMTracer image Filename. This is shown on vmtracer supported L3 linux plateforms. "
         ::= { agentSwitchCurrBootFilesGroupExtension 12 }

    --**************************************************************************************
    --    agentLinkStateConfigGroup
    --**************************************************************************************

    agentLinkStateConfigGroup                      OBJECT IDENTIFIER ::= { switchingExtension 15 }

    agentLinkStateConfigAdminMode OBJECT-TYPE
         SYNTAX      INTEGER {
                     enable(1),
                     disable(2)
                  }
         MAX-ACCESS  read-write
         STATUS      current
         DESCRIPTION
                     "The administration mode of the Link state."
         ::= { agentLinkStateConfigGroup 1 }

    -- *****************************************************************
    --      agentLinkStateGroupTable
    -- *****************************************************************

    agentLinkStateGroupTable OBJECT-TYPE
         SYNTAX      SEQUENCE OF AgentLinkStateGroupEntry
         MAX-ACCESS  not-accessible
         STATUS      current
         DESCRIPTION
                     "This table includes entries for the status of
                      all currently configured Link state group."
         ::= { agentLinkStateConfigGroup 2 }

    agentLinkStateGroupEntry OBJECT-TYPE
         SYNTAX      AgentLinkStateGroupEntry
         MAX-ACCESS  not-accessible
         STATUS      current
         DESCRIPTION
                     "This table includes entries for the status of
                      all currently configured Link state group."
         INDEX       { agentLinkStateGroupId }
         ::= { agentLinkStateGroupTable 1 }

    AgentLinkStateGroupEntry ::= SEQUENCE {
         agentLinkStateGroupId
              Integer32,
         agentLinkStateGroupMode
              INTEGER,
         agentLinkStateGroupUpstreamPort
              DisplayString,
         agentLinkStateGroupDownstreamPort
              DisplayString,
         agentLinkStateGroupStatus
              RowStatus
         }

    agentLinkStateGroupId OBJECT-TYPE
         SYNTAX      Integer32 (1..6)
         MAX-ACCESS  read-only
         STATUS      current
         DESCRIPTION
                     "The id of the Link State group."
         ::= { agentLinkStateGroupEntry 1 }

    agentLinkStateGroupMode OBJECT-TYPE
         SYNTAX      INTEGER {
                     enable(1),
                     disable(2)
                  }
         MAX-ACCESS  read-write
         STATUS      current
         DESCRIPTION
                     "The mode of this Link State group."
         ::= { agentLinkStateGroupEntry 2 }

    agentLinkStateGroupUpstreamPort OBJECT-TYPE
         SYNTAX      DisplayString
         MAX-ACCESS  read-write
         STATUS      current
         DESCRIPTION
                     "The up stream port of the Link State group."
         ::= { agentLinkStateGroupEntry 3 }

    agentLinkStateGroupDownstreamPort OBJECT-TYPE
         SYNTAX      DisplayString
         MAX-ACCESS  read-write
         STATUS      current
         DESCRIPTION
                     "The down stream port of the Link State group."
         ::= { agentLinkStateGroupEntry 4 }

    agentLinkStateGroupStatus OBJECT-TYPE
         SYNTAX      RowStatus
         MAX-ACCESS  read-create
         STATUS      current
         DESCRIPTION
                     "The status of Link State group.
                     active(1)  - This group setting is active.
                     createAndGo(4) -  Set to this value to create a new group.
                     destroy(6) - Set to this value to remove this group."
         ::= { agentLinkStateGroupEntry 5 }


    --**************************************************************************************
    --    agentPortBackupConfigGroup
    --**************************************************************************************

    agentPortBackupConfigGroup                      OBJECT IDENTIFIER ::= { switchingExtension 16 }

    agentPortBackupConfigAdminMode OBJECT-TYPE
         SYNTAX      INTEGER {
                     enable(1),
                     disable(2)
                  }
         MAX-ACCESS  read-write
         STATUS      current
         DESCRIPTION
                     "The administration mode of the Port-backup."
         ::= { agentPortBackupConfigGroup 1 }

    -- *****************************************************************
    --      agentPortBackupGroupTable
    -- *****************************************************************

    agentPortBackupGroupTable OBJECT-TYPE
         SYNTAX      SEQUENCE OF AgentPortBackupGroupEntry
         MAX-ACCESS  not-accessible
         STATUS      current
         DESCRIPTION
                     "This table includes entries for the status of
                      all currently configured Port-backup group."
         ::= { agentPortBackupConfigGroup 2 }

    agentPortBackupGroupEntry OBJECT-TYPE
         SYNTAX      AgentPortBackupGroupEntry
         MAX-ACCESS  not-accessible
         STATUS      current
         DESCRIPTION
                     "This table includes entries for the status of
                      all currently configured Port-backup group."
         INDEX       { agentPortBackupGroupId }
         ::= { agentPortBackupGroupTable 1 }

    AgentPortBackupGroupEntry ::= SEQUENCE {
         agentPortBackupGroupId
              Integer32,
         agentPortBackupGroupMode
              INTEGER,
         agentPortBackupGroupActivePort
              DisplayString,
         agentPortBackupGroupBackupPort
              DisplayString,
         agentMacMoveUpdatetMode
              INTEGER,
         agentPortBackupGroupStatus
              RowStatus,
         agentPortBackupGroupFailBackTime
              Integer32
         }

    agentPortBackupGroupId OBJECT-TYPE
         SYNTAX      Integer32 (1..6)
         MAX-ACCESS  read-only
         STATUS      current
         DESCRIPTION
                     "The id of the Port-backup group."
         ::= { agentPortBackupGroupEntry 1 }

    agentPortBackupGroupMode OBJECT-TYPE
         SYNTAX      INTEGER {
                     enable(1),
                     disable(2)
                  }
         MAX-ACCESS  read-write
         STATUS      current
         DESCRIPTION
                     "The mode of this Port-backup group."
         ::= { agentPortBackupGroupEntry 2 }

    agentPortBackupGroupActivePort OBJECT-TYPE
         SYNTAX      DisplayString
         MAX-ACCESS  read-write
         STATUS      current
         DESCRIPTION
                     "The active port of the Port-backup group."
         ::= { agentPortBackupGroupEntry 3 }

    agentPortBackupGroupBackupPort OBJECT-TYPE
         SYNTAX      DisplayString
         MAX-ACCESS  read-write
         STATUS      current
         DESCRIPTION
                     "The backup port of the Port-backup group."
         ::= { agentPortBackupGroupEntry 4 }

    agentMacMoveUpdatetMode OBJECT-TYPE
         SYNTAX      INTEGER {
                     enable(1),
                     disable(2)
                  }
         MAX-ACCESS  read-write
         STATUS      current
         DESCRIPTION
                     "The mode of MAC Address-Table Move Update."
         ::= { agentPortBackupGroupEntry 5 }

    agentPortBackupGroupStatus OBJECT-TYPE
         SYNTAX      RowStatus
         MAX-ACCESS  read-create
         STATUS      current
         DESCRIPTION
                     "The status of Port-backup group.
                     active(1)  - This group setting is active.
                     createAndGo(4) -  Set to this value to create a new group.
                     destroy(6) - Set to this value to remove this group."
         ::= { agentPortBackupGroupEntry 6 }
   
    agentPortBackupGroupFailBackTime OBJECT-TYPE
         SYNTAX      Integer32 (0..60)
         MAX-ACCESS  read-write
         STATUS      current
         DESCRIPTION
                     "The value of the Port-backup fail back time."
         ::= { agentPortBackupGroupEntry 7 }
   

--**************************************************************************************
--    agentCDPConfigGroup
--**************************************************************************************

agentCDPConfigGroup                             OBJECT IDENTIFIER ::= { switchingExtension 110 }

agentCDPConfigAdminMode    OBJECT-TYPE
         SYNTAX      INTEGER {
                     enable(1),
                     disable(2)
                  }
         MAX-ACCESS  read-write
         STATUS      current
         DESCRIPTION
                     "enable/disable CDP (Cisco Discovery Protocol)"
         DEFVAL { disable }
         ::= { agentCDPConfigGroup 1 }


agentCDPConfigTimeToLive   OBJECT-TYPE
         SYNTAX      Unsigned32 (10..255)
         MAX-ACCESS  read-write
         STATUS      current
         DESCRIPTION
                     "The time that CDP information will be kept in other CDP-aware switch. The range is 10 to 255."
         ::= { agentCDPConfigGroup 2 }

agentCDPConfigTransmitInterval   OBJECT-TYPE
         SYNTAX      Unsigned32 (5..254)
         MAX-ACCESS  read-write
         STATUS      current
         DESCRIPTION
                     "The time interval that the CDP information is sent. The range is 5 to 254."
         ::= { agentCDPConfigGroup 3 }

agentCDPConfigNumInPkts   OBJECT-TYPE
         SYNTAX      Integer32 (0..2147483647)
         MAX-ACCESS  read-only
         STATUS      current
         DESCRIPTION
                     "The number of CDP packets received."
         ::= { agentCDPConfigGroup 4 }

agentCDPConfigNumOutPkts   OBJECT-TYPE
         SYNTAX      Integer32 (0..2147483647)
         MAX-ACCESS  read-only
         STATUS      current
         DESCRIPTION
                     "The number of CDP packets sent out."
         ::= { agentCDPConfigGroup 5 }


agentCDPConfigNumErrPkts   OBJECT-TYPE
         SYNTAX      Integer32 (0..2147483647)
         MAX-ACCESS  read-only
         STATUS      current
         DESCRIPTION
                     "The number of error CDP packets received/sent."
         ::= { agentCDPConfigGroup 6 }


    agentCDPConfigResetNumPkts   OBJECT-TYPE
         SYNTAX      INTEGER {
                     enable(1),
                     disable(2)
                  }
         MAX-ACCESS  read-write
         STATUS      current
         DESCRIPTION
                     "reset CDP in/out/err packet counters"
         DEFVAL { disable }
         ::= { agentCDPConfigGroup 7 }

    agentCDPConfigResetDeviceInformation  OBJECT-TYPE
         SYNTAX      INTEGER {
                     enable(1),
                     disable(2)
                  }
         MAX-ACCESS  read-write
         STATUS      current
         DESCRIPTION
                     "clear CDP neighbor information"
         DEFVAL { disable }
         ::= { agentCDPConfigGroup 8}

    agentCDPConfigPortModeTable OBJECT-TYPE
         SYNTAX      SEQUENCE OF AgentCDPConfigPortModeEntry
         MAX-ACCESS  not-accessible
         STATUS      current
         DESCRIPTION
                     "The switch CDP administration table"
         ::= { agentCDPConfigGroup 10 }

    agentCDPConfigPortModeEntry OBJECT-TYPE
         SYNTAX      AgentCDPConfigPortModeEntry
         MAX-ACCESS  not-accessible
         STATUS      current
         DESCRIPTION
                     "CDP administration setting for a specific port."
         INDEX       { agentCDPConfigPortModeIfIndex }
         ::= { agentCDPConfigPortModeTable 1 }

    AgentCDPConfigPortModeEntry ::=
         SEQUENCE {
             agentCDPConfigPortModeIfIndex           Integer32,
             agentCDPConfigPortModeAdminMode         INTEGER
         }

    agentCDPConfigPortModeIfIndex OBJECT-TYPE
         SYNTAX      Integer32 (0..2147483647)
         MAX-ACCESS  read-only
         STATUS      current
         DESCRIPTION
                     "port index used to uniquelly identify an entry of the CDP administration Table"
         ::= { agentCDPConfigPortModeEntry 1 }


    agentCDPConfigPortModeAdminMode  OBJECT-TYPE
         SYNTAX      INTEGER {
                     enable(1),
                     disable(2)
                  }
         MAX-ACCESS  read-write
         STATUS      current
         DESCRIPTION
                     "CDP administration for every individual port. "
         ::= { agentCDPConfigPortModeEntry 2 }




    agentCDPConfigNeighborInfoTable OBJECT-TYPE
         SYNTAX      SEQUENCE OF AgentCDPConfigNeighborInfoEntry
         MAX-ACCESS  not-accessible
         STATUS      current
         DESCRIPTION
                     "The switch CDP neighbor information table"
         ::= { agentCDPConfigGroup 20 }

    agentCDPConfigNeighborInfoEntry OBJECT-TYPE
         SYNTAX      AgentCDPConfigNeighborInfoEntry
         MAX-ACCESS  not-accessible
         STATUS      current
         DESCRIPTION
                     "CDP neighbor information."
         INDEX       { agentCDPConfigNeighborInfoIndex }
         ::= { agentCDPConfigNeighborInfoTable 1 }

    AgentCDPConfigNeighborInfoEntry ::=
         SEQUENCE {
             agentCDPConfigNeighborInfoIndex           Integer32,
             agentCDPConfigNeighborInfoDeviceID        DisplayString,
             agentCDPConfigNeighborInfoLocalIF         Integer32,
             agentCDPConfigNeighborInfoHoldTime        Integer32,
             agentCDPConfigNeighborInfoCapability      DisplayString,
             agentCDPConfigNeighborInfoPlatform        DisplayString,
             agentCDPConfigNeighborInfoPortID          DisplayString,
             agentCDPConfigNeighborInfoManagementAddress    IpAddress
         }

    agentCDPConfigNeighborInfoIndex OBJECT-TYPE
         SYNTAX      Integer32 (0..2147483647)
         MAX-ACCESS  read-only
         STATUS      current
         DESCRIPTION
                     "index used to uniquelly identify an entry of the CDP neighbor information Table"
         ::= { agentCDPConfigNeighborInfoEntry 1 }


    agentCDPConfigNeighborInfoDeviceID  OBJECT-TYPE
         SYNTAX      DisplayString
         MAX-ACCESS  read-only
         STATUS      current
         DESCRIPTION
                     "neighbor CDP device ID. "
         ::= { agentCDPConfigNeighborInfoEntry 2 }


    agentCDPConfigNeighborInfoLocalIF  OBJECT-TYPE
         SYNTAX      Integer32 (0..2147483647)
         MAX-ACCESS  read-only
         STATUS      current
         DESCRIPTION
                     "Local IF number from which the CDP packets are received. "
         ::= { agentCDPConfigNeighborInfoEntry 3 }

     agentCDPConfigNeighborInfoHoldTime  OBJECT-TYPE
         SYNTAX      Integer32 (0..2147483647)
         MAX-ACCESS  read-only
         STATUS      current
         DESCRIPTION
                     "CDP packets' time to live. "
         ::= { agentCDPConfigNeighborInfoEntry 4 }


     agentCDPConfigNeighborInfoCapability  OBJECT-TYPE
         SYNTAX      DisplayString
         MAX-ACCESS  read-only
         STATUS      current
         DESCRIPTION
                     "neighborhood's capabilities. "
         ::= { agentCDPConfigNeighborInfoEntry 5 }


     agentCDPConfigNeighborInfoPlatform  OBJECT-TYPE
         SYNTAX      DisplayString
         MAX-ACCESS  read-only
         STATUS      current
         DESCRIPTION
                     "neighborhood's platform. "
         ::= { agentCDPConfigNeighborInfoEntry 6 }


     agentCDPConfigNeighborInfoPortID  OBJECT-TYPE
         SYNTAX      DisplayString
         MAX-ACCESS  read-only
         STATUS      current
         DESCRIPTION
                     "neighborhood's port ID from which the CDP packets are sent out. "
         ::= { agentCDPConfigNeighborInfoEntry 7 }

     agentCDPConfigNeighborInfoManagementAddress  OBJECT-TYPE
         SYNTAX      IpAddress
         MAX-ACCESS  read-only
         STATUS      current
         DESCRIPTION
                     "neighborhood's management address from which the CDP packets are sent out. "
         ::= { agentCDPConfigNeighborInfoEntry 8 }


--**************************************************************************************
--    agentVlanVoiceConfigGroup
--**************************************************************************************

    agentVlanVoiceConfigGroup                             OBJECT IDENTIFIER ::= { switchingExtension 111 }

    agentVlanVoiceVlanIDCreate    OBJECT-TYPE
         SYNTAX      Integer32 (0..4093)
         MAX-ACCESS  read-write
         STATUS      current
         DESCRIPTION
                       "The Voice Vlan Vlan Id."
           ::= { agentVlanVoiceConfigGroup 1 }

	agentVlanVoiceAdminMode OBJECT-TYPE
         SYNTAX     INTEGER {
                    enable(1),
                    disable(2)
                    }
         MAX-ACCESS  read-write
         STATUS      current
         DESCRIPTION
                     "The Voice Vlan administration."
         ::= { agentVlanVoiceConfigGroup 2 }

    agentVlanVoiceMacAddress OBJECT-TYPE
         SYNTAX   DisplayString
         MAX-ACCESS  read-write
         STATUS      current
         DESCRIPTION
                     "The Voice Vlan MAC address. Multicast mac address is not allowed."
         ::= { agentVlanVoiceConfigGroup 3 }

    agentVlanVoiceMacMask OBJECT-TYPE
         SYNTAX   Integer32 (0 | 128 | 192 | 224 | 240 | 248 | 252 | 254 | 255)
         MAX-ACCESS  read-write
         STATUS      current
         DESCRIPTION
                     "The Voice Vlan MAC mask."
         ::= { agentVlanVoiceConfigGroup 4 }

    agentVlanVoicePriority   OBJECT-TYPE
         SYNTAX      Integer32 (0..7)
         MAX-ACCESS  read-write
         STATUS      current
         DESCRIPTION
                     "The Voice Vlan priority."
         ::= { agentVlanVoiceConfigGroup 5 }

    agentVlanVoiceName  OBJECT-TYPE
         SYNTAX      DisplayString
         MAX-ACCESS  read-write
         STATUS      current
         DESCRIPTION
                     "The Voice Vlan name."
         ::= { agentVlanVoiceConfigGroup 6 }

	-- *****************************************************************
     	-- agentVlanVoiceConfigTable
     	--
     	-- *****************************************************************

    agentVlanVoiceConfigTable OBJECT-TYPE
         SYNTAX      SEQUENCE OF AgentVlanVoiceConfigEntry
         MAX-ACCESS  not-accessible
         STATUS      current
         DESCRIPTION
                     "The switch Voice Vlan show table."
         ::= { agentVlanVoiceConfigGroup 7 }

    agentVlanVoiceConfigEntry OBJECT-TYPE
         SYNTAX      AgentVlanVoiceConfigEntry
         MAX-ACCESS  not-accessible
         STATUS      current
         DESCRIPTION
                     "The switch Voice Vlan show entry."
         INDEX       { agentVlanVoiceConfigIndex }
         ::= { agentVlanVoiceConfigTable 1 }

    AgentVlanVoiceConfigEntry ::=
         SEQUENCE {
             agentVlanVoiceConfigIndex           Integer32,
             agentVlanVoiceConfigName            DisplayString,
             agentVlanVoiceConfigMacAddress      DisplayString,
             agentVlanVoiceConfigMacMask         Integer32,
             agentVlanVoiceConfigPriority        Integer32,
             agentVlanVoiceConfigDelete          INTEGER
         }

    agentVlanVoiceConfigIndex OBJECT-TYPE
         SYNTAX      Integer32 (0..2147483647)
         MAX-ACCESS  read-only
         STATUS      current
         DESCRIPTION
                     "Voice Vlan Index."
         ::= { agentVlanVoiceConfigEntry 1 }

	agentVlanVoiceConfigName  OBJECT-TYPE
         SYNTAX      DisplayString
         MAX-ACCESS  read-only
         STATUS      current
         DESCRIPTION
                     "The Voice Vlan name."
         ::= { agentVlanVoiceConfigEntry 2 }

    agentVlanVoiceConfigMacAddress OBJECT-TYPE
         SYNTAX      DisplayString
         MAX-ACCESS  read-only
         STATUS      current
         DESCRIPTION
                     "The Voice Vlan MAC address."
         ::= { agentVlanVoiceConfigEntry 3 }

	agentVlanVoiceConfigMacMask OBJECT-TYPE
         SYNTAX      Integer32 (0 | 128 | 192 | 224 | 240 | 248 | 252 | 254 | 255)
         MAX-ACCESS  read-only
         STATUS      current
         DESCRIPTION
                     "The Voice Vlan MAC mask."
         ::= { agentVlanVoiceConfigEntry 4 }

    agentVlanVoiceConfigPriority   OBJECT-TYPE
         SYNTAX      Integer32 (0..7)
         MAX-ACCESS  read-only
         STATUS      current
         DESCRIPTION
                     "The Voice Vlan priority."
         ::= { agentVlanVoiceConfigEntry 5 }

    agentVlanVoiceConfigDelete OBJECT-TYPE
         SYNTAX     INTEGER {
                    enable(1),
                    disable(2)
                    }
         MAX-ACCESS  read-write
         STATUS      current
         DESCRIPTION
                     "Remove Voice Vlan entry."
         ::= { agentVlanVoiceConfigEntry 6 }

        -- *****************************************************************
     	-- agentVlanVoiceConfigPortModeTable
     	--
     	-- *****************************************************************

--    agentVlanVoiceConfigPortModeTable OBJECT-TYPE
--         SYNTAX      SEQUENCE OF AgentVlanVoiceConfigPortModeEntry
--         MAX-ACCESS  not-accessible
--         STATUS      current
--         DESCRIPTION
--                     "The switch Voice Vlan administration table"
--         ::= { agentVlanVoiceConfigGroup 11 }

--    agentVlanVoiceConfigPortModeEntry OBJECT-TYPE
--         SYNTAX      AgentVlanVoiceConfigPortModeEntry
--         MAX-ACCESS  not-accessible
--         STATUS      current
--         DESCRIPTION
--                     "Voice Vlan administration setting for a specific port."
--         INDEX       { agentVlanVoiceConfigPortModeIfIndex }
--         ::= { agentVlanVoiceConfigPortModeTable 1 }

--    AgentVlanVoiceConfigPortModeEntry ::=
--         SEQUENCE {
--             agentVlanVoiceConfigPortModeIfIndex           Integer32,
--             agentVlanVoiceConfigPortModeAdminMode         INTEGER
--         }

--    agentVlanVoiceConfigPortModeIfIndex OBJECT-TYPE
--         SYNTAX      Integer32
--         MAX-ACCESS  read-only
--         STATUS      current
--         DESCRIPTION
--                     "port index used to uniquelly identify an entry of the Voice Vlan administration Table"
--         ::= { agentVlanVoiceConfigPortModeEntry 1 }


--    agentVlanVoiceConfigPortModeAdminMode  OBJECT-TYPE
--         SYNTAX      INTEGER {
--                     enable(1),
--                     disable(2)
--                  }
--         MAX-ACCESS  read-write
--         STATUS      current
--         DESCRIPTION
--                     "Voice Vlan administration for every individual port. "
--         ::= { agentVlanVoiceConfigPortModeEntry 2 }


--**************************************************************************************
--    agentVoiceVlanConfigGroup
--**************************************************************************************

    agentVoiceVlanConfigGroup                             OBJECT IDENTIFIER ::= { switchingExtension 114 }

	agentVoiceVlanAdminMode OBJECT-TYPE
         SYNTAX     INTEGER {
                    enable(1),
                    disable(2)
                    }
         MAX-ACCESS  read-write
         STATUS      current
         DESCRIPTION
                     "The Voice Vlan administration Mode. The default mode is disabled."
         DEFVAL { disable }
         ::= { agentVoiceVlanConfigGroup 1 }


    -- *****************************************************************
    -- agentVoiceVlanConfigTable
    --
    -- *****************************************************************

    agentVoiceVlanConfigTable OBJECT-TYPE
         SYNTAX      SEQUENCE OF AgentVoiceVlanConfigEntry
         MAX-ACCESS  not-accessible
         STATUS      current
         DESCRIPTION
                     "The switch Voice Vlan show table."
         ::= { agentVoiceVlanConfigGroup 2 }

    agentVoiceVlanConfigEntry OBJECT-TYPE
         SYNTAX      AgentVoiceVlanConfigEntry
         MAX-ACCESS  not-accessible
         STATUS      current
         DESCRIPTION
                     "The switch Voice Vlan show entry."
         INDEX       { agentVoiceVlanConfigIndex }
         ::= { agentVoiceVlanConfigTable 1 }

   AgentVoiceVlanConfigEntry ::=
         SEQUENCE {
             agentVoiceVlanConfigIndex           Integer32,
             agentVoiceVlanConfigIfMode          INTEGER,
             agentVoiceVlanConfigIfModeValue     Integer32,
             agentVoiceVlanConfigCosOverrideMode INTEGER,
             agentVoiceVlanConfigOperState       INTEGER
         }

    agentVoiceVlanConfigIndex OBJECT-TYPE
         SYNTAX      Integer32 (0..4093)
         MAX-ACCESS  read-only
         STATUS      current
         DESCRIPTION
                     "Voice Vlan Index."
         ::= { agentVoiceVlanConfigEntry 1 }

    agentVoiceVlanConfigIfMode OBJECT-TYPE
         SYNTAX     INTEGER {
                        disable(0),
                        vlanid(1),
                        dot1p(2),
                        none(3),
                        untagged(4)
                    }
         MAX-ACCESS  read-write
         STATUS      current
         DESCRIPTION
                     "The Voice VLAN mode for selected interface."
         DEFVAL { disable }
         ::= { agentVoiceVlanConfigEntry 2 }

    agentVoiceVlanConfigIfModeValue OBJECT-TYPE
         SYNTAX      Integer32 (0..2147483647)
         MAX-ACCESS  read-write
         STATUS      current
         DESCRIPTION
                     "The Voice VLAN mode value of the selected interface."
         ::= { agentVoiceVlanConfigEntry 3 }

    agentVoiceVlanConfigCosOverrideMode OBJECT-TYPE
         SYNTAX     INTEGER {
                    enable(1),
                    disable(2)
                    }
         MAX-ACCESS  read-write
         STATUS      current
         DESCRIPTION
                     "The CoS Override mode for selected interface. The default mode is disabled."
         DEFVAL { disable }
         ::= { agentVoiceVlanConfigEntry 4 }

    agentVoiceVlanConfigOperState OBJECT-TYPE
         SYNTAX     INTEGER {
                    enable(1),
                    disable(2)
                    }
         MAX-ACCESS  read-only
         STATUS      current
         DESCRIPTION
                     "The operational status of the voice vlan of the given interface."
         ::= { agentVoiceVlanConfigEntry 5 }

--**************************************************************************************
--    agentVTPConfigGroup
--**************************************************************************************
    agentVTPConfigGroup                             OBJECT IDENTIFIER ::= { switchingExtension 115 }

	agentVTPAdminMode OBJECT-TYPE
         SYNTAX     INTEGER {
                    enable(1),
                    disable(2)
                    }
         MAX-ACCESS  read-write
         STATUS      current
         DESCRIPTION
                     "Enable or disable the VTP feature. The default mode is enabled."
         DEFVAL { enable }
         ::= { agentVTPConfigGroup 1 }

	agentVTPVersion OBJECT-TYPE
         SYNTAX      Integer32 (0..2147483647)
         MAX-ACCESS  read-only
         STATUS      current
         DESCRIPTION
                     "The VTP version."
         ::= { agentVTPConfigGroup 2 }

	agentVTPConfigRevision OBJECT-TYPE
         SYNTAX      Integer32 (0..2147483647)
         MAX-ACCESS  read-only
         STATUS      current
         DESCRIPTION
                     "The revision for the VTP domain status."
         ::= { agentVTPConfigGroup 3 }

	agentVTPMaxVlanNumSupported OBJECT-TYPE
         SYNTAX      Integer32 (0..2147483647)
         MAX-ACCESS  read-only
         STATUS      current
         DESCRIPTION
                     "The maximum VLANs supported for VTP."
         ::= { agentVTPConfigGroup 4 }

	agentVTPVlanNumSupported OBJECT-TYPE
         SYNTAX      Integer32 (0..2147483647)
         MAX-ACCESS  read-only
         STATUS      current
         DESCRIPTION
                     "The VLAN number for VTP currently."
         ::= { agentVTPConfigGroup 5 }

	agentVTPOperatingMode OBJECT-TYPE
         SYNTAX     INTEGER {
                    server(0),
                    client(1),
                    transparent(2)
                    }
         MAX-ACCESS  read-write
         STATUS      current
         DESCRIPTION
                     "The operational mode of VTP device. The default setting is server mode."
         DEFVAL { server }
         ::= { agentVTPConfigGroup 6 }

	agentVTPDomainName OBJECT-TYPE
         SYNTAX      DisplayString (SIZE(0..32))
         MAX-ACCESS  read-write
         STATUS      current
         DESCRIPTION
                     "The name of the VTP administrative domain."
         ::= { agentVTPConfigGroup 7 }

	agentVTPPruningMode OBJECT-TYPE
         SYNTAX     INTEGER {
                    enable(1),
                    disable(2)
                    }
         MAX-ACCESS  read-write
         STATUS      current
         DESCRIPTION
                     "Enable or disable the VTP pruning mode."
         DEFVAL { disable }
         ::= { agentVTPConfigGroup 8 }

	agentVTPDomainPassword OBJECT-TYPE
         SYNTAX      DisplayString (SIZE(0..64))
         MAX-ACCESS  read-write
         STATUS      current
         DESCRIPTION
                     "The the password for the VTP administrative domain."
         ::= { agentVTPConfigGroup 9 }

	agentVTPV2Mode OBJECT-TYPE
         SYNTAX     INTEGER {
                    enable(1),
                    disable(2)
                    }
         MAX-ACCESS  read-write
         STATUS      current
         DESCRIPTION
                     "Enable or disable the VTP V2 mode."
         DEFVAL { disable }
         ::= { agentVTPConfigGroup 10 }

	agentVTPMD5Digest OBJECT-TYPE
         SYNTAX      DisplayString (SIZE(0..64))
         MAX-ACCESS  read-only
         STATUS      current
         DESCRIPTION
                     "The MD5 Digest for the VTP domain status."
         ::= { agentVTPConfigGroup 11 }

	agentVTPConfigLastModified OBJECT-TYPE
         SYNTAX      DisplayString (SIZE(0..64))
         MAX-ACCESS  read-only
         STATUS      current
         DESCRIPTION
                     "The timestamp of the last configuration modification and 
                     the IP address of the switch that caused the configuration 
                     change to the database."
         ::= { agentVTPConfigGroup 12 }

	agentVTPLocalUpdaterID OBJECT-TYPE
         SYNTAX      DisplayString (SIZE(0..64))
         MAX-ACCESS  read-only
         STATUS      current
         DESCRIPTION
                     "The local updater ID for the VTP domain status."
         ::= { agentVTPConfigGroup 13 }


    -- *****************************************************************
    -- agentVTPPortConfigTable
    --
    -- *****************************************************************
    agentVTPPortConfigTable OBJECT-TYPE
         SYNTAX      SEQUENCE OF AgentVTPPortConfigEntry
         MAX-ACCESS  not-accessible
         STATUS      current
         DESCRIPTION
                     "The VTP Trunk status show table."
         ::= { agentVTPConfigGroup 14 }

    agentVTPPortConfigEntry OBJECT-TYPE
         SYNTAX      AgentVTPPortConfigEntry
         MAX-ACCESS  not-accessible
         STATUS      current
         DESCRIPTION
                     "The switch Voice Vlan show entry."
         INDEX       { agentVTPPortConfigIndex }
         ::= { agentVTPPortConfigTable 1 }

   AgentVTPPortConfigEntry ::=
         SEQUENCE {
             agentVTPPortConfigIndex           Integer32,
             agentVTPPortConfigTrunkMode       INTEGER
         }

    agentVTPPortConfigIndex OBJECT-TYPE
         SYNTAX      Integer32 (0..2147483647)
         MAX-ACCESS  not-accessible
         STATUS      current
         DESCRIPTION
                     "VTP Trunkport Index."
         ::= { agentVTPPortConfigEntry 1 }

    agentVTPPortConfigTrunkMode OBJECT-TYPE
         SYNTAX     INTEGER {
                        enable(1),
                        disable(2)
                    }
         MAX-ACCESS  read-write
         STATUS      current
         DESCRIPTION
                     "The VTP Trunk mode for selected interface."
         DEFVAL { disable }
         ::= { agentVTPPortConfigEntry 2 }

    --**************************************************************************************

    --**************************************************************************************
    -- FIP Snooping Table
    --
    --**************************************************************************************
    agentFIPSnoopingGroup                             OBJECT IDENTIFIER ::= { switchingExtension 116 }

      agentFIPSnoopingAdminMode OBJECT-TYPE
         SYNTAX     INTEGER {
                    enable(1),
                    disable(2)
                    }
         MAX-ACCESS  read-write
         STATUS      current
         DESCRIPTION
                     "Enable or disable the FIPSnooping feature. The default mode is disable."
         DEFVAL { disable }
         ::= { agentFIPSnoopingGroup 1 }

      agentFIPSnoopingVlanConfigTable OBJECT-TYPE
         SYNTAX      SEQUENCE OF AgentFIPSnoopingVlanConfigEntry
         MAX-ACCESS  not-accessible
         STATUS      current
         DESCRIPTION
                     "A table of the FIP Snooping Vlan configuration entries."
         ::= { agentFIPSnoopingGroup 2 }

      agentFIPSnoopingVlanConfigEntry OBJECT-TYPE
         SYNTAX      AgentFIPSnoopingVlanConfigEntry
         MAX-ACCESS  not-accessible
         STATUS      current
         DESCRIPTION
                     "Represents entry for a FIP Snooping configurable Vlan."
         INDEX       { agentFIPSnoopingVlanIndex }
         ::= { agentFIPSnoopingVlanConfigTable 1 }

      AgentFIPSnoopingVlanConfigEntry ::= SEQUENCE {
          agentFIPSnoopingVlanIndex
              Integer32,
          agentFIPSnoopingVlanAdminMode
              INTEGER
          }

      agentFIPSnoopingVlanIndex OBJECT-TYPE
         SYNTAX      Integer32 (0..2147483647)
         MAX-ACCESS  read-only
         STATUS      current
         DESCRIPTION
                     "VlanIndex values in the vlans."
         ::= { agentFIPSnoopingVlanConfigEntry 1 }

      agentFIPSnoopingVlanAdminMode OBJECT-TYPE
         SYNTAX      INTEGER {
                     disable(0),
                     enable(1)
                  }
         MAX-ACCESS  read-write
         STATUS      current
         DESCRIPTION
                     "This enables or disables FIP Snooping on a selected Vlan interface."
         DEFVAL { disable }
         ::= { agentFIPSnoopingVlanConfigEntry 2 }

--Remove by KevinLee 2014/07/21 [Defect: Bugzilla V Bug 519]
--      agentFIPSnoopingFCMap OBJECT-TYPE
--         SYNTAX      Integer32
--         MAX-ACCESS  read-write
--         STATUS      current
--         DESCRIPTION
--                     "The value of FC-MAP value."
--         ::= { agentFIPSnoopingGroup 3 }
--
--      agentFIPSnoopingPortConfigTable OBJECT-TYPE
--         SYNTAX      SEQUENCE OF AgentFIPSnoopingPortConfigEntry
--         MAX-ACCESS  not-accessible
--         STATUS      current
--         DESCRIPTION
--         "A table that contains the configuration objects for the
--         with each port."
--
--         ::= { agentFIPSnoopingGroup 4 }
--
--      agentFIPSnoopingPortConfigEntry OBJECT-TYPE
--         SYNTAX      AgentFIPSnoopingPortConfigEntry
--         MAX-ACCESS  not-accessible
--         STATUS      current
--         DESCRIPTION
--         "The configuration information for FIP Snooping on a selected interface."
--         INDEX { agentFIPSnoopingPortIndex }
--         ::= { agentFIPSnoopingPortConfigTable 1 }
--
--      AgentFIPSnoopingPortConfigEntry ::=
--         SEQUENCE {
--         agentFIPSnoopingPortIndex
--                 Integer32,
--         agentFIPSnoopingPortMode
--                 INTEGER
--         }
--
--      agentFIPSnoopingPortIndex OBJECT-TYPE
--         SYNTAX      Integer32 (0..2147483647)
--         MAX-ACCESS  read-only
--         STATUS      current
--         DESCRIPTION
--                     "ifIndex values in the ifTable."
--         ::= { agentFIPSnoopingPortConfigEntry 1 }
--
--      agentFIPSnoopingPortMode OBJECT-TYPE
--         SYNTAX      INTEGER {
--                     disable(0),
--                     enable(1)
--                  }
--         MAX-ACCESS  read-write
--         STATUS      current
--         DESCRIPTION
--                     "It specifies FCF is connected to the interface. It can be either enable or disable
--                      default will be disable."
--         DEFVAL   { disable }
--         ::= { agentFIPSnoopingPortConfigEntry 2 }

      agentFIPSnoopingSessionTable OBJECT-TYPE
         SYNTAX      SEQUENCE OF AgentFIPSnoopingSessionEntry
         MAX-ACCESS  not-accessible
         STATUS      current
         DESCRIPTION
         "A table that contains the objects for the
         with each port."

         ::= { agentFIPSnoopingGroup 5 }

      agentFIPSnoopingSessionEntry OBJECT-TYPE
         SYNTAX      AgentFIPSnoopingSessionEntry
         MAX-ACCESS  not-accessible
         STATUS      current
         DESCRIPTION
         "The information for FIP Snooping sessions."
         INDEX { agentFIPSnoopingSessionKey }
         ::= { agentFIPSnoopingSessionTable 1 }

      AgentFIPSnoopingSessionEntry ::=
         SEQUENCE {
         agentFIPSnoopingSessionKey
                 PhysAddress,
         agentFIPSnoopingSessionIfIndex
                 Integer32,
         agentFIPSnoopingSessionFCFMacAddress
                 PhysAddress,
         agentFIPSnoopingSessionENodeMacAddress
                 PhysAddress,
         agentFIPSnoopingSessionENodeIfIndex
                 Integer32
         }

      agentFIPSnoopingSessionKey OBJECT-TYPE
         SYNTAX      PhysAddress
         MAX-ACCESS  read-only
         STATUS      current
         DESCRIPTION
                     "The FIP Snooping Session Key."
         ::= { agentFIPSnoopingSessionEntry 1 }

      agentFIPSnoopingSessionIfIndex OBJECT-TYPE
         SYNTAX      Integer32
         MAX-ACCESS  read-only
         STATUS      current
         DESCRIPTION
                     "Name of the interface which is connected."
         ::= { agentFIPSnoopingSessionEntry 2 }

      agentFIPSnoopingSessionFCFMacAddress OBJECT-TYPE
         SYNTAX      PhysAddress
         MAX-ACCESS  read-only
         STATUS      current
         DESCRIPTION
                     "The FCF MAC address of the session."
         ::= { agentFIPSnoopingSessionEntry 3 }

      agentFIPSnoopingSessionENodeMacAddress OBJECT-TYPE
         SYNTAX      PhysAddress
         MAX-ACCESS  read-only
         STATUS      current
         DESCRIPTION
                     "The ENode MAC address of the session."
         ::= { agentFIPSnoopingSessionEntry 4 }

      agentFIPSnoopingSessionENodeIfIndex OBJECT-TYPE
         SYNTAX      Integer32
         MAX-ACCESS  read-only
         STATUS      current
         DESCRIPTION
                     "The ENode interface of the session."
         ::= { agentFIPSnoopingSessionEntry 5 }

      agentFIPSnoopingFCFTable OBJECT-TYPE
         SYNTAX      SEQUENCE OF AgentFIPSnoopingFCFEntry
         MAX-ACCESS  not-accessible
         STATUS      current
         DESCRIPTION
         "A table that contains the objects for the
         with each port."

         ::= { agentFIPSnoopingGroup 6 }

      agentFIPSnoopingFCFEntry OBJECT-TYPE
         SYNTAX      AgentFIPSnoopingFCFEntry
         MAX-ACCESS  not-accessible
         STATUS      current
         DESCRIPTION
         "The information for FIP Snooping FCF."
         INDEX { agentFIPSnoopingFCFKey }
         ::= { agentFIPSnoopingFCFTable 1 }

      AgentFIPSnoopingFCFEntry ::=
         SEQUENCE {
         agentFIPSnoopingFCFKey
                 PhysAddress,
         agentFIPSnoopingFCFIfIndex
                 Integer32,
         agentFIPSnoopingFCFVlan
                 VlanIndex,
         agentFIPSnoopingFCFENodeNumber
                 Integer32,
         agentFIPSnoopingFCFFCMap
                 Integer32,
         agentFIPSnoopingFCFSwitchName
                 DisplayString,
         agentFIPSnoopingFCFFabricName
                 DisplayString
         }

      agentFIPSnoopingFCFKey OBJECT-TYPE
         SYNTAX      PhysAddress
         MAX-ACCESS  read-only
         STATUS      current
         DESCRIPTION
                     "The FIP Snooping FCF Key."
         ::= { agentFIPSnoopingFCFEntry 1 }

      agentFIPSnoopingFCFIfIndex OBJECT-TYPE
         SYNTAX      Integer32
         MAX-ACCESS  read-only
         STATUS      current
         DESCRIPTION
                     "Name of the interface to which the FCoE Forwarder (FCF) is connected."
         ::= { agentFIPSnoopingFCFEntry 2 }

      agentFIPSnoopingFCFVlan OBJECT-TYPE
         SYNTAX   VlanIndex
         MAX-ACCESS  read-only
         STATUS      current
         DESCRIPTION
                     "Vlan Index for which this entry is associated with."
         ::= { agentFIPSnoopingFCFEntry 3 }

      agentFIPSnoopingFCFENodeNumber OBJECT-TYPE
         SYNTAX      Integer32
         MAX-ACCESS  read-only
         STATUS      current
         DESCRIPTION
                     "Total number of ENodes that are connected to the FCF"
         ::= { agentFIPSnoopingFCFEntry 4 }

      agentFIPSnoopingFCFFCMap OBJECT-TYPE
         SYNTAX      Integer32
         MAX-ACCESS  read-only
         STATUS      current
         DESCRIPTION
                     "FC-Map value used by the FCF. The default value is 0xEFC00."
         ::= { agentFIPSnoopingFCFEntry 5 }

      agentFIPSnoopingFCFSwitchName OBJECT-TYPE
         SYNTAX      DisplayString
         MAX-ACCESS  read-only
         STATUS      current
         DESCRIPTION
                     "Name ID"
         ::= { agentFIPSnoopingFCFEntry 6 }

      agentFIPSnoopingFCFFabricName OBJECT-TYPE
         SYNTAX      DisplayString
         MAX-ACCESS  read-only
         STATUS      current
         DESCRIPTION
                     "Name of the FCF."
         ::= { agentFIPSnoopingFCFEntry 7 }

      agentFIPSnoopingENodeTable OBJECT-TYPE
         SYNTAX      SEQUENCE OF AgentFIPSnoopingENodeEntry
         MAX-ACCESS  not-accessible
         STATUS      current
         DESCRIPTION
         "A table that contains the objects for the
         with each port."

         ::= { agentFIPSnoopingGroup 7 }

      agentFIPSnoopingENodeEntry OBJECT-TYPE
         SYNTAX      AgentFIPSnoopingENodeEntry
         MAX-ACCESS  not-accessible
         STATUS      current
         DESCRIPTION
         "The information for FIP Snooping ENode."
         INDEX { agentFIPSnoopingENodeKey }
         ::= { agentFIPSnoopingENodeTable 1 }

      AgentFIPSnoopingENodeEntry ::=
         SEQUENCE {
         agentFIPSnoopingENodeKey
                 PhysAddress,
         agentFIPSnoopingENodeIfIndex
                 Integer32,
         agentFIPSnoopingENodeVlan
                 VlanIndex,
         agentFIPSnoopingENodeNameID
                 DisplayString
         }

      agentFIPSnoopingENodeKey OBJECT-TYPE
         SYNTAX      PhysAddress
         MAX-ACCESS  read-only
         STATUS      current
         DESCRIPTION
                     "The FIP Snooping ENode Key."
         ::= { agentFIPSnoopingENodeEntry 1 }

      agentFIPSnoopingENodeIfIndex OBJECT-TYPE
         SYNTAX      Integer32
         MAX-ACCESS  read-only
         STATUS      current
         DESCRIPTION
                     "The interface of enode."
         ::= { agentFIPSnoopingENodeEntry 2 }

      agentFIPSnoopingENodeVlan OBJECT-TYPE
         SYNTAX   VlanIndex
         MAX-ACCESS  read-only
         STATUS      current
         DESCRIPTION
                     "Vlan Index for which this entry is associated with."
         ::= { agentFIPSnoopingENodeEntry 3 }

      agentFIPSnoopingENodeNameID OBJECT-TYPE
         SYNTAX      DisplayString
         MAX-ACCESS  read-only
         STATUS      current
         DESCRIPTION
                     "Name ID"
         ::= { agentFIPSnoopingENodeEntry 4}

    --**************************************************************************************
    -- MLAG Group
    --
    --**************************************************************************************
	  agentMLAGGroup                             OBJECT IDENTIFIER ::= { switchingExtension 117 }

      agentMLAGAdminMode OBJECT-TYPE
         SYNTAX     INTEGER {
                    enable(1),
                    disable(2)
                    }
         MAX-ACCESS  read-write
         STATUS      current
         DESCRIPTION
                     "Enable or disable the MLAG feature. The default mode is disabled."
         DEFVAL { disable }
         ::= { agentMLAGGroup 1 }

      agentMLAGDomainId OBJECT-TYPE
         SYNTAX     INTEGER (1..1000)
         MAX-ACCESS  read-write
         STATUS      current
         DESCRIPTION
                     "Configure the domain Id of Multi-Chassis Link Aggregation."
         DEFVAL { 1 }
         ::= { agentMLAGGroup 2 }

      agentMLAGConfigurationConsistancyStatus OBJECT-TYPE
         SYNTAX     INTEGER {
         					success(1),
         					failure(2)
         					}
         MAX-ACCESS  read-only
         STATUS      current
         DESCRIPTION
                     "Check the switch configuration for consistency parameter."
         ::= { agentMLAGGroup 3 }

      agentMLAGMemberCount OBJECT-TYPE
         SYNTAX     Unsigned32 (0..2147483647)
         MAX-ACCESS  read-only
         STATUS      current
         DESCRIPTION
                     "Get the number of MLAG members."
         ::= { agentMLAGGroup 4 }

      agentMLAGSystemMac OBJECT-TYPE
         SYNTAX     MacAddress
         MAX-ACCESS  read-write
         STATUS      current
         DESCRIPTION
                     "Set the system mac of  Multi-Chassis Link Aggregation."
         ::= { agentMLAGGroup 5 }

      agentMLAGKeepaliveTimeout OBJECT-TYPE
         SYNTAX     INTEGER (5..600)
         MAX-ACCESS  read-write
         STATUS      current
         DESCRIPTION
                     "To specify the timeout (in seconds) between re-transmissions to the MLAG peer device. The range is from 3 to 20. The default is 5."
         DEFVAL { 1 }
         ::= { agentMLAGGroup 6 }

      agentMLAGPeerGatewayMode OBJECT-TYPE
         SYNTAX     INTEGER {
                    enable(1),
                    disable(2)
                    }
         MAX-ACCESS  read-write
         STATUS      current
         DESCRIPTION
                     "Enable or disable Layer 3 forwarding for packets destined to the gateway MAC address of the MLAG. The default mode is enabled."
         DEFVAL { disable }
         ::= { agentMLAGGroup 7 }

      agentMLAGDelayRestore OBJECT-TYPE
         SYNTAX     INTEGER (0..600)
         MAX-ACCESS  read-write
         STATUS      current
         DESCRIPTION
                     "To delay the MLAG from coming up on the restored MLAG peer device after a reload when the peer adjacency is already established. The default value is 0, it means that there is no delay time. The range of delay time is from 5 to 600 seconds."
         DEFVAL { 1 }
         ::= { agentMLAGGroup 8 }

      agentMLAGMemberLinkdownMode OBJECT-TYPE
         SYNTAX     INTEGER {
                    enable(1),
                    disable(2)
                    }
         MAX-ACCESS  read-write
         STATUS      current
         DESCRIPTION
                     "Enable or disable member port link down mode when MLAG is starting or stopping. The default mode is disabled."
         DEFVAL { disable }
         ::= { agentMLAGGroup 9 }

    --**************************************************************************************
    -- MLAG peer link Group
    --
    --**************************************************************************************
	  agentMLAGPeerLinkGroup                             OBJECT IDENTIFIER ::= { agentMLAGGroup 10 }

      agentMLAGPeerLinkifIndex OBJECT-TYPE
         SYNTAX     Integer32 (0..2147483647)
         MAX-ACCESS  read-write
         STATUS      current
         DESCRIPTION
                     "Use this to set MLAG peer link interface.
					 Set 0 to disable MLAG peer link."
         ::= { agentMLAGPeerLinkGroup 1 }

      agentMLAGPeerLinkifStatus OBJECT-TYPE
      	 SYNTAX      INTEGER {
         					up(1),
         					down(2)
         					}
         MAX-ACCESS  read-only
         STATUS      current
         DESCRIPTION
                     "Show MLAG peer link interface status."
         ::= { agentMLAGPeerLinkGroup 2 }

      agentMLAGPeerLinkActiveVlans OBJECT-TYPE
         SYNTAX     DisplayString
         MAX-ACCESS  read-only
         STATUS      current
         DESCRIPTION
                     "Show MLAG peer link interface active vlans."
         ::= { agentMLAGPeerLinkGroup 3 }

      agentMLAGPeerLinkForbiddenVlans OBJECT-TYPE
         SYNTAX     DisplayString
         MAX-ACCESS  read-only
         STATUS      current
         DESCRIPTION
                     "Show MLAG peer link interface forbidden vlans."
         ::= { agentMLAGPeerLinkGroup 4 }

    --**************************************************************************************
    -- MLAG port channel
    --
    --**************************************************************************************
	  agentMLAGPortChannelTable OBJECT-TYPE
		 SYNTAX      SEQUENCE OF AgentMLAGPortChannelEntry
		 MAX-ACCESS  not-accessible
		 STATUS      current
		 DESCRIPTION
					 "Table of Multi-Chassis Link Aggregation
					 port channel status for the specified interface."
		 ::= { agentMLAGGroup 11 }
		
      agentMLAGPortChannelEntry OBJECT-TYPE
		 SYNTAX      AgentMLAGPortChannelEntry
		 MAX-ACCESS  not-accessible
		 STATUS      current
		 DESCRIPTION
					 "Table of Multi-Chassis Link Aggregation
					 port channel status for the specified interface."
		 INDEX       { agentMLAGPortChannelifIndex }
		 ::= { agentMLAGPortChannelTable 1 }
      
      AgentMLAGPortChannelEntry ::= SEQUENCE {
		   agentMLAGPortChannelifIndex
			   InterfaceIndex,
		   agentMLAGPortChannelId
			   INTEGER,
		   agentMLAGPortChannelifIndexStatus
			   INTEGER,
		   agentMLAGPortChannelConsistancy
			   INTEGER,
		   agentMLAGPortChannelActiveVlans
			   DisplayString
		   }
      
      agentMLAGPortChannelifIndex OBJECT-TYPE
		 SYNTAX      InterfaceIndex
		 MAX-ACCESS  read-only
		 STATUS      current
		 DESCRIPTION
					 "This is a unique index for an entry in the
					 agentMLAGPortChannelTable.  A non-zero value
					 indicates the ifIndex for the corresponding interface
					 entry in the ifTable."
		 ::= { agentMLAGPortChannelEntry 1 }

      agentMLAGPortChannelId OBJECT-TYPE
      	 SYNTAX      INTEGER (0..4096)
      	 MAX-ACCESS  read-create
      	 STATUS      current
      	 DESCRIPTION
      				 "Identity of MLAG port channel number.
      				 Zero to disable MLAG mode."
      	 ::= { agentMLAGPortChannelEntry 2 }

      agentMLAGPortChannelifIndexStatus OBJECT-TYPE
      	 SYNTAX      INTEGER {
         					up(1),
         					down(2)
         					}
      	 MAX-ACCESS  read-only
      	 STATUS      current
      	 DESCRIPTION
      				 "Interface status of MLAG port channel number."
      	 ::= { agentMLAGPortChannelEntry 3 }

      agentMLAGPortChannelConsistancy OBJECT-TYPE
      	 SYNTAX      INTEGER {
         					success(1),
         					failure(2)
         					}
      	 MAX-ACCESS  read-only
      	 STATUS      current
      	 DESCRIPTION
      				 "Configuration consistancy of MLAG port channel number."
      	 ::= { agentMLAGPortChannelEntry 4 }
      
      agentMLAGPortChannelActiveVlans OBJECT-TYPE
      	 SYNTAX      DisplayString
      	 MAX-ACCESS  read-only
      	 STATUS      current
      	 DESCRIPTION
      				 "Active vlans of MLAG port channel number."
      	 ::= { agentMLAGPortChannelEntry 5 }


    --**************************************************************************************
    -- MLAG vlan routing interface
    --
    --**************************************************************************************
      agentMLAGVlanRoutingPortTable OBJECT-TYPE
		 SYNTAX      SEQUENCE OF AgentMLAGVlanRoutingPortEntry
		 MAX-ACCESS  not-accessible
		 STATUS      current
		 DESCRIPTION
			"Table of Multi-Chassis Link Aggregation
			Forbidden Configuration for the specified vlan routing interface."
		 ::= { agentMLAGGroup 12 }

      agentMLAGVlanRoutingPortEntry OBJECT-TYPE
		 SYNTAX      AgentMLAGVlanRoutingPortEntry
		 MAX-ACCESS  not-accessible
		 STATUS      current
		 DESCRIPTION
			"Table of Multi-Chassis Link Aggregation
			Forbidden Configuration for the specified vlan routing interface."
		 INDEX       { agentMLAGVlanRoutingPortifIndex }
		 ::= { agentMLAGVlanRoutingPortTable 1 }

      AgentMLAGVlanRoutingPortEntry ::= SEQUENCE {
		   agentMLAGVlanRoutingPortifIndex
			   InterfaceIndex,
		   agentMLAGVlanRoutingPortForbiddenMode
			   INTEGER
		   }

      agentMLAGVlanRoutingPortifIndex OBJECT-TYPE
		 SYNTAX      InterfaceIndex
		 MAX-ACCESS  read-only
		 STATUS      current
		 DESCRIPTION
			"This is a unique index for an entry in the
			agentMLAGVlanRoutingPortTable.  A non-zero value
			indicates the ifIndex for the corresponding interface
			entry in the ifTable."
		 ::= { agentMLAGVlanRoutingPortEntry 1 }

      agentMLAGVlanRoutingPortForbiddenMode OBJECT-TYPE
		 SYNTAX     INTEGER {
                    enable(1),
                    disable(2)
                    }
		 MAX-ACCESS  read-write
		 STATUS      current
		 DESCRIPTION
                     "Enable or disable forbidden mode of VLAN on peer link interface. The default mode is disabled."
		 DEFVAL { disable }
		 ::= { agentMLAGVlanRoutingPortEntry 2 }

    --**************************************************************************************
    -- DCBX Group
    --
    --**************************************************************************************
	  agentDCBXGroup                             OBJECT IDENTIFIER ::= { switchingExtension 118 }

    --**************************************************************************************
    -- DCBX Config Table
    --
    --**************************************************************************************
	  agentDCBXConfigTable OBJECT-TYPE
		 SYNTAX      SEQUENCE OF AgentDCBXConfigEntry
		 MAX-ACCESS  not-accessible
		 STATUS      current
		 DESCRIPTION
					 "Table of Data center bridging exchange configurations
					 for the specified interface."
		 ::= { agentDCBXGroup 1 }
		
      agentDCBXConfigEntry OBJECT-TYPE
		 SYNTAX      AgentDCBXConfigEntry
		 MAX-ACCESS  not-accessible
		 STATUS      current
		 DESCRIPTION
					 "Table of Data center bridging exchange configurations
					 for the specified interface."
		 INDEX       { agentDCBXifIndex }
		 ::= { agentDCBXConfigTable 1 }
      
      AgentDCBXConfigEntry ::= SEQUENCE {
		   agentDCBXifIndex
			   InterfaceIndex,
		   agentDCBXAdminMode
			   INTEGER,
		   agentDCBXVersion
			   INTEGER
		   }
      
      agentDCBXifIndex OBJECT-TYPE
		 SYNTAX      InterfaceIndex
		 MAX-ACCESS  read-only
		 STATUS      current
		 DESCRIPTION
					 "This is a unique index for an entry in the
					 agentDCBXPFCConfigTable.  A non-zero value
					 indicates the ifIndex for the corresponding interface
					 entry in the ifTable."
		 ::= { agentDCBXConfigEntry 1 }

      agentDCBXAdminMode OBJECT-TYPE
      	 SYNTAX      INTEGER {
							enable(1),
							disable(2)
							}
      	 MAX-ACCESS  read-write
      	 STATUS      current
      	 DESCRIPTION
      				 "Enable/Disable DCBX for the specified interface."
      	 ::= { agentDCBXConfigEntry 2 }

      agentDCBXVersion OBJECT-TYPE
      	 SYNTAX      INTEGER {
							cee(1),
							ieee(2),
							auto(3)
							}
      	 MAX-ACCESS  read-write
      	 STATUS      current
      	 DESCRIPTION
      				 "Configure DCBX version for the specified interface."
      	 ::= { agentDCBXConfigEntry 3 }
		 
    --**************************************************************************************
    -- DCBX PFC Config Table
    --
    --**************************************************************************************
	  agentDCBXPFCConfigTable OBJECT-TYPE
		 SYNTAX      SEQUENCE OF AgentDCBXPFCConfigEntry
		 MAX-ACCESS  not-accessible
		 STATUS      current
		 DESCRIPTION
					 "Table of Data center bridging exchange configurations
					 for the specified interface."
		 ::= { agentDCBXGroup 2 }
		
      agentDCBXPFCConfigEntry OBJECT-TYPE
		 SYNTAX      AgentDCBXPFCConfigEntry
		 MAX-ACCESS  not-accessible
		 STATUS      current
		 DESCRIPTION
					 "Table of Data center bridging exchange configurations
					 for the specified interface."
		 INDEX       { agentDCBXifIndex }
		 ::= { agentDCBXPFCConfigTable 1 }
      
      AgentDCBXPFCConfigEntry ::= SEQUENCE {
		   agentDCBXPFCEnableMode
			   INTEGER,
		   agentDCBXPFCAdvertiseMode
			   INTEGER,
		   agentDCBXPFCWillingMode
			   INTEGER,
		   agentDCBXPFCPriorityMask
			   Unsigned32,
		   agentDCBXPFCMaxTrafficClass
			   Unsigned32,
		   agentDCBXPFCOperVersion
			   Unsigned32,
		   agentDCBXPFCOperMaxVersion
			   Unsigned32,
		   agentDCBXPFCOperErrors
			   DisplayString,
		   agentDCBXPFCOperMode
			   INTEGER,
		   agentDCBXPFCOperPeerSyncd
			   INTEGER,
		   agentDCBXPFCOperPriorityMask
			   Unsigned32,
		   agentDCBXPFCOperMaxTrafficClass
			   Unsigned32,
		   agentDCBXPFCPeerLocalifIndex
			   InterfaceIndex,
		   agentDCBXPFCPeerStatus
			   INTEGER,
		   agentDCBXPFCPeerEnableMode
			   INTEGER,
		   agentDCBXPFCPeerWillingMode
			   INTEGER,
		   agentDCBXPFCPeerPriorityMask
			   Unsigned32,
		   agentDCBXPFCPeerMaxTrafficClass
			   Unsigned32,
		   agentDCBXPFCDCBXOperVersion
			   INTEGER
		   }
      
      agentDCBXPFCEnableMode OBJECT-TYPE
      	 SYNTAX      INTEGER {
							true(1),
							false(2)
							}
      	 MAX-ACCESS  read-only
      	 STATUS      current
      	 DESCRIPTION
      				 "Show the enable mode setting for DCBX PFC feature."
      	 ::= { agentDCBXPFCConfigEntry 1 }

      agentDCBXPFCAdvertiseMode OBJECT-TYPE
      	 SYNTAX      INTEGER {
							true(1),
							false(2)
							}
      	 MAX-ACCESS  read-only
      	 STATUS      current
      	 DESCRIPTION
      				 "Configure advertise mode setting for DCBX PFC feature."
      	 ::= { agentDCBXPFCConfigEntry 2 }

      agentDCBXPFCWillingMode OBJECT-TYPE
      	 SYNTAX      INTEGER {
							true(1),
							false(2)
							}
      	 MAX-ACCESS  read-write
      	 STATUS      current
      	 DESCRIPTION
      				 "Configure willing mode setting for DCBX PFC feature."
      	 ::= { agentDCBXPFCConfigEntry 3 }

      agentDCBXPFCPriorityMask OBJECT-TYPE
      	 SYNTAX      Unsigned32 (0..255)
      	 MAX-ACCESS  read-only
      	 STATUS      current
      	 DESCRIPTION
      				 "Show the priority mask for DCBX PFC feature."
      	 ::= { agentDCBXPFCConfigEntry 4 }

      agentDCBXPFCMaxTrafficClass OBJECT-TYPE
      	 SYNTAX      Unsigned32 (0..255)
      	 MAX-ACCESS  read-only
      	 STATUS      current
      	 DESCRIPTION
      				 "Show the max traffic class for DCBX PFC feature."
      	 ::= { agentDCBXPFCConfigEntry 5 }

      agentDCBXPFCOperVersion OBJECT-TYPE
      	 SYNTAX      Unsigned32 (0..255)
      	 MAX-ACCESS  read-only
      	 STATUS      current
      	 DESCRIPTION
      				 "Show the version for Operational DCBX PFC feature."
      	 ::= { agentDCBXPFCConfigEntry 6 }

      agentDCBXPFCOperMaxVersion OBJECT-TYPE
      	 SYNTAX      Unsigned32 (0..255)
      	 MAX-ACCESS  read-only
      	 STATUS      current
      	 DESCRIPTION
      				 "Show the max version for Operational DCBX PFC feature."
      	 ::= { agentDCBXPFCConfigEntry 7 }

      agentDCBXPFCOperErrors OBJECT-TYPE
      	 SYNTAX      DisplayString
      	 MAX-ACCESS  read-only
      	 STATUS      current
      	 DESCRIPTION
      				 "Shows error reason for DCBX PFC feature."
      	 ::= { agentDCBXPFCConfigEntry 8 }

      agentDCBXPFCOperMode OBJECT-TYPE
      	 SYNTAX      INTEGER {
							true(1),
							false(2)
							}
      	 MAX-ACCESS  read-only
      	 STATUS      current
      	 DESCRIPTION
      				 "Show the operational mode for DCBX PFC feature."
      	 ::= { agentDCBXPFCConfigEntry 9 }

      agentDCBXPFCOperPeerSyncd OBJECT-TYPE
      	 SYNTAX      INTEGER {
							true(1),
							false(2)
							}
      	 MAX-ACCESS  read-only
      	 STATUS      current
      	 DESCRIPTION
      				 "Show feature sync for Operational DCBX PFC feature."
      	 ::= { agentDCBXPFCConfigEntry 10 }

      agentDCBXPFCOperPriorityMask OBJECT-TYPE
      	 SYNTAX      Unsigned32 (0..255)
      	 MAX-ACCESS  read-only
      	 STATUS      current
      	 DESCRIPTION
      				 "Show the priority mask for Operational DCBX PFC feature."
      	 ::= { agentDCBXPFCConfigEntry 11 }

      agentDCBXPFCOperMaxTrafficClass OBJECT-TYPE
      	 SYNTAX      Unsigned32 (0..255)
      	 MAX-ACCESS  read-only
      	 STATUS      current
      	 DESCRIPTION
      				 "Show the max traffic class for Operational DCBX PFC feature."
      	 ::= { agentDCBXPFCConfigEntry 12 }

      agentDCBXPFCPeerLocalifIndex OBJECT-TYPE
		 SYNTAX      InterfaceIndex
		 MAX-ACCESS  read-only
		 STATUS      current
		 DESCRIPTION
					 "Show the local interface for Peer DCBX PFC feature."
		 ::= { agentDCBXPFCConfigEntry 13 }

      agentDCBXPFCPeerStatus OBJECT-TYPE
      	 SYNTAX      INTEGER {
							notpresent(0),
							successful(1),
							unsuccessful(2)
							}
      	 MAX-ACCESS  read-only
      	 STATUS      current
      	 DESCRIPTION
      				 "Show the status for Peer DCBX PFC feature."
      	 ::= { agentDCBXPFCConfigEntry 14 }

      agentDCBXPFCPeerEnableMode OBJECT-TYPE
      	 SYNTAX      INTEGER {
							true(1),
							false(2)
							}
      	 MAX-ACCESS  read-only
      	 STATUS      current
      	 DESCRIPTION
      				 "Show administrative mode setting for Peer DCBX PFC feature."
      	 ::= { agentDCBXPFCConfigEntry 15 }

      agentDCBXPFCPeerWillingMode OBJECT-TYPE
      	 SYNTAX      INTEGER {
							true(1),
							false(2)
							}
      	 MAX-ACCESS  read-only
      	 STATUS      current
      	 DESCRIPTION
      				 "Show willing mode setting for Peer DCBX PFC feature."
      	 ::= { agentDCBXPFCConfigEntry 16 }

      agentDCBXPFCPeerPriorityMask OBJECT-TYPE
      	 SYNTAX      Unsigned32 (0..255)
      	 MAX-ACCESS  read-only
      	 STATUS      current
      	 DESCRIPTION
      				 "Show priority mask for Peer DCBX PFC feature."
      	 ::= { agentDCBXPFCConfigEntry 17 }

      agentDCBXPFCPeerMaxTrafficClass OBJECT-TYPE
      	 SYNTAX      Unsigned32 (0..255)
      	 MAX-ACCESS  read-only
      	 STATUS      current
      	 DESCRIPTION
      				 "Show the max traffic class for Peer DCBX PFC feature."
      	 ::= { agentDCBXPFCConfigEntry 18 }

	  agentDCBXPFCDCBXOperVersion OBJECT-TYPE
      	 SYNTAX      INTEGER {
							cee(1),
							ieee(2)
							}
      	 MAX-ACCESS  read-only
      	 STATUS      current
      	 DESCRIPTION
      				 "Show the operational version for DCBX PFC feature."
      	 ::= { agentDCBXPFCConfigEntry 19 }
		 
    --**************************************************************************************
    -- DCBX Priority Group Config Table
    --
    --**************************************************************************************
	  agentDCBXPgConfigTable OBJECT-TYPE
		 SYNTAX      SEQUENCE OF AgentDCBXPgConfigEntry
		 MAX-ACCESS  not-accessible
		 STATUS      current
		 DESCRIPTION
					 "Table of Data center bridging exchange Priority Group feature
					 configurations for the specified interface."
		 ::= { agentDCBXGroup 3 }
		
      agentDCBXPgConfigEntry OBJECT-TYPE
		 SYNTAX      AgentDCBXPgConfigEntry
		 MAX-ACCESS  not-accessible
		 STATUS      current
		 DESCRIPTION
					 "Table of Data center bridging exchange Priority Group feature
					 configurations for the specified interface."
		 INDEX       { agentDCBXifIndex }
		 ::= { agentDCBXPgConfigTable 1 }
      
      AgentDCBXPgConfigEntry ::= SEQUENCE {
		   agentDCBXPgEnableMode
			   INTEGER,
		   agentDCBXPgAdvertiseMode
			   INTEGER,
		   agentDCBXPgWillingMode
			   INTEGER,
		   agentDCBXPgGroupBandwidth
			   DisplayString,
		   agentDCBXPgPriorityGroupId
			   DisplayString,
		   agentDCBXPgMaxTrafficClass
			   Unsigned32,
		   agentDCBXPgOperVersion
			   Unsigned32,
		   agentDCBXPgMaxVersion
			   Unsigned32,
		   agentDCBXPgErrorReason
			   DisplayString,
		   agentDCBXPgIsOperational
			   INTEGER,
		   agentDCBXPgSyncedMode
			   INTEGER,
		   agentDCBXPgOperGroupBandwidth
			   DisplayString,
		   agentDCBXPgOperPriorityGroupId
			   DisplayString,
		   agentDCBXPgOperMaxTrafficClass
			   Unsigned32,
		   agentDCBXPgPeerStatus
			   INTEGER,
		   agentDCBXPgPeerEnableMode
			   INTEGER,
		   agentDCBXPgPeerWillingMode
			   INTEGER,
		   agentDCBXPgPeerGroupBandwidth
			   DisplayString,
		   agentDCBXPgPeerPriorityGroupId
			   DisplayString,
		   agentDCBXPgPeerMaxTrafficClass
			   Unsigned32,
		   agentDCBXPgDCBXOperVersion
			   INTEGER
		   }

      agentDCBXPgEnableMode OBJECT-TYPE
      	 SYNTAX      INTEGER {
							true(1),
							false(2)
							}
      	 MAX-ACCESS  read-only
      	 STATUS      current
      	 DESCRIPTION
      				 "Show enable mode setting for DCBX Priority Group feature."
      	 ::= { agentDCBXPgConfigEntry 1 }

      agentDCBXPgAdvertiseMode OBJECT-TYPE
      	 SYNTAX      INTEGER {
							true(1),
							false(2)
							}
      	 MAX-ACCESS  read-only
      	 STATUS      current
      	 DESCRIPTION
      				 "Enable/Disable advertise mode setting for DCBX Priority Group feature."
      	 ::= { agentDCBXPgConfigEntry 2 }

      agentDCBXPgWillingMode OBJECT-TYPE
      	 SYNTAX      INTEGER {
							true(1),
							false(2)
							}
      	 MAX-ACCESS  read-write
      	 STATUS      current
      	 DESCRIPTION
      				 "Enable/Disable willing mode setting for DCBX Priority Group feature."
      	 ::= { agentDCBXPgConfigEntry 3 }

      agentDCBXPgGroupBandwidth OBJECT-TYPE
      	 SYNTAX      DisplayString
      	 MAX-ACCESS  read-only
      	 STATUS      current
      	 DESCRIPTION
      				 "Show a 8 byte array which will be filled
      				 with bandwidth of 8 priority group."
      	 ::= { agentDCBXPgConfigEntry 4 }

      agentDCBXPgPriorityGroupId OBJECT-TYPE
      	 SYNTAX      DisplayString
      	 MAX-ACCESS  read-only
      	 STATUS      current
      	 DESCRIPTION
      				 "Show priority map for Peer DCBX Priority Group feature."
      	 ::= { agentDCBXPgConfigEntry 5 }

      agentDCBXPgMaxTrafficClass OBJECT-TYPE
      	 SYNTAX      Unsigned32 (0..255)
      	 MAX-ACCESS  read-only
      	 STATUS      current
      	 DESCRIPTION
      				 "Show the max traffic class for Peer DCBX Priority Group feature."
      	 ::= { agentDCBXPgConfigEntry 6 }

      agentDCBXPgOperVersion OBJECT-TYPE
      	 SYNTAX      Unsigned32(0..255)
      	 MAX-ACCESS  read-only
      	 STATUS      current
      	 DESCRIPTION
      				 "Show opertional version for DCBX Priority Group feature."
      	 ::= { agentDCBXPgConfigEntry 7 }

      agentDCBXPgMaxVersion OBJECT-TYPE
      	 SYNTAX      Unsigned32(0..255)
      	 MAX-ACCESS  read-only
      	 STATUS      current
      	 DESCRIPTION
      				 "Show max version for DCBX Priority Group feature."
      	 ::= { agentDCBXPgConfigEntry 8 }

      agentDCBXPgErrorReason OBJECT-TYPE
      	 SYNTAX      DisplayString
      	 MAX-ACCESS  read-only
      	 STATUS      current
      	 DESCRIPTION
      				 "Show error reason for DCBX Priority Group feature."
      	 ::= { agentDCBXPgConfigEntry 9 }

      agentDCBXPgIsOperational OBJECT-TYPE
      	 SYNTAX      INTEGER {
							true(1),
							false(2)
							}
      	 MAX-ACCESS  read-only
      	 STATUS      current
      	 DESCRIPTION
      				 "Show the operational mode of the PG for a interface."
      	 ::= { agentDCBXPgConfigEntry 10 }

      agentDCBXPgSyncedMode OBJECT-TYPE
      	 SYNTAX      INTEGER {
							true(1),
							false(2)
							}
      	 MAX-ACCESS  read-only
      	 STATUS      current
      	 DESCRIPTION
      				 "Show feature sync for DCBX Priority Group feature."
      	 ::= { agentDCBXPgConfigEntry 11 }

      agentDCBXPgOperGroupBandwidth OBJECT-TYPE
      	 SYNTAX      DisplayString
      	 MAX-ACCESS  read-only
      	 STATUS      current
      	 DESCRIPTION
      				 "Show a 8 byte array which will be filled
      				 with bandwidth of 8 priority group."
      	 ::= { agentDCBXPgConfigEntry 12 }

      agentDCBXPgOperPriorityGroupId OBJECT-TYPE
      	 SYNTAX      DisplayString
      	 MAX-ACCESS  read-only
      	 STATUS      current
      	 DESCRIPTION
      				 "Show the operational priority map of the PG for a interface."
      	 ::= { agentDCBXPgConfigEntry 13 }

      agentDCBXPgOperMaxTrafficClass OBJECT-TYPE
      	 SYNTAX      Unsigned32 (0..255)
      	 MAX-ACCESS  read-only
      	 STATUS      current
      	 DESCRIPTION
      				 "Show the max traffic class for Operational DCBX Priority Group feature."
      	 ::= { agentDCBXPgConfigEntry 14 }

      agentDCBXPgPeerStatus OBJECT-TYPE
      	 SYNTAX      INTEGER {
							notpresent(0),
							successful(1),
							unsuccessful(2)
							}
      	 MAX-ACCESS  read-only
      	 STATUS      current
      	 DESCRIPTION
      				 "Show status (Error bit) for Peer DCBX Priority Group feature."
      	 ::= { agentDCBXPgConfigEntry 15 }

      agentDCBXPgPeerEnableMode OBJECT-TYPE
      	 SYNTAX      INTEGER {
							true(1),
							false(2)
							}
      	 MAX-ACCESS  read-only
      	 STATUS      current
      	 DESCRIPTION
      				 "Show enable mode setting for Peer DCBX Priority Group feature."
      	 ::= { agentDCBXPgConfigEntry 16 }

      agentDCBXPgPeerWillingMode OBJECT-TYPE
      	 SYNTAX      INTEGER {
							true(1),
							false(2)
							}
      	 MAX-ACCESS  read-only
      	 STATUS      current
      	 DESCRIPTION
      				 "Show willing mode setting for Peer DCBX Priority Group feature."
      	 ::= { agentDCBXPgConfigEntry 17 }

      agentDCBXPgPeerGroupBandwidth OBJECT-TYPE
      	 SYNTAX      DisplayString
      	 MAX-ACCESS  read-only
      	 STATUS      current
      	 DESCRIPTION
      				 "Show a 8 byte array which will be filled
      				 with bandwidth of 8 priority group."
      	 ::= { agentDCBXPgConfigEntry 18 }

      agentDCBXPgPeerPriorityGroupId OBJECT-TYPE
      	 SYNTAX      DisplayString
      	 MAX-ACCESS  read-only
      	 STATUS      current
      	 DESCRIPTION
      				 "Show priority map for Peer DCBX Priority Group feature."
      	 ::= { agentDCBXPgConfigEntry 19 }

      agentDCBXPgPeerMaxTrafficClass OBJECT-TYPE
      	 SYNTAX      Unsigned32 (0..255)
      	 MAX-ACCESS  read-only
      	 STATUS      current
      	 DESCRIPTION
      				 "Show the max traffic class for Peer DCBX Priority Group feature."
      	 ::= { agentDCBXPgConfigEntry 20 }
		
     agentDCBXPgDCBXOperVersion OBJECT-TYPE
      	 SYNTAX      INTEGER {
							cee(1),
							ieee(2)
							}
      	 MAX-ACCESS  read-only
      	 STATUS      current
      	 DESCRIPTION
      				 "Show the operational version for DCBX Priority Group feature."
      	 ::= { agentDCBXPgConfigEntry 21 }
 

   -- 
   -- ***********************************************************
   -- 
   -- Textual Conventions
   -- 
   -- ***********************************************************
   
	BridgeEvbTLVTC ::= TEXTUAL-CONVENTION
	    STATUS     current
	    DESCRIPTION
	           "EVB TLV structure."
	    SYNTAX   BITS {
	                vdpCapable        (0),
	                ecpCapable        (1),
	                ecpRTE            (2),
	                vdpTimerCapable   (3),
	                reflectiveRelayCap(14),
	                stdForwardingCap  (15)
	                }

    --**************************************************************************************
    -- EVB Group
    --
    --**************************************************************************************
	  agentEvbGroup                             OBJECT IDENTIFIER ::= { switchingExtension 119 }

    --**************************************************************************************
    -- EVB Config Table
    --
    --**************************************************************************************
	  agentEvbConfigTable OBJECT-TYPE
		 SYNTAX      SEQUENCE OF AgentEvbConfigEntry
		 MAX-ACCESS  not-accessible
		 STATUS      current
		 DESCRIPTION
					 "Table of Edge Virtual Bridging feature
					 configurations for the specified interface."
		 ::= { agentEvbGroup 1 }
		
      agentEvbConfigEntry OBJECT-TYPE
		 SYNTAX      AgentEvbConfigEntry
		 MAX-ACCESS  not-accessible
		 STATUS      current
		 DESCRIPTION
					 "Table of Edge Virtual Bridging feature
					 configurations for the specified interface."
		 INDEX       { agentEvbifIndex }
		 ::= { agentEvbConfigTable 1 }
      
      AgentEvbConfigEntry ::= SEQUENCE {
		   agentEvbifIndex
			   INTEGER,
		   agentEvbAdminMode
			   INTEGER,
		   agentEvbCapability
		       BridgeEvbTLVTC,
		   agentEvbForwardingMode
		       BridgeEvbTLVTC,
		   agentEvbRetransmissionExp
		       Unsigned32,
		   agentEvbOperCapability
		       BridgeEvbTLVTC,
		   agentEvbOperForwardingMode
		       BridgeEvbTLVTC,
		   agentEvbOperRetransmissionExp
		       Unsigned32
		   }

      agentEvbifIndex OBJECT-TYPE
      	 SYNTAX      INTEGER (1..53)
      	 MAX-ACCESS  read-only
      	 STATUS      current
      	 DESCRIPTION
      				 "Show interface index for Evb feature."
      	 ::= { agentEvbConfigEntry 1 }

      agentEvbAdminMode OBJECT-TYPE
      	 SYNTAX      INTEGER {
							enable(1),
							disable(2)
							}
      	 MAX-ACCESS  read-write
      	 STATUS      current
      	 DESCRIPTION
      				 "Enable/disable mode setting for Evb feature."
      	 ::= { agentEvbConfigEntry 2 }

      agentEvbCapability OBJECT-TYPE
      	 SYNTAX      BridgeEvbTLVTC
      	 MAX-ACCESS  read-only
      	 STATUS      current
      	 DESCRIPTION
      				 "Configure capabilities for Evb feature."
      	 ::= { agentEvbConfigEntry 3 }

      agentEvbForwardingMode OBJECT-TYPE
      	 SYNTAX      BridgeEvbTLVTC
      	 MAX-ACCESS  read-only
      	 STATUS      current
      	 DESCRIPTION
      				 "Configure forwarding mode for Evb feature."
      	 ::= { agentEvbConfigEntry 4 }

      agentEvbRetransmissionExp OBJECT-TYPE
      	 SYNTAX      Unsigned32
      	 MAX-ACCESS  read-write
      	 STATUS      current
      	 DESCRIPTION
      				 "Configure RTE for Evb feature."
      	 ::= { agentEvbConfigEntry 5 }

      agentEvbOperCapability OBJECT-TYPE
      	 SYNTAX      BridgeEvbTLVTC
      	 MAX-ACCESS  read-only
      	 STATUS      current
      	 DESCRIPTION
      				 "Show current capabilities for Evb feature."
      	 ::= { agentEvbConfigEntry 6 }

      agentEvbOperForwardingMode OBJECT-TYPE
      	 SYNTAX      BridgeEvbTLVTC
      	 MAX-ACCESS  read-only
      	 STATUS      current
      	 DESCRIPTION
      				 "Show forwarding mode for Evb feature."
      	 ::= { agentEvbConfigEntry 7 }

      agentEvbOperRetransmissionExp OBJECT-TYPE
      	 SYNTAX      Unsigned32
      	 MAX-ACCESS  read-only
      	 STATUS      current
      	 DESCRIPTION
      				 "Show RTE for Evb feature."
      	 ::= { agentEvbConfigEntry 8 }

    --**************************************************************************************
    -- EVB VSI Group
    --
    --**************************************************************************************
	  agentEvbVsiGroup                             OBJECT IDENTIFIER ::= { agentEvbGroup 2 }
	  
    --**************************************************************************************
    -- EVB VSI Table
    --
    --**************************************************************************************
	  agentEvbVsiTable OBJECT-TYPE
		 SYNTAX      SEQUENCE OF AgentEvbVsiEntry
		 MAX-ACCESS  not-accessible
		 STATUS      current
		 DESCRIPTION
					 "Table of Edge Virtual Bridging VSI feature
					 status for the specified interface."
		 ::= { agentEvbVsiGroup 1 }
		
      agentEvbVsiEntry OBJECT-TYPE
		 SYNTAX      AgentEvbVsiEntry
		 MAX-ACCESS  not-accessible
		 STATUS      current
		 DESCRIPTION
					 "Table of Edge Virtual Bridging VSI feature
					 status for the specified interface."
		 INDEX       { agentEvbifIndex,agentEvbVsiInstanceId }
		 ::= { agentEvbVsiTable 1 }
      
      AgentEvbVsiEntry ::= SEQUENCE {
		   agentEvbVsiInstanceId
			   DisplayString,
		   agentEvbVsiMgrId
			   Unsigned32,
		   agentEvbVsiId
			   Unsigned32,
		   agentEvbVsiVersion
			   Unsigned32,
		   agentEvbVsiMode
			   INTEGER,
		   agentEvbVsiState
			   INTEGER,
		   agentEvbVsiNumMacs
			   Unsigned32
		   }

      agentEvbVsiInstanceId OBJECT-TYPE
      	 SYNTAX      DisplayString (SIZE(16))
      	 MAX-ACCESS  read-only
      	 STATUS      current
      	 DESCRIPTION
      				 "Show interface instance id for Evb Vsi feature."
      	 ::= { agentEvbVsiEntry 1 }

      agentEvbVsiMgrId OBJECT-TYPE
      	 SYNTAX      Unsigned32
      	 MAX-ACCESS  read-only
      	 STATUS      current
      	 DESCRIPTION
      				 "Show interface mgr id for Evb Vsi feature."
      	 ::= { agentEvbVsiEntry 2 }

      agentEvbVsiId OBJECT-TYPE
      	 SYNTAX      Unsigned32
      	 MAX-ACCESS  read-only
      	 STATUS      current
      	 DESCRIPTION
      				 "Show id for Evb Vsi feature."
      	 ::= { agentEvbVsiEntry 3 }

      agentEvbVsiVersion OBJECT-TYPE
      	 SYNTAX      Unsigned32
      	 MAX-ACCESS  read-only
      	 STATUS      current
      	 DESCRIPTION
      				 "Show interface version for Evb Vsi feature."
      	 ::= { agentEvbVsiEntry 4 }

      agentEvbVsiMode OBJECT-TYPE
      	 SYNTAX      INTEGER {
      	                    preassociate(1),
      	                    preassocerr(2),
      	                    associate(3),
      	                    deassociate(4)
      	                    }
      	 MAX-ACCESS  read-only
      	 STATUS      current
      	 DESCRIPTION
      				 "Show interface mode for Evb Vsi feature."
      	 ::= { agentEvbVsiEntry 5 }

      agentEvbVsiState OBJECT-TYPE
      	 SYNTAX      INTEGER {
      	                    unassociated(1),
      	                    assocprocessing(2),
      	                    associated(3),
      	                    preassocprocessing(4),
      	                    preassociated(5),
      	                    deassocprocessing(6),
      	                    exit(7)
      	                    }
      	 MAX-ACCESS  read-only
      	 STATUS      current
      	 DESCRIPTION
      				 "Show interface state for Evb Vsi feature."
      	 ::= { agentEvbVsiEntry 6 }

      agentEvbVsiNumMacs OBJECT-TYPE
      	 SYNTAX      Unsigned32
      	 MAX-ACCESS  read-only
      	 STATUS      current
      	 DESCRIPTION
      				 "Show interface number of Macs for Evb Vsi feature."
      	 ::= { agentEvbVsiEntry 7 }

    --**************************************************************************************
    -- EVB VSI Mac Table
    --
    --**************************************************************************************
	  agentEvbVsiMacTable OBJECT-TYPE
		 SYNTAX      SEQUENCE OF AgentEvbVsiMacEntry
		 MAX-ACCESS  not-accessible
		 STATUS      current
		 DESCRIPTION
					 "Table of Edge Virtual Bridging VSI Mac feature
					 status for the specified interface."
		 ::= { agentEvbVsiGroup 2 }
		
      agentEvbVsiMacEntry OBJECT-TYPE
		 SYNTAX      AgentEvbVsiMacEntry
		 MAX-ACCESS  not-accessible
		 STATUS      current
		 DESCRIPTION
					 "Table of Edge Virtual Bridging VSI Mac feature
					 status for the specified interface."
		 INDEX       { agentEvbifIndex,agentEvbVsiInstanceId,agentEvbVsiMacAddress,agentEvbVsiVlanId }
		 ::= { agentEvbVsiMacTable 1 }
      
      AgentEvbVsiMacEntry ::= SEQUENCE {
		   agentEvbVsiMacAddress
			   MacAddress,
		   agentEvbVsiVlanId
			   INTEGER
		   }
      	 
      agentEvbVsiMacAddress OBJECT-TYPE
      	 SYNTAX      MacAddress
      	 MAX-ACCESS  read-only
      	 STATUS      current
      	 DESCRIPTION
      				 "Show interface MacAddress for Evb Vsi feature."
      	 ::= { agentEvbVsiMacEntry 1 }

      agentEvbVsiVlanId OBJECT-TYPE
      	 SYNTAX      INTEGER (1..4093)
      	 MAX-ACCESS  read-only
      	 STATUS      current
      	 DESCRIPTION
      				 "Show interface VlanId for Evb Vsi feature."
      	 ::= { agentEvbVsiMacEntry 2 }
    --**************************************************************************************
    -- VMTracer Group
    --
    --**************************************************************************************
	  agentVMTracerGroup                             OBJECT IDENTIFIER ::= { switchingExtension 120 }

    --**************************************************************************************
    -- VMTracer Interface Control Table
    --
    --**************************************************************************************
	  agentVMTracerIfCtlTable OBJECT-TYPE
		 SYNTAX      SEQUENCE OF AgentVMTracerIfCtlEntry
		 MAX-ACCESS  not-accessible
		 STATUS      current
		 DESCRIPTION
					 "Table of VM Tracer feature
					 status for the specified interface."
		 ::= { agentVMTracerGroup 1 }
		
      agentVMTracerIfCtlEntry OBJECT-TYPE
		 SYNTAX      AgentVMTracerIfCtlEntry
		 MAX-ACCESS  not-accessible
		 STATUS      current
		 DESCRIPTION
					 "Table of VM Tracer feature
					 status for the specified interface."
		 INDEX       { agentVMTracerIfIndex }
		 ::= { agentVMTracerIfCtlTable 1 }
      
      AgentVMTracerIfCtlEntry ::= SEQUENCE {
		   agentVMTracerIfIndex
			   INTEGER,
		   agentVMTracerAdminMode
			   INTEGER
		   }
      	 
      agentVMTracerIfIndex OBJECT-TYPE
      	 SYNTAX      INTEGER (1..65535)
      	 MAX-ACCESS  read-only
      	 STATUS      current
      	 DESCRIPTION
      				 "Show interface index for VM Tracer feature."
      	 ::= { agentVMTracerIfCtlEntry 1 }

      agentVMTracerAdminMode OBJECT-TYPE
      	 SYNTAX      INTEGER {
      	                    enable(1),
  	                     	disable(2)
      	                    }
      	 MAX-ACCESS  read-write
      	 STATUS      current
      	 DESCRIPTION
      				 "Enable/Disable VM Tracer mode for specified interface."
      	 ::= { agentVMTracerIfCtlEntry 2 }

    --**************************************************************************************
    -- VMTracer Session Table
    --
    --**************************************************************************************
	  agentVMTracerSessionTable OBJECT-TYPE
		 SYNTAX      SEQUENCE OF AgentVMTracerSessionEntry
		 MAX-ACCESS  not-accessible
		 STATUS      current
		 DESCRIPTION
					 "Table of VM Tracer feature session."
		 ::= { agentVMTracerGroup 2 }
		
      agentVMTracerSessionEntry OBJECT-TYPE
		 SYNTAX      AgentVMTracerSessionEntry
		 MAX-ACCESS  not-accessible
		 STATUS      current
		 DESCRIPTION
					 "Table of VM Tracer feature session."
		 INDEX       { agentVMTracerSessionIndex }
		 ::= { agentVMTracerSessionTable 1 }
      
      AgentVMTracerSessionEntry ::= SEQUENCE {
		   agentVMTracerSessionIndex
			   INTEGER,
		   agentVMTracerSessionName
			   DisplayString,
		   agentVMTracerSessionUrl
			   DisplayString,
		   agentVMTracerSessionUsername
			   DisplayString,
		   agentVMTracerSessionPassword
			   DisplayString,
		   agentVMTracerSessionAutoVlanMode
			   INTEGER,
		   agentVMTracerSessionAllowVlan
			   VlanList,
		   agentVMTracerSessionConnectionStatus
		       INTEGER,
		   agentVMTracerSessionClear
		       INTEGER
		   }

      agentVMTracerSessionIndex OBJECT-TYPE
      	 SYNTAX      INTEGER (0..3)
      	 MAX-ACCESS  read-only
      	 STATUS      current
      	 DESCRIPTION
      				 "Index of VM Tracer feature session."
      	 ::= { agentVMTracerSessionEntry 1 }

      agentVMTracerSessionName OBJECT-TYPE
      	 SYNTAX      DisplayString(SIZE(0..32))
      	 MAX-ACCESS  read-write
      	 STATUS      current
      	 DESCRIPTION
      				 "Name of VM Tracer feature session."
      	 ::= { agentVMTracerSessionEntry 2 }

      agentVMTracerSessionUrl OBJECT-TYPE
      	 SYNTAX      DisplayString(SIZE(0..64))
      	 MAX-ACCESS  read-write
      	 STATUS      current
      	 DESCRIPTION
      				 "Url of VM Tracer feature session."
      	 ::= { agentVMTracerSessionEntry 3 }

      agentVMTracerSessionUsername OBJECT-TYPE
      	 SYNTAX      DisplayString(SIZE(0..32))
      	 MAX-ACCESS  read-write
      	 STATUS      current
      	 DESCRIPTION
      				 "Username of VM Tracer feature session."
      	 ::= { agentVMTracerSessionEntry 4 }

      agentVMTracerSessionPassword OBJECT-TYPE
      	 SYNTAX      DisplayString(SIZE(0..32))
      	 MAX-ACCESS  read-write
      	 STATUS      current
      	 DESCRIPTION
      				 "Password of VM Tracer feature session."
      	 ::= { agentVMTracerSessionEntry 5 }

      agentVMTracerSessionAutoVlanMode OBJECT-TYPE
      	 SYNTAX      INTEGER {
      	                    enable(1),
      	                    disable(2)
      	                    }
      	 MAX-ACCESS  read-write
      	 STATUS      current
      	 DESCRIPTION
      				 "AutoVlan mode of VM Tracer feature session."
      	 ::= { agentVMTracerSessionEntry 6 }

      agentVMTracerSessionAllowVlan OBJECT-TYPE
      	 SYNTAX      VlanList
      	 MAX-ACCESS  read-write
      	 STATUS      current
      	 DESCRIPTION
      				 "Allow vlan range of VM Tracer feature session."
      	 ::= { agentVMTracerSessionEntry 7 }

      agentVMTracerSessionConnectionStatus OBJECT-TYPE
      	 SYNTAX      INTEGER {
      	                    connected(1),
      	                    disconnected(2)
      	                    }
      	 MAX-ACCESS  read-only
      	 STATUS      current
      	 DESCRIPTION
      				 "Connection status of VM Tracer feature session."
      	 ::= { agentVMTracerSessionEntry 8 }

      agentVMTracerSessionClear OBJECT-TYPE
      	 SYNTAX      INTEGER {
      	                    clear(1)
      	                    }
      	 MAX-ACCESS  read-write
      	 STATUS      current
      	 DESCRIPTION
      				 "Clear current VM Tracer feature session."
      	 ::= { agentVMTracerSessionEntry 9 }

    --**************************************************************************************
    -- VMTracer VM Table
    --
    --**************************************************************************************
	  agentVMTracerVMTable OBJECT-TYPE
		 SYNTAX      SEQUENCE OF AgentVMTracerVMEntry
		 MAX-ACCESS  not-accessible
		 STATUS      current
		 DESCRIPTION
					 "Table of VM Tracer feature vm."
		 ::= { agentVMTracerGroup 3 }
		
      agentVMTracerVMEntry OBJECT-TYPE
		 SYNTAX      AgentVMTracerVMEntry
		 MAX-ACCESS  not-accessible
		 STATUS      current
		 DESCRIPTION
					 "Table of VM Tracer feature vm."
		 INDEX       { agentVMTracerSessionIndex,agentVMTracerVMIndex }
		 ::= { agentVMTracerVMTable 1 }
      
      AgentVMTracerVMEntry ::= SEQUENCE {
		   agentVMTracerVMIndex
			   INTEGER,
		   agentVMTracerVMName
			   DisplayString,
		   agentVMTracerVMInterface
			   DisplayString,
		   agentVMTracerVMAdapter
			   DisplayString,
		   agentVMTracerVMMacAddress
			   DisplayString,
		   agentVMTracerVMPortGroup
			   DisplayString,
		   agentVMTracerVMVlanId
			   Unsigned32,
		   agentVMTracerVMSwitch
			   DisplayString,
		   agentVMTracerVMHost
			   DisplayString,
		   agentVMTracerVMHostCpuSpeed
			   DisplayString,
		   agentVMTracerVMHostMemory
			   DisplayString,
		   agentVMTracerVMHostSystem
			   DisplayString,
		   agentVMTracerVMHostVendor
			   DisplayString,
		   agentVMTracerVMHostCpuCores
			   Unsigned32,
		   agentVMTracerVMHostCpuPackages
			   Unsigned32
		   }

      agentVMTracerVMIndex OBJECT-TYPE
      	 SYNTAX      INTEGER (1..65535)
      	 MAX-ACCESS  read-only
      	 STATUS      current
      	 DESCRIPTION
      				 "Index of VM Tracer feature vm."
      	 ::= { agentVMTracerVMEntry 1 }

      agentVMTracerVMName OBJECT-TYPE
      	 SYNTAX      DisplayString
      	 MAX-ACCESS  read-only
      	 STATUS      current
      	 DESCRIPTION
      				 "Name of VM Tracer feature vm."
      	 ::= { agentVMTracerVMEntry 2 }

      agentVMTracerVMInterface OBJECT-TYPE
      	 SYNTAX      DisplayString
      	 MAX-ACCESS  read-only
      	 STATUS      current
      	 DESCRIPTION
      				 "Interface of VM Tracer feature vm."
      	 ::= { agentVMTracerVMEntry 3 }

      agentVMTracerVMAdapter OBJECT-TYPE
      	 SYNTAX      DisplayString
      	 MAX-ACCESS  read-only
      	 STATUS      current
      	 DESCRIPTION
      				 "Adapter of VM Tracer feature vm."
      	 ::= { agentVMTracerVMEntry 4 }

      agentVMTracerVMMacAddress OBJECT-TYPE
      	 SYNTAX      DisplayString
      	 MAX-ACCESS  read-only
      	 STATUS      current
      	 DESCRIPTION
      				 "MacAddress of VM Tracer feature vm."
      	 ::= { agentVMTracerVMEntry 5 }

      agentVMTracerVMPortGroup OBJECT-TYPE
      	 SYNTAX      DisplayString
      	 MAX-ACCESS  read-only
      	 STATUS      current
      	 DESCRIPTION
      				 "PortGroup of VM Tracer feature vm."
      	 ::= { agentVMTracerVMEntry 6 }

      agentVMTracerVMVlanId OBJECT-TYPE
      	 SYNTAX      Unsigned32
      	 MAX-ACCESS  read-only
      	 STATUS      current
      	 DESCRIPTION
      				 "VlanId of VM Tracer feature vm."
      	 ::= { agentVMTracerVMEntry 7 }

      agentVMTracerVMSwitch OBJECT-TYPE
      	 SYNTAX      DisplayString
      	 MAX-ACCESS  read-only
      	 STATUS      current
      	 DESCRIPTION
      				 "Switch of VM Tracer feature vm."
      	 ::= { agentVMTracerVMEntry 8 }

      agentVMTracerVMHost OBJECT-TYPE
      	 SYNTAX      DisplayString
      	 MAX-ACCESS  read-only
      	 STATUS      current
      	 DESCRIPTION
      				 "Host of VM Tracer feature vm."
      	 ::= { agentVMTracerVMEntry 9 }

      agentVMTracerVMHostCpuSpeed OBJECT-TYPE
      	 SYNTAX      DisplayString
      	 MAX-ACCESS  read-only
      	 STATUS      current
      	 DESCRIPTION
      				 "Host Cpu Speed of VM Tracer feature vm."
      	 ::= { agentVMTracerVMEntry 10 }

      agentVMTracerVMHostMemory OBJECT-TYPE
      	 SYNTAX      DisplayString
      	 MAX-ACCESS  read-only
      	 STATUS      current
      	 DESCRIPTION
      				 "Host Memory of VM Tracer feature vm."
      	 ::= { agentVMTracerVMEntry 11 }

      agentVMTracerVMHostSystem OBJECT-TYPE
      	 SYNTAX      DisplayString
      	 MAX-ACCESS  read-only
      	 STATUS      current
      	 DESCRIPTION
      				 "Host System of VM Tracer feature vm."
      	 ::= { agentVMTracerVMEntry 12 }

      agentVMTracerVMHostVendor OBJECT-TYPE
      	 SYNTAX      DisplayString
      	 MAX-ACCESS  read-only
      	 STATUS      current
      	 DESCRIPTION
      				 "Host Vendor of VM Tracer feature vm."
      	 ::= { agentVMTracerVMEntry 13 }

      agentVMTracerVMHostCpuCores OBJECT-TYPE
      	 SYNTAX      Unsigned32
      	 MAX-ACCESS  read-only
      	 STATUS      current
      	 DESCRIPTION
      				 "Host Cpu Cores of VM Tracer feature vm."
      	 ::= { agentVMTracerVMEntry 14 }

      agentVMTracerVMHostCpuPackages OBJECT-TYPE
      	 SYNTAX      Unsigned32
      	 MAX-ACCESS  read-only
      	 STATUS      current
      	 DESCRIPTION
      				 "Host Cpu Packages of VM Tracer feature vm."
      	 ::= { agentVMTracerVMEntry 15 }
END
