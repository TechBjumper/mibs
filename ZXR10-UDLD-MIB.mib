--  ********************************************************
--  $Id: ZXR10-UDLD.mib 2008-10-21 01:34:21Z LiXuwen $
--
--  ZXR10-UDLD.mib: ZXR10 UDLD MIB file
--
--  Oct. 2008, LiXuwen
--  Copyright(c) 2008 by ZTE Corporation
--  All rights reserved
--
--  ********************************************************

ZXR10-UDLD-MIB DEFINITIONS ::= BEGIN

IMPORTS
    MODULE-IDENTITY,
    OBJECT-TYPE,
    Unsigned32
        FROM SNMPv2-SMI

    TEXTUAL-CONVENTION,    
--    TruthValue
--        FROM SNMPv2-TC   
        
    MacAddress      
        FROM SNMPv2-TC -- [RFC2579] 

    ifIndex
        FROM RFC1213-MIB
             
    zxr10					    
    	FROM ZXR10-SMI
   
     ;


    zxr10UdldMIB MODULE-IDENTITY

        LAST-UPDATED "200810210000Z"  -- October 21, 2008

        ORGANIZATION "ZTE Corporation"

        CONTACT-INFO
            "ZTE Corporation

             Nanjing Institute of ZTE Corporation

             No.68 ZiJinghua Rd. YuHuatai District, Nanjing, China

             Tel: +86-25-52870000"

        DESCRIPTION
            "ZXROS V4.8.30 UDLD MIB"
        ::= { zxr10 313 } 
                                              
    zxr10UdldMibObjects  OBJECT IDENTIFIER ::= { zxr10UdldMIB  1 }


--TEXTUAL-CONVENTION

    UINT32 ::=
           Unsigned32
    -- This data type is used to unsigned integer.

    Char ::=
         OCTET STRING
    -- This data type is used to model textual information taken
    -- from the NVT ASCII character set.  By convention, objects
    -- with this syntax are declared as having 0-65535 characters.
                                        
    UdldPortMode ::= TEXTUAL-CONVENTION
        DISPLAY-HINT  "d"
        STATUS        current
        DESCRIPTION   "Udld Port Mode"
        SYNTAX        INTEGER
                      {      
                         normal    (0),
                         aggressive (1)          
                      }
                                    

    UdldPortState ::= TEXTUAL-CONVENTION
        DISPLAY-HINT  "d"
        STATUS        current
        DESCRIPTION   "Udld Port State"
        SYNTAX        INTEGER
                      {    
                         disable(0),
                         probe(1),
                         alwaysHello(2),
                         peerBuild(3),
                         bidirection(4),
                         unidirection(5)                         
                      }



-- groups in zxr10UdldMibObjects

      zxr10PortUdldMibPara      OBJECT IDENTIFIER ::= { zxr10UdldMibObjects  1 }

--      zxr10PortUdldMibPara       OBJECT IDENTIFIER ::= { zxr10UdldMibObjects  2 }


---zxr10PortUdldMibPara

	  portUdldMibTable	OBJECT-TYPE
	      SYNTAX		  SEQUENCE OF PortUdldMibEntry
	      MAX-ACCESS	  not-accessible
	      STATUS		  current
	      DESCRIPTION     "Configure Udld Port parameters."
	  ::=  { zxr10PortUdldMibPara  1 }

	  portUdldMibEntry	OBJECT-TYPE
	      SYNTAX		  PortUdldMibEntry
	      MAX-ACCESS	  not-accessible
	      STATUS		  current
	      DESCRIPTION     "Each row index by ifIndex And contain imformation of Udld Port."
		  INDEX		      {  ifIndex  }
    ::=  { portUdldMibTable 1 }

	  PortUdldMibEntry
	  ::=  SEQUENCE
	  {    
	       portUdldMibDeviceID                Char,
           portUdldMibDeviceName              Char,
           portUdldMibPortID                  Char,
           portUdldMibEnable                  INTEGER,
           portUdldMibMode                    UdldPortMode,
           portUdldMibCurrentState            UdldPortState,
           portUdldMibRecoveryEnable          INTEGER,
           portUdldMibRecoveryTimer           UINT32,
           portUdldMibMsgTimer                UINT32,
      
           portUdldMibNeighbour00DeviceID   Char,
           portUdldMibNeighbour00PortID     Char,
           portUdldMibNeighbour01DeviceID   Char,
           portUdldMibNeighbour01PortID     Char,
           portUdldMibNeighbour02DeviceID   Char,
           portUdldMibNeighbour02PortID     Char,
           portUdldMibNeighbour03DeviceID   Char,
           portUdldMibNeighbour03PortID     Char,
           portUdldMibNeighbour04DeviceID   Char,
           portUdldMibNeighbour04PortID     Char,
           portUdldMibNeighbour05DeviceID   Char,
           portUdldMibNeighbour05PortID     Char,
           portUdldMibNeighbour06DeviceID   Char,
           portUdldMibNeighbour06PortID     Char,
           portUdldMibNeighbour07DeviceID   Char,
           portUdldMibNeighbour07PortID     Char,
           portUdldMibNeighbour08DeviceID   Char,
           portUdldMibNeighbour08PortID     Char,
           portUdldMibNeighbour09DeviceID   Char,
           portUdldMibNeighbour09PortID     Char,
           portUdldMibNeighbour10DeviceID   Char,
           portUdldMibNeighbour10PortID     Char, 
           portUdldMibNeighbour11DeviceID   Char,
           portUdldMibNeighbour11PortID     Char, 
           portUdldMibNeighbour12DeviceID   Char,
           portUdldMibNeighbour12PortID     Char,  
           portUdldMibNeighbour13DeviceID   Char,
           portUdldMibNeighbour13PortID     Char,       
           portUdldMibNeighbour14DeviceID   Char,
           portUdldMibNeighbour14PortID     Char,      
           portUdldMibNeighbour15DeviceID   Char,
           portUdldMibNeighbour15PortID     Char  
 	  } 
 	  
	  portUdldMibDeviceID   OBJECT-TYPE
            SYNTAX		  Char
		    MAX-ACCESS	  read-only
		    STATUS		  current
		    DESCRIPTION   "Port Udld Mib DeviceID(Mac)."
	  ::=  { portUdldMibEntry  1 }

	  portUdldMibDeviceName   OBJECT-TYPE
          SYNTAX		  Char
	      MAX-ACCESS	  read-only
		  STATUS		  current
		  DESCRIPTION     "Port Udld Mib Device Name."
	  ::=  { portUdldMibEntry  2 }

	  portUdldMibPortID   OBJECT-TYPE
            SYNTAX		  Char
		    MAX-ACCESS	  read-only
		    STATUS		  current
		    DESCRIPTION   "Port Udld Mib PortID."
	  ::=  { portUdldMibEntry  3 }

	  portUdldMibEnable   OBJECT-TYPE
            SYNTAX		  INTEGER
		    MAX-ACCESS	  read-only
		    STATUS		  current
		    DESCRIPTION   "Port Udld Mib Enable."
	  ::=  { portUdldMibEntry  4 }

	  portUdldMibMode     OBJECT-TYPE
            SYNTAX		  UdldPortMode
		    MAX-ACCESS	  read-only
		    STATUS		  current
		    DESCRIPTION   "Port Udld Mib Mode."
	  ::=  { portUdldMibEntry  5 }
                           
	  portUdldMibCurrentState   OBJECT-TYPE
            SYNTAX		    UdldPortState
		    MAX-ACCESS	    read-only
		    STATUS		    current
		    DESCRIPTION     "Port Udld Mib Current State."
	  ::=  { portUdldMibEntry  6 }
                 	      
	  portUdldMibRecoveryEnable   OBJECT-TYPE
            SYNTAX		    INTEGER
		    MAX-ACCESS	    read-only
		    STATUS		    current
		    DESCRIPTION     "Port Udld Mib Recovery Enable."
	  ::=  { portUdldMibEntry  7 }

	  portUdldMibRecoveryTimer   OBJECT-TYPE
            SYNTAX		    UINT32
		    MAX-ACCESS	    read-only
		    STATUS		    current
		    DESCRIPTION     "Port Udld Mib Recovery Timer."
	  ::=  { portUdldMibEntry  8 }

	  portUdldMibMsgTimer   OBJECT-TYPE
            SYNTAX		    UINT32
		    MAX-ACCESS	    read-only
		    STATUS		    current
		    DESCRIPTION     "Port Udld Mib Msg Timer."
	  ::=  { portUdldMibEntry  9 }

	  portUdldMibNeighbour00DeviceID   OBJECT-TYPE
            SYNTAX		    Char
		    MAX-ACCESS	    read-only
		    STATUS		    current
		    DESCRIPTION     "portUdldMibNeighbour_00_DeviceID."
	  ::=  { portUdldMibEntry  10 }

	  portUdldMibNeighbour00PortID   OBJECT-TYPE
            SYNTAX		    Char
		    MAX-ACCESS	    read-only
		    STATUS		    current
		    DESCRIPTION     "portUdldMibNeighbour_00_PortID."
	  ::=  { portUdldMibEntry  11 }
	  
	  portUdldMibNeighbour01DeviceID   OBJECT-TYPE
            SYNTAX		    Char
		    MAX-ACCESS	    read-only
		    STATUS		    current
		    DESCRIPTION     "portUdldMibNeighbour_01_DeviceID."
	  ::=  { portUdldMibEntry  12 }

	  portUdldMibNeighbour01PortID   OBJECT-TYPE
            SYNTAX		    Char
		    MAX-ACCESS	    read-only
		    STATUS		    current
		    DESCRIPTION     "portUdldMibNeighbour_01_PortID."
	  ::=  { portUdldMibEntry  13 } 
	  
	  portUdldMibNeighbour02DeviceID   OBJECT-TYPE
            SYNTAX		    Char
		    MAX-ACCESS	    read-only
		    STATUS		    current
		    DESCRIPTION     "portUdldMibNeighbour_02_DeviceID."
	  ::=  { portUdldMibEntry  14 }

	  portUdldMibNeighbour02PortID   OBJECT-TYPE
            SYNTAX		    Char
		    MAX-ACCESS	    read-only
		    STATUS		    current
		    DESCRIPTION     "portUdldMibNeighbour_02_PortID."
	  ::=  { portUdldMibEntry  15 }  
	  
	  portUdldMibNeighbour03DeviceID   OBJECT-TYPE
            SYNTAX		    Char
		    MAX-ACCESS	    read-only
		    STATUS		    current
		    DESCRIPTION     "portUdldMibNeighbour_03_DeviceID."
	  ::=  { portUdldMibEntry  16 }

	  portUdldMibNeighbour03PortID   OBJECT-TYPE
            SYNTAX		    Char
		    MAX-ACCESS	    read-only
		    STATUS		    current
		    DESCRIPTION     "portUdldMibNeighbour_03_PortID."
	  ::=  { portUdldMibEntry  17 }    
	  
	  portUdldMibNeighbour04DeviceID   OBJECT-TYPE
            SYNTAX		    Char
		    MAX-ACCESS	    read-only
		    STATUS		    current
		    DESCRIPTION     "portUdldMibNeighbour_04_DeviceID."
	  ::=  { portUdldMibEntry  18 }

	  portUdldMibNeighbour04PortID   OBJECT-TYPE
            SYNTAX		    Char
		    MAX-ACCESS	    read-only
		    STATUS		    current
		    DESCRIPTION     "portUdldMibNeighbour_04_PortID."
	  ::=  { portUdldMibEntry  19 }   
	  
	  portUdldMibNeighbour05DeviceID   OBJECT-TYPE
            SYNTAX		    Char
		    MAX-ACCESS	    read-only
		    STATUS		    current
		    DESCRIPTION     "portUdldMibNeighbour_05_DeviceID."
	  ::=  { portUdldMibEntry  20 }

	  portUdldMibNeighbour05PortID   OBJECT-TYPE
            SYNTAX		    Char
		    MAX-ACCESS	    read-only
		    STATUS		    current
		    DESCRIPTION     "portUdldMibNeighbour_05_PortID."
	  ::=  { portUdldMibEntry  21 }  
	  
	  portUdldMibNeighbour06DeviceID   OBJECT-TYPE
            SYNTAX		    Char
		    MAX-ACCESS	    read-only
		    STATUS		    current
		    DESCRIPTION     "portUdldMibNeighbour_06_DeviceID."
	  ::=  { portUdldMibEntry  22 }

	  portUdldMibNeighbour06PortID   OBJECT-TYPE
            SYNTAX		    Char
		    MAX-ACCESS	    read-only
		    STATUS		    current
		    DESCRIPTION     "portUdldMibNeighbour_06_PortID."
	  ::=  { portUdldMibEntry  23 }  
	  
	  portUdldMibNeighbour07DeviceID   OBJECT-TYPE
            SYNTAX		    Char
		    MAX-ACCESS	    read-only
		    STATUS		    current
		    DESCRIPTION     "portUdldMibNeighbour_07_DeviceID."
	  ::=  { portUdldMibEntry  24 }

	  portUdldMibNeighbour07PortID   OBJECT-TYPE
            SYNTAX		    Char
		    MAX-ACCESS	    read-only
		    STATUS		    current
		    DESCRIPTION     "portUdldMibNeighbour_07_PortID."
	  ::=  { portUdldMibEntry  25 } 
	  
	  portUdldMibNeighbour08DeviceID   OBJECT-TYPE
            SYNTAX		    Char
		    MAX-ACCESS	    read-only
		    STATUS		    current
		    DESCRIPTION     "portUdldMibNeighbour_08_DeviceID."
	  ::=  { portUdldMibEntry  26 }

	  portUdldMibNeighbour08PortID   OBJECT-TYPE
            SYNTAX		    Char
		    MAX-ACCESS	    read-only
		    STATUS		    current
		    DESCRIPTION   "portUdldMibNeighbour_08_PortID."
	  ::=  { portUdldMibEntry  27 }  
	  
	  portUdldMibNeighbour09DeviceID   OBJECT-TYPE
            SYNTAX		    Char
		    MAX-ACCESS	    read-only
		    STATUS		    current
		    DESCRIPTION     "portUdldMibNeighbour_09_DeviceID."
	  ::=  { portUdldMibEntry  28 }

	  portUdldMibNeighbour09PortID   OBJECT-TYPE
            SYNTAX		    Char
		    MAX-ACCESS	    read-only
		    STATUS		    current
		    DESCRIPTION     "portUdldMibNeighbour_09_PortID."
	  ::=  { portUdldMibEntry  29 }  
	  
	  portUdldMibNeighbour10DeviceID   OBJECT-TYPE
            SYNTAX		    Char
		    MAX-ACCESS	    read-only
		    STATUS		    current
		    DESCRIPTION     "portUdldMibNeighbour_10_DeviceID."
	  ::=  { portUdldMibEntry  30 }

	  portUdldMibNeighbour10PortID   OBJECT-TYPE
            SYNTAX		    Char
		    MAX-ACCESS	    read-only
		    STATUS		    current
		    DESCRIPTION     "portUdldMibNeighbour_10_PortID."
	  ::=  { portUdldMibEntry  31 }  
	  
	  portUdldMibNeighbour11DeviceID   OBJECT-TYPE
            SYNTAX		    Char
		    MAX-ACCESS	    read-only
		    STATUS		    current
		    DESCRIPTION     "portUdldMibNeighbour_11_DeviceID."
	  ::=  { portUdldMibEntry  32 }

	  portUdldMibNeighbour11PortID   OBJECT-TYPE
            SYNTAX		    Char
		    MAX-ACCESS	    read-only
		    STATUS		    current
		    DESCRIPTION     "portUdldMibNeighbour_11_PortID."
	  ::=  { portUdldMibEntry  33 } 
	  
	  portUdldMibNeighbour12DeviceID   OBJECT-TYPE
            SYNTAX		    Char
		    MAX-ACCESS	    read-only
		    STATUS		    current
		    DESCRIPTION     "portUdldMibNeighbour_12_DeviceID."
	  ::=  { portUdldMibEntry  34 }

	  portUdldMibNeighbour12PortID   OBJECT-TYPE
            SYNTAX		    Char
		    MAX-ACCESS	    read-only
		    STATUS		    current
		    DESCRIPTION     "portUdldMibNeighbour_12_PortID."
	  ::=  { portUdldMibEntry  35 } 
	  
	  portUdldMibNeighbour13DeviceID   OBJECT-TYPE
            SYNTAX		    Char
		    MAX-ACCESS	    read-only
		    STATUS		    current
		    DESCRIPTION     "portUdldMibNeighbour_13_DeviceID."
	  ::=  { portUdldMibEntry  36 }

	  portUdldMibNeighbour13PortID   OBJECT-TYPE
            SYNTAX		    Char
		    MAX-ACCESS	    read-only
		    STATUS		    current
		    DESCRIPTION     "portUdldMibNeighbour_13_PortID."
	  ::=  { portUdldMibEntry  37 } 
	  
	  portUdldMibNeighbour14DeviceID   OBJECT-TYPE
            SYNTAX		    Char
		    MAX-ACCESS	    read-only
		    STATUS		    current
		    DESCRIPTION     "portUdldMibNeighbour_14_DeviceID."
	  ::=  { portUdldMibEntry  38 }

	  portUdldMibNeighbour14PortID   OBJECT-TYPE
            SYNTAX		    Char
		    MAX-ACCESS	    read-only
		    STATUS		    current
		    DESCRIPTION     "portUdldMibNeighbour_14_PortID."
	  ::=  { portUdldMibEntry  39 }  
	  
	  portUdldMibNeighbour15DeviceID   OBJECT-TYPE
            SYNTAX		    Char
		    MAX-ACCESS	    read-only
		    STATUS		    current
		    DESCRIPTION     "portUdldMibNeighbour_15_DeviceID."
	  ::=  { portUdldMibEntry  40 }

	  portUdldMibNeighbour15PortID   OBJECT-TYPE
            SYNTAX		    Char
		    MAX-ACCESS	    read-only
		    STATUS		    current
		    DESCRIPTION     "portUdldMibNeighbour_15_PortID."
	  ::=  { portUdldMibEntry  41 }

	 
END
