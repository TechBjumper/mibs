SCANET-MIB DEFINITIONS ::= BEGIN

-- Copyright (C) 1997 Intel Corporation. All rights reserved.
--
-- Intel System MIB, 11-04-1997
--
-- Change History:
-- <date> <change>
--

          IMPORTS
              enterprises,IpAddress,TimeTicks     FROM RFC1155-SMI
              DisplayString                       FROM RFC1213-MIB
              OBJECT-TYPE                         FROM RFC-1212;
--          EXPORTS
--             scanet, scaProt;

          scanet              OBJECT IDENTIFIER ::= { enterprises 208 }

          products            OBJECT IDENTIFIER ::= { scanet 1 }
            ts-2104           OBJECT IDENTIFIER ::= { products 12 } -- Async. MPTS
            cs-72xx           OBJECT IDENTIFIER ::= { products 13 } -- 3270 MPTS
            cs-76xx           OBJECT IDENTIFIER ::= { products 15 } -- AS/400 MPTS
            cs-14xx           OBJECT IDENTIFIER ::= { products 32 } -- RemotePC Server
            ethernetSwitch    OBJECT IDENTIFIER ::= { products 35 } -- Ethernet$
              es-1810         OBJECT IDENTIFIER ::= {   ethernetSwitch 1 }  --
              es-1820         OBJECT IDENTIFIER ::= {   ethernetSwitch 2 }  --
              es10t24         OBJECT IDENTIFIER ::= {   ethernetSwitch 3 }  --
              es10t24plus     OBJECT IDENTIFIER ::= {   ethernetSwitch 4 }  --
              es-1520         OBJECT IDENTIFIER ::= {   ethernetSwitch 5 }  --
              es-1850         OBJECT IDENTIFIER ::= {   ethernetSwitch 6 }  --
              es-1851         OBJECT IDENTIFIER ::= {   ethernetSwitch 7 }  --
              es100fx         OBJECT IDENTIFIER ::= {   ethernetSwitch 8 }  --
            cs-3300           OBJECT IDENTIFIER ::= { products 42 } -- BRouter
            mfts              OBJECT IDENTIFIER ::= { products 67 } -- Multi-Function TS
            cs-21xx           OBJECT IDENTIFIER ::= { products 68 } -- Async. MPTS
            ct-30xx           OBJECT IDENTIFIER ::= { products 69 } -- 10BASE-T
            in-40xx           OBJECT IDENTIFIER ::= { products 82 } -- Ether/FDDI Bridge
            ct-40xx           OBJECT IDENTIFIER ::= { products 83 } -- FDDI Concentrator
            matchboxRouter    OBJECT IDENTIFIER ::= { products 88 } -- MatchBox Routers
              mr-1010         OBJECT IDENTIFIER ::= { matchboxRouter 1 }
              mr-1011         OBJECT IDENTIFIER ::= { matchboxRouter 2 }
              mr-1013         OBJECT IDENTIFIER ::= { matchboxRouter 3 }
              mr-1014         OBJECT IDENTIFIER ::= { matchboxRouter 4 }
              mr-1050         OBJECT IDENTIFIER ::= { matchboxRouter 5 }
              mr-1051         OBJECT IDENTIFIER ::= { matchboxRouter 6 }
              mr-1110         OBJECT IDENTIFIER ::= { matchboxRouter 7 }
              mr-1111         OBJECT IDENTIFIER ::= { matchboxRouter 8 }
              mr-1113         OBJECT IDENTIFIER ::= { matchboxRouter 9 }
              mr-1114         OBJECT IDENTIFIER ::= { matchboxRouter 10 }
              mr-1150         OBJECT IDENTIFIER ::= { matchboxRouter 11 }
              mr-1151         OBJECT IDENTIFIER ::= { matchboxRouter 12 }
              mr-1055         OBJECT IDENTIFIER ::= { matchboxRouter 13 }
              mr-1155         OBJECT IDENTIFIER ::= { matchboxRouter 14 }
              mr-1020         OBJECT IDENTIFIER ::= { matchboxRouter 15 }
              mr-1120         OBJECT IDENTIFIER ::= { matchboxRouter 16 }
              mr-1023         OBJECT IDENTIFIER ::= { matchboxRouter 17 }
              mr-1123         OBJECT IDENTIFIER ::= { matchboxRouter 18 }
              mr-1024         OBJECT IDENTIFIER ::= { matchboxRouter 19 }
              mr-1124         OBJECT IDENTIFIER ::= { matchboxRouter 20 }
              mr-1040         OBJECT IDENTIFIER ::= { matchboxRouter 21 }
              mr-1140         OBJECT IDENTIFIER ::= { matchboxRouter 22 }
              mr-1021         OBJECT IDENTIFIER ::= { matchboxRouter 23 }
              mr-1121         OBJECT IDENTIFIER ::= { matchboxRouter 24 }
              er9100          OBJECT IDENTIFIER ::= { matchboxRouter 25 }
              er9200          OBJECT IDENTIFIER ::= { matchboxRouter 26 }
              er9300          OBJECT IDENTIFIER ::= { matchboxRouter 27 }
              er9400          OBJECT IDENTIFIER ::= { matchboxRouter 28 }

          mib2ext             OBJECT IDENTIFIER ::= { scanet 2 }
            system            OBJECT IDENTIFIER ::= { mib2ext 1 }
            ip                OBJECT IDENTIFIER ::= { mib2ext 4 }
            snmp              OBJECT IDENTIFIER ::= { mib2ext 11 }
            swUpdate          OBJECT IDENTIFIER ::= { mib2ext 40 }

--        box                 OBJECT IDENTIFIER ::= { scanet 3 }

          scaProt             OBJECT IDENTIFIER ::= { scanet 4 }
--          ifh               OBJECT IDENTIFIER ::= { scaProt 1 }
--          tp4               OBJECT IDENTIFIER ::= { scaProt 2 }
--          lat               OBJECT IDENTIFIER ::= { scaProt 3 }
--          tsPorts           OBJECT IDENTIFIER ::= { scaProt 4 }

--        rlm                 OBJECT IDENTIFIER ::= { scanet 20 }
--        x25                 OBJECT IDENTIFIER ::= { scanet 21 }
--        osne                OBJECT IDENTIFIER ::= { scanet 22 }
--        clns                OBJECT IDENTIFIER ::= { scanet 23 }
--        mpLink              OBJECT IDENTIFIER ::= { scanet 24 }
--        ipx                 OBJECT IDENTIFIER ::= { scanet 25 }
--        acl                 OBJECT IDENTIFIER ::= { scanet 26 }
--        nac                 OBJECT IDENTIFIER ::= { scanet 27 }
--        rptrx               OBJECT IDENTIFIER ::= { scanet 28 }
--        fddiconc            OBJECT IDENTIFIER ::= { scanet 29 }
--        trap                OBJECT IDENTIFIER ::= { scanet 30 }
--        board               OBJECT IDENTIFIER ::= { scanet 31 }
--        sdlc                OBJECT IDENTIFIER ::= { scanet 32 }
--        ulam                OBJECT IDENTIFIER ::= { scanet 33 }
--        llc2                OBJECT IDENTIFIER ::= { scanet 34 }
--        stp                 OBJECT IDENTIFIER ::= { scanet 35 }
--        trn                 OBJECT IDENTIFIER ::= { scanet 36 }
--        cau                 OBJECT IDENTIFIER ::= { scanet 37 }
--        gw                  OBJECT IDENTIFIER ::= { scanet 38 }
--        switch              OBJECT IDENTIFIER ::= { scanet 39 }
--        rpcs                OBJECT IDENTIFIER ::= { scanet 40 }
--        vlan                OBJECT IDENTIFIER ::= { scanet 41 }
--        iprouter            OBJECT IDENTIFIER ::= { scanet 42 }
--        ppp                 OBJECT IDENTIFIER ::= { scanet 43 }
--        mpLink2             OBJECT IDENTIFIER ::= { scanet 44 }
--        async               OBJECT IDENTIFIER ::= { scanet 45 }
--        frext               OBJECT IDENTIFIER ::= { scanet 46 }
--        diag                OBJECT IDENTIFIER ::= { scanet 47 }
--        isd2                OBJECT IDENTIFIER ::= { scanet 48 }
--        wbr                 OBJECT IDENTIFIER ::= { scanet 49 }
--        l3Link              OBJECT IDENTIFIER ::= { scanet 50 }
--        x25ext              OBJECT IDENTIFIER ::= { scanet 51 }
--        tunnel              OBJECT IDENTIFIER ::= { scanet 52 }

--          DisplayString ::= OCTET STRING


          -- mib2ext.system (Local System group)
          -- ***********************************

          reboot OBJECT-TYPE
               SYNTAX  INTEGER {
--                        resetCancel(0),
                          resetNow(1),
                          resetIdle(2),
                          reset1hour(3),
                          reset8hours(4),
                          reloadTerminfo(5),
                          reloadProfile(6),
                          reloadParm(7),
                          saveParm(8),
                          reloadAnnounce(9),
                          rebootAndLoadFlash(10),
                          resetWarm(11),
                          reloadDefaultKeepIP(12),
                          reloadDefault(13)
                          }
               ACCESS  read-write
               STATUS  mandatory
               DESCRIPTION "Object to control actions in the device such as:
                           resetNow(1) is reset the device immediately,
                           reloadParm(7) is reload parameterblock from FLASH.
                           saveParm(8) is save the parameter block to FLASH.
                           Notice that not all products supports all values
                           of this object."
               ::= { system 1 }

          ram  OBJECT-TYPE
               SYNTAX  INTEGER
               ACCESS  read-only
               STATUS  mandatory
               DESCRIPTION "The size of the CPU RAM."
               ::= { system 2 }

          -- the H/W and F/W table

          idTable OBJECT-TYPE
               SYNTAX  SEQUENCE OF IdEntry
               ACCESS  not-accessible
               STATUS  mandatory
               DESCRIPTION "A table containing H/W and F/W identification."
               ::= { system 3 }

               idEntry OBJECT-TYPE
                       SYNTAX  IdEntry
                       ACCESS  not-accessible
                       STATUS  mandatory
                       DESCRIPTION "A H/W and F/W information entry for each
                                   set of boards."
                       INDEX   { brdNumber }
                       ::= { idTable 1 }

               IdEntry ::= SEQUENCE {
                   brdNumber     INTEGER,
                   hwId          DisplayString,
                   fwId          DisplayString
               }

               brdNumber OBJECT-TYPE
                       SYNTAX  INTEGER
                       ACCESS  read-only
                       STATUS  mandatory
                       DESCRIPTION "An index identifying one or more boards."
                       ::= { idEntry 1 }

               hwId OBJECT-TYPE
                       SYNTAX  DisplayString (SIZE (0..255))
                       ACCESS  read-only
                       STATUS  mandatory
                       DESCRIPTION "H/W identification for the board, ex 10T24."
                       ::= { idEntry 2 }

               fwId OBJECT-TYPE
                       SYNTAX  DisplayString (SIZE (0..255))
                       ACCESS  read-only
                       STATUS  mandatory
                       DESCRIPTION "F/W identification for the board. ex PROM
                                   version number."
                       ::= { idEntry 3 }

          -- the S/W table

          swTable OBJECT-TYPE
               SYNTAX  SEQUENCE OF SwEntry
               ACCESS  not-accessible
               STATUS  mandatory
               DESCRIPTION "A table af S/W filenames."
               ::= { system 4 }

               swEntry OBJECT-TYPE
                       SYNTAX  SwEntry
                       ACCESS  not-accessible
                       STATUS  mandatory
                       DESCRIPTION "A filename."
                       ::= { swTable 1 }

               SwEntry ::= SEQUENCE {
                   swName        DisplayString
               }

               swName  OBJECT-TYPE
                       SYNTAX  DisplayString (SIZE (0..255))
                       ACCESS  read-only
                       STATUS  mandatory
                       DESCRIPTION "Filename of S/W."
                       ::= { swEntry 1 }

          -- Log's

          errorLogNumber  OBJECT-TYPE
               SYNTAX  INTEGER
               ACCESS  read-write
               STATUS  mandatory
               DESCRIPTION "Number of entries in the error log. Setting the
                            value zero will clear the log. Set of any other
                            value is invalid."
               ::= { system 5 }

          systemLogNumber  OBJECT-TYPE
               SYNTAX  INTEGER
               ACCESS  read-write
               STATUS  mandatory
               DESCRIPTION "Number of entries in the system log. Setting the
                            value zero will clear the log. Set of any other
                            value is invalid."
               ::= { system 6 }

          -- Authorization Access List

          autAccessTable OBJECT-TYPE
               SYNTAX  SEQUENCE OF AutAccessEntry
               ACCESS  not-accessible
               STATUS  mandatory
               DESCRIPTION "Authorization Access list. A list of all IP
                            addresses that has passed the authorization.
                            The access can be from either SNMP, TFTP or Telnet"
               ::= { system 7 }

               autAccessEntry OBJECT-TYPE
                       SYNTAX  AutAccessEntry
                       ACCESS  not-accessible
                       STATUS  mandatory
                       DESCRIPTION "Authorization accept entry."
--                       INDEX   { INTEGER }
                       ::= { autAccessTable 1 }

               AutAccessEntry ::= SEQUENCE {
                   autAccessIP      IpAddress,
                   autAccessTime    TimeTicks
               }

               autAccessIP OBJECT-TYPE
                       SYNTAX  IpAddress
                       ACCESS  read-only
                       STATUS  mandatory
                       DESCRIPTION "IP address of the host that has
                                    successfully passed the authorization."
                       ::= { autAccessEntry 1 }

               autAccessTime OBJECT-TYPE
                       SYNTAX  TimeTicks
                       ACCESS  read-only
                       STATUS  mandatory
                       DESCRIPTION "Time of last successfully access."
                       ::= { autAccessEntry 2 }

          -- Time Of Day

          timeOfDay  OBJECT-TYPE
               SYNTAX  INTEGER
               ACCESS  read-write
               STATUS  mandatory
               DESCRIPTION "The system's Time Of Day. The time is expresed
                           in seconds since midnight (0 hour), Januar 1, 1970."
               ::= { system 8 }

          configurationLastChanged OBJECT-TYPE
               SYNTAX  INTEGER
               ACCESS  read-only
               STATUS  mandatory
               DESCRIPTION "Time Of Day the configuration was last changed.
                            The time is expresed in seconds since midnight
                            (0 hour), Januar 1, 1970."
               ::= { system 9 }

          configurationLastSaved OBJECT-TYPE
               SYNTAX  INTEGER
               ACCESS  read-only
               STATUS  mandatory
               DESCRIPTION "Time Of Day the configuration was saved to FLASH.
                            The time is expresed in seconds since midnight
                            (0 hour), Januar 1, 1970."
               ::= { system 10 }

          unsavedConfiguration OBJECT-TYPE
               SYNTAX  INTEGER {
                          no(1),
                          yes(2)
                          }
               ACCESS  read-only
               STATUS  mandatory
               DESCRIPTION "Indicates if there are unsaved configuration
                            changes to FLASH. If the value is yes(2) the
                            configuration has been changed and can be
                            saved by setting the object reboot to saveParm(8)."
               ::= { system 11 }


          -- mib2ext.ip (Local IP group)
          -- ***********************************


          ipTable OBJECT-TYPE
               SYNTAX  SEQUENCE OF IpEntry
               ACCESS  not-accessible
               STATUS  mandatory
               DESCRIPTION "This table is needed to set the IP address and
                            the IP mask. Refer to the table ipAddrTable
                            in MIB-II, for a description."
               ::= { ip 1 }

               ipEntry OBJECT-TYPE
                       SYNTAX  IpEntry
                       ACCESS  not-accessible
                       STATUS  mandatory
                       DESCRIPTION "Entry with an IP address and an IP mask."
--                       INDEX   { ipIndex, IpAddress }
                       ::= { ipTable 1 }

               IpEntry ::= SEQUENCE {
                   ipIndex       INTEGER,
                   ipAddrAndMask OCTET STRING (SIZE (8))
               }

               ipIndex OBJECT-TYPE
                    SYNTAX  INTEGER
                    ACCESS  read-only
                    STATUS  mandatory
                    DESCRIPTION "The value of an interface indentified
                                 by ifIndex."
                    ::= { ipEntry 1 }

               ipAddrAndMask OBJECT-TYPE
                    SYNTAX  OCTET STRING (SIZE (8))
                    ACCESS  read-write
                    STATUS  mandatory
                    DESCRIPTION "The IP Address and the Subnet Mask.
                                 The format of the octet string is:
                                   4 bytes : IP Address
                                   4 bytes : IP Subnet Mask."
                    ::= { ipEntry 2 }


          -- mib2ext.snmp (Local Snmp group)
          -- *******************************

          filter OBJECT-TYPE
               SYNTAX INTEGER {
--                        emergency(0),
                          alert(1),
                          critical(2),
                          error(3),
                          warning(4),
                          notice(5),
                          info(6),
                          debug(7)
                          }
               ACCESS  read-write
               STATUS  obsolete
               DESCRIPTION "Filter to control logging af events."
               ::= { snmp 1 }

          print OBJECT-TYPE
               SYNTAX  DisplayString (SIZE (0..255))
               ACCESS  read-only
               STATUS  mandatory
               DESCRIPTION "A general object used for SNMP-TRAPS.
                           Notice that this object for newer products is
                           obsolete and replaced by unique TRAP's."
               ::= { snmp 2 }

          cause OBJECT-TYPE
               SYNTAX  DisplayString (SIZE (0..255))
               ACCESS  read-only
               STATUS  mandatory
               DESCRIPTION "A general object used for SNMP-TRAPS.
                           Notice that this object for newer products is
                           obsolete and replaced by unique TRAP's."
               ::= { snmp 3 }

          solution OBJECT-TYPE
               SYNTAX  DisplayString (SIZE (0..255))
               ACCESS  read-only
               STATUS  mandatory
               DESCRIPTION "A general object used for SNMP-TRAPS.
                           Notice that this object for newer products is
                           obsolete and replaced by unique TRAP's."
               ::= { snmp 4 }

          -- Authorization List

          autMaxEntries OBJECT-TYPE
               SYNTAX INTEGER
               ACCESS  read-only
               STATUS  mandatory
               DESCRIPTION "Maximun number of entries in the autTable"
               ::= { snmp 5 }

          autTable OBJECT-TYPE
               SYNTAX  SEQUENCE OF AutEntry
               ACCESS  not-accessible
               STATUS  mandatory
               DESCRIPTION "Authorization list."
               ::= { snmp 6 }

               autEntry OBJECT-TYPE
                       SYNTAX  AutEntry
                       ACCESS  not-accessible
                       STATUS  mandatory
                       DESCRIPTION "Authorization entry."
                       INDEX   { autNumber }
                       ::= { autTable 1 }

               AutEntry ::= SEQUENCE {
                   autNumber                   INTEGER,
                   autIpAndAccessAndCommunity  OCTET STRING,
                   autDelete                   INTEGER
               }

               autNumber OBJECT-TYPE
                       SYNTAX  INTEGER
                       ACCESS  read-only
                       STATUS  mandatory
                       DESCRIPTION "A number that uniquely identifies an
                                    authorization entry."
                       ::= { autEntry 1 }

               autIpAndAccessAndCommunity OBJECT-TYPE
                       SYNTAX  OCTET STRING (SIZE (0..36))
                       ACCESS  read-write
                       STATUS  mandatory
                       DESCRIPTION "This object contains the Ip address (4 byte),
                                    Access (1 byte) and Community (0 to
                                    31 byte). If the Ip address is zero
                                    then any ip address is allowed. The
                                    Access can take the values
                                    readOnly(1) and readWrite(2). If
                                    the community string is zero length,
                                    then any value of community is allowed."
                       ::= { autEntry 2 }

               autDelete OBJECT-TYPE
                       SYNTAX  INTEGER {
                               delete(1)
                               }
                       ACCESS  read-write
                       STATUS  mandatory
                       DESCRIPTION "The autEntry is removed when set to
                                    1. Allways returns 0"
                       ::= { autEntry 3 }

          -- Host Trap List

          trapMaxEntries OBJECT-TYPE
               SYNTAX INTEGER
               ACCESS  read-only
               STATUS  mandatory
               DESCRIPTION "Maximun number of entries in the trapTable"
               ::= { snmp 7 }

          trapTable OBJECT-TYPE
               SYNTAX  SEQUENCE OF TrapEntry
               ACCESS  not-accessible
               STATUS  mandatory
               DESCRIPTION "Host Trap list."
               ::= { snmp 8 }

               trapEntry OBJECT-TYPE
                       SYNTAX  TrapEntry
                       ACCESS  not-accessible
                       STATUS  mandatory
                       DESCRIPTION "Host Trap entry."
                       INDEX   { trapNumber }
                       ::= { trapTable 1 }

               TrapEntry ::= SEQUENCE {
                   trapNumber          INTEGER,
                   trapIpAndCommunity  OCTET STRING,
                   trapDelete          INTEGER
               }

               trapNumber OBJECT-TYPE
                       SYNTAX  INTEGER
                       ACCESS  read-only
                       STATUS  mandatory
                       DESCRIPTION "A number that uniquely identifies an
                                    trap entry."
                       ::= { trapEntry 1 }

               trapIpAndCommunity OBJECT-TYPE
                       SYNTAX  OCTET STRING (SIZE (0..35))
                       ACCESS  read-write
                       STATUS  mandatory
                       DESCRIPTION "This object contains the Ip address
                                    (4 byte) and the Community (0 to 31
                                    byte) used in the Traps."
                       ::= { trapEntry 2 }

               trapDelete OBJECT-TYPE
                       SYNTAX  INTEGER {
                               delete(1)
                               }
                       ACCESS  read-write
                       STATUS  mandatory
                       DESCRIPTION "The trapEntry is removed when set to
                                    1. Allways returns 0"
                       ::= { trapEntry 3 }

          -- mib2ext.swUpdate (Local software update group)
          -- **********************************************

          swInfoTable OBJECT-TYPE
               SYNTAX  SEQUENCE OF SwInfoEntry
               ACCESS  not-accessible
               STATUS  mandatory
               DESCRIPTION "Software information table. If the product
                            has a dual software system the table contains
                            two entries."
               ::= { swUpdate 1 }

               swInfoEntry OBJECT-TYPE
                       SYNTAX  SwInfoEntry
                       ACCESS  not-accessible
                       STATUS  mandatory
                       DESCRIPTION "Software information entry."
--                       INDEX   { INTEGER }
                       ::= { swInfoTable 1 }

               SwInfoEntry ::= SEQUENCE {
                   swStatus         INTEGER,
                   swName           OCTET STRING,
                   swLoadTime       TimeTicks,
                   swTftpIp         IpAddress
               }

               swStatus OBJECT-TYPE
                       SYNTAX  INTEGER {
                                  unavailable(1),
                                  approved(2),
                                  experimental(3),
                                  none(4)
                               }
                       ACCESS  read-write
                       STATUS  mandatory
                       DESCRIPTION "This object is only used for products
                                    with a dual software system. After loading
                                    and initiating new software the status
                                    is experimental. The software must be
                                    approved to be used after power off."
                       ::= { swInfoEntry 1 }

               swName2 OBJECT-TYPE
                       SYNTAX  OCTET STRING (SIZE (0..46))
                       ACCESS  read-only
                       STATUS  mandatory
                       DESCRIPTION "The software file name (0 to 46 bytes)"
                       ::= { swInfoEntry 2 }

               swLoadTime OBJECT-TYPE
                       SYNTAX  TimeTicks
                       ACCESS  read-only
                       STATUS  mandatory
                       DESCRIPTION "The time the software was loaded and
                                    saved to FLASH."
                       ::= { swInfoEntry 3 }

               swTftpIp OBJECT-TYPE
                       SYNTAX  IpAddress
                       ACCESS  read-only
                       STATUS  mandatory
                       DESCRIPTION "IP address of the TFTP server from
                                    which the software was loaded."
                       ::= { swInfoEntry 4 }

          swTftpIpAndSwName OBJECT-TYPE
               SYNTAX  OCTET STRING (SIZE (0..50))
               ACCESS  read-write
               STATUS  mandatory
               DESCRIPTION "This object contains the IP address of the TFTP
                            server (4 bytes) and the software file name
                            (0 to 46 bytes). This is used to initiate a
                            software update."
               ::= { swUpdate 2 }

          swUpdateResult OBJECT-TYPE
               SYNTAX  INTEGER {
                          noError(1),
                          swUpdateRunning(2),
                          errorUnknown(3),
                          errorNoTftpServer(4),
                          errorNoSoftware(5),
                          errorSoftwareMismatch(6),
                          errorMoreFlash(7),
                          errorMoreRAM(8)
                       }
               ACCESS  read-only
               STATUS  mandatory
               DESCRIPTION "The result of software update."
               ::= { swUpdate 3 }
          END
