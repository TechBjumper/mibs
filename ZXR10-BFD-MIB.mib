--  ******************************************************
--  $Id: ZTE-BFD-MIB.mib 2009-01$
--
--  ZTE-BFD-MIB.mib: 
--    Bidirectional Forwarding Detection MIB file
--  
--  Jan. 2009, Wei Hong Bo
--   
--  Copyright(c) 2008 by ZTE Corporaton
--  All rights reservered
--
--  ******************************************************

ZXR10-BFD-MIB DEFINITIONS ::= BEGIN

IMPORTS
    MODULE-IDENTITY, 
    OBJECT-TYPE,
    Unsigned32,
    Counter32,
    enterprises,
    NOTIFICATION-TYPE       
        FROM SNMPv2-SMI
    IpAddress
        FROM SNMPv2-SMI
    InetAddressType,
    InetAddress
            FROM INET-ADDRESS-MIB
    TruthValue,
    TimeStamp,
    TEXTUAL-CONVENTION,
    DisplayString
        FROM SNMPv2-TC; 

zteBfdMib MODULE-IDENTITY
    LAST-UPDATED    "201603011639Z"
    ORGANIZATION    "ZTE Corporation."
    CONTACT-INFO
        "       Zhao yanhua
        Tel:    +86-25-52870000
        E-Mail: zhao.yanhua3@zte.com.cn
        "
    DESCRIPTION 
        "ZTE BFD MIB
        "
    REVISION        "201603011639Z"
    DESCRIPTION
        "modify:    DESCRIPTION of zxr10BfdSessApplicationId
        "
    REVISION        "201503091630Z"
    DESCRIPTION
        "modify:    DESCRIPTION of zxr10BfdSessApplicationId
                    add lagBfd(11) for zxr10BfdStatsType
                    add lagBfd(10) for zxr10BfdSessType 
        "
    REVISION        "201311181936Z"
    DESCRIPTION
        "add:    zxr10BfdSessActualTxInterval
                 zxr10BfdSessActualRxInterval
                 zxr10BfdSessActualDetectMult
         modify: DESCRIPTION of zxr10BfdSessApplicationId  
        "
    REVISION        "201305101730Z"
    DESCRIPTION
        "modify:    DESCRIPTION of zxr10BfdSessApplicationId                    
        "
    REVISION        "201305071000Z"
    DESCRIPTION
        "modify:    add rsvpLspBfd(10) for zxr10BfdStatsType                    
        "
    REVISION        "201304191130Z"
    DESCRIPTION
        "modify:    zxr10BfdSessType                    
        "
    REVISION        "201303191130Z"
    DESCRIPTION
        "add:       zxr10BfdSessPwTTL
                    zxr10BfdSessDscp
                    zxr10BfdSessMultiPortMode
                    zxr10BfdStatsTable
        "
    REVISION        "200901070000Z"
    DESCRIPTION
        "Initial version of this MIB module.
        "

    ::= { zxr10 322 }

-- Top level components of this MIB module.

zxr10BfdNotifications  OBJECT IDENTIFIER ::= { zteBfdMib 0 }

zxr10BfdObjects        OBJECT IDENTIFIER ::= { zteBfdMib 1 }

zxr10BfdScalarObjects  OBJECT IDENTIFIER ::= { zxr10BfdObjects 1 }

zte                    OBJECT IDENTIFIER ::= { enterprises 3902 }    

zxr10                  OBJECT IDENTIFIER ::= { zte 3 }

-- Textual Conventions

Zxr10BfdSessIndexTC ::= TEXTUAL-CONVENTION
    DISPLAY-HINT    "d"
    STATUS          current
    DESCRIPTION
        "An index used to uniquely identify BFD sessions."
    SYNTAX          Unsigned32 (1..4294967295 )

Zxr10BfdInterval ::= TEXTUAL-CONVENTION
    STATUS          current
    DESCRIPTION
        "The BFD interval delay in microseconds."
    SYNTAX          Unsigned32 (1..4294967295 )

Zxr10BfdDiag ::= TEXTUAL-CONVENTION
    STATUS          current
    DESCRIPTION
        "A common BFD diagnostic code."
    SYNTAX          INTEGER  {
                        noDiagnostic(1),
                        controlDetectionTimeExpired(2),
                        echoFunctionFailed(3),
                        neighborSignaledSessionDown(4),
                        forwardingPlaneReset(5),
                        pathDown(6),
                        concatenatedPathDown(7),
                        administrativelyDown(8),
                        reverseConcatenatedPathDown(9)
                    }    
                    
 Zxr10BfdAddr ::= TEXTUAL-CONVENTION
       STATUS       current
       DESCRIPTION "An octet string containing bfd addr type."
       SYNTAX       OCTET STRING (SIZE (0..64)) 

-- BFD General Variables
--   
-- These parameters apply globally to the Router's
-- BFD Process.

zxr10BfdAdminStatus OBJECT-TYPE
    SYNTAX          INTEGER  {
                        enabled(1),
                        disabled(2)
                    }
    MAX-ACCESS      read-only
    STATUS          current
    DESCRIPTION
        "The global administrative status of BFD in this router.
        The value 'enabled' denotes that the BFD Process is 
        active on at least one interface; 'disabled' disables  
        it on all interfaces."
    DEFVAL          { enabled } 
    ::= { zxr10BfdScalarObjects 1 }

zxr10BfdVersionNumber OBJECT-TYPE
    SYNTAX          Unsigned32
    MAX-ACCESS      read-only
    STATUS          current
    DESCRIPTION
        "The current version number of the BFD protocol."
    REFERENCE       "BFD Version 0 (draft-katz-ward-bfd-02.txt)"
    DEFVAL          { 0 } 
    ::= { zxr10BfdScalarObjects 2 }
    
-- Notification Configuration

zxr10BfdSessNotificationsEnable OBJECT-TYPE
    SYNTAX          TruthValue
    MAX-ACCESS      read-write
    STATUS          current
    DESCRIPTION
        "If this object is set to true(1), then it enables
        the emission of zxr10BfdSessUp and zxr10BfdSessDown 
        notifications; otherwise these notifications are not 
        emitted."
    REFERENCE
        "See also RFC3413 for explanation that  
           notifications are under the ultimate control of the  
           MIB modules in this document."
    DEFVAL          { false } 
    ::= { zxr10BfdScalarObjects 3 }

zxr10BfdDefault OBJECT-TYPE
    SYNTAX          Zxr10BfdAddr
    MAX-ACCESS      read-only
    STATUS          current
    DESCRIPTION
        "This object specifies the remote IP address which is
        being associated with L2 BFD session."
    REFERENCE
        ""
    ::= { zxr10BfdScalarObjects 4 }
    
-- BFD Session Table
-- The BFD Session Table specifies the BFD session specific
-- information.

zxr10BfdSessTable OBJECT-TYPE
    SYNTAX          SEQUENCE OF Zxr10BfdSessEntry 
    MAX-ACCESS      not-accessible
    STATUS          current
    DESCRIPTION
        "The BFD Session Table describes the BFD sessions."
    REFERENCE       "BFD Version 0 (draft-katz-ward-ciscoBfd-02.txt)"
    ::= { zxr10BfdObjects 2 }

zxr10BfdSessEntry OBJECT-TYPE
    SYNTAX          Zxr10BfdSessEntry
    MAX-ACCESS      not-accessible
    STATUS          current
    DESCRIPTION
        "The BFD Session Entry describes BFD session."
    INDEX           { zxr10BfdSessIndex } 
    ::= { zxr10BfdSessTable 1 }

Zxr10BfdSessEntry ::=
    SEQUENCE {
        zxr10BfdSessIndex                   Zxr10BfdSessIndexTC,
        zxr10BfdSessApplicationId           Unsigned32,
        zxr10BfdSessInitMode                INTEGER,
        zxr10BfdSessDiscriminator           Unsigned32,
        zxr10BfdSessRemoteDiscr             Unsigned32,
        zxr10BfdSessSrcUdpPort              Unsigned32,
        zxr10BfdSessState                   INTEGER,
        zxr10BfdSessRemoteHeardFlag         TruthValue,
        zxr10BfdSessDiag                    Zxr10BfdDiag,
        zxr10BfdSessOperMode                INTEGER,
        zxr10BfdSessDemandModeDesiredFlag   TruthValue,
        zxr10BfdSessEchoFuncModeDesiredFlag TruthValue,
        zxr10BfdSessControlPlanIndepFlag    TruthValue,
        zxr10BfdSessAddrType                InetAddressType,
        zxr10BfdSessLocalAddr               Zxr10BfdAddr,
        zxr10BfdSessRemoteAddr              Zxr10BfdAddr,
        zxr10BfdSessLdpDestAddr             IpAddress,
        zxr10BfdSessLdpPrefixLength         Unsigned32,
        zxr10BfdSessRsvpTunnelId            Unsigned32,
        zxr10BfdSessPWPeerAddr              InetAddress,
        zxr10BfdSessPWVcId                  Unsigned32,
        zxr10BfdSessDesiredMinTxInterval    Zxr10BfdInterval,
        zxr10BfdSessReqMinRxInterval        Zxr10BfdInterval,
        zxr10BfdSessReqMinEchoRxInterval    Zxr10BfdInterval,
        zxr10BfdSessDetectMult              Unsigned32,
        zxr10BfdSessHoldTime                Unsigned32,
        zxr10BfdSessAuthPresFlag            TruthValue,
        zxr10BfdSessAuthenticationType      INTEGER,
        zxr10BfdSessVersionNumber           Unsigned32,
        zxr10BfdSessType                    INTEGER,
        zxr10BfdSessInterface               Unsigned32,
        zxr10BfdSessName                    DisplayString,
        zxr10BfdSessVrfName                 DisplayString,
        zxr10BfdSessPwName                  DisplayString,
        zxr10BfdSessPktLenMin               Unsigned32,
        zxr10BfdSessPktLenMax               Unsigned32,
        zxr10BfdSessIntfName                DisplayString,
        zxr10BfdSessPwTTL                   Unsigned32,
        zxr10BfdSessDscp                    Unsigned32,
        zxr10BfdSessMultiPortMode           TruthValue,
        zxr10BfdSessActualTxInterval        Zxr10BfdInterval,
        zxr10BfdSessActualRxInterval        Zxr10BfdInterval,
        zxr10BfdSessActualDetectMult        Unsigned32
}

zxr10BfdSessIndex OBJECT-TYPE
    SYNTAX          Zxr10BfdSessIndexTC
    MAX-ACCESS      read-only
    STATUS          current
    DESCRIPTION
        "This object contains an index used to represent a
        unique BFD session on this device." 
    ::= { zxr10BfdSessEntry 1 }

zxr10BfdSessApplicationId OBJECT-TYPE
    SYNTAX          Unsigned32
    MAX-ACCESS      read-only
    STATUS          current
    DESCRIPTION
        "This object contains an index used to indicate
        a local application which owns or maintains this 
        BFD session. This object value may be one of
        the following values or sum of some values which
        indicates that the session is owned by several
        applications:
        BGP_BFD(0x0001),
        OSPF_BFD(0x0002),
        ISIS_BFD(0x0004),
        RSVP_BFD(0x0008),
        LDP_BFD(0x0010),
        STATIC_BFD(0x0020),
        RSVP_LSP_BFD(0x0040),
        LDP_LSP_BFD(0x0080),
        VRRP_BFD(0x0100),
        PBR_BFD(0x0200),
        INSTANCE_BFD(0x0400),
        PIM_BFD(0x0800),
        MSDP_BFD(0x1000),
        RIP_BFD(0x2000),
        GRE_BFD(0x4000),
        RSVP_TUNNEL_BFD(0x8000),
        SIBMGR_BFD(0x10000),
        BIDIR_RSVPLSP_BFD(0x20000),
        LACP_BFD(0x40000),
        L2VPN_BFD(0x80000).
        " 
    ::= { zxr10BfdSessEntry 2 }

zxr10BfdSessInitMode OBJECT-TYPE
    SYNTAX          INTEGER  {
                        active(1),
                        passive(2)
                    }
    MAX-ACCESS      read-only
    STATUS          current
    DESCRIPTION
        "The Init Mode of the BFD session." 
    ::= { zxr10BfdSessEntry 3 }
    
zxr10BfdSessDiscriminator OBJECT-TYPE
    SYNTAX          Unsigned32 (1..4294967295 )
    MAX-ACCESS      read-only
    STATUS          current
    DESCRIPTION
        "This object specifies the local discriminator for this BFD
        session, used to uniquely identify it." 
    ::= { zxr10BfdSessEntry 4 }

zxr10BfdSessRemoteDiscr OBJECT-TYPE
    SYNTAX          Unsigned32 (1..4294967295 )
    MAX-ACCESS      read-only
    STATUS          current
    DESCRIPTION
        "This object specifies the session discriminator chosen
        by the remote system for this BFD session." 
    ::= { zxr10BfdSessEntry 5 }

zxr10BfdSessSrcUdpPort OBJECT-TYPE
    SYNTAX          Unsigned32 ( 0..65535 )
    MAX-ACCESS      read-only
    STATUS          current
    DESCRIPTION
        "The source UDP Port for BFD."
    REFERENCE
        ""
    DEFVAL          { 0 } 
    ::= { zxr10BfdSessEntry 6 }

zxr10BfdSessState OBJECT-TYPE
    SYNTAX          INTEGER  {
                        adminDown(1),
                        down(2),
                        init(3),
                        up(4),
                        failing(5)
                    }
    MAX-ACCESS      read-only
    STATUS          current
    DESCRIPTION
        "The perceived state of the BFD session." 
    ::= { zxr10BfdSessEntry 7 }

zxr10BfdSessRemoteHeardFlag OBJECT-TYPE
    SYNTAX          TruthValue
    MAX-ACCESS      read-only
    STATUS          current
    DESCRIPTION
        "This object specifies status of BFD packet reception from
        the remote system. Specifically, it is set to true(1) if 
        the local system is actively receiving BFD packets from the  
        remote system, and is set to false(0) if the local system  
        has not received BFD packets recently (within the detection  
        time) or if the local system is attempting to tear down 
        the BFD session. It is only applicable if this BFD session 
        is running version 0" 
    ::= { zxr10BfdSessEntry 8 }

zxr10BfdSessDiag OBJECT-TYPE
    SYNTAX          Zxr10BfdDiag
    MAX-ACCESS      read-only
    STATUS          current
    DESCRIPTION
        "A diagnostic code specifying the local system's reason
        for the last transition of the session from up(1)  
        to some other state." 
    ::= { zxr10BfdSessEntry 9 }

zxr10BfdSessOperMode OBJECT-TYPE
    SYNTAX          INTEGER  {
                        asyncModeWEchoFun(1),
                        asynchModeWOEchoFun(2),
                        demandModeWEchoFunction(3),
                        demandModeWOEchoFunction(4)
                    }
    MAX-ACCESS      read-only
    STATUS          current
    DESCRIPTION
        "This object specifies current operating mode that BFD
        session is operating in." 
    ::= { zxr10BfdSessEntry 10 }

zxr10BfdSessDemandModeDesiredFlag OBJECT-TYPE
    SYNTAX          TruthValue
    MAX-ACCESS      read-only
    STATUS          current
    DESCRIPTION
        "This object indicates that the local system's
        desire to use Demand mode. Specifically, it is set  
        to true(1) if the local system wishes to use  
        Demand mode or false(0) if not"
    DEFVAL          { false } 
    ::= { zxr10BfdSessEntry 11 }

zxr10BfdSessEchoFuncModeDesiredFlag OBJECT-TYPE
    SYNTAX          TruthValue
    MAX-ACCESS      read-only
    STATUS          current
    DESCRIPTION
        "This object indicates that the local system's
        desire to use Echo mode. Specifically, it is set  
        to true(1) if the local system wishes to use  
        Echo mode or false(0) if not"
    DEFVAL          { false } 
    ::= { zxr10BfdSessEntry 12 }

zxr10BfdSessControlPlanIndepFlag OBJECT-TYPE
    SYNTAX          TruthValue
    MAX-ACCESS      read-only
    STATUS          current
    DESCRIPTION
        "This object indicates that the local system's
        ability to continue to function through a disruption of  
        the control plane. Specifically, it is set  
        to true(1) if the local system BFD implementation is 
        independent of the control plane. Otherwise, the  
        value is set to false(0)"
    DEFVAL          { false } 
    ::= { zxr10BfdSessEntry 13 }

zxr10BfdSessAddrType OBJECT-TYPE
    SYNTAX          InetAddressType
    MAX-ACCESS      read-only
    STATUS          current
    DESCRIPTION
        "This object specifies IP address type of the neighboring IP
        address which is being monitored with this BFD session.

        Only values unknown(0), ipv4(1) or ipv6(2) 
        have to be supported.  

        A value of unknown(0) is allowed only when  
        the outgoing interface is of type point-to-point, or 
        when the BFD session is not associated with a specific  
        interface. 

        If any other unsupported values are attempted in a set 
        operation, the agent MUST return an inconsistentValue  
        error." 
    ::= { zxr10BfdSessEntry 14 }

zxr10BfdSessLocalAddr OBJECT-TYPE
    SYNTAX          Zxr10BfdAddr
    MAX-ACCESS      read-only
    STATUS          current
    DESCRIPTION
        "This object specifies the local IP address which is
        being associated with this BFD session." 
    ::= { zxr10BfdSessEntry 15 }

zxr10BfdSessRemoteAddr OBJECT-TYPE
    SYNTAX          Zxr10BfdAddr
    MAX-ACCESS      read-only
    STATUS          current
    DESCRIPTION
        "This object specifies the neighboring IP address which is
        being monitored with this BFD session."
    ::= { zxr10BfdSessEntry 16 }

zxr10BfdSessLdpDestAddr OBJECT-TYPE
    SYNTAX          IpAddress
    MAX-ACCESS      read-only
    STATUS          current
    DESCRIPTION
        "This object specifies the FEC's destination address which is
        being associated with this LDP LSP BFD session."
    ::= { zxr10BfdSessEntry 17 }

zxr10BfdSessLdpPrefixLength OBJECT-TYPE
    SYNTAX          Unsigned32
    MAX-ACCESS      read-only
    STATUS          current
    DESCRIPTION
        "This object specifies the prefix length which is being associated 
        with this LDP LSP BFD session."
    ::= { zxr10BfdSessEntry 18 }
    
zxr10BfdSessRsvpTunnelId OBJECT-TYPE
    SYNTAX          Unsigned32
    MAX-ACCESS      read-only
    STATUS          current
    DESCRIPTION
        "This object specifies the tunnle Id which is being monitored with 
        this RSVP LSP BFD session."
    ::= { zxr10BfdSessEntry 19 }
    
zxr10BfdSessPWPeerAddr OBJECT-TYPE
    SYNTAX          InetAddress
    MAX-ACCESS      read-only
    STATUS          obsolete
    DESCRIPTION
        "This object specifies the Pseudowire's remote IP address which is
        being monitored with this PW BFD session."
    ::= { zxr10BfdSessEntry 20 }
    
zxr10BfdSessPWVcId OBJECT-TYPE
    SYNTAX          Unsigned32
    MAX-ACCESS      read-only
    STATUS          obsolete
    DESCRIPTION
        "This object specifies the Pseudowire's Vc-Id which is being monitored 
        with this PW BFD session."
    ::= { zxr10BfdSessEntry 21 }

zxr10BfdSessDesiredMinTxInterval OBJECT-TYPE
    SYNTAX          Zxr10BfdInterval
    MAX-ACCESS      read-only
    STATUS          current
    DESCRIPTION
        "This object specifies the minimum interval, in
        microseconds, that the local system would like to use when 
             transmitting BFD Control packets." 
    ::= { zxr10BfdSessEntry 22 }

zxr10BfdSessReqMinRxInterval OBJECT-TYPE
    SYNTAX          Zxr10BfdInterval
    MAX-ACCESS      read-only
    STATUS          current
    DESCRIPTION
        "This object specifies the minimum interval, in
        microseconds, between received  BFD Control packets the  
        local system is capable of supporting." 
    ::= { zxr10BfdSessEntry 23 }

zxr10BfdSessReqMinEchoRxInterval OBJECT-TYPE
    SYNTAX          Zxr10BfdInterval
    MAX-ACCESS      read-only
    STATUS          current
    DESCRIPTION
        "This object specifies the minimum interval, in
        microseconds, between received BFD Echo packets that this 
        system is capable of supporting." 
    ::= { zxr10BfdSessEntry 24 }

zxr10BfdSessDetectMult OBJECT-TYPE
    SYNTAX          Unsigned32
    MAX-ACCESS      read-only
    STATUS          current
    DESCRIPTION
        "This object specifies the Detect time multiplier." 
    ::= { zxr10BfdSessEntry 25 }

zxr10BfdSessHoldTime OBJECT-TYPE
    SYNTAX          Unsigned32
    MAX-ACCESS      read-only
    STATUS          current
    DESCRIPTION
        "This object specifies the Hold time of this BFD session." 
    ::= { zxr10BfdSessEntry 26 }

zxr10BfdSessAuthPresFlag OBJECT-TYPE
    SYNTAX          TruthValue
    MAX-ACCESS      read-only
    STATUS          current
    DESCRIPTION
        "This object indicates that the local system's
        desire to use Authentication. Specifically, it is set  
        to true(1) if the local system wishes the session  
        to be authenticated or false(0) if not"
    DEFVAL          { false } 
    ::= { zxr10BfdSessEntry 27 }

zxr10BfdSessAuthenticationType OBJECT-TYPE
    SYNTAX          INTEGER  {
                        simplePassword(1),
                        keyedMD5(2),
                        meticulousKeyedMD5(3),
                        keyedSHA1(4),
                        meticulousKeyedSHA1(5)
                    }
    MAX-ACCESS      read-only
    STATUS          current
    DESCRIPTION
        "The Authentication Type used for this BFD session. This
        field is valid only when the Authentication Present bit is set" 
    ::= { zxr10BfdSessEntry 28 }

zxr10BfdSessVersionNumber OBJECT-TYPE
    SYNTAX          Unsigned32
    MAX-ACCESS      read-only
    STATUS          current
    DESCRIPTION
        "The version number of the BFD protocol that this session is
        running in."
    REFERENCE
        "BFD Version 0 (draft-katz-ward-bfd-02.txt) and BFD Version
        1 (draft-ietf-bfd-base-07.txt)"
    DEFVAL          { 0 } 
    ::= { zxr10BfdSessEntry 29 }

zxr10BfdSessType OBJECT-TYPE
    SYNTAX          INTEGER  {
                        singleHop(1),
                        multiHop(2),
                        l2Bfd(3),
                        ldpBfd(4),
                        pwBfd(5),
                        rsvpTunnelBfd(6),
                        rsvpLspBfd(7),
                        staticLdpBfd(8),
                        staticRsvpTunnelBfd(9),
                        lagBfd(10)
                    }
    MAX-ACCESS      read-only
    STATUS          current
    DESCRIPTION
        "The type of this BFD session." 
    ::= { zxr10BfdSessEntry 30 }

zxr10BfdSessInterface OBJECT-TYPE
    SYNTAX          Unsigned32 ( 1..65535 )
    MAX-ACCESS      read-only
    STATUS          current
    DESCRIPTION
        "This object contains an interface index used to indicate
        the interface which this BFD session is running on." 
    ::= { zxr10BfdSessEntry 31 }

zxr10BfdSessName OBJECT-TYPE
    SYNTAX          DisplayString
    MAX-ACCESS      read-only
    STATUS          current
    DESCRIPTION
        "The instance name of this BFD session." 
    ::= { zxr10BfdSessEntry 32 }

zxr10BfdSessVrfName OBJECT-TYPE
    SYNTAX          DisplayString
    MAX-ACCESS      read-only
    STATUS          current
    DESCRIPTION
        "The vrf name of this BFD session." 
    ::= { zxr10BfdSessEntry 33 }

zxr10BfdSessPwName OBJECT-TYPE
    SYNTAX          DisplayString
    MAX-ACCESS      read-only
    STATUS          current
    DESCRIPTION
        "The pw name of this BFD session." 
    ::= { zxr10BfdSessEntry 34 }

zxr10BfdSessPktLenMin OBJECT-TYPE
    SYNTAX          Unsigned32
    MAX-ACCESS      read-only
    STATUS          current
    DESCRIPTION
        "This object specifies the min pktLen of this BFD session." 
    ::= { zxr10BfdSessEntry 35 }

zxr10BfdSessPktLenMax OBJECT-TYPE
    SYNTAX          Unsigned32
    MAX-ACCESS      read-only
    STATUS          current
    DESCRIPTION
        "This object specifies the max pktLen of this BFD session." 
    ::= { zxr10BfdSessEntry 36 }

zxr10BfdSessIntfName OBJECT-TYPE
    SYNTAX          DisplayString
    MAX-ACCESS      read-only
    STATUS          current
    DESCRIPTION
        "This object contains an interface name used to indicate
        the interface which this BFD session is running on." 
    ::= { zxr10BfdSessEntry 37 }

zxr10BfdSessPwTTL OBJECT-TYPE
    SYNTAX          Unsigned32 ( 0..255 )
    MAX-ACCESS      read-only
    STATUS          current
    DESCRIPTION
        "PW TTL of this BFD session."
    ::= { zxr10BfdSessEntry 38 }

zxr10BfdSessDscp OBJECT-TYPE
    SYNTAX          Unsigned32(0..63)
    MAX-ACCESS      read-only
    STATUS          current
    DESCRIPTION
        "This object specifies the DSCP value of BFD packet."
    DEFVAL          { 56 }
    ::= { zxr10BfdSessEntry 39 }

zxr10BfdSessMultiPortMode OBJECT-TYPE
    SYNTAX          TruthValue { true(1), false(2) }
    MAX-ACCESS      read-only
    STATUS          current
    DESCRIPTION
        "This object specifies the UDP port of multi-hop BFD,
        'false' denotes to use UDP port 3784, 'true' denotes
        to use 4784."
    DEFVAL          { false }
    ::= { zxr10BfdSessEntry 40 }

zxr10BfdSessActualTxInterval OBJECT-TYPE
    SYNTAX          Zxr10BfdInterval
    MAX-ACCESS      read-only
    STATUS          current
    DESCRIPTION
        "This object specifies the actual Tx interval, inmicroseconds."
    ::= { zxr10BfdSessEntry 41 }

zxr10BfdSessActualRxInterval OBJECT-TYPE
    SYNTAX          Zxr10BfdInterval
    MAX-ACCESS      read-only
    STATUS          current
    DESCRIPTION
        "This object specifies the actual Rx interval, inmicroseconds."
    ::= { zxr10BfdSessEntry 42 }

zxr10BfdSessActualDetectMult OBJECT-TYPE
    SYNTAX          Unsigned32
    MAX-ACCESS      read-only
    STATUS          current
    DESCRIPTION
        "This object specifies the actual Detect time multiplier."
    ::= { zxr10BfdSessEntry 43 }

-- BFD Session Performance Table

zxr10BfdSessPerfTable OBJECT-TYPE
    SYNTAX          SEQUENCE OF Zxr10BfdSessPerfEntry 
    MAX-ACCESS      not-accessible
    STATUS          current
    DESCRIPTION
        "This table specifies BFD Session performance counters."
    ::= { zxr10BfdObjects 3 }

zxr10BfdSessPerfEntry OBJECT-TYPE
    SYNTAX          Zxr10BfdSessPerfEntry
    MAX-ACCESS      not-accessible
    STATUS          current
    DESCRIPTION
        "The BFD Session Entry describes BFD session Performance."  
    AUGMENTS           { zxr10BfdSessEntry  } 
 
    ::= { zxr10BfdSessPerfTable 1 }

Zxr10BfdSessPerfEntry ::=
    SEQUENCE {
        zxr10BfdSessPerfIndex            Zxr10BfdSessIndexTC,
        zxr10BfdSessPerfPktIn            Counter32,
        zxr10BfdSessPerfPktOut           Counter32,
        zxr10BfdSessUpTime               TimeStamp,
        zxr10BfdSessPerfLastCommLostDiag Zxr10BfdDiag,
        zxr10BfdSessPerfMinTxInterval    Zxr10BfdInterval,
        zxr10BfdSessPerfMaxTxInterval    Zxr10BfdInterval,
        zxr10BfdSessPerfAvgTxInterval    Zxr10BfdInterval,
        zxr10BfdSessPerfMinRxInterval    Zxr10BfdInterval,
        zxr10BfdSessPerfMaxRxInterval    Zxr10BfdInterval,
        zxr10BfdSessPerfAvgRxInterval    Zxr10BfdInterval
}
  
zxr10BfdSessPerfIndex OBJECT-TYPE
    SYNTAX          Zxr10BfdSessIndexTC
    MAX-ACCESS      read-only
    STATUS          current
    DESCRIPTION
        "This object contains an index used to represent a
        unique BFD session on this device." 
    ::= { zxr10BfdSessPerfEntry 1 }
  
zxr10BfdSessPerfPktIn OBJECT-TYPE
    SYNTAX          Counter32
    MAX-ACCESS      read-only
    STATUS          current
    DESCRIPTION
        "The total number of BFD messages received for this BFD
        session." 
    ::= { zxr10BfdSessPerfEntry 2 }

zxr10BfdSessPerfPktOut OBJECT-TYPE
    SYNTAX          Counter32
    MAX-ACCESS      read-only
    STATUS          current
    DESCRIPTION
        "The total number of BFD messages sent for this BFD session." 
    ::= { zxr10BfdSessPerfEntry 3 }

zxr10BfdSessUpTime OBJECT-TYPE
    SYNTAX          TimeStamp
    MAX-ACCESS      read-only
    STATUS          current
    DESCRIPTION
        "The value of sysUpTime on the most recent occasion at which
        the session came up. If no such up event exists this object 
        contains a zero value." 
    ::= { zxr10BfdSessPerfEntry 4 }

zxr10BfdSessPerfLastCommLostDiag OBJECT-TYPE
    SYNTAX          Zxr10BfdDiag
    MAX-ACCESS      read-only
    STATUS          current
    DESCRIPTION
        "The BFD diag code for the last time communication was lost
        with the neighbor. If no such down event exists this object  
        contains a zero value." 
    ::= { zxr10BfdSessPerfEntry 5 }

zxr10BfdSessPerfMinTxInterval OBJECT-TYPE
    SYNTAX          Zxr10BfdInterval
    MAX-ACCESS      read-only
    STATUS          current
    DESCRIPTION
        "This object specifies the minimum interval, in microseconds, 
        that the local system have transmitting BFD Control packets." 
    ::= { zxr10BfdSessPerfEntry 6 }

zxr10BfdSessPerfMaxTxInterval OBJECT-TYPE
    SYNTAX          Zxr10BfdInterval
    MAX-ACCESS      read-only
    STATUS          current
    DESCRIPTION
        "This object specifies the maximum interval, in microseconds, 
        that the local system have transmitting BFD Control packets." 
    ::= { zxr10BfdSessPerfEntry 7 }

zxr10BfdSessPerfAvgTxInterval OBJECT-TYPE
    SYNTAX          Zxr10BfdInterval
    MAX-ACCESS      read-only
    STATUS          current
    DESCRIPTION
        "This object specifies the average interval, in microseconds, 
        that the local system have transmitting BFD Control packets." 
    ::= { zxr10BfdSessPerfEntry 8 }

zxr10BfdSessPerfMinRxInterval OBJECT-TYPE
    SYNTAX          Zxr10BfdInterval
    MAX-ACCESS      read-only
    STATUS          current
    DESCRIPTION
        "This object specifies the minimum interval, in microseconds, 
        that the local system have recieving BFD Control packets." 
    ::= { zxr10BfdSessPerfEntry 9 }

zxr10BfdSessPerfMaxRxInterval OBJECT-TYPE
    SYNTAX          Zxr10BfdInterval
    MAX-ACCESS      read-only
    STATUS          current
    DESCRIPTION
        "This object specifies the maximum interval, in microseconds, 
        that the local system have recieving BFD Control packets." 
    ::= { zxr10BfdSessPerfEntry 10 }

zxr10BfdSessPerfAvgRxInterval OBJECT-TYPE
    SYNTAX          Zxr10BfdInterval
    MAX-ACCESS      read-only
    STATUS          current
    DESCRIPTION
        "This object specifies the average interval, in microseconds, 
        that the local system have recieving BFD Control packets." 
    ::= { zxr10BfdSessPerfEntry 11 }

-- BFD Session name to index Table
zxr10BfdSessName2IndexTable OBJECT-TYPE
    SYNTAX          SEQUENCE OF Zxr10BfdSessName2IndexEntry 
    MAX-ACCESS      not-accessible
    STATUS          current
    DESCRIPTION
        "This table specifies the relationship between BFD Session Name and
        Session Index."
    ::= { zxr10BfdObjects 4 }

zxr10BfdSessName2IndexEntry OBJECT-TYPE
    SYNTAX          Zxr10BfdSessName2IndexEntry
    MAX-ACCESS      not-accessible
    STATUS          current
    DESCRIPTION
        "The BFD Session Entry describes the relationship between BFD Session
        Name and Session Index."
    INDEX           { zxr10BfdSessName2IndexSessName } 
 
    ::= { zxr10BfdSessName2IndexTable 1 }

Zxr10BfdSessName2IndexEntry ::=
    SEQUENCE {
        zxr10BfdSessName2IndexSessName             DisplayString,
        zxr10BfdSessName2IndexSessIndex            Zxr10BfdSessIndexTC
}

zxr10BfdSessName2IndexSessName OBJECT-TYPE
    SYNTAX          DisplayString
    MAX-ACCESS      read-only
    STATUS          current
    DESCRIPTION
        "The name of this BFD session." 
    ::= { zxr10BfdSessName2IndexEntry 1 }

zxr10BfdSessName2IndexSessIndex OBJECT-TYPE
    SYNTAX          Zxr10BfdSessIndexTC
    MAX-ACCESS      read-only
    STATUS          current
    DESCRIPTION
        "This object contains an index used to represent a
        unique BFD session on this device." 
    ::= { zxr10BfdSessName2IndexEntry 2 }

-- BFD Session interface para Table
zxr10BfdIntfParaTable OBJECT-TYPE
    SYNTAX          SEQUENCE OF Zxr10BfdIntfParaEntry 
    MAX-ACCESS      not-accessible
    STATUS          current
    DESCRIPTION
        "This table specifies the BFD time parameters of interface."
    ::= { zxr10BfdObjects 5 }

zxr10BfdIntfParaEntry OBJECT-TYPE
    SYNTAX          Zxr10BfdIntfParaEntry
    MAX-ACCESS      not-accessible
    STATUS          current
    DESCRIPTION
        "The BFD Session Entry describes BFD time parameters of interface."  
    INDEX           { zxr10BfdIntfParaIntfName } 
 
    ::= { zxr10BfdIntfParaTable 1 }

Zxr10BfdIntfParaEntry ::=
    SEQUENCE {
        zxr10BfdIntfParaIntfName             DisplayString,
        zxr10BfdIntfParaInterval             Zxr10BfdInterval,
        zxr10BfdIntfParaMinRx                Zxr10BfdInterval,
        zxr10BfdIntfParaMultiplier           Unsigned32
}

zxr10BfdIntfParaIntfName OBJECT-TYPE
    SYNTAX          DisplayString
    MAX-ACCESS      read-only
    STATUS          current
    DESCRIPTION
        "The name of interface." 
    ::= { zxr10BfdIntfParaEntry 1 }

zxr10BfdIntfParaInterval OBJECT-TYPE
    SYNTAX          Zxr10BfdInterval
    MAX-ACCESS      read-only
    STATUS          current
    DESCRIPTION
        "This object specifies the minimum interval, in
        microseconds, that the local system would like to use when 
             transmitting BFD Control packets." 
    ::= { zxr10BfdIntfParaEntry 2 }

zxr10BfdIntfParaMinRx OBJECT-TYPE
    SYNTAX          Zxr10BfdInterval
    MAX-ACCESS      read-only
    STATUS          current
    DESCRIPTION
        "This object specifies the minimum interval, in
        microseconds, between received  BFD Control packets the  
        local system is capable of supporting." 
    ::= { zxr10BfdIntfParaEntry 3 }

zxr10BfdIntfParaMultiplier OBJECT-TYPE
    SYNTAX          Unsigned32
    MAX-ACCESS      read-only
    STATUS          current
    DESCRIPTION
        "This object specifies the Detect time multiplier." 
    ::= { zxr10BfdIntfParaEntry 4 }

-- BFD session Notification
zxr10BfdSessUp NOTIFICATION-TYPE
    OBJECTS         {
                        zxr10BfdSessIndex,
                        zxr10BfdSessIndex
                    }
    STATUS          current
    DESCRIPTION
        "This notification is generated when the
        zxr10BfdSessState object for one or more contiguous 
        entries in zxr10BfdSessTable are about to enter the up(4) 
        state from some other state. The included values of 
        zxr10BfdSessDiag MUST both be set equal to this 
        new state (i.e: up(4)).  The two instances of  
        zxr10BfdSessDiag in this notification indicate the range  
        of indexes that are affected.  Note that all the indexes  
        of the two ends of the range can be derived from the 
        instance identifiers of these two objects.  For the 
        cases where a contiguous range of sessions 
        have transitioned into the up(4) state at roughly 
        the same time, the device SHOULD issue a single 
        notification for each range of contiguous indexes in 
        an effort to minimize the emission of a large number 
        of notifications.  If a notification has to be 
        issued for just a single zxr10BfdSessEntry, then 
        the instance identifier (and values) of the two 
        Zxr10BfdSessIndexTC objects MUST be the identical."
   ::= { zxr10BfdNotifications 1 }

zxr10BfdSessDown NOTIFICATION-TYPE
    OBJECTS         {
                        zxr10BfdSessIndex,
                        zxr10BfdSessIndex
                    }
    STATUS          current
    DESCRIPTION
        "This notification is generated when the
        zxr10BfdSessState object for one or more contiguous 
        entries in zxr10BfdSessTable are about to enter the down(2) 
        or adminDown(1) states from some other state. The included  
        values of zxr10BfdSessDiag MUST both be set equal to this 
        new state (i.e: down(2) or adminDown(1)).  The two instances  
        of zxr10BfdSessDiag in this notification indicate the range  
        of indexes that are affected.  Note that all the indexes  
        of the two ends of the range can be derived from the 
        instance identifiers of these two objects.  For 
        cases where a contiguous range of sessions 
        have transitioned into the down(2) or adminDown(1) states  
        at roughly the same time, the device SHOULD issue a single 
        notification for each range of contiguous indexes in 
        an effort to minimize the emission of a large number 
        of notifications.  If a notification has to be 
        issued for just a single zxr10BfdSessEntry, then 
        the instance identifier (and values) of the two 
        Zxr10BfdSessIndexTC objects MUST be the identical."
   ::= { zxr10BfdNotifications 2 }
-- Note: We need to add notification for changes
-- when the two ends automatically negotiate to a new detection time
-- value or when detection multiplier changes.
-- Similarly, changes in the operating mode (zxr10BfdSessOperMode)
-- also need to be notified.

-- BFD Statistics Table
zxr10BfdStatsTable OBJECT-TYPE
    SYNTAX          SEQUENCE OF Zxr10BfdStatsEntry
    MAX-ACCESS      not-accessible
    STATUS          current
    DESCRIPTION
        "This table contains the statistics of BFD sessions."
    ::= { zxr10BfdObjects 6 }

zxr10BfdStatsEntry OBJECT-TYPE
    SYNTAX          Zxr10BfdStatsEntry
    MAX-ACCESS      not-accessible
    STATUS          current
    DESCRIPTION
        "The Entry describes the statistics of BFD session."
    INDEX           { zxr10BfdStatsType }

    ::= { zxr10BfdStatsTable 1 }

Zxr10BfdStatsEntry ::=
    SEQUENCE {
        zxr10BfdStatsType               INTEGER,
        zxr10BfdStatsUp                 Unsigned32,
        zxr10BfdStatsDown               Unsigned32,
        zxr10BfdStatsInitOrAdmindown    Unsigned32
    }

zxr10BfdStatsType OBJECT-TYPE
    SYNTAX          INTEGER  {
                        all(1),
                        singleHop(2),
                        multiHop(3),
                        l2Bfd(4),
                        ldpActiveBfd(5),
                        ldpPassiveBfd(6),
                        pwBfd(7),
                        rsvpTunnelActiveBfd(8),
                        rsvpTunnelPassiveBfd(9),
                        rsvpLspBfd(10),
                        lagBfd(11)
    }
    MAX-ACCESS      not-accessible
    STATUS          current
    DESCRIPTION
        "The type of this BFD session."
    ::= { zxr10BfdStatsEntry 1 }

zxr10BfdStatsUp OBJECT-TYPE
    SYNTAX          Unsigned32
    MAX-ACCESS      read-only
    STATUS          current
    DESCRIPTION
        "This object contains the number of BFD session
        which state is up."
    ::= { zxr10BfdStatsEntry 2 }

zxr10BfdStatsDown OBJECT-TYPE
    SYNTAX          Unsigned32
    MAX-ACCESS      read-only
    STATUS          current
    DESCRIPTION
        "This object contains the number of BFD session
        which state is down."
    ::= { zxr10BfdStatsEntry 3 }

zxr10BfdStatsInitOrAdmindown OBJECT-TYPE
    SYNTAX          Unsigned32
    MAX-ACCESS      read-only
    STATUS          current
    DESCRIPTION
        "This object contains the number of BFD session
        which state is init or admin down."
    ::= { zxr10BfdStatsEntry 4 }

END
