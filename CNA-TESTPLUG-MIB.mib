CNA-TESTPLUG-MIB DEFINITIONS ::= BEGIN
   IMPORTS
     OBJECT-GROUP, NOTIFICATION-GROUP, MODULE-COMPLIANCE
         FROM SNMPv2-CONF
     Integer32, Unsigned32, enterprises, Gauge32, Counter32, OBJECT-TYPE, 
      MODULE-IDENTITY, NOTIFICATION-TYPE
         FROM SNMPv2-SMI
      RowStatus, TEXTUAL-CONVENTION, TruthValue, DateAndTime, TimeInterval, DisplayString
         FROM SNMPv2-TC      
       InetAddressType, InetAddress, InetPortNumber
         FROM INET-ADDRESS-MIB;
      


     avCnaTestPlugMIB MODULE-IDENTITY
       LAST-UPDATED "200410140843Z"   
     ORGANIZATION
                       "Avaya"
     CONTACT-INFO
     "
       Avaya Customer Services
       Postal: Avaya, Inc.
       211 Mt Airy Rd.
       Basking Ridge, NJ 07920
       USA
       Tel:	+1 908 953 6000
       WWW: 	http://www.avaya.com
     "
     DESCRIPTION
     "              
     This module defines an interface to control an monitor an Avaya's Converged Network
      Analyzer (CNA) test-plug

     Copyright notice:
     
     This AVAYA SNMP Management Information Base Specification (Specification) embodies
     AVAYA confidential and Proprietary intellectual property.  AVAYA retains all Title
     and ownership in the Specification, including any revisionsIt is AVAYA's intent to
     encourage the widespread use of this Specification in connection with the management
     of AVAYA products. AVAYA grants vendors, end-users, and other interested parties a
     non-exclusive license to use this Specification in connection with the management 
     of AVAYA products.This Specification is supplied 'as is', and AVAYA makes no warranty,
     either express or implied, as to the use, operation, condition, or performance of the
      Specification.     
     "
           ::= { avCnaMibs 2 } 
-- Version "200410140843Z"     
--  Add avCnaTpMonLastTestSchedAddrType, avCnaTpMonLastTestSchedAddr, 
--   avCnaTpConfMAC,  avCnaTpConfTestLimiterInterval, avCnaTpConfTestLimiterMaxTests
--
-- Version "200408260848Z"   
--   1. Rename prefix to 'avCna'
--   2. Move root under avCnaMibs
--
-- Version "200408251145Z"   
-- Initial version

avaya OBJECT IDENTIFIER ::= { enterprises 6889 }
       
mibs OBJECT IDENTIFIER ::= { avaya 2 }

avCnaMibs OBJECT IDENTIFIER ::= { mibs 13 }
              
avCnaTpNotification OBJECT IDENTIFIER ::= { avCnaTestPlugMIB 0 }

            
avCnaTpObjects OBJECT IDENTIFIER ::= { avCnaTestPlugMIB 1 }
      
avCnaTpGlobalEnable  OBJECT-TYPE
	SYNTAX TruthValue
    MAX-ACCESS read-write
    STATUS current
    DESCRIPTION 
    "Enable/Disable all testplugs"
    ::= { avCnaTpObjects 1}

avCnaTpVersion  OBJECT-TYPE
	SYNTAX DisplayString
    MAX-ACCESS read-write
    STATUS current
    DESCRIPTION 
    "The version of the test plugs"
    ::= { avCnaTpObjects 2}

avCnaTpMaxNumber  OBJECT-TYPE
	SYNTAX Integer32
    MAX-ACCESS read-write
    STATUS current
    DESCRIPTION 
    "The maximum number of testplugs supported by the device"
    ::= { avCnaTpObjects 3}

avCnaTpConfTable OBJECT-TYPE
	SYNTAX	   SEQUENCE OF AvCnaTpConfEntry
	MAX-ACCESS not-accessible
	STATUS	   current
	DESCRIPTION
	    "Testplug creation and configuration table"
	::= { avCnaTpObjects 4 }
	
	avCnaTpConfEntry OBJECT-TYPE
	SYNTAX	   AvCnaTpConfEntry
	MAX-ACCESS not-accessible
	STATUS	   current
	DESCRIPTION
	    ""
	INDEX {
	     avCnaTpConfId
	}
	::= { avCnaTpConfTable 1 }



    AvCnaTpConfEntry ::= SEQUENCE {
    	avCnaTpConfId	Integer32,
    	avCnaTpConfBindTo	INTEGER,
		avCnaTpConfIfIndex	Integer32,
		avCnaTpConfAddressType	InetAddressType,
		avCnaTpConfAddress	InetAddress,
		avCnaTpConfControlPort	InetPortNumber,
		avCnaTpConfRtpTestPoint	INTEGER,
		avCnaTpConfRtpTestPort	InetPortNumber,
		avCnaTpConfRtpEchoPort	InetPortNumber,
		avCnaTpConfClearCounters	TruthValue,
		avCnaTpConfMAC	OCTET STRING,
		avCnaTpConfTestLimiterInterval	Integer32,
		avCnaTpConfTestLimiterMaxTests	Integer32,		
		avCnaTpConfRowStatus	RowStatus
    }

    avCnaTpConfId OBJECT-TYPE
            SYNTAX Integer32
            MAX-ACCESS not-accessible
            STATUS current
            DESCRIPTION
              "The test plug instance identifier."    
            ::= { avCnaTpConfEntry 1 }
	
    avCnaTpConfBindTo OBJECT-TYPE
            SYNTAX INTEGER {  none(1),   pmi(2),  ifIndex(3),  ipAddress(4)}
            MAX-ACCESS read-write
            STATUS current
            DESCRIPTION
              "The test plug interface binding method:
                 none(1) - the tesplug is disabled
                 
                 pmi(2) - bind to the primary management interface (i.e. the SNMP agent
                   interface). This method is applicable to devices with only one interface
                   (like IP phones) and to G350 R4.  
                   
                 ifIndex(3) - bind to a specific interface. This method is applicable to
                  devices that supports dynamic IP addresses (like security gateways). 

                 ipAddress(4) - bind to a specific IP interface. This method is applicable
                  to L2 interfaces with multiple L3 interface (e.g. two IP interfaces
                  over a VLAN)."    
            DEFVAL { none }
            ::= { avCnaTpConfEntry 2 }
            

     avCnaTpConfIfIndex OBJECT-TYPE
            SYNTAX Integer32
            MAX-ACCESS read-write
            STATUS current
            DESCRIPTION
              "The interface number (RFC1213-MIB/IfIndex) for this test-plug.
              
              This item is writeable when avCnaTpConfBindTo is 'none(1) or ifIndex(3)."    
            ::= { avCnaTpConfEntry 3 }            
            
            

      avCnaTpConfAddressType OBJECT-TYPE
            SYNTAX InetAddressType
            MAX-ACCESS read-write
            STATUS current            
            DESCRIPTION
              "The address type for the test plug.
              
              This item is writeable when avCnaTpConfBindTo is 'none(1) or ipAddress (4)."    
            ::= { avCnaTpConfEntry 4 }                        
            
            
      avCnaTpConfAddress OBJECT-TYPE
            SYNTAX  InetAddress
            MAX-ACCESS read-write
            STATUS current
            DESCRIPTION
              "The address for the test plug.
              
              This item is writeable when avCnaTpConfBindTo is 'none(1) or ipAddress (4)."    
            ::= { avCnaTpConfEntry 5 }                        
                        
      avCnaTpConfControlPort OBJECT-TYPE
            SYNTAX InetPortNumber 
            MAX-ACCESS read-write
            STATUS current
            DESCRIPTION
              "The UDP port on which the test plug listens for commands from the scheduler."    
            ::= { avCnaTpConfEntry  6}                        
            
            
      avCnaTpConfRtpTestPoint OBJECT-TYPE
            SYNTAX INTEGER {network(1), voip-app(2)}
            MAX-ACCESS read-write
            STATUS current
            DESCRIPTION
              "Select the test point for RTP test to be either the 'network' or the
               'voip-app' (including internal delays)"    
            ::= { avCnaTpConfEntry  7}                        
                        
      avCnaTpConfRtpTestPort OBJECT-TYPE
            SYNTAX InetPortNumber
            MAX-ACCESS read-write
            STATUS current
            DESCRIPTION
              "The UDP port for RTP tests."  
            ::= { avCnaTpConfEntry  8}                        

      avCnaTpConfRtpEchoPort OBJECT-TYPE
            SYNTAX InetPortNumber
            MAX-ACCESS read-write
            STATUS current
            DESCRIPTION
              "The UDP RTP tests echo port."  
            ::= { avCnaTpConfEntry  9}               
            
      avCnaTpConfClearCounters OBJECT-TYPE
            SYNTAX TruthValue
            MAX-ACCESS read-write
            STATUS current
            DESCRIPTION
              "Clear the test plug activity counters"    
            ::= { avCnaTpConfEntry 10 }      
            
     avCnaTpConfMAC OBJECT-TYPE
            SYNTAX OCTET STRING
            MAX-ACCESS read-write
            STATUS current
            DESCRIPTION
              "The MAC address used to uniquely identify the test plug"    
            ::= { avCnaTpConfEntry 11 }      

	 avCnaTpConfTestLimiterInterval OBJECT-TYPE
            SYNTAX Integer32
            MAX-ACCESS read-write
            STATUS current
            DESCRIPTION
              "The Test rate limiter interval in seconds"    
            DEFVAL {60}
            ::= { avCnaTpConfEntry 12 }                 

	 avCnaTpConfTestLimiterMaxTests OBJECT-TYPE
            SYNTAX Integer32
            MAX-ACCESS read-write
            STATUS current
            DESCRIPTION
              "The Test rate limiter interval in seconds"    
            DEFVAL {10}
            ::= { avCnaTpConfEntry 13 }
	
      avCnaTpConfRowStatus OBJECT-TYPE
            SYNTAX RowStatus
            MAX-ACCESS read-write
            STATUS current
            DESCRIPTION
              "Create/Delete a test-plug."    
            ::= { avCnaTpConfEntry 14 }  


----
avCnaTpSchedulerTable OBJECT-TYPE
	SYNTAX	   SEQUENCE OF AvCnaTpSchedulerEntry
	MAX-ACCESS not-accessible
	STATUS	   current
	DESCRIPTION
	    "Scheduler list configuration table"
	::= { avCnaTpObjects 5 }
	
	avCnaTpSchedulerEntry OBJECT-TYPE
	SYNTAX	   AvCnaTpSchedulerEntry
	MAX-ACCESS not-accessible
	STATUS	   current
	DESCRIPTION
	    ""
	INDEX {
	     avCnaTpConfId, avCnaTpSchedulerIndex
	}
	::= { avCnaTpSchedulerTable 1 }



    AvCnaTpSchedulerEntry ::= SEQUENCE {
      avCnaTpSchedulerIndex	Integer32,
      avCnaTpSchedulerAddressType	InetAddressType,
      avCnaTpSchedulerAddress	InetAddress,
      avCnaTpSchedulerPortNumber	InetPortNumber,
      avCnaTpSchedulerRowStatus	RowStatus

    }

     avCnaTpSchedulerIndex OBJECT-TYPE
            SYNTAX Integer32
            MAX-ACCESS not-accessible
            STATUS current
            DESCRIPTION
              "The index of this scheduler in the Scheduler-list."    
            ::= { avCnaTpSchedulerEntry 1 }
            

     avCnaTpSchedulerAddressType OBJECT-TYPE
            SYNTAX InetAddressType
            MAX-ACCESS read-write
            STATUS current
            DESCRIPTION
              "Address type for the scheduler"    
            DEFVAL { ipv4 }
            ::= { avCnaTpSchedulerEntry 2  }

     avCnaTpSchedulerAddress OBJECT-TYPE
            SYNTAX  InetAddress
            MAX-ACCESS read-write
            STATUS current
            DESCRIPTION
              "Address of the scheduler."    
            ::= { avCnaTpSchedulerEntry 3 }

     avCnaTpSchedulerPortNumber OBJECT-TYPE
            SYNTAX InetPortNumber
            MAX-ACCESS read-write
            STATUS current
            DESCRIPTION
              "Scheduler registration TCP port (default: 8888)."                 
            DEFVAL {8888}
            ::= { avCnaTpSchedulerEntry 4 }

     avCnaTpSchedulerRowStatus OBJECT-TYPE
            SYNTAX RowStatus
            MAX-ACCESS read-write
            STATUS current
            DESCRIPTION
              "Create/Delete a scheduler to the list."    
            ::= { avCnaTpSchedulerEntry 5 }

---
avCnaTpMonTable OBJECT-TYPE
	SYNTAX	   SEQUENCE OF AvCnaTpMonEntry
	MAX-ACCESS not-accessible
	STATUS	   current
	DESCRIPTION
	    "This table monitors test plugs activity."
	::= { avCnaTpObjects 6 }
	
	avCnaTpMonEntry OBJECT-TYPE
	SYNTAX	   AvCnaTpMonEntry
	MAX-ACCESS not-accessible
	STATUS	   current
	DESCRIPTION
	    ""
	INDEX {
	     avCnaTpConfId
	}
	::= { avCnaTpMonTable 1 }



    AvCnaTpMonEntry ::= SEQUENCE {
       avCnaTpMonRegStatus	INTEGER,
       avCnaTpMonSchedIndex	Integer32,
       avCnaTpMonLastTest	INTEGER,
       avCnaTpMonRemTestAddrType	InetAddressType,
       avCnaTpMonRemTestAddr	InetAddress, 
       avCnaTpMonLastTestSchedAddrType	InetAddressType,	
       avCnaTpMonLastTestSchedAddr	InetAddress,	
       avCnaTpMonLastTestRes	DisplayString
       
    }

     avCnaTpMonRegStatus OBJECT-TYPE
            SYNTAX INTEGER {
               unregistered(1),
               schedListExhausted(2),
               idle(3),
               test(4),
               suspended(5),
               noIp(6),
               badIP(7),
               schedListEmpty(8),
               controlPortBindFailed(9),
               rtpPortBindFailed(10) }
            MAX-ACCESS read-only
            STATUS current
            DESCRIPTION
              "Test Plug status where:
                 unregistered ::= The test plug is attempting to register and is
                   currently unregistered.
                   
                 schedListExhausted ::= The test plug has exhausted its scheduler 
                   list at least once, and is now attempting to register.
                 
                 idle ::= Test Plug is registering but idle.
                 
                 test ::= The test plug is running a test.
                 
                 suspended ::= The test plug is idle because a test was cancelled.
                 
                 noIp ::= No IP address is configured for the test-plug interface
                 
                 badIP ::= The configured test plug address is not configured for the                 
                       test-plug interface. 
                 
                 schedListEmpty ::= The scheduler list is empty (test plug disabled)
                 
                 controlPortBindFailed ::= cannot bind the UDP control port
                 
                 rtpPortBindFailed ::= cannot bind the UDP port for RTP tests."    
            ::= { avCnaTpMonEntry 1 }

     avCnaTpMonSchedIndex OBJECT-TYPE
            SYNTAX Integer32
            MAX-ACCESS read-only
            STATUS current
            DESCRIPTION
              "The index of the scheduler on which the test plug is registered or 
                attempting to register (avCnaTpSchedulerIndex)"    
            ::= { avCnaTpMonEntry 2 }

     avCnaTpMonLastTest OBJECT-TYPE
            SYNTAX INTEGER {
              none(0),
              traceRoute(1),
              rtp(2),
              ping(3),
              tcpConnect(4),
              merge(5)
            }
            MAX-ACCESS read-only
            STATUS current
            DESCRIPTION
              "The current/last test performed by the test plug."    
            ::= { avCnaTpMonEntry 3 }

     avCnaTpMonRemTestAddrType OBJECT-TYPE
            SYNTAX InetAddressType
            MAX-ACCESS read-only
            STATUS current
            DESCRIPTION
              "The Remote test peer address type"    
            ::= { avCnaTpMonEntry 4 }
                      

     avCnaTpMonRemTestAddr OBJECT-TYPE
            SYNTAX InetAddress
            MAX-ACCESS read-only
            STATUS current
            DESCRIPTION
              "The remote test peer address."    
            ::= { avCnaTpMonEntry 5 }

     avCnaTpMonLastTestSchedAddrType OBJECT-TYPE
            SYNTAX InetAddressType
            MAX-ACCESS read-only
            STATUS current
            DESCRIPTION
              ""    
            ::= { avCnaTpMonEntry 6 }
                      

     avCnaTpMonLastTestSchedAddr OBJECT-TYPE
            SYNTAX InetAddress
            MAX-ACCESS read-only
            STATUS current
            DESCRIPTION
              "Address of scheduler which initiated the last test."    
            ::= { avCnaTpMonEntry 7 }



     avCnaTpMonLastTestRes OBJECT-TYPE
            SYNTAX DisplayString
            MAX-ACCESS read-only
            STATUS current
            DESCRIPTION
              "Last test result string"    
            ::= { avCnaTpMonEntry 8 }
            
--

avCnaTpTestTable OBJECT-TYPE
	SYNTAX	   SEQUENCE OF AvCnaTpTestEntry
	MAX-ACCESS not-accessible
	STATUS	   current
	DESCRIPTION
	    "Per test activity counters"
	::= { avCnaTpObjects 7 }
	
	avCnaTpTestEntry OBJECT-TYPE
	SYNTAX	   AvCnaTpTestEntry
	MAX-ACCESS not-accessible
	STATUS	   current
	DESCRIPTION
	    ""
	INDEX {
	     avCnaTpConfId, avCnaTpTestId
	}
	::= { avCnaTpTestTable 1 }



    AvCnaTpTestEntry ::= SEQUENCE {
   		avCnaTpTestId	Integer32,
   		avCnaTpTestName	DisplayString,
   		avCnaTpTestCount	Counter32,
   		avCnaTpTestCancelled	Counter32,
   		avCnaTpTestFailed	Counter32
    }

      avCnaTpTestId OBJECT-TYPE
            SYNTAX Integer32
            MAX-ACCESS not-accessible
            STATUS current
            DESCRIPTION
              "Test ID"    
            ::= { avCnaTpTestEntry 1 }
            

      avCnaTpTestName OBJECT-TYPE
            SYNTAX  DisplayString
            MAX-ACCESS read-only
            STATUS current
            DESCRIPTION
              "The test name (e.g. 'ping')"    
            ::= { avCnaTpTestEntry 2}

      avCnaTpTestCount OBJECT-TYPE
            SYNTAX  Counter32
            MAX-ACCESS read-only
            STATUS current
            DESCRIPTION
              "Number of executed tests"    
            ::= { avCnaTpTestEntry 3}

      avCnaTpTestCancelled OBJECT-TYPE
            SYNTAX Counter32
            MAX-ACCESS read-only
            STATUS current
            DESCRIPTION
              "Number of cancelled tests"    
            ::= { avCnaTpTestEntry 4}


      avCnaTpTestFailed OBJECT-TYPE
            SYNTAX Counter32
            MAX-ACCESS read-only
            STATUS current
            DESCRIPTION
              "Number of failed tests"    
            ::= { avCnaTpTestEntry 5 }
           
      
END
