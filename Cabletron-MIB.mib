-- 
--            Cabletron Management Information Base
--       For the MMAC Intelligent Repeater (IRBM & IRM2)
--                       By: Howard Brown
--                           Rev: 1.2 
--                     Date: July 20, 1991 
-- 
-- NOTE: Not all devices support all objects
-- 
-- REVISION HISTORY
-- 
-- Rev. 0.1 - Initial REV.
-- 
-- Rev. 0.2 - Revised to simplify and reflect IRM
-- 
-- Rev. 0.3 - Revised and updated.
--      (1) Changed Errors to Collisions where appropriate.
--      (2) Removed the redundant entries
--      (3) Renumbered boards to reflect reality
--      (4) Renamed  err_limit to alarm_limit to reflect proper
-- use.
-- 
-- Rev. 0.4 - Revised and updated. Now fully reflects IRBM, IRM
-- MIB       seperated.
--      (1) Added topological port types
--      (2) Added statistics by topological port type.
--      (3) Spread  port status  to 3  variables ( admin, link,
-- network)
--      (4) Added source address support
--      (5) Added Redundancy
--      (6) Added SNMP controlled device discovery
--      (7) Moved Alarm control to its own section of the MIB.
--      (8) Redefined alarms
--      (9) Defined TRAP types
-- 
-- Rev. 0.5 - Reflects the IRBM as of release 0.0.1
-- 
-- Rev. 0.5a - Working version - Reflects as built for 0.0.4
-- 
-- Rev. 0.6  - Reflects the IRBM as of 0.1.1
-- Formal description of the Cabletron MIB
-- 
-- Rev 1.0 - Reflects the IRBM, IRM2, MRXI, and MiniMMAC products as 
-- 	of their first customer ship (NOT BETA)
--	Put into concise format and run thru the Mosy compiler
-- Rev 1.1 - Fixed the first round of bugs
--	(1) Added missing token ring based objects to RepeaterRev2.device
--	(2) Added the PC card variable
--	(3) fixed typos
--	(4) added more complete definition of RepeaterRev2 tree
--
-- Rev 1.2 - Removed the duplicate names
--

Cabletron-MIB DEFINITIONS ::= BEGIN

IMPORTS
	enterprises, Counter FROM RFC1155-SMI
	OBJECT-TYPE, IpAddress FROM SNMPv2-SMI;

cabletron      OBJECT IDENTIFIER ::= { enterprises 52 }

commsDevice    OBJECT IDENTIFIER ::= { cabletron 1 }

layerMgmt      OBJECT IDENTIFIER ::= { cabletron 2 }

common         OBJECT IDENTIFIER ::= { commsDevice 1 } 

repeater       OBJECT IDENTIFIER ::= { commsDevice 2 }

bridge         OBJECT IDENTIFIER ::= { commsDevice 3 }

router         OBJECT IDENTIFIER ::= { commsDevice 4 }

product        OBJECT IDENTIFIER ::= { commsDevice 5 }

subsystem      OBJECT IDENTIFIER ::= { commsDevice 6 }

commonRev1     OBJECT IDENTIFIER  ::= { common  1 }

sysOIDs	       OBJECT IDENTIFIER  ::= { common 2 }

repeaterRev1   OBJECT IDENTIFIER  ::= { repeater 1 }

repeaterRev2   OBJECT IDENTIFIER  ::= { repeater 2 } 

-- Common MIB Structure
-- ---------------------
-- 
--      The Common MIB is a group of objects that are common to
-- all communications devices. This section will describe these
-- objects.
-- 
-- Instance Identifiers for Common objects
-- ----------------------------------------
-- 
--      There is  only one  instance of an Common object in any
-- device. Thus the Instance Identifier is 0.




deviceType     OBJECT-TYPE

SYNTAX  INTEGER
ACCESS  read-only
STATUS  mandatory
DESCRIPTION
	"This object  defines the  board type for the Management
board in  the device.  (eg. IRBM,  IRM). See  appendix A for
value."

::= { commonRev1 1 }



deviceName    OBJECT-TYPE

SYNTAX  OCTET STRING
ACCESS  read-write
STATUS  mandatory
DESCRIPTION
	"An ASCII name of the device that this agent manages."
::= { commonRev1 2 }



deviceIPAddress    OBJECT-TYPE

SYNTAX  IpAddress
ACCESS  read-write
STATUS  mandatory
DESCRIPTION
     "The Internet address of this device."
::= { commonRev1 3 }




currentTime    OBJECT-TYPE

SYNTAX  OCTET STRING (SIZE(8))
ACCESS  read-write
STATUS  mandatory
DESCRIPTION
     "The current time of day as measured by the device"
::= { commonRev1 4 }




currentDate        OBJECT-TYPE

SYNTAX  OCTET STRING (SIZE(8))
ACCESS  read-write
STATUS  mandatory 
DESCRIPTION
     "Character representation of the current date"
::= { commonRev1 5 }




mACAddress   OBJECT-TYPE
	 
SYNTAX   OCTET STRING
ACCESS  read-only 
STATUS   mandatory
DESCRIPTION 
      	"The  MAC (Ethernet)  address of  the MMAC. This
can also be obtained from address translation MIB. The 
Instance   Identifier  for   the  MAC  address  is interface
number. For the IRBM, their are 2."

::= { commonRev1 6 }

-- SysOIDs definitions
-- 
-- This section defines the values returned by the System OID
-- in the Internet MIB. These are NOT objects in the MIB but
-- come from the OID tree assigned to Cabletron.
-- 
-- 
-- Formal Definitions

sysOtherType	OBJECT IDENTIFIER ::= { sysOIDs 1 }
	-- All devices that do not fit into the following classes
	--

sysIRMType 	OBJECT IDENTIFIER ::= { sysOIDs 2 }
	-- All devices that fit into the IRM slot of an MMAC

sysRepType	OBJECT IDENTIFIER ::= { sysOIDs 3 }
	-- All standalone Repeater devices

sysBDGType	OBJECT IDENTIFIER ::= { sysOIDs 4 }
	-- All standalone bridges

-- sysIRM Object Identifiers

soidIRMSNMP	OBJECT IDENTIFIER ::= { sysIRMType 1 }

soidIRBM	OBJECT IDENTIFIER ::= { sysIRMType 2 }

soidIRM2	OBJECT IDENTIFIER ::= { sysIRMType 3 }

-- sysRepType Object identifiers

soidMINIMMAC	OBJECT IDENTIFIER ::= { sysRepType 1 }

soidMRXI	OBJECT IDENTIFIER ::= { sysRepType 2 }

-- Formal definitions for RepeaterRev1	 

device    OBJECT IDENTIFIER   ::= { repeaterRev1 1 }

board     OBJECT IDENTIFIER   ::= { repeaterRev1 2 }

port      OBJECT IDENTIFIER   ::= { repeaterRev1 3 }
					 
sourceAddr OBJECT IDENTIFIER ::= { repeaterRev1 7 }
     					 
redundancy OBJECT IDENTIFIER   ::= { repeaterRev1 8 }

alarm    OBJECT IDENTIFIER   ::= { repeaterRev1 9 }



-- device Object Definitions
-- 
--      This section defines the objects under the Device node.
-- 
-- Instance Identifiers for device objects
-- 
--      Again there is only one instance of an device object in
-- any device. Thus the Instance Identifier is 0.
-- 
-- device Objects




deviceMMACType   OBJECT-TYPE

SYNTAX     INTEGER
     {
          mMAC8(0),
          mMAC3(1)
     }
ACCESS  read-only
STATUS  mandatory
DESCRIPTION
	"Indicates the type of MMAC."
::= { device 2 }




deviceSlots   OBJECT-TYPE

SYNTAX     INTEGER
     {
          mMAC8(8),
          mMAC3(3)
     }

ACCESS  read-only
STATUS  mandatory
DESCRIPTION
     "Number  of  available  device  slots  in  this  device,
     including the IRM slot."
::= { device 3 }


deviceOccupiedSlots   OBJECT-TYPE

SYNTAX  INTEGER
ACCESS  read-only
STATUS  mandatory
DESCRIPTION
     "The slots that contain MIM boards.
  
     This field  is bit  encoded (eg.  If a  bit is set then
that board  is present.  For example, a value of 3 indicates
that there  are boards  in the  IRM slot  and the  first MIM
slot."

::= { device 4 }


devicePortsOn   OBJECT-TYPE

SYNTAX  INTEGER
ACCESS  read-only
STATUS  mandatory
DESCRIPTION
     "The number of operating ports on the device."

::= { device 5 }


deviceTotalPorts   OBJECT-TYPE

SYNTAX  INTEGER
ACCESS  read-only
STATUS  mandatory
DESCRIPTION
     "The total number of repeater ports on the MMAC."

::= { device 6 }

deviceTotalPkts   OBJECT-TYPE

SYNTAX  Counter
ACCESS  read-only    
STATUS  mandatory
DESCRIPTION
     "The number  of packets  detected on  all ports  of this
     device."


::= { device 7 }


deviceTotalErrors   OBJECT-TYPE

SYNTAX  Counter
ACCESS  read-only
STATUS  mandatory
DESCRIPTION
     "The  sum   of  all   of  the  errors  listed  including
     alignment,CRC,  runts,   giants,  and   Out  of  window
     collisions."

::= { device 8 }


deviceTransmitColl  OBJECT-TYPE

SYNTAX  Counter
ACCESS  read-only
STATUS  optional
DESCRIPTION
     "The number  of transmit  collisions  detected  by  this
MMAC."


::= { device 9 }

deviceRecColls   OBJECT-TYPE

SYNTAX  Counter
ACCESS  read-only
STATUS  optional
DESCRIPTION
     "The number of receive collsions detected by this MMAC."

::= { device 10 }

deviceAlign   OBJECT-TYPE

SYNTAX  Counter
ACCESS  read-only
STATUS  optional
DESCRIPTION
     "The number  of packets with alignement errors detected.
    "


::= { device 11 }

deviceCRC   OBJECT-TYPE

SYNTAX  Counter
ACCESS  read-only
STATUS  optional
DESCRIPTION
     "The number of packets with bad CRC detected. "


::= { device 12 }

deviceRunt   OBJECT-TYPE


SYNTAX  Counter
ACCESS  read-only
STATUS  optional
DESCRIPTION
     "The number  of runt  frames detected  by  this  device."


::= { device 13  }

deviceOOWColl  OBJECT-TYPE

SYNTAX  Counter
ACCESS  read-only
STATUS  optional
DESCRIPTION
     "The number of out-of-window collisions detected by this"
::= { device 14 }

deviceNoResources OBJECT-TYPE

SYNTAX  Counter
ACCESS  read-only
STATUS  mandatory
DESCRIPTION
     "The number of No resource condtions detected."


::= { device 15 }

deviceRecBytes   OBJECT-TYPE

SYNTAX  Counter
ACCESS  read-only
STATUS  optional
DESCRIPTION
     "The number of bytes detected on the network."

::= { device 16 }


deviceGiantFrames   OBJECT-TYPE

SYNTAX  Counter
ACCESS  read-only
STATUS  mandatory
DESCRIPTION
     "The number of longer than 1518 bytes."

::= { device 17 }


deviceRestart    OBJECT-TYPE

SYNTAX  INTEGER
ACCESS  read-write 
STATUS  mandatory
DESCRIPTION
     "If this object is set to 0 the device is restarted."
::= { device 18 }

deviceResetCounter  OBJECT-TYPE

SYNTAX  Counter
ACCESS  read-write 
STATUS  mandatory
DESCRIPTION
     "If this object is set to 0, all of the devices Counters
     are reset to 0."

::= { device 19 }


deviceRedundantCts  OBJECT-TYPE

SYNTAX  INTEGER
ACCESS  read-only
STATUS  mandatory
DESCRIPTION
     "The number of redundant circuits available for use."

::= { device 20 }


deviceTimeBase  OBJECT-TYPE

SYNTAX  INTEGER
ACCESS  read-write
STATUS  mandatory
DESCRIPTION
     "The  number   of  seconds  used  as  the  interval  for
performing all  of the  rate alarm checks. The minimum is 10
secs."

::= { device 24 }




deviceResetRedundancy       OBJECT-TYPE

SYNTAX	 INTEGER
ACCESS  read-write
STATUS  mandatory
DESCRIPTION
	"Setting this object to a 1 will reset redundancy for the 
entire box."

::= { device 25 }




deviceSrcAddrAgingTime       OBJECT-TYPE

SYNTAX	 INTEGER
ACCESS  read-write
STATUS  mandatory
DESCRIPTION
	"The number of minutes that a source address is not detected before 
it is removed from the source address table."

::= { device 26 }

deviceSrcAddrTraps       OBJECT-TYPE
SYNTAX	 INTEGER
	{
	  trapsoff(1),
	  trapson(2)
	}
ACCESS  read-write
STATUS  mandatory
DESCRIPTION
	"Controls sending of source address related traps."
::= { device 27 }

deviceSrcAddrLocked       OBJECT-TYPE

SYNTAX	INTEGER
	{
	  lockoff(1),
	  lockon(2)
	}

ACCESS  read-write
STATUS  mandatory
DESCRIPTION
	"If this is set to 2, any source addresses
that are detected on station ports that are not in the table 
will cause the port to be turned off."

::= { device 28 }


deviceEnetBoardMap OBJECT-TYPE

SYNTAX INTEGER
ACCESS read-only
STATUS mandatory
DESCRIPTION
    "The slots that contain Ethernet MIM boards."

--    This field is bit encoded (e.g.  If a bit is set then that board
-- is present and is an Ethernet MIM.)  For example, a value of 3 indicates
-- that there are boards in the IRM slot and the first MIM slot and that 
-- these boards are Ethernet MIMs.

::= { device 29 }

deviceTokenRingBoardMap	OBJECT-TYPE

SYNTAX INTEGER
ACCESS read-only
STATUS mandatory

DESCRIPTION

    "The slots that contain Token Ring MIM boards."

--    This field is bit encoded (e.g.  If a bit is set then that board
-- is present and is a Token Ring MIM.)  For example, a value of 2 indicates
-- that there is a board in the first MIM slot and the board is a Token Ring
-- MIM.

::= { device 30 }

deviceFDDIBoardMap OBJECT-TYPE

SYNTAX INTEGER
ACCESS read-only
STATUS mandatory
DESCRIPTION

    "The slots that contain FDDI MIM boards."

--    This field is bit encoded (e.g.  If a bit is set then that board
-- is present and is a FDDI MIM.)  For example, a value of 2 indicates
-- that there is a board in the first MIM slot and the board is a FDDI
-- MIM.
::= { device 31 }

-- sourceAddr object definitions
-- 
--      The sourceAddr object section contains objects that can
-- be accessed by source address.
-- 
--  Instance Identifier for sourceAddr objects
-- 
--      The instance  identifier for  these  variables  is  the
-- source address  the user is interested in. Each octet of the
-- source address  forms a term in the instance identifier (see
-- below)
     




sourceAddrBoard  OBJECT-TYPE

SYNTAX  INTEGER
ACCESS  read-only
STATUS  mandatory
DESCRIPTION
     "The board  number of  the port that the supplied source
     address has been found on."
::= { sourceAddr 1 }




sourceAddrPort  OBJECT-TYPE

SYNTAX  INTEGER
ACCESS  read-only
STATUS  mandatory
DESCRIPTION
     "The port  number of  the port  that the supplied source
     address has been found on."

::= { sourceAddr 2 }

-- redundancy Object Definitions
-- 
--      This section  defines the  objects that  are associated
-- with cable  level redundancy.  The  concepts  for  this  are
-- described in  other documentation.  It should  be noted here
-- that the  port specific  objects for redundancy can be found
-- in the PORT section of the MIB.
-- The maximum number of redundant circuits can be found in the
-- DEVICE section of the MIB.
-- 
-- Instance Identifiers for redundancy Objects
-- 
--      There  are   two  types  of  instance  identifiers  for
-- redundancy objects. First, are the global objects that apply
-- to all redundant circuits. These have an instance identifier
-- of 0.  The second  kind of  object is  circuit specific, the
-- instance identifier for these is the circuit number.





redundancyPollInterval   OBJECT-TYPE

SYNTAX  INTEGER
ACCESS  read-write
STATUS  mandatory
DESCRIPTION
     "The number of seconds between polls for redundancy."

::= { redundancy 1 }




redundancyTestTod   OBJECT-TYPE

SYNTAX  OCTET STRING
ACCESS  read-write
STATUS  mandatory
DESCRIPTION
     "The time of day at which the redundant circuits should be tested."

::= { redundancy 2 }




redundancyPerformTest   OBJECT-TYPE

SYNTAX  INTEGER
	{
	   performTest(1)
	}

ACCESS  read-write
STATUS  mandatory
DESCRIPTION
	"Test the redundant circuit."
::= { redundancy 3 }




redundancyCircuitName   OBJECT-TYPE

SYNTAX  OCTET STRING
ACCESS  read-write
STATUS  mandatory
DESCRIPTION
     "The name of the indicated circuit."

::= { redundancy 4 }




redundancyRetryCount  OBJECT-TYPE

SYNTAX  INTEGER
ACCESS  read-write
STATUS  mandatory
DESCRIPTION
     "The number  of unanswered polls  allowed for the indicated 
     circuit before the current connection is declared bad."

::= { redundancy 5 }




redundancyNumBPs   OBJECT-TYPE

SYNTAX  INTEGER
ACCESS  read-only
STATUS  mandatory
DESCRIPTION
     "The number of board/port combinations associated with the 
     indicated circuit."

::= { redundancy 6 }




redundancyCircuitBoards   OBJECT-TYPE

--      Note:The  instance identifier for this object is the circuit 
--      number followed by an index.  The index  has no  other meaning 
--      than to be used as an index for the purposes of the GET NEXT 
--      operation.

SYNTAX  INTEGER
ACCESS  read-only
STATUS  mandatory
DESCRIPTION
     "The boards associated with the indicated circuit, accessed by index."

::= { redundancy 7 }




redundancyCircuitPort   OBJECT-TYPE

--      Note:The  instance identifier for this object is the circuit 
--      number followed by an index.  The index  has no  other meaning 
--      than to be used as an index for the purposes of the GET NEXT 

SYNTAX  INTEGER
ACCESS  read-only
STATUS  mandatory
DESCRIPTION
     "The ports associated with the indicated circuit, accessed by index."

::= { redundancy 8 }




redundancyCircuitTypes   OBJECT-TYPE

--      Note:The  instance identifier for this object is the circuit 
--      number followed by an index.  The index  has no  other meaning 
--      than to be used as an index for the purposes of the GET NEXT 
--      operation.

SYNTAX  INTEGER
ACCESS  read-only
STATUS  mandatory
DESCRIPTION
     "The type of each port associated with the indicated circuit, 
     accessed by index."

::= { redundancy 9 }




redundancyCircuitNumAddr   OBJECT-TYPE

SYNTAX  INTEGER
ACCESS  read-only
STATUS  mandatory
DESCRIPTION
     "The number of addresses associated with the indicated circuit."

::= { redundancy 10 }




redundancyCircuitMACAddrAdd   OBJECT-TYPE

SYNTAX  OCTET STRING
ACCESS  read-write
STATUS  mandatory
DESCRIPTION
     "Adds the ethernet address to the polling list for the 
     indicated circuit."

::= { redundancy 11 }




redundancyCircuitMACAddrDel   OBJECT-TYPE

SYNTAX  OCTET STRING
ACCESS  read-write
STATUS  mandatory
DESCRIPTION
     "Removes the ethernet address from the polling list for the 
     indicated circuit."

::= { redundancy 12 }




redundancyCircuitMACAddrDisp   OBJECT-TYPE

--      Note:The  instance identifier for this object is the circuit 
--      number followed by an index.  The index  has no  other meaning 
--      than to be used as an index for the purposes of the GET NEXT 
--      operation.

SYNTAX  OCTET STRING
ACCESS  read-only
STATUS  mandatory
DESCRIPTION
     "The ethernet addresses associated with the indicated circuit, 
     accessed by index."
::= { redundancy 13 }

redundancyCircuitEnable   OBJECT-TYPE

SYNTAX  INTEGER
     {
          disable(1),
          enable(2)
     }

ACCESS  read-write
STATUS  mandatory
DESCRIPTION
     "Enables and disables the indicated circuit."

::= { redundancy 14 }


redundancyCircuitReset   OBJECT-TYPE

SYNTAX  INTEGER
     {
          reset(1)
     }

ACCESS  read-write
STATUS  mandatory
DESCRIPTION
     "Reset the  indicated circuit. Return all  of the  associated 
     board and ports to NOT-USED, remove  associated addresses
     from the polling list, reset the circuit name and retry 
     count to default values ."
::= { redundancy 15 }

-- alarm Object definitions
-- 
--      This section  defines the objects that can cause alarms
-- to be  generated. All  of the  alarm objects  presented  are
-- objects that derive there values from other parts of the MIB
-- and hence  the structure  of this section of the MIB mirrors
-- the sections that generate the raw data.
-- 
--      For each section there are 3 sources of alarms:Traffic
-- levels, collsion  rates (as  they relate  to  traffic),  and
-- error rates  (also  related  to  traffic).  All  alarms  are
-- qualified by  the Devicetimebase (ie. the rates are measured
-- for a particular length of time).
-- 
--  Formal defintions for the structure below alarm

     devAlrm        OBJECT IDENTIFIER   ::= { alarm 1 }

     bdAlrm         OBJECT IDENTIFIER   ::= { alarm 2 }

     portAlrm       OBJECT IDENTIFIER   ::= { alarm 3 }


-- devAlrm object defintions
-- 
--      This section  defines the  objects  that  will  control
-- alarms associated with the device.
-- 
-- devAlrm Instance Identifiers
--      There is  only one  set of device level alarms per MMAC
-- thus the instance identifiers for DevAlrm objects is 0.
-- 
-- Formal defintions below devAlrm

     devTraffic     OBJECT IDENTIFIER   ::= { devAlrm 1 }

     devColls       OBJECT IDENTIFIER   ::= { devAlrm 2 }

     devError       OBJECT IDENTIFIER   ::= { devAlrm 3 }


-- devTraffic Object Definitions
-- 
--      This  section  define  the  devTraffic  objects.  These
-- objects control the device level traffic alarm generation.




devTrafficEnable OBJECT-TYPE

SYNTAX  INTEGER
     {
          disable(1),
          enable(2)
     }

ACCESS  read-write
STATUS  mandatory
DESCRIPTION
     "Enable the sending of device level traffic traps."

::= { devTraffic 1 }




devTrafficThreshold  OBJECT-TYPE

SYNTAX  Counter
ACCESS  read-write
STATUS  mandatory
DESCRIPTION 
	  "The   threshold   of   packets   within   the
     devicetimebase that will cause a traffic alarm."

::= { devTraffic 2 }


-- devColls Object Defintions
-- 
--      This section  defines  the  objects  that  control  the
-- device level collision alarm.




devCollsEnable  OBJECT-TYPE

SYNTAX  INTEGER
     {
          disable(1),
          enable(2)
     }

ACCESS  read-write
STATUS  mandatory
DESCRIPTION
     "Enable the sending of device level collsion alarms."

::= { devColls  1 }




devCollsThreshold  OBJECT-TYPE

SYNTAX  INTEGER 
ACCESS  read-write
STATUS  mandatory
DESCRIPTION
     "This object  represents the  number of  collisions  per
     good packet  measured by  the device that will generate
     an alarm. valid values are 1 to 15"

::= { devColls 2  }
                                                 
--  devErrorS Object Defintions
-- 
--      This section  defines  the  objects  that  control  the
-- device level error alarm.




devErrorEnable  OBJECT-TYPE

SYNTAX  INTEGER
     {
          disable(1),
          enable(2)
     }

ACCESS  read-write
STATUS  mandatory
DESCRIPTION
     "Enable the sending of device level error alarms."

::= { devError  1 }




devErrorThreshold  OBJECT-TYPE

SYNTAX  INTEGER
ACCESS  read-write
STATUS  mandatory
DESCRIPTION
     "This object  represents the  percentage of  errors  per
     good packet that will generate an alarm."

::= { devError 2  }




devErrorSource  OBJECT-TYPE

SYNTAX     INTEGER
     
--      The INTEGER is a bit encoded version of which errors to
-- include in the error sum. The bits are encoded as follows:
--           CRC_errors   - Bit 0 - Least Significant Bit
--           runts        - Bit 1
--           OOW_colls    - Bit 2
--           align_errs   - Bit 3
--           No_resource  - Bit 4
--           Giants       - Bit 5
          

ACCESS  read-write
STATUS  mandatory
DESCRIPTION
     "The type of error used for the error alarm."

::= { devError 3 }


-- bdAlrm object defintions
-- 
--      This section  defines the  objects  that  will  control
-- alarms associated with the board.
-- 
-- bdAlrm Instance Identifiers
-- 
-- 
--      There is  set of  board level alarms per board thus the
-- instance identifiers for bdAlrm objects is teh board number.
-- 
--  Formal defintions below bdAlrm

     bdTraffic      OBJECT IDENTIFIER   ::= { bdAlrm 1 }

     bdColls        OBJECT IDENTIFIER   ::= { bdAlrm 2 }

     bdError        OBJECT IDENTIFIER   ::= { bdAlrm 3 }


-- bdTraffic Object Definitions
-- 
-- 
--      This  section   define  the  bdTraffic  objects.  These
-- objects control the board level traffic alarm generation.




bdTrafficEnable OBJECT-TYPE

SYNTAX  INTEGER
     {
          disable(1),
          enable(2)
     }

ACCESS  read-write
STATUS  mandatory
DESCRIPTION
     "Enable the  sending of  board level  traffic traps  for
     this board."
::= { bdTraffic 1 }




bdTrafficThreshold  OBJECT-TYPE

SYNTAX  Counter
ACCESS  read-write
STATUS  mandatory
DESCRIPTION
     "The threshold of packets within the Devicetimebase that
     will cause a traffic alarm."

::= { bdTraffic 2 }

-- bdColls Object Defintions
-- 
--      This section defines the objects that control the board
-- level collision alarm.




bdCollsEnable  OBJECT-TYPE

SYNTAX  INTEGER
     {         disable(1),	
          enable(2)
     }

ACCESS  read-write
STATUS  mandatory
DESCRIPTION
     "Enable the sending of board level collsion alarms."

::= { bdColls  1 }




bdCollsThreshold  OBJECT-TYPE

SYNTAX INTEGER
ACCESS read-write
STATUS  mandatory
DESCRIPTION
     "This object  represents the  number of  collisions  per
     good packet measured by the board that will generate an
     alarm. valid values are 1 to 15"

::= { bdColls 2  }

-- bdErrorS Object Defintions
-- 
--      This section defines the objects that control the board
-- level error alarm.




bdErrorEnable  OBJECT-TYPE

SYNTAX  INTEGER
     {
          disable(1),
          enable(2)
     }

ACCESS  read-write
STATUS  mandatory
DESCRIPTION 
	"Enable the sending of board level error alarms."

::= { bdError  1 }




bdErrorThreshold  OBJECT-TYPE

SYNTAX  INTEGER
ACCESS  read-write
STATUS  mandatory
DESCRIPTION
     "This object  represents the  percentage of  errors  per
     good packet that will generate an alarm."

::= { bdError 2  }




bdErrorSource  OBJECT-TYPE

SYNTAX  INTEGER
    
--      The INTEGER is a bit encoded version of which errors to
-- include in the error sum. The bits are encoded as follows:
-- 
--           CRC_errors   - Bit 0 - Least Significant Bit
--           runts        - Bit 1
--           OOW_colls    - Bit 2
--           align_errs   - Bit 3
--           No_resource  - Bit 4
-- 	  Giants       - Bit 5
 
ACCESS  read-write
STATUS  mandatory
DESCRIPTION
     "The type of error used for the error alarm."

::= { bdError 3 }


-- portAlrm object defintions
-- 
--      This section  defines the  objects  that  will  control
-- alarms associated with the port.
-- 
-- portAlrm Instance Identifiers
-- 
--      There is  set of  port level  alarms per board thus the
-- instance identifiers  for  portAlrm  objects  is  teh  board
-- number.
-- 
--  Formal defintions below portAlrm
-- 
     portTraffic    OBJECT IDENTIFIER   ::= { portAlrm 1 }

     portColls      OBJECT IDENTIFIER   ::= { portAlrm 2 }

     portError      OBJECT IDENTIFIER   ::= { portAlrm 3 }


-- portTraffic Object Definitions
-- 
--      This section  define  the  portTraffic  objects.  These
-- objects control the port level traffic alarm generation.
-- 




portTrafficEnable OBJECT-TYPE

SYNTAX  INTEGER
     {
          disable(1),
          enable(2)
     }

ACCESS  read-write
STATUS  mandatory
DESCRIPTION
     "Enable the sending of port level traffic traps for this
     port."

::= { portTraffic 1 }




portTrafficThreshold  OBJECT-TYPE

SYNTAX  Counter
ACCESS  read-write
STATUS  mandatory
DESCRIPTION
     "The threshold of packets within the Devicetimebase that
     will cause a traffic alarm."

::= { portTraffic 2 }

-- portColls Object Defintions
-- 
--      This section  defines the objects that control the port
-- level collision alarm.
-- 




portCollsEnable  OBJECT-TYPE

SYNTAX  INTEGER
     {
          disable(1),
          enable(2)
     }

ACCESS  read-write
STATUS  mandatory
DESCRIPTION
     "Enable the sending of port level collsion alarms."

::= { portColls  1 }




portCollsThreshold  OBJECT-TYPE

SYNTAX	 INTEGER
ACCESS  read-write
STATUS  mandatory
DESCRIPTION
     "This object  represents the  number of  collisions  per
     good packet  measured by the port that will generate an
     alarm."

::= { portColls 2  }

-- portErrorS Object Defintions
-- 
--      This section  defines the objects that control the port
-- level error alarm.




portErrorEnable  OBJECT-TYPE

SYNTAX  INTEGER
     {
          disable(1),	
          enable(2)
     }

ACCESS  read-write
STATUS  mandatory
DESCRIPTION
     "Enable the sending of port level error alarms."

::= { portError  1 }




portErrorThreshold  OBJECT-TYPE

SYNTAX  INTEGER

ACCESS  read-write
STATUS  mandatory
DESCRIPTION
     "This object  represents the  percentage of  errors  per
     good packet that will generate an alarm."

::= { portError 2  }




portErrorSource  OBJECT-TYPE

SYNTAX  INTEGER


--      The INTEGER is a bit encoded version of which errors to
-- include in the error sum. The bits are encoded as follows:
--           CRC_errors   - Bit 0 - Least Significant Bit
--           runts        - Bit 1
--           OOW_colls    - Bit 2
--           align_errs   - Bit 3
--           No_resource  - Bit 4
-- 	  Giants       - Bit 5

ACCESS  read-write
STATUS  mandatory
DESCRIPTION
     "The type of error used for the error alarm."


::= { portError 3 }

-- RepeaterRev2 Formal declarations


rr2device   OBJECT IDENTIFIER ::= { repeaterRev2 1 }

network     OBJECT IDENTIFIER ::= { repeaterRev2 2 }

rr2board    OBJECT IDENTIFIER ::= { repeaterRev2 3 }

rr2port        OBJECT IDENTIFIER ::= { repeaterRev2 4 }

repeaterTables OBJECT IDENTIFIER   ::= { repeaterRev2 5 }

commonD  OBJECT IDENTIFIER ::= { rr2device 1 }

ethernetD OBJECT IDENTIFIER ::= { rr2device 2 }

tokenRingD OBJECT IDENTIFIER ::= { rr2device 3 }

deviceTRTokenRingPortsOn OBJECT-TYPE

SYNTAX INTEGER
ACCESS read-only
STATUS mandatory
DESCRIPTION
	"The number of Token Ring Ports (i.e. station, Ring In and 
Ring Out ports) enabled on this device."

::= { tokenRingD 1 }

deviceTRTotalTokenRingPorts OBJECT-TYPE

SYNTAX INTEGER
ACCESS read-only
STATUS mandatory
DESCRIPTION
	"The total number of Token Ring Ports (i.e. station, Ring In and
Ring Out ports) on this device."


::= { tokenRingD 2 }

deviceTRTotalTokenRingRingPortsOn	OBJECT-TYPE

SYNTAX INTEGER
ACCESS read-only
STATUS mandatory
DESCRIPTION
	"The total number of Ring In and Ring Out ports (active) enabled on 
this device."

::= { tokenRingD 3 }

deviceTRTotalTokenRingRingPorts	OBJECT-TYPE

SYNTAX INTEGER
ACCESS read-only
STATUS mandatory
DESCRIPTION
	"The total number of Ring In and Ring Out ports on this
device."

::= { tokenRingD 4 }			   

deviceTRTotalTokenRingRings	OBJECT-TYPE

SYNTAX INTEGER
ACCESS read-only
STATUS mandatory
DESCRIPTION
	"The total number of (Token Ring) rings formed on this device."

::= { tokenRingD 5 }



-- board Object Definitions
-- 
--      This  section  will  describe  the  management  objects
-- associated with a board. The board variables have been broken down into 
-- Network type independent and Network Type Dependent variables.
-- 
-- Formal Definitions within board

commonB    OBJECT IDENTIFIER ::= { rr2board 1 }

ethernetB  OBJECT IDENTIFIER ::= { rr2board 2 }

tokenRingB OBJECT IDENTIFIER ::= { rr2board 3 }

fddiB      OBJECT IDENTIFIER ::= { rr2board 4 }

-- 
-- Instance Identifiers for board s
-- 
--      The Instance  Identifiers  for  board  objects  is  the
-- number of the slot in the MMAC cage. The current valid range
-- is from  1-8. The  IRM being  in slot  1.  B  indicates  the
-- instance of a board number.
-- 
-- 
-- common board Objects





boardIndex    OBJECT-TYPE

SYNTAX  INTEGER
ACCESS  read-only
STATUS  mandatory
DESCRIPTION
     "The slot number of this board."

::= { commonB 1 }


boardName   OBJECT-TYPE

SYNTAX  OCTET STRING
ACCESS  read-write
STATUS  mandatory
DESCRIPTION
     "The name  of the  board. This  field will  only contain
     printable ASCII characters."
				
::= { commonB 2 }





boardType    OBJECT-TYPE

SYNTAX  INTEGER
ACCESS  read-only
STATUS  mandatory
DESCRIPTION
"The type of the MIM. (eg. FOT, TPT, etc). See appendix A for
encoding."

::= { commonB 3 }




boardTotalPorts    OBJECT-TYPE

SYNTAX  INTEGER
ACCESS  read-only     
STATUS  mandatory
DESCRIPTION
     "Total number of ports supported on this board."

::= { commonB 4 }





boardSTATUS    OBJECT-TYPE

SYNTAX  INTEGER
     {
          disabled(1),
          enabled(2)
     }

ACCESS  read-write
STATUS  optional
DESCRIPTION
     "The administrative status of this MIM."

::= { commonB  5 }
     



boardPortsOn   OBJECT-TYPE

SYNTAX  INTEGER
ACCESS  read-only
STATUS  mandatory
DESCRIPTION
     "The number of operating ports on the board."
::= { commonB 6 }


-- Ethernet board Objects

boardTotalPkts   OBJECT-TYPE

SYNTAX  Counter
ACCESS  read-only
STATUS  mandatory
DESCRIPTION
     "The total  number of  packets this board has seen since
     the last reset."
::= { ethernetB 1 }

boardErrorPkts   OBJECT-TYPE

SYNTAX  Counter
ACCESS  read-only    
STATUS  mandatory
DESCRIPTION
     "The number  of packets  that have experienced an error.
     VAlid only on the IRBM, IRM2, and MiniMMAC."
::= { ethernetB 2 }




boardTransColl   OBJECT-TYPE

SYNTAX  Counter
ACCESS  read-only
STATUS  optional
DESCRIPTION
     "The  number  of  transmit  collisions  this  board  has
     detected."

::= { ethernetB 3 }




boardRecColl   OBJECT-TYPE

SYNTAX  Counter
ACCESS  read-only
STATUS  optional
DESCRIPTION
     "The number  of Receive  mode collisions  this board has
     detected."

::= { ethernetB 4 }




boardAlign   OBJECT-TYPE

SYNTAX  Counter
ACCESS  read-only
STATUS  optional
DESCRIPTION 
	 "The number of mis-aligned frames this board has
detected. Only valid for the IRBM, IRM2, and MiniMMAC."

::= { ethernetB 5 }





boardCRC   OBJECT-TYPE

SYNTAX  Counter
ACCESS  read-only
STATUS  optional
DESCRIPTION
     "The number of packets with bad CRC detected. Only valid
     on IRBM, IRM2, and MiniMMAC."

::= { ethernetB 6 }




boardRunt   OBJECT-TYPE

SYNTAX  Counter
ACCESS  read-only
STATUS  optional
DESCRIPTION
     "The number of runt frames detected by this board. Valid
     fr the IRBM, IRM2, and MiniMMAC only."
		       
::= { ethernetB 7 }





boardOOWColl  OBJECT-TYPE

SYNTAX  Counter
ACCESS  read-only
STATUS  optional
DESCRIPTION
     "The number of out-of-window collisions detected by this
     board. Only valid on the IRBM, IRM2, and MiniMMAC."

::= { ethernetB 8 }




boardNoResources  OBJECT-TYPE

SYNTAX  Counter
ACCESS  read-only
STATUS  optional
DESCRIPTION
     "The number  of times  The no  resources  condition  was
     detected for this board."

::= { ethernetB 9 }




boardRecBytes   OBJECT-TYPE

SYNTAX  Counter
ACCESS  read-only
STATUS  optional
DESCRIPTION
     "The number of bytes detected on the network. Valid only
     on the IRBM, IRM2, and MiniMMAC."

::= { ethernetB 10 }




boardGiants   OBJECT-TYPE

SYNTAX  Counter
ACCESS  read-only
STATUS  mandatory
DESCRIPTION
"The number  of packets  longer than  1518 bytes  detected on
this board."
	    
::= { ethernetB 11 }


-- Token Ring board Objects




boardTotalRingPorts                OBJECT-TYPE


SYNTAX	 INTEGER
ACCESS   read-only
STATUS	 mandatory
DESCRIPTION
      "The total number of ring ports on this board.  Currently, zero or
two."

::= { tokenRingB 1 }



boardTotalStationPorts             OBJECT-TYPE


SYNTAX	 INTEGER
ACCESS   read-only
STATUS	 mandatory
DESCRIPTION
      "The total number of station ports on this board."

::= { tokenRingB 2 }



boardModeStatus                    OBJECT-TYPE

SYNTAX  INTEGER
ACCESS  read-write
STATUS	 mandatory
DESCRIPTION
    "The board is configured for 2 == Auto Mode or 1 == Management Mode"

::= { tokenRingB 3 }




boardTotalRingPortsOn              OBJECT-TYPE


SYNTAX  INTEGER
ACCESS   read-only
STATUS	 mandatory
DESCRIPTION
     "The number of enabled ring ports on this board."

::= { tokenRingB 4 }

boardTotalStationPortsOn           OBJECT-TYPE


SYNTAX  INTEGER
ACCESS   read-only
STATUS	 mandatory
DESCRIPTION                                                            
     "The number of enabled station ports on this board."

::= { tokenRingB 5 }

boardSpeed                    OBJECT-TYPE

SYNTAX  INTEGER
ACCESS  read-write
STATUS	 mandatory
DESCRIPTION
     " Speed 4 == 4 Mhz
     Speed 16 == 16 Mhz"
::= { tokenRingB 6 }

boardRingSpeedFault          OBJECT-TYPE

SYNTAX  INTEGER {
                 noFaultDetected (1),
                 faultDetected (2)
             }
ACCESS   read-only
STATUS	 mandatory
DESCRIPTION
     "Data speed of station mismatches configuration speed of board.
board is automatically bypassed."

::= { tokenRingB 7 }





-- Port Object Definitions
-- 
--      This section  will define  the objects  associated with
-- ports. Here again the objects are deperateed into common objects and
-- network type specific objects.
-- 
-- Formal Definitions within Port

commonP    OBJECT IDENTIFIER ::= { rr2port 1 }

ethernetP  OBJECT IDENTIFIER ::= { rr2port 2 }

tokenRingP OBJECT IDENTIFIER ::= { rr2port 3 }

fddiP      OBJECT IDENTIFIER ::= { rr2port 4 }

-- 
-- 
--  Instance Identifiers for port s
-- 
--      The instance  identifiers for  port objects  are board#
-- and port#.  The format of the port identifier is thus:Board_num.Port_num or B.P

portIndex    OBJECT-TYPE

SYNTAX  INTEGER
ACCESS  read-only
STATUS  mandatory
DESCRIPTION
     "The slot number of this port."

::= { commonP 1 }

portMediaType    OBJECT-TYPE

SYNTAX  INTEGER
ACCESS  read-only
STATUS  mandatory
DESCRIPTION
     "The type  of the port. (eg. FOT, TPT, etc). See appendix
     A for values."

::= { commonP 2 }

portAdminState OBJECT-TYPE

SYNTAX  INTEGER
     {
          off(1),
          on( 2)
     }

ACCESS  read-write
STATUS  mandatory
DESCRIPTION
     "The administrative status of this port."

::= { commonP  3 }




portSourceAddr     OBJECT-TYPE

SYNTAX  OCTET STRING
ACCESS  read-only
STATUS  mandatory
DESCRIPTION
     "A source address that has been seen on this port."

::= { commonP 4 }


-- Ethernet port Objects




portTopologyType    OBJECT-TYPE

SYNTAX  INTEGER
ACCESS  read-only
STATUS  mandatory
DESCRIPTION
     "The topological type of the port.
     {
 	Station(1)
	Link(2)

     }"

::= { ethernetP 1 }





portLinkStatus    OBJECT-TYPE
SYNTAX  INTEGER
     {
          linkSignalInactive(1),
          linkSignalActive(2),
          linkSignalNotSupported(3)
     }

ACCESS  read-only
STATUS  mandatory
DESCRIPTION
     "The state of the link signal for this port"

::= { ethernetP  2 }




portStatus    OBJECT-TYPE
SYNTAX  INTEGER
     {
          active(1),
          segmented(2)
     }

ACCESS  read-only
STATUS  mandatory
	DESCRIPTION ""
::= { ethernetP  3 }

portTotalPkts   OBJECT-TYPE

SYNTAX  INTEGER
ACCESS  read-only
STATUS  mandatory
DESCRIPTION
     "The total  number of  packets this  port has seen since
     the last reset."
::= { ethernetP 4 }




portErrorPkts   OBJECT-TYPE

SYNTAX  Counter
ACCESS  read-only    
STATUS  mandatory
DESCRIPTION
     "The number  of packets  that have experienced an error.
     Valid only on the IRBM, IRM2, and MiniMMAC"

::= { ethernetP 5 }




portXmitColls   OBJECT-TYPE

SYNTAX  Counter
ACCESS  read-only
STATUS  optional
DESCRIPTION
     "The number  of Transmit  mode collisions  this port has
     detected. Only valid on IRBM, IRM2, and MiniMMAC."

::= { ethernetP 6 }




portRecColls   OBJECT-TYPE

SYNTAX  Counter
ACCESS  read-only
STATUS  optional
DESCRIPTION
     "The number  of Receive  mode collisions  this port  has
     detected. Only valid on IRBM, IRM2, and MiniMMAC."

::= { ethernetP 7 }




portAlign   OBJECT-TYPE

SYNTAX  Counter
ACCESS  read-only
STATUS  optional
DESCRIPTION
     "The  number   of  mis-aligned   frames  this  port  has
     detected. Only valid for the IRBM, IRM2, and MiniMMAC."

::= { ethernetP 8 }





portCRC   OBJECT-TYPE

SYNTAX  Counter
ACCESS  read-only
STATUS  optional
DESCRIPTION
     "The number of packets with bad CRC detected. Only valid
     on IRBM, IRM2, and MiniMMAC."

::= { ethernetP 9 }




portRunt   OBJECT-TYPE

SYNTAX  Counter
ACCESS  read-only
STATUS  optional
DESCRIPTION
     "The number  of runt frames detected by this port. Valid
     for the IRBM, IRM2, and MiniMMAC only."

::= { ethernetP 10 }




portOOWColl  OBJECT-TYPE

SYNTAX  Counter
ACCESS  read-only
STATUS  optional
DESCRIPTION
     "The number of out-of-window collisions detected by this
     port. Only valid on the IRBM, IRM2, and MiniMMAC."

::= { ethernetP 11 }




portNoResorces  OBJECT-TYPE

SYNTAX	 Counter
ACCESS  read-only
STATUS  optional
DESCRIPTION
     "The number  of  times  the  no  resource  condition  is
     detected on this port."

::= { ethernetP 12 }




portRecBytes   OBJECT-TYPE

SYNTAX  Counter
ACCESS  read-only
STATUS  optional
DESCRIPTION
     "The number of bytes detected on the network. Valid only
     on the IRBM, IRM2, and MiniMMAC."

::= { ethernetP 13 }




portGiants   OBJECT-TYPE

SYNTAX  Counter
ACCESS  read-only
STATUS  optional
DESCRIPTION
	"The number of frames longer than 1518 bytes detected on this
port."
      
::= { ethernetP 14 }





portRedundCrt   OBJECT-TYPE

SYNTAX  INTEGER
ACCESS  read-write
STATUS  mandatory
DESCRIPTION
     "The  redundant   circuit  with   which  this   port  is
     associated."

::= { ethernetP 15 }




portRedundType   OBJECT-TYPE

SYNTAX  INTEGER
    {
          notUsed(1),     
          primary(3),
          backup(4)
     }

ACCESS  read-write
STATUS  mandatory
DESCRIPTION
     "The type of port this port is in the redundant circuit."

::= { ethernetP 16 }




portRedundStatus   OBJECT-TYPE

SYNTAX  INTEGER
     {
          notUsed(1),     
          active(2),
          inactive(3)
     }

ACCESS  read-write
STATUS  mandatory
DESCRIPTION
     "The current  state of  this port  is in  the  redundant
     circuit."

::= { ethernetP 17 }




portForceLinkType    OBJECT-TYPE

SYNTAX	 INTEGER
	{
	   notForced(1),
	   forced(2)
	}

ACCESS  read-write
STATUS  mandatory
DESCRIPTION
	"This variable forces a port to be a link port."

::= { ethernetP 18 }


-- Token Ring Port Objects
-- 
-- Token Ring Port Objects are further broken down into station objects 
-- and Ring-In/Ring-Out objects. The formal defintions is:

stationP            OBJECT IDENTIFIER ::= { tokenRingP 1 }

ringP               OBJECT IDENTIFIER ::= { tokenRingP 2 }

stationPortLinkStatus OBJECT-TYPE
SYNTAX	 INTEGER {
               linkSignalInactive(1),	
               linkSignalActive(2)
             }
ACCESS   read-only
STATUS	 mandatory
DESCRIPTION
     "When station is supplying phantom current the Link Signal is
active.  When there is no phantom current the Link Signal is inactive."

::= { stationP 1 }

stationPortLinkStateTime           OBJECT-TYPE

SYNTAX  INTEGER
ACCESS  read-write
STATUS	 mandatory
DESCRIPTION
     "The amount of time (in seconds) elapsed since the station port
last changed state."

::= { stationP 2 }


-- This section will define the objects associated with Ring In and Ring
-- Out ports, e.g. TRMIM-10R.




ringPortLinkStatus                 OBJECT-TYPE

SYNTAX  INTEGER {
                off(1),
                on(2)
             }
ACCESS   read-only
STATUS	 mandatory
DESCRIPTION
     "Off (wrapped).
     On (active)."

::= { ringP 1 }



ringPortLinkStateTime              OBJECT-TYPE


SYNTAX  INTEGER
ACCESS  read-write
STATUS	 mandatory                                                         
DESCRIPTION
     "The amount of time (in seconds) elapsed since ring port last
changed state."

::= { ringP 2 }


-- Product specific Objects
-- 
--      For each  of the individual repeaters/bridges there are
-- several objects  that particular to that product. below is a
-- description of these objects. 
-- 
-- Formal description of Product specfics

     productRev1    OBJECT IDENTIFIER  ::= { product 1 }

     iRBM           OBJECT IDENTIFIER  ::= { productRev1 1 }


-- iRBM specific Objects

-- These objects are particular to the iRBM.


iRBMRevision OBJECT-TYPE

SYNTAX  INTEGER
     {
          rev0(0),
          rev1(1),
          rev2(2),
          rev3(3)
     }

ACCESS  read-write
STATUS  mandatory
DESCRIPTION
     "The revision of the IRBM board"

::= { iRBM 1 }




iRBMPortAssociation OBJECT-TYPE

SYNTAX  INTEGER
ACCESS  read-write
STATUS  mandatory
DESCRIPTION
     "Controls how  front panel ports are associated with the
bridge or the repeater. The valid values are:

Value     AUI Port            Fiber Port

  0       Bridge              Redundant
  1       Redundant           Bridge
  2       Bridge              Repeater
  3       Repeater            Bridge
  4       Redundant           Repeater
  5       Repeater            Redundant

Note: only  values 0  and 1  are valid  for rev 2 boards and
before."

::= { iRBM 2 }

-- Subsystem defined objects

mMAC                OBJECT IDENTIFIER ::= { subsystem 1 }

-- MMAC Objects


fnb                 OBJECT IDENTIFIER ::= { mMAC 1 }


fnbConnectedLeft 		OBJECT-TYPE

SYNTAX  INTEGER
ACCESS  read-write
STATUS	 mandatory
DESCRIPTION
"The Connected Left board (board n + 1) has the following states:

     Detached == 1  (Management (only management) detached,
                    read/write).
     Attached == 2  (Management/AutoMode  attached,
                    read/write).
     Faulted == 3  (Management/AutoMode tried to attach
                    but failed read ONLY)."

::= { fnb 1 }


fnbConnectedRight                     OBJECT-TYPE

SYNTAX  INTEGER
ACCESS  read-write
STATUS  mandatory
DESCRIPTION
"The Connected Right board (board n - 1) has the following states:


     Detached == 1  (Management (only management) detached,
                    read/write).
     Attached == 2  (Management/AutoMode attached,
                    read/write ).
     Faulted == 3  (Management/AutoMode tried to attach
                    but failed read ONLY)."

::= { fnb 2 }

fnbBoardBypassState                   OBJECT-TYPE


SYNTAX	 INTEGER
ACCESS  read-write
STATUS	 mandatory
DESCRIPTION
     "Off == 1  (NOT bypassed).
     On == 2  (bypassed)."

::= { fnb 3 }



-- TrapTypes 
-- 
--      This section  will describe  the trap  types  that  the
-- repeater section  of the  IRBM can  generate. These  are not
-- objects, but  Object identifers used to indicate the specfic
-- trap. They  are taken  from the  object space  and are  thus
-- documented here.
-- 
--      The   SNMP    protocol   provides   a   mechanism   for
-- asynchronusly notifying  management stations  of significant
-- changes in  the network.  This mechanism  is the  SNMP  trap
-- message. This  document will describe the general format for
-- all trap  messages that  Cabletron products will generate as
-- well as the specific traps that the will be generated by the
-- IRBM.
-- 
--  Trap Formats
-- 
--      The  SNMP  trap  messages  are  composed  of  two  user
-- definable areas: the specific trap type and the VarBindings
-- (eg. the interesting information). The specific trap type is
-- an INTEGER  that is used to determine the specific trap that
-- has occurred. The "interesting information" contains a group
-- of objects  identifiers (OID)  and their values that provide
-- information about the trap.
-- 
-- 
-- Trap Description
-- 
-- PortSegmenting 
-- 
-- Specfic Trap Type Code - 0x101
-- 
--      When a  port goes from operational to segmented, a trap
-- will be  generated. For  these purposes, the port state will
-- be sampled  every XXX seconds, thus it will be statistically
-- possible to miss oscillating circuits.
-- 
--      The interesting information will include:
--           - Board number
--           - Port number
-- 
-- Trap Description
-- 
--  PortUnsegementing 
-- Specfic Trap Type Code - 0x102
-- 
--      When it  is detected  that a  previously segmented port
-- has gone  operational, a  trap will  be generated.   This is
-- also sampled,  thus a  trap may  not be  generated for  each
-- transition.
-- 
--      The interesting information will include:
--           - Board number
--           - Port number
-- 
-- 
-- 
-- Trap Description
-- 
--  PortLinkUp 
-- 
-- Specfic Trap Type Code - 0x103
-- 
--      This trap  will be generated when it is determined that
-- MAU has  been attached to the MMAC. This is only appropriate
-- for MIMs that support the concept of a link state.
-- 
--      The interesting information will include:
--           - Board number
--           - Port number
-- 
-- Trap Description
-- 
--  PortLinkDown 
-- 
-- Specfic Trap Type Code - 0x104
-- 
--      This trap  will be generated when a previously attached
-- MAU  is  removed  or  powered  down.  Again,  this  is  only
-- appropriate for MIM's that support link state.
-- 
--      The interesting information will include:
--           - Board number
--           - Port number
-- 
-- Trap Description
--  NewSourceAddress 
-- Specfic Trap Type Code - 0x105
-- 
--      This trap  will be  generated when the MMAC detects the
-- existence of a new source address on one of it's ports.
-- 
--      The interesting information will include:
-- 
--           - Board number
--           - Port number
--           - The new source address
-- 
-- Trap Description
--  SourceAddressTimeout 
-- 
-- Specfic Trap Type Code - 0x106
-- 
--      This trap  will indicate that the MMAC has not detected
-- a packet  generated by  this source address within a certain
-- timeout.
-- 
-- 
-- 
--      The interesting information will include:
-- 
--           - Board number
--           - Port number
--           - Source address that timed out.
-- 
-- Trap Description
-- 
--  BoardRemoval 
-- 
-- Specfic Trap Type Code - 0x107
-- 
--      This trap  will be generated when the MMAC detects that
-- MIM has been removed.
-- 
--      The interesting information will include:
-- 
--           - Board number
--           
-- Trap Description
--  BoardInsertion 
-- 
-- Specfic Trap Type Code - 0x108
-- 
-- 
--      This trap  will be  generated when  the MMAC determines
-- that a new board has been inserted.
-- 
--      The interesting information will include:
-- 
--           - Board number
--           - Board type
-- 
-- Trap Description
--  ActivePortInRedundantCircuitFailed 
-- 
-- Specfic Trap Type Code - 0x109
-- 
--      This trap  will be  generated when the active port in a
-- redundant circuit has failed polling. This will indicate the
-- activation of redundancy.
-- 
--      The interesting information will include:
-- 
--           - Board number
--           - Port number
--           - Circuit number
-- 
-- Trap Description
--  RedundantPortActivated 
-- 
-- Specfic Trap Type Code - 0x10a
-- 
-- 
-- 
--      This trap  indicates that a new port has been activated
-- in a  redundant circuit.  This does  NOT indicate  that this
-- port is  usable, but  is being tested. If the port fails the
-- above (3.9) trap will be generated.
-- 
--      The interesting information will include:
-- 
--           - Board number
--           - Port number
--           - Circuit number
-- 
-- Trap Description
--  RedundantPortTestFailed 
-- 
-- Specfic Trap Type Code - 0x10b
-- 
-- 
-- 
--      This trap will be generated when the MMAC executes it's
-- periodic redundancy diagnostics and finds on of the ports in
-- a redundant  circuit  has  failed.  This  message  will  not
-- indicate that  redundancy has  been activated, just that the
-- port has failed and should be fixed before it is needed.
-- 
--      The interesting information will include:
-- 
--           - Board number
--           - Port number
--           - Circuit number
-- 
-- Trap Description
--  deviceTrafficThresholdExceeded 
-- 
-- Specfic Trap Type Code - 0x10c
-- 
--      This trap  will be  generated when  the  traffic  (good
-- packets per  time interval)  has been  exceed for the entire
-- MMAC.
-- 
--      The interesting information will include:
-- 
--           - threshold value
--           - timebase value
-- 
-- Trap Description
--  deviceErrorThresholdExceeded 
-- 
-- Specfic Trap Type Code - 0x10d
-- 
--      This  trap  will  be  generated  when  packets  of  the
-- selected error  type exceeds  a threshold  percentage of the
-- good packets for a particular interval for the entire MMAC.
-- 
--      The interesting information will include:
-- 
--           - threshold value
-- 
-- 
--           - selected error type
--           - timebase
-- 
-- Trap Description
--  deviceCollsionThresholdExceeded 
-- 
-- Specfic Trap Type Code - 0x10e
-- 
--      This trap  will be  generated when  collsions exceed  a
-- threshold percentage  of the  good packets  for a particular
-- interval for the entire MMAC.
-- 
--      The interesting information will include:
-- 
--           - threshold value
--           - timebase
-- 
-- Trap Description
--  BoardTrafficThresholdExceeded 
-- 
-- Specfic Trap Type Code - 0x10f
-- 
--      This trap  will be  generated when  the  traffic  (good
-- packets per  time interval) has been exceed for a particular
-- MIM.
-- 
--      The interesting information will include:
-- 
--           - threshold value
--           - timebase value
--           - board number
-- 
-- Trap Description
--  BoardErrorThresholdExceeded 
-- 
-- Specfic Trap Type Code - 0x110
-- 
--      This  trap  will  be  generated  when  packets  of  the
-- selected error  type exceeds  a threshold  percentage of the
-- good packets for a particular interval for a particular MIM.
-- This will most likely indicate a bad MIM.
-- 
--      The interesting information will include:
--           - threshold value
--           - selected error type
--           - timebase
--           - Board number
-- 
-- Trap Description
--  BoardCollisionThresholdExceeded 
-- 
-- 
-- 
-- Specfic Trap Type Code - 0x111
-- 
-- 
--      This trap  will be  generated when  collisions exceed a
-- threshold percentage  of the  good packets  for a particular
-- interval for a particular MIM.
-- 
--      The interesting information will include:
-- 
--           - threshold value
--           - timebase
--           - Board number
-- 
-- Trap Description
--  PortTrafficThresholdExceeded 
-- 
-- Specfic Trap Type Code - 0x112
-- 
-- 
--      This trap  will be  generated when  the  traffic  (good
-- packets per  time interval) has been exceed for a particular
-- port.
-- 
--      The interesting information will include:
-- 
--           - threshold value
--           - timebase value
--           - board number
--           - port number
-- 
-- Trap Description
--  PortErrorThresholdExceeded 
-- 
-- Specfic Trap Type Code - 0x1113
-- 
-- 
-- 
--      This  trap  will  be  generated  when  packets  of  the
-- selected error  type exceeds  a threshold  percentage of the
-- good packets  for a  particular interval  for  a  particular
-- port.
-- 
--      The interesting information will include:
-- 
--           - threshold value
--           - selected error type
--           - timebase
--           - board number
--           - port number
-- 
-- 
-- Trap Description
--  PortCollisionThresholdExceeded 
-- 
-- Specfic Trap Type Code - 0x114
-- 
--      This trap  will be  generated when  collisions exceed a
-- threshold percentage  of the  good packets  for a particular
-- interval for a particular port.
-- 
--      The interesting information will include:
-- 
--           - threshold value
--           - timebase
--           - board number
--           - port number
-- 
-- Trap Description
--  PortTypeChanged
-- 
-- Specfic Trap Type Code - 0x115
-- 
-- 	This trap indicates that a port has changed from a 
-- station port to a link port or vice versa.
-- 
-- 	The interesting information is:
-- 
-- 	- Board number
-- 	- Port Number
-- 	- New type value
-- 
-- Trap Description
--  LockSTATUSChanged
-- 
-- Specfic Trap Type Code - 0x116
-- 
-- 	This trap is generated when the status of the address lock 
-- changes.
-- 
-- 	The interesting information is:
-- 
-- 	- New lock status
-- 
-- 
-- Trap Description
--  PortSecurityViolation
-- 
-- Specfic Trap Type Code - 0x117
-- 
-- 	This trap is generated when a source address other than those
-- locked to a port is seen.
-- 
-- 	The interesting information is:
-- 
-- 	- Board number
-- 	- Port Number
-- 	- Violating Address
-- 
-- 
-- Trap Description
--  PortViolationReset
-- 
-- Specfic Trap Type Code - 0x118 
-- 
-- 	This trap is generated when management intervention has 
-- reset a port after a violation has occured.
-- 
-- 	The interesting information is:
-- 	
-- 	- Board Number
-- 	- Port Number
-- 
-- Trap Description
--  EnvTempWarm
-- 
-- Specfic Trap Type Code - 0x119
-- 
-- 	This trap is generated when the device detects that the temperature
-- within the device has reached a WARM condition.
-- 
-- 
-- 	The interesting information is:
-- 
-- 	None
-- 
-- Trap Description
--  EnvTempHot
-- 
-- Specfic Trap Type Code - 0x11A
-- 
-- 	This trap is generated when the device detects a temperature
-- that is classified as HOT.
-- 
-- 
-- 	The interesting information is:
-- 
-- 	None
-- 
-- Trap Description
--  EnvVoltageLow
-- 
-- Specfic Trap Type Code - 0x11B
-- 
-- 	This trap is generated when a board detects that it's power supply
-- voltage is LOW.
-- 
-- 
-- 	The interesting information is:
-- 
-- 	- Board
-- 

--             Appendix A - Media type values
-- 
-- Board Type          Value
-- 
-- MMAC Board & Port types
--  IRM                0x01
--  NB25,NB20          0x02
--  NB35               0x03
--  THIN_MIM           0x10,0x50
-- 
--  TRMIM_12           0x30
-- 
--  TRMIM_RPT          0x31
--  TRMIM_24           0x32
--  TRMIM_22           0x33
--  TRMIM_34           0x34
--      
--  TRMIM_32           0x35
--  TRFOT_28           0x36
--  TRFOT_26           0x37
--  TRFOT_22           0x38
--  TRFOT_18           0x39
--  TRFOT_12           0x3A
--  TRFOT_16           0x3B
-- 
--  TPMIM_T1           0x41
--  TPMIM_T            0x42
--  TPMIM_T3           0x43
-- 
--  TPMIM_24           0x60
--  TPMIM_22           0x61
--  TPMIM_34           0x62
--  TPMIM_32           0x63
-- 
--  FO_22              0x70      
--  FO_16              0x80      
--  FOIRL              0x90      
--  FOM_18             0x90      
-- 
--  FOM_12             0x92 
--  FOM_16             0x93 
--  FOM_28             0x94 
--  FOM_22             0x96 
--  FOM_26             0x97 
-- 
--  MT8MIM	       0xA0
--
--  IRM2               0xB0
--  IRBM               0xB1
--  TRMBM              0xB4
--  IRM/SNMP           0xB5
-- 
--  FOT_12             0xC0
-- 
--  TPT                0xD0
-- 
--  FOT_6              0xE0
--  NOMIM              0xFF
-- 
-- 
-- Device Codes
--  MiniMMAC	                0x10010
-- 
-- Multi-Port Interfaces Modules
--  MPIM-X		    	0x20000
--  MPIM-A		    	0x20001
--  MPIM-C	            	0x20002
--  MPIM-T			0x20003
--  MPIM-F2     		0x20004
--  MPIM-F1			0x20005
--  MPIM-T1			0x20006
--  MPIM-B			0x20007 - BLANK
-- 
-- 
-- Single-Port Interface Modules
-- 
--  SPIM-A		    	0x20001
--  SPIM-C	            	0x20002
--  SPIM-T			0x20003
--  SPIM-F2	 		0x20004
--  SPIM-F1			0x20005
--  SPIM-T1			0x20006
--  SPIM-B			0x20007 - BLANK
-- 
-- MRXI Interface modules
--
--  MRXI			0x30043 
--  MRXI-28		        0x300A0
--  MRXI-2			0x30042
--  

--                   Cabletron Management Information Base
--              For the Ethernet Bridge (IRBM, NB25E, and NB20E)
--                            By: Gayle Delaney
--                               Revision 0.7
--                         Date: February 21, 1991
--
--
-- REVISION HISTORY
--
-- Rev. 0.1 - Initial revision.
--            Compatible with versions 0.00.02 and 0.00.03 of the SNMP NB25E
--            bridge.
--
-- Rev. 0.2 - Revised and updated.
--            Added Bridgerev1 to object identifiers.
--
-- Rev. 0.3 - Revised and updated.
-- 	          Added PortRuntPackets, PortOversizePackets, and PortFrFilt.
-- 	          Changed syntax of all four AcqCreate objects and AcqDelete
--            object to INTEGER.
-- 	          Changed syntax of all four PermCreate object and PermDelete
--            object to INTEGER.
--
-- Rev. 0.4 - Revised and updated.
--            Added trap object identifiers.
--
-- Rev. 0.5 - Changed certain device and port objects to counter types.
--
-- Rev. 0.6 - Added AcqSrcAddress and PermSrcAddress.
--
-- Rev. 0.7 - Updated DeviceRestoreSettings and Traps.

bridgeRev1  OBJECT IDENTIFIER ::= { bridge 1 }
	
bdgdevice      OBJECT IDENTIFIER ::= { bridgeRev1 1 }

bdgPort        OBJECT IDENTIFIER ::= { bridgeRev1 2 }

filterDB    OBJECT IDENTIFIER ::= { bridgeRev1 3 }

trapTypes   OBJECT IDENTIFIER ::= { bridgeRev1 4 }

bdgTables   OBJECT IDENTIFIER ::= { bridgeRev1 5 }

acqDB       OBJECT IDENTIFIER ::= { filterDB 1 }

permDB      OBJECT IDENTIFIER ::= { filterDB 2 }

specialDB   OBJECT IDENTIFIER ::= { filterDB 3 }

acqStats    OBJECT IDENTIFIER ::= { acqDB 1 }

acqOptions  OBJECT IDENTIFIER ::= { acqDB 2 }

permStats   OBJECT IDENTIFIER ::= { permDB 1 }

permOptions OBJECT IDENTIFIER ::= { permDB 2 }

specStats   OBJECT IDENTIFIER ::= { specialDB 1 }

specFilters OBJECT IDENTIFIER ::= { specialDB 2 }


-- Device Object Definitions
--
--      This section defines the objects under the Device node.
--
-- Instance Identifiers for Device Objects
--
--      There is only one instance of a Device object, thus the Instance
--      Identifier is 0.
--
-- Device Objects


bdgdeviceDisableBdg OBJECT-TYPE	
SYNTAX INTEGER 
     {
          disableBridge (0),
          enableBridge  (1)
     }
ACCESS read-write
STATUS mandatory
DESCRIPTION
     "Indicates if the bridge will be disabled."
::= { bdgdevice 1 }


bdgdeviceRestoreSettings OBJECT-TYPE
SYNTAX INTEGER 
	{
		restoreSettings (0)
	}
ACCESS read-write
STATUS mandatory
DESCRIPTION
	"Restore the following settings to their default values:
		Bridge Name to ETHERNET_BRIDGE,
		Location to LOCAL,
		Port 1 Name to PORT_1,
		Port 2 Name to PORT_2,
		Port 1 Network Name to LAN_1,
		Port 2 Network Name to LAN_2,
		Ageing Time for Acquired Database to 300 seconds,
		Erase the acquired database,
		Erase the permanent database,
		Place sixteen default multicast addresses into
		the permanent and acquired databases,
		Type of Spanning Tree to 802.1,
		Type of Filtering to IEEE 802.1,
		Bridge Max Age to 20 seconds,
		Bridge Forward Delay to 15 seconds,
		Bridge Hello Time to 2 seconds,
		Bridge Priority to 8000,
		Port 1 Priority to 80,
		Port 2 Priority to 80,
		Port 1 Path Cost to 100,
		Port 2 Path Cost to 100,
		Restart the bridge."
::= { bdgdevice 2 }


bdgdeviceBdgName OBJECT-TYPE
SYNTAX OCTET STRING
ACCESS read-write
STATUS mandatory
DESCRIPTION
	"The user-defined name (up to 32 characters long) of the bridge.
	The default bridge name is ETHERNET_BRIDGE."
::=	{ bdgdevice 4 }


bdgdeviceNumPorts OBJECT-TYPE
SYNTAX INTEGER
ACCESS read-only
STATUS mandatory
DESCRIPTION
	"The number of ports present on the bridge."
::= { bdgdevice 5 }


bdgdeviceType OBJECT-TYPE
SYNTAX OCTET STRING
ACCESS read-only
STATUS mandatory
DESCRIPTION
	"The type of bridge, NB25E, IRBM, or NB20E."
::= { bdgdevice 6 }


bdgdeviceVersion OBJECT-TYPE
SYNTAX OCTET STRING
ACCESS read-only
STATUS mandatory
DESCRIPTION
	"The release version of the firmware installed in the bridge."
::= { bdgdevice 7 }


bdgdeviceLocation OBJECT-TYPE
SYNTAX OCTET STRING
ACCESS read-write
STATUS mandatory
DESCRIPTION
	"The user-defined name to indicate the location of the bridge on
	the network. The default location name is LOCAL."
::= { bdgdevice 8 }


bdgdeviceStatus OBJECT-TYPE
SYNTAX OCTET STRING
ACCESS read-only
STATUS mandatory
DESCRIPTION
	"The status of the bridge, ON-LINE, STAND BY or DISABLED."
::= { bdgdevice 9 }


bdgdeviceRestartBdg OBJECT-TYPE
SYNTAX INTEGER 
	{
		restartBridge (0)
	}
ACCESS read-write
STATUS mandatory
DESCRIPTION
	"Force the bridge to undergo a software reset."
::= { bdgdevice 10 }


bdgdeviceFrFwd OBJECT-TYPE
SYNTAX Counter
ACCESS read-only
STATUS mandatory
DESCRIPTION
	"The number of frames forwarded by the bridge."
::= { bdgdevice 11 }


bdgdeviceFrRx OBJECT-TYPE
SYNTAX Counter
ACCESS read-only
STATUS mandatory
DESCRIPTION
	"The number of frames received by the bridge."
::= { bdgdevice 12 }


bdgdeviceFrFlt OBJECT-TYPE
SYNTAX Counter
ACCESS read-only
STATUS mandatory
DESCRIPTION
	"The number of frames filtered by the bridge."
::= { bdgdevice 13 }


bdgdeviceErr OBJECT-TYPE
SYNTAX Counter
ACCESS read-only
STATUS mandatory
DESCRIPTION
	"The total number of network errors that have occurred."
::= { bdgdevice 14 }


bdgdeviceSwitchSetting OBJECT-TYPE
SYNTAX OCTET STRING
ACCESS read-only
STATUS mandatory
DESCRIPTION
	"Indicates the current switch settings read from the bridge
	hardware."
::= { bdgdevice 15 }


bdgdeviceNumRestarts OBJECT-TYPE
SYNTAX Counter
ACCESS read-only
STATUS mandatory
DESCRIPTION
	"The number of times the bridge has been powered up or restarted."
::= { bdgdevice 16 }


bdgdeviceTypeFiltering OBJECT-TYPE
SYNTAX INTEGER 
	{
		ieee8021 (0),
		specialDB (1),
		both      (2)
	}
ACCESS read-write
STATUS mandatory
DESCRIPTION
	"The type of filtering to be performed by the bridge. The default
	is IEEE 802.1."
::= { bdgdevice 17 }


bdgdeviceSTAProtocol OBJECT-TYPE
SYNTAX INTEGER 
	{
		ieee8021 (0),
		dec   (1),
		none  (2)
	}
ACCESS read-write
STATUS mandatory
DESCRIPTION
	"The spanning tree algorithm under which the bridge is operating.
	The selections are as follows:
		- IEEE 802.1 compliant spanning tree algorithm
		  environment (802.1)
		- DEC LAN Bridge 100 environment (DEC)
		- Without the spanning tree algorithm enabled (NONE)
	The default is 802.1."
::= { bdgdevice 18 }


bdgdeviceBridgeID OBJECT-TYPE
SYNTAX OCTET STRING
ACCESS read-only
STATUS mandatory
DESCRIPTION
	"The unique identifier of the bridge. The first two bytes of the
	identifier are the bridge priority and the last six bytes are the
	Ethernet address."
::= { bdgdevice 19 }


bdgdeviceTopChgCnt OBJECT-TYPE
SYNTAX Counter
ACCESS read-only
STATUS mandatory
DESCRIPTION
	"The number of times the bridge's Topology Change Flag has been
	changed since the bridge was powered up or initialized."
::= { bdgdevice 20 }


bdgdeviceRootCost OBJECT-TYPE
SYNTAX INTEGER
ACCESS read-only
STATUS mandatory
DESCRIPTION
	"The cost of the path to the root from this bridge."
::= { bdgdevice 21 }


bdgdeviceRootPort OBJECT-TYPE
SYNTAX INTEGER
ACCESS read-only
STATUS mandatory
DESCRIPTION
	"The port identifier for the port which offers the lowest cost
	path to the root, i.e. that port for which the sum of the values
	of the designated cost and path cost parameters held for the port
	is lowest."
::= { bdgdevice 22 }


bdgdeviceHelloTime OBJECT-TYPE
SYNTAX INTEGER
ACCESS read-only
STATUS mandatory
DESCRIPTION
	"The time interval between the transmission of Configuration
	BPDU's by a bridge which is attempting to become the root or is
	the root."
::= { bdgdevice 23 }


bdgdeviceBdgMaxAge OBJECT-TYPE
SYNTAX INTEGER
ACCESS read-write
STATUS mandatory
DESCRIPTION
	"The value of the Max Age parameter when the bridge is the root
	or is attempting to become the root. A time of 6 to 40 seconds is
	allowed. The default is 20 seconds."
::= { bdgdevice 24 }


bdgdeviceBdgFwdDly OBJECT-TYPE
SYNTAX INTEGER
ACCESS read-write
STATUS mandatory
DESCRIPTION
	"The value of the forward delay parameter when the bridge is the
	root or is attempting to become the root. A time of 4 to 30
	seconds is allowed."
::= { bdgdevice 25 }


bdgdeviceTimeTopChg OBJECT-TYPE
SYNTAX INTEGER
ACCESS read-only
STATUS mandatory
DESCRIPTION
	"The time in seconds that has elapsed since the bridge's Topology
	Change Flag last recorded the value of a topology change."
::= { bdgdevice 26 }


bdgdeviceTopChg OBJECT-TYPE
SYNTAX INTEGER 
{
	noTopologyChangeInProgress (0),
	topologyChangeInProgress   (1)
}
ACCESS read-only
STATUS mandatory
DESCRIPTION
	"Indicates if a bridge topology change is in progress."
::= { bdgdevice 27 }


bdgdeviceDesigRoot OBJECT-TYPE
SYNTAX OCTET STRING
ACCESS read-only
STATUS mandatory
DESCRIPTION
	"The unique identifier of the bridge recorded as the root."
::= { bdgdevice 28 }


bdgdeviceMaxAge OBJECT-TYPE
SYNTAX INTEGER
ACCESS read-only
STATUS mandatory
DESCRIPTION
	"The maximum age of received protocol information before it is
	discarded."
::= { bdgdevice 29 }


bdgdeviceHoldTime OBJECT-TYPE
SYNTAX INTEGER
ACCESS read-only
STATUS mandatory
DESCRIPTION
	"The minimum time period elapsing between the transmission of
	configuration BPDU's through a given bridge port."
::= { bdgdevice 30 }


bdgdeviceFwdDly OBJECT-TYPE
SYNTAX INTEGER
ACCESS read-only
STATUS mandatory
DESCRIPTION
	"The time spent in the listening state while moving from the
	blocking state to the learning state, or the time spent in the
	learning state while moving from the listening state to the
	forwarding state."
::= { bdgdevice 31 }


bdgdeviceBdgHello OBJECT-TYPE
SYNTAX INTEGER
ACCESS read-write
STATUS mandatory
DESCRIPTION
	"The value of the Hello Time parameter when the bridge is the
	root or is attempting to become the root. A time of 1 to 10
	seconds is allowed. The default is 2 seconds."
::= { bdgdevice 32 }


bdgdeviceBdgPriority OBJECT-TYPE
SYNTAX INTEGER
ACCESS read-write
STATUS mandatory
DESCRIPTION
	"The part of the bridge address that contains the identifier used
	in the spanning tree for priority comparisons. Allowed range is 0
	through FFFF. The default is 8000."
::= { bdgdevice 33 }


bdgdeviceResetCounts OBJECT-TYPE
SYNTAX INTEGER 
	{
		resetCounts (0)
	}
ACCESS read-write
STATUS mandatory
DESCRIPTION
	"Reset all counters to zero."
::= { bdgdevice 34 }


bdgdeviceUptime OBJECT-TYPE
SYNTAX INTEGER
ACCESS read-only
STATUS mandatory
DESCRIPTION
	"The time, in seconds, that has elapsed since the bridge was last
	reset or initialized."
::= { bdgdevice 35 }


bdgdeviceTrapType OBJECT-TYPE
SYNTAX OBJECT IDENTIFIER
ACCESS read-only
STATUS mandatory
DESCRIPTION
	"Contains the object identifier of the first VarBinding in the
	last trap generated by the bridge."
::= { bdgdevice 36 }


-- Port Object Definitions
--
--      This section defines the objects under the Port node.
--
-- Instance Identifiers for Port Objects
--
--      The Instance Identifier for port objects is the number of the port on
--      the bridge. Valid instance identifiers for the ports on the IRBM,
--      NB25E, and NB20E bridges are 1 and 2.
--
-- Port Objects


bdgPortAddress OBJECT-TYPE
SYNTAX OCTET STRING
ACCESS read-only
STATUS mandatory
DESCRIPTION
	"The Ethernet address of the port."
::= { bdgPort 1 }

bdgPortName OBJECT-TYPE
SYNTAX OCTET STRING
ACCESS read-write
STATUS mandatory
DESCRIPTION
	"The user-defined name assigned to the port. The default port 1
	name is PORT_1 and the default Port 2 name is PORT_2."
::= { bdgPort 2 }

bdgPortType OBJECT-TYPE
SYNTAX OCTET STRING
ACCESS read-only
STATUS mandatory
DESCRIPTION
	"The IEEE specification the port meets, e.g. 802.3."
::= { bdgPort 3 }

bdgPortStatus OBJECT-TYPE
SYNTAX OCTET STRING
ACCESS read-only
STATUS mandatory
DESCRIPTION
	"The status in which the port is operating. The status messages
	for Ports 1 and 2 are:

		OFF - The port is off, due to a failed network interface
		chip associated with that port.

		OK/SQE ON - The port is communicating with the network
		and the transceiver making the connection to the network
		has SQE enabled.

		OK/SQE OFF - The port is communicating with the network
		and the transceiver making the connection to the network
		has SQE disabled.

		CARRIER LOST - Communication with the network has not
		been established or has been lost."
::= { bdgPort 4 }

bdgPortNetName OBJECT-TYPE
SYNTAX OCTET STRING
ACCESS read-write
STATUS mandatory
DESCRIPTION
	"The user-defined name assigned to a network segment connected to
	the port. The default network name for Port 1 is LAN_1 and the
	default network name for Port 2 is LAN_2."
::= { bdgPort 5 }

bdgPortFrRx OBJECT-TYPE
SYNTAX Counter
ACCESS read-only
STATUS mandatory
DESCRIPTION
	"The number of frames received at the specified port."
::= { bdgPort 6 }

bdgPortDisInb OBJECT-TYPE
SYNTAX Counter
ACCESS read-only
STATUS mandatory
DESCRIPTION
	"The total number of valid frames that were received at the port
	but then discarded by the bridge in the forwarding process."
::= { bdgPort 7 }

bdgPortFwdOutb OBJECT-TYPE
SYNTAX Counter
ACCESS read-only
STATUS mandatory
DESCRIPTION
	"The number of frames forwarded successfully to the appropriate
	port."
::= { bdgPort 8 }

bdgPortDisLOB OBJECT-TYPE
SYNTAX Counter
ACCESS read-only
STATUS mandatory
DESCRIPTION
	"The number of packets that were discarded by the bridge because
	of a lack of buffer space to maintain the data."
::= { bdgPort 9 }

bdgPortDisTDE OBJECT-TYPE
SYNTAX Counter
ACCESS read-only
STATUS mandatory
DESCRIPTION
	"The number of frames that were intended for forwarding but were
	discarded when the maximum time period set for transmission was
	exceeded before forwarding was possible."
::= { bdgPort 10 }

bdgPortDisErr OBJECT-TYPE
SYNTAX Counter
ACCESS read-only
STATUS mandatory
DESCRIPTION
	"The number of frames that could not be transmitted because the
	frame was too large for the attached network (1526 bytes,
	including preamble, for 802.3 networks)."
::= { bdgPort 11 }

bdgPortColl OBJECT-TYPE
SYNTAX Counter
ACCESS read-only
STATUS mandatory
DESCRIPTION
	"The number of collisions that have occurred on the network at
	the specified port."
::= { bdgPort 12 }

bdgPortTxAbrt OBJECT-TYPE
SYNTAX Counter
ACCESS read-only
STATUS mandatory
DESCRIPTION
	"The number of transmissions that have been aborted due to
	excessive collisions (over 16 attempts to transmit the same
	packet)."
::= { bdgPort 13 }

bdgPortOowColl OBJECT-TYPE
SYNTAX Counter
ACCESS read-only
STATUS mandatory
DESCRIPTION
	"The number of collisions out of the standard collision window
	(51.2 uS). This indicates a network problem."
::= { bdgPort 14 }

bdgPortCRCErr OBJECT-TYPE
SYNTAX Counter
ACCESS read-only
STATUS mandatory
DESCRIPTION
	"The number of packets detected with Cyclical Redundancy Check
	failures."
::= { bdgPort 15 }

bdgPortFrAlErr OBJECT-TYPE
SYNTAX Counter
ACCESS read-only
STATUS mandatory
DESCRIPTION
	"The number of errors due to misaligned packets."
::= { bdgPort 16 }

bdgPortPriority OBJECT-TYPE
SYNTAX INTEGER
ACCESS read-write
STATUS mandatory
DESCRIPTION
	"The part of the port identifier which is used with the spanning
	tree algorithm when determining which port in a LAN segment has
	priority. The default is 80."
::= { bdgPort 17 }

bdgPortState OBJECT-TYPE
SYNTAX OCTET STRING
ACCESS read-only
STATUS mandatory
DESCRIPTION
	"The current state of the port, DISABLED, LISTENING, LEARNING,
	FORWARDING or BLOCKING."
::= { bdgPort 18 }

bdgPortPathCost OBJECT-TYPE
SYNTAX INTEGER
ACCESS read-write
STATUS mandatory
DESCRIPTION
	"The contributory cost of the applicable port to the overall cost
	of the path when the specified port is the root port. Allowable
	range is 1 to 65535. The default is 100."
::= { bdgPort 19 }

bdgPortDesigCost OBJECT-TYPE
SYNTAX INTEGER
ACCESS read-only
STATUS mandatory
DESCRIPTION
	"The cost of the path of this port to the root bridge on the
	network."
::= { bdgPort 20 }

bdgPortDesigBrdg OBJECT-TYPE
SYNTAX OCTET STRING
ACCESS read-only
STATUS mandatory
DESCRIPTION
	"The network address of the bridge that is assumed to be the root
	bridge on the network."
::= { bdgPort 21 }

bdgPortDesigPort OBJECT-TYPE
SYNTAX INTEGER
ACCESS read-only
STATUS mandatory
DESCRIPTION
	"The port identifier of the bridge port believed to be the
	designated port for the LAN associated with the port."
::= { bdgPort 22 }

bdgPortTopChgAck OBJECT-TYPE
SYNTAX INTEGER 
	{
		noTopologyChangeIsOccurring (0),
		topologyChangeIsOccurring   (1)
	}
ACCESS read-only
STATUS mandatory
DESCRIPTION
	"The value of the topology change acknowledgement flag in the
	next configuration BPDU to be transmitted on the associated port."
::= { bdgPort 23 }

bdgPortDesigRoot OBJECT-TYPE
SYNTAX OCTET STRING
ACCESS read-only
STATUS mandatory
DESCRIPTION
	"The unique bridge identifier of the bridge that is assumed to be
	the root bridge on the network."
::= { bdgPort 24 }

bdgPortRuntPackets OBJECT-TYPE
SYNTAX Counter
ACCESS read-only
STATUS mandatory
DESCRIPTION
	"The number of packets received at the indicated bdgPort that were
	less than the IEEE 802.3 minimum Ethernet frame size of 64 bytes."
::= { bdgPort 25 }

bdgPortOversizePackets OBJECT-TYPE
SYNTAX Counter
ACCESS read-only
STATUS mandatory
DESCRIPTION
	"The number of packets received at the indicated port that were
	greater than the IEEE 802.3 maximum Ethernet frame size of 1518
	bytes."
::= { bdgPort 26 }

bdgPortFrFilt OBJECT-TYPE
SYNTAX Counter
ACCESS read-only
STATUS mandatory
DESCRIPTION
	"The number of frames received at the indicated port that were
	filtered by the bridge."
::= { bdgPort 27 }


-- Acquired Database Statistical Object Definitions
--
--      This section defines the objects under the Acquired Database
--      Statistics node.
--
-- Instance Identifiers for Acquired Database Statistical Objects
--
--      There is only one instance of an Acquired Database Statistical object,
--      thus the Instance Identifier is 0.
--
--  Acquired Database Statistical Objects


acqTotalEntries OBJECT-TYPE
SYNTAX INTEGER
ACCESS read-only
STATUS mandatory
DESCRIPTION
	"The total number of entries in the acquired database."
::= { acqStats 1 }

acqMaxEntries OBJECT-TYPE
SYNTAX INTEGER
ACCESS read-only
STATUS mandatory
DESCRIPTION
	"The maximum number of entries allowed in the acquired database."
::= { acqStats 2 }

acqStaticEntries OBJECT-TYPE
SYNTAX INTEGER
ACCESS 	read-only
STATUS 	mandatory
DESCRIPTION
	"The number of addresses added to the Acquired database by the
	user or network manager."
::= { acqStats 3 }

acqStaticAgeTime OBJECT-TYPE
SYNTAX INTEGER
ACCESS read-only
STATUS mandatory
DESCRIPTION
	"The length of time allowed for a static entry in the Acquired
	database to be inactive before it is dropped from the database.
	This time is fixed at zero."
::= { acqStats 4 }

acqDynEntries OBJECT-TYPE
SYNTAX INTEGER
ACCESS read-only
STATUS mandatory
DESCRIPTION
	"The number of entries that have been accumulated in the Acquired
	database through the bridge's learning process."
::= { acqStats 5 }

acqDynAgeTime OBJECT-TYPE
SYNTAX INTEGER
ACCESS read-write
STATUS mandatory
DESCRIPTION
	"The length of time allowed for a dynamic entry in the acquired
	database to be inactive before it is dropped from the database. A
	time from 10 - 1,000,000 seconds is allowed. The default is 300
	seconds."
::= { acqStats 6 }

acqEraseDatabase OBJECT-TYPE
SYNTAX INTEGER 
	{
		eraseAcquiredDatabase (0)
	}
ACCESS read-write
STATUS mandatory
DESCRIPTION
	"Set to zero to erase all entries in the acquired database."
::= { acqStats 7 }


-- Acquired Database Option Object Definitions
--
--      This section defines the objects under the Acquired Database
--      Option node.
--
-- Instance Identifiers for Acquired Database Option Objects
--
--      The instance identifier for the acquired database option objects is
--      the 6-byte Ethernet address of the device to be added, deleted or
--      displayed to/from the acquired database.
--
--  Acquired Database Option Objects


acqCreate00 OBJECT-TYPE
SYNTAX INTEGER 
	{
		createAcquiredEntryFilterPort1FilterPort2  (0)
	}
ACCESS read-write
STATUS mandatory
DESCRIPTION
	"Add an entry to the acquired database to filter packets entering
	ports 1 and 2 if those packets are destined for the specified
	address."
::= { acqOptions 1 }

acqCreate20 OBJECT-TYPE
SYNTAX INTEGER 
	{
		createAcquiredEntryForwardPort1FilterPort2  (0)
	}
ACCESS read-write
STATUS mandatory
DESCRIPTION
	"Add an entry to the acquired database to forward packets
	entering port1 to port2 and filter packets entering port2 if
	those packets are destined for the specified address."
::= { acqOptions 2 }

acqCreate01 OBJECT-TYPE
SYNTAX INTEGER 
	{
		createAcquiredEntryFilterPort1ForwardPort2  (0)
	}
ACCESS read-write
STATUS mandatory
DESCRIPTION
	"Add an entry to the acquired database to filter packets entering
	port 1 and forward packets entering port 2 to port 1 if those
	packets are destined for the specified address."
::= { acqOptions 3 }

acqCreate21 OBJECT-TYPE
SYNTAX INTEGER 
	{
		createAcquiredEntryForwardPort1ForwardPort2 (0)
	}
ACCESS read-write
STATUS mandatory
DESCRIPTION
	"Add an entry to the acquired database to forward packets
	entering port 1 to port 2 and to forward packets entering port 2
	to port 1 if those packets are destined for the specified
	address."
::= { acqOptions 4 }

acqDelete OBJECT-TYPE
SYNTAX INTEGER 
	{
		deleteAcquiredEntry (0)
	}
ACCESS read-write
STATUS mandatory
DESCRIPTION
	"Delete an entry from the acquired database."
::= { acqOptions 5 }

acqDispType OBJECT-TYPE
SYNTAX OCTET STRING
ACCESS read-only
STATUS mandatory
DESCRIPTION
	"Display the entry type, STATIC or DYNAMIC."
::= { acqOptions 6 }

acqDispOutp1 OBJECT-TYPE
SYNTAX INTEGER 
	{
		filter (0),
		relay  (2)
	}
ACCESS read-only
STATUS mandatory
DESCRIPTION
	"The outbound port for packets entering port 1."
::= { acqOptions 7 }

acqDispOutp2 OBJECT-TYPE
SYNTAX INTEGER 
	{
		filter (0),
		relay  (1)
	}
ACCESS read-only
STATUS mandatory
DESCRIPTION
	"The outbound port for packets entering port 2."
::= { acqOptions 8 }

acqSrcAddress OBJECT-TYPE
SYNTAX OCTET STRING
ACCESS read-only
STATUS mandatory
DESCRIPTION
	"The source address of this acquired database entry, i.e. the
	instance."
::= { acqOptions 9 }

-- Permanent Database Statistical Object Definitions
--
--      This section defines the objects under the Permanent Database
--      Statistics node.
--
-- Instance Identifiers for Permanent Database Statistical Objects
--
--      There is only one instance of an Permanent Database Statistical
--      object, thus the Instance Identifier is 0.
--
--  Permanent Database Statistical Objects


permMaxEntries OBJECT-TYPE
SYNTAX INTEGER
ACCESS read-only
STATUS mandatory
DESCRIPTION
	"The maximum number of entries allowed in the permanent database."
::= { permStats 1 }

permCurrEntries OBJECT-TYPE
SYNTAX INTEGER
ACCESS read-only
STATUS mandatory
DESCRIPTION
	"The number of entries currently recorded in the bridge's
	permanent database."
::= { permStats 2 }

permEraseDatabase OBJECT-TYPE
SYNTAX INTEGER 
	{
		erasePermanentDatabase (0)
	}
ACCESS read-write
STATUS mandatory
DESCRIPTION
	"Erase all entries in the permanent database."
::= { permStats 3 }

-- Permanent Database Option Object Definitions
--
--      This section defines the objects under the Permanent Database
--      Option node.
--
-- Instance Identifiers for Permanent Database Option Objects
--
--      The instance identifier for the permanent database option objects is
--      the 6-byte Ethernet address of the device to be added, deleted or
--      displayed to/from the permanent database.
--
--  Permanent Database Option Objects

permCreate00 OBJECT-TYPE
SYNTAX INTEGER 
	{
		createPermanentEntryFilterPort1FilterPort2 (0)
	}
ACCESS read-write
STATUS mandatory
DESCRIPTION
	"Add an entry to the permanent database to filter packets
	entering ports 1 and 2 if those packets are destined for the
	specified address."
::= { permOptions 1 }

permCreate20 OBJECT-TYPE
SYNTAX INTEGER 
	{
		createPermanentEntryForwardPort1FilterPort2 (0)
	}
ACCESS read-write
STATUS mandatory
DESCRIPTION
	"Add an entry to the permanent database to forward packets
	entering port 1 and filter packets entering port 2 if those
	packets are destined for the specified address."
::= { permOptions 2 }

permCreate01 OBJECT-TYPE
SYNTAX INTEGER 
	{
		createPermanentEntryFilterPort1ForwardPort2 (0)
	}
ACCESS read-write
STATUS mandatory
DESCRIPTION
	"Add an entry to the permanent database to filter packets
	entering port 1 and forward packets entering port 2 if those
	packets are destined for the specified address."
::= { permOptions 3 }

permCreate21 OBJECT-TYPE
SYNTAX INTEGER
	{
		createPermanentEntryForwardPort1ForwardPort2 (0)
	}
ACCESS read-write
STATUS mandatory
DESCRIPTION
	"Add an entry to the permanent database to forward packets
	entering ports 1 and 2 if those packets are destined for the
	specified address."
::= { permOptions 4 }

permDelete OBJECT-TYPE
SYNTAX INTEGER 
	{
		deletePermanentEntry (0)
	}
ACCESS read-write
STATUS mandatory
DESCRIPTION
	"Delete an entry from the permanent database."
::= { permOptions 5 }

permDispType OBJECT-TYPE
SYNTAX OCTET STRING
ACCESS read-only
STATUS mandatory
DESCRIPTION
	"Display the entry type, STATIC or DYNAMIC."
::= { permOptions 6 }

permDispOutp1 OBJECT-TYPE
SYNTAX INTEGER 
	{
		filter (0),
		relay  (2)
	}
ACCESS read-only
STATUS mandatory
DESCRIPTION
	"The outbound port for packets entering port 1."
::= { permOptions 7 }

permDispOutp2 OBJECT-TYPE
SYNTAX INTEGER 
	{
		filter (0),
		relay  (1)
	}
ACCESS read-only
STATUS mandatory
DESCRIPTION
	"The outbound port for packets entering port 2."
::= { permOptions 8 }

permSrcAddress OBJECT-TYPE
SYNTAX OCTET STRING
ACCESS read-only
STATUS mandatory
DESCRIPTION
	"The source address in this permanent database entry, i.e. the
	instance."
::= { permOptions 9 }

-- Special Database Statistical Object Definitions
--
--      This section defines the objects under the Special Database
--      Statistical node.
--
-- Instance Identifiers for Special Database Statistical Objects
--
--      There is only one instance of a Special Database Statistical object,
--      thus the Instance Identifier is 0.
--
-- Special Database Statistical Objects

specNumEntries OBJECT-TYPE
SYNTAX INTEGER
ACCESS read-only
STATUS mandatory
DESCRIPTION
	"The number of filters in the special database."
::= { specStats 1 }

specMaxEntries OBJECT-TYPE
SYNTAX INTEGER
ACCESS read-only
STATUS mandatory
DESCRIPTION
	"The maximum number of filters the special database can contain."
::= { specStats 2 }

specNextFilterNum OBJECT-TYPE
SYNTAX INTEGER
ACCESS read-only
STATUS mandatory
DESCRIPTION
	"The number of the next available filter that can be added to the
	special database."
::= { specStats 3 }

-- Special Database Filter Object Definitions
--
--      This section defines the objects under the Special Database
--      Filter node.
--
-- Instance Identifiers for Special Database Filter Objects
--
--      The instance identifier of the special database filter objects
--      is the filter number, values from 1 through 10 are allowed.
--
-- Special Database Filter Objects

specEnable OBJECT-TYPE
SYNTAX INTEGER 
	{
		disableFilter (0),
		enableFilter  (1)
	}
ACCESS read-write
STATUS mandatory
DESCRIPTION
	"Enable or disable the filter."
::= { specFilters 1 }

specPort1 OBJECT-TYPE
SYNTAX INTEGER 
	{
		filter (0),
		relay  (2)
	}
ACCESS read-write
STATUS mandatory
DESCRIPTION
	"Set port 1 to filter or forward packets."
::= { specFilters 2 }

specPort2 OBJECT-TYPE
SYNTAX INTEGER 
	{
		filter (0),
		relay  (1)
	}
ACCESS read-write
STATUS mandatory
DESCRIPTION
	"Set port 2 to filter or forward packets."
::= { specFilters 3 }

specDestAddress OBJECT-TYPE
SYNTAX OCTET STRING
ACCESS read-write
STATUS mandatory
DESCRIPTION
	"Set the special database to filter packets with a specific
	destination address."
::= { specFilters 4 }

specSrcAddress OBJECT-TYPE
SYNTAX OCTET STRING
ACCESS read-write
STATUS mandatory
DESCRIPTION
	"Set the special database to filter packets with a specific
	source address."
::= { specFilters 5 }

specType OBJECT-TYPE
SYNTAX OCTET STRING
ACCESS read-write
STATUS mandatory
DESCRIPTION
	"Set the special database to filter packets with a specific type
	field."
::= { specFilters 6 }

specDataField OBJECT-TYPE
SYNTAX OCTET STRING
ACCESS read-write
STATUS mandatory
DESCRIPTION
	"Set the special database to filter packets based on the first
	sixteen bytes of data in the packet."
::= { specFilters 7 }

specDeleteFilter OBJECT-TYPE
SYNTAX INTEGER 
	{
		deleteFilter (0)
	}
ACCESS read-write
STATUS mandatory
DESCRIPTION
	"Delete a filter from the special database."
::= { specFilters 8 }


-- TRAP TYPES OBJECT DEFINITIONS
--
-- This section describes the trap types that the bridge can generate. These
-- are not objects, but Object Identifiers used to indicate the specific trap.
-- They are taken from the object space and are thus documented here.
--
-- The SNMP trap messages are composed of two user definable areas: 
--     a) the specific trap type and 
--     b) the VarBindings (e.g. the interesting information)
--
-- The specific trap type is an integer that is used to determine the
-- specific trap which has occurred. The "interesting information" contains
-- a group of object identifiers and their values that provide information
-- about the trap.
--
-- Trap Decription
--
-- 	BridgeStatus
--
-- 	Specific Trap Type Code - 0x0301
--
-- 	When the bridge status changes, a trap will be generated. The
--   interesting information includes the current status of the bridge.
--
--
-- Trap Description
--
-- 	AcqDbaseFull
--
--	Specific Trap Type Code - 0x0302
--
-- 	When the acquired portion of the bridge's filtering database is full, a
--   trap is generated. The interesting information included with this trap
--   is the number of entries in the acquired database.
          
-- Formal definition of the Layer Management MIB. (e.g. PC cards )

     lmcommon         OBJECT IDENTIFIER ::= { layerMgmt 1 }
          
     mAC            OBJECT IDENTIFIER ::= { layerMgmt 2 }          

     ieee8023      OBJECT IDENTIFIER ::= {  mAC 1 }
          
     pcIF           OBJECT IDENTIFIER ::= { ieee8023 1 }

     pcIfRev        OBJECT IDENTIFIER ::= { pcIF 1 }

          
          		
pcDeviceName OBJECT-TYPE   
          
SYNTAX OCTET STRING
ACCESS read-only
STATUS mandatory
DESCRIPTION
    "Name of the PC device"
::= { pcIfRev 1 }


pcBoardType   OBJECT-TYPE

SYNTAX OBJECT IDENTIFIER
ACCESS read-only
STATUS mandatory
DESCRIPTION
     "An object  Identifier that  indicates the  type of  the  PC
     board. This will include MAC type and Media type."


::= { pcIfRev 2  }

pcOwnerName    OBJECT-TYPE

SYNTAX OCTET STRING
ACCESS read-only
STATUS mandatory
DESCRIPTION
     "The owner of this PC."


::= { pcIfRev 3 }

pcLocation    OBJECT-TYPE

SYNTAX OCTET STRING
ACCESS read-only
STATUS mandatory
DESCRIPTION
     "A text description of the location of this PC."

::= { pcIfRev 4 }

pcMMACAddr    OBJECT-TYPE

SYNTAX OCTET STRING
ACCESS read-only
STATUS mandatory
DESCRIPTION
     "The MAC address of the MMAC that this PC is connected to."


::= { pcIfRev 5 }

pcMMACBoard    OBJECT-TYPE

SYNTAX OCTET STRING
ACCESS read-only
STATUS mandatory
DESCRIPTION
     "The slot  number of  the board  in the MMAC that this PC is
connected to."


::= { pcIfRev 6  }

pcMMACPort    OBJECT-TYPE

SYNTAX OCTET STRING
ACCESS read-only
STATUS mandatory
DESCRIPTION
     "The number  of the  port on the board of the MMAC that this
PC is connected to."
::= { pcIfRev 7 }

pcApplication    OBJECT-TYPE

SYNTAX OCTET STRING
ACCESS read-only
STATUS mandatory
DESCRIPTION
     "A text  description of  the network  application running on
this PC."


::= { pcIfRev 8 }

pcDriverRev    OBJECT-TYPE

SYNTAX OCTET STRING
ACCESS read-only
STATUS mandatory
DESCRIPTION
     "The revision of the LAN card driver."
::= { pcIfRev 9 }

pcOnboardMemory    OBJECT-TYPE

SYNTAX INTEGER
ACCESS read-only
STATUS mandatory
DESCRIPTION
     "The number  of Kilobytes  of memory  (eg. a 16K board would
reply 16)"

::= { pcIfRev 10 }

pcComment    OBJECT-TYPE

SYNTAX OCTET STRING
ACCESS read-only
STATUS mandatory
DESCRIPTION
     "A user-defined character string."


::= { pcIfRev 11 }
 
pcMACAddr   OBJECT-TYPE

SYNTAX OCTET STRING
ACCESS read-only
STATUS mandatory
DESCRIPTION
     "The MAC address of the PC card."


::= { pcIfRev 12  }

pcFramesXmit   OBJECT-TYPE

SYNTAX INTEGER
ACCESS read-only
STATUS mandatory
DESCRIPTION
     "The number of MAC frames transmitted by this PC card."


::= { pcIfRev 13  }

pcBytesXmit    OBJECT-TYPE

SYNTAX INTEGER
ACCESS read-only
STATUS mandatory
DESCRIPTION
     "The number bytes transmitted by this PC card."


::= { pcIfRev 14 }

pcMcastXmit    OBJECT-TYPE
SYNTAX INTEGER
ACCESS read-only
STATUS mandatory
DESCRIPTION
     "The number of multicasted frames sent by this PC card."

::= { pcIfRev 15 }

pcBcastXmit    OBJECT-TYPE

SYNTAX INTEGER
ACCESS read-only
STATUS mandatory
DESCRIPTION
     "The number of broadcast frames from this PC card."


::= { pcIfRev 16 }

pcDeferXmit    OBJECT-TYPE

SYNTAX INTEGER
ACCESS read-only
STATUS mandatory
DESCRIPTION
     "The number  of transmit  packets that  were deferred due to
busy media."

::= { pcIfRev 17 }

pcSglColl     OBJECT-TYPE

SYNTAX INTEGER
ACCESS read-only
STATUS mandatory
DESCRIPTION
     "The  number   of  transmit  packet  experiencing  a  single
collision."

::= { pcIfRev 18 }

pcMultiColl    OBJECT-TYPE

SYNTAX INTEGER
ACCESS read-only
STATUS mandatory
DESCRIPTION
     "The  number  of  transmit  packets  that  have  experienced
multiple collisions."

::= { pcIfRev 19 }

pcTotXmitErrs    OBJECT-TYPE

SYNTAX INTEGER
ACCESS read-only
STATUS mandatory
DESCRIPTION
     "The total number of transmit errors."

::= { pcIfRev 20 }

pcLateColls   OBJECT-TYPE

SYNTAX INTEGER
ACCESS read-only
STATUS mandatory
DESCRIPTION
     "The  number  of  transmit  packets  that  experienced  late
collisions."


::= { pcIfRev 21 }

pcXcessColls    OBJECT-TYPE

SYNTAX INTEGER
ACCESS read-only
STATUS mandatory
DESCRIPTION
     "The number  of  transmit  packets  aborted  due  to  excess
collisions."

::= { pcIfRev 22 }

pcCarrErr   OBJECT-TYPE

SYNTAX INTEGER
ACCESS read-only
STATUS mandatory
DESCRIPTION
     "The number  of transmit  packets  that  experience  carrier
sense errors (ie. lose carrier during transmission)."

::= { pcIfRev 23 }

pcFramesRec   OBJECT-TYPE

SYNTAX INTEGER
ACCESS read-only
STATUS mandatory
DESCRIPTION
     "The number of frames received."

::= { pcIfRev 24 }

pcBytesRec    OBJECT-TYPE

SYNTAX INTEGER
ACCESS read-only
STATUS mandatory
DESCRIPTION
     "The number of bytes received by this station."


::= { pcIfRev 25 }

pcMcastRec    OBJECT-TYPE

SYNTAX INTEGER
ACCESS read-only
STATUS mandatory
DESCRIPTION
     "The number of multicasted frames received."

::= { pcIfRev 26 }

pcBcastRec    OBJECT-TYPE

SYNTAX INTEGER
ACCESS read-only
STATUS mandatory
DESCRIPTION
     "The number of broadcast packets received."

::= { pcIfRev 27 }

pcTotRecErrs    OBJECT-TYPE

SYNTAX INTEGER
ACCESS read-only
STATUS mandatory
DESCRIPTION
     "The total number of receive errors."

::= { pcIfRev 28 }

pcTooLong   OBJECT-TYPE

SYNTAX INTEGER
ACCESS read-only
STATUS mandatory
DESCRIPTION
     "The number of packets received that are too long (over 1518
bytes)."

::= { pcIfRev 29 }

pcTooShort    OBJECT-TYPE
SYNTAX INTEGER
ACCESS read-only
STATUS mandatory
DESCRIPTION
     "The number  of packets  that are too short. (under 64 bytes
long)."

::= { pcIfRev 30 }

pcAlignErrs    OBJECT-TYPE

SYNTAX INTEGER
ACCESS read-only
STATUS mandatory
DESCRIPTION
     "The number of alignment errors in receive packets."


::= { pcIfRev 31 }

pcCRCErrs     OBJECT-TYPE

SYNTAX INTEGER
ACCESS read-only
STATUS mandatory
DESCRIPTION
     "The number of receive packets with CRC errors."

::= { pcIfRev 32  }

pcLenErrs    OBJECT-TYPE

SYNTAX INTEGER
ACCESS read-only
STATUS mandatory
DESCRIPTION
     "The number  of packets  whose length  is not  equal to  the
number of bytes received."

::= { pcIfRev 33 }

pcIntRecErr    OBJECT-TYPE

SYNTAX INTEGER
ACCESS read-only
STATUS mandatory
DESCRIPTION
     "The number  of receive  packets that  experienced  internal
errors (eg. no receive buffers)."

::= { pcIfRev 34 }

pcSqeErr    OBJECT-TYPE

SYNTAX INTEGER
ACCESS read-only
STATUS mandatory
DESCRIPTION
     "The number of SQE errors."

::= { pcIfRev 35 }



END
