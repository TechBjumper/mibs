-- file automatically created


TELDAT-TRAP-CIF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


cifTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the CIF event subsystem."
    REVISION "201401200930Z"
    DESCRIPTION "Initial implementation"
        ::= { telEventTraps 141 }


cifEventsGroup	OBJECT IDENTIFIER	::= { cifTrapsMIB 1 }

cifNotifications	OBJECT IDENTIFIER	::= { cifTrapsMIB 2 }
cifNotificationsPrefix	OBJECT IDENTIFIER	::= { cifNotifications 0 }

cifEventObjects1 OBJECT-IDENTITY
    STATUS current
    DESCRIPTION
        "Event CIF.1
        This message is generated for each request of ciphering a frame."
    ::= { cifEventsGroup 1 }

cif1-source-ifc OBJECT-TYPE
    SYNTAX Integer32
    MAX-ACCESS accessible-for-notify
    STATUS current
    DESCRIPTION
        "Parameter 'source-ifc' in event CIF.1"
    ::= { cifEventObjects1 1 }

cif1-source-dlci OBJECT-TYPE
    SYNTAX Integer32
    MAX-ACCESS accessible-for-notify
    STATUS current
    DESCRIPTION
        "Parameter 'source-dlci' in event CIF.1"
    ::= { cifEventObjects1 2 }

cifEventObjects2 OBJECT-IDENTITY
    STATUS current
    DESCRIPTION
        "Event CIF.2
        This message is generated for each request of deciphering a frame."
    ::= { cifEventsGroup 2 }

cif2-source-ifc OBJECT-TYPE
    SYNTAX Integer32
    MAX-ACCESS accessible-for-notify
    STATUS current
    DESCRIPTION
        "Parameter 'source-ifc' in event CIF.2"
    ::= { cifEventObjects2 1 }

cif2-source-dlci OBJECT-TYPE
    SYNTAX Integer32
    MAX-ACCESS accessible-for-notify
    STATUS current
    DESCRIPTION
        "Parameter 'source-dlci' in event CIF.2"
    ::= { cifEventObjects2 2 }

cifEventObjects3 OBJECT-IDENTITY
    STATUS current
    DESCRIPTION
        "Event CIF.3
        This message is generated for each ciphered frame that is transmitted."
    ::= { cifEventsGroup 3 }

cif3-dest-ifc OBJECT-TYPE
    SYNTAX Integer32
    MAX-ACCESS accessible-for-notify
    STATUS current
    DESCRIPTION
        "Parameter 'dest-ifc' in event CIF.3"
    ::= { cifEventObjects3 1 }

cif3-dest-dlci OBJECT-TYPE
    SYNTAX Integer32
    MAX-ACCESS accessible-for-notify
    STATUS current
    DESCRIPTION
        "Parameter 'dest-dlci' in event CIF.3"
    ::= { cifEventObjects3 2 }

cifEventObjects4 OBJECT-IDENTITY
    STATUS current
    DESCRIPTION
        "Event CIF.4
        This message is generated for each deciphered frame that is transmitted."
    ::= { cifEventsGroup 4 }

cif4-dest-ifc OBJECT-TYPE
    SYNTAX Integer32
    MAX-ACCESS accessible-for-notify
    STATUS current
    DESCRIPTION
        "Parameter 'dest-ifc' in event CIF.4"
    ::= { cifEventObjects4 1 }

cif4-dest-dlci OBJECT-TYPE
    SYNTAX Integer32
    MAX-ACCESS accessible-for-notify
    STATUS current
    DESCRIPTION
        "Parameter 'dest-dlci' in event CIF.4"
    ::= { cifEventObjects4 2 }

cifEventObjects5 OBJECT-IDENTITY
    STATUS current
    DESCRIPTION
        "Event CIF.5
        This message is generated for each bypass frame that is transmitted."
    ::= { cifEventsGroup 5 }

cif5-dest-ifc OBJECT-TYPE
    SYNTAX Integer32
    MAX-ACCESS accessible-for-notify
    STATUS current
    DESCRIPTION
        "Parameter 'dest-ifc' in event CIF.5"
    ::= { cifEventObjects5 1 }

cif5-dest-dlci OBJECT-TYPE
    SYNTAX Integer32
    MAX-ACCESS accessible-for-notify
    STATUS current
    DESCRIPTION
        "Parameter 'dest-dlci' in event CIF.5"
    ::= { cifEventObjects5 2 }

cifEventObjects6 OBJECT-IDENTITY
    STATUS current
    DESCRIPTION
        "Event CIF.6
        This message is generated for each deciphered frame using default key."
    ::= { cifEventsGroup 6 }

cif6-dest-ifc OBJECT-TYPE
    SYNTAX DisplayString
    MAX-ACCESS accessible-for-notify
    STATUS current
    DESCRIPTION
        "Parameter 'dest-ifc' in event CIF.6"
    ::= { cifEventObjects6 1 }

cif6-dest-dlci OBJECT-TYPE
    SYNTAX Integer32
    MAX-ACCESS accessible-for-notify
    STATUS current
    DESCRIPTION
        "Parameter 'dest-dlci' in event CIF.6"
    ::= { cifEventObjects6 2 }

cifEventObjects7 OBJECT-IDENTITY
    STATUS current
    DESCRIPTION
        "Event CIF.7
        This message is generated for each frame that arrives bad ciphered."
    ::= { cifEventsGroup 7 }

cif7-source-ifc OBJECT-TYPE
    SYNTAX Integer32
    MAX-ACCESS accessible-for-notify
    STATUS current
    DESCRIPTION
        "Parameter 'source-ifc' in event CIF.7"
    ::= { cifEventObjects7 1 }

cif7-source-dlci OBJECT-TYPE
    SYNTAX Integer32
    MAX-ACCESS accessible-for-notify
    STATUS current
    DESCRIPTION
        "Parameter 'source-dlci' in event CIF.7"
    ::= { cifEventObjects7 2 }

cifEventObjects8 OBJECT-IDENTITY
    STATUS current
    DESCRIPTION
        "Event CIF.8
        This message is generated for each discarded frame."
    ::= { cifEventsGroup 8 }

cif8-source-ifc OBJECT-TYPE
    SYNTAX DisplayString
    MAX-ACCESS accessible-for-notify
    STATUS current
    DESCRIPTION
        "Parameter 'source-ifc' in event CIF.8"
    ::= { cifEventObjects8 1 }

cif8-source-dlci OBJECT-TYPE
    SYNTAX Integer32
    MAX-ACCESS accessible-for-notify
    STATUS current
    DESCRIPTION
        "Parameter 'source-dlci' in event CIF.8"
    ::= { cifEventObjects8 2 }

cifEventObjects9 OBJECT-IDENTITY
    STATUS current
    DESCRIPTION
        "Event CIF.9
        This message is generated for each discarded frame due to an error on
        ciphering card."
    ::= { cifEventsGroup 9 }

cif9-source-ifc OBJECT-TYPE
    SYNTAX DisplayString
    MAX-ACCESS accessible-for-notify
    STATUS current
    DESCRIPTION
        "Parameter 'source-ifc' in event CIF.9"
    ::= { cifEventObjects9 1 }

cif9-source-dlci OBJECT-TYPE
    SYNTAX Integer32
    MAX-ACCESS accessible-for-notify
    STATUS current
    DESCRIPTION
        "Parameter 'source-dlci' in event CIF.9"
    ::= { cifEventObjects9 2 }

cifEventObjects19 OBJECT-IDENTITY
    STATUS current
    DESCRIPTION
        "Event CIF.19
        This message is generated for each request of ciphering a backup frame."
    ::= { cifEventsGroup 19 }

cif19-source-ifc OBJECT-TYPE
    SYNTAX DisplayString
    MAX-ACCESS accessible-for-notify
    STATUS current
    DESCRIPTION
        "Parameter 'source-ifc' in event CIF.19"
    ::= { cifEventObjects19 1 }

cif19-source-dlci OBJECT-TYPE
    SYNTAX Integer32
    MAX-ACCESS accessible-for-notify
    STATUS current
    DESCRIPTION
        "Parameter 'source-dlci' in event CIF.19"
    ::= { cifEventObjects19 2 }

cifEventObjects20 OBJECT-IDENTITY
    STATUS current
    DESCRIPTION
        "Event CIF.20
        This message is generated for each request of deciphering
        a backup frame."
    ::= { cifEventsGroup 20 }

cif20-source-ifc OBJECT-TYPE
    SYNTAX DisplayString
    MAX-ACCESS accessible-for-notify
    STATUS current
    DESCRIPTION
        "Parameter 'source-ifc' in event CIF.20"
    ::= { cifEventObjects20 1 }

cif20-source-dlci OBJECT-TYPE
    SYNTAX Integer32
    MAX-ACCESS accessible-for-notify
    STATUS current
    DESCRIPTION
        "Parameter 'source-dlci' in event CIF.20"
    ::= { cifEventObjects20 2 }

cifEventObjects22 OBJECT-IDENTITY
    STATUS current
    DESCRIPTION
        "Event CIF.22
        This message is generated for each too long received frame."
    ::= { cifEventsGroup 22 }

cif22-source-ifc OBJECT-TYPE
    SYNTAX Integer32
    MAX-ACCESS accessible-for-notify
    STATUS current
    DESCRIPTION
        "Parameter 'source-ifc' in event CIF.22"
    ::= { cifEventObjects22 1 }

cif22-source-dlci OBJECT-TYPE
    SYNTAX Integer32
    MAX-ACCESS accessible-for-notify
    STATUS current
    DESCRIPTION
        "Parameter 'source-dlci' in event CIF.22"
    ::= { cifEventObjects22 2 }

cifEventObjects23 OBJECT-IDENTITY
    STATUS current
    DESCRIPTION
        "Event CIF.23
        This message is generated for each received frame which cannot be sent
        because the line is not active."
    ::= { cifEventsGroup 23 }

cif23-source-ifc OBJECT-TYPE
    SYNTAX Integer32
    MAX-ACCESS accessible-for-notify
    STATUS current
    DESCRIPTION
        "Parameter 'source-ifc' in event CIF.23"
    ::= { cifEventObjects23 1 }

cif23-source-dlci OBJECT-TYPE
    SYNTAX Integer32
    MAX-ACCESS accessible-for-notify
    STATUS current
    DESCRIPTION
        "Parameter 'source-dlci' in event CIF.23"
    ::= { cifEventObjects23 2 }

cifEventObjects25 OBJECT-IDENTITY
    STATUS current
    DESCRIPTION
        "Event CIF.25
        This message is generated when a call request is received
        in the ciphering module."
    ::= { cifEventsGroup 25 }

cif25-called-nri OBJECT-TYPE
    SYNTAX DisplayString
    MAX-ACCESS accessible-for-notify
    STATUS current
    DESCRIPTION
        "Parameter 'called-nri' in event CIF.25"
    ::= { cifEventObjects25 1 }

cif25-calling-nri OBJECT-TYPE
    SYNTAX DisplayString
    MAX-ACCESS accessible-for-notify
    STATUS current
    DESCRIPTION
        "Parameter 'calling-nri' in event CIF.25"
    ::= { cifEventObjects25 2 }

cif25-in-tables OBJECT-TYPE
    SYNTAX DisplayString
    MAX-ACCESS accessible-for-notify
    STATUS current
    DESCRIPTION
        "Parameter 'in-tables' in event CIF.25"
    ::= { cifEventObjects25 3 }

cif25-key-change OBJECT-TYPE
    SYNTAX DisplayString
    MAX-ACCESS accessible-for-notify
    STATUS current
    DESCRIPTION
        "Parameter 'key-change' in event CIF.25"
    ::= { cifEventObjects25 4 }

cifEventObjects30 OBJECT-IDENTITY
    STATUS current
    DESCRIPTION
        "Event CIF.30
        Message generated for each IPSEC packet sent to the HW ciphering module."
    ::= { cifEventsGroup 30 }

cif30-source-ifc OBJECT-TYPE
    SYNTAX DisplayString
    MAX-ACCESS accessible-for-notify
    STATUS current
    DESCRIPTION
        "Parameter 'source-ifc' in event CIF.30"
    ::= { cifEventObjects30 1 }

cif30-SA-spi OBJECT-TYPE
    SYNTAX Integer32
    MAX-ACCESS accessible-for-notify
    STATUS current
    DESCRIPTION
        "Parameter 'SA-spi' in event CIF.30"
    ::= { cifEventObjects30 2 }

cifEventObjects31 OBJECT-IDENTITY
    STATUS current
    DESCRIPTION
        "Event CIF.31
        Message generated for each IPSEC packet sent to the HW ciphering module."
    ::= { cifEventsGroup 31 }

cif31-source-ifc OBJECT-TYPE
    SYNTAX DisplayString
    MAX-ACCESS accessible-for-notify
    STATUS current
    DESCRIPTION
        "Parameter 'source-ifc' in event CIF.31"
    ::= { cifEventObjects31 1 }

cif31-SA-spi OBJECT-TYPE
    SYNTAX Integer32
    MAX-ACCESS accessible-for-notify
    STATUS current
    DESCRIPTION
        "Parameter 'SA-spi' in event CIF.31"
    ::= { cifEventObjects31 2 }

cifEventObjects32 OBJECT-IDENTITY
    STATUS current
    DESCRIPTION
        "Event CIF.32
        Message generated for each IPSEC packet sent to the HW ciphering card."
    ::= { cifEventsGroup 32 }

cif32-source-ifc OBJECT-TYPE
    SYNTAX DisplayString
    MAX-ACCESS accessible-for-notify
    STATUS current
    DESCRIPTION
        "Parameter 'source-ifc' in event CIF.32"
    ::= { cifEventObjects32 1 }

cif32-SA-spi OBJECT-TYPE
    SYNTAX Integer32
    MAX-ACCESS accessible-for-notify
    STATUS current
    DESCRIPTION
        "Parameter 'SA-spi' in event CIF.32"
    ::= { cifEventObjects32 2 }

cifEventObjects33 OBJECT-IDENTITY
    STATUS current
    DESCRIPTION
        "Event CIF.33
        Message generated for each IPSEC packet sent to the HW ciphering card."
    ::= { cifEventsGroup 33 }

cif33-source-ifc OBJECT-TYPE
    SYNTAX DisplayString
    MAX-ACCESS accessible-for-notify
    STATUS current
    DESCRIPTION
        "Parameter 'source-ifc' in event CIF.33"
    ::= { cifEventObjects33 1 }

cif33-SA-spi OBJECT-TYPE
    SYNTAX Integer32
    MAX-ACCESS accessible-for-notify
    STATUS current
    DESCRIPTION
        "Parameter 'SA-spi' in event CIF.33"
    ::= { cifEventObjects33 2 }


cifNotification1 NOTIFICATION-TYPE
    OBJECTS { 
              cif1-source-ifc, 
              cif1-source-dlci 
            }
    STATUS current
    DESCRIPTION
        "Notification of Event CIF.1

        Message: 'Frame received to be ciphered on interface $1, dlci $2'

        Parameters list:
              $1: cif1-source-ifc
              $2: cif1-source-dlci

        This message is generated for each request of ciphering a frame."
    ::= { cifNotificationsPrefix 1 }

cifNotification2 NOTIFICATION-TYPE
    OBJECTS { 
              cif2-source-ifc, 
              cif2-source-dlci 
            }
    STATUS current
    DESCRIPTION
        "Notification of Event CIF.2

        Message: 'Frame received to be deciphered on interface $1, dlci $2'

        Parameters list:
              $1: cif2-source-ifc
              $2: cif2-source-dlci

        This message is generated for each request of deciphering a frame."
    ::= { cifNotificationsPrefix 2 }

cifNotification3 NOTIFICATION-TYPE
    OBJECTS { 
              cif3-dest-ifc, 
              cif3-dest-dlci 
            }
    STATUS current
    DESCRIPTION
        "Notification of Event CIF.3

        Message: 'Ciphered frame transmitted on interface $1, dlci $2'

        Parameters list:
              $1: cif3-dest-ifc
              $2: cif3-dest-dlci

        This message is generated for each ciphered frame that is transmitted."
    ::= { cifNotificationsPrefix 3 }

cifNotification4 NOTIFICATION-TYPE
    OBJECTS { 
              cif4-dest-ifc, 
              cif4-dest-dlci 
            }
    STATUS current
    DESCRIPTION
        "Notification of Event CIF.4

        Message: 'Deciphered frame transmitted on interface $1, dlci $2'

        Parameters list:
              $1: cif4-dest-ifc
              $2: cif4-dest-dlci

        This message is generated for each deciphered frame that is transmitted."
    ::= { cifNotificationsPrefix 4 }

cifNotification5 NOTIFICATION-TYPE
    OBJECTS { 
              cif5-dest-ifc, 
              cif5-dest-dlci 
            }
    STATUS current
    DESCRIPTION
        "Notification of Event CIF.5

        Message: 'Bypass frame transmitted on interface $1, dlci $2'

        Parameters list:
              $1: cif5-dest-ifc
              $2: cif5-dest-dlci

        This message is generated for each bypass frame that is transmitted."
    ::= { cifNotificationsPrefix 5 }

cifNotification6 NOTIFICATION-TYPE
    OBJECTS { 
              cif6-dest-ifc, 
              cif6-dest-dlci 
            }
    STATUS current
    DESCRIPTION
        "Notification of Event CIF.6

        Message: 'Deciphered frame transmitted using default key on interface $1, dlci $2'

        Parameters list:
              $1: cif6-dest-ifc
              $2: cif6-dest-dlci

        This message is generated for each deciphered frame using default key."
    ::= { cifNotificationsPrefix 6 }

cifNotification7 NOTIFICATION-TYPE
    OBJECTS { 
              cif7-source-ifc, 
              cif7-source-dlci 
            }
    STATUS current
    DESCRIPTION
        "Notification of Event CIF.7

        Message: 'Received bad ciphered frame on interface $1, dlci $2'

        Parameters list:
              $1: cif7-source-ifc
              $2: cif7-source-dlci

        This message is generated for each frame that arrives bad ciphered."
    ::= { cifNotificationsPrefix 7 }

cifNotification8 NOTIFICATION-TYPE
    OBJECTS { 
              cif8-source-ifc, 
              cif8-source-dlci 
            }
    STATUS current
    DESCRIPTION
        "Notification of Event CIF.8

        Message: 'Received frame on interface $1, dlci $2 discarded'

        Parameters list:
              $1: cif8-source-ifc
              $2: cif8-source-dlci

        This message is generated for each discarded frame."
    ::= { cifNotificationsPrefix 8 }

cifNotification9 NOTIFICATION-TYPE
    OBJECTS { 
              cif9-source-ifc, 
              cif9-source-dlci 
            }
    STATUS current
    DESCRIPTION
        "Notification of Event CIF.9

        Message: 'Error on ciphering card: received frame on interface $1, dlci $2 discarded'

        Parameters list:
              $1: cif9-source-ifc
              $2: cif9-source-dlci

        This message is generated for each discarded frame due to an error on
        ciphering card."
    ::= { cifNotificationsPrefix 9 }

cifNotification10 NOTIFICATION-TYPE
    STATUS current
    DESCRIPTION
        "Notification of Event CIF.10

        Message: 'Ciphering card TS-288 cannot be detected or is not present'

        This message is generated when ciphering card TS-288 cannot be detected
        or is not present."
    ::= { cifNotificationsPrefix 10 }

cifNotification11 NOTIFICATION-TYPE
    STATUS current
    DESCRIPTION
        "Notification of Event CIF.11

        Message: 'Ciphering card TM-184 cannot be detected or is not present.'

        This message is generated when ciphering card TM-184 cannot be detected
        or is not present."
    ::= { cifNotificationsPrefix 11 }

cifNotification12 NOTIFICATION-TYPE
    STATUS current
    DESCRIPTION
        "Notification of Event CIF.12

        Message: 'Error downloading ciphering program on TS-288 card'

        This message is generated when ciphering program cannot be downloaded
        on TS-288 card."
    ::= { cifNotificationsPrefix 12 }

cifNotification13 NOTIFICATION-TYPE
    STATUS current
    DESCRIPTION
        "Notification of Event CIF.13

        Message: 'Error downloading test program on TM-184 card'

        This message is generated when test program cannot be downloaded on
        TM-184 card."
    ::= { cifNotificationsPrefix 13 }

cifNotification14 NOTIFICATION-TYPE
    STATUS current
    DESCRIPTION
        "Notification of Event CIF.14

        Message: 'TM-184 RAM test not passed'

        This message is generated when DSP on TM-184 card cannnot access to RAM."
    ::= { cifNotificationsPrefix 14 }

cifNotification15 NOTIFICATION-TYPE
    STATUS current
    DESCRIPTION
        "Notification of Event CIF.15

        Message: 'TM-184 COMMON MEMORY test not passed'

        This message is generated when an error has occurred while performing
        COMMON MEMORY test on TM-184 card."
    ::= { cifNotificationsPrefix 15 }

cifNotification16 NOTIFICATION-TYPE
    STATUS current
    DESCRIPTION
        "Notification of Event CIF.16

        Message: 'Error downloading ciphering program on TM-184 card'

        This message is generated when ciphering program cannot be downloaded
        on TM-184 card."
    ::= { cifNotificationsPrefix 16 }

cifNotification17 NOTIFICATION-TYPE
    STATUS current
    DESCRIPTION
        "Notification of Event CIF.17

        Message: 'Error awaiting answer to a high-priority command'

        This message is generated when awaiting answer to a high-priority
        command and too much time has passed."
    ::= { cifNotificationsPrefix 17 }

cifNotification18 NOTIFICATION-TYPE
    STATUS current
    DESCRIPTION
        "Notification of Event CIF.18

        Message: 'Error awaiting answer to a non high-priority command'

        This message is generated when awaiting answer to a non high-priority
        command and too much time has passed."
    ::= { cifNotificationsPrefix 18 }

cifNotification19 NOTIFICATION-TYPE
    OBJECTS { 
              cif19-source-ifc, 
              cif19-source-dlci 
            }
    STATUS current
    DESCRIPTION
        "Notification of Event CIF.19

        Message: 'Backup frame received to be ciphered on interface $1, dlci $2'

        Parameters list:
              $1: cif19-source-ifc
              $2: cif19-source-dlci

        This message is generated for each request of ciphering a backup frame."
    ::= { cifNotificationsPrefix 19 }

cifNotification20 NOTIFICATION-TYPE
    OBJECTS { 
              cif20-source-ifc, 
              cif20-source-dlci 
            }
    STATUS current
    DESCRIPTION
        "Notification of Event CIF.20

        Message: 'Backup frame received to be deciphered on interface $1, dlci $2'

        Parameters list:
              $1: cif20-source-ifc
              $2: cif20-source-dlci

        This message is generated for each request of deciphering
        a backup frame."
    ::= { cifNotificationsPrefix 20 }

cifNotification21 NOTIFICATION-TYPE
    STATUS current
    DESCRIPTION
        "Notification of Event CIF.21

        Message: 'Overload, frame discarded'

        This message is generated when received traffic is too high or it could
        not be sent because internal buffers are full. Usually this situation
        takes place when line rates in both ends are not equal."
    ::= { cifNotificationsPrefix 21 }

cifNotification22 NOTIFICATION-TYPE
    OBJECTS { 
              cif22-source-ifc, 
              cif22-source-dlci 
            }
    STATUS current
    DESCRIPTION
        "Notification of Event CIF.22

        Message: 'Rx frame is too long on interface $1, dlci $2'

        Parameters list:
              $1: cif22-source-ifc
              $2: cif22-source-dlci

        This message is generated for each too long received frame."
    ::= { cifNotificationsPrefix 22 }

cifNotification23 NOTIFICATION-TYPE
    OBJECTS { 
              cif23-source-ifc, 
              cif23-source-dlci 
            }
    STATUS current
    DESCRIPTION
        "Notification of Event CIF.23

        Message: 'Received frame cannot be sent because the line is not active, interface $1, dlci $2'

        Parameters list:
              $1: cif23-source-ifc
              $2: cif23-source-dlci

        This message is generated for each received frame which cannot be sent
        because the line is not active."
    ::= { cifNotificationsPrefix 23 }

cifNotification24 NOTIFICATION-TYPE
    STATUS current
    DESCRIPTION
        "Notification of Event CIF.24

        Message: 'Too much time awaiting for ciphering card release'

        This message is generated when too much time has passed while awaiting
        ciphering card release."
    ::= { cifNotificationsPrefix 24 }

cifNotification25 NOTIFICATION-TYPE
    OBJECTS { 
              cif25-called-nri, 
              cif25-calling-nri,
              cif25-in-tables,
              cif25-key-change 
            }
    STATUS current
    DESCRIPTION
        "Notification of Event CIF.25

        Message: 'A call request is received in the ciphering module. Called:$1 Calling:$2 In-tables:$3 Key-change:$4'

        Parameters list:
              $1: cif25-called-nri
              $2: cif25-calling-nri
              $3: cif25-in-tables
              $4: cif25-key-change

        This message is generated when a call request is received
        in the ciphering module."
    ::= { cifNotificationsPrefix 25 }

cifNotification26 NOTIFICATION-TYPE
    STATUS current
    DESCRIPTION
        "Notification of Event CIF.26

        Message: 'No size found in the configuration file. Default size is set instead.'

        No size found in the configuration file. Default size is set instead."
    ::= { cifNotificationsPrefix 26 }

cifNotification27 NOTIFICATION-TYPE
    STATUS current
    DESCRIPTION
        "Notification of Event CIF.27

        Message: 'Error while allocating memory with 'als' for ciphering queue'

        Error while allocating memory with 'als' for filling
        the generic ciphering queues."
    ::= { cifNotificationsPrefix 27 }

cifNotification28 NOTIFICATION-TYPE
    STATUS current
    DESCRIPTION
        "Notification of Event CIF.28

        Message: 'Error while checking algorithm DES CBC Standard'

        Error while checking algorithm DES CBC Standard."
    ::= { cifNotificationsPrefix 28 }

cifNotification29 NOTIFICATION-TYPE
    STATUS current
    DESCRIPTION
        "Notification of Event CIF.29

        Message: 'Successful checking of the 3DES, DES, CBC Standard algorithm with ciphering card'

        Successful checking of the Standard comands used by the ciphering card."
    ::= { cifNotificationsPrefix 29 }

cifNotification30 NOTIFICATION-TYPE
    OBJECTS { 
              cif30-source-ifc, 
              cif30-SA-spi 
            }
    STATUS current
    DESCRIPTION
        "Notification of Event CIF.30

        Message: 'Received packet to cipher from IPSEC, interface $1, spi $2'

        Parameters list:
              $1: cif30-source-ifc
              $2: cif30-SA-spi

        Message generated for each IPSEC packet sent to the HW ciphering module."
    ::= { cifNotificationsPrefix 30 }

cifNotification31 NOTIFICATION-TYPE
    OBJECTS { 
              cif31-source-ifc, 
              cif31-SA-spi 
            }
    STATUS current
    DESCRIPTION
        "Notification of Event CIF.31

        Message: 'Received packet to decipher from IPSEC, interface $1, spi $2'

        Parameters list:
              $1: cif31-source-ifc
              $2: cif31-SA-spi

        Message generated for each IPSEC packet sent to the HW ciphering module."
    ::= { cifNotificationsPrefix 31 }

cifNotification32 NOTIFICATION-TYPE
    OBJECTS { 
              cif32-source-ifc, 
              cif32-SA-spi 
            }
    STATUS current
    DESCRIPTION
        "Notification of Event CIF.32

        Message: 'Packet is sent to the ciph card from IPSEC, interface $1, spi $2'

        Parameters list:
              $1: cif32-source-ifc
              $2: cif32-SA-spi

        Message generated for each IPSEC packet sent to the HW ciphering card."
    ::= { cifNotificationsPrefix 32 }

cifNotification33 NOTIFICATION-TYPE
    OBJECTS { 
              cif33-source-ifc, 
              cif33-SA-spi 
            }
    STATUS current
    DESCRIPTION
        "Notification of Event CIF.33

        Message: 'Packet is sent to the deciph card from IPSEC, interface $1, spi $2'

        Parameters list:
              $1: cif33-source-ifc
              $2: cif33-SA-spi

        Message generated for each IPSEC packet sent to the HW ciphering card."
    ::= { cifNotificationsPrefix 33 }

cifNotification34 NOTIFICATION-TYPE
    STATUS current
    DESCRIPTION
        "Notification of Event CIF.34

        Message: 'Successful checking of the 3DES, DES, CBC Standard software algorithm'

        Successful checking of the Standard comands implemented by software."
    ::= { cifNotificationsPrefix 34 }


END
