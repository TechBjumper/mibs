-- file automatically created


TELDAT-TRAP-ISDN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


isdnTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ISDN event subsystem."
    REVISION "201401200930Z"
    DESCRIPTION "Initial implementation"
        ::= { telEventTraps 99 }


isdnEventsGroup	OBJECT IDENTIFIER	::= { isdnTrapsMIB 1 }

isdnNotifications	OBJECT IDENTIFIER	::= { isdnTrapsMIB 2 }
isdnNotificationsPrefix	OBJECT IDENTIFIER	::= { isdnNotifications 0 }

isdnEventObjects1 OBJECT-IDENTITY
    STATUS current
    DESCRIPTION
        "Event ISDN.1
        ALERTING message received for the mentioned Q931 conversation."
    ::= { isdnEventsGroup 1 }

isdn1-call-ref OBJECT-TYPE
    SYNTAX Integer32
    MAX-ACCESS accessible-for-notify
    STATUS current
    DESCRIPTION
        "Parameter 'call-ref' in event ISDN.1"
    ::= { isdnEventObjects1 1 }

isdn1-interface OBJECT-TYPE
    SYNTAX DisplayString
    MAX-ACCESS accessible-for-notify
    STATUS current
    DESCRIPTION
        "Parameter 'interface' in event ISDN.1"
    ::= { isdnEventObjects1 2 }

isdnEventObjects2 OBJECT-IDENTITY
    STATUS current
    DESCRIPTION
        "Event ISDN.2
        CONN ACK message received for the mentioned Q931 conversation."
    ::= { isdnEventsGroup 2 }

isdn2-call-ref OBJECT-TYPE
    SYNTAX Integer32
    MAX-ACCESS accessible-for-notify
    STATUS current
    DESCRIPTION
        "Parameter 'call-ref' in event ISDN.2"
    ::= { isdnEventObjects2 1 }

isdn2-interface OBJECT-TYPE
    SYNTAX DisplayString
    MAX-ACCESS accessible-for-notify
    STATUS current
    DESCRIPTION
        "Parameter 'interface' in event ISDN.2"
    ::= { isdnEventObjects2 2 }

isdnEventObjects3 OBJECT-IDENTITY
    STATUS current
    DESCRIPTION
        "Event ISDN.3
        CONN message received for the mentioned Q931 conversation."
    ::= { isdnEventsGroup 3 }

isdn3-call-ref OBJECT-TYPE
    SYNTAX Integer32
    MAX-ACCESS accessible-for-notify
    STATUS current
    DESCRIPTION
        "Parameter 'call-ref' in event ISDN.3"
    ::= { isdnEventObjects3 1 }

isdn3-interface OBJECT-TYPE
    SYNTAX DisplayString
    MAX-ACCESS accessible-for-notify
    STATUS current
    DESCRIPTION
        "Parameter 'interface' in event ISDN.3"
    ::= { isdnEventObjects3 2 }

isdnEventObjects4 OBJECT-IDENTITY
    STATUS current
    DESCRIPTION
        "Event ISDN.4
        CALL PROC message received for the mentioned Q931 conversation."
    ::= { isdnEventsGroup 4 }

isdn4-call-ref OBJECT-TYPE
    SYNTAX Integer32
    MAX-ACCESS accessible-for-notify
    STATUS current
    DESCRIPTION
        "Parameter 'call-ref' in event ISDN.4"
    ::= { isdnEventObjects4 1 }

isdn4-chan OBJECT-TYPE
    SYNTAX DisplayString
    MAX-ACCESS accessible-for-notify
    STATUS current
    DESCRIPTION
        "Parameter 'chan' in event ISDN.4"
    ::= { isdnEventObjects4 2 }

isdn4-interface OBJECT-TYPE
    SYNTAX DisplayString
    MAX-ACCESS accessible-for-notify
    STATUS current
    DESCRIPTION
        "Parameter 'interface' in event ISDN.4"
    ::= { isdnEventObjects4 3 }

isdnEventObjects5 OBJECT-IDENTITY
    STATUS current
    DESCRIPTION
        "Event ISDN.5
        DISC message received for the mentioned Q931 conversation."
    ::= { isdnEventsGroup 5 }

isdn5-call-ref OBJECT-TYPE
    SYNTAX Integer32
    MAX-ACCESS accessible-for-notify
    STATUS current
    DESCRIPTION
        "Parameter 'call-ref' in event ISDN.5"
    ::= { isdnEventObjects5 1 }

isdn5-cause OBJECT-TYPE
    SYNTAX Integer32
    MAX-ACCESS accessible-for-notify
    STATUS current
    DESCRIPTION
        "Parameter 'cause' in event ISDN.5"
    ::= { isdnEventObjects5 2 }

isdn5-cost OBJECT-TYPE
    SYNTAX Integer32
    MAX-ACCESS accessible-for-notify
    STATUS current
    DESCRIPTION
        "Parameter 'cost' in event ISDN.5"
    ::= { isdnEventObjects5 3 }

isdn5-interface OBJECT-TYPE
    SYNTAX DisplayString
    MAX-ACCESS accessible-for-notify
    STATUS current
    DESCRIPTION
        "Parameter 'interface' in event ISDN.5"
    ::= { isdnEventObjects5 4 }

isdnEventObjects6 OBJECT-IDENTITY
    STATUS current
    DESCRIPTION
        "Event ISDN.6
        INFO message received for the mentioned Q931 conversation."
    ::= { isdnEventsGroup 6 }

isdn6-call-ref OBJECT-TYPE
    SYNTAX Integer32
    MAX-ACCESS accessible-for-notify
    STATUS current
    DESCRIPTION
        "Parameter 'call-ref' in event ISDN.6"
    ::= { isdnEventObjects6 1 }

isdn6-interface OBJECT-TYPE
    SYNTAX DisplayString
    MAX-ACCESS accessible-for-notify
    STATUS current
    DESCRIPTION
        "Parameter 'interface' in event ISDN.6"
    ::= { isdnEventObjects6 2 }

isdnEventObjects7 OBJECT-IDENTITY
    STATUS current
    DESCRIPTION
        "Event ISDN.7
        PROGR message received for the mentioned Q931 conversation."
    ::= { isdnEventsGroup 7 }

isdn7-call-ref OBJECT-TYPE
    SYNTAX Integer32
    MAX-ACCESS accessible-for-notify
    STATUS current
    DESCRIPTION
        "Parameter 'call-ref' in event ISDN.7"
    ::= { isdnEventObjects7 1 }

isdn7-interface OBJECT-TYPE
    SYNTAX DisplayString
    MAX-ACCESS accessible-for-notify
    STATUS current
    DESCRIPTION
        "Parameter 'interface' in event ISDN.7"
    ::= { isdnEventObjects7 2 }

isdnEventObjects8 OBJECT-IDENTITY
    STATUS current
    DESCRIPTION
        "Event ISDN.8
        RELEASE message received for the mentioned Q931 conversation."
    ::= { isdnEventsGroup 8 }

isdn8-call-ref OBJECT-TYPE
    SYNTAX Integer32
    MAX-ACCESS accessible-for-notify
    STATUS current
    DESCRIPTION
        "Parameter 'call-ref' in event ISDN.8"
    ::= { isdnEventObjects8 1 }

isdn8-cause OBJECT-TYPE
    SYNTAX Integer32
    MAX-ACCESS accessible-for-notify
    STATUS current
    DESCRIPTION
        "Parameter 'cause' in event ISDN.8"
    ::= { isdnEventObjects8 2 }

isdn8-cost OBJECT-TYPE
    SYNTAX Integer32
    MAX-ACCESS accessible-for-notify
    STATUS current
    DESCRIPTION
        "Parameter 'cost' in event ISDN.8"
    ::= { isdnEventObjects8 3 }

isdn8-interface OBJECT-TYPE
    SYNTAX DisplayString
    MAX-ACCESS accessible-for-notify
    STATUS current
    DESCRIPTION
        "Parameter 'interface' in event ISDN.8"
    ::= { isdnEventObjects8 4 }

isdnEventObjects9 OBJECT-IDENTITY
    STATUS current
    DESCRIPTION
        "Event ISDN.9
        REL COMPLETE message received for the mentioned Q931 conversation."
    ::= { isdnEventsGroup 9 }

isdn9-call-ref OBJECT-TYPE
    SYNTAX Integer32
    MAX-ACCESS accessible-for-notify
    STATUS current
    DESCRIPTION
        "Parameter 'call-ref' in event ISDN.9"
    ::= { isdnEventObjects9 1 }

isdn9-cause OBJECT-TYPE
    SYNTAX Integer32
    MAX-ACCESS accessible-for-notify
    STATUS current
    DESCRIPTION
        "Parameter 'cause' in event ISDN.9"
    ::= { isdnEventObjects9 2 }

isdn9-cost OBJECT-TYPE
    SYNTAX Integer32
    MAX-ACCESS accessible-for-notify
    STATUS current
    DESCRIPTION
        "Parameter 'cost' in event ISDN.9"
    ::= { isdnEventObjects9 3 }

isdn9-interface OBJECT-TYPE
    SYNTAX DisplayString
    MAX-ACCESS accessible-for-notify
    STATUS current
    DESCRIPTION
        "Parameter 'interface' in event ISDN.9"
    ::= { isdnEventObjects9 4 }

isdnEventObjects10 OBJECT-IDENTITY
    STATUS current
    DESCRIPTION
        "Event ISDN.10
        STATUS message received for the mentioned Q931 conversation."
    ::= { isdnEventsGroup 10 }

isdn10-call-ref OBJECT-TYPE
    SYNTAX Integer32
    MAX-ACCESS accessible-for-notify
    STATUS current
    DESCRIPTION
        "Parameter 'call-ref' in event ISDN.10"
    ::= { isdnEventObjects10 1 }

isdn10-interface OBJECT-TYPE
    SYNTAX DisplayString
    MAX-ACCESS accessible-for-notify
    STATUS current
    DESCRIPTION
        "Parameter 'interface' in event ISDN.10"
    ::= { isdnEventObjects10 2 }

isdnEventObjects11 OBJECT-IDENTITY
    STATUS current
    DESCRIPTION
        "Event ISDN.11
        SETUP message received for the mentioned Q931 conversation."
    ::= { isdnEventsGroup 11 }

isdn11-call-ref OBJECT-TYPE
    SYNTAX Integer32
    MAX-ACCESS accessible-for-notify
    STATUS current
    DESCRIPTION
        "Parameter 'call-ref' in event ISDN.11"
    ::= { isdnEventObjects11 1 }

isdn11-chan OBJECT-TYPE
    SYNTAX Integer32
    MAX-ACCESS accessible-for-notify
    STATUS current
    DESCRIPTION
        "Parameter 'chan' in event ISDN.11"
    ::= { isdnEventObjects11 2 }

isdn11-caller-num OBJECT-TYPE
    SYNTAX DisplayString
    MAX-ACCESS accessible-for-notify
    STATUS current
    DESCRIPTION
        "Parameter 'caller-num' in event ISDN.11"
    ::= { isdnEventObjects11 3 }

isdn11-interface OBJECT-TYPE
    SYNTAX DisplayString
    MAX-ACCESS accessible-for-notify
    STATUS current
    DESCRIPTION
        "Parameter 'interface' in event ISDN.11"
    ::= { isdnEventObjects11 4 }

isdnEventObjects12 OBJECT-IDENTITY
    STATUS current
    DESCRIPTION
        "Event ISDN.12
        An incoming call has been established."
    ::= { isdnEventsGroup 12 }

isdn12-called OBJECT-TYPE
    SYNTAX DisplayString
    MAX-ACCESS accessible-for-notify
    STATUS current
    DESCRIPTION
        "Parameter 'called' in event ISDN.12"
    ::= { isdnEventObjects12 1 }

isdn12-caller OBJECT-TYPE
    SYNTAX DisplayString
    MAX-ACCESS accessible-for-notify
    STATUS current
    DESCRIPTION
        "Parameter 'caller' in event ISDN.12"
    ::= { isdnEventObjects12 2 }

isdn12-interface OBJECT-TYPE
    SYNTAX DisplayString
    MAX-ACCESS accessible-for-notify
    STATUS current
    DESCRIPTION
        "Parameter 'interface' in event ISDN.12"
    ::= { isdnEventObjects12 3 }

isdnEventObjects13 OBJECT-IDENTITY
    STATUS current
    DESCRIPTION
        "Event ISDN.13
        An outgoing call has been established."
    ::= { isdnEventsGroup 13 }

isdn13-called OBJECT-TYPE
    SYNTAX DisplayString
    MAX-ACCESS accessible-for-notify
    STATUS current
    DESCRIPTION
        "Parameter 'called' in event ISDN.13"
    ::= { isdnEventObjects13 1 }

isdn13-caller OBJECT-TYPE
    SYNTAX DisplayString
    MAX-ACCESS accessible-for-notify
    STATUS current
    DESCRIPTION
        "Parameter 'caller' in event ISDN.13"
    ::= { isdnEventObjects13 2 }

isdn13-interface OBJECT-TYPE
    SYNTAX DisplayString
    MAX-ACCESS accessible-for-notify
    STATUS current
    DESCRIPTION
        "Parameter 'interface' in event ISDN.13"
    ::= { isdnEventObjects13 3 }

isdnEventObjects14 OBJECT-IDENTITY
    STATUS current
    DESCRIPTION
        "Event ISDN.14
        An incoming call has been released."
    ::= { isdnEventsGroup 14 }

isdn14-called OBJECT-TYPE
    SYNTAX DisplayString
    MAX-ACCESS accessible-for-notify
    STATUS current
    DESCRIPTION
        "Parameter 'called' in event ISDN.14"
    ::= { isdnEventObjects14 1 }

isdn14-caller OBJECT-TYPE
    SYNTAX DisplayString
    MAX-ACCESS accessible-for-notify
    STATUS current
    DESCRIPTION
        "Parameter 'caller' in event ISDN.14"
    ::= { isdnEventObjects14 2 }

isdn14-interface OBJECT-TYPE
    SYNTAX DisplayString
    MAX-ACCESS accessible-for-notify
    STATUS current
    DESCRIPTION
        "Parameter 'interface' in event ISDN.14"
    ::= { isdnEventObjects14 3 }

isdnEventObjects15 OBJECT-IDENTITY
    STATUS current
    DESCRIPTION
        "Event ISDN.15
        An outgoing call has been released."
    ::= { isdnEventsGroup 15 }

isdn15-called OBJECT-TYPE
    SYNTAX DisplayString
    MAX-ACCESS accessible-for-notify
    STATUS current
    DESCRIPTION
        "Parameter 'called' in event ISDN.15"
    ::= { isdnEventObjects15 1 }

isdn15-caller OBJECT-TYPE
    SYNTAX DisplayString
    MAX-ACCESS accessible-for-notify
    STATUS current
    DESCRIPTION
        "Parameter 'caller' in event ISDN.15"
    ::= { isdnEventObjects15 2 }

isdn15-interface OBJECT-TYPE
    SYNTAX DisplayString
    MAX-ACCESS accessible-for-notify
    STATUS current
    DESCRIPTION
        "Parameter 'interface' in event ISDN.15"
    ::= { isdnEventObjects15 3 }

isdnEventObjects16 OBJECT-IDENTITY
    STATUS current
    DESCRIPTION
        "Event ISDN.16
        CONN message transmitted for the mentioned Q931 conversation."
    ::= { isdnEventsGroup 16 }

isdn16-call-ref OBJECT-TYPE
    SYNTAX Integer32
    MAX-ACCESS accessible-for-notify
    STATUS current
    DESCRIPTION
        "Parameter 'call-ref' in event ISDN.16"
    ::= { isdnEventObjects16 1 }

isdn16-chan OBJECT-TYPE
    SYNTAX Integer32
    MAX-ACCESS accessible-for-notify
    STATUS current
    DESCRIPTION
        "Parameter 'chan' in event ISDN.16"
    ::= { isdnEventObjects16 2 }

isdn16-interface OBJECT-TYPE
    SYNTAX DisplayString
    MAX-ACCESS accessible-for-notify
    STATUS current
    DESCRIPTION
        "Parameter 'interface' in event ISDN.16"
    ::= { isdnEventObjects16 3 }

isdnEventObjects17 OBJECT-IDENTITY
    STATUS current
    DESCRIPTION
        "Event ISDN.17
        CONN ACK message transmitted for the mentioned Q931 conversation."
    ::= { isdnEventsGroup 17 }

isdn17-call-ref OBJECT-TYPE
    SYNTAX Integer32
    MAX-ACCESS accessible-for-notify
    STATUS current
    DESCRIPTION
        "Parameter 'call-ref' in event ISDN.17"
    ::= { isdnEventObjects17 1 }

isdn17-interface OBJECT-TYPE
    SYNTAX DisplayString
    MAX-ACCESS accessible-for-notify
    STATUS current
    DESCRIPTION
        "Parameter 'interface' in event ISDN.17"
    ::= { isdnEventObjects17 2 }

isdnEventObjects18 OBJECT-IDENTITY
    STATUS current
    DESCRIPTION
        "Event ISDN.18
        DISC message transmitted for the mentioned Q931 conversation."
    ::= { isdnEventsGroup 18 }

isdn18-call-ref OBJECT-TYPE
    SYNTAX Integer32
    MAX-ACCESS accessible-for-notify
    STATUS current
    DESCRIPTION
        "Parameter 'call-ref' in event ISDN.18"
    ::= { isdnEventObjects18 1 }

isdn18-cause OBJECT-TYPE
    SYNTAX Integer32
    MAX-ACCESS accessible-for-notify
    STATUS current
    DESCRIPTION
        "Parameter 'cause' in event ISDN.18"
    ::= { isdnEventObjects18 2 }

isdn18-interface OBJECT-TYPE
    SYNTAX DisplayString
    MAX-ACCESS accessible-for-notify
    STATUS current
    DESCRIPTION
        "Parameter 'interface' in event ISDN.18"
    ::= { isdnEventObjects18 3 }

isdnEventObjects19 OBJECT-IDENTITY
    STATUS current
    DESCRIPTION
        "Event ISDN.19
        REL message transmitted for the mentioned Q931 conversation."
    ::= { isdnEventsGroup 19 }

isdn19-call-ref OBJECT-TYPE
    SYNTAX Integer32
    MAX-ACCESS accessible-for-notify
    STATUS current
    DESCRIPTION
        "Parameter 'call-ref' in event ISDN.19"
    ::= { isdnEventObjects19 1 }

isdn19-cause OBJECT-TYPE
    SYNTAX Integer32
    MAX-ACCESS accessible-for-notify
    STATUS current
    DESCRIPTION
        "Parameter 'cause' in event ISDN.19"
    ::= { isdnEventObjects19 2 }

isdn19-interface OBJECT-TYPE
    SYNTAX DisplayString
    MAX-ACCESS accessible-for-notify
    STATUS current
    DESCRIPTION
        "Parameter 'interface' in event ISDN.19"
    ::= { isdnEventObjects19 3 }

isdnEventObjects20 OBJECT-IDENTITY
    STATUS current
    DESCRIPTION
        "Event ISDN.20
        REL COM message transmitted for the mentioned Q931 conversation."
    ::= { isdnEventsGroup 20 }

isdn20-call-ref OBJECT-TYPE
    SYNTAX Integer32
    MAX-ACCESS accessible-for-notify
    STATUS current
    DESCRIPTION
        "Parameter 'call-ref' in event ISDN.20"
    ::= { isdnEventObjects20 1 }

isdn20-cause OBJECT-TYPE
    SYNTAX Integer32
    MAX-ACCESS accessible-for-notify
    STATUS current
    DESCRIPTION
        "Parameter 'cause' in event ISDN.20"
    ::= { isdnEventObjects20 2 }

isdn20-interface OBJECT-TYPE
    SYNTAX DisplayString
    MAX-ACCESS accessible-for-notify
    STATUS current
    DESCRIPTION
        "Parameter 'interface' in event ISDN.20"
    ::= { isdnEventObjects20 3 }

isdnEventObjects21 OBJECT-IDENTITY
    STATUS current
    DESCRIPTION
        "Event ISDN.21
        SETUP message transmitted for the mentioned Q931 conversation."
    ::= { isdnEventsGroup 21 }

isdn21-call-ref OBJECT-TYPE
    SYNTAX Integer32
    MAX-ACCESS accessible-for-notify
    STATUS current
    DESCRIPTION
        "Parameter 'call-ref' in event ISDN.21"
    ::= { isdnEventObjects21 1 }

isdn21-called-num OBJECT-TYPE
    SYNTAX DisplayString
    MAX-ACCESS accessible-for-notify
    STATUS current
    DESCRIPTION
        "Parameter 'called-num' in event ISDN.21"
    ::= { isdnEventObjects21 2 }

isdn21-interface OBJECT-TYPE
    SYNTAX DisplayString
    MAX-ACCESS accessible-for-notify
    STATUS current
    DESCRIPTION
        "Parameter 'interface' in event ISDN.21"
    ::= { isdnEventObjects21 3 }

isdnEventObjects22 OBJECT-IDENTITY
    STATUS current
    DESCRIPTION
        "Event ISDN.22
        STATUS message transmitted for the mentioned Q931 conversation."
    ::= { isdnEventsGroup 22 }

isdn22-call-ref OBJECT-TYPE
    SYNTAX Integer32
    MAX-ACCESS accessible-for-notify
    STATUS current
    DESCRIPTION
        "Parameter 'call-ref' in event ISDN.22"
    ::= { isdnEventObjects22 1 }

isdn22-status OBJECT-TYPE
    SYNTAX Integer32
    MAX-ACCESS accessible-for-notify
    STATUS current
    DESCRIPTION
        "Parameter 'status' in event ISDN.22"
    ::= { isdnEventObjects22 2 }

isdn22-interface OBJECT-TYPE
    SYNTAX DisplayString
    MAX-ACCESS accessible-for-notify
    STATUS current
    DESCRIPTION
        "Parameter 'interface' in event ISDN.22"
    ::= { isdnEventObjects22 3 }

isdnEventObjects23 OBJECT-IDENTITY
    STATUS current
    DESCRIPTION
        "Event ISDN.23
        message transmitted contents."
    ::= { isdnEventsGroup 23 }

isdn23-frame-tx OBJECT-TYPE
    SYNTAX DisplayString
    MAX-ACCESS accessible-for-notify
    STATUS current
    DESCRIPTION
        "Parameter 'frame-tx' in event ISDN.23"
    ::= { isdnEventObjects23 1 }

isdn23-interface OBJECT-TYPE
    SYNTAX DisplayString
    MAX-ACCESS accessible-for-notify
    STATUS current
    DESCRIPTION
        "Parameter 'interface' in event ISDN.23"
    ::= { isdnEventObjects23 2 }

isdnEventObjects24 OBJECT-IDENTITY
    STATUS current
    DESCRIPTION
        "Event ISDN.24
        message received contents."
    ::= { isdnEventsGroup 24 }

isdn24-frame-rx OBJECT-TYPE
    SYNTAX DisplayString
    MAX-ACCESS accessible-for-notify
    STATUS current
    DESCRIPTION
        "Parameter 'frame-rx' in event ISDN.24"
    ::= { isdnEventObjects24 1 }

isdn24-interface OBJECT-TYPE
    SYNTAX DisplayString
    MAX-ACCESS accessible-for-notify
    STATUS current
    DESCRIPTION
        "Parameter 'interface' in event ISDN.24"
    ::= { isdnEventObjects24 2 }

isdnEventObjects25 OBJECT-IDENTITY
    STATUS current
    DESCRIPTION
        "Event ISDN.25
        RESTART message received."
    ::= { isdnEventsGroup 25 }

isdn25-restart-ind OBJECT-TYPE
    SYNTAX Integer32
    MAX-ACCESS accessible-for-notify
    STATUS current
    DESCRIPTION
        "Parameter 'restart-ind' in event ISDN.25"
    ::= { isdnEventObjects25 1 }

isdn25-channel-id OBJECT-TYPE
    SYNTAX DisplayString
    MAX-ACCESS accessible-for-notify
    STATUS current
    DESCRIPTION
        "Parameter 'channel-id' in event ISDN.25"
    ::= { isdnEventObjects25 2 }

isdn25-interface OBJECT-TYPE
    SYNTAX DisplayString
    MAX-ACCESS accessible-for-notify
    STATUS current
    DESCRIPTION
        "Parameter 'interface' in event ISDN.25"
    ::= { isdnEventObjects25 3 }

isdnEventObjects26 OBJECT-IDENTITY
    STATUS current
    DESCRIPTION
        "Event ISDN.26
        A RESTART ACK message has been transmitted."
    ::= { isdnEventsGroup 26 }

isdn26-interface OBJECT-TYPE
    SYNTAX DisplayString
    MAX-ACCESS accessible-for-notify
    STATUS current
    DESCRIPTION
        "Parameter 'interface' in event ISDN.26"
    ::= { isdnEventObjects26 1 }

isdnEventObjects27 OBJECT-IDENTITY
    STATUS current
    DESCRIPTION
        "Event ISDN.27
        An INFO message has been transmited in order to initialize SPID."
    ::= { isdnEventsGroup 27 }

isdn27-call-ref OBJECT-TYPE
    SYNTAX Integer32
    MAX-ACCESS accessible-for-notify
    STATUS current
    DESCRIPTION
        "Parameter 'call-ref' in event ISDN.27"
    ::= { isdnEventObjects27 1 }

isdn27-spid OBJECT-TYPE
    SYNTAX DisplayString
    MAX-ACCESS accessible-for-notify
    STATUS current
    DESCRIPTION
        "Parameter 'spid' in event ISDN.27"
    ::= { isdnEventObjects27 2 }

isdn27-interface OBJECT-TYPE
    SYNTAX DisplayString
    MAX-ACCESS accessible-for-notify
    STATUS current
    DESCRIPTION
        "Parameter 'interface' in event ISDN.27"
    ::= { isdnEventObjects27 3 }

isdnEventObjects28 OBJECT-IDENTITY
    STATUS current
    DESCRIPTION
        "Event ISDN.28
        SPEED is being sending to the network."
    ::= { isdnEventsGroup 28 }

isdn28-spid OBJECT-TYPE
    SYNTAX DisplayString
    MAX-ACCESS accessible-for-notify
    STATUS current
    DESCRIPTION
        "Parameter 'spid' in event ISDN.28"
    ::= { isdnEventObjects28 1 }

isdn28-interface OBJECT-TYPE
    SYNTAX DisplayString
    MAX-ACCESS accessible-for-notify
    STATUS current
    DESCRIPTION
        "Parameter 'interface' in event ISDN.28"
    ::= { isdnEventObjects28 2 }

isdnEventObjects29 OBJECT-IDENTITY
    STATUS current
    DESCRIPTION
        "Event ISDN.29
        An INFO message has been received acknowing successfully SPID initialize."
    ::= { isdnEventsGroup 29 }

isdn29-spid OBJECT-TYPE
    SYNTAX DisplayString
    MAX-ACCESS accessible-for-notify
    STATUS current
    DESCRIPTION
        "Parameter 'spid' in event ISDN.29"
    ::= { isdnEventObjects29 1 }

isdn29-interface OBJECT-TYPE
    SYNTAX DisplayString
    MAX-ACCESS accessible-for-notify
    STATUS current
    DESCRIPTION
        "Parameter 'interface' in event ISDN.29"
    ::= { isdnEventObjects29 2 }

isdnEventObjects30 OBJECT-IDENTITY
    STATUS current
    DESCRIPTION
        "Event ISDN.30
        An INFO message has been received with indicated cause."
    ::= { isdnEventsGroup 30 }

isdn30-spid OBJECT-TYPE
    SYNTAX DisplayString
    MAX-ACCESS accessible-for-notify
    STATUS current
    DESCRIPTION
        "Parameter 'spid' in event ISDN.30"
    ::= { isdnEventObjects30 1 }

isdn30-cause OBJECT-TYPE
    SYNTAX Integer32
    MAX-ACCESS accessible-for-notify
    STATUS current
    DESCRIPTION
        "Parameter 'cause' in event ISDN.30"
    ::= { isdnEventObjects30 2 }

isdn30-interface OBJECT-TYPE
    SYNTAX DisplayString
    MAX-ACCESS accessible-for-notify
    STATUS current
    DESCRIPTION
        "Parameter 'interface' in event ISDN.30"
    ::= { isdnEventObjects30 3 }

isdnEventObjects31 OBJECT-IDENTITY
    STATUS current
    DESCRIPTION
        "Event ISDN.31
        A CALL PROCEEDING message has been transmitted."
    ::= { isdnEventsGroup 31 }

isdn31-call-ref OBJECT-TYPE
    SYNTAX Integer32
    MAX-ACCESS accessible-for-notify
    STATUS current
    DESCRIPTION
        "Parameter 'call-ref' in event ISDN.31"
    ::= { isdnEventObjects31 1 }

isdn31-interface OBJECT-TYPE
    SYNTAX DisplayString
    MAX-ACCESS accessible-for-notify
    STATUS current
    DESCRIPTION
        "Parameter 'interface' in event ISDN.31"
    ::= { isdnEventObjects31 2 }

isdnEventObjects32 OBJECT-IDENTITY
    STATUS current
    DESCRIPTION
        "Event ISDN.32
        An ALERTING message has been transmitted."
    ::= { isdnEventsGroup 32 }

isdn32-call-ref OBJECT-TYPE
    SYNTAX Integer32
    MAX-ACCESS accessible-for-notify
    STATUS current
    DESCRIPTION
        "Parameter 'call-ref' in event ISDN.32"
    ::= { isdnEventObjects32 1 }

isdn32-interface OBJECT-TYPE
    SYNTAX DisplayString
    MAX-ACCESS accessible-for-notify
    STATUS current
    DESCRIPTION
        "Parameter 'interface' in event ISDN.32"
    ::= { isdnEventObjects32 2 }

isdnEventObjects33 OBJECT-IDENTITY
    STATUS current
    DESCRIPTION
        "Event ISDN.33
        A SETUP-ACK message has been transmitted."
    ::= { isdnEventsGroup 33 }

isdn33-call-ref OBJECT-TYPE
    SYNTAX Integer32
    MAX-ACCESS accessible-for-notify
    STATUS current
    DESCRIPTION
        "Parameter 'call-ref' in event ISDN.33"
    ::= { isdnEventObjects33 1 }

isdn33-interface OBJECT-TYPE
    SYNTAX DisplayString
    MAX-ACCESS accessible-for-notify
    STATUS current
    DESCRIPTION
        "Parameter 'interface' in event ISDN.33"
    ::= { isdnEventObjects33 2 }

isdnEventObjects34 OBJECT-IDENTITY
    STATUS current
    DESCRIPTION
        "Event ISDN.34
        SETUP ACK message received for the mentioned Q931 conversation."
    ::= { isdnEventsGroup 34 }

isdn34-call-ref OBJECT-TYPE
    SYNTAX Integer32
    MAX-ACCESS accessible-for-notify
    STATUS current
    DESCRIPTION
        "Parameter 'call-ref' in event ISDN.34"
    ::= { isdnEventObjects34 1 }

isdn34-interface OBJECT-TYPE
    SYNTAX DisplayString
    MAX-ACCESS accessible-for-notify
    STATUS current
    DESCRIPTION
        "Parameter 'interface' in event ISDN.34"
    ::= { isdnEventObjects34 2 }

isdnEventObjects35 OBJECT-IDENTITY
    STATUS current
    DESCRIPTION
        "Event ISDN.35
        FACILITY message received for the mentioned Q931 conversation."
    ::= { isdnEventsGroup 35 }

isdn35-call-ref OBJECT-TYPE
    SYNTAX Integer32
    MAX-ACCESS accessible-for-notify
    STATUS current
    DESCRIPTION
        "Parameter 'call-ref' in event ISDN.35"
    ::= { isdnEventObjects35 1 }

isdn35-interface OBJECT-TYPE
    SYNTAX DisplayString
    MAX-ACCESS accessible-for-notify
    STATUS current
    DESCRIPTION
        "Parameter 'interface' in event ISDN.35"
    ::= { isdnEventObjects35 2 }

isdnEventObjects36 OBJECT-IDENTITY
    STATUS current
    DESCRIPTION
        "Event ISDN.36
        NOTIFY message received for the mentioned Q931 conversation."
    ::= { isdnEventsGroup 36 }

isdn36-call-ref OBJECT-TYPE
    SYNTAX Integer32
    MAX-ACCESS accessible-for-notify
    STATUS current
    DESCRIPTION
        "Parameter 'call-ref' in event ISDN.36"
    ::= { isdnEventObjects36 1 }

isdn36-interface OBJECT-TYPE
    SYNTAX DisplayString
    MAX-ACCESS accessible-for-notify
    STATUS current
    DESCRIPTION
        "Parameter 'interface' in event ISDN.36"
    ::= { isdnEventObjects36 2 }

isdnEventObjects37 OBJECT-IDENTITY
    STATUS current
    DESCRIPTION
        "Event ISDN.37
        Display information elements."
    ::= { isdnEventsGroup 37 }

isdn37-sense OBJECT-TYPE
    SYNTAX DisplayString
    MAX-ACCESS accessible-for-notify
    STATUS current
    DESCRIPTION
        "Parameter 'sense' in event ISDN.37"
    ::= { isdnEventObjects37 1 }

isdn37-type OBJECT-TYPE
    SYNTAX DisplayString
    MAX-ACCESS accessible-for-notify
    STATUS current
    DESCRIPTION
        "Parameter 'type' in event ISDN.37"
    ::= { isdnEventObjects37 2 }

isdn37-length OBJECT-TYPE
    SYNTAX Integer32
    MAX-ACCESS accessible-for-notify
    STATUS current
    DESCRIPTION
        "Parameter 'length' in event ISDN.37"
    ::= { isdnEventObjects37 3 }

isdn37-data OBJECT-TYPE
    SYNTAX DisplayString
    MAX-ACCESS accessible-for-notify
    STATUS current
    DESCRIPTION
        "Parameter 'data' in event ISDN.37"
    ::= { isdnEventObjects37 4 }

isdnEventObjects38 OBJECT-IDENTITY
    STATUS current
    DESCRIPTION
        "Event ISDN.38
        An MAN-INFO message has been transmited in order to initialize SPID."
    ::= { isdnEventsGroup 38 }

isdn38-call-ref OBJECT-TYPE
    SYNTAX Integer32
    MAX-ACCESS accessible-for-notify
    STATUS current
    DESCRIPTION
        "Parameter 'call-ref' in event ISDN.38"
    ::= { isdnEventObjects38 1 }

isdn38-usid OBJECT-TYPE
    SYNTAX Integer32
    MAX-ACCESS accessible-for-notify
    STATUS current
    DESCRIPTION
        "Parameter 'usid' in event ISDN.38"
    ::= { isdnEventObjects38 2 }

isdn38-tid OBJECT-TYPE
    SYNTAX Integer32
    MAX-ACCESS accessible-for-notify
    STATUS current
    DESCRIPTION
        "Parameter 'tid' in event ISDN.38"
    ::= { isdnEventObjects38 3 }

isdn38-interfaces OBJECT-TYPE
    SYNTAX DisplayString
    MAX-ACCESS accessible-for-notify
    STATUS current
    DESCRIPTION
        "Parameter 'interfaces' in event ISDN.38"
    ::= { isdnEventObjects38 4 }

isdnEventObjects39 OBJECT-IDENTITY
    STATUS current
    DESCRIPTION
        "Event ISDN.39
        Indicated interface is not available due to physical and/or LAPD problems"
    ::= { isdnEventsGroup 39 }

isdn39-interface OBJECT-TYPE
    SYNTAX DisplayString
    MAX-ACCESS accessible-for-notify
    STATUS current
    DESCRIPTION
        "Parameter 'interface' in event ISDN.39"
    ::= { isdnEventObjects39 1 }

isdnEventObjects40 OBJECT-IDENTITY
    STATUS current
    DESCRIPTION
        "Event ISDN.40
        Indicated interface is available to make calls. This means that physcal level is active and LAPD is established"
    ::= { isdnEventsGroup 40 }

isdn40-interface OBJECT-TYPE
    SYNTAX DisplayString
    MAX-ACCESS accessible-for-notify
    STATUS current
    DESCRIPTION
        "Parameter 'interface' in event ISDN.40"
    ::= { isdnEventObjects40 1 }

isdnEventObjects41 OBJECT-IDENTITY
    STATUS current
    DESCRIPTION
        "Event ISDN.41
        An PROGRESS message has been transmitted."
    ::= { isdnEventsGroup 41 }

isdn41-call-ref OBJECT-TYPE
    SYNTAX Integer32
    MAX-ACCESS accessible-for-notify
    STATUS current
    DESCRIPTION
        "Parameter 'call-ref' in event ISDN.41"
    ::= { isdnEventObjects41 1 }

isdn41-interface OBJECT-TYPE
    SYNTAX DisplayString
    MAX-ACCESS accessible-for-notify
    STATUS current
    DESCRIPTION
        "Parameter 'interface' in event ISDN.41"
    ::= { isdnEventObjects41 2 }


isdnNotification1 NOTIFICATION-TYPE
    OBJECTS { 
              isdn1-call-ref, 
              isdn1-interface 
            }
    STATUS current
    DESCRIPTION
        "Notification of Event ISDN.1

        Message: 'An ALERTING message has been received with Call Reference $1 interface $2'

        Parameters list:
              $1: isdn1-call-ref
              $2: isdn1-interface

        ALERTING message received for the mentioned Q931 conversation."
    ::= { isdnNotificationsPrefix 1 }

isdnNotification2 NOTIFICATION-TYPE
    OBJECTS { 
              isdn2-call-ref, 
              isdn2-interface 
            }
    STATUS current
    DESCRIPTION
        "Notification of Event ISDN.2

        Message: 'A CONN ACK message has been received with Call Reference $1 interface $2'

        Parameters list:
              $1: isdn2-call-ref
              $2: isdn2-interface

        CONN ACK message received for the mentioned Q931 conversation."
    ::= { isdnNotificationsPrefix 2 }

isdnNotification3 NOTIFICATION-TYPE
    OBJECTS { 
              isdn3-call-ref, 
              isdn3-interface 
            }
    STATUS current
    DESCRIPTION
        "Notification of Event ISDN.3

        Message: 'A CONN message has been received with Call Reference $1 interface $2'

        Parameters list:
              $1: isdn3-call-ref
              $2: isdn3-interface

        CONN message received for the mentioned Q931 conversation."
    ::= { isdnNotificationsPrefix 3 }

isdnNotification4 NOTIFICATION-TYPE
    OBJECTS { 
              isdn4-call-ref, 
              isdn4-chan,
              isdn4-interface 
            }
    STATUS current
    DESCRIPTION
        "Notification of Event ISDN.4

        Message: 'A CALL PROC message has been received with Call Reference $1 assigning B channel $2e $3'

        Parameters list:
              $1: isdn4-call-ref
              $2: isdn4-chan
              $3: isdn4-interface

        CALL PROC message received for the mentioned Q931 conversation."
    ::= { isdnNotificationsPrefix 4 }

isdnNotification5 NOTIFICATION-TYPE
    OBJECTS { 
              isdn5-call-ref, 
              isdn5-cause,
              isdn5-cost,
              isdn5-interface 
            }
    STATUS current
    DESCRIPTION
        "Notification of Event ISDN.5

        Message: 'A DISC message has been received with Call Reference $1, Cause $2 and Cost $3 interface $4'

        Parameters list:
              $1: isdn5-call-ref
              $2: isdn5-cause
              $3: isdn5-cost
              $4: isdn5-interface

        DISC message received for the mentioned Q931 conversation."
    ::= { isdnNotificationsPrefix 5 }

isdnNotification6 NOTIFICATION-TYPE
    OBJECTS { 
              isdn6-call-ref, 
              isdn6-interface 
            }
    STATUS current
    DESCRIPTION
        "Notification of Event ISDN.6

        Message: 'A INFO message has been received with Call Reference $1 interface $2'

        Parameters list:
              $1: isdn6-call-ref
              $2: isdn6-interface

        INFO message received for the mentioned Q931 conversation."
    ::= { isdnNotificationsPrefix 6 }

isdnNotification7 NOTIFICATION-TYPE
    OBJECTS { 
              isdn7-call-ref, 
              isdn7-interface 
            }
    STATUS current
    DESCRIPTION
        "Notification of Event ISDN.7

        Message: 'A PROGR message has been received with Call Reference $1 interface $2'

        Parameters list:
              $1: isdn7-call-ref
              $2: isdn7-interface

        PROGR message received for the mentioned Q931 conversation."
    ::= { isdnNotificationsPrefix 7 }

isdnNotification8 NOTIFICATION-TYPE
    OBJECTS { 
              isdn8-call-ref, 
              isdn8-cause,
              isdn8-cost,
              isdn8-interface 
            }
    STATUS current
    DESCRIPTION
        "Notification of Event ISDN.8

        Message: 'A RELEASE message has been received with Call Reference $1, Cause $2 and Cost $3 interface $4'

        Parameters list:
              $1: isdn8-call-ref
              $2: isdn8-cause
              $3: isdn8-cost
              $4: isdn8-interface

        RELEASE message received for the mentioned Q931 conversation."
    ::= { isdnNotificationsPrefix 8 }

isdnNotification9 NOTIFICATION-TYPE
    OBJECTS { 
              isdn9-call-ref, 
              isdn9-cause,
              isdn9-cost,
              isdn9-interface 
            }
    STATUS current
    DESCRIPTION
        "Notification of Event ISDN.9

        Message: 'A REL COMPLETE message has been received with Call Reference $1, Cause $2 and Cost $3 interface $4'

        Parameters list:
              $1: isdn9-call-ref
              $2: isdn9-cause
              $3: isdn9-cost
              $4: isdn9-interface

        REL COMPLETE message received for the mentioned Q931 conversation."
    ::= { isdnNotificationsPrefix 9 }

isdnNotification10 NOTIFICATION-TYPE
    OBJECTS { 
              isdn10-call-ref, 
              isdn10-interface 
            }
    STATUS current
    DESCRIPTION
        "Notification of Event ISDN.10

        Message: 'A STATUS message has been received with Call Reference $1 interface $2'

        Parameters list:
              $1: isdn10-call-ref
              $2: isdn10-interface

        STATUS message received for the mentioned Q931 conversation."
    ::= { isdnNotificationsPrefix 10 }

isdnNotification11 NOTIFICATION-TYPE
    OBJECTS { 
              isdn11-call-ref, 
              isdn11-chan,
              isdn11-caller-num,
              isdn11-interface 
            }
    STATUS current
    DESCRIPTION
        "Notification of Event ISDN.11

        Message: 'A SETUP message has been received with Call Reference $1, assigning B channel $2 and with Calling Number $3 interface $4'

        Parameters list:
              $1: isdn11-call-ref
              $2: isdn11-chan
              $3: isdn11-caller-num
              $4: isdn11-interface

        SETUP message received for the mentioned Q931 conversation."
    ::= { isdnNotificationsPrefix 11 }

isdnNotification12 NOTIFICATION-TYPE
    OBJECTS { 
              isdn12-called, 
              isdn12-caller,
              isdn12-interface 
            }
    STATUS current
    DESCRIPTION
        "Notification of Event ISDN.12

        Message: 'An incoming call has been established Called:$1  Caller $2 interface $3'

        Parameters list:
              $1: isdn12-called
              $2: isdn12-caller
              $3: isdn12-interface

        An incoming call has been established."
    ::= { isdnNotificationsPrefix 12 }

isdnNotification13 NOTIFICATION-TYPE
    OBJECTS { 
              isdn13-called, 
              isdn13-caller,
              isdn13-interface 
            }
    STATUS current
    DESCRIPTION
        "Notification of Event ISDN.13

        Message: 'An outgoing call has been established Called:$1  Caller $2 interface $3'

        Parameters list:
              $1: isdn13-called
              $2: isdn13-caller
              $3: isdn13-interface

        An outgoing call has been established."
    ::= { isdnNotificationsPrefix 13 }

isdnNotification14 NOTIFICATION-TYPE
    OBJECTS { 
              isdn14-called, 
              isdn14-caller,
              isdn14-interface 
            }
    STATUS current
    DESCRIPTION
        "Notification of Event ISDN.14

        Message: 'An incoming call has been released Called:$1  Caller $2 interface $3'

        Parameters list:
              $1: isdn14-called
              $2: isdn14-caller
              $3: isdn14-interface

        An incoming call has been released."
    ::= { isdnNotificationsPrefix 14 }

isdnNotification15 NOTIFICATION-TYPE
    OBJECTS { 
              isdn15-called, 
              isdn15-caller,
              isdn15-interface 
            }
    STATUS current
    DESCRIPTION
        "Notification of Event ISDN.15

        Message: 'An outgoing call has been released Called:$1  Caller $2 interface $3'

        Parameters list:
              $1: isdn15-called
              $2: isdn15-caller
              $3: isdn15-interface

        An outgoing call has been released."
    ::= { isdnNotificationsPrefix 15 }

isdnNotification16 NOTIFICATION-TYPE
    OBJECTS { 
              isdn16-call-ref, 
              isdn16-chan,
              isdn16-interface 
            }
    STATUS current
    DESCRIPTION
        "Notification of Event ISDN.16

        Message: 'A CONN message has been transmitted with Call Reference $1, confirming B channel $2 interface $3'

        Parameters list:
              $1: isdn16-call-ref
              $2: isdn16-chan
              $3: isdn16-interface

        CONN message transmitted for the mentioned Q931 conversation."
    ::= { isdnNotificationsPrefix 16 }

isdnNotification17 NOTIFICATION-TYPE
    OBJECTS { 
              isdn17-call-ref, 
              isdn17-interface 
            }
    STATUS current
    DESCRIPTION
        "Notification of Event ISDN.17

        Message: 'A CONN ACK message has been transmitted with Call Reference $1 interface $2'

        Parameters list:
              $1: isdn17-call-ref
              $2: isdn17-interface

        CONN ACK message transmitted for the mentioned Q931 conversation."
    ::= { isdnNotificationsPrefix 17 }

isdnNotification18 NOTIFICATION-TYPE
    OBJECTS { 
              isdn18-call-ref, 
              isdn18-cause,
              isdn18-interface 
            }
    STATUS current
    DESCRIPTION
        "Notification of Event ISDN.18

        Message: 'A DISC message has been transmitted with Call Reference $1, and Cause $2 interface $3'

        Parameters list:
              $1: isdn18-call-ref
              $2: isdn18-cause
              $3: isdn18-interface

        DISC message transmitted for the mentioned Q931 conversation."
    ::= { isdnNotificationsPrefix 18 }

isdnNotification19 NOTIFICATION-TYPE
    OBJECTS { 
              isdn19-call-ref, 
              isdn19-cause,
              isdn19-interface 
            }
    STATUS current
    DESCRIPTION
        "Notification of Event ISDN.19

        Message: 'A REL message has been transmitted with Call Reference $1, and Cause $2 interface $3'

        Parameters list:
              $1: isdn19-call-ref
              $2: isdn19-cause
              $3: isdn19-interface

        REL message transmitted for the mentioned Q931 conversation."
    ::= { isdnNotificationsPrefix 19 }

isdnNotification20 NOTIFICATION-TYPE
    OBJECTS { 
              isdn20-call-ref, 
              isdn20-cause,
              isdn20-interface 
            }
    STATUS current
    DESCRIPTION
        "Notification of Event ISDN.20

        Message: 'A REL COM message has been transmitted with Call Reference $1, and Cause $2 interface $3'

        Parameters list:
              $1: isdn20-call-ref
              $2: isdn20-cause
              $3: isdn20-interface

        REL COM message transmitted for the mentioned Q931 conversation."
    ::= { isdnNotificationsPrefix 20 }

isdnNotification21 NOTIFICATION-TYPE
    OBJECTS { 
              isdn21-call-ref, 
              isdn21-called-num,
              isdn21-interface 
            }
    STATUS current
    DESCRIPTION
        "Notification of Event ISDN.21

        Message: 'A SETUP message has been transmitted with Call Reference $1, and Called Number $2 interface $3'

        Parameters list:
              $1: isdn21-call-ref
              $2: isdn21-called-num
              $3: isdn21-interface

        SETUP message transmitted for the mentioned Q931 conversation."
    ::= { isdnNotificationsPrefix 21 }

isdnNotification22 NOTIFICATION-TYPE
    OBJECTS { 
              isdn22-call-ref, 
              isdn22-status,
              isdn22-interface 
            }
    STATUS current
    DESCRIPTION
        "Notification of Event ISDN.22

        Message: 'A STATUS message has been transmitted with Call Reference $1, indicating Status $2 interface $3'

        Parameters list:
              $1: isdn22-call-ref
              $2: isdn22-status
              $3: isdn22-interface

        STATUS message transmitted for the mentioned Q931 conversation."
    ::= { isdnNotificationsPrefix 22 }

isdnNotification23 NOTIFICATION-TYPE
    OBJECTS { 
              isdn23-frame-tx, 
              isdn23-interface 
            }
    STATUS current
    DESCRIPTION
        "Notification of Event ISDN.23

        Message: 'Sent FRAME: $1 interface $2'

        Parameters list:
              $1: isdn23-frame-tx
              $2: isdn23-interface

        message transmitted contents."
    ::= { isdnNotificationsPrefix 23 }

isdnNotification24 NOTIFICATION-TYPE
    OBJECTS { 
              isdn24-frame-rx, 
              isdn24-interface 
            }
    STATUS current
    DESCRIPTION
        "Notification of Event ISDN.24

        Message: 'Received FRAME: $1 interface $2'

        Parameters list:
              $1: isdn24-frame-rx
              $2: isdn24-interface

        message received contents."
    ::= { isdnNotificationsPrefix 24 }

isdnNotification25 NOTIFICATION-TYPE
    OBJECTS { 
              isdn25-restart-ind, 
              isdn25-channel-id,
              isdn25-interface 
            }
    STATUS current
    DESCRIPTION
        "Notification of Event ISDN.25

        Message: 'A RESTART message has been received with class $1  $2 interface $3'

        Parameters list:
              $1: isdn25-restart-ind
              $2: isdn25-channel-id
              $3: isdn25-interface

        RESTART message received."
    ::= { isdnNotificationsPrefix 25 }

isdnNotification26 NOTIFICATION-TYPE
    OBJECTS { 
              isdn26-interface 
            }
    STATUS current
    DESCRIPTION
        "Notification of Event ISDN.26

        Message: 'A RESTART ACK message has been transmitted interface $1'

        Parameters list:
              $1: isdn26-interface

        A RESTART ACK message has been transmitted."
    ::= { isdnNotificationsPrefix 26 }

isdnNotification27 NOTIFICATION-TYPE
    OBJECTS { 
              isdn27-call-ref, 
              isdn27-spid,
              isdn27-interface 
            }
    STATUS current
    DESCRIPTION
        "Notification of Event ISDN.27

        Message: 'An INFO message has been transmited with Call Reference $1 SPID $2 interface $3'

        Parameters list:
              $1: isdn27-call-ref
              $2: isdn27-spid
              $3: isdn27-interface

        An INFO message has been transmited in order to initialize SPID."
    ::= { isdnNotificationsPrefix 27 }

isdnNotification28 NOTIFICATION-TYPE
    OBJECTS { 
              isdn28-spid, 
              isdn28-interface 
            }
    STATUS current
    DESCRIPTION
        "Notification of Event ISDN.28

        Message: 'An INFO message has been transmited with SPID n- $1 interface $2'

        Parameters list:
              $1: isdn28-spid
              $2: isdn28-interface

        SPEED is being sending to the network."
    ::= { isdnNotificationsPrefix 28 }

isdnNotification29 NOTIFICATION-TYPE
    OBJECTS { 
              isdn29-spid, 
              isdn29-interface 
            }
    STATUS current
    DESCRIPTION
        "Notification of Event ISDN.29

        Message: 'An INFO message has been received acknowing successfully SPID $1 initialize interface $2'

        Parameters list:
              $1: isdn29-spid
              $2: isdn29-interface

        An INFO message has been received acknowing successfully SPID initialize."
    ::= { isdnNotificationsPrefix 29 }

isdnNotification30 NOTIFICATION-TYPE
    OBJECTS { 
              isdn30-spid, 
              isdn30-cause,
              isdn30-interface 
            }
    STATUS current
    DESCRIPTION
        "Notification of Event ISDN.30

        Message: 'An INFO message has been received for SPID $1 with cause $2 interface $3'

        Parameters list:
              $1: isdn30-spid
              $2: isdn30-cause
              $3: isdn30-interface

        An INFO message has been received with indicated cause."
    ::= { isdnNotificationsPrefix 30 }

isdnNotification31 NOTIFICATION-TYPE
    OBJECTS { 
              isdn31-call-ref, 
              isdn31-interface 
            }
    STATUS current
    DESCRIPTION
        "Notification of Event ISDN.31

        Message: 'A CALL PROCEEDING message has been transmitted   Call Ref $1 interface $2'

        Parameters list:
              $1: isdn31-call-ref
              $2: isdn31-interface

        A CALL PROCEEDING message has been transmitted."
    ::= { isdnNotificationsPrefix 31 }

isdnNotification32 NOTIFICATION-TYPE
    OBJECTS { 
              isdn32-call-ref, 
              isdn32-interface 
            }
    STATUS current
    DESCRIPTION
        "Notification of Event ISDN.32

        Message: 'A ALERTING message has been transmitted   Call Ref $1 interface $2'

        Parameters list:
              $1: isdn32-call-ref
              $2: isdn32-interface

        An ALERTING message has been transmitted."
    ::= { isdnNotificationsPrefix 32 }

isdnNotification33 NOTIFICATION-TYPE
    OBJECTS { 
              isdn33-call-ref, 
              isdn33-interface 
            }
    STATUS current
    DESCRIPTION
        "Notification of Event ISDN.33

        Message: 'A SETUP-ACK message has been transmitted   Call Ref $1 interface $2'

        Parameters list:
              $1: isdn33-call-ref
              $2: isdn33-interface

        A SETUP-ACK message has been transmitted."
    ::= { isdnNotificationsPrefix 33 }

isdnNotification34 NOTIFICATION-TYPE
    OBJECTS { 
              isdn34-call-ref, 
              isdn34-interface 
            }
    STATUS current
    DESCRIPTION
        "Notification of Event ISDN.34

        Message: 'A SETUP ACK message has been received with Call Reference $1 interface $2'

        Parameters list:
              $1: isdn34-call-ref
              $2: isdn34-interface

        SETUP ACK message received for the mentioned Q931 conversation."
    ::= { isdnNotificationsPrefix 34 }

isdnNotification35 NOTIFICATION-TYPE
    OBJECTS { 
              isdn35-call-ref, 
              isdn35-interface 
            }
    STATUS current
    DESCRIPTION
        "Notification of Event ISDN.35

        Message: 'A FACILITY message has been received with Call Reference $1 interface $2'

        Parameters list:
              $1: isdn35-call-ref
              $2: isdn35-interface

        FACILITY message received for the mentioned Q931 conversation."
    ::= { isdnNotificationsPrefix 35 }

isdnNotification36 NOTIFICATION-TYPE
    OBJECTS { 
              isdn36-call-ref, 
              isdn36-interface 
            }
    STATUS current
    DESCRIPTION
        "Notification of Event ISDN.36

        Message: 'A NOTIFY message has been received with Call Reference $1 interface $2'

        Parameters list:
              $1: isdn36-call-ref
              $2: isdn36-interface

        NOTIFY message received for the mentioned Q931 conversation."
    ::= { isdnNotificationsPrefix 36 }

isdnNotification37 NOTIFICATION-TYPE
    OBJECTS { 
              isdn37-sense, 
              isdn37-type,
              isdn37-length,
              isdn37-data 
            }
    STATUS current
    DESCRIPTION
        "Notification of Event ISDN.37

        Message: 'Info Element: Sense $1, Type $2, Len $3, Value: $4'

        Parameters list:
              $1: isdn37-sense
              $2: isdn37-type
              $3: isdn37-length
              $4: isdn37-data

        Display information elements."
    ::= { isdnNotificationsPrefix 37 }

isdnNotification38 NOTIFICATION-TYPE
    OBJECTS { 
              isdn38-call-ref, 
              isdn38-usid,
              isdn38-tid,
              isdn38-interfaces 
            }
    STATUS current
    DESCRIPTION
        "Notification of Event ISDN.38

        Message: 'An MAN-INFO message has been transmited with Call Reference $1  USID:$2 TID:$3 interface $4'

        Parameters list:
              $1: isdn38-call-ref
              $2: isdn38-usid
              $3: isdn38-tid
              $4: isdn38-interfaces

        An MAN-INFO message has been transmited in order to initialize SPID."
    ::= { isdnNotificationsPrefix 38 }

isdnNotification39 NOTIFICATION-TYPE
    OBJECTS { 
              isdn39-interface 
            }
    STATUS current
    DESCRIPTION
        "Notification of Event ISDN.39

        Message: 'Interface is NOT available to make calls $1'

        Parameters list:
              $1: isdn39-interface

        Indicated interface is not available due to physical and/or LAPD problems"
    ::= { isdnNotificationsPrefix 39 }

isdnNotification40 NOTIFICATION-TYPE
    OBJECTS { 
              isdn40-interface 
            }
    STATUS current
    DESCRIPTION
        "Notification of Event ISDN.40

        Message: 'Interface is available to make calls $1'

        Parameters list:
              $1: isdn40-interface

        Indicated interface is available to make calls. This means that physcal level is active and LAPD is established"
    ::= { isdnNotificationsPrefix 40 }

isdnNotification41 NOTIFICATION-TYPE
    OBJECTS { 
              isdn41-call-ref, 
              isdn41-interface 
            }
    STATUS current
    DESCRIPTION
        "Notification of Event ISDN.41

        Message: 'A PROGRESS message has been transmitted   Call Ref $1 interface $2'

        Parameters list:
              $1: isdn41-call-ref
              $2: isdn41-interface

        An PROGRESS message has been transmitted."
    ::= { isdnNotificationsPrefix 41 }


END
