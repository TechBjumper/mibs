-- *****************************************************************
-- ZXROSNG-L2VPN-MIB.mib 
-- MPLS Layer 2 Virtual Private Networks MIB Definitions  
-- yaojie10102482
-- 2010-05-12
--
-- Copyright (c) 1985-2010 by ZTE Corp.
-- All rights reserved.
-- *****************************************************************


ZXROSNG-L2VPN-MIB DEFINITIONS ::= BEGIN  
     
IMPORTS
       OBJECT-TYPE,MODULE-IDENTITY,             
       Integer32,Counter32,Unsigned32,Counter64,enterprises,
       IpAddress
                                           FROM SNMPv2-SMI
       RowStatus,DisplayString,MacAddress,TEXTUAL-CONVENTION
                                           FROM SNMPv2-TC
       Ipv6Address  
                                           FROM IPV6-TC
       zxr10RosngMIB
                                           FROM ZXR10-SMI;
             
zxL2vpnMIB MODULE-IDENTITY
         LAST-UPDATED "201705221800Z"
         ORGANIZATION "ZTE Corporation"
         CONTACT-INFO
             "ZTE Corporation
              Nanjing Institute of ZTE Corporation

              No.68 Zijinghua Rd. Yuhuatai District, Nanjing, China

              Tel: +86-25-52870000"

         DESCRIPTION
             "This MIB contains managed object definitions for the ZXROSng 
             L2vpn"

        REVISION "201705221800Z"
        DESCRIPTION
            "modify name, enum value and DEFVAL: 
                zxAcParaEtherL2cpAbm,
                zxAcParaEtherL2cpStp,
                zxAcParaEtherL2cpDot1x,
                zxAcParaEtherL2cpDot3x,
                zxAcParaEtherL2cpLacp,
                zxAcParaEtherL2cpGarp,
                zxAcParaEtherL2cpGmrp,
                zxAcParaEtherL2cpGvrp,
                zxAcParaEtherL2cpCisco,
                zxAcParaEtherL2cpDldp,
                zxAcParaEtherL2cpEfm,
                zxAcParaEtherL2cpCfm,
                zxAcParaEtherL2cpLldp,
                zxAcParaEtherL2cpPvst,
                zxAcParaEtherL2cpZdp
             add: 
                zxAcParaEtherL2cpErps,
                zxAcParaEtherL2cpUdld,
                zxAcParaEtherL2cpVtp,
                zxAcParaEtherL2cpZesr,
                zxAcParaEtherL2cpUserProtocolName,
                zxAcParaEtherL2cpUserProtocol
            "
             
        REVISION "201512231500Z"
        DESCRIPTION
            "Obsolete leaf objects of zxVplsBgpADPwDetailsVplsID,
            zxVplsBgpADPwDetailsPwName and zxVplsBgpADRTVplsID."

        REVISION "201503031500Z"
        DESCRIPTION
            "Delete syntax value(acCoworker) of zxPwProtectBindInterChassis,
            zxPwProtectBindInterChassis.
            Obsolete leaf object zxPwProtectStrategyAcType.
            Add table objects for access PW protect group:
            zxAccessPwBindTable, zxAcCeSideTable."

        REVISION "201408181500Z"
        DESCRIPTION
            "Add leaf objects for statistics:
            zxL2vpnVplsCount, zxL2vpnVpwsCount, zxL2vpnVlssCount,
            zxL2vpnMspwCount, zxL2vpnMaxVplsCount, zxL2vpnMaxVpwsCount.
            zxL2vpnMaxVlssCount, zxL2vpnMaxMspwCount, zxL2vpnPwCount,
            zxL2vpnMaxPwCount, zxL2vpnPwTrafficCount.
            Add table objects for VPWS-for-monitor and admin-VPLS:
            zxMonitorVpwsInstTable, zxAdminVplsInstTable."

        REVISION "201407101500Z"
        DESCRIPTION
            "Modify description of zxAcParaIwfEtherRemoteMac and 
            zxAcParaEtherIngressAdjustDropTaggedFrames."

        REVISION "201407011500Z"
        DESCRIPTION
            "Modify syntax of zxPwInstBindSplitHorizon:
            from {spokeOrVpws(0), hub(1)} to {spokeOrNull(0), hub(1)},
            Modify syntax of zxAcInstBindSplitHorizon:
            from {spokeOrVpws(0), hub(1)} to {serverOrNull(0), client(1)},
            Modify syntax of zxVplsBgpADPwDetailsHubOrSpoke:
            from {spokeOrVpws(0), hub(1)} to {spoke(0), hub(1)}."

        REVISION "201406191200Z"
        DESCRIPTION
            "Add leaf objects for IPv6:
            zxPwObjectTunnelDstIpv6."

        REVISION "201403311500Z"
        DESCRIPTION
            "Add leaf objects for NNI ping:
            zxAcParaEtherMonitorIp, zxAcParaEtherMonitorMac, 
            zxAcParaEtherMonitorMode."
            
        REVISION "201402281200Z"
        DESCRIPTION
            "Add leaf objects for L2CP packet filter:
            zxAcParaEtherDropWildcard, zxAcParaEtherDropAbm, 
            zxAcParaEtherDropStp, zxAcParaEtherDropDot1x, 
            zxAcParaEtherDropDot3x, zxAcParaEtherDropLacp,
            zxAcParaEtherDropGarp, zxAcParaEtherDropGmrp,
            zxAcParaEtherDropGvrp, zxAcParaEtherDropCisco,
            zxAcParaEtherDropDldp, zxAcParaEtherDropEfm,
            zxAcParaEtherDropCfm, zxAcParaEtherDropLldp,
            zxAcParaEtherDropPvst, zxAcParaEtherDropZdp."

        REVISION "201401211500Z"
        DESCRIPTION
            "Change default value of zxAcParaMspwRmtTdmAal1Mode 
            from unstructured to structured."

        REVISION "201401091200Z"
        DESCRIPTION
            "Because these oids have not been used, Change STATUS from current
             to deprecated:
            zxVplsBgpADPwDetailsVplsID, zxVplsBgpADRTVplsID."

        REVISION "201311221500Z"
        DESCRIPTION
            "Add leaf objects for terminaling status signal:
            zxMspwInstStatSigTerminal."

        REVISION "201311141700Z"
        DESCRIPTION
            "Add leaf objects for split horizon scope:
            zxPwInstBindSplitHorizonScope, zxAcInstBindSplitHorizonScope."

        REVISION "201309171200Z"
        DESCRIPTION
            "Add leaf objects for threshhold of traffic statistics:
            zxStatisSwitchInstInUnknowBps, zxStatisSwitchInstInUnknowPps,
            zxStatisSwitchInstInBroadBps, zxStatisSwitchInstInBroadPps,
            zxStatisSwitchInstInDropBps, zxStatisSwitchInstInDropPps,
            zxPwObjectInUnknowBps, zxPwObjectInUnknowPps, zxPwObjectInBroadBps,
            zxPwObjectInBroadPps, zxPwObjectInDropBps, zxPwObjectInDropPps,
            zxAcParaEtherInUnknowBps, zxAcParaEtherInUnknowPps,
            zxAcParaEtherInBroadBps, zxAcParaEtherInBroadPps,
            zxAcParaEtherInDropBps, zxAcParaEtherInDropPps,
            zxAcParaTdmStatisEnStatus, zxAcParaTdmInUnknowBps,
            zxAcParaTdmInUnknowPps, zxAcParaTdmInBroadBps,
            zxAcParaTdmInBroadPps, zxAcParaTdmInDropBps, zxAcParaTdmInDropPps,
            zxAcParaIwfIPStatisEnStatus, zxAcParaIwfIPInUnknowBps,
            zxAcParaIwfIPInUnknowPps, zxAcParaIwfIPInBroadBps,
            zxAcParaIwfIPInBroadPps, zxAcParaIwfIPInDropBps,
            zxAcParaIwfIPInDropPps, zxAcParaIwfEtherStatisEnStatus,
            zxAcParaIwfEtherInUnknowBps, zxAcParaIwfEtherInUnknowPps,
            zxAcParaIwfEtherInBroadBps, zxAcParaIwfEtherInBroadPps,
            zxAcParaIwfEtherInDropBps, zxAcParaIwfEtherInDropPps,
            zxAcParaAtmStatisEnStatus, zxAcParaAtmInUnknowBps,
            zxAcParaAtmInUnknowPps, zxAcParaAtmInBroadBps,
            zxAcParaAtmInBroadPps, zxAcParaAtmInDropBps, zxAcParaAtmInDropPps,
            zxAcParaHdlcStatisEnStatus, zxAcParaHdlcInUnknowBps,
            zxAcParaHdlcInUnknowPps, zxAcParaHdlcInBroadBps,
            zxAcParaHdlcInBroadPps,zxAcParaHdlcInDropBps,zxAcParaHdlcInDropPps,
            zxAcParaPppStatisEnStatus, zxAcParaPppInUnknowBps,
            zxAcParaPppInUnknowPps, zxAcParaPppInBroadBps,
            zxAcParaPppInBroadPps, zxAcParaPppInDropBps, zxAcParaPppInDropPps,
            zxAcParaFrStatisEnStatus, zxAcParaFrInUnknowBps,
            zxAcParaFrInUnknowPps, zxAcParaFrInBroadBps,
            zxAcParaFrInBroadPps, zxAcParaFrInDropBps, zxAcParaFrInDropPps"

        REVISION "201309041700Z"
        DESCRIPTION
            "Add leaf objects for PW pretending:
            zxPwObjectPwTypeReverse, zxPwObjectControlWordForce;
            Add leaf objects for CSF:
            zxPwObjectFrrIgnore, zxPwObjectOamMappingAbort;
            Add table\leaf objects for DNI-PW:
            zxPwProtectStrategyPattern, zxPwProtectStrategyAcType,
            zxPwProtectableGroupType, zxPwProtectableMcRole, 
            zxPwProtectMcSelectTable;
            Add table objects for PW list:
            zxPwListTable, zxPwListSlaveTable;
            Modify zxPwProtectBindInterChassis syntax for DNI-PW:
            from {local(1), interChassis(2)}
            to {local(1), interChassis(2),pwCoworker(3),acCoworker(4)}."

        REVISION "201308021200Z"
        DESCRIPTION
            "Add table\leaf objects for AC fault-spread:
            zxAcParaHdlcTable, zxAcParaPppTable, zxAcParaFrTable,
            zxAcParaEtherFaultSpread, zxAcParaTdmFaultSpread,
            zxAcParaIwfIPFaultSpread, zxAcParaIwfEtherFaultSpread,
            zxAcParaAtmFaultSpread."

        REVISION "201307151200Z"
        DESCRIPTION
            "Modify syntax of all instance name objects:
            from DisplayString (SIZE(0..31)) to DisplayString (SIZE(0..32))."

        REVISION "201307091000Z"
        DESCRIPTION
            "Modify syntax of zxPwStatusNegoedStatusSignalAbility:
            from INTEGER{osbit(1),fsbit(2),rssbit(3),none(4)} to 
            INTEGER{osbit(1),pfsbit(2),rssbit(3),none(4)}."

        REVISION "201307021200Z"
        DESCRIPTION
            "Add table object for ATM emulation :
            zxAcParaAtmTable."

        REVISION "201305221200Z"
        DESCRIPTION
            "Add leaf objects for PW rate limit:
            zxPwObjectLimitMode, zxPwObjectLimitCIR, zxPwObjectLimitCBS,
            zxPwObjectLimitPIR, zxPwObjectLimitPBS."

        REVISION "201305071200Z"
        DESCRIPTION
            "Add table objects : zxAcParaMspwRmtTable,zxVplsKempollaADTable,
            zxVplsKempollaADRTTable, zxVplsKempollaADVETable;
            Add leaf objects : zxMspwInstCwConflict,zxVplsInstDsMode,
            zxVplsInstServiceClass,zxVplsInstColour,zxVpwsInstDsMode,
            zxVpwsInstServiceClass,zxVpwsInstColour,zxPwObjectVccvStaticCC,
            zxPwObjectCwLBit,zxPwObjectSdEnStatus,zxPwProtectBindDistance,
            zxPwProtectablePfsAdvertise,zxPwTemplateVccvStaticCC,
            zxAcParaTdmTimeSlotCompatible."
            
        REVISION "201305031100Z"
        DESCRIPTION
            "Delete all RowStatus objects,because the project does not
             request the create operation and ZXROSNG-L2VPN-MIB tables nodes
             with read-only attributes can't pass the MIB tool check."

        REVISION "201304161200Z"
        DESCRIPTION
            "Add table objects : zxStatisSwitchInstTable,zxPwProtectIccpTable;
            Add leaf objects : zxPwObjectStatisEnStatus,zxPwObjectInBRateLow,
            zxPwObjectInBRateHigh,zxPwObjectOutBRateLow,zxPwObjectOutBRateHigh,
            zxPwProtectBindInterChassis,zxAcParaEtherStatisEnStatus;
            Modify leaf object : zxAcInstBindType."

        REVISION "201304031100Z"
        DESCRIPTION
            "Add objects for default control-word."

         ::= { zxr10RosngMIB 400 }      
       
      zxL2vpnGlobalConfig       OBJECT IDENTIFIER ::= { zxL2vpnMIB 1}
      zxL2vpnInstance           OBJECT IDENTIFIER ::= { zxL2vpnMIB 2}
      zxL2vpnPW                 OBJECT IDENTIFIER ::= { zxL2vpnMIB 3}
      zxL2vpnAC                 OBJECT IDENTIFIER ::= { zxL2vpnMIB 4}
      zxL2vpnVplsBgpAD          OBJECT IDENTIFIER ::= { zxL2vpnMIB 5}
      zxL2vpnStatus             OBJECT IDENTIFIER ::= { zxL2vpnMIB 6}
      
L2vpnPWType ::= TEXTUAL-CONVENTION
        STATUS       current
        DESCRIPTION
            "L2vpn PW Type. Assigned values are specified in 'IANA Allocations 
             for Pseudowire Edge to Edge Emulation (PWE3)"
        SYNTAX INTEGER {
            unknown(0),
            dlciOld(1),
            atmSdu(2),
            atmCell(3),
            vlan(4),
            ethernet(5),
            hdlc(6),
            ppp(7),
            sdhCESoM(8),
            atmVCCn(9),
            atmVPCn(10),
            ipL2(11),
            atmVCC1(12),
            atmVPC1(13),
            atmPDU(14),
            frPort(15),
            sdhCEoP(16),
            saTopE1(17),
            saTopT1(18),
            saTopE3(19),
            saTopT3(20),
            ceSoPSNB(21),
            tdmAAL1(22),
            ceSoPSNC(23),
            tdmAAL2(24),
            dlciNew(25)            
         }     
         
--********************************************         
--definition of tables::  
--********************************************   
--*************zxL2vpnGlobalConfig**************** 
zxL2vpnEnable OBJECT-TYPE
            SYNTAX      INTEGER{
            disable(0),
            enable(1)
            }
            MAX-ACCESS  read-only
            STATUS      current
            DESCRIPTION 
                " The enable status of L2VPN service."
            ::= { zxL2vpnGlobalConfig 1 }
            
zxL2vpnStatisStatus OBJECT-TYPE
            SYNTAX      INTEGER{
            disable(0),
            enable(1)
            }
            MAX-ACCESS  read-only
            STATUS      current
            DESCRIPTION 
                " The enable status of L2VPN service statistics."
            ::= { zxL2vpnGlobalConfig 2 }

zxL2vpnVplsCount OBJECT-TYPE
            SYNTAX       Unsigned32
            MAX-ACCESS   read-only
            STATUS       current
            DESCRIPTION
                "The numbers of configured VPLS instances."
            ::= { zxL2vpnGlobalConfig 3 } 

zxL2vpnVpwsCount OBJECT-TYPE
            SYNTAX       Unsigned32
            MAX-ACCESS   read-only
            STATUS       current
            DESCRIPTION
                "The numbers of configured VPWS instances."
            ::= { zxL2vpnGlobalConfig 4 } 

zxL2vpnVlssCount OBJECT-TYPE
            SYNTAX       Unsigned32
            MAX-ACCESS   read-only
            STATUS       current
            DESCRIPTION
                "The numbers of configured VLSS instances."
            ::= { zxL2vpnGlobalConfig 5 } 

zxL2vpnMspwCount OBJECT-TYPE
            SYNTAX       Unsigned32
            MAX-ACCESS   read-only
            STATUS       current
            DESCRIPTION
                "The numbers of configured MSPW instances."
            ::= { zxL2vpnGlobalConfig 6 } 

zxL2vpnMaxVplsCount OBJECT-TYPE
            SYNTAX       Unsigned32
            MAX-ACCESS   read-only
            STATUS       current
            DESCRIPTION
                "The maximum numbers of supported VPLS instances."
            ::= { zxL2vpnGlobalConfig 7 } 

zxL2vpnMaxVpwsCount OBJECT-TYPE
            SYNTAX       Unsigned32
            MAX-ACCESS   read-only
            STATUS       current
            DESCRIPTION
                "The maximum numbers of supported VPWS instances."
            ::= { zxL2vpnGlobalConfig 8 } 

zxL2vpnMaxVlssCount OBJECT-TYPE
            SYNTAX       Unsigned32
            MAX-ACCESS   read-only
            STATUS       current
            DESCRIPTION
                "The maximum numbers of supported VLSS instances."
            ::= { zxL2vpnGlobalConfig 9 } 

zxL2vpnMaxMspwCount OBJECT-TYPE
            SYNTAX       Unsigned32
            MAX-ACCESS   read-only
            STATUS       current
            DESCRIPTION
                "The maximum numbers of supported MSPW instances."
            ::= { zxL2vpnGlobalConfig 10 } 

zxL2vpnPwCount OBJECT-TYPE
            SYNTAX       Unsigned32
            MAX-ACCESS   read-only
            STATUS       current
            DESCRIPTION
                "The numbers of configured PWs."
            ::= { zxL2vpnGlobalConfig 11 } 

zxL2vpnMaxPwCount OBJECT-TYPE
            SYNTAX       Unsigned32
            MAX-ACCESS   read-only
            STATUS       current
            DESCRIPTION
                "The maximum numbers of supported PWs."
            ::= { zxL2vpnGlobalConfig 12 } 

zxL2vpnPwTrafficCount OBJECT-TYPE
            SYNTAX       Unsigned32
            MAX-ACCESS   read-only
            STATUS       current
            DESCRIPTION
                "The numbers of PWs whose traffic statistics are enabled."
            ::= { zxL2vpnGlobalConfig 13 } 
 
--*************zxMspwInstTable**************** 
zxMspwInstTable OBJECT-TYPE
            SYNTAX     SEQUENCE OF ZxMspwInstEntry
            MAX-ACCESS not-accessible
            STATUS     current
            DESCRIPTION
                "MSPW instance Table. This table contains
                 one entry per MSPW instance table."        
            ::= { zxL2vpnInstance 1 }

zxMspwInstEntry OBJECT-TYPE
            SYNTAX     ZxMspwInstEntry
            MAX-ACCESS not-accessible
            STATUS     current
            DESCRIPTION
                "The parameter of a MSPW instance entity containing "
            INDEX { zxMspwInstName }
            ::= { zxMspwInstTable 1 }

ZxMspwInstEntry ::= SEQUENCE {
            zxMspwInstName                      DisplayString,
            zxMspwInstMspwType                  L2vpnPWType,
            zxMspwInstDescription               DisplayString,
            zxMspwInstEnStatus                  INTEGER,
            zxMspwInstCwConflict                INTEGER,
            zxMspwInstStatSigTerminal           INTEGER
            }

zxMspwInstName OBJECT-TYPE
            SYNTAX       DisplayString  (SIZE(0..32))
            MAX-ACCESS   read-only
            STATUS       current
            DESCRIPTION
                "The name of the MSPW instance."
            ::= { zxMspwInstEntry 1 }   

zxMspwInstMspwType OBJECT-TYPE
            SYNTAX       L2vpnPWType
            MAX-ACCESS   read-only
            STATUS       current
            DESCRIPTION
                "The PW type of the MSPW instance."
            ::= { zxMspwInstEntry 2 }

zxMspwInstDescription OBJECT-TYPE
            SYNTAX       DisplayString  (SIZE(0..104))
            MAX-ACCESS   read-only
            STATUS       current
            DESCRIPTION
                "The description of the MSPW instance."
            ::= { zxMspwInstEntry 3 } 

zxMspwInstEnStatus OBJECT-TYPE
            SYNTAX       INTEGER{
            disable(0),
            enable(1)
            }
            MAX-ACCESS   read-only
            STATUS       current
            DESCRIPTION
                "The enable status of the MSPW instance."
            ::= { zxMspwInstEntry 4 } 

zxMspwInstCwConflict OBJECT-TYPE
            SYNTAX       INTEGER{
            disable(1),
            enable(2)
            }
            MAX-ACCESS   read-only
            STATUS       current
            DESCRIPTION
                "The enable status of control-word conflict function of the 
                MSPW instance."
            DEFVAL       { disable }
            ::= { zxMspwInstEntry 6 }

zxMspwInstStatSigTerminal OBJECT-TYPE
            SYNTAX       INTEGER{
            disable(1),
            enable(2)
            }
            MAX-ACCESS   read-only
            STATUS       current
            DESCRIPTION
                "The enable status of terminaling status signal function of 
                the MSPW instance."
            DEFVAL       { disable }
            ::= { zxMspwInstEntry 7 }

--*************zxVplsInstTable**************** 
zxVplsInstTable OBJECT-TYPE
            SYNTAX     SEQUENCE OF ZxVplsInstEntry
            MAX-ACCESS not-accessible
            STATUS     current
            DESCRIPTION
                "VPLS instance Table. This table contains
                 one entry per VPLS instance table."        
            ::= { zxL2vpnInstance 2 }

zxVplsInstEntry OBJECT-TYPE
            SYNTAX     ZxVplsInstEntry
            MAX-ACCESS not-accessible
            STATUS     current
            DESCRIPTION
                "The parameter of a VPLS instance entity containing "
            INDEX { zxVplsInstName }
            ::= { zxVplsInstTable 1 }

ZxVplsInstEntry ::= SEQUENCE {
            zxVplsInstName                      DisplayString,
            zxVplsInstQualified                 INTEGER,  
            zxVplsInstDefaultVcid               Unsigned32,  
            zxVplsInstMacWithdraw               INTEGER,
            zxVplsInstMtu                       Unsigned32,
            zxVplsInstDescription               DisplayString,
            zxVplsInstEnStatus                  INTEGER,
            zxVplsInstDscvVplsID                DisplayString,
            zxVplsInstDefaultCw                 INTEGER,
            zxVplsInstDsMode                    INTEGER,
            zxVplsInstServiceClass              INTEGER,
            zxVplsInstColour                    INTEGER
            }

zxVplsInstName OBJECT-TYPE
            SYNTAX       DisplayString (SIZE(0..32))
            MAX-ACCESS   read-only
            STATUS       current
            DESCRIPTION
                "The name of the VPLS instance."
            ::= { zxVplsInstEntry 1 } 

zxVplsInstQualified OBJECT-TYPE
            SYNTAX       INTEGER{
            disable(0),
            enable(1)
            }
            MAX-ACCESS   read-only
            STATUS       current
            DESCRIPTION
                "The qualified flag of the VPLS instance."
            ::= { zxVplsInstEntry 2 }

zxVplsInstDefaultVcid OBJECT-TYPE
            SYNTAX       Unsigned32
            MAX-ACCESS   read-only
            STATUS       current
            DESCRIPTION
                "The default VCID of the VPLS instance."
            ::= { zxVplsInstEntry 3 } 

zxVplsInstMacWithdraw OBJECT-TYPE
            SYNTAX       INTEGER{
            disable(0),
            enable(1)
            }
            MAX-ACCESS   read-only
            STATUS       current
            DESCRIPTION
                "The mac-withdraw capability of the VPLS instance."
            ::= { zxVplsInstEntry 4 }

zxVplsInstMtu OBJECT-TYPE
            SYNTAX       Unsigned32(60..9216)
            MAX-ACCESS   read-only
            STATUS       current
            DESCRIPTION
                "The MTU value of the VPLS instance."
            ::= { zxVplsInstEntry 5 } 

zxVplsInstDescription OBJECT-TYPE
            SYNTAX       DisplayString  (SIZE(0..104))
            MAX-ACCESS   read-only
            STATUS       current
            DESCRIPTION
                "The description of the VPLS instance."
            ::= { zxVplsInstEntry 6 } 

zxVplsInstEnStatus OBJECT-TYPE
            SYNTAX       INTEGER{
            disable(0),
            enable(1)
            }
            MAX-ACCESS   read-only
            STATUS       current
            DESCRIPTION
                "The enable status of the VPLS instance."
            ::= { zxVplsInstEntry 7 }

zxVplsInstDscvVplsID OBJECT-TYPE
            SYNTAX       DisplayString 
            MAX-ACCESS   read-only
            STATUS       current
            DESCRIPTION
                "The VPLS id of BGP auto-discovery instance."
            ::= { zxVplsInstEntry 9 } 

zxVplsInstDefaultCw OBJECT-TYPE
            SYNTAX       INTEGER{
            notPreferred(1),
            preferred(2)
            }
            MAX-ACCESS   read-only
            STATUS       current
            DESCRIPTION
                "The default control-word capability of the VPLS instance."
            DEFVAL       { notPreferred }
            ::= { zxVplsInstEntry 10 }

zxVplsInstDsMode OBJECT-TYPE
            SYNTAX       INTEGER{
            null(1),
            uniform(2),
            pipe(3),
            shortPipe(4)
            }
            MAX-ACCESS   read-only
            STATUS       current
            DESCRIPTION
                "The QoS service mode of the VPLS instance."
            DEFVAL       { null }
            ::= { zxVplsInstEntry 11 }

zxVplsInstServiceClass OBJECT-TYPE
            SYNTAX       INTEGER{
            null(1),
            be(2),
            af1(3),
            af2(4),
            af3(5),
            af4(6),
            ef(7),
            cs6(8),
            cs7(9)
            }
            MAX-ACCESS   read-only
            STATUS       current
            DESCRIPTION
                "The QoS service class of the VPLS instance."
            DEFVAL       { null }
            ::= { zxVplsInstEntry 12 }

zxVplsInstColour OBJECT-TYPE
            SYNTAX       INTEGER{
            null(1),
            green(2),
            yellow(3),
            red(4)
            }
            MAX-ACCESS   read-only
            STATUS       current
            DESCRIPTION
                "The QoS packet colour of the VPLS instance."
            DEFVAL       { null }
            ::= { zxVplsInstEntry 13 }
            
--*************zxVpwsInstTable**************** 
zxVpwsInstTable OBJECT-TYPE
            SYNTAX     SEQUENCE OF ZxVpwsInstEntry
            MAX-ACCESS not-accessible
            STATUS     current
            DESCRIPTION
                "VPWS instance Table. This table contains
                 one entry per VPWS instance table."        
            ::= { zxL2vpnInstance 3 }

zxVpwsInstEntry OBJECT-TYPE
            SYNTAX     ZxVpwsInstEntry
            MAX-ACCESS not-accessible
            STATUS     current
            DESCRIPTION
                "The parameter of a VPWS instance entity containing "
            INDEX { zxVpwsInstName }
            ::= { zxVpwsInstTable 1 }

ZxVpwsInstEntry ::= SEQUENCE {
            zxVpwsInstName                      DisplayString,
            zxVpwsInstMtu                           Unsigned32,
            zxVpwsInstDescription               DisplayString,
            zxVpwsInstEnStatus                  INTEGER,
            zxVpwsInstDefaultCw                 INTEGER,
            zxVpwsInstDsMode                    INTEGER,
            zxVpwsInstServiceClass              INTEGER,
            zxVpwsInstColour                    INTEGER
            }

zxVpwsInstName OBJECT-TYPE
            SYNTAX       DisplayString  (SIZE(0..32))
            MAX-ACCESS   read-only
            STATUS       current
            DESCRIPTION
                "The name of the VPWS instance."
            ::= { zxVpwsInstEntry 1 }   

zxVpwsInstMtu OBJECT-TYPE
            SYNTAX       Unsigned32(0..9216)
            MAX-ACCESS   read-only
            STATUS       current
            DESCRIPTION
                "The MTU value of the VPWS instance."
            ::= { zxVpwsInstEntry 2 }

zxVpwsInstDescription OBJECT-TYPE
            SYNTAX       DisplayString  (SIZE(0..104))
            MAX-ACCESS   read-only
            STATUS       current
            DESCRIPTION
                "The description of the VPWS instance."
            ::= { zxVpwsInstEntry 3 } 

zxVpwsInstEnStatus OBJECT-TYPE
            SYNTAX       INTEGER{
            disable(0),
            enable(1)
            }
            MAX-ACCESS   read-only
            STATUS       current
            DESCRIPTION
                "The enable status of the VPWS instance."
            ::= { zxVpwsInstEntry 4 }    

zxVpwsInstDefaultCw OBJECT-TYPE
            SYNTAX       INTEGER{
            notPreferred(1),
            preferred(2)
            }
            MAX-ACCESS   read-only
            STATUS       current
            DESCRIPTION
                "The default control-word capability of the VPWS instance."
            DEFVAL       { notPreferred }
            ::= { zxVpwsInstEntry 6 }

zxVpwsInstDsMode OBJECT-TYPE
            SYNTAX       INTEGER{
            null(1),
            uniform(2),
            pipe(3),
            shortPipe(4)
            }
            MAX-ACCESS   read-only
            STATUS       current
            DESCRIPTION
                "The QoS service mode of the VPWS instance."
            DEFVAL       { null }
            ::= { zxVpwsInstEntry 7 }

zxVpwsInstServiceClass OBJECT-TYPE
            SYNTAX       INTEGER{
            null(1),
            be(2),
            af1(3),
            af2(4),
            af3(5),
            af4(6),
            ef(7),
            cs6(8),
            cs7(9)
            }
            MAX-ACCESS   read-only
            STATUS       current
            DESCRIPTION
                "The QoS service class of the VPWS instance."
            DEFVAL       { null }
            ::= { zxVpwsInstEntry 8 }

zxVpwsInstColour OBJECT-TYPE
            SYNTAX       INTEGER{
            null(1),
            green(2),
            yellow(3),
            red(4)
            }
            MAX-ACCESS   read-only
            STATUS       current
            DESCRIPTION
                "The QoS packet colour of the VPWS instance."
            DEFVAL       { null }
            ::= { zxVpwsInstEntry 9 }

--*************zxVlssInstTable**************** 
zxVlssInstTable OBJECT-TYPE
            SYNTAX     SEQUENCE OF ZxVlssInstEntry
            MAX-ACCESS not-accessible
            STATUS     current
            DESCRIPTION
                "VLSS instance Table. This table contains
                 one entry per VLSS instance table."        
            ::= { zxL2vpnInstance 4 }

zxVlssInstEntry OBJECT-TYPE
            SYNTAX     ZxVlssInstEntry
            MAX-ACCESS not-accessible
            STATUS     current
            DESCRIPTION
                "The parameter of a VLSS instance entity containing "
            INDEX { zxVlssInstName }
            ::= { zxVlssInstTable 1 }

ZxVlssInstEntry ::= SEQUENCE {
            zxVlssInstName                      DisplayString,
            zxVlssInstDescription               DisplayString,
            zxVlssInstEnStatus                  INTEGER
            }

zxVlssInstName OBJECT-TYPE
            SYNTAX       DisplayString  (SIZE(0..32))
            MAX-ACCESS   read-only
            STATUS       current
            DESCRIPTION
                "The name of the VLSS instance."
            ::= { zxVlssInstEntry 1 }   

zxVlssInstDescription OBJECT-TYPE
            SYNTAX       DisplayString  (SIZE(0..104))
            MAX-ACCESS   read-only
            STATUS       current
            DESCRIPTION
                "The description of the VLSS instance."
            ::= { zxVlssInstEntry 2 } 

zxVlssInstEnStatus OBJECT-TYPE
            SYNTAX       INTEGER{
            disable(0),
            enable(1)
            }
            MAX-ACCESS   read-only
            STATUS       current
            DESCRIPTION
                "The enable status of the VLSS instance."
            ::= { zxVlssInstEntry 3 }

--*************zxStatisSwitchInstTable**************** 
zxStatisSwitchInstTable OBJECT-TYPE
            SYNTAX     SEQUENCE OF ZxStatisSwitchInstEntry
            MAX-ACCESS not-accessible
            STATUS     current
            DESCRIPTION
                "Statistics switch instance Table. This table contains
                 one entry per instance table."        
            ::= { zxL2vpnInstance 5 }

zxStatisSwitchInstEntry OBJECT-TYPE
            SYNTAX     ZxStatisSwitchInstEntry
            MAX-ACCESS not-accessible
            STATUS     current
            DESCRIPTION
                "The parameter of a statistics switch instance entity 
                containing."
            INDEX { zxStatisSwitchInstName }
            ::= { zxStatisSwitchInstTable 1 }

ZxStatisSwitchInstEntry ::= SEQUENCE {
            zxStatisSwitchInstName              DisplayString,
            zxStatisSwitchInstType              INTEGER,
            zxStatisSwitchInstEnStatus          INTEGER,
            zxStatisSwitchInstInUnknowBps       Counter64,
            zxStatisSwitchInstInUnknowPps       Unsigned32,
            zxStatisSwitchInstInBroadBps        Counter64,
            zxStatisSwitchInstInBroadPps        Unsigned32,
            zxStatisSwitchInstInDropBps         Counter64,
            zxStatisSwitchInstInDropPps         Unsigned32            
            }

zxStatisSwitchInstName OBJECT-TYPE
            SYNTAX       DisplayString  (SIZE(0..32))
            MAX-ACCESS   not-accessible
            STATUS       current
            DESCRIPTION
                "The name of the instance."
            ::= { zxStatisSwitchInstEntry 1 }  

zxStatisSwitchInstType OBJECT-TYPE
            SYNTAX       INTEGER{
            vpls(1),
            mspw(3),
            vlss(4),
            vpws(5)
            }
            MAX-ACCESS   read-only
            STATUS       current
            DESCRIPTION
                "The VPN type of the instance."
            ::= { zxStatisSwitchInstEntry 2 }

zxStatisSwitchInstEnStatus OBJECT-TYPE
            SYNTAX       INTEGER{
            disable(1),
            enable(2)
            }
            MAX-ACCESS   read-only
            STATUS       current
            DESCRIPTION
                "The enable status of the instance's statistics switch."
            DEFVAL       { disable }
            ::= { zxStatisSwitchInstEntry 3 }

zxStatisSwitchInstInUnknowBps OBJECT-TYPE
            SYNTAX       Counter64
            UNITS         "Bytes per second"
            MAX-ACCESS   read-only
            STATUS       current
            DESCRIPTION
                "The threshold of warnning for input unknown unicast bytes 
                rate."
            ::= { zxStatisSwitchInstEntry 4 }

zxStatisSwitchInstInUnknowPps OBJECT-TYPE
            SYNTAX       Unsigned32
            UNITS         "Packets per second"
            MAX-ACCESS   read-only
            STATUS       current
            DESCRIPTION
                "The threshold of warnning for input unknown unicast packets 
                rate."
            ::= { zxStatisSwitchInstEntry 5 }

zxStatisSwitchInstInBroadBps OBJECT-TYPE
            SYNTAX       Counter64
            UNITS         "Bytes per second"
            MAX-ACCESS   read-only
            STATUS       current
            DESCRIPTION
                "The threshold of warnning for input broadcast bytes rate."
            ::= { zxStatisSwitchInstEntry 6}

zxStatisSwitchInstInBroadPps OBJECT-TYPE
            SYNTAX       Unsigned32
            UNITS         "Packets per second"
            MAX-ACCESS   read-only
            STATUS       current
            DESCRIPTION
                "The threshold of warnning for input broadcast packets rate."
            ::= { zxStatisSwitchInstEntry 7 }

zxStatisSwitchInstInDropBps OBJECT-TYPE
            SYNTAX       Counter64
            UNITS         "Bytes per second"
            MAX-ACCESS   read-only
            STATUS       current
            DESCRIPTION
                "The threshold of warnning for input dropped bytes rate."
            ::= { zxStatisSwitchInstEntry 8 }

zxStatisSwitchInstInDropPps OBJECT-TYPE
            SYNTAX       Unsigned32
            UNITS         "Packets per second"
            MAX-ACCESS   read-only
            STATUS       current
            DESCRIPTION
                "The threshold of warnning for input dropped packets rate."
            ::= { zxStatisSwitchInstEntry 9 }

--*************zxMonitorVpwsInstTable**************** 
zxMonitorVpwsInstTable OBJECT-TYPE
            SYNTAX     SEQUENCE OF ZxMonitorVpwsInstEntry
            MAX-ACCESS not-accessible
            STATUS     current
            DESCRIPTION
                "VPWS-for-monitor instance Table. This table contains
                 one entry per VPWS-for-monitor instance table."
            ::= { zxL2vpnInstance 6 }

zxMonitorVpwsInstEntry OBJECT-TYPE
            SYNTAX     ZxMonitorVpwsInstEntry
            MAX-ACCESS not-accessible
            STATUS     current
            DESCRIPTION
                "The parameter of a VPWS-for-monitor instance entity 
                containing."
            INDEX { zxMonitorVpwsInstName }
            ::= { zxMonitorVpwsInstTable 1 }

ZxMonitorVpwsInstEntry ::= SEQUENCE {
            zxMonitorVpwsInstName               DisplayString,
            zxMonitorVpwsInstDescription        DisplayString
            }

zxMonitorVpwsInstName OBJECT-TYPE
            SYNTAX       DisplayString  (SIZE(0..32))
            MAX-ACCESS   not-accessible
            STATUS       current
            DESCRIPTION
                "The name of the VPWS-for-monitor instance."
            ::= { zxMonitorVpwsInstEntry 1 }   

zxMonitorVpwsInstDescription OBJECT-TYPE
            SYNTAX       DisplayString  (SIZE(0..104))
            MAX-ACCESS   read-only
            STATUS       current
            DESCRIPTION
                "The description of the VPWS-for-monitor instance."
            ::= { zxMonitorVpwsInstEntry 2 } 

--*************zxAdminVplsInstTable**************** 
zxAdminVplsInstTable OBJECT-TYPE
            SYNTAX     SEQUENCE OF ZxAdminVplsInstEntry
            MAX-ACCESS not-accessible
            STATUS     current
            DESCRIPTION
                "Admin-VPLS instance Table. This table contains
                 one entry per admin-VPLS instance table."
            ::= { zxL2vpnInstance 7 }

zxAdminVplsInstEntry OBJECT-TYPE
            SYNTAX     ZxAdminVplsInstEntry
            MAX-ACCESS not-accessible
            STATUS     current
            DESCRIPTION
                "The parameter of an admin-VPLS instance entity containing."
            INDEX { zxAdminVplsInstName }
            ::= { zxAdminVplsInstTable 1 }

ZxAdminVplsInstEntry ::= SEQUENCE {
            zxAdminVplsInstName                 DisplayString,
            zxAdminVplsInstDescription          DisplayString
            }

zxAdminVplsInstName OBJECT-TYPE
            SYNTAX       DisplayString  (SIZE(0..32))
            MAX-ACCESS   not-accessible
            STATUS       current
            DESCRIPTION
                "The name of the admin-VPLS instance."
            ::= { zxAdminVplsInstEntry 1 }   

zxAdminVplsInstDescription OBJECT-TYPE
            SYNTAX       DisplayString  (SIZE(0..104))
            MAX-ACCESS   read-only
            STATUS       current
            DESCRIPTION
                "The description of the admin-VPLS instance."
            ::= { zxAdminVplsInstEntry 2 } 

--*************zxPwInstBindTable**************** 
zxPwInstBindTable OBJECT-TYPE
            SYNTAX     SEQUENCE OF ZxPwInstBindEntry
            MAX-ACCESS not-accessible
            STATUS     current
            DESCRIPTION
                "PW bind Table. This table contains
                 one entry per PW bind table."        
            ::= { zxL2vpnPW 1 }

zxPwInstBindEntry OBJECT-TYPE
            SYNTAX     ZxPwInstBindEntry
            MAX-ACCESS not-accessible
            STATUS     current
            DESCRIPTION
                "The parameter of a PW bind entity containing "
            INDEX { zxPwInstBindInstName , zxPwInstBindPwName }
            ::= { zxPwInstBindTable 1 }

ZxPwInstBindEntry ::= SEQUENCE {
            zxPwInstBindInstName                DisplayString,
            zxPwInstBindPwName                  DisplayString,
            zxPwInstBindSplitHorizon            INTEGER,
            zxPwInstBindSplitHorizonScope       DisplayString
            }

zxPwInstBindInstName OBJECT-TYPE
            SYNTAX       DisplayString  (SIZE(0..32))
            MAX-ACCESS   read-only
            STATUS       current
            DESCRIPTION
                "The name of the instance in the bind."
            ::= { zxPwInstBindEntry 1 }   

zxPwInstBindPwName OBJECT-TYPE
            SYNTAX       DisplayString  (SIZE(0..31))
            MAX-ACCESS   read-only
            STATUS       current
            DESCRIPTION
                "The name of the PW in the bind."
            ::= { zxPwInstBindEntry 2 } 

zxPwInstBindSplitHorizon OBJECT-TYPE
            SYNTAX       INTEGER{
            spokeOrNull(0),
            hub(1)
            }
            MAX-ACCESS   read-only
            STATUS       current
            DESCRIPTION
                "The split horizon flag of the PW bind."
            ::= { zxPwInstBindEntry 3 } 

zxPwInstBindSplitHorizonScope OBJECT-TYPE
            SYNTAX       DisplayString  (SIZE(0..51))
            MAX-ACCESS   read-only
            STATUS       current
            DESCRIPTION
                "The split horizon scope of the PW bind."
            ::= { zxPwInstBindEntry 4 }

--*************zxPwObjectTable**************** 
zxPwObjectTable OBJECT-TYPE
            SYNTAX     SEQUENCE OF ZxPwObjectEntry
            MAX-ACCESS not-accessible
            STATUS     current
            DESCRIPTION
                "PW object Table. This table contains
                 one entry per PW object table."        
            ::= { zxL2vpnPW 2 }

zxPwObjectEntry OBJECT-TYPE
            SYNTAX     ZxPwObjectEntry
            MAX-ACCESS not-accessible
            STATUS     current
            DESCRIPTION
                "The parameter of a PW object entity containing "
            INDEX { zxPwObjectInstName , zxPwObjectPwName }
            ::= { zxPwObjectTable 1 }

ZxPwObjectEntry ::= SEQUENCE {
            zxPwObjectInstName                  DisplayString,
            zxPwObjectPwName                    DisplayString, 
            zxPwObjectPwRoler                   INTEGER, 
            zxPwObjectNegbPeerId                IpAddress,
            zxPwObjectNegbVcid                  Unsigned32,
            zxPwObjectPwType                    L2vpnPWType,
            zxPwObjectControlWord               INTEGER,
            zxPwObjectVccvBfd                   INTEGER,
            zxPwObjectBfdRaw                    INTEGER,
            zxPwObjectBfdStatus                 INTEGER,
            zxPwObjectSignalType                INTEGER,
            zxPwObjectLocalLabel                Unsigned32,
            zxPwObjectRemoteLabel               Unsigned32,
            zxPwObjectTunlPlcyName              DisplayString,
            zxPwObjectGroupId                   Unsigned32,
            zxPwObjectPwTemplateName            DisplayString,
            zxPwObjectTrackName                 DisplayString,
            zxPwObjectBandWidth                 Unsigned32,
            zxPwObjectPwEnStatus                INTEGER,
            zxPwObjectVcidExtend                Unsigned32,
            zxPwObjectRemoteSiteID              Unsigned32,
            zxPwObjectBandWidthCBS              Unsigned32,
            zxPwObjectBandWidthPIR              Unsigned32,
            zxPwObjectBandWidthEBS              Unsigned32,
            zxPwObjectStatisEnStatus            INTEGER,
            zxPwObjectInBRateLow                Unsigned32,
            zxPwObjectInBRateHigh               Unsigned32,
            zxPwObjectOutBRateLow               Unsigned32,
            zxPwObjectOutBRateHigh              Unsigned32,
            zxPwObjectVccvStaticCC              INTEGER,
            zxPwObjectCwLBit                    INTEGER,
            zxPwObjectSdEnStatus                INTEGER,
            zxPwObjectLimitMode                 INTEGER,
            zxPwObjectLimitCIR                  Unsigned32,
            zxPwObjectLimitCBS                  Unsigned32,
            zxPwObjectLimitPIR                  Unsigned32,
            zxPwObjectLimitPBS                  Unsigned32,
            zxPwObjectPwTypeReverse             INTEGER,
            zxPwObjectControlWordForce          INTEGER,
            zxPwObjectFrrIgnore                 INTEGER,
            zxPwObjectOamMappingAbort           INTEGER,
            zxPwObjectInUnknowBps               Counter64,
            zxPwObjectInUnknowPps               Unsigned32,
            zxPwObjectInBroadBps                Counter64,
            zxPwObjectInBroadPps                Unsigned32,
            zxPwObjectInDropBps                 Counter64,
            zxPwObjectInDropPps                 Unsigned32,
            zxPwObjectTunnelDstIpv6             Ipv6Address
            }

zxPwObjectInstName OBJECT-TYPE
            SYNTAX       DisplayString  (SIZE(0..32))
            MAX-ACCESS   read-only
            STATUS       current
            DESCRIPTION
                "The name of the instance which the PW object belongs to."
            ::= { zxPwObjectEntry 1 }

zxPwObjectPwName OBJECT-TYPE
            SYNTAX       DisplayString  (SIZE(0..31))
            MAX-ACCESS   read-only
            STATUS       current
            DESCRIPTION
                "The name of the PW object."
            ::= { zxPwObjectEntry 2 }

zxPwObjectPwRoler OBJECT-TYPE
            SYNTAX       INTEGER{
            none(0),
            master(1),
            slave(2)
            }
            MAX-ACCESS   read-only
            STATUS       current
            DESCRIPTION
                "The master/slave role of the PW object."
            ::= { zxPwObjectEntry 3 } 

zxPwObjectNegbPeerId OBJECT-TYPE
            SYNTAX       IpAddress
            MAX-ACCESS   read-only
            STATUS       current
            DESCRIPTION
                "The remote peer's IP address of the PW object."
            ::= { zxPwObjectEntry 4 } 

zxPwObjectNegbVcid OBJECT-TYPE
            SYNTAX       Unsigned32
            MAX-ACCESS   read-only
            STATUS       current
            DESCRIPTION
                "The VCID of the PW object."
            ::= { zxPwObjectEntry 5 }  

zxPwObjectPwType OBJECT-TYPE
            SYNTAX       L2vpnPWType
            MAX-ACCESS   read-only
            STATUS       current
            DESCRIPTION
                "The PW type of the PW object."
            ::= { zxPwObjectEntry 6 } 

zxPwObjectControlWord OBJECT-TYPE
            SYNTAX       INTEGER{
            notPreferred(0),
            preferred(1)
            }
            MAX-ACCESS   read-only
            STATUS       current
            DESCRIPTION
                "The control-word capability of the PW object."
            ::= { zxPwObjectEntry 7 } 

zxPwObjectVccvBfd OBJECT-TYPE
            SYNTAX       INTEGER{
            disable(0),
            enable(1)
            }
            MAX-ACCESS   read-only
            STATUS       current
            DESCRIPTION
                "The BFD capability of the PW object."
            ::= { zxPwObjectEntry 8 }

zxPwObjectBfdRaw OBJECT-TYPE
            SYNTAX       INTEGER{
            disable(0),
            enable(1)
            }
            MAX-ACCESS   read-only
            STATUS       current
            DESCRIPTION
                "The BFD raw encapsulation capability of the PW object."
            ::= { zxPwObjectEntry 9 }

zxPwObjectBfdStatus OBJECT-TYPE
            SYNTAX       INTEGER{
            disable(0),
            enable(1)
            }
            MAX-ACCESS   read-only
            STATUS       current
            DESCRIPTION
                "The BFD signal status capability of the PW object."
            ::= { zxPwObjectEntry 10 }

zxPwObjectSignalType OBJECT-TYPE
            SYNTAX       INTEGER{
            static(0),
            fec128(1),
            fec129(2)
            }
            MAX-ACCESS   read-only
            STATUS       current
            DESCRIPTION
                "The signal type of the PW object."
            ::= { zxPwObjectEntry 11 }  

zxPwObjectLocalLabel OBJECT-TYPE
            SYNTAX       Unsigned32(0..1048575)
            MAX-ACCESS   read-only
            STATUS       current
            DESCRIPTION
                "The local label of the PW object."
            ::= { zxPwObjectEntry 12 }  

zxPwObjectRemoteLabel OBJECT-TYPE
            SYNTAX       Unsigned32(0..1048575)
            MAX-ACCESS   read-only
            STATUS       current
            DESCRIPTION
                "The remote label of the PW object."
            ::= { zxPwObjectEntry 13 } 

zxPwObjectTunlPlcyName OBJECT-TYPE
            SYNTAX       DisplayString  (SIZE(0..63))
            MAX-ACCESS   read-only
            STATUS       current
            DESCRIPTION
                "The name of tunnel policy that bind to the PW object"
            ::= { zxPwObjectEntry 14 }

zxPwObjectGroupId OBJECT-TYPE
            SYNTAX       Unsigned32(0..63)
            MAX-ACCESS   read-only
            STATUS       current
            DESCRIPTION
                "The group ID of the PW object."
            ::= { zxPwObjectEntry 15 } 

zxPwObjectPwTemplateName OBJECT-TYPE
            SYNTAX       DisplayString  (SIZE(0..31))
            MAX-ACCESS   read-only
            STATUS       current
            DESCRIPTION
                "The name of PW class that bind to the PW object"
            ::= { zxPwObjectEntry 16 }

zxPwObjectTrackName OBJECT-TYPE
            SYNTAX       DisplayString  (SIZE(0..31))
            MAX-ACCESS   read-only
            STATUS       current
            DESCRIPTION
                "The name of track object that bind to the PW object"
            ::= { zxPwObjectEntry 17 }

zxPwObjectBandWidth OBJECT-TYPE
            SYNTAX       Unsigned32
            MAX-ACCESS   read-only
            STATUS       current
            DESCRIPTION
                "The bandwidth value of the PW object."
            ::= { zxPwObjectEntry 18 }

zxPwObjectPwEnStatus OBJECT-TYPE
            SYNTAX       INTEGER{
            disable(0),
            enable(1)
            }
            MAX-ACCESS   read-only
            STATUS       current
            DESCRIPTION
                "The enable status of the PW object."
            ::= { zxPwObjectEntry 19 } 

zxPwObjectVcidExtend OBJECT-TYPE
            SYNTAX       Unsigned32
            MAX-ACCESS   read-only
            STATUS       current
            DESCRIPTION
                "The extend VCID for 129 type of the PW object."
            ::= { zxPwObjectEntry 20 }

zxPwObjectRemoteSiteID OBJECT-TYPE
            SYNTAX       Unsigned32
            MAX-ACCESS   read-only
            STATUS       current
            DESCRIPTION
                "The remote pw ID of the PW object."
            ::= { zxPwObjectEntry 21 } 

zxPwObjectBandWidthCBS OBJECT-TYPE
            SYNTAX       Unsigned32
            MAX-ACCESS   read-only
            STATUS       current
            DESCRIPTION
                "The Committed Burst Size value of the PW object."
            ::= { zxPwObjectEntry 22 }

zxPwObjectBandWidthPIR OBJECT-TYPE
            SYNTAX       Unsigned32
            MAX-ACCESS   read-only
            STATUS       current
            DESCRIPTION
                "The Peak Information Rate value of the PW object."
            ::= { zxPwObjectEntry 23 }

zxPwObjectBandWidthEBS OBJECT-TYPE
            SYNTAX       Unsigned32
            MAX-ACCESS   read-only
            STATUS       current
            DESCRIPTION
                "The Excess Burst Size value of the PW object."
            ::= { zxPwObjectEntry 24 }

zxPwObjectStatisEnStatus OBJECT-TYPE
            SYNTAX       INTEGER{
            disable(1),
            enable(2)
            }
            MAX-ACCESS   read-only
            STATUS       current
            DESCRIPTION
                "The enable status of the PW traffic statistics."
            DEFVAL       { disable }
            ::= { zxPwObjectEntry 25 }

zxPwObjectInBRateLow OBJECT-TYPE
            SYNTAX       Unsigned32(0..4294967294)
            UNITS         "Bytes per second"
            MAX-ACCESS   read-only
            STATUS       current
            DESCRIPTION
                "The low threshold of warnning for input bytes rate."
            DEFVAL       { 0 }
            ::= { zxPwObjectEntry 26 }

zxPwObjectInBRateHigh OBJECT-TYPE
            SYNTAX       Unsigned32(1..4294967295)
            UNITS         "Bytes per second"
            MAX-ACCESS   read-only
            STATUS       current
            DESCRIPTION
                "The high threshold of warnning for input bytes rate."
            DEFVAL       { 4294967295 }
            ::= { zxPwObjectEntry 27 }  

zxPwObjectOutBRateLow OBJECT-TYPE
            SYNTAX       Unsigned32(0..4294967294)
            UNITS         "Bytes per second"
            MAX-ACCESS   read-only
            STATUS       current
            DESCRIPTION
                "The low threshold of warnning for output bytes rate."
            DEFVAL       { 0 }
            ::= { zxPwObjectEntry 28 }

zxPwObjectOutBRateHigh OBJECT-TYPE
            SYNTAX       Unsigned32(1..4294967295)
            UNITS         "Bytes per second"
            MAX-ACCESS   read-only
            STATUS       current
            DESCRIPTION
                "The high threshold of warnning for output bytes rate."
            DEFVAL       { 4294967295 }
            ::= { zxPwObjectEntry 29 }             

zxPwObjectVccvStaticCC OBJECT-TYPE
            SYNTAX       INTEGER{
            null(1),
            ttl(2),
            alertLabel(3),
            controlWord(4)
            }
            MAX-ACCESS   read-only
            STATUS       current
            DESCRIPTION
                "The static VCCV's CC type of the PW object."
            DEFVAL       { null }
            ::= { zxPwObjectEntry 30 }

zxPwObjectCwLBit OBJECT-TYPE
            SYNTAX       INTEGER{
            disable(1),
            enable(2)
            }
            MAX-ACCESS   read-only
            STATUS       current
            DESCRIPTION
                "The control-word L-bit capability of the PW object."
            DEFVAL       { enable }
            ::= { zxPwObjectEntry 31 }

zxPwObjectSdEnStatus OBJECT-TYPE
            SYNTAX       INTEGER{
            disable(1),
            enable(2)
            }
            MAX-ACCESS   read-only
            STATUS       current
            DESCRIPTION
                "The enable status  of the PW SD propagation."
            DEFVAL       { disable }
            ::= { zxPwObjectEntry 32 }

zxPwObjectLimitMode OBJECT-TYPE
            SYNTAX       INTEGER{
            null(1),
            blind(2),
            aware(3)
            }
            MAX-ACCESS   read-only
            STATUS       current
            DESCRIPTION
                "The mode of PW rate limit."
            DEFVAL       { null }
            ::= { zxPwObjectEntry 33 }

zxPwObjectLimitCIR OBJECT-TYPE
            SYNTAX       Unsigned32(8..20000000)
            UNITS         "KBytes per second"
            MAX-ACCESS   read-only
            STATUS       current
            DESCRIPTION
                "The Committed Information Rate value of PW rate limit. 
                Invalid value is 0."
            DEFVAL       { 0 }
            ::= { zxPwObjectEntry 34 }  

zxPwObjectLimitCBS OBJECT-TYPE
            SYNTAX       Unsigned32(1..5120000)
            UNITS         "KBytes"
            MAX-ACCESS   read-only
            STATUS       current
            DESCRIPTION
                "The Committed Burst Size value of PW rate limit. Invalid 
                value is 0."
            DEFVAL       { 0 }
            ::= { zxPwObjectEntry 35 }  

zxPwObjectLimitPIR OBJECT-TYPE
            SYNTAX       Unsigned32(8..20000000)
            UNITS         "KBytes per second"
            MAX-ACCESS   read-only
            STATUS       current
            DESCRIPTION
                "The Peak Information Rate value of PW rate limit. Invalid 
                value is 0."
            DEFVAL       { 0 }
            ::= { zxPwObjectEntry 36 } 

zxPwObjectLimitPBS OBJECT-TYPE
            SYNTAX       Unsigned32(1..5120000)
            UNITS         "KBytes"
            MAX-ACCESS   read-only
            STATUS       current
            DESCRIPTION
                "The Peak Burst Size value of PW rate limit. Invalid value is 
                0."
            DEFVAL       { 0 }
            ::= { zxPwObjectEntry 37 } 

zxPwObjectPwTypeReverse OBJECT-TYPE
            SYNTAX       INTEGER{
            disable(1),
            enable(2)
            }
            MAX-ACCESS   read-only
            STATUS       current
            DESCRIPTION
                "The reversing PW type flag of the PW object."
            DEFVAL       { disable }
            ::= { zxPwObjectEntry 38 }

zxPwObjectControlWordForce OBJECT-TYPE
            SYNTAX       INTEGER{
            null(1),
            unused(2),
            used(3)
            }
            MAX-ACCESS   read-only
            STATUS       current
            DESCRIPTION
                "The force control word parameter of the PW object."
            DEFVAL       { null }
            ::= { zxPwObjectEntry 39 }

zxPwObjectFrrIgnore OBJECT-TYPE
            SYNTAX       INTEGER{
            disable(1),
            enable(2)
            }
            MAX-ACCESS   read-only
            STATUS       current
            DESCRIPTION
                "The Flag of ignoring FRR of the PW object."
            DEFVAL       { disable }
            ::= { zxPwObjectEntry 40 }
            
zxPwObjectOamMappingAbort OBJECT-TYPE
            SYNTAX       INTEGER{
            disable(1),
            enable(2)
            }
            MAX-ACCESS   read-only
            STATUS       current
            DESCRIPTION
                "The Flag of aborting OAM mapping of the PW object."
            DEFVAL       { disable }
            ::= { zxPwObjectEntry 41 }
            
zxPwObjectInUnknowBps OBJECT-TYPE
            SYNTAX       Counter64
            UNITS         "Bytes per second"
            MAX-ACCESS   read-only
            STATUS       current
            DESCRIPTION
                "The threshold of warnning for input unknown unicast bytes 
                rate."
            ::= { zxPwObjectEntry 42 }

zxPwObjectInUnknowPps OBJECT-TYPE
            SYNTAX       Unsigned32
            UNITS         "Packets per second"
            MAX-ACCESS   read-only
            STATUS       current
            DESCRIPTION
                "The threshold of warnning for input unknown unicast packets 
                rate."
            ::= { zxPwObjectEntry 43 }

zxPwObjectInBroadBps OBJECT-TYPE
            SYNTAX       Counter64
            UNITS         "Bytes per second"
            MAX-ACCESS   read-only
            STATUS       current
            DESCRIPTION
                "The threshold of warnning for input broadcast bytes rate."
            ::= { zxPwObjectEntry 44 }

zxPwObjectInBroadPps OBJECT-TYPE
            SYNTAX       Unsigned32
            UNITS         "Packets per second"
            MAX-ACCESS   read-only
            STATUS       current
            DESCRIPTION
                "The threshold of warnning for input broadcast packets rate."
            ::= { zxPwObjectEntry 45 }

zxPwObjectInDropBps OBJECT-TYPE
            SYNTAX       Counter64
            UNITS         "Bytes per second"
            MAX-ACCESS   read-only
            STATUS       current
            DESCRIPTION
                "The threshold of warnning for input dropped bytes rate."
            ::= { zxPwObjectEntry 46 }

zxPwObjectInDropPps OBJECT-TYPE
            SYNTAX       Unsigned32
            UNITS         "Packets per second"
            MAX-ACCESS   read-only
            STATUS       current
            DESCRIPTION
                "The threshold of warnning for input dropped packets rate."
            ::= { zxPwObjectEntry 47 }

zxPwObjectTunnelDstIpv6 OBJECT-TYPE
            SYNTAX       Ipv6Address
            MAX-ACCESS   read-only
            STATUS       current
            DESCRIPTION
                "The IPv6 address of tunnel destination."
            ::= { zxPwObjectEntry 48 }
            
--*************zxPwProtectBindTable**************** 
zxPwProtectBindTable OBJECT-TYPE
            SYNTAX     SEQUENCE OF ZxPwProtectBindEntry
            MAX-ACCESS not-accessible
            STATUS     current
            DESCRIPTION
                "PW protect bind Table. This table contains
                 one entry per PW protect bind table."        
            ::= { zxL2vpnPW 3 }

zxPwProtectBindEntry OBJECT-TYPE
            SYNTAX     ZxPwProtectBindEntry
            MAX-ACCESS not-accessible
            STATUS     current
            DESCRIPTION
                "The parameter of a PW protect bind entity containing "
            INDEX { zxPwProtectBindInstName , zxPwProtectBindProtectedPwName , 
                zxPwProtectBindPwName }
            ::= { zxPwProtectBindTable 1 }

ZxPwProtectBindEntry ::= SEQUENCE {
            zxPwProtectBindInstName             DisplayString,
            zxPwProtectBindProtectedPwName      DisplayString,
            zxPwProtectBindPwName               DisplayString,
            zxPwProtectBindInterChassis         INTEGER,
            zxPwProtectBindDistance             Unsigned32
            }

zxPwProtectBindInstName OBJECT-TYPE
            SYNTAX       DisplayString  (SIZE(0..32))
            MAX-ACCESS   read-only
            STATUS       current
            DESCRIPTION
                "The name of the instance in the bind."
            ::= { zxPwProtectBindEntry 1 }

zxPwProtectBindProtectedPwName OBJECT-TYPE
            SYNTAX       DisplayString  (SIZE(0..31))
            MAX-ACCESS   read-only
            STATUS       current
            DESCRIPTION
                "The name of the protected PW in the bind."
            ::= { zxPwProtectBindEntry 2 }

zxPwProtectBindPwName OBJECT-TYPE
            SYNTAX       DisplayString  (SIZE(0..31))
            MAX-ACCESS   read-only
            STATUS       current
            DESCRIPTION
                "The name of the protect PW in the bind."
            ::= { zxPwProtectBindEntry 3 } 

zxPwProtectBindInterChassis OBJECT-TYPE
            SYNTAX       INTEGER{
            local(1),
            interChassis(2),
            pwCoworker(3)
            }
            MAX-ACCESS   read-only
            STATUS       current
            DESCRIPTION
                "The inter-chassis flag of the PW protect bind."
            ::= { zxPwProtectBindEntry 5 }

zxPwProtectBindDistance OBJECT-TYPE
            SYNTAX       Unsigned32(0..255)
            MAX-ACCESS   read-only
            STATUS       current
            DESCRIPTION
                "The distance between back-up PW and protected PW-segment."
            DEFVAL       { 0 }
            ::= { zxPwProtectBindEntry 6 } 

--*************zxPwProtectStrategyTable**************** 
zxPwProtectStrategyTable OBJECT-TYPE
            SYNTAX     SEQUENCE OF ZxPwProtectStrategyEntry
            MAX-ACCESS not-accessible
            STATUS     current
            DESCRIPTION
                "PW protect strategy Table. This table contains
                 one entry per PW protect strategy table."        
            ::= { zxL2vpnPW 4 }

zxPwProtectStrategyEntry OBJECT-TYPE
            SYNTAX     ZxPwProtectStrategyEntry
            MAX-ACCESS not-accessible
            STATUS     current
            DESCRIPTION
                "The parameter of a PW protect strategy entity containing "
            INDEX { zxPwProtectStrategyInstName , zxPwProtectStrategyIfName }
            ::= { zxPwProtectStrategyTable 1 }

ZxPwProtectStrategyEntry ::= SEQUENCE {
            zxPwProtectStrategyInstName         DisplayString,
            zxPwProtectStrategyIfName           DisplayString,
            zxPwProtectStrategyProtectType      INTEGER,
            zxPwProtectStrategyProtectStrategy  INTEGER,
            zxPwProtectStrategyDirection        INTEGER,
            zxPwProtectStrategyReceiver         INTEGER,
            zxPwProtectStrategyPattern          INTEGER,
            zxPwProtectStrategyAcType           INTEGER
            }

zxPwProtectStrategyInstName OBJECT-TYPE
            SYNTAX       DisplayString  (SIZE(0..32))
            MAX-ACCESS   read-only
            STATUS       current
            DESCRIPTION
                "The name of the instance of the PW which is configured with 
                the PW protect strategy."
            ::= { zxPwProtectStrategyEntry 1 } 

zxPwProtectStrategyIfName OBJECT-TYPE
            SYNTAX       DisplayString  (SIZE(0..31))
            MAX-ACCESS   read-only
            STATUS       current
            DESCRIPTION
                "The name of the PW which is configured with the PW protect 
                strategy."
            ::= { zxPwProtectStrategyEntry 2 }

zxPwProtectStrategyProtectType OBJECT-TYPE
            SYNTAX       INTEGER{
            oneByOne(1),
            onePlusOne(2)
            }
            MAX-ACCESS   read-only
            STATUS       current
            DESCRIPTION
                "The protect type of the PW protect strategy."
            ::= { zxPwProtectStrategyEntry 3 }

zxPwProtectStrategyProtectStrategy OBJECT-TYPE
            SYNTAX       INTEGER{
            null(0),
            aps(1),
            mcapsMaster(2),
            mcapsBackup(3)
            }
            MAX-ACCESS   read-only
            STATUS       current
            DESCRIPTION
                "The protect strategy of the PW protect strategy."
            ::= { zxPwProtectStrategyEntry 4 }

zxPwProtectStrategyDirection OBJECT-TYPE
            SYNTAX       INTEGER{
            single(1),
            double(2)
            }
            MAX-ACCESS   read-only
            STATUS       current
            DESCRIPTION
                "The protected direction of the PW protect strategy."
            ::= { zxPwProtectStrategyEntry 5 }  

zxPwProtectStrategyReceiver OBJECT-TYPE
            SYNTAX       INTEGER{
            single(1),
            double(2)
            }
            MAX-ACCESS   read-only
            STATUS       current
            DESCRIPTION
                "The protected receiver of the PW protect strategy."
            ::= { zxPwProtectStrategyEntry 6 }      

zxPwProtectStrategyPattern OBJECT-TYPE
            SYNTAX       INTEGER{
            local(1),
            interChassis(2),
            pwCoworker(3)
            }
            MAX-ACCESS   read-only
            STATUS       current
            DESCRIPTION
                "The protect pattern of the PW protect strategy."
            ::= { zxPwProtectStrategyEntry 7 }

zxPwProtectStrategyAcType OBJECT-TYPE
            SYNTAX       INTEGER{
            null(1),
            onePlusOne(2),
            oneByOne(3),
            loadBalance(4)
            }
            MAX-ACCESS   read-only
            STATUS       obsolete
            DESCRIPTION
                "The AC protect type of the PW protect strategy."
            DEFVAL       { null }
            ::= { zxPwProtectStrategyEntry 8 }

--*************zxPwProtectableTable**************** 
zxPwProtectableTable OBJECT-TYPE
            SYNTAX     SEQUENCE OF ZxPwProtectableEntry
            MAX-ACCESS not-accessible
            STATUS     current
            DESCRIPTION
                "PW protectable Table. This table contains
                 one entry per PW protectable table."        
            ::= { zxL2vpnPW 5 }

zxPwProtectableEntry OBJECT-TYPE
            SYNTAX     ZxPwProtectableEntry
            MAX-ACCESS not-accessible
            STATUS     current
            DESCRIPTION
                "The parameter of a PW protectable entity containing "
            INDEX { zxPwProtectableInstName , zxPwProtectableIfName }
            ::= { zxPwProtectableTable 1 }

ZxPwProtectableEntry ::= SEQUENCE {
            zxPwProtectableInstName             DisplayString,
            zxPwProtectableIfName               DisplayString,
            zxPwProtectablePfsBits              INTEGER,
            zxPwProtectablePfsAdvertise         INTEGER,
            zxPwProtectableGroupType            INTEGER,
            zxPwProtectableMcRole               INTEGER
            }

zxPwProtectableInstName OBJECT-TYPE
            SYNTAX       DisplayString  (SIZE(0..32))
            MAX-ACCESS   read-only
            STATUS       current
            DESCRIPTION
                "The name of the instance of the PW which is configured with 
                the PW protectable."
            ::= { zxPwProtectableEntry 1 } 

zxPwProtectableIfName OBJECT-TYPE
            SYNTAX       DisplayString  (SIZE(0..31))
            MAX-ACCESS   read-only
            STATUS       current
            DESCRIPTION
                "The name of the PW which is configured with the PW 
                protectable."
            ::= { zxPwProtectableEntry 2 }

zxPwProtectablePfsBits OBJECT-TYPE
            SYNTAX       INTEGER{
            null(0),
            independent(1),
            master(2),
            slave(3)
            }
            MAX-ACCESS   read-only
            STATUS       current
            DESCRIPTION
                "The negotiation type of the PW protectable."
            ::= { zxPwProtectableEntry 3 }

zxPwProtectablePfsAdvertise OBJECT-TYPE
            SYNTAX       INTEGER{
            regardOfAC(1),
            regardlessOfAC(2)
            }
            MAX-ACCESS   read-only
            STATUS       current
            DESCRIPTION
                "The advertise type of the PW protectable."
            DEFVAL       { regardOfAC }
            ::= { zxPwProtectableEntry 4 }
            
zxPwProtectableGroupType OBJECT-TYPE
            SYNTAX       INTEGER{
            pw(1),
            ac(2)
            }
            MAX-ACCESS   read-only
            STATUS       current
            DESCRIPTION
                "The protect group type of the PW protectable."
            ::= { zxPwProtectableEntry 5 }

zxPwProtectableMcRole OBJECT-TYPE
            SYNTAX       INTEGER{
            null(1),
            mcMaster(2),
            mcSlave(3)
            }
            MAX-ACCESS   read-only
            STATUS       current
            DESCRIPTION
                "The multi-chassis role of the PW protectable."
            DEFVAL       { null }
            ::= { zxPwProtectableEntry 6 }
            
--*************zxPwTemplateTable**************** 
zxPwTemplateTable OBJECT-TYPE
            SYNTAX     SEQUENCE OF ZxPwTemplateEntry
            MAX-ACCESS not-accessible
            STATUS     current
            DESCRIPTION
                "PW template Table. This table contains
                 one entry per PW template table."        
            ::= { zxL2vpnPW 6 }

zxPwTemplateEntry OBJECT-TYPE
            SYNTAX     ZxPwTemplateEntry
            MAX-ACCESS not-accessible
            STATUS     current
            DESCRIPTION
                "The parameter of a PW template entity containing "
            INDEX { zxPwTemplateName }
            ::= { zxPwTemplateTable 1 }

ZxPwTemplateEntry ::= SEQUENCE {
            zxPwTemplateName                    DisplayString,
            zxPwTemplateCword                   INTEGER,
            zxPwTemplateCWordSequencing         INTEGER,
            zxPwTemplatePwVccvBfd               INTEGER,
            zxPwTemplatePwVccvBfdRaw            INTEGER,
            zxPwTemplatePwVccvBfdStatus         INTEGER,
            zxPwTemplateKeepIngressTag          INTEGER,
            zxPwTemplateVccvStaticCC            INTEGER
            }

zxPwTemplateName OBJECT-TYPE
            SYNTAX       DisplayString  (SIZE(0..31))
            MAX-ACCESS   read-only
            STATUS       current
            DESCRIPTION
                "The name of the PW template."
            ::= { zxPwTemplateEntry 1 }    

zxPwTemplateCword OBJECT-TYPE
            SYNTAX       INTEGER{
            notPreferred(0),
            preferred(1)
            }
            MAX-ACCESS   read-only
            STATUS       current
            DESCRIPTION
                "The control-word capability of the PW template."
            ::= { zxPwTemplateEntry 2 }   

zxPwTemplateCWordSequencing OBJECT-TYPE
            SYNTAX       INTEGER{
            disable(0),
            enable(1)
            }
            MAX-ACCESS   read-only
            STATUS       current
            DESCRIPTION
                "The control-word sequence capability of the PW template."
            ::= { zxPwTemplateEntry 3 }

zxPwTemplatePwVccvBfd OBJECT-TYPE
            SYNTAX       INTEGER{
            disable(0),
            enable(1)
            }
            MAX-ACCESS   read-only
            STATUS       current
            DESCRIPTION
                "The BFD capability of the PW template."
            ::= { zxPwTemplateEntry 4 }    

zxPwTemplatePwVccvBfdRaw OBJECT-TYPE
            SYNTAX       INTEGER{
            disable(0),
            enable(1)
            }
            MAX-ACCESS   read-only
            STATUS       current
            DESCRIPTION
                "The BFD raw encapsulation capability of the PW template."
            ::= { zxPwTemplateEntry 5 }  

zxPwTemplatePwVccvBfdStatus OBJECT-TYPE
            SYNTAX       INTEGER{
            disable(0),
            enable(1)
            }
            MAX-ACCESS   read-only
            STATUS       current
            DESCRIPTION
                "The BFD signal status capability of the PW template."
            ::= { zxPwTemplateEntry 6 }

zxPwTemplateKeepIngressTag OBJECT-TYPE
            SYNTAX       INTEGER{
            disable(0),
            enable(1)
            }
            MAX-ACCESS   read-only
            STATUS       current
            DESCRIPTION
                "The keep ingress tag capability of the PW template."
            ::= { zxPwTemplateEntry 7 }

zxPwTemplateVccvStaticCC OBJECT-TYPE
            SYNTAX       INTEGER{
            null(1),
            ttl(2),
            alertLabel(3),
            controlWord(4)
            }
            MAX-ACCESS   read-only
            STATUS       current
            DESCRIPTION
                "The static VCCV's CC type of  the PW template."
            DEFVAL       { null }
            ::= { zxPwTemplateEntry 9 }

--*************zxPwProtectIccpTable**************** 
zxPwProtectIccpTable OBJECT-TYPE
            SYNTAX     SEQUENCE OF ZxPwProtectIccpEntry
            MAX-ACCESS not-accessible
            STATUS     current
            DESCRIPTION
                "PW ICCP protect Table. This table contains
                 one entry per PW ICCP protect table."        
            ::= { zxL2vpnPW 7 }

zxPwProtectIccpEntry OBJECT-TYPE
            SYNTAX     ZxPwProtectIccpEntry
            MAX-ACCESS not-accessible
            STATUS     current
            DESCRIPTION
                "The parameter of a PW ICCP protect entity containing "
            INDEX { zxPwProtectIccpInstName , zxPwProtectIccpIfName }
            ::= { zxPwProtectIccpTable 1 }

ZxPwProtectIccpEntry ::= SEQUENCE {
            zxPwProtectIccpInstName             DisplayString,
            zxPwProtectIccpIfName               DisplayString,
            zxPwProtectIccpGroupId              Unsigned32,
            zxPwProtectIccpGroupRoid            Counter64
            }

zxPwProtectIccpInstName OBJECT-TYPE
            SYNTAX       DisplayString  (SIZE(0..32))
            MAX-ACCESS   not-accessible
            STATUS       current
            DESCRIPTION
                "The name of the instance of the PW which is configured with 
                the PW ICCP protect."
            ::= { zxPwProtectIccpEntry 1 }

zxPwProtectIccpIfName OBJECT-TYPE
            SYNTAX       DisplayString  (SIZE(0..31))
            MAX-ACCESS   not-accessible
            STATUS       current
            DESCRIPTION
                "The name of the PW which is configured with the PW ICCP 
                protect."
            ::= { zxPwProtectIccpEntry 2 }

zxPwProtectIccpGroupId OBJECT-TYPE
            SYNTAX       Unsigned32(1..4294967295)
            MAX-ACCESS   read-only
            STATUS       current
            DESCRIPTION
                "The group ID of the PW ICCP protect."
            ::= { zxPwProtectIccpEntry 3 }

zxPwProtectIccpGroupRoid OBJECT-TYPE
            SYNTAX       Counter64
            MAX-ACCESS   read-only
            STATUS       current
            DESCRIPTION
                "The group ROID of the PW ICCP protect."
            ::= { zxPwProtectIccpEntry 4 }

--*************zxPwProtectMcSelectTable**************** 
zxPwProtectMcSelectTable OBJECT-TYPE
            SYNTAX     SEQUENCE OF ZxPwProtectMcSelectEntry
            MAX-ACCESS not-accessible
            STATUS     current
            DESCRIPTION
                "PW MC selection protect Table. This table contains
                 one entry per PW MC selection protect table."        
            ::= { zxL2vpnPW 8 }

zxPwProtectMcSelectEntry OBJECT-TYPE
            SYNTAX     ZxPwProtectMcSelectEntry
            MAX-ACCESS not-accessible
            STATUS     current
            DESCRIPTION
                "The parameter of a PW MC selection protect entity containing "
            INDEX { zxPwProtectMcSelectInstName , zxPwProtectMcSelectIfName }
            ::= { zxPwProtectMcSelectTable 1 }

ZxPwProtectMcSelectEntry ::= SEQUENCE {
            zxPwProtectMcSelectInstName         DisplayString,
            zxPwProtectMcSelectIfName           DisplayString,
            zxPwProtectMcSelectType             INTEGER
            }

zxPwProtectMcSelectInstName OBJECT-TYPE
            SYNTAX       DisplayString  (SIZE(0..32))
            MAX-ACCESS   not-accessible
            STATUS       current
            DESCRIPTION
                "The name of the instance of the PW which is configured with 
                the PW MC selection protect."
            ::= { zxPwProtectMcSelectEntry 1 }

zxPwProtectMcSelectIfName OBJECT-TYPE
            SYNTAX       DisplayString  (SIZE(0..31))
            MAX-ACCESS   not-accessible
            STATUS       current
            DESCRIPTION
                "The name of the PW which is configured with the PW MC 
                selection protect."
            ::= { zxPwProtectMcSelectEntry 2 }

zxPwProtectMcSelectType OBJECT-TYPE
            SYNTAX       INTEGER{
            basic(1),
            oamMapping(2)
            }            
            MAX-ACCESS   read-only
            STATUS       current
            DESCRIPTION
                "The type of the PW MC selection protect."
            ::= { zxPwProtectMcSelectEntry 3 }

--*************zxPwListTable**************** 
zxPwListTable OBJECT-TYPE
            SYNTAX     SEQUENCE OF ZxPwListEntry
            MAX-ACCESS not-accessible
            STATUS     current
            DESCRIPTION
                "PW list Table. This table contains one entry per PW list 
                table."
            ::= { zxL2vpnPW 9 }

zxPwListEntry OBJECT-TYPE
            SYNTAX     ZxPwListEntry
            MAX-ACCESS not-accessible
            STATUS     current
            DESCRIPTION
                "The parameter of a PW list entity containing "
            INDEX { zxPwListId }
            ::= { zxPwListTable 1 }

ZxPwListEntry ::= SEQUENCE {
            zxPwListId                          Unsigned32,
            zxPwListMasterPwName                DisplayString
            }

zxPwListId OBJECT-TYPE
            SYNTAX       Unsigned32(1..256)
            MAX-ACCESS   not-accessible
            STATUS       current
            DESCRIPTION
                "The PW list ID of the object."
            ::= { zxPwListEntry 1 }

zxPwListMasterPwName OBJECT-TYPE
            SYNTAX       DisplayString  (SIZE(0..31))
            MAX-ACCESS   read-only
            STATUS       current
            DESCRIPTION
                "The name of the master PW which is configured in the PW list."
            ::= { zxPwListEntry 2 }

--*************zxPwListSlaveTable**************** 
zxPwListSlaveTable OBJECT-TYPE
            SYNTAX     SEQUENCE OF ZxPwListSlaveEntry
            MAX-ACCESS not-accessible
            STATUS     current
            DESCRIPTION
                "PW list slave PW Table. This table contains one entry per 
                slave PW table."
            ::= { zxL2vpnPW 10 }

zxPwListSlaveEntry OBJECT-TYPE
            SYNTAX     ZxPwListSlaveEntry
            MAX-ACCESS not-accessible
            STATUS     current
            DESCRIPTION
                "The parameter of a PW list slave PW entity containing "
            INDEX { zxPwListSlaveListId , zxPwListSlavePwName }
            ::= { zxPwListSlaveTable 1 }

ZxPwListSlaveEntry ::= SEQUENCE {
            zxPwListSlaveListId                 Unsigned32,
            zxPwListSlavePwName                 DisplayString
            }

zxPwListSlaveListId OBJECT-TYPE
            SYNTAX       Unsigned32(1..256)
            MAX-ACCESS   not-accessible
            STATUS       current
            DESCRIPTION
                "The PW list ID of the object."
            ::= { zxPwListSlaveEntry 1 }

zxPwListSlavePwName OBJECT-TYPE
            SYNTAX       DisplayString  (SIZE(0..31))
            MAX-ACCESS   read-only
            STATUS       current
            DESCRIPTION
                "The name of the slave PW which is configured in the PW list."
            ::= { zxPwListSlaveEntry 2 }

--*************zxAccessPwBindTable**************** 
zxAccessPwBindTable OBJECT-TYPE
            SYNTAX     SEQUENCE OF ZxAccessPwBindEntry
            MAX-ACCESS not-accessible
            STATUS     current
            DESCRIPTION
                "AC protect bind Table. This table contains one entry per AC 
                protect bind table."
            ::= { zxL2vpnPW 11 }

zxAccessPwBindEntry OBJECT-TYPE
            SYNTAX     ZxAccessPwBindEntry
            MAX-ACCESS not-accessible
            STATUS     current
            DESCRIPTION
                "The parameter of a AC protect bind entity containing "
            INDEX { zxAccessPwBindInstName , zxAccessPwBindRedirectPwName , 
                zxAccessPwBindAccessPwName }
            ::= { zxAccessPwBindTable 1 }

ZxAccessPwBindEntry ::= SEQUENCE {
            zxAccessPwBindInstName              DisplayString,
            zxAccessPwBindRedirectPwName        DisplayString,
            zxAccessPwBindAccessPwName          DisplayString
            }

zxAccessPwBindInstName OBJECT-TYPE
            SYNTAX       DisplayString  (SIZE(0..32))
            MAX-ACCESS   not-accessible
            STATUS       current
            DESCRIPTION
                "The name of the instance in the bind."
            ::= { zxAccessPwBindEntry 1 }

zxAccessPwBindRedirectPwName OBJECT-TYPE
            SYNTAX       DisplayString  (SIZE(0..31))
            MAX-ACCESS   not-accessible
            STATUS       current
            DESCRIPTION
                "The name of the redirected PW in the bind."
            ::= { zxAccessPwBindEntry 2 }

zxAccessPwBindAccessPwName OBJECT-TYPE
            SYNTAX       DisplayString  (SIZE(0..31))
            MAX-ACCESS   read-only
            STATUS       current
            DESCRIPTION
                "The name of the access PW in the bind."
            ::= { zxAccessPwBindEntry 3 } 

--*************zxAcCeSideTable**************** 
zxAcCeSideTable OBJECT-TYPE
            SYNTAX     SEQUENCE OF ZxAcCeSideEntry
            MAX-ACCESS not-accessible
            STATUS     current
            DESCRIPTION
                "CE side Table. This table contains one entry per CE side 
                table."
            ::= { zxL2vpnPW 12 }

zxAcCeSideEntry OBJECT-TYPE
            SYNTAX     ZxAcCeSideEntry
            MAX-ACCESS not-accessible
            STATUS     current
            DESCRIPTION
                "The parameter of a CE side entity containing "
            INDEX { zxAcCeSideInstName , zxAcCeSideRedirectPwName , 
                zxAcCeSideAccessPwName }
            ::= { zxAcCeSideTable 1 }

ZxAcCeSideEntry ::= SEQUENCE {
            zxAcCeSideInstName                  DisplayString,
            zxAcCeSideRedirectPwName            DisplayString,
            zxAcCeSideAccessPwName              DisplayString,
            zxAcCeSideProtectType               INTEGER
            }

zxAcCeSideInstName OBJECT-TYPE
            SYNTAX       DisplayString  (SIZE(0..32))
            MAX-ACCESS   not-accessible
            STATUS       current
            DESCRIPTION
                "The name of the instance in the CE side entry."
            ::= { zxAcCeSideEntry 1 }

zxAcCeSideRedirectPwName OBJECT-TYPE
            SYNTAX       DisplayString  (SIZE(0..31))
            MAX-ACCESS   not-accessible
            STATUS       current
            DESCRIPTION
                "The name of the redirected PW in the CE side entry."
            ::= { zxAcCeSideEntry 2 }

zxAcCeSideAccessPwName OBJECT-TYPE
            SYNTAX       DisplayString  (SIZE(0..31))
            MAX-ACCESS   not-accessible
            STATUS       current
            DESCRIPTION
                "The name of the access PW in the CE side entry."
            ::= { zxAcCeSideEntry 3 } 

zxAcCeSideProtectType OBJECT-TYPE
            SYNTAX       INTEGER{
            onePlusOne(1),
            oneByOne(2),
            loadBalance(3)
            }
            MAX-ACCESS   read-only
            STATUS       current
            DESCRIPTION
                "The AC protect type of the CE side entry."
            ::= { zxAcCeSideEntry 4 }  

--*************zxAcInstBindTable****************  
zxAcInstBindTable OBJECT-TYPE
            SYNTAX     SEQUENCE OF ZxAcInstBindEntry
            MAX-ACCESS not-accessible
            STATUS     current
            DESCRIPTION
                "AC bind Table. This table contains
                 one entry per AC bind table."        
            ::= { zxL2vpnAC 1 }

zxAcInstBindEntry OBJECT-TYPE
            SYNTAX     ZxAcInstBindEntry
            MAX-ACCESS not-accessible
            STATUS     current
            DESCRIPTION
                "The parameter of a AC bind entity containing "
            INDEX { zxAcInstBindInstName , zxAcInstBindIfName }
            ::= { zxAcInstBindTable 1 }

ZxAcInstBindEntry ::= SEQUENCE {
            zxAcInstBindInstName                DisplayString,
            zxAcInstBindIfName                  DisplayString,
            zxAcInstBindIfIndex                 Unsigned32,
            zxAcInstBindSplitHorizon            INTEGER,
            zxAcInstBindType                    INTEGER,
            zxAcInstBindSplitHorizonScope       DisplayString
            }

zxAcInstBindInstName OBJECT-TYPE
            SYNTAX       DisplayString  (SIZE(0..32))
            MAX-ACCESS   read-only
            STATUS       current
            DESCRIPTION
            "The name of the instance in the bind."
            ::= { zxAcInstBindEntry 1 }

zxAcInstBindIfName OBJECT-TYPE
            SYNTAX       DisplayString  (SIZE(0..31))
            MAX-ACCESS   read-only
            STATUS       current
            DESCRIPTION
                "The name of the AC in the bind."
            ::= { zxAcInstBindEntry 2 }

zxAcInstBindIfIndex OBJECT-TYPE
            SYNTAX       Unsigned32
            MAX-ACCESS   read-only
            STATUS       current
            DESCRIPTION
                "The interface index of the AC in the bind."
            ::= { zxAcInstBindEntry 3 } 

zxAcInstBindSplitHorizon OBJECT-TYPE
            SYNTAX       INTEGER{
            serverOrNull(0),
            client(1)
            }
            MAX-ACCESS   read-only
            STATUS       current
            DESCRIPTION
                "The split horizon flag of the bind."
            ::= { zxAcInstBindEntry 4 }  

zxAcInstBindType OBJECT-TYPE
            SYNTAX       INTEGER{
            null(0),
            ether(1),
            tdm(2),
            iwfIp(3),
            iwfEther(4),
            hdlc(5),
            ppp(6),
            fr(7),
            atm(8)
            }
            MAX-ACCESS   read-only
            STATUS       current
            DESCRIPTION
                "The Access type of the bind."
            ::= { zxAcInstBindEntry 5 }

zxAcInstBindSplitHorizonScope OBJECT-TYPE
            SYNTAX       DisplayString  (SIZE(0..51))
            MAX-ACCESS   read-only
            STATUS       current
            DESCRIPTION
                "The split horizon scope of the bind."
            ::= { zxAcInstBindEntry 6 }

--*************zxAcParaEtherTable****************  
zxAcParaEtherTable OBJECT-TYPE
            SYNTAX     SEQUENCE OF ZxAcParaEtherEntry
            MAX-ACCESS not-accessible
            STATUS     current
            DESCRIPTION
                "AC ethernet Table. This table contains
                 one entry per AC ethernet table."        
            ::= { zxL2vpnAC 2 }

zxAcParaEtherEntry OBJECT-TYPE
            SYNTAX     ZxAcParaEtherEntry
            MAX-ACCESS not-accessible
            STATUS     current
            DESCRIPTION
                "The parameter of a AC ethernet entity containing "
            INDEX { zxAcParaEtherInstName , zxAcParaEtherIfName }
            ::= { zxAcParaEtherTable 1 }

ZxAcParaEtherEntry ::= SEQUENCE {
            zxAcParaEtherInstName               DisplayString,
            zxAcParaEtherIfName                 DisplayString,
            zxAcParaEtherIngressAdjustPush      INTEGER,
            zxAcParaEtherIngressAdjustRewrite   INTEGER,
            zxAcParaEtherRewriteVlanId          Unsigned32,
            zxAcParaEtherPushVlanId             Unsigned32,
            zxAcParaEtherGroupId                Unsigned32,
            zxAcParaEtherIngressTagAsPayload    INTEGER,
            zxAcParaEtherIngressAdjustDropTaggedFrames  INTEGER,
            zxAcParaEtherTrackName              DisplayString,
            zxAcParaEtherIfLst                  INTEGER,
            zxAcParaEtherOamMapping             INTEGER,
            zxAcParaEtherStatisEnStatus         INTEGER,
            zxAcParaEtherFaultSpread            INTEGER,
            zxAcParaEtherInUnknowBps            Counter64,
            zxAcParaEtherInUnknowPps            Unsigned32,
            zxAcParaEtherInBroadBps             Counter64,
            zxAcParaEtherInBroadPps             Unsigned32,
            zxAcParaEtherInDropBps              Counter64,
            zxAcParaEtherInDropPps              Unsigned32,
            zxAcParaEtherDropWildcard           MacAddress,
            zxAcParaEtherL2cpAbm                INTEGER,
            zxAcParaEtherL2cpStp                INTEGER,
            zxAcParaEtherL2cpDot1x              INTEGER,
            zxAcParaEtherL2cpDot3x              INTEGER,
            zxAcParaEtherL2cpLacp               INTEGER,
            zxAcParaEtherL2cpGarp               INTEGER,
            zxAcParaEtherL2cpGmrp               INTEGER,
            zxAcParaEtherL2cpGvrp               INTEGER,
            zxAcParaEtherL2cpCisco              INTEGER,
            zxAcParaEtherL2cpDldp               INTEGER,
            zxAcParaEtherL2cpEfm                INTEGER,
            zxAcParaEtherL2cpCfm                INTEGER,
            zxAcParaEtherL2cpLldp               INTEGER,
            zxAcParaEtherL2cpPvst               INTEGER,
            zxAcParaEtherL2cpZdp                INTEGER,
            zxAcParaEtherMonitorIp              IpAddress,
            zxAcParaEtherMonitorMac             MacAddress,
            zxAcParaEtherMonitorMode            INTEGER,
            zxAcParaEtherL2cpErps               INTEGER,
            zxAcParaEtherL2cpUdld               INTEGER,
            zxAcParaEtherL2cpVtp                INTEGER,
            zxAcParaEtherL2cpZesr               INTEGER,
            zxAcParaEtherL2cpUserProtocolName   DisplayString,
            zxAcParaEtherL2cpUserProtocol       INTEGER
            }

zxAcParaEtherInstName OBJECT-TYPE
            SYNTAX       DisplayString  (SIZE(0..32))
            MAX-ACCESS   read-only
            STATUS       current
            DESCRIPTION
                "The name of the instance in the ethernet parameter."
            ::= { zxAcParaEtherEntry 1 }  

zxAcParaEtherIfName OBJECT-TYPE
            SYNTAX       DisplayString  (SIZE(0..31))
            MAX-ACCESS   read-only
            STATUS       current
            DESCRIPTION
                "The name of the AC in the ethernet parameter."
            ::= { zxAcParaEtherEntry 2 } 

zxAcParaEtherIngressAdjustPush OBJECT-TYPE
            SYNTAX       INTEGER{
            disable(0),
            enable(1)
            }
            MAX-ACCESS   read-only
            STATUS       current
            DESCRIPTION
                "The ingress adjust push flag of the ethernet parameter."
            ::= { zxAcParaEtherEntry 3 }

zxAcParaEtherIngressAdjustRewrite OBJECT-TYPE
            SYNTAX       INTEGER{
            disable(0),
            enable(1)
            }
            MAX-ACCESS   read-only
            STATUS       current
            DESCRIPTION
                "The ingress adjust rewrite flag of the ethernet parameter."
            ::= { zxAcParaEtherEntry 4 } 

zxAcParaEtherRewriteVlanId OBJECT-TYPE
            SYNTAX       Unsigned32(0..4094)
            MAX-ACCESS   read-only
            STATUS       current
            DESCRIPTION
                "The ingress adjust rewrite VLAN ID of the ethernet parameter."
            ::= { zxAcParaEtherEntry 5 }   

zxAcParaEtherPushVlanId OBJECT-TYPE
            SYNTAX       Unsigned32(0..4094)
            MAX-ACCESS   read-only
            STATUS       current
            DESCRIPTION
                "The ingress adjust push VLAN ID of the ethernet parameter."
            ::= { zxAcParaEtherEntry 6 }  

zxAcParaEtherGroupId OBJECT-TYPE
            SYNTAX       Unsigned32(0..63)
            MAX-ACCESS   read-only
            STATUS       current
            DESCRIPTION
                "The group ID of the ethernet parameter."
            ::= { zxAcParaEtherEntry 7 }

zxAcParaEtherIngressTagAsPayload OBJECT-TYPE
            SYNTAX       INTEGER{
            no(0),
            fromOutermost(1),
            fromSubLayer(2)
            }
            MAX-ACCESS   read-only
            STATUS       current
            DESCRIPTION
                "The ingress tag as payload flag of the ethernet parameter."
            ::= { zxAcParaEtherEntry 8 }

zxAcParaEtherIngressAdjustDropTaggedFrames OBJECT-TYPE
            SYNTAX       INTEGER{
            disable(0),
            enable(1),
            null(254)
            }
            MAX-ACCESS   read-only
            STATUS       current
            DESCRIPTION
                "The ingress adjust drop tagged frames flag of the ethernet 
                parameter. Invalid value is 254."
            ::= { zxAcParaEtherEntry 9 }

zxAcParaEtherTrackName OBJECT-TYPE
            SYNTAX       DisplayString  (SIZE(0..31))
            MAX-ACCESS   read-only
            STATUS       current
            DESCRIPTION
                "The name of the track object which bind to the AC."
            ::= { zxAcParaEtherEntry 10 }

zxAcParaEtherIfLst OBJECT-TYPE
            SYNTAX       INTEGER{
            disable(0),
            enable(1)
            }
            MAX-ACCESS   read-only
            STATUS       current
            DESCRIPTION
                "The lst flag of the ethernet parameter."
            ::= { zxAcParaEtherEntry 11 }   

zxAcParaEtherOamMapping OBJECT-TYPE
            SYNTAX       INTEGER{
            disable(0),
            enable(1)
            }
            MAX-ACCESS   read-only
            STATUS       current
            DESCRIPTION
                "The oam-mapping flag of the ethernet parameter."
            ::= { zxAcParaEtherEntry 12 }

zxAcParaEtherStatisEnStatus OBJECT-TYPE
            SYNTAX       INTEGER{
            disable(1),
            enable(2)
            }
            MAX-ACCESS   read-only
            STATUS       current
            DESCRIPTION
                "The enable status of the ethernet parameter's traffic 
                statistics."
            DEFVAL       { disable }
            ::= { zxAcParaEtherEntry 13 }

zxAcParaEtherFaultSpread OBJECT-TYPE
            SYNTAX       INTEGER{
            enable(1),
            disable(2)
            }
            MAX-ACCESS   read-only
            STATUS       current
            DESCRIPTION
                "The flag of the ethernet parameter's fault-spread."
            DEFVAL       { enable }
            ::= { zxAcParaEtherEntry 14 }

zxAcParaEtherInUnknowBps OBJECT-TYPE
            SYNTAX       Counter64
            UNITS         "Bytes per second"
            MAX-ACCESS   read-only
            STATUS       current
            DESCRIPTION
                "The threshold of warnning for input unknown unicast bytes 
                rate."
            ::= { zxAcParaEtherEntry 15 }

zxAcParaEtherInUnknowPps OBJECT-TYPE
            SYNTAX       Unsigned32
            UNITS         "Packets per second"
            MAX-ACCESS   read-only
            STATUS       current
            DESCRIPTION
                "The threshold of warnning for input unknown unicast packets 
                rate."
            ::= { zxAcParaEtherEntry 16 }

zxAcParaEtherInBroadBps OBJECT-TYPE
            SYNTAX       Counter64
            UNITS         "Bytes per second"
            MAX-ACCESS   read-only
            STATUS       current
            DESCRIPTION
                "The threshold of warnning for input broadcast bytes rate."
            ::= { zxAcParaEtherEntry 17 }

zxAcParaEtherInBroadPps OBJECT-TYPE
            SYNTAX       Unsigned32
            UNITS         "Packets per second"
            MAX-ACCESS   read-only
            STATUS       current
            DESCRIPTION
                "The threshold of warnning for input broadcast packets rate."
            ::= { zxAcParaEtherEntry 18 }

zxAcParaEtherInDropBps OBJECT-TYPE
            SYNTAX       Counter64
            UNITS         "Bytes per second"
            MAX-ACCESS   read-only
            STATUS       current
            DESCRIPTION
                "The threshold of warnning for input dropped bytes rate."
            ::= { zxAcParaEtherEntry 19 }

zxAcParaEtherInDropPps OBJECT-TYPE
            SYNTAX       Unsigned32
            UNITS         "Packets per second"
            MAX-ACCESS   read-only
            STATUS       current
            DESCRIPTION
                "The threshold of warnning for input dropped packets rate."
            ::= { zxAcParaEtherEntry 20 }

zxAcParaEtherDropWildcard OBJECT-TYPE
            SYNTAX       MacAddress
            MAX-ACCESS   read-only
            STATUS       current
            DESCRIPTION
                "The L2 protocol filter for wildcard MAC."
            ::= { zxAcParaEtherEntry 21 }

zxAcParaEtherL2cpAbm OBJECT-TYPE
            SYNTAX       INTEGER{
            tunnelled(1),
            drop(2),
            terminate(3),
            tunnelledMonitor(4),
            unknown(255)
            }
            MAX-ACCESS   read-only
            STATUS       current
            DESCRIPTION
                "The L2 protocol filter for all bridge multicast protocol 
                packets."
            ::= { zxAcParaEtherEntry 22 }

zxAcParaEtherL2cpStp OBJECT-TYPE
            SYNTAX       INTEGER{
            tunnelled(1),
            drop(2),
            terminate(3),
            tunnelledMonitor(4),
            unknown(255)
            }
            MAX-ACCESS   read-only
            STATUS       current
            DESCRIPTION
                "The L2 protocol filter for STP protocol packets."
            ::= { zxAcParaEtherEntry 23 }

zxAcParaEtherL2cpDot1x OBJECT-TYPE
            SYNTAX       INTEGER{
            tunnelled(1),
            drop(2),
            terminate(3),
            tunnelledMonitor(4),
            unknown(255)
            }
            MAX-ACCESS   read-only
            STATUS       current
            DESCRIPTION
                "The L2 protocol filter for 802.1x protocol packets."
            ::= { zxAcParaEtherEntry 24 }

zxAcParaEtherL2cpDot3x OBJECT-TYPE
            SYNTAX       INTEGER{
            tunnelled(1),
            drop(2),
            terminate(3),
            tunnelledMonitor(4),
            unknown(255)
            }
            MAX-ACCESS   read-only
            STATUS       current
            DESCRIPTION
                "The L2 protocol filter for 802.3x protocol packets."
            ::= { zxAcParaEtherEntry 25 }

zxAcParaEtherL2cpLacp OBJECT-TYPE
            SYNTAX       INTEGER{
            tunnelled(1),
            drop(2),
            terminate(3),
            tunnelledMonitor(4),
            unknown(255)
            }
            MAX-ACCESS   read-only
            STATUS       current
            DESCRIPTION
                "The L2 protocol filter for LACP protocol packets."
            ::= { zxAcParaEtherEntry 26 }

zxAcParaEtherL2cpGarp OBJECT-TYPE
            SYNTAX       INTEGER{
            tunnelled(1),
            drop(2),
            terminate(3),
            tunnelledMonitor(4),
            unknown(255)
            }
            MAX-ACCESS   read-only
            STATUS       current
            DESCRIPTION
                "The L2 protocol filter for GARP protocol packets."
            ::= { zxAcParaEtherEntry 27 }

zxAcParaEtherL2cpGmrp OBJECT-TYPE
            SYNTAX       INTEGER{
            tunnelled(1),
            drop(2),
            terminate(3),
            tunnelledMonitor(4),
            unknown(255)
            }
            MAX-ACCESS   read-only
            STATUS       current
            DESCRIPTION
                "The L2 protocol filter for GMRP protocol packets."
            ::= { zxAcParaEtherEntry 28 }

zxAcParaEtherL2cpGvrp OBJECT-TYPE
            SYNTAX       INTEGER{
            tunnelled(1),
            drop(2),
            terminate(3),
            tunnelledMonitor(4),
            unknown(255)
            }
            MAX-ACCESS   read-only
            STATUS       current
            DESCRIPTION
                "The L2 protocol filter for GVRP protocol packets."
            ::= { zxAcParaEtherEntry 29 }

zxAcParaEtherL2cpCisco OBJECT-TYPE
            SYNTAX       INTEGER{
            tunnelled(1),
            drop(2),
            terminate(3),
            tunnelledMonitor(4),
            unknown(255)
            }
            MAX-ACCESS   read-only
            STATUS       current
            DESCRIPTION
                "The L2 protocol filter for CISCO protocol packets."
            ::= { zxAcParaEtherEntry 30 }

zxAcParaEtherL2cpDldp OBJECT-TYPE
            SYNTAX       INTEGER{
            tunnelled(1),
            drop(2),
            terminate(3),
            tunnelledMonitor(4),
            unknown(255)
            }
            MAX-ACCESS   read-only
            STATUS       current
            DESCRIPTION
                "The L2 protocol filter for DLDP protocol packets."
            ::= { zxAcParaEtherEntry 31 }

zxAcParaEtherL2cpEfm OBJECT-TYPE
            SYNTAX       INTEGER{
            tunnelled(1),
            drop(2),
            terminate(3),
            tunnelledMonitor(4),
            unknown(255)
            }
            MAX-ACCESS   read-only
            STATUS       current
            DESCRIPTION
                "The L2 protocol filter for EFM protocol packets."
            ::= { zxAcParaEtherEntry 32 }

zxAcParaEtherL2cpCfm OBJECT-TYPE
            SYNTAX       INTEGER{
            tunnelled(1),
            drop(2),
            terminate(3),
            tunnelledMonitor(4),
            unknown(255)
            }
            MAX-ACCESS   read-only
            STATUS       current
            DESCRIPTION
                "The L2 protocol filter for CFM protocol packets."
            ::= { zxAcParaEtherEntry 33 }

zxAcParaEtherL2cpLldp OBJECT-TYPE
            SYNTAX       INTEGER{
            tunnelled(1),
            drop(2),
            terminate(3),
            tunnelledMonitor(4),
            unknown(255)
            }
            MAX-ACCESS   read-only
            STATUS       current
            DESCRIPTION
                "The L2 protocol filter for LLDP protocol packets."
            ::= { zxAcParaEtherEntry 34 }

zxAcParaEtherL2cpPvst OBJECT-TYPE
            SYNTAX       INTEGER{
            tunnelled(1),
            drop(2),
            terminate(3),
            tunnelledMonitor(4),
            unknown(255)
            }
            MAX-ACCESS   read-only
            STATUS       current
            DESCRIPTION
                "The L2 protocol filter for PVST protocol packets."
            ::= { zxAcParaEtherEntry 35 }

zxAcParaEtherL2cpZdp OBJECT-TYPE
            SYNTAX       INTEGER{
            tunnelled(1),
            drop(2),
            terminate(3),
            tunnelledMonitor(4),
            unknown(255)
            }
            MAX-ACCESS   read-only
            STATUS       current
            DESCRIPTION
                "The L2 protocol filter for ZDP protocol packets."
            ::= { zxAcParaEtherEntry 36 }

zxAcParaEtherMonitorIp OBJECT-TYPE
            SYNTAX       IpAddress
            MAX-ACCESS   read-only
            STATUS       current
            DESCRIPTION
                "The monitor IP of NNI ping."
            ::= { zxAcParaEtherEntry 37 }

zxAcParaEtherMonitorMac OBJECT-TYPE
            SYNTAX       MacAddress
            MAX-ACCESS   read-only
            STATUS       current
            DESCRIPTION
                "The monitor MAC of NNI ping."
            ::= { zxAcParaEtherEntry 38 }

zxAcParaEtherMonitorMode OBJECT-TYPE
            SYNTAX       INTEGER{
            masterSlave(1),
            loadBalance(2)
            }
            MAX-ACCESS   read-only
            STATUS       current
            DESCRIPTION
                "The monitor mode of NNI ping."
            DEFVAL       { masterSlave }
            ::= { zxAcParaEtherEntry 39 }

zxAcParaEtherL2cpErps OBJECT-TYPE
            SYNTAX       INTEGER{
            tunnelled(1),
            drop(2),
            terminate(3),
            tunnelledMonitor(4),
            unknown(255)
            }
            MAX-ACCESS   read-only
            STATUS       current
            DESCRIPTION
                "The L2 protocol filter for ERPS protocol packets."
            ::= { zxAcParaEtherEntry 40 }
            
zxAcParaEtherL2cpUdld OBJECT-TYPE
            SYNTAX       INTEGER{
            tunnelled(1),
            drop(2),
            terminate(3),
            tunnelledMonitor(4),
            unknown(255)
            }
            MAX-ACCESS   read-only
            STATUS       current
            DESCRIPTION
                "The L2 protocol filter for UDLD protocol packets."
            ::= { zxAcParaEtherEntry 41 }
            
zxAcParaEtherL2cpVtp OBJECT-TYPE
            SYNTAX       INTEGER{
            tunnelled(1),
            drop(2),
            terminate(3),
            tunnelledMonitor(4),
            unknown(255)
            }
            MAX-ACCESS   read-only
            STATUS       current
            DESCRIPTION
                "The L2 protocol filter for VTP protocol packets."
            ::= { zxAcParaEtherEntry 42 }
            
zxAcParaEtherL2cpZesr OBJECT-TYPE
            SYNTAX       INTEGER{
            tunnelled(1),
            drop(2),
            terminate(3),
            tunnelledMonitor(4),
            unknown(255)
            }
            MAX-ACCESS   read-only
            STATUS       current
            DESCRIPTION
                "The L2 protocol filter for ZESR protocol packets."
            ::= { zxAcParaEtherEntry 43 }
            
zxAcParaEtherL2cpUserProtocolName OBJECT-TYPE
            SYNTAX       DisplayString  (SIZE(0..31))
            MAX-ACCESS   read-only
            STATUS       current
            DESCRIPTION
                "The L2 protocol filter for user protocol name."
            ::= { zxAcParaEtherEntry 44 }
            
zxAcParaEtherL2cpUserProtocol OBJECT-TYPE
            SYNTAX       INTEGER{
            tunnelled(1),
            drop(2),
            terminate(3),
            tunnelledMonitor(4),
            unknown(255)
            }
            MAX-ACCESS   read-only
            STATUS       current
            DESCRIPTION
                "The L2 protocol filter for user protocol packets."
            ::= { zxAcParaEtherEntry 45 }
--*************zxAcParaTdmTable****************  
zxAcParaTdmTable OBJECT-TYPE
            SYNTAX     SEQUENCE OF ZxAcParaTdmEntry
            MAX-ACCESS not-accessible
            STATUS     current
            DESCRIPTION
                "AC TDM Table. This table contains
                 one entry per AC TDM table."        
            ::= { zxL2vpnAC 3 }

zxAcParaTdmEntry OBJECT-TYPE
            SYNTAX     ZxAcParaTdmEntry
            MAX-ACCESS not-accessible
            STATUS     current
            DESCRIPTION
                "The parameter of a AC TDM entity containing "
            INDEX { zxAcParaTdmInstName , zxAcParaTdmIfName }
            ::= { zxAcParaTdmTable 1 }

ZxAcParaTdmEntry ::= SEQUENCE {
            zxAcParaTdmInstName                 DisplayString,
            zxAcParaTdmIfName                   DisplayString,
            zxAcParaTdmDistributePeriod         Unsigned32,
            zxAcParaTdmCasUsed                  INTEGER,
            zxAcParaTdmJitterBuffer             Unsigned32,
            zxAcParaTdmRtpHeaderUsed            INTEGER,
            zxAcParaTdmRtpTimeStamp             INTEGER,
            zxAcParaTdmTrackName                DisplayString,
            zxAcParaTdmStructure                INTEGER,
            zxAcParaTdmIdleCode                 INTEGER,
            zxAcParaTdmOamMapping               INTEGER,
            zxAcParaTdmTimeSlotCompatible       INTEGER,
            zxAcParaTdmFaultSpread              INTEGER,
            zxAcParaTdmStatisEnStatus           INTEGER,
            zxAcParaTdmInUnknowBps              Counter64,
            zxAcParaTdmInUnknowPps              Unsigned32,
            zxAcParaTdmInBroadBps               Counter64,
            zxAcParaTdmInBroadPps               Unsigned32,
            zxAcParaTdmInDropBps                Counter64,
            zxAcParaTdmInDropPps                Unsigned32
            }

zxAcParaTdmInstName OBJECT-TYPE
            SYNTAX       DisplayString  (SIZE(0..32))
            MAX-ACCESS   read-only
            STATUS       current
            DESCRIPTION
                "The name of the instance in the bind."
            ::= { zxAcParaTdmEntry 1 }

zxAcParaTdmIfName OBJECT-TYPE
            SYNTAX       DisplayString  (SIZE(0..31))
            MAX-ACCESS   read-only
            STATUS       current
            DESCRIPTION
                "The name of the AC in the bind."
            ::= { zxAcParaTdmEntry 2 }

zxAcParaTdmDistributePeriod OBJECT-TYPE
            SYNTAX       Unsigned32(0..64)
            MAX-ACCESS   read-only
            STATUS       current
            DESCRIPTION
                "The distribute period value of the TDM parameter. 
                Invalid value is 254"
            ::= { zxAcParaTdmEntry 3 } 

zxAcParaTdmCasUsed OBJECT-TYPE
            SYNTAX       INTEGER{
            disable(0),
            enable(1)
            }
            MAX-ACCESS   read-only
            STATUS       current
            DESCRIPTION
                "The cas used flag of the TDM parameter."
            ::= { zxAcParaTdmEntry 4 }

zxAcParaTdmJitterBuffer OBJECT-TYPE
            SYNTAX       Unsigned32(1..400)
            MAX-ACCESS   read-only
            STATUS       current
            DESCRIPTION
                "The jitter buffer value of the TDM parameter."
            ::= { zxAcParaTdmEntry 5 }

zxAcParaTdmRtpHeaderUsed OBJECT-TYPE
            SYNTAX       INTEGER{
            disable(0),
            enable(1)
            }
            MAX-ACCESS   read-only
            STATUS       current
            DESCRIPTION
                "The RTP header used flag of the TDM parameter."
            ::= { zxAcParaTdmEntry 6 } 

zxAcParaTdmRtpTimeStamp OBJECT-TYPE
            SYNTAX       INTEGER{
            null(0),
            absolute(1),
            differ(2)
            }
            MAX-ACCESS   read-only
            STATUS       current
            DESCRIPTION
                "The RTP timestamp mode of the TDM parameter."
            ::= { zxAcParaTdmEntry 7 } 

zxAcParaTdmTrackName OBJECT-TYPE
            SYNTAX       DisplayString  (SIZE(0..31))
            MAX-ACCESS   read-only
            STATUS       current
            DESCRIPTION
                "The name of the track object which bind to the AC."
            ::= { zxAcParaTdmEntry 8 }

zxAcParaTdmStructure OBJECT-TYPE
            SYNTAX       INTEGER{
            none(0),
            aware(1),
            awareWithCas(2),
            agnostic(3)
            }
            MAX-ACCESS   read-only
            STATUS       current
            DESCRIPTION
                "The structure type of the TDM parameter."
            ::= { zxAcParaTdmEntry 9 }

zxAcParaTdmIdleCode OBJECT-TYPE
            SYNTAX       INTEGER{
            code0xff(0),
            code0x7e(1)
            }
            MAX-ACCESS   read-only
            STATUS       current
            DESCRIPTION
                "The idle code value of the TDM parameter."
            ::= { zxAcParaTdmEntry 10 }

zxAcParaTdmOamMapping OBJECT-TYPE
            SYNTAX       INTEGER{
            disable(0),
            enable(1)
            }
            MAX-ACCESS   read-only
            STATUS       current
            DESCRIPTION
                "The oam-mapping flag of the TDM parameter."
            ::= { zxAcParaTdmEntry 11 }

zxAcParaTdmTimeSlotCompatible OBJECT-TYPE
            SYNTAX       INTEGER{
            disable(1),
            enable(2)
            }
            MAX-ACCESS   read-only
            STATUS       current
            DESCRIPTION
                "The timeslot compatible mode of the TDM parameter."
            ::= { zxAcParaTdmEntry 12 }

zxAcParaTdmFaultSpread OBJECT-TYPE
            SYNTAX       INTEGER{
            enable(1),
            disable(2)
            }
            MAX-ACCESS   read-only
            STATUS       current
            DESCRIPTION
                "The flag of the TDM parameter's fault-spread."
            DEFVAL       { enable }
            ::= { zxAcParaTdmEntry 13 }

zxAcParaTdmStatisEnStatus OBJECT-TYPE
            SYNTAX       INTEGER{
            disable(1),
            enable(2)
            }
            MAX-ACCESS   read-only
            STATUS       current
            DESCRIPTION
                "The enable status of the TDM parameter's traffic statistics."
            DEFVAL       { disable }
            ::= { zxAcParaTdmEntry 14 }

zxAcParaTdmInUnknowBps OBJECT-TYPE
            SYNTAX       Counter64
            UNITS         "Bytes per second"
            MAX-ACCESS   read-only
            STATUS       current
            DESCRIPTION
                "The threshold of warnning for input unknown unicast bytes 
                rate."
            ::= { zxAcParaTdmEntry 15 }

zxAcParaTdmInUnknowPps OBJECT-TYPE
            SYNTAX       Unsigned32
            UNITS         "Packets per second"
            MAX-ACCESS   read-only
            STATUS       current
            DESCRIPTION
                "The threshold of warnning for input unknown unicast packets 
                rate."
            ::= { zxAcParaTdmEntry 16 }

zxAcParaTdmInBroadBps OBJECT-TYPE
            SYNTAX       Counter64
            UNITS         "Bytes per second"
            MAX-ACCESS   read-only
            STATUS       current
            DESCRIPTION
                "The threshold of warnning for input broadcast bytes rate."
            ::= { zxAcParaTdmEntry 17 }

zxAcParaTdmInBroadPps OBJECT-TYPE
            SYNTAX       Unsigned32
            UNITS         "Packets per second"
            MAX-ACCESS   read-only
            STATUS       current
            DESCRIPTION
                "The threshold of warnning for input broadcast packets rate."
            ::= { zxAcParaTdmEntry 18 }

zxAcParaTdmInDropBps OBJECT-TYPE
            SYNTAX       Counter64
            UNITS         "Bytes per second"
            MAX-ACCESS   read-only
            STATUS       current
            DESCRIPTION
                "The threshold of warnning for input dropped bytes rate."
            ::= { zxAcParaTdmEntry 19 }

zxAcParaTdmInDropPps OBJECT-TYPE
            SYNTAX       Unsigned32
            UNITS         "Packets per second"
            MAX-ACCESS   read-only
            STATUS       current
            DESCRIPTION
                "The threshold of warnning for input dropped packets rate."
            ::= { zxAcParaTdmEntry 20 }
            
--*************zxAcParaIwfIPTable****************  
zxAcParaIwfIPTable OBJECT-TYPE
            SYNTAX     SEQUENCE OF ZxAcParaIwfIPEntry
            MAX-ACCESS not-accessible
            STATUS     current
            DESCRIPTION
                "AC IP inter-working Table. This table contains
                 one entry per AC IP inter-working table."        
            ::= { zxL2vpnAC 4 }

zxAcParaIwfIPEntry OBJECT-TYPE
            SYNTAX     ZxAcParaIwfIPEntry
            MAX-ACCESS not-accessible
            STATUS     current
            DESCRIPTION
                "The parameter of a AC IP inter-working entity containing "
            INDEX { zxAcParaIwfIPInstName , zxAcParaIwfIPIfName }
            ::= { zxAcParaIwfIPTable 1 }

ZxAcParaIwfIPEntry ::= SEQUENCE {
            zxAcParaIwfIPInstName               DisplayString,
            zxAcParaIwfIPIfName                 DisplayString,
            zxAcParaIwfIPLocalCeMac             MacAddress,
            zxAcParaIwfIPTrackName              DisplayString,
            zxAcParaIwfIPOamMapping             INTEGER,
            zxAcParaIwfIPRemoteIP               IpAddress,
            zxAcParaIwfIPFaultSpread            INTEGER,
            zxAcParaIwfIPStatisEnStatus         INTEGER,
            zxAcParaIwfIPInUnknowBps            Counter64,
            zxAcParaIwfIPInUnknowPps            Unsigned32,
            zxAcParaIwfIPInBroadBps             Counter64,
            zxAcParaIwfIPInBroadPps             Unsigned32,
            zxAcParaIwfIPInDropBps              Counter64,
            zxAcParaIwfIPInDropPps              Unsigned32
            }

zxAcParaIwfIPInstName OBJECT-TYPE
            SYNTAX       DisplayString  (SIZE(0..32))
            MAX-ACCESS   read-only
            STATUS       current
            DESCRIPTION
                "The name of the instance in the bind."
            ::= { zxAcParaIwfIPEntry 1 }

zxAcParaIwfIPIfName OBJECT-TYPE
            SYNTAX       DisplayString  (SIZE(0..31))
            MAX-ACCESS   read-only
            STATUS       current
            DESCRIPTION
                "The name of the AC in the bind."
            ::= { zxAcParaIwfIPEntry 2 }

zxAcParaIwfIPLocalCeMac OBJECT-TYPE
            SYNTAX       MacAddress
            MAX-ACCESS   read-only
            STATUS       current
            DESCRIPTION
                "The local CE MAC address of the IP inter-working parameter."
            ::= { zxAcParaIwfIPEntry 3 }

zxAcParaIwfIPTrackName OBJECT-TYPE
            SYNTAX       DisplayString  (SIZE(0..31))
            MAX-ACCESS   read-only
            STATUS       current
            DESCRIPTION
                "The name of the track object which bind to the AC."
            ::= { zxAcParaIwfIPEntry 4 }

zxAcParaIwfIPOamMapping OBJECT-TYPE
            SYNTAX       INTEGER{
            disable(0),
            enable(1)
            }
            MAX-ACCESS   read-only
            STATUS       current
            DESCRIPTION
                "The oam-mapping flag of the IP inter-working parameter."
            ::= { zxAcParaIwfIPEntry 5 }

zxAcParaIwfIPRemoteIP OBJECT-TYPE
            SYNTAX       IpAddress
            MAX-ACCESS   read-only
            STATUS       current
            DESCRIPTION
                "The local CE IP address of the IP inter-working parameter."
            ::= { zxAcParaIwfIPEntry 6 }
 
zxAcParaIwfIPFaultSpread OBJECT-TYPE
            SYNTAX       INTEGER{
            enable(1),
            disable(2)
            }
            MAX-ACCESS   read-only
            STATUS       current
            DESCRIPTION
                "The flag of the IP inter-working parameter's fault-spread."
            DEFVAL       { enable }
            ::= { zxAcParaIwfIPEntry 7 }
 
zxAcParaIwfIPStatisEnStatus OBJECT-TYPE
            SYNTAX       INTEGER{
            disable(1),
            enable(2)
            }
            MAX-ACCESS   read-only
            STATUS       current
            DESCRIPTION
                "The enable status of the IP inter-working parameter's traffic
                 statistics."
            DEFVAL       { disable }
            ::= { zxAcParaIwfIPEntry 8 }

zxAcParaIwfIPInUnknowBps OBJECT-TYPE
            SYNTAX       Counter64
            UNITS         "Bytes per second"
            MAX-ACCESS   read-only
            STATUS       current
            DESCRIPTION
                "The threshold of warnning for input unknown unicast bytes 
                rate."
            ::= { zxAcParaIwfIPEntry 9 }

zxAcParaIwfIPInUnknowPps OBJECT-TYPE
            SYNTAX       Unsigned32
            UNITS         "Packets per second"
            MAX-ACCESS   read-only
            STATUS       current
            DESCRIPTION
                "The threshold of warnning for input unknown unicast packets 
                rate."
            ::= { zxAcParaIwfIPEntry 10 }

zxAcParaIwfIPInBroadBps OBJECT-TYPE
            SYNTAX       Counter64
            UNITS         "Bytes per second"
            MAX-ACCESS   read-only
            STATUS       current
            DESCRIPTION
                "The threshold of warnning for input broadcast bytes rate."
            ::= { zxAcParaIwfIPEntry 11 }

zxAcParaIwfIPInBroadPps OBJECT-TYPE
            SYNTAX       Unsigned32
            UNITS         "Packets per second"
            MAX-ACCESS   read-only
            STATUS       current
            DESCRIPTION
                "The threshold of warnning for input broadcast packets rate."
            ::= { zxAcParaIwfIPEntry 12 }

zxAcParaIwfIPInDropBps OBJECT-TYPE
            SYNTAX       Counter64
            UNITS         "Bytes per second"
            MAX-ACCESS   read-only
            STATUS       current
            DESCRIPTION
                "The threshold of warnning for input dropped bytes rate."
            ::= { zxAcParaIwfIPEntry 13 }

zxAcParaIwfIPInDropPps OBJECT-TYPE
            SYNTAX       Unsigned32
            UNITS         "Packets per second"
            MAX-ACCESS   read-only
            STATUS       current
            DESCRIPTION
                "The threshold of warnning for input dropped packets rate."
            ::= { zxAcParaIwfIPEntry 14 }
 
--*************zxAcParaIwfEtherTable****************  
zxAcParaIwfEtherTable OBJECT-TYPE
            SYNTAX     SEQUENCE OF ZxAcParaIwfEtherEntry
            MAX-ACCESS not-accessible
            STATUS     current
            DESCRIPTION
                "AC bind Table. This table contains
                 one entry per AC bind table."        
            ::= { zxL2vpnAC 5 }

zxAcParaIwfEtherEntry OBJECT-TYPE
            SYNTAX     ZxAcParaIwfEtherEntry
            MAX-ACCESS not-accessible
            STATUS     current
            DESCRIPTION
                "The parameter of a AC bind entity containing "
            INDEX { zxAcParaIwfEtherInstName , zxAcParaIwfEtherIfName }
            ::= { zxAcParaIwfEtherTable 1 }

ZxAcParaIwfEtherEntry ::= SEQUENCE {
            zxAcParaIwfEtherInstName            DisplayString,
            zxAcParaIwfEtherIfName              DisplayString,
            zxAcParaIwfEtherProxyMac            MacAddress,
            zxAcParaIwfEtherLocalIP             IpAddress,
            zxAcParaIwfEtherRemoteIP            IpAddress,
            zxAcParaIwfEtherRemoteMac           MacAddress,
            zxAcParaIwfEtherServiceVlan         Unsigned32,
            zxAcParaIwfEtherFaultSpread         INTEGER,
            zxAcParaIwfEtherStatisEnStatus      INTEGER,
            zxAcParaIwfEtherInUnknowBps         Counter64,
            zxAcParaIwfEtherInUnknowPps         Unsigned32,
            zxAcParaIwfEtherInBroadBps          Counter64,
            zxAcParaIwfEtherInBroadPps          Unsigned32,
            zxAcParaIwfEtherInDropBps           Counter64,
            zxAcParaIwfEtherInDropPps           Unsigned32
            }

zxAcParaIwfEtherInstName OBJECT-TYPE
            SYNTAX       DisplayString  (SIZE(0..32))
            MAX-ACCESS   read-only
            STATUS       current
            DESCRIPTION
                "The name of the instance in the bind."
            ::= { zxAcParaIwfEtherEntry 1 }

zxAcParaIwfEtherIfName OBJECT-TYPE
            SYNTAX       DisplayString  (SIZE(0..31))
            MAX-ACCESS   read-only
            STATUS       current
            DESCRIPTION
                "The name of the AC in the bind."
            ::= { zxAcParaIwfEtherEntry 2 }  
                                        
zxAcParaIwfEtherProxyMac OBJECT-TYPE
            SYNTAX       MacAddress
            MAX-ACCESS   read-only
            STATUS       current
            DESCRIPTION
                "The proxy MAC address of the ethernet inter-working 
                parameter."
            ::= { zxAcParaIwfEtherEntry 3 }

zxAcParaIwfEtherLocalIP OBJECT-TYPE
            SYNTAX       IpAddress
            MAX-ACCESS   read-only
            STATUS       current
            DESCRIPTION
                "The local CE IP address of the ethernet inter-working 
                parameter."
            ::= { zxAcParaIwfEtherEntry 4 } 

zxAcParaIwfEtherRemoteIP OBJECT-TYPE
            SYNTAX       IpAddress
            MAX-ACCESS   read-only
            STATUS       current
            DESCRIPTION
                "The remote CE IP address of the ethernet inter-working 
                parameter."
            ::= { zxAcParaIwfEtherEntry 5 } 

zxAcParaIwfEtherRemoteMac OBJECT-TYPE
            SYNTAX       MacAddress
            MAX-ACCESS   read-only
            STATUS       current
            DESCRIPTION
                "The remote MAC address of the ethernet inter-working 
                parameter."
            ::= { zxAcParaIwfEtherEntry 6 }

zxAcParaIwfEtherServiceVlan OBJECT-TYPE
            SYNTAX       Unsigned32(0..4094)
            MAX-ACCESS   read-only
            STATUS       current
            DESCRIPTION
                "The service VLAN ID of the ethernet inter-working parameter. 
                Invalid value is 65534."
            ::= { zxAcParaIwfEtherEntry 7 }  

zxAcParaIwfEtherFaultSpread OBJECT-TYPE
            SYNTAX       INTEGER{
            enable(1),
            disable(2)
            }
            MAX-ACCESS   read-only
            STATUS       current
            DESCRIPTION
                "The flag of the ethernet inter-working parameter's 
                fault-spread."
            DEFVAL       { enable }
            ::= { zxAcParaIwfEtherEntry 8 }

zxAcParaIwfEtherStatisEnStatus OBJECT-TYPE
            SYNTAX       INTEGER{
            disable(1),
            enable(2)
            }
            MAX-ACCESS   read-only
            STATUS       current
            DESCRIPTION
                "The enable status of the ethernet inter-working parameter's 
                traffic statistics."
            DEFVAL       { disable }
            ::= { zxAcParaIwfEtherEntry 9 }

zxAcParaIwfEtherInUnknowBps OBJECT-TYPE
            SYNTAX       Counter64
            UNITS         "Bytes per second"
            MAX-ACCESS   read-only
            STATUS       current
            DESCRIPTION
                "The threshold of warnning for input unknown unicast bytes 
                rate."
            ::= { zxAcParaIwfEtherEntry 10 }

zxAcParaIwfEtherInUnknowPps OBJECT-TYPE
            SYNTAX       Unsigned32
            UNITS         "Packets per second"
            MAX-ACCESS   read-only
            STATUS       current
            DESCRIPTION
                "The threshold of warnning for input unknown unicast packets 
                rate."
            ::= { zxAcParaIwfEtherEntry 11 }

zxAcParaIwfEtherInBroadBps OBJECT-TYPE
            SYNTAX       Counter64
            UNITS         "Bytes per second"
            MAX-ACCESS   read-only
            STATUS       current
            DESCRIPTION
                "The threshold of warnning for input broadcast bytes rate."
            ::= { zxAcParaIwfEtherEntry 12 }

zxAcParaIwfEtherInBroadPps OBJECT-TYPE
            SYNTAX       Unsigned32
            UNITS         "Packets per second"
            MAX-ACCESS   read-only
            STATUS       current
            DESCRIPTION
                "The threshold of warnning for input broadcast packets rate."
            ::= { zxAcParaIwfEtherEntry 13 }

zxAcParaIwfEtherInDropBps OBJECT-TYPE
            SYNTAX       Counter64
            UNITS         "Bytes per second"
            MAX-ACCESS   read-only
            STATUS       current
            DESCRIPTION
                "The threshold of warnning for input dropped bytes rate."
            ::= { zxAcParaIwfEtherEntry 14 }

zxAcParaIwfEtherInDropPps OBJECT-TYPE
            SYNTAX       Unsigned32
            UNITS         "Packets per second"
            MAX-ACCESS   read-only
            STATUS       current
            DESCRIPTION
                "The threshold of warnning for input dropped packets rate."
            ::= { zxAcParaIwfEtherEntry 15 }

--*************zxAcParaMspwRmtTable****************  
zxAcParaMspwRmtTable OBJECT-TYPE
            SYNTAX     SEQUENCE OF ZxAcParaMspwRmtEntry
            MAX-ACCESS not-accessible
            STATUS     current
            DESCRIPTION
                "MSPW remote AC parameters Table. This table contains
                 one entry per MSPW remote AC parameters Table."        
            ::= { zxL2vpnAC 6 }

zxAcParaMspwRmtEntry OBJECT-TYPE
            SYNTAX     ZxAcParaMspwRmtEntry
            MAX-ACCESS not-accessible
            STATUS     current
            DESCRIPTION
                "The parameter of a MSPW remote AC parameters entity 
                containing."
            INDEX { zxAcParaMspwRmtInstName }
            ::= { zxAcParaMspwRmtTable 1 }

ZxAcParaMspwRmtEntry ::= SEQUENCE {
            zxAcParaMspwRmtInstName             DisplayString,
            zxAcParaMspwRmtDescription          DisplayString,
            zxAcParaMspwRmtMTU                  Unsigned32,
            zxAcParaMspwRmtFragment             INTEGER,
            zxAcParaMspwRmtFcsRetHeadLenFlag    INTEGER,
            zxAcParaMspwRmtAtmCellCon           Unsigned32,
            zxAcParaMspwRmtRequestedVlanID      Unsigned32,
            zxAcParaMspwRmtFrDlciHeadLen        Unsigned32,
            zxAcParaMspwRmtTdmTimeSlots         Unsigned32,
            zxAcParaMspwRmtTdmDistPeriod        Unsigned32,
            zxAcParaMspwRmtTdmRtpHeader         INTEGER,
            zxAcParaMspwRmtTdmRtpDiffTS         INTEGER,
            zxAcParaMspwRmtTdmRtpSSRC           Unsigned32,
            zxAcParaMspwRmtTdmRtpFrequency      Unsigned32,
            zxAcParaMspwRmtTdmPayloadType       Unsigned32,
            zxAcParaMspwRmtTdmCasTrunk          INTEGER,
            zxAcParaMspwRmtTdmSigPkts           INTEGER,
            zxAcParaMspwRmtTdmCepDbaAis         INTEGER,
            zxAcParaMspwRmtTdmCepDbaUne         INTEGER,
            zxAcParaMspwRmtTdmCepEMB            INTEGER,
            zxAcParaMspwRmtTdmCepAsyncType      INTEGER,
            zxAcParaMspwRmtTdmCepConnType       INTEGER,
            zxAcParaMspwRmtTdmAal1CellPerPkt    Unsigned32,
            zxAcParaMspwRmtTdmAal1Mode          INTEGER,
            zxAcParaMspwRmtTdmAal2MaxDurt       Unsigned32,
            zxAcParaMspwRmtTdmAal2VadMode       INTEGER
            }

zxAcParaMspwRmtInstName OBJECT-TYPE
            SYNTAX       DisplayString  (SIZE(0..32))
            MAX-ACCESS   not-accessible
            STATUS       current
            DESCRIPTION
                "The name of the MSPW instance."
            ::= { zxAcParaMspwRmtEntry 1 }

zxAcParaMspwRmtDescription OBJECT-TYPE
            SYNTAX       DisplayString  (SIZE(0..80))
            MAX-ACCESS   read-only
            STATUS       current
            DESCRIPTION
                "Interface description of the remote interface parameter."
            ::= { zxAcParaMspwRmtEntry 2 }
 
zxAcParaMspwRmtMTU OBJECT-TYPE
            SYNTAX       Unsigned32(60..9216)
            MAX-ACCESS   read-only
            STATUS       current
            DESCRIPTION
                "The MTU value of the remote interface parameter."
            DEFVAL       { 1500 }
            ::= { zxAcParaMspwRmtEntry 3 }

zxAcParaMspwRmtFragment OBJECT-TYPE
            SYNTAX       INTEGER{
            disable(1),
            enable(2)
            }
            MAX-ACCESS   read-only
            STATUS       current
            DESCRIPTION
                "Fragmentation flag of the remote interface parameter."
            DEFVAL       { disable }
            ::= { zxAcParaMspwRmtEntry 4 } 

zxAcParaMspwRmtFcsRetHeadLenFlag OBJECT-TYPE
            SYNTAX       INTEGER{
            null(1),
            fcsHeadLenIsTwo(2),
            fcsHeadLenIsFour(3)
            }
            MAX-ACCESS   read-only
            STATUS       current
            DESCRIPTION
                "Frame check sequence retention head length flag of the remote
                interface parameter."
            DEFVAL       { null }
            ::= { zxAcParaMspwRmtEntry 5 }

zxAcParaMspwRmtAtmCellCon OBJECT-TYPE
            SYNTAX       Unsigned32(0..64)
            MAX-ACCESS   read-only
            STATUS       current
            DESCRIPTION
                "The maximum of ATM cell concatenate of the remote interface
                parameter."
            DEFVAL       { 0 }
            ::= { zxAcParaMspwRmtEntry 6 }

zxAcParaMspwRmtRequestedVlanID OBJECT-TYPE
            SYNTAX       Unsigned32(0..4094)
            MAX-ACCESS   read-only
            STATUS       current
            DESCRIPTION
                "Ethernet request VLAN ID of the remote interface parameter."
            DEFVAL       { 0 }
            ::= { zxAcParaMspwRmtEntry 7 }

zxAcParaMspwRmtFrDlciHeadLen OBJECT-TYPE
            SYNTAX       Unsigned32(0..4)
            MAX-ACCESS   read-only
            STATUS       current
            DESCRIPTION
                "FR DLCI header length of the remote interface parameter."
            DEFVAL       { 0 }
            ::= { zxAcParaMspwRmtEntry 8 }

zxAcParaMspwRmtTdmTimeSlots OBJECT-TYPE
            SYNTAX       Unsigned32(0..1000)
            MAX-ACCESS   read-only
            STATUS       current
            DESCRIPTION
                "TDM time slots count of the remote interface parameter."
            DEFVAL       { 0 }
            ::= { zxAcParaMspwRmtEntry 9 }

zxAcParaMspwRmtTdmDistPeriod OBJECT-TYPE
            SYNTAX       Unsigned32(0..64)
            MAX-ACCESS   read-only
            STATUS       current
            DESCRIPTION
                "TDM distribute period of the remote interface parameter."
            DEFVAL       { 0 }
            ::= { zxAcParaMspwRmtEntry 10 }

zxAcParaMspwRmtTdmRtpHeader OBJECT-TYPE
            SYNTAX       INTEGER{
            disable(1),
            enable(2)
            }
            MAX-ACCESS   read-only
            STATUS       current
            DESCRIPTION
                "The RTP header used flag of the remote interface parameter."
            DEFVAL       { disable }
            ::= { zxAcParaMspwRmtEntry 11 } 

zxAcParaMspwRmtTdmRtpDiffTS OBJECT-TYPE
            SYNTAX       INTEGER{
            disable(1),
            enable(2)
            }
            MAX-ACCESS   read-only
            STATUS       current
            DESCRIPTION
                "The RTP differential timestamp mode flag of the remote
                interface parameter."
            DEFVAL       { disable }
            ::= { zxAcParaMspwRmtEntry 12 } 

zxAcParaMspwRmtTdmRtpSSRC OBJECT-TYPE
            SYNTAX       Unsigned32(0..4294967295)
            MAX-ACCESS   read-only
            STATUS       current
            DESCRIPTION
                "The RTP synchronization source ID of the remote interface 
                parameter."
            DEFVAL       { 0 }
            ::= { zxAcParaMspwRmtEntry 13 }

zxAcParaMspwRmtTdmRtpFrequency OBJECT-TYPE
            SYNTAX       Unsigned32(0..65535)
            MAX-ACCESS   read-only
            STATUS       current
            DESCRIPTION
                "The RTP frequency of the remote interface parameter."
            DEFVAL       { 0 }
            ::= { zxAcParaMspwRmtEntry 14 }

zxAcParaMspwRmtTdmPayloadType OBJECT-TYPE
            SYNTAX       Unsigned32(0..127)
            MAX-ACCESS   read-only
            STATUS       current
            DESCRIPTION
                "TDM payload type of the remote interface parameter."
            DEFVAL       { 0 }
            ::= { zxAcParaMspwRmtEntry 15 }

zxAcParaMspwRmtTdmCasTrunk OBJECT-TYPE
            SYNTAX       INTEGER{
            null(1),
            e1(2),
            t1Esf(3),
            t1Sf(4)
            }
            MAX-ACCESS   read-only
            STATUS       current
            DESCRIPTION
                "TDM CAS trunk type of the remote interface parameter."
            DEFVAL       { null }
            ::= { zxAcParaMspwRmtEntry 16 }

zxAcParaMspwRmtTdmSigPkts OBJECT-TYPE
            SYNTAX       INTEGER{
            nonTransmitted(1),
            togetherWithData(2),
            apartFromDataJustHere(3),
            apartFromDataOverThere(4)
            }
            MAX-ACCESS   read-only
            STATUS       current
            DESCRIPTION
                "TDM signalling packets type of the remote interface 
                parameter."
            DEFVAL       { nonTransmitted }
            ::= { zxAcParaMspwRmtEntry 17 }

zxAcParaMspwRmtTdmCepDbaAis OBJECT-TYPE
            SYNTAX       INTEGER{
            disable(1),
            enable(2)
            }
            MAX-ACCESS   read-only
            STATUS       current
            DESCRIPTION
                "TDM CEP DBA trigger event of AIS flag of the remote interface
                parameter."
            DEFVAL       { disable }
            ::= { zxAcParaMspwRmtEntry 18 }

zxAcParaMspwRmtTdmCepDbaUne OBJECT-TYPE
            SYNTAX       INTEGER{
            disable(1),
            enable(2)
            }
            MAX-ACCESS   read-only
            STATUS       current
            DESCRIPTION
                "TDM CEP DBA trigger evnent of UNE flag of the remote 
                interface parameter."
            DEFVAL       { disable }
            ::= { zxAcParaMspwRmtEntry 19 }

zxAcParaMspwRmtTdmCepEMB OBJECT-TYPE
            SYNTAX       INTEGER{
            disable(1),
            enable(2)
            }
            MAX-ACCESS   read-only
            STATUS       current
            DESCRIPTION
                "TDM CEP EMB flag of the remote interface parameter."
            DEFVAL       { disable }
            ::= { zxAcParaMspwRmtEntry 20 }

zxAcParaMspwRmtTdmCepAsyncType OBJECT-TYPE
            SYNTAX       INTEGER{
            null(1),
            t3(2),
            e3(3)
            }
            MAX-ACCESS   read-only
            STATUS       current
            DESCRIPTION
                "TDM CEP Async E3/T3 bandwidth reduction type of the remote
                interface parameter."
            DEFVAL       { null }
            ::= { zxAcParaMspwRmtEntry 21 }

zxAcParaMspwRmtTdmCepConnType OBJECT-TYPE
            SYNTAX       INTEGER{
            spe(1),
            vt(2),
            fractionalSpe(3)
            }
            MAX-ACCESS   read-only
            STATUS       current
            DESCRIPTION
                "TDM CEP connection type of the remote interface parameter."
            DEFVAL       { spe }
            ::= { zxAcParaMspwRmtEntry 22 }

zxAcParaMspwRmtTdmAal1CellPerPkt OBJECT-TYPE
            SYNTAX       Unsigned32(0..100)
            MAX-ACCESS   read-only
            STATUS       current
            DESCRIPTION
                "TDM AAL1 cell per packet of the remote interface parameter."
            DEFVAL       { 0 }
            ::= { zxAcParaMspwRmtEntry 23 }

zxAcParaMspwRmtTdmAal1Mode OBJECT-TYPE
            SYNTAX       INTEGER{
            unstructured(1),
            structured(2),
            structuredWithCas(3)
            }
            MAX-ACCESS   read-only
            STATUS       current
            DESCRIPTION
                "TDM AAL1 mode of the remote interface parameter."
            DEFVAL       { structured }
            ::= { zxAcParaMspwRmtEntry 24 }

zxAcParaMspwRmtTdmAal2MaxDurt OBJECT-TYPE
            SYNTAX       Unsigned32(0..64)
            MAX-ACCESS   read-only
            STATUS       current
            DESCRIPTION
                "TDM AAL2 max duration of the remote interface parameter."
            DEFVAL       { 0 }
            ::= { zxAcParaMspwRmtEntry 25 }

zxAcParaMspwRmtTdmAal2VadMode OBJECT-TYPE
            SYNTAX       INTEGER{
            signalIndicated(1),
            byDectection(2),
            alwaysActive(3)
            }
            MAX-ACCESS   read-only
            STATUS       current
            DESCRIPTION
                "TDM AAL2 VAD mode of the remote interface parameter."
            DEFVAL       { signalIndicated }
            ::= { zxAcParaMspwRmtEntry 26 }

--*************zxAcParaAtmTable****************  
zxAcParaAtmTable OBJECT-TYPE
            SYNTAX     SEQUENCE OF ZxAcParaAtmEntry
            MAX-ACCESS not-accessible
            STATUS     current
            DESCRIPTION
                "AC ATM Table.This table contains one entry per AC ATM table."
            ::= { zxL2vpnAC 7 }

zxAcParaAtmEntry OBJECT-TYPE
            SYNTAX     ZxAcParaAtmEntry
            MAX-ACCESS not-accessible
            STATUS     current
            DESCRIPTION
                "The parameter of a AC ATM entity containing."
            INDEX { zxAcParaAtmInstName , zxAcParaAtmIfName }
            ::= { zxAcParaAtmTable 1 }

ZxAcParaAtmEntry ::= SEQUENCE {
            zxAcParaAtmInstName                 DisplayString,
            zxAcParaAtmIfName                   DisplayString,
            zxAcParaAtmCellCon                  Unsigned32,
            zxAcParaAtmFaultSpread              INTEGER,
            zxAcParaAtmStatisEnStatus           INTEGER,
            zxAcParaAtmInUnknowBps              Counter64,
            zxAcParaAtmInUnknowPps              Unsigned32,
            zxAcParaAtmInBroadBps               Counter64,
            zxAcParaAtmInBroadPps               Unsigned32,
            zxAcParaAtmInDropBps                Counter64,
            zxAcParaAtmInDropPps                Unsigned32
            }

zxAcParaAtmInstName OBJECT-TYPE
            SYNTAX       DisplayString  (SIZE(0..32))
            MAX-ACCESS   not-accessible
            STATUS       current
            DESCRIPTION
                "The name of the instance in the bind."
            ::= { zxAcParaAtmEntry 1 }

zxAcParaAtmIfName OBJECT-TYPE
            SYNTAX       DisplayString  (SIZE(0..31))
            MAX-ACCESS   not-accessible
            STATUS       current
            DESCRIPTION
                "The name of the AC in the bind."
            ::= { zxAcParaAtmEntry 2 }  

zxAcParaAtmCellCon OBJECT-TYPE
            SYNTAX       Unsigned32(0..28)
            MAX-ACCESS   read-only
            STATUS       current
            DESCRIPTION
                "The maximum of ATM cell concatenate of the AC ATM parameter."
            DEFVAL       { 0 }
            ::= { zxAcParaAtmEntry 3 }

zxAcParaAtmFaultSpread OBJECT-TYPE
            SYNTAX       INTEGER{
            enable(1),
            disable(2)
            }
            MAX-ACCESS   read-only
            STATUS       current
            DESCRIPTION
                "The flag of the ATM parameter's fault-spread."
            DEFVAL       { enable }
            ::= { zxAcParaAtmEntry 4 }

zxAcParaAtmStatisEnStatus OBJECT-TYPE
            SYNTAX       INTEGER{
            disable(1),
            enable(2)
            }
            MAX-ACCESS   read-only
            STATUS       current
            DESCRIPTION
                "The enable status of the AC ATM parameter's traffic 
                statistics."
            DEFVAL       { disable }
            ::= { zxAcParaAtmEntry 5 }

zxAcParaAtmInUnknowBps OBJECT-TYPE
            SYNTAX       Counter64
            UNITS         "Bytes per second"
            MAX-ACCESS   read-only
            STATUS       current
            DESCRIPTION
                "The threshold of warnning for input unknown unicast bytes 
                rate."
            ::= { zxAcParaAtmEntry 6 }

zxAcParaAtmInUnknowPps OBJECT-TYPE
            SYNTAX       Unsigned32
            UNITS         "Packets per second"
            MAX-ACCESS   read-only
            STATUS       current
            DESCRIPTION
                "The threshold of warnning for input unknown unicast packets 
                rate."
            ::= { zxAcParaAtmEntry 7 }

zxAcParaAtmInBroadBps OBJECT-TYPE
            SYNTAX       Counter64
            UNITS         "Bytes per second"
            MAX-ACCESS   read-only
            STATUS       current
            DESCRIPTION
                "The threshold of warnning for input broadcast bytes rate."
            ::= { zxAcParaAtmEntry 8 }

zxAcParaAtmInBroadPps OBJECT-TYPE
            SYNTAX       Unsigned32
            UNITS         "Packets per second"
            MAX-ACCESS   read-only
            STATUS       current
            DESCRIPTION
                "The threshold of warnning for input broadcast packets rate."
            ::= { zxAcParaAtmEntry 9 }

zxAcParaAtmInDropBps OBJECT-TYPE
            SYNTAX       Counter64
            UNITS         "Bytes per second"
            MAX-ACCESS   read-only
            STATUS       current
            DESCRIPTION
                "The threshold of warnning for input dropped bytes rate."
            ::= { zxAcParaAtmEntry 10 }

zxAcParaAtmInDropPps OBJECT-TYPE
            SYNTAX       Unsigned32
            UNITS         "Packets per second"
            MAX-ACCESS   read-only
            STATUS       current
            DESCRIPTION
                "The threshold of warnning for input dropped packets rate."
            ::= { zxAcParaAtmEntry 11 }

--*************zxAcParaHdlcTable****************  
zxAcParaHdlcTable OBJECT-TYPE
            SYNTAX     SEQUENCE OF ZxAcParaHdlcEntry
            MAX-ACCESS not-accessible
            STATUS     current
            DESCRIPTION
                "AC HDLC Table.This table contains one entry per AC HDLC 
                table."
            ::= { zxL2vpnAC 8 }

zxAcParaHdlcEntry OBJECT-TYPE
            SYNTAX     ZxAcParaHdlcEntry
            MAX-ACCESS not-accessible
            STATUS     current
            DESCRIPTION
                "The parameter of a AC HDLC entity containing."
            INDEX { zxAcParaHdlcInstName , zxAcParaHdlcIfName }
            ::= { zxAcParaHdlcTable 1 }

ZxAcParaHdlcEntry ::= SEQUENCE {
            zxAcParaHdlcInstName                DisplayString,
            zxAcParaHdlcIfName                  DisplayString,
            zxAcParaHdlcFaultSpread             INTEGER,
            zxAcParaHdlcStatisEnStatus          INTEGER,
            zxAcParaHdlcInUnknowBps             Counter64,
            zxAcParaHdlcInUnknowPps             Unsigned32,
            zxAcParaHdlcInBroadBps              Counter64,
            zxAcParaHdlcInBroadPps              Unsigned32,
            zxAcParaHdlcInDropBps               Counter64,
            zxAcParaHdlcInDropPps               Unsigned32
            }

zxAcParaHdlcInstName OBJECT-TYPE
            SYNTAX       DisplayString  (SIZE(0..32))
            MAX-ACCESS   not-accessible
            STATUS       current
            DESCRIPTION
                "The name of the instance in the bind."
            ::= { zxAcParaHdlcEntry 1 }

zxAcParaHdlcIfName OBJECT-TYPE
            SYNTAX       DisplayString  (SIZE(0..31))
            MAX-ACCESS   not-accessible
            STATUS       current
            DESCRIPTION
                "The name of the AC in the bind."
            ::= { zxAcParaHdlcEntry 2 }  

zxAcParaHdlcFaultSpread OBJECT-TYPE
            SYNTAX       INTEGER{
            enable(1),
            disable(2)
            }
            MAX-ACCESS   read-only
            STATUS       current
            DESCRIPTION
                "The flag of the HDLC parameter's fault-spread."
            DEFVAL       { enable }
            ::= { zxAcParaHdlcEntry 3 }

zxAcParaHdlcStatisEnStatus OBJECT-TYPE
            SYNTAX       INTEGER{
            disable(1),
            enable(2)
            }
            MAX-ACCESS   read-only
            STATUS       current
            DESCRIPTION
                "The enable status of the AC HDLC parameter's traffic 
                statistics."
            DEFVAL       { disable }
            ::= { zxAcParaHdlcEntry 4 }

zxAcParaHdlcInUnknowBps OBJECT-TYPE
            SYNTAX       Counter64
            UNITS         "Bytes per second"
            MAX-ACCESS   read-only
            STATUS       current
            DESCRIPTION
                "The threshold of warnning for input unknown unicast bytes 
                rate."
            ::= { zxAcParaHdlcEntry 5 }

zxAcParaHdlcInUnknowPps OBJECT-TYPE
            SYNTAX       Unsigned32
            UNITS         "Packets per second"
            MAX-ACCESS   read-only
            STATUS       current
            DESCRIPTION
                "The threshold of warnning for input unknown unicast packets 
                rate."
            ::= { zxAcParaHdlcEntry 6 }

zxAcParaHdlcInBroadBps OBJECT-TYPE
            SYNTAX       Counter64
            UNITS         "Bytes per second"
            MAX-ACCESS   read-only
            STATUS       current
            DESCRIPTION
                "The threshold of warnning for input broadcast bytes rate."
            ::= { zxAcParaHdlcEntry 7 }

zxAcParaHdlcInBroadPps OBJECT-TYPE
            SYNTAX       Unsigned32
            UNITS         "Packets per second"
            MAX-ACCESS   read-only
            STATUS       current
            DESCRIPTION
                "The threshold of warnning for input broadcast packets rate."
            ::= { zxAcParaHdlcEntry 8 }

zxAcParaHdlcInDropBps OBJECT-TYPE
            SYNTAX       Counter64
            UNITS         "Bytes per second"
            MAX-ACCESS   read-only
            STATUS       current
            DESCRIPTION
                "The threshold of warnning for input dropped bytes rate."
            ::= { zxAcParaHdlcEntry 9 }

zxAcParaHdlcInDropPps OBJECT-TYPE
            SYNTAX       Unsigned32
            UNITS         "Packets per second"
            MAX-ACCESS   read-only
            STATUS       current
            DESCRIPTION
                "The threshold of warnning for input dropped packets rate."
            ::= { zxAcParaHdlcEntry 10 }

--*************zxAcParaPppTable****************  
zxAcParaPppTable OBJECT-TYPE
            SYNTAX     SEQUENCE OF ZxAcParaPppEntry
            MAX-ACCESS not-accessible
            STATUS     current
            DESCRIPTION
                "AC PPP Table.This table contains one entry per AC PPP table."
            ::= { zxL2vpnAC 9 }

zxAcParaPppEntry OBJECT-TYPE
            SYNTAX     ZxAcParaPppEntry
            MAX-ACCESS not-accessible
            STATUS     current
            DESCRIPTION
                "The parameter of a AC PPP entity containing."
            INDEX { zxAcParaPppInstName , zxAcParaPppIfName }
            ::= { zxAcParaPppTable 1 }

ZxAcParaPppEntry ::= SEQUENCE {
            zxAcParaPppInstName                 DisplayString,
            zxAcParaPppIfName                   DisplayString,
            zxAcParaPppFaultSpread              INTEGER,
            zxAcParaPppStatisEnStatus           INTEGER,
            zxAcParaPppInUnknowBps              Counter64,
            zxAcParaPppInUnknowPps              Unsigned32,
            zxAcParaPppInBroadBps               Counter64,
            zxAcParaPppInBroadPps               Unsigned32,
            zxAcParaPppInDropBps                Counter64,
            zxAcParaPppInDropPps                Unsigned32
            }

zxAcParaPppInstName OBJECT-TYPE
            SYNTAX       DisplayString  (SIZE(0..32))
            MAX-ACCESS   not-accessible
            STATUS       current
            DESCRIPTION
                "The name of the instance in the bind."
            ::= { zxAcParaPppEntry 1 }

zxAcParaPppIfName OBJECT-TYPE
            SYNTAX       DisplayString  (SIZE(0..31))
            MAX-ACCESS   not-accessible
            STATUS       current
            DESCRIPTION
                "The name of the AC in the bind."
            ::= { zxAcParaPppEntry 2 }  

zxAcParaPppFaultSpread OBJECT-TYPE
            SYNTAX       INTEGER{
            enable(1),
            disable(2)
            }
            MAX-ACCESS   read-only
            STATUS       current
            DESCRIPTION
                "The flag of the PPP parameter's fault-spread."
            DEFVAL       { enable }
            ::= { zxAcParaPppEntry 3 }

zxAcParaPppStatisEnStatus OBJECT-TYPE
            SYNTAX       INTEGER{
            disable(1),
            enable(2)
            }
            MAX-ACCESS   read-only
            STATUS       current
            DESCRIPTION
                "The enable status of the AC PPP parameter's traffic 
                statistics."
            DEFVAL       { disable }
            ::= { zxAcParaPppEntry 4 }

zxAcParaPppInUnknowBps OBJECT-TYPE
            SYNTAX       Counter64
            UNITS         "Bytes per second"
            MAX-ACCESS   read-only
            STATUS       current
            DESCRIPTION
                "The threshold of warnning for input unknown unicast bytes 
                rate."
            ::= { zxAcParaPppEntry 5 }

zxAcParaPppInUnknowPps OBJECT-TYPE
            SYNTAX       Unsigned32
            UNITS         "Packets per second"
            MAX-ACCESS   read-only
            STATUS       current
            DESCRIPTION
                "The threshold of warnning for input unknown unicast packets 
                rate."
            ::= { zxAcParaPppEntry 6 }

zxAcParaPppInBroadBps OBJECT-TYPE
            SYNTAX       Counter64
            UNITS         "Bytes per second"
            MAX-ACCESS   read-only
            STATUS       current
            DESCRIPTION
                "The threshold of warnning for input broadcast bytes rate."
            ::= { zxAcParaPppEntry 7 }

zxAcParaPppInBroadPps OBJECT-TYPE
            SYNTAX       Unsigned32
            UNITS         "Packets per second"
            MAX-ACCESS   read-only
            STATUS       current
            DESCRIPTION
                "The threshold of warnning for input broadcast packets rate."
            ::= { zxAcParaPppEntry 8 }

zxAcParaPppInDropBps OBJECT-TYPE
            SYNTAX       Counter64
            UNITS         "Bytes per second"
            MAX-ACCESS   read-only
            STATUS       current
            DESCRIPTION
                "The threshold of warnning for input dropped bytes rate."
            ::= { zxAcParaPppEntry 9 }

zxAcParaPppInDropPps OBJECT-TYPE
            SYNTAX       Unsigned32
            UNITS         "Packets per second"
            MAX-ACCESS   read-only
            STATUS       current
            DESCRIPTION
                "The threshold of warnning for input dropped packets rate."
            ::= { zxAcParaPppEntry 10 }

--*************zxAcParaFrTable****************  
zxAcParaFrTable OBJECT-TYPE
            SYNTAX     SEQUENCE OF ZxAcParaFrEntry
            MAX-ACCESS not-accessible
            STATUS     current
            DESCRIPTION
                "AC FR Table.This table contains one entry per AC FR table."
            ::= { zxL2vpnAC 10 }

zxAcParaFrEntry OBJECT-TYPE
            SYNTAX     ZxAcParaFrEntry
            MAX-ACCESS not-accessible
            STATUS     current
            DESCRIPTION
                "The parameter of a AC FR entity containing."
            INDEX { zxAcParaFrInstName , zxAcParaFrIfName }
            ::= { zxAcParaFrTable 1 }

ZxAcParaFrEntry ::= SEQUENCE {
            zxAcParaFrInstName                  DisplayString,
            zxAcParaFrIfName                    DisplayString,
            zxAcParaFrFaultSpread               INTEGER,
            zxAcParaFrStatisEnStatus            INTEGER,
            zxAcParaFrInUnknowBps               Counter64,
            zxAcParaFrInUnknowPps               Unsigned32,
            zxAcParaFrInBroadBps                Counter64,
            zxAcParaFrInBroadPps                Unsigned32,
            zxAcParaFrInDropBps                 Counter64,
            zxAcParaFrInDropPps                 Unsigned32
            }

zxAcParaFrInstName OBJECT-TYPE
            SYNTAX       DisplayString  (SIZE(0..32))
            MAX-ACCESS   not-accessible
            STATUS       current
            DESCRIPTION
                "The name of the instance in the bind."
            ::= { zxAcParaFrEntry 1 }

zxAcParaFrIfName OBJECT-TYPE
            SYNTAX       DisplayString  (SIZE(0..31))
            MAX-ACCESS   not-accessible
            STATUS       current
            DESCRIPTION
                "The name of the AC in the bind."
            ::= { zxAcParaFrEntry 2 }  

zxAcParaFrFaultSpread OBJECT-TYPE
            SYNTAX       INTEGER{
            enable(1),
            disable(2)
            }
            MAX-ACCESS   read-only
            STATUS       current
            DESCRIPTION
                "The flag of the FR parameter's fault-spread."
            DEFVAL       { enable }
            ::= { zxAcParaFrEntry 3 }
            
zxAcParaFrStatisEnStatus OBJECT-TYPE
            SYNTAX       INTEGER{
            disable(1),
            enable(2)
            }
            MAX-ACCESS   read-only
            STATUS       current
            DESCRIPTION
                "The enable status of the AC FR parameter's traffic 
                statistics."
            DEFVAL       { disable }
            ::= { zxAcParaFrEntry 4 }

zxAcParaFrInUnknowBps OBJECT-TYPE
            SYNTAX       Counter64
            UNITS         "Bytes per second"
            MAX-ACCESS   read-only
            STATUS       current
            DESCRIPTION
                "The threshold of warnning for input unknown unicast bytes 
                rate."
            ::= { zxAcParaFrEntry 5 }

zxAcParaFrInUnknowPps OBJECT-TYPE
            SYNTAX       Unsigned32
            UNITS         "Packets per second"
            MAX-ACCESS   read-only
            STATUS       current
            DESCRIPTION
                "The threshold of warnning for input unknown unicast packets 
                rate."
            ::= { zxAcParaFrEntry 6 }

zxAcParaFrInBroadBps OBJECT-TYPE
            SYNTAX       Counter64
            UNITS         "Bytes per second"
            MAX-ACCESS   read-only
            STATUS       current
            DESCRIPTION
                "The threshold of warnning for input broadcast bytes rate."
            ::= { zxAcParaFrEntry 7 }

zxAcParaFrInBroadPps OBJECT-TYPE
            SYNTAX       Unsigned32
            UNITS         "Packets per second"
            MAX-ACCESS   read-only
            STATUS       current
            DESCRIPTION
                "The threshold of warnning for input broadcast packets rate."
            ::= { zxAcParaFrEntry 8 }

zxAcParaFrInDropBps OBJECT-TYPE
            SYNTAX       Counter64
            UNITS         "Bytes per second"
            MAX-ACCESS   read-only
            STATUS       current
            DESCRIPTION
                "The threshold of warnning for input dropped bytes rate."
            ::= { zxAcParaFrEntry 9 }

zxAcParaFrInDropPps OBJECT-TYPE
            SYNTAX       Unsigned32
            UNITS         "Packets per second"
            MAX-ACCESS   read-only
            STATUS       current
            DESCRIPTION
                "The threshold of warnning for input dropped packets rate."
            ::= { zxAcParaFrEntry 10 }
            
--*************zxVplsBgpADPwDetailsTable**************** 
zxVplsBgpADPwDetailsTable OBJECT-TYPE
            SYNTAX     SEQUENCE OF ZxVplsBgpADPwDetailsEntry
            MAX-ACCESS not-accessible
            STATUS     current
            DESCRIPTION
                "Vpls auto-discovery Table."        
            ::= { zxL2vpnVplsBgpAD 1 }

zxVplsBgpADPwDetailsEntry OBJECT-TYPE
            SYNTAX     ZxVplsBgpADPwDetailsEntry
            MAX-ACCESS not-accessible
            STATUS     current
            DESCRIPTION
                "The parameter of a Vpls auto-discovery details "
            INDEX { zxVplsBgpADPwDetailsInstName , 
                zxVplsBgpADPwDetailsDscvType , 
                zxVplsBgpADPwDetailsRemoteEndPoint , 
                zxVplsBgpADPwDetailsRemoteInstanceID }
            ::= { zxVplsBgpADPwDetailsTable 1 }

ZxVplsBgpADPwDetailsEntry ::= SEQUENCE {
            zxVplsBgpADPwDetailsInstName                DisplayString,
            zxVplsBgpADPwDetailsDscvType                INTEGER,
            zxVplsBgpADPwDetailsRemoteEndPoint          IpAddress,
            zxVplsBgpADPwDetailsRemoteDomainID          IpAddress,
            zxVplsBgpADPwDetailsRemoteInstanceID        IpAddress,
            zxVplsBgpADPwDetailsVplsID                  DisplayString,
            zxVplsBgpADPwDetailsEncapType               L2vpnPWType,
            zxVplsBgpADPwDetailsTunlPlcyName            DisplayString,
            zxVplsBgpADPwDetailsControlWord             INTEGER,
            zxVplsBgpADPwDetailsPwTemplateName      DisplayString,
            zxVplsBgpADPwDetailsPwName                  DisplayString,
            zxVplsBgpADPwDetailsLifespanPermanent       INTEGER,
            zxVplsBgpADPwDetailsHubOrSpoke              INTEGER,
            zxVplsBgpADPwDetailsVccvBfd                 INTEGER,
            zxVplsBgpADPwDetailsVccvBfdRaw              INTEGER,  
            zxVplsBgpADPwDetailsVccvBfdStatus           INTEGER
            }

zxVplsBgpADPwDetailsInstName OBJECT-TYPE
            SYNTAX       DisplayString  (SIZE(0..32))
            MAX-ACCESS   read-only
            STATUS       current
            DESCRIPTION
                "The name of the VPLS instance name."
            ::= { zxVplsBgpADPwDetailsEntry 1 } 

zxVplsBgpADPwDetailsDscvType OBJECT-TYPE
            SYNTAX       INTEGER{
            vpls(1),
            mspw(2),
            kompella(3)
            }
            MAX-ACCESS   read-only
            STATUS       current
            DESCRIPTION
                "The type of the auto-discovery."
            ::= { zxVplsBgpADPwDetailsEntry 2 }

zxVplsBgpADPwDetailsRemoteEndPoint OBJECT-TYPE
            SYNTAX       IpAddress
            MAX-ACCESS   read-only
            STATUS       current
            DESCRIPTION
                "The IP address of remote endpoint."
            ::= { zxVplsBgpADPwDetailsEntry 3 } 

zxVplsBgpADPwDetailsRemoteDomainID OBJECT-TYPE
            SYNTAX       IpAddress
            MAX-ACCESS   read-only
            STATUS       current
            DESCRIPTION
                "The domain ID of remote endpoint."
            ::= { zxVplsBgpADPwDetailsEntry 4 }

zxVplsBgpADPwDetailsRemoteInstanceID OBJECT-TYPE
            SYNTAX       IpAddress
            MAX-ACCESS   read-only
            STATUS       current
            DESCRIPTION
                "The instnace ID of remote endpoint."
            ::= { zxVplsBgpADPwDetailsEntry 5 } 

zxVplsBgpADPwDetailsVplsID OBJECT-TYPE
            SYNTAX       DisplayString
            MAX-ACCESS   read-only
            STATUS       obsolete
            DESCRIPTION
                "The Vpls ID of the instance."
            ::= { zxVplsBgpADPwDetailsEntry 6 } 

zxVplsBgpADPwDetailsEncapType OBJECT-TYPE
            SYNTAX       L2vpnPWType
            MAX-ACCESS   read-only
            STATUS       current
            DESCRIPTION
                "The encapulation type ID of the auto-PW ."
            ::= { zxVplsBgpADPwDetailsEntry 7 }

zxVplsBgpADPwDetailsTunlPlcyName OBJECT-TYPE
            SYNTAX       DisplayString  (SIZE(0..63))
            MAX-ACCESS   read-only
            STATUS       current
            DESCRIPTION
                "The tunnel policy name of the auto-PW ."
            ::= { zxVplsBgpADPwDetailsEntry 8 }

zxVplsBgpADPwDetailsControlWord OBJECT-TYPE
            SYNTAX       INTEGER{
            notPreferred(0),
            preferred(1)
            }
            MAX-ACCESS   read-only
            STATUS       current
            DESCRIPTION
                "The control-word capability of the auto-PW ."
            ::= { zxVplsBgpADPwDetailsEntry 9 } 

zxVplsBgpADPwDetailsPwTemplateName OBJECT-TYPE
            SYNTAX       DisplayString  (SIZE(0..31))
            MAX-ACCESS   read-only
            STATUS       current
            DESCRIPTION
                "The template name of the auto-PW ."
            ::= { zxVplsBgpADPwDetailsEntry 10 } 

zxVplsBgpADPwDetailsPwName OBJECT-TYPE
            SYNTAX       DisplayString  (SIZE(0..31))
            MAX-ACCESS   read-only
            STATUS       obsolete
            DESCRIPTION
                "The interface name of the auto-PW ."
            ::= { zxVplsBgpADPwDetailsEntry 11 } 

zxVplsBgpADPwDetailsLifespanPermanent OBJECT-TYPE
            SYNTAX       INTEGER{
            once(0),
            export(1)
            }
            MAX-ACCESS   read-only
            STATUS       current
            DESCRIPTION
                "The life span attribute of the auto-PW ."
            ::= { zxVplsBgpADPwDetailsEntry 12 }

zxVplsBgpADPwDetailsHubOrSpoke OBJECT-TYPE
            SYNTAX       INTEGER{
            spoke(0),
            hub(1)
            }
            MAX-ACCESS   read-only
            STATUS       deprecated
            DESCRIPTION
                "The horizen attribute of the auto-PW ."
            ::= { zxVplsBgpADPwDetailsEntry 13 } 

zxVplsBgpADPwDetailsVccvBfd OBJECT-TYPE
            SYNTAX       INTEGER{
            disable(0),
            enable(1)
            }
            MAX-ACCESS   read-only
            STATUS       current
            DESCRIPTION
                "The BFD capability of the auto-PW ."
            ::= { zxVplsBgpADPwDetailsEntry 14 }

zxVplsBgpADPwDetailsVccvBfdRaw OBJECT-TYPE
            SYNTAX       INTEGER{
            disable(0),
            enable(1)
            }
            MAX-ACCESS   read-only
            STATUS       current
            DESCRIPTION
                "The BFD raw encapsulation capability of the auto-PW ."
            ::= { zxVplsBgpADPwDetailsEntry 15 }

zxVplsBgpADPwDetailsVccvBfdStatus OBJECT-TYPE
            SYNTAX       INTEGER{
            disable(0),
            enable(1)
            }
            MAX-ACCESS   read-only
            STATUS       current
            DESCRIPTION
                "The BFD signal status capability of the auto-PW ."
            ::= { zxVplsBgpADPwDetailsEntry 16 }

--*************zxVplsBgpADRTTable**************** 
zxVplsBgpADRTTable OBJECT-TYPE
            SYNTAX     SEQUENCE OF ZxVplsBgpADRTEntry
            MAX-ACCESS not-accessible
            STATUS     current
            DESCRIPTION
                "Vpls auto-discovery Table."        
            ::= { zxL2vpnVplsBgpAD 2 }

zxVplsBgpADRTEntry OBJECT-TYPE
            SYNTAX     ZxVplsBgpADRTEntry
            MAX-ACCESS not-accessible
            STATUS     current
            DESCRIPTION
                "The parameter of a Vpls auto-discovery route target "
            INDEX { zxVplsBgpADRTInstName , zxVplsBgpADRTDscvType , 
                zxVplsBgpADRTRouteTarget , zxVplsBgpADRTRtEffectType }
            ::= { zxVplsBgpADRTTable 1 }

ZxVplsBgpADRTEntry ::= SEQUENCE {
            zxVplsBgpADRTInstName               DisplayString,
            zxVplsBgpADRTDscvType               INTEGER,
            zxVplsBgpADRTRouteTarget            DisplayString,
            zxVplsBgpADRTRtEffectType           INTEGER,
            zxVplsBgpADRTVplsID                 DisplayString
            }

zxVplsBgpADRTInstName OBJECT-TYPE
            SYNTAX       DisplayString  (SIZE(0..32))
            MAX-ACCESS   read-only
            STATUS       current
            DESCRIPTION
                "The name of the VPLS instance name."
            ::= { zxVplsBgpADRTEntry 1 } 

zxVplsBgpADRTDscvType OBJECT-TYPE
            SYNTAX       INTEGER{
            vpls(1),
            mspw(2),
            kompella(3)
            }
            MAX-ACCESS   read-only
            STATUS       current
            DESCRIPTION
                "The type of the auto-discovery."
            ::= { zxVplsBgpADRTEntry 2 }

zxVplsBgpADRTRouteTarget OBJECT-TYPE
            SYNTAX       DisplayString
            MAX-ACCESS   read-only
            STATUS       current
            DESCRIPTION
                "The route target parameter."
            ::= { zxVplsBgpADRTEntry 3 } 

zxVplsBgpADRTRtEffectType OBJECT-TYPE
            SYNTAX       INTEGER{
            both(1),
            export(2),
            import(3)
            }
            MAX-ACCESS   read-only
            STATUS       current
            DESCRIPTION
                "The route target type parameter."
            ::= { zxVplsBgpADRTEntry 4 }

zxVplsBgpADRTVplsID OBJECT-TYPE
            SYNTAX       DisplayString
            MAX-ACCESS   read-only
            STATUS       obsolete
            DESCRIPTION
                "The Vpls ID of the instance."
            ::= { zxVplsBgpADRTEntry 5 } 

--*************zxVplsKempollaADTable**************** 
zxVplsKempollaADTable OBJECT-TYPE
            SYNTAX     SEQUENCE OF ZxVplsKempollaADEntry
            MAX-ACCESS not-accessible
            STATUS     current
            DESCRIPTION
                "VPLS kempolla auto-discovery route distinguisher table."
            ::= { zxL2vpnVplsBgpAD 3 }

zxVplsKempollaADEntry OBJECT-TYPE
            SYNTAX     ZxVplsKempollaADEntry
            MAX-ACCESS not-accessible
            STATUS     current
            DESCRIPTION
                "The parameter of a VPLS kempolla auto-discovery route
                distinguisher."
            INDEX { zxVplsKempollaADInstName }
            ::= { zxVplsKempollaADTable 1 }

ZxVplsKempollaADEntry ::= SEQUENCE {
            zxVplsKempollaADInstName            DisplayString,
            zxVplsKempollaADRD                  DisplayString,
            zxVplsKempollaADVeID                Unsigned32,
            zxVplsKempollaADVeSetStyle          INTEGER,
            zxVplsKempollaADMaxVeID             Unsigned32,
            zxVplsKempollaADTunnelPolicy        DisplayString
            }

zxVplsKempollaADInstName OBJECT-TYPE
            SYNTAX       DisplayString  (SIZE(0..32))
            MAX-ACCESS   not-accessible
            STATUS       current
            DESCRIPTION
                "The name of the VPLS instance name."
            ::= { zxVplsKempollaADEntry 1 } 

zxVplsKempollaADRD OBJECT-TYPE
            SYNTAX       DisplayString
            MAX-ACCESS   read-only
            STATUS       current
            DESCRIPTION
                "The route distinguisher parameter."
            ::= { zxVplsKempollaADEntry 2 } 

zxVplsKempollaADVeID OBJECT-TYPE
            SYNTAX       Unsigned32(0..65535)
            MAX-ACCESS   read-only
            STATUS       current
            DESCRIPTION
                "The VE ID value parameter.The invalid value is 65535."
            ::= { zxVplsKempollaADEntry 3 }

zxVplsKempollaADVeSetStyle OBJECT-TYPE
            SYNTAX       INTEGER{
            null(1),
            continuous(2),
            discrete(3)
            }
            MAX-ACCESS   read-only
            STATUS       current
            DESCRIPTION
                "The style of VE set parameter."
            DEFVAL       { null }
            ::= { zxVplsKempollaADEntry 4 }
            
zxVplsKempollaADMaxVeID OBJECT-TYPE
            SYNTAX       Unsigned32
            MAX-ACCESS   read-only
            STATUS       current
            DESCRIPTION
                "The maximum VE ID value parameter. The invalid value is 
                4294967295."
            ::= { zxVplsKempollaADEntry 5 }

zxVplsKempollaADTunnelPolicy OBJECT-TYPE
            SYNTAX       DisplayString  (SIZE(0..63))
            MAX-ACCESS   read-only
            STATUS       current
            DESCRIPTION
                "The name of tunnel policy parameter."
            ::= { zxVplsKempollaADEntry 6 } 

--*************zxVplsKempollaADRTTable**************** 
zxVplsKempollaADRTTable OBJECT-TYPE
            SYNTAX     SEQUENCE OF ZxVplsKempollaADRTEntry
            MAX-ACCESS not-accessible
            STATUS     current
            DESCRIPTION
                "VPLS kempolla auto-discovery route target table."        
            ::= { zxL2vpnVplsBgpAD 4 }

zxVplsKempollaADRTEntry OBJECT-TYPE
            SYNTAX     ZxVplsKempollaADRTEntry
            MAX-ACCESS not-accessible
            STATUS     current
            DESCRIPTION
                "The parameter of VPLS kempolla auto-discovery route target."
            INDEX { zxVplsKempollaADRTInstName, 
            zxVplsKempollaADRTRouteTarget,
            zxVplsKempollaADRTRtEffectType }
            ::= { zxVplsKempollaADRTTable 1 }

ZxVplsKempollaADRTEntry ::= SEQUENCE {
            zxVplsKempollaADRTInstName          DisplayString,
            zxVplsKempollaADRTRouteTarget       DisplayString,
            zxVplsKempollaADRTRtEffectType      INTEGER
            }

zxVplsKempollaADRTInstName OBJECT-TYPE
            SYNTAX       DisplayString  (SIZE(0..32))
            MAX-ACCESS   not-accessible
            STATUS       current
            DESCRIPTION
                "The name of the VPLS instance name."
            ::= { zxVplsKempollaADRTEntry 1 } 

zxVplsKempollaADRTRouteTarget OBJECT-TYPE
            SYNTAX       DisplayString
            MAX-ACCESS   not-accessible
            STATUS       current
            DESCRIPTION
                "The route target parameter."
            ::= { zxVplsKempollaADRTEntry 2 } 

zxVplsKempollaADRTRtEffectType OBJECT-TYPE
            SYNTAX       INTEGER{
            both(1),
            export(2),
            import(3)
            }
            MAX-ACCESS   read-only
            STATUS       current
            DESCRIPTION
                "The route target type parameter."
            ::= { zxVplsKempollaADRTEntry 3 }

--*************zxVplsKempollaADVETable**************** 
zxVplsKempollaADVETable OBJECT-TYPE
            SYNTAX     SEQUENCE OF ZxVplsKempollaADVEEntry
            MAX-ACCESS not-accessible
            STATUS     current
            DESCRIPTION
                "VPLS kempolla auto-discovery route target table."        
            ::= { zxL2vpnVplsBgpAD 5 }

zxVplsKempollaADVEEntry OBJECT-TYPE
            SYNTAX     ZxVplsKempollaADVEEntry
            MAX-ACCESS not-accessible
            STATUS     current
            DESCRIPTION
                "The parameter of VPLS kempolla auto-discovery route target."
            INDEX { zxVplsKempollaADRTInstName , zxVplsKempollaADVEBeginID }
            ::= { zxVplsKempollaADVETable 1 }

ZxVplsKempollaADVEEntry ::= SEQUENCE {
            zxVplsKempollaADVEInstName          DisplayString,
            zxVplsKempollaADVEBeginID           Unsigned32,
            zxVplsKempollaADVEEndID             Unsigned32
            }

zxVplsKempollaADVEInstName OBJECT-TYPE
            SYNTAX       DisplayString  (SIZE(0..32))
            MAX-ACCESS   not-accessible
            STATUS       current
            DESCRIPTION
                "The name of the VPLS instance name."
            ::= { zxVplsKempollaADVEEntry 1 } 

zxVplsKempollaADVEBeginID OBJECT-TYPE
            SYNTAX       Unsigned32(0..65535)
            MAX-ACCESS   not-accessible
            STATUS       current
            DESCRIPTION
                "The begin value of the VE ID block."
            ::= { zxVplsKempollaADVEEntry 2 } 

zxVplsKempollaADVEEndID OBJECT-TYPE
            SYNTAX       Unsigned32(0..65535)
            MAX-ACCESS   read-only
            STATUS       current
            DESCRIPTION
                "The end value of the VE ID set."
            ::= { zxVplsKempollaADVEEntry 3 }

--*************zxPwStatusTable**************** 
zxPwStatusTable OBJECT-TYPE
            SYNTAX     SEQUENCE OF ZxPwStatusEntry
            MAX-ACCESS not-accessible
            STATUS     current
            DESCRIPTION
                "PW status Table. This table contains
                 one entry per PW."        
            ::= { zxL2vpnStatus 1 }

zxPwStatusEntry OBJECT-TYPE
            SYNTAX     ZxPwStatusEntry
            MAX-ACCESS not-accessible
            STATUS     current
            DESCRIPTION
                "The parameter of a PW status entity containing "
            INDEX { zxPwStatusName }
            ::= { zxPwStatusTable 1 }

ZxPwStatusEntry ::= SEQUENCE {
            zxPwStatusName                      DisplayString,
            zxPwStatusSignalType                INTEGER,
            zxPwStatusPsnTunnelType             INTEGER,
            zxPwStatusPsnTunnelPolicyName       DisplayString,
            zxPwStatusPsnOutLabelDepth          Unsigned32,
            zxPwStatusPsnOutLabel1              Unsigned32,
            zxPwStatusPsnOutLabel2              Unsigned32,
            zxPwStatusPsnOutLabel3              Unsigned32,
            zxPwStatusServiceState              INTEGER,
            zxPwStatusWorkState                 INTEGER,
            zxPwStatusLocalLabel                Unsigned32,
            zxPwStatusRemoteLabel               Unsigned32,
            zxPwStatusLocalGroupId              Unsigned32,
            zxPwStatusLocalCbit                 INTEGER,
            zxPwStatusLocalMTU                  Unsigned32,
            zxPwStatusLocalDescription          DisplayString,
            zxPwStatusLocalStatusWord           Unsigned32,
            zxPwStatusLocalStatusSignalAbility  INTEGER,
            zxPwStatusRemoteGroupId             Unsigned32,
            zxPwStatusRemoteCbit                INTEGER,
            zxPwStatusRemoteMTU                 Unsigned32,
            zxPwStatusRemoteDescription         DisplayString,
            zxPwStatusRemoteStatusWord          Unsigned32,
            zxPwStatusRemoteStatusSignalAbility INTEGER,
            zxPwStatusNegoedCbit                INTEGER,
            zxPwStatusNegoedMTU                 Unsigned32,
            zxPwStatusNegoedStatusSignalAbility INTEGER,
            zxPwStatusSignalState               INTEGER,
            zxPwStatusVccvLocalParas            Unsigned32,
            zxPwStatusVccvRemoteParas           Unsigned32,
            zxPwStatusVccvNegoedParas           Unsigned32,
            zxPwStatusPsnTunnelID                   Unsigned32,
            zxPwStatusPsnOutInterface           DisplayString
            }

zxPwStatusName OBJECT-TYPE
            SYNTAX       DisplayString  (SIZE(0..31))
            MAX-ACCESS   read-only
            STATUS       current
            DESCRIPTION
                "The name of the PW."
            ::= { zxPwStatusEntry 1 }   

zxPwStatusSignalType OBJECT-TYPE
            SYNTAX       INTEGER{
            static(0),
            fec128(1),
            fec129(2)
            }
            MAX-ACCESS   read-only
            STATUS       current
            DESCRIPTION
                "The signal type of the PW."
            ::= { zxPwStatusEntry 2 }

zxPwStatusPsnTunnelType OBJECT-TYPE
            SYNTAX       INTEGER{
            unknown(0),
            route(1),
            te(2)
            }
            MAX-ACCESS   read-only
            STATUS       current
            DESCRIPTION
                "The PSN tunnel type of the PW."
            ::= { zxPwStatusEntry 3 }   

zxPwStatusPsnTunnelPolicyName OBJECT-TYPE
            SYNTAX       DisplayString  (SIZE(0..63))
            MAX-ACCESS   read-only
            STATUS       current
            DESCRIPTION
                "The PSN tunnel policy name of the PW."
            ::= { zxPwStatusEntry 4 } 

zxPwStatusPsnOutLabelDepth OBJECT-TYPE
            SYNTAX       Unsigned32
            MAX-ACCESS   read-only
            STATUS       current
            DESCRIPTION
                "The PSN out label depth of the PW."
            ::= { zxPwStatusEntry 5 }

zxPwStatusPsnOutLabel1 OBJECT-TYPE
            SYNTAX       Unsigned32
            MAX-ACCESS   read-only
            STATUS       current
            DESCRIPTION
                "The PSN out label 1 of the PW."
            ::= { zxPwStatusEntry 6 } 

zxPwStatusPsnOutLabel2 OBJECT-TYPE
            SYNTAX       Unsigned32
            MAX-ACCESS   read-only
            STATUS       current
            DESCRIPTION
                "The PSN out label 2 of the PW."
            ::= { zxPwStatusEntry 7 } 

zxPwStatusPsnOutLabel3 OBJECT-TYPE
            SYNTAX       Unsigned32
            MAX-ACCESS   read-only
            STATUS       current
            DESCRIPTION
                "The PSN out label 3 of the PW."
            ::= { zxPwStatusEntry 8 }    

zxPwStatusServiceState OBJECT-TYPE
            SYNTAX       INTEGER{
            unknown(0),
            down(1),
            up(2)
            }
            MAX-ACCESS   read-only
            STATUS       current
            DESCRIPTION
                "The service state of the PW."
            ::= { zxPwStatusEntry 9 }

zxPwStatusWorkState OBJECT-TYPE
            SYNTAX       INTEGER{
            unknown(0),
            active(1),
            standby(2),
            down(3)
            }
            MAX-ACCESS   read-only
            STATUS       current
            DESCRIPTION
                "The work state of the PW."
            ::= { zxPwStatusEntry 10 }     

zxPwStatusLocalLabel OBJECT-TYPE
            SYNTAX       Unsigned32
            MAX-ACCESS   read-only
            STATUS       current
            DESCRIPTION
                "The local label of the PW."
            ::= { zxPwStatusEntry 11 } 

zxPwStatusRemoteLabel OBJECT-TYPE
            SYNTAX       Unsigned32
            MAX-ACCESS   read-only
            STATUS       current
            DESCRIPTION
                "The remote label of the PW."
            ::= { zxPwStatusEntry 12 }   

zxPwStatusLocalGroupId OBJECT-TYPE
            SYNTAX       Unsigned32
            MAX-ACCESS   read-only
            STATUS       current
            DESCRIPTION
                "The local group id of the PW."
            ::= { zxPwStatusEntry 13 } 

zxPwStatusLocalCbit OBJECT-TYPE
            SYNTAX       INTEGER{
            notPreferred(0),
            preferred(1)
            }
            MAX-ACCESS   read-only
            STATUS       current
            DESCRIPTION
                "The local control word ability of the PW."
            ::= { zxPwStatusEntry 14 }  

zxPwStatusLocalMTU OBJECT-TYPE
            SYNTAX       Unsigned32
            MAX-ACCESS   read-only
            STATUS       current
            DESCRIPTION
                "The local MTU value of the PW."
            ::= { zxPwStatusEntry 15 }

zxPwStatusLocalDescription OBJECT-TYPE
            SYNTAX       DisplayString
            MAX-ACCESS   read-only
            STATUS       current
            DESCRIPTION
                "The local description of the PW."
            ::= { zxPwStatusEntry 16 }  

zxPwStatusLocalStatusWord OBJECT-TYPE
            SYNTAX       Unsigned32
            MAX-ACCESS   read-only
            STATUS       current
            DESCRIPTION
                "The local status of the PW."
            ::= { zxPwStatusEntry 17 }

zxPwStatusLocalStatusSignalAbility OBJECT-TYPE
            SYNTAX       INTEGER{
            unknown(0),
            martini(1),
            pwe3(2)
            }
            MAX-ACCESS   read-only
            STATUS       current
            DESCRIPTION
                "The local status signal ability of the PW."
            ::= { zxPwStatusEntry 18 }

zxPwStatusRemoteGroupId OBJECT-TYPE
            SYNTAX       Unsigned32
            MAX-ACCESS   read-only
            STATUS       current
            DESCRIPTION
                "The remote group id of the PW."
            ::= { zxPwStatusEntry 19 } 

zxPwStatusRemoteCbit OBJECT-TYPE
            SYNTAX       INTEGER{
            notPreferred(0),
            preferred(1)
            }
            MAX-ACCESS   read-only
            STATUS       current
            DESCRIPTION
                "The remote control word ability of the PW."
            ::= { zxPwStatusEntry 20 }  

zxPwStatusRemoteMTU OBJECT-TYPE
            SYNTAX       Unsigned32
            MAX-ACCESS   read-only
            STATUS       current
            DESCRIPTION
                "The remote MTU value of the PW."
            ::= { zxPwStatusEntry 21 }

zxPwStatusRemoteDescription OBJECT-TYPE
            SYNTAX       DisplayString
            MAX-ACCESS   read-only
            STATUS       current
            DESCRIPTION
                "The remote description of the PW."
            ::= { zxPwStatusEntry 22 }  

zxPwStatusRemoteStatusWord OBJECT-TYPE
            SYNTAX       Unsigned32
            MAX-ACCESS   read-only
            STATUS       current
            DESCRIPTION
                "The remote status of the PW."
            ::= { zxPwStatusEntry 23 }

zxPwStatusRemoteStatusSignalAbility OBJECT-TYPE
            SYNTAX       INTEGER{
            unknown(0),
            martini(1),
            pwe3(2)
            }
            MAX-ACCESS   read-only
            STATUS       current
            DESCRIPTION
                "The remote status signal ability of the PW."
            ::= { zxPwStatusEntry 24 }   

zxPwStatusNegoedCbit OBJECT-TYPE
            SYNTAX       INTEGER{
            notPreferred(0),
            preferred(1)
            }
            MAX-ACCESS   read-only
            STATUS       current
            DESCRIPTION
                "The negotiatied control word ability of the PW."
            ::= { zxPwStatusEntry 25 }  

zxPwStatusNegoedMTU OBJECT-TYPE
            SYNTAX       Unsigned32
            MAX-ACCESS   read-only
            STATUS       current
            DESCRIPTION
                "The negotiatied MTU value of the PW."
            ::= { zxPwStatusEntry 26 }

zxPwStatusNegoedStatusSignalAbility OBJECT-TYPE
            SYNTAX       INTEGER{
            unknown(0),
            martini(1),
            pwe3(2)
            }
            MAX-ACCESS   read-only
            STATUS       current
            DESCRIPTION
                "The negotiatied status signal ability of the PW."
            ::= { zxPwStatusEntry 27 }  

zxPwStatusSignalState OBJECT-TYPE
            SYNTAX       INTEGER{
            down(0),
            up(1)
            }
            MAX-ACCESS   read-only
            STATUS       current
            DESCRIPTION
                "The PW's signal state on protocol level."
            ::= { zxPwStatusEntry 28 }

zxPwStatusVccvLocalParas OBJECT-TYPE
            SYNTAX       Unsigned32
            MAX-ACCESS   read-only
            STATUS       current
            DESCRIPTION
                "The local VCCV value of the PW."
            ::= { zxPwStatusEntry 29 } 

zxPwStatusVccvRemoteParas OBJECT-TYPE
            SYNTAX       Unsigned32
            MAX-ACCESS   read-only
            STATUS       current
            DESCRIPTION
                "The remote VCCV value of the PW."
            ::= { zxPwStatusEntry 30 } 

zxPwStatusVccvNegoedParas OBJECT-TYPE
            SYNTAX       Unsigned32
            MAX-ACCESS   read-only
            STATUS       current
            DESCRIPTION
                "The negotiatied VCCV value of the PW."
            ::= { zxPwStatusEntry 31 }   

zxPwStatusPsnTunnelID OBJECT-TYPE
            SYNTAX       Unsigned32
            MAX-ACCESS   read-only
            STATUS       current
            DESCRIPTION
                "PSN tunnel ID."
            ::= { zxPwStatusEntry 32 }

zxPwStatusPsnOutInterface OBJECT-TYPE
            SYNTAX       DisplayString  (SIZE(0..31))
            MAX-ACCESS   read-only
            STATUS       current
            DESCRIPTION
                "The name of the PSN out interface."
            ::= { zxPwStatusEntry 33 }
END
