-- file automatically created


TELDAT-TRAP-TVRP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tvrpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TVRP event subsystem."
    REVISION "201401200930Z"
    DESCRIPTION "Initial implementation"
        ::= { telEventTraps 135 }


tvrpEventsGroup	OBJECT IDENTIFIER	::= { tvrpTrapsMIB 1 }

tvrpNotifications	OBJECT IDENTIFIER	::= { tvrpTrapsMIB 2 }
tvrpNotificationsPrefix	OBJECT IDENTIFIER	::= { tvrpNotifications 0 }

tvrpEventObjects1 OBJECT-IDENTITY
    STATUS current
    DESCRIPTION
        "Event TVRP.1
        TVRP group has become active."
    ::= { tvrpEventsGroup 1 }

tvrp1-group-number OBJECT-TYPE
    SYNTAX Integer32
    MAX-ACCESS accessible-for-notify
    STATUS current
    DESCRIPTION
        "Parameter 'group-number' in event TVRP.1"
    ::= { tvrpEventObjects1 1 }

tvrpEventObjects2 OBJECT-IDENTITY
    STATUS current
    DESCRIPTION
        "Event TVRP.2
        TVRP group deactivated."
    ::= { tvrpEventsGroup 2 }

tvrp2-group-number OBJECT-TYPE
    SYNTAX Integer32
    MAX-ACCESS accessible-for-notify
    STATUS current
    DESCRIPTION
        "Parameter 'group-number' in event TVRP.2"
    ::= { tvrpEventObjects2 1 }

tvrpEventObjects3 OBJECT-IDENTITY
    STATUS current
    DESCRIPTION
        "Event TVRP.3
        Active timer has expired."
    ::= { tvrpEventsGroup 3 }

tvrp3-group-number OBJECT-TYPE
    SYNTAX Integer32
    MAX-ACCESS accessible-for-notify
    STATUS current
    DESCRIPTION
        "Parameter 'group-number' in event TVRP.3"
    ::= { tvrpEventObjects3 1 }

tvrpEventObjects4 OBJECT-IDENTITY
    STATUS current
    DESCRIPTION
        "Event TVRP.4
        Standby timer has expired."
    ::= { tvrpEventsGroup 4 }

tvrp4-group-number OBJECT-TYPE
    SYNTAX Integer32
    MAX-ACCESS accessible-for-notify
    STATUS current
    DESCRIPTION
        "Parameter 'group-number' in event TVRP.4"
    ::= { tvrpEventObjects4 1 }

tvrpEventObjects5 OBJECT-IDENTITY
    STATUS current
    DESCRIPTION
        "Event TVRP.5
        Hello timer has expired."
    ::= { tvrpEventsGroup 5 }

tvrp5-group-number OBJECT-TYPE
    SYNTAX Integer32
    MAX-ACCESS accessible-for-notify
    STATUS current
    DESCRIPTION
        "Parameter 'group-number' in event TVRP.5"
    ::= { tvrpEventObjects5 1 }

tvrpEventObjects6 OBJECT-IDENTITY
    STATUS current
    DESCRIPTION
        "Event TVRP.6
        Receipt a Hello message of higher priority from a router in Speak state."
    ::= { tvrpEventsGroup 6 }

tvrp6-group-number OBJECT-TYPE
    SYNTAX Integer32
    MAX-ACCESS accessible-for-notify
    STATUS current
    DESCRIPTION
        "Parameter 'group-number' in event TVRP.6"
    ::= { tvrpEventObjects6 1 }

tvrpEventObjects7 OBJECT-IDENTITY
    STATUS current
    DESCRIPTION
        "Event TVRP.7
        Receipt a Hello message of higher priority from a router in Active state."
    ::= { tvrpEventsGroup 7 }

tvrp7-group-number OBJECT-TYPE
    SYNTAX Integer32
    MAX-ACCESS accessible-for-notify
    STATUS current
    DESCRIPTION
        "Parameter 'group-number' in event TVRP.7"
    ::= { tvrpEventObjects7 1 }

tvrpEventObjects8 OBJECT-IDENTITY
    STATUS current
    DESCRIPTION
        "Event TVRP.8
        Receipt a Hello message of lower priority from a router in Active state."
    ::= { tvrpEventsGroup 8 }

tvrp8-group-number OBJECT-TYPE
    SYNTAX Integer32
    MAX-ACCESS accessible-for-notify
    STATUS current
    DESCRIPTION
        "Parameter 'group-number' in event TVRP.8"
    ::= { tvrpEventObjects8 1 }

tvrpEventObjects9 OBJECT-IDENTITY
    STATUS current
    DESCRIPTION
        "Event TVRP.9
        Receipt a Resign message from the Active router."
    ::= { tvrpEventsGroup 9 }

tvrp9-group-number OBJECT-TYPE
    SYNTAX Integer32
    MAX-ACCESS accessible-for-notify
    STATUS current
    DESCRIPTION
        "Parameter 'group-number' in event TVRP.9"
    ::= { tvrpEventObjects9 1 }

tvrpEventObjects10 OBJECT-IDENTITY
    STATUS current
    DESCRIPTION
        "Event TVRP.10
        Receipt a Coup message from a higher priority router."
    ::= { tvrpEventsGroup 10 }

tvrp10-group-number OBJECT-TYPE
    SYNTAX Integer32
    MAX-ACCESS accessible-for-notify
    STATUS current
    DESCRIPTION
        "Parameter 'group-number' in event TVRP.10"
    ::= { tvrpEventObjects10 1 }

tvrpEventObjects11 OBJECT-IDENTITY
    STATUS current
    DESCRIPTION
        "Event TVRP.11
        Receipt a Hello message of higher priority from a router in Standby state."
    ::= { tvrpEventsGroup 11 }

tvrp11-group-number OBJECT-TYPE
    SYNTAX Integer32
    MAX-ACCESS accessible-for-notify
    STATUS current
    DESCRIPTION
        "Parameter 'group-number' in event TVRP.11"
    ::= { tvrpEventObjects11 1 }

tvrpEventObjects12 OBJECT-IDENTITY
    STATUS current
    DESCRIPTION
        "Event TVRP.12
        Receipt a Hello message of lower priority from a router in Standby state."
    ::= { tvrpEventsGroup 12 }

tvrp12-group-number OBJECT-TYPE
    SYNTAX Integer32
    MAX-ACCESS accessible-for-notify
    STATUS current
    DESCRIPTION
        "Parameter 'group-number' in event TVRP.12"
    ::= { tvrpEventObjects12 1 }

tvrpEventObjects13 OBJECT-IDENTITY
    STATUS current
    DESCRIPTION
        "Event TVRP.13
        Receipt a wrong TVRP packet."
    ::= { tvrpEventsGroup 13 }

tvrp13-discard-reason OBJECT-TYPE
    SYNTAX DisplayString
    MAX-ACCESS accessible-for-notify
    STATUS current
    DESCRIPTION
        "Parameter 'discard-reason' in event TVRP.13"
    ::= { tvrpEventObjects13 1 }

tvrpEventObjects14 OBJECT-IDENTITY
    STATUS current
    DESCRIPTION
        "Event TVRP.14
        Learnt TVRP parameters."
    ::= { tvrpEventsGroup 14 }

tvrp14-hello-time OBJECT-TYPE
    SYNTAX Integer32
    MAX-ACCESS accessible-for-notify
    STATUS current
    DESCRIPTION
        "Parameter 'hello-time' in event TVRP.14"
    ::= { tvrpEventObjects14 1 }

tvrp14-hold-time OBJECT-TYPE
    SYNTAX Integer32
    MAX-ACCESS accessible-for-notify
    STATUS current
    DESCRIPTION
        "Parameter 'hold-time' in event TVRP.14"
    ::= { tvrpEventObjects14 2 }

tvrp14-virtual-IP OBJECT-TYPE
    SYNTAX IpAddress
    MAX-ACCESS accessible-for-notify
    STATUS current
    DESCRIPTION
        "Parameter 'virtual-IP' in event TVRP.14"
    ::= { tvrpEventObjects14 3 }

tvrp14-group-number OBJECT-TYPE
    SYNTAX Integer32
    MAX-ACCESS accessible-for-notify
    STATUS current
    DESCRIPTION
        "Parameter 'group-number' in event TVRP.14"
    ::= { tvrpEventObjects14 4 }

tvrpEventObjects15 OBJECT-IDENTITY
    STATUS current
    DESCRIPTION
        "Event TVRP.15
        Changed TVRP state."
    ::= { tvrpEventsGroup 15 }

tvrp15-previous-state OBJECT-TYPE
    SYNTAX DisplayString
    MAX-ACCESS accessible-for-notify
    STATUS current
    DESCRIPTION
        "Parameter 'previous-state' in event TVRP.15"
    ::= { tvrpEventObjects15 1 }

tvrp15-new-state OBJECT-TYPE
    SYNTAX DisplayString
    MAX-ACCESS accessible-for-notify
    STATUS current
    DESCRIPTION
        "Parameter 'new-state' in event TVRP.15"
    ::= { tvrpEventObjects15 2 }

tvrp15-group-number OBJECT-TYPE
    SYNTAX Integer32
    MAX-ACCESS accessible-for-notify
    STATUS current
    DESCRIPTION
        "Parameter 'group-number' in event TVRP.15"
    ::= { tvrpEventObjects15 3 }

tvrpEventObjects16 OBJECT-IDENTITY
    STATUS current
    DESCRIPTION
        "Event TVRP.16
        Added mac address to TVRP mac address list."
    ::= { tvrpEventsGroup 16 }

tvrp16-virtual-mac OBJECT-TYPE
    SYNTAX DisplayString
    MAX-ACCESS accessible-for-notify
    STATUS current
    DESCRIPTION
        "Parameter 'virtual-mac' in event TVRP.16"
    ::= { tvrpEventObjects16 1 }

tvrpEventObjects17 OBJECT-IDENTITY
    STATUS current
    DESCRIPTION
        "Event TVRP.17
        Deleted mac address from TVRP mac address list."
    ::= { tvrpEventsGroup 17 }

tvrp17-virtual-mac OBJECT-TYPE
    SYNTAX DisplayString
    MAX-ACCESS accessible-for-notify
    STATUS current
    DESCRIPTION
        "Parameter 'virtual-mac' in event TVRP.17"
    ::= { tvrpEventObjects17 1 }

tvrpEventObjects18 OBJECT-IDENTITY
    STATUS current
    DESCRIPTION
        "Event TVRP.18
        Gratuitous ARP message sent."
    ::= { tvrpEventsGroup 18 }

tvrp18-virtual-IP OBJECT-TYPE
    SYNTAX IpAddress
    MAX-ACCESS accessible-for-notify
    STATUS current
    DESCRIPTION
        "Parameter 'virtual-IP' in event TVRP.18"
    ::= { tvrpEventObjects18 1 }

tvrp18-virtual-MAC OBJECT-TYPE
    SYNTAX DisplayString
    MAX-ACCESS accessible-for-notify
    STATUS current
    DESCRIPTION
        "Parameter 'virtual-MAC' in event TVRP.18"
    ::= { tvrpEventObjects18 2 }

tvrp18-group-number OBJECT-TYPE
    SYNTAX Integer32
    MAX-ACCESS accessible-for-notify
    STATUS current
    DESCRIPTION
        "Parameter 'group-number' in event TVRP.18"
    ::= { tvrpEventObjects18 3 }

tvrpEventObjects19 OBJECT-IDENTITY
    STATUS current
    DESCRIPTION
        "Event TVRP.19
        Sent of TVRP message."
    ::= { tvrpEventsGroup 19 }

tvrp19-message-type OBJECT-TYPE
    SYNTAX DisplayString
    MAX-ACCESS accessible-for-notify
    STATUS current
    DESCRIPTION
        "Parameter 'message-type' in event TVRP.19"
    ::= { tvrpEventObjects19 1 }

tvrp19-group-number OBJECT-TYPE
    SYNTAX Integer32
    MAX-ACCESS accessible-for-notify
    STATUS current
    DESCRIPTION
        "Parameter 'group-number' in event TVRP.19"
    ::= { tvrpEventObjects19 2 }

tvrpEventObjects20 OBJECT-IDENTITY
    STATUS current
    DESCRIPTION
        "Event TVRP.20
        Not found MAC address in list while trying to delete it."
    ::= { tvrpEventsGroup 20 }

tvrp20-virtual-MAC OBJECT-TYPE
    SYNTAX DisplayString
    MAX-ACCESS accessible-for-notify
    STATUS current
    DESCRIPTION
        "Parameter 'virtual-MAC' in event TVRP.20"
    ::= { tvrpEventObjects20 1 }

tvrpEventObjects21 OBJECT-IDENTITY
    STATUS current
    DESCRIPTION
        "Event TVRP.21
        Timer started to the specified value."
    ::= { tvrpEventsGroup 21 }

tvrp21-timer OBJECT-TYPE
    SYNTAX DisplayString
    MAX-ACCESS accessible-for-notify
    STATUS current
    DESCRIPTION
        "Parameter 'timer' in event TVRP.21"
    ::= { tvrpEventObjects21 1 }

tvrp21-value OBJECT-TYPE
    SYNTAX Integer32
    MAX-ACCESS accessible-for-notify
    STATUS current
    DESCRIPTION
        "Parameter 'value' in event TVRP.21"
    ::= { tvrpEventObjects21 2 }

tvrp21-group-number OBJECT-TYPE
    SYNTAX Integer32
    MAX-ACCESS accessible-for-notify
    STATUS current
    DESCRIPTION
        "Parameter 'group-number' in event TVRP.21"
    ::= { tvrpEventObjects21 3 }

tvrpEventObjects22 OBJECT-IDENTITY
    STATUS current
    DESCRIPTION
        "Event TVRP.22
        Timer stopped."
    ::= { tvrpEventsGroup 22 }

tvrp22-timer OBJECT-TYPE
    SYNTAX DisplayString
    MAX-ACCESS accessible-for-notify
    STATUS current
    DESCRIPTION
        "Parameter 'timer' in event TVRP.22"
    ::= { tvrpEventObjects22 1 }

tvrp22-group-number OBJECT-TYPE
    SYNTAX Integer32
    MAX-ACCESS accessible-for-notify
    STATUS current
    DESCRIPTION
        "Parameter 'group-number' in event TVRP.22"
    ::= { tvrpEventObjects22 2 }

tvrpEventObjects24 OBJECT-IDENTITY
    STATUS current
    DESCRIPTION
        "Event TVRP.24
        Unabled to find an inia for output messages."
    ::= { tvrpEventsGroup 24 }

tvrp24-group-number OBJECT-TYPE
    SYNTAX Integer32
    MAX-ACCESS accessible-for-notify
    STATUS current
    DESCRIPTION
        "Parameter 'group-number' in event TVRP.24"
    ::= { tvrpEventObjects24 1 }

tvrpEventObjects25 OBJECT-IDENTITY
    STATUS current
    DESCRIPTION
        "Event TVRP.25
        Unabled to register TVRP UDP port at startup."
    ::= { tvrpEventsGroup 25 }

tvrp25-port-number OBJECT-TYPE
    SYNTAX Integer32
    MAX-ACCESS accessible-for-notify
    STATUS current
    DESCRIPTION
        "Parameter 'port-number' in event TVRP.25"
    ::= { tvrpEventObjects25 1 }

tvrpEventObjects26 OBJECT-IDENTITY
    STATUS current
    DESCRIPTION
        "Event TVRP.26
        Tried to use TVRP in a no LAN interface."
    ::= { tvrpEventsGroup 26 }

tvrp26-interface-type OBJECT-TYPE
    SYNTAX Integer32
    MAX-ACCESS accessible-for-notify
    STATUS current
    DESCRIPTION
        "Parameter 'interface-type' in event TVRP.26"
    ::= { tvrpEventObjects26 1 }

tvrpEventObjects27 OBJECT-IDENTITY
    STATUS current
    DESCRIPTION
        "Event TVRP.27
        Show a generic message about MD5 authentication"
    ::= { tvrpEventsGroup 27 }

tvrp27-msg OBJECT-TYPE
    SYNTAX DisplayString
    MAX-ACCESS accessible-for-notify
    STATUS current
    DESCRIPTION
        "Parameter 'msg' in event TVRP.27"
    ::= { tvrpEventObjects27 1 }

tvrpEventObjects28 OBJECT-IDENTITY
    STATUS current
    DESCRIPTION
        "Event TVRP.28
        Rcvd TVRP MD5 packet using a key ID not configured."
    ::= { tvrpEventsGroup 28 }

tvrp28-group-number OBJECT-TYPE
    SYNTAX Integer32
    MAX-ACCESS accessible-for-notify
    STATUS current
    DESCRIPTION
        "Parameter 'group-number' in event TVRP.28"
    ::= { tvrpEventObjects28 1 }

tvrp28-key-id OBJECT-TYPE
    SYNTAX Integer32
    MAX-ACCESS accessible-for-notify
    STATUS current
    DESCRIPTION
        "Parameter 'key-id' in event TVRP.28"
    ::= { tvrpEventObjects28 2 }

tvrpEventObjects29 OBJECT-IDENTITY
    STATUS current
    DESCRIPTION
        "Event TVRP.29
        Bad authentication in TVRP MD5 message rcvd."
    ::= { tvrpEventsGroup 29 }

tvrp29-group-number OBJECT-TYPE
    SYNTAX Integer32
    MAX-ACCESS accessible-for-notify
    STATUS current
    DESCRIPTION
        "Parameter 'group-number' in event TVRP.29"
    ::= { tvrpEventObjects29 1 }

tvrp29-message-type OBJECT-TYPE
    SYNTAX DisplayString
    MAX-ACCESS accessible-for-notify
    STATUS current
    DESCRIPTION
        "Parameter 'message-type' in event TVRP.29"
    ::= { tvrpEventObjects29 2 }

tvrp29-source-IP OBJECT-TYPE
    SYNTAX IpAddress
    MAX-ACCESS accessible-for-notify
    STATUS current
    DESCRIPTION
        "Parameter 'source-IP' in event TVRP.29"
    ::= { tvrpEventObjects29 3 }


tvrpNotification1 NOTIFICATION-TYPE
    OBJECTS { 
              tvrp1-group-number 
            }
    STATUS current
    DESCRIPTION
        "Notification of Event TVRP.1

        Message: 'Enabled TVRP on group $1'

        Parameters list:
              $1: tvrp1-group-number

        TVRP group has become active."
    ::= { tvrpNotificationsPrefix 1 }

tvrpNotification2 NOTIFICATION-TYPE
    OBJECTS { 
              tvrp2-group-number 
            }
    STATUS current
    DESCRIPTION
        "Notification of Event TVRP.2

        Message: 'Disabled TVRP on group $1'

        Parameters list:
              $1: tvrp2-group-number

        TVRP group deactivated."
    ::= { tvrpNotificationsPrefix 2 }

tvrpNotification3 NOTIFICATION-TYPE
    OBJECTS { 
              tvrp3-group-number 
            }
    STATUS current
    DESCRIPTION
        "Notification of Event TVRP.3

        Message: 'Active timer expiry on group $1'

        Parameters list:
              $1: tvrp3-group-number

        Active timer has expired."
    ::= { tvrpNotificationsPrefix 3 }

tvrpNotification4 NOTIFICATION-TYPE
    OBJECTS { 
              tvrp4-group-number 
            }
    STATUS current
    DESCRIPTION
        "Notification of Event TVRP.4

        Message: 'Standby timer expiry on group $1'

        Parameters list:
              $1: tvrp4-group-number

        Standby timer has expired."
    ::= { tvrpNotificationsPrefix 4 }

tvrpNotification5 NOTIFICATION-TYPE
    OBJECTS { 
              tvrp5-group-number 
            }
    STATUS current
    DESCRIPTION
        "Notification of Event TVRP.5

        Message: 'Hello timer expiry on group $1'

        Parameters list:
              $1: tvrp5-group-number

        Hello timer has expired."
    ::= { tvrpNotificationsPrefix 5 }

tvrpNotification6 NOTIFICATION-TYPE
    OBJECTS { 
              tvrp6-group-number 
            }
    STATUS current
    DESCRIPTION
        "Notification of Event TVRP.6

        Message: 'Hello of Higher prio from Speak router on group $1'

        Parameters list:
              $1: tvrp6-group-number

        Receipt a Hello message of higher priority from a router in Speak state."
    ::= { tvrpNotificationsPrefix 6 }

tvrpNotification7 NOTIFICATION-TYPE
    OBJECTS { 
              tvrp7-group-number 
            }
    STATUS current
    DESCRIPTION
        "Notification of Event TVRP.7

        Message: 'Hello of Higher prio from Active router on group $1'

        Parameters list:
              $1: tvrp7-group-number

        Receipt a Hello message of higher priority from a router in Active state."
    ::= { tvrpNotificationsPrefix 7 }

tvrpNotification8 NOTIFICATION-TYPE
    OBJECTS { 
              tvrp8-group-number 
            }
    STATUS current
    DESCRIPTION
        "Notification of Event TVRP.8

        Message: 'Hello of Lower prio from Active router on group $1'

        Parameters list:
              $1: tvrp8-group-number

        Receipt a Hello message of lower priority from a router in Active state."
    ::= { tvrpNotificationsPrefix 8 }

tvrpNotification9 NOTIFICATION-TYPE
    OBJECTS { 
              tvrp9-group-number 
            }
    STATUS current
    DESCRIPTION
        "Notification of Event TVRP.9

        Message: 'Resign message received on group $1'

        Parameters list:
              $1: tvrp9-group-number

        Receipt a Resign message from the Active router."
    ::= { tvrpNotificationsPrefix 9 }

tvrpNotification10 NOTIFICATION-TYPE
    OBJECTS { 
              tvrp10-group-number 
            }
    STATUS current
    DESCRIPTION
        "Notification of Event TVRP.10

        Message: 'Coup of Higher prio on group $1'

        Parameters list:
              $1: tvrp10-group-number

        Receipt a Coup message from a higher priority router."
    ::= { tvrpNotificationsPrefix 10 }

tvrpNotification11 NOTIFICATION-TYPE
    OBJECTS { 
              tvrp11-group-number 
            }
    STATUS current
    DESCRIPTION
        "Notification of Event TVRP.11

        Message: 'Hello of Higher prio from Standby router on group $1'

        Parameters list:
              $1: tvrp11-group-number

        Receipt a Hello message of higher priority from a router in Standby state."
    ::= { tvrpNotificationsPrefix 11 }

tvrpNotification12 NOTIFICATION-TYPE
    OBJECTS { 
              tvrp12-group-number 
            }
    STATUS current
    DESCRIPTION
        "Notification of Event TVRP.12

        Message: 'Hello of Lower prio from Standby router on group $1'

        Parameters list:
              $1: tvrp12-group-number

        Receipt a Hello message of lower priority from a router in Standby state."
    ::= { tvrpNotificationsPrefix 12 }

tvrpNotification13 NOTIFICATION-TYPE
    OBJECTS { 
              tvrp13-discard-reason 
            }
    STATUS current
    DESCRIPTION
        "Notification of Event TVRP.13

        Message: 'Discarded TVRP packet due to: $1'

        Parameters list:
              $1: tvrp13-discard-reason

        Receipt a wrong TVRP packet."
    ::= { tvrpNotificationsPrefix 13 }

tvrpNotification14 NOTIFICATION-TYPE
    OBJECTS { 
              tvrp14-hello-time, 
              tvrp14-hold-time,
              tvrp14-virtual-IP,
              tvrp14-group-number 
            }
    STATUS current
    DESCRIPTION
        "Notification of Event TVRP.14

        Message: 'learnt hello $1, hold $2, virtual IP $3 on group $4'

        Parameters list:
              $1: tvrp14-hello-time
              $2: tvrp14-hold-time
              $3: tvrp14-virtual-IP
              $4: tvrp14-group-number

        Learnt TVRP parameters."
    ::= { tvrpNotificationsPrefix 14 }

tvrpNotification15 NOTIFICATION-TYPE
    OBJECTS { 
              tvrp15-previous-state, 
              tvrp15-new-state,
              tvrp15-group-number 
            }
    STATUS current
    DESCRIPTION
        "Notification of Event TVRP.15

        Message: 'Changed state from $1 to $2 on group $3'

        Parameters list:
              $1: tvrp15-previous-state
              $2: tvrp15-new-state
              $3: tvrp15-group-number

        Changed TVRP state."
    ::= { tvrpNotificationsPrefix 15 }

tvrpNotification16 NOTIFICATION-TYPE
    OBJECTS { 
              tvrp16-virtual-mac 
            }
    STATUS current
    DESCRIPTION
        "Notification of Event TVRP.16

        Message: 'Added mac $1 to TVRP mac list'

        Parameters list:
              $1: tvrp16-virtual-mac

        Added mac address to TVRP mac address list."
    ::= { tvrpNotificationsPrefix 16 }

tvrpNotification17 NOTIFICATION-TYPE
    OBJECTS { 
              tvrp17-virtual-mac 
            }
    STATUS current
    DESCRIPTION
        "Notification of Event TVRP.17

        Message: 'Deleted mac $1 from TVRP mac list'

        Parameters list:
              $1: tvrp17-virtual-mac

        Deleted mac address from TVRP mac address list."
    ::= { tvrpNotificationsPrefix 17 }

tvrpNotification18 NOTIFICATION-TYPE
    OBJECTS { 
              tvrp18-virtual-IP, 
              tvrp18-virtual-MAC,
              tvrp18-group-number 
            }
    STATUS current
    DESCRIPTION
        "Notification of Event TVRP.18

        Message: 'Gratuitous ARP sent, IP: $1 MAC: $2, on group $3'

        Parameters list:
              $1: tvrp18-virtual-IP
              $2: tvrp18-virtual-MAC
              $3: tvrp18-group-number

        Gratuitous ARP message sent."
    ::= { tvrpNotificationsPrefix 18 }

tvrpNotification19 NOTIFICATION-TYPE
    OBJECTS { 
              tvrp19-message-type, 
              tvrp19-group-number 
            }
    STATUS current
    DESCRIPTION
        "Notification of Event TVRP.19

        Message: 'Sent $1 message on group $2'

        Parameters list:
              $1: tvrp19-message-type
              $2: tvrp19-group-number

        Sent of TVRP message."
    ::= { tvrpNotificationsPrefix 19 }

tvrpNotification20 NOTIFICATION-TYPE
    OBJECTS { 
              tvrp20-virtual-MAC 
            }
    STATUS current
    DESCRIPTION
        "Notification of Event TVRP.20

        Message: 'Not found MAC: $1'

        Parameters list:
              $1: tvrp20-virtual-MAC

        Not found MAC address in list while trying to delete it."
    ::= { tvrpNotificationsPrefix 20 }

tvrpNotification21 NOTIFICATION-TYPE
    OBJECTS { 
              tvrp21-timer, 
              tvrp21-value,
              tvrp21-group-number 
            }
    STATUS current
    DESCRIPTION
        "Notification of Event TVRP.21

        Message: 'Start $1 timer:$2 on group $3'

        Parameters list:
              $1: tvrp21-timer
              $2: tvrp21-value
              $3: tvrp21-group-number

        Timer started to the specified value."
    ::= { tvrpNotificationsPrefix 21 }

tvrpNotification22 NOTIFICATION-TYPE
    OBJECTS { 
              tvrp22-timer, 
              tvrp22-group-number 
            }
    STATUS current
    DESCRIPTION
        "Notification of Event TVRP.22

        Message: 'Stop $1 timer on group $2'

        Parameters list:
              $1: tvrp22-timer
              $2: tvrp22-group-number

        Timer stopped."
    ::= { tvrpNotificationsPrefix 22 }

tvrpNotification23 NOTIFICATION-TYPE
    STATUS current
    DESCRIPTION
        "Notification of Event TVRP.23

        Message: 'Can't set or quit vMAC'

        Unabled to set-quit promiscuous mode on Ethernet or functional address
        on Token Ring interface."
    ::= { tvrpNotificationsPrefix 23 }

tvrpNotification24 NOTIFICATION-TYPE
    OBJECTS { 
              tvrp24-group-number 
            }
    STATUS current
    DESCRIPTION
        "Notification of Event TVRP.24

        Message: 'Not found inia for output on group $1'

        Parameters list:
              $1: tvrp24-group-number

        Unabled to find an inia for output messages."
    ::= { tvrpNotificationsPrefix 24 }

tvrpNotification25 NOTIFICATION-TYPE
    OBJECTS { 
              tvrp25-port-number 
            }
    STATUS current
    DESCRIPTION
        "Notification of Event TVRP.25

        Message: 'UDP port $1 not registered'

        Parameters list:
              $1: tvrp25-port-number

        Unabled to register TVRP UDP port at startup."
    ::= { tvrpNotificationsPrefix 25 }

tvrpNotification26 NOTIFICATION-TYPE
    OBJECTS { 
              tvrp26-interface-type 
            }
    STATUS current
    DESCRIPTION
        "Notification of Event TVRP.26

        Message: 'NO LAN interface: $1'

        Parameters list:
              $1: tvrp26-interface-type

        Tried to use TVRP in a no LAN interface."
    ::= { tvrpNotificationsPrefix 26 }

tvrpNotification27 NOTIFICATION-TYPE
    OBJECTS { 
              tvrp27-msg 
            }
    STATUS current
    DESCRIPTION
        "Notification of Event TVRP.27

        Message: 'MD5 authentication: $1'

        Parameters list:
              $1: tvrp27-msg

        Show a generic message about MD5 authentication"
    ::= { tvrpNotificationsPrefix 27 }

tvrpNotification28 NOTIFICATION-TYPE
    OBJECTS { 
              tvrp28-group-number, 
              tvrp28-key-id 
            }
    STATUS current
    DESCRIPTION
        "Notification of Event TVRP.28

        Message: 'Authentication failed in group $1, NO KEY configured with ID $2'

        Parameters list:
              $1: tvrp28-group-number
              $2: tvrp28-key-id

        Rcvd TVRP MD5 packet using a key ID not configured."
    ::= { tvrpNotificationsPrefix 28 }

tvrpNotification29 NOTIFICATION-TYPE
    OBJECTS { 
              tvrp29-group-number, 
              tvrp29-message-type,
              tvrp29-source-IP 
            }
    STATUS current
    DESCRIPTION
        "Notification of Event TVRP.29

        Message: 'Authentication failed in group $1 for $2 message from $3, MD5 auth failed'

        Parameters list:
              $1: tvrp29-group-number
              $2: tvrp29-message-type
              $3: tvrp29-source-IP

        Bad authentication in TVRP MD5 message rcvd."
    ::= { tvrpNotificationsPrefix 29 }


END
