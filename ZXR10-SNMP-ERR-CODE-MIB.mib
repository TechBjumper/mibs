-- *****************************************************************
-- ZXR10-SNMP-ERR-CODE-MIB.mib
--
-- ZTE Corporation Enterprise Structure of Management Information
--
-- Copyright (c) 2009 by ZTE Corporation
-- All rights reserved.
-- *****************************************************************
--
ZXR10-SNMP-ERR-CODE-MIB DEFINITIONS ::= BEGIN

    IMPORTS
        RowStatus, DisplayString            FROM SNMPv2-TC
        MODULE-IDENTITY, OBJECT-IDENTITY,
        OBJECT-TYPE, enterprises,
        Integer32                           FROM SNMPv2-SMI;

    zxr10SnmpGlobalObjects MODULE-IDENTITY
        LAST-UPDATED "201709201500Z"
        ORGANIZATION "ZTE Corporation"
        CONTACT-INFO "Wu Jian  ZTE Corporation 
                      Mail: wu.jian1@zte.com.cn
                      Tel : +86-021-68897223"
        DESCRIPTION  
            "The MIB module to describe the information for SNMP error code."
        REVISION     "201709201500Z"
        DESCRIPTION  
            "Initial version of this MIB module."
        ::= {zxr10RosngMIB 101} 

    zte                     OBJECT IDENTIFIER ::= { enterprises 3902 }
    zxr10                   OBJECT IDENTIFIER ::= { zte 3}
    zxr10RosngMIB           OBJECT IDENTIFIER ::= { zxr10 6000}

    zxr10SnmpSetCmdErrCode  OBJECT-TYPE
        SYNTAX      Integer32
        MAX-ACCESS  read-only
        STATUS      current
        DESCRIPTION 
            "Error code for SNMP set command. When agent executes an SNMP set,
             this variable should be maintained. Value 0 means no error."
        DEFVAL { 0 }
        ::={ zxr10SnmpGlobalObjects 1}   

END
