-- file automatically created


TELDAT-TRAP-IPSE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ipseTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPSE event subsystem."
    REVISION "201401200930Z"
    DESCRIPTION "Initial implementation"
        ::= { telEventTraps 138 }


ipseEventsGroup	OBJECT IDENTIFIER	::= { ipseTrapsMIB 1 }

ipseNotifications	OBJECT IDENTIFIER	::= { ipseTrapsMIB 2 }
ipseNotificationsPrefix	OBJECT IDENTIFIER	::= { ipseNotifications 0 }

ipseEventObjects1 OBJECT-IDENTITY
    STATUS current
    DESCRIPTION
        "Event IPSE.1
        It is shown the protocol of the encapsulated packet and the SPI."
    ::= { ipseEventsGroup 1 }

ipse1-packet-type OBJECT-TYPE
    SYNTAX DisplayString
    MAX-ACCESS accessible-for-notify
    STATUS current
    DESCRIPTION
        "Parameter 'packet-type' in event IPSE.1"
    ::= { ipseEventObjects1 1 }

ipse1-SPI OBJECT-TYPE
    SYNTAX Integer32
    MAX-ACCESS accessible-for-notify
    STATUS current
    DESCRIPTION
        "Parameter 'SPI' in event IPSE.1"
    ::= { ipseEventObjects1 2 }

ipseEventObjects2 OBJECT-IDENTITY
    STATUS current
    DESCRIPTION
        "Event IPSE.2
        The received encapsulated packet has an unknown protocol."
    ::= { ipseEventsGroup 2 }

ipse2-protocol-type OBJECT-TYPE
    SYNTAX DisplayString
    MAX-ACCESS accessible-for-notify
    STATUS current
    DESCRIPTION
        "Parameter 'protocol-type' in event IPSE.2"
    ::= { ipseEventObjects2 1 }

ipseEventObjects3 OBJECT-IDENTITY
    STATUS current
    DESCRIPTION
        "Event IPSE.3
        The output function of the tunnel net has encapsulated a ESP or
        AH packet successfully. It is shown the protocol of the encapsulated
        packet, the source and destination direction and the SPI."
    ::= { ipseEventsGroup 3 }

ipse3-protocol-type OBJECT-TYPE
    SYNTAX DisplayString
    MAX-ACCESS accessible-for-notify
    STATUS current
    DESCRIPTION
        "Parameter 'protocol-type' in event IPSE.3"
    ::= { ipseEventObjects3 1 }

ipse3-src-ip-addr OBJECT-TYPE
    SYNTAX IpAddress
    MAX-ACCESS accessible-for-notify
    STATUS current
    DESCRIPTION
        "Parameter 'src-ip-addr' in event IPSE.3"
    ::= { ipseEventObjects3 2 }

ipse3-dest-ip-addr OBJECT-TYPE
    SYNTAX IpAddress
    MAX-ACCESS accessible-for-notify
    STATUS current
    DESCRIPTION
        "Parameter 'dest-ip-addr' in event IPSE.3"
    ::= { ipseEventObjects3 3 }

ipse3-SPI OBJECT-TYPE
    SYNTAX Integer32
    MAX-ACCESS accessible-for-notify
    STATUS current
    DESCRIPTION
        "Parameter 'SPI' in event IPSE.3"
    ::= { ipseEventObjects3 4 }

ipseEventObjects4 OBJECT-IDENTITY
    STATUS current
    DESCRIPTION
        "Event IPSE.4
        The authentication of an ESP or AH packet failed."
    ::= { ipseEventsGroup 4 }

ipse4-protocol-type OBJECT-TYPE
    SYNTAX DisplayString
    MAX-ACCESS accessible-for-notify
    STATUS current
    DESCRIPTION
        "Parameter 'protocol-type' in event IPSE.4"
    ::= { ipseEventObjects4 1 }

ipse4-sa-number OBJECT-TYPE
    SYNTAX Integer32
    MAX-ACCESS accessible-for-notify
    STATUS current
    DESCRIPTION
        "Parameter 'sa-number' in event IPSE.4"
    ::= { ipseEventObjects4 2 }

ipseEventObjects5 OBJECT-IDENTITY
    STATUS current
    DESCRIPTION
        "Event IPSE.5
        A packet was discarded because its secuence number was below
        the minimum admited in the reception window."
    ::= { ipseEventsGroup 5 }

ipse5-protocol-name OBJECT-TYPE
    SYNTAX DisplayString
    MAX-ACCESS accessible-for-notify
    STATUS current
    DESCRIPTION
        "Parameter 'protocol-name' in event IPSE.5"
    ::= { ipseEventObjects5 1 }

ipse5-src-ip-addr OBJECT-TYPE
    SYNTAX IpAddress
    MAX-ACCESS accessible-for-notify
    STATUS current
    DESCRIPTION
        "Parameter 'src-ip-addr' in event IPSE.5"
    ::= { ipseEventObjects5 2 }

ipse5-dest-ip-addr OBJECT-TYPE
    SYNTAX IpAddress
    MAX-ACCESS accessible-for-notify
    STATUS current
    DESCRIPTION
        "Parameter 'dest-ip-addr' in event IPSE.5"
    ::= { ipseEventObjects5 3 }

ipseEventObjects6 OBJECT-IDENTITY
    STATUS current
    DESCRIPTION
        "Event IPSE.6
        A packet was discarded because the antireplay options were active
        and it was already received."
    ::= { ipseEventsGroup 6 }

ipse6-protocol-name OBJECT-TYPE
    SYNTAX DisplayString
    MAX-ACCESS accessible-for-notify
    STATUS current
    DESCRIPTION
        "Parameter 'protocol-name' in event IPSE.6"
    ::= { ipseEventObjects6 1 }

ipse6-src-ip-addr OBJECT-TYPE
    SYNTAX IpAddress
    MAX-ACCESS accessible-for-notify
    STATUS current
    DESCRIPTION
        "Parameter 'src-ip-addr' in event IPSE.6"
    ::= { ipseEventObjects6 2 }

ipse6-dest-ip-addr OBJECT-TYPE
    SYNTAX IpAddress
    MAX-ACCESS accessible-for-notify
    STATUS current
    DESCRIPTION
        "Parameter 'dest-ip-addr' in event IPSE.6"
    ::= { ipseEventObjects6 3 }

ipseEventObjects8 OBJECT-IDENTITY
    STATUS current
    DESCRIPTION
        "Event IPSE.8
        A packet is discarded because it has a wrong length (it is not multiple
        of 32 bits)."
    ::= { ipseEventsGroup 8 }

ipse8-protocol-type OBJECT-TYPE
    SYNTAX DisplayString
    MAX-ACCESS accessible-for-notify
    STATUS current
    DESCRIPTION
        "Parameter 'protocol-type' in event IPSE.8"
    ::= { ipseEventObjects8 1 }

ipse8-src-ip-addr OBJECT-TYPE
    SYNTAX IpAddress
    MAX-ACCESS accessible-for-notify
    STATUS current
    DESCRIPTION
        "Parameter 'src-ip-addr' in event IPSE.8"
    ::= { ipseEventObjects8 2 }

ipse8-dest-ip-addr OBJECT-TYPE
    SYNTAX IpAddress
    MAX-ACCESS accessible-for-notify
    STATUS current
    DESCRIPTION
        "Parameter 'dest-ip-addr' in event IPSE.8"
    ::= { ipseEventObjects8 3 }

ipseEventObjects9 OBJECT-IDENTITY
    STATUS current
    DESCRIPTION
        "Event IPSE.9
        Packet with correct sequence number in window."
    ::= { ipseEventsGroup 9 }

ipse9-protocol-type OBJECT-TYPE
    SYNTAX DisplayString
    MAX-ACCESS accessible-for-notify
    STATUS current
    DESCRIPTION
        "Parameter 'protocol-type' in event IPSE.9"
    ::= { ipseEventObjects9 1 }

ipse9-src-ip-addr OBJECT-TYPE
    SYNTAX IpAddress
    MAX-ACCESS accessible-for-notify
    STATUS current
    DESCRIPTION
        "Parameter 'src-ip-addr' in event IPSE.9"
    ::= { ipseEventObjects9 2 }

ipse9-dest-ip-addr OBJECT-TYPE
    SYNTAX IpAddress
    MAX-ACCESS accessible-for-notify
    STATUS current
    DESCRIPTION
        "Parameter 'dest-ip-addr' in event IPSE.9"
    ::= { ipseEventObjects9 3 }

ipseEventObjects10 OBJECT-IDENTITY
    STATUS current
    DESCRIPTION
        "Event IPSE.10
        The packet has arrived to window secuence with 0 as secuence number."
    ::= { ipseEventsGroup 10 }

ipse10-protocol-type OBJECT-TYPE
    SYNTAX DisplayString
    MAX-ACCESS accessible-for-notify
    STATUS current
    DESCRIPTION
        "Parameter 'protocol-type' in event IPSE.10"
    ::= { ipseEventObjects10 1 }

ipse10-src-ip-addr OBJECT-TYPE
    SYNTAX IpAddress
    MAX-ACCESS accessible-for-notify
    STATUS current
    DESCRIPTION
        "Parameter 'src-ip-addr' in event IPSE.10"
    ::= { ipseEventObjects10 2 }

ipse10-dest-ip-addr OBJECT-TYPE
    SYNTAX IpAddress
    MAX-ACCESS accessible-for-notify
    STATUS current
    DESCRIPTION
        "Parameter 'dest-ip-addr' in event IPSE.10"
    ::= { ipseEventObjects10 3 }

ipseEventObjects11 OBJECT-IDENTITY
    STATUS current
    DESCRIPTION
        "Event IPSE.11
        The protocol, the SA sequence number and the packet sequence number
        are shown."
    ::= { ipseEventsGroup 11 }

ipse11-protocol-type OBJECT-TYPE
    SYNTAX DisplayString
    MAX-ACCESS accessible-for-notify
    STATUS current
    DESCRIPTION
        "Parameter 'protocol-type' in event IPSE.11"
    ::= { ipseEventObjects11 1 }

ipse11-spi OBJECT-TYPE
    SYNTAX Integer32
    MAX-ACCESS accessible-for-notify
    STATUS current
    DESCRIPTION
        "Parameter 'spi' in event IPSE.11"
    ::= { ipseEventObjects11 2 }

ipse11-sa-seq-num OBJECT-TYPE
    SYNTAX Integer32
    MAX-ACCESS accessible-for-notify
    STATUS current
    DESCRIPTION
        "Parameter 'sa-seq-num' in event IPSE.11"
    ::= { ipseEventObjects11 3 }

ipse11-inbound-seq-num OBJECT-TYPE
    SYNTAX Integer32
    MAX-ACCESS accessible-for-notify
    STATUS current
    DESCRIPTION
        "Parameter 'inbound-seq-num' in event IPSE.11"
    ::= { ipseEventObjects11 4 }

ipseEventObjects12 OBJECT-IDENTITY
    STATUS current
    DESCRIPTION
        "Event IPSE.12
        A packet has arrived with the SPI showed and there is not an
        static SA configured for it."
    ::= { ipseEventsGroup 12 }

ipse12-spi OBJECT-TYPE
    SYNTAX Integer32
    MAX-ACCESS accessible-for-notify
    STATUS current
    DESCRIPTION
        "Parameter 'spi' in event IPSE.12"
    ::= { ipseEventObjects12 1 }

ipse12-protocol OBJECT-TYPE
    SYNTAX Integer32
    MAX-ACCESS accessible-for-notify
    STATUS current
    DESCRIPTION
        "Parameter 'protocol' in event IPSE.12"
    ::= { ipseEventObjects12 2 }

ipse12-remote-peer OBJECT-TYPE
    SYNTAX IpAddress
    MAX-ACCESS accessible-for-notify
    STATUS current
    DESCRIPTION
        "Parameter 'remote-peer' in event IPSE.12"
    ::= { ipseEventObjects12 3 }

ipseEventObjects13 OBJECT-IDENTITY
    STATUS current
    DESCRIPTION
        "Event IPSE.13
        Overflow in sequence number the next sequence number is 1."
    ::= { ipseEventsGroup 13 }

ipse13-protocol-type OBJECT-TYPE
    SYNTAX DisplayString
    MAX-ACCESS accessible-for-notify
    STATUS current
    DESCRIPTION
        "Parameter 'protocol-type' in event IPSE.13"
    ::= { ipseEventObjects13 1 }

ipseEventObjects14 OBJECT-IDENTITY
    STATUS current
    DESCRIPTION
        "Event IPSE.14
        A packet has arrived with SPI %x and there is not an
        static SA configured for it."
    ::= { ipseEventsGroup 14 }

ipse14-spi OBJECT-TYPE
    SYNTAX Integer32
    MAX-ACCESS accessible-for-notify
    STATUS current
    DESCRIPTION
        "Parameter 'spi' in event IPSE.14"
    ::= { ipseEventObjects14 1 }

ipse14-protocol OBJECT-TYPE
    SYNTAX Integer32
    MAX-ACCESS accessible-for-notify
    STATUS current
    DESCRIPTION
        "Parameter 'protocol' in event IPSE.14"
    ::= { ipseEventObjects14 2 }

ipse14-remote-peer OBJECT-TYPE
    SYNTAX IpAddress
    MAX-ACCESS accessible-for-notify
    STATUS current
    DESCRIPTION
        "Parameter 'remote-peer' in event IPSE.14"
    ::= { ipseEventObjects14 3 }

ipseEventObjects15 OBJECT-IDENTITY
    STATUS current
    DESCRIPTION
        "Event IPSE.15
        Found entry hasn't policy assigned. (Debug)."
    ::= { ipseEventsGroup 15 }

ipse15-src-ip-addr OBJECT-TYPE
    SYNTAX IpAddress
    MAX-ACCESS accessible-for-notify
    STATUS current
    DESCRIPTION
        "Parameter 'src-ip-addr' in event IPSE.15"
    ::= { ipseEventObjects15 1 }

ipse15-dest-ip-addr OBJECT-TYPE
    SYNTAX IpAddress
    MAX-ACCESS accessible-for-notify
    STATUS current
    DESCRIPTION
        "Parameter 'dest-ip-addr' in event IPSE.15"
    ::= { ipseEventObjects15 2 }

ipseEventObjects16 OBJECT-IDENTITY
    STATUS current
    DESCRIPTION
        "Event IPSE.16
        Attributes are wrong."
    ::= { ipseEventsGroup 16 }

ipse16-message OBJECT-TYPE
    SYNTAX Integer32
    MAX-ACCESS accessible-for-notify
    STATUS current
    DESCRIPTION
        "Parameter 'message' in event IPSE.16"
    ::= { ipseEventObjects16 1 }

ipse16-phase OBJECT-TYPE
    SYNTAX Integer32
    MAX-ACCESS accessible-for-notify
    STATUS current
    DESCRIPTION
        "Parameter 'phase' in event IPSE.16"
    ::= { ipseEventObjects16 2 }

ipse16-src-ip-addr OBJECT-TYPE
    SYNTAX IpAddress
    MAX-ACCESS accessible-for-notify
    STATUS current
    DESCRIPTION
        "Parameter 'src-ip-addr' in event IPSE.16"
    ::= { ipseEventObjects16 3 }

ipse16-dest-ip-addr OBJECT-TYPE
    SYNTAX IpAddress
    MAX-ACCESS accessible-for-notify
    STATUS current
    DESCRIPTION
        "Parameter 'dest-ip-addr' in event IPSE.16"
    ::= { ipseEventObjects16 4 }

ipseEventObjects17 OBJECT-IDENTITY
    STATUS current
    DESCRIPTION
        "Event IPSE.17
        Error allocating memory."
    ::= { ipseEventsGroup 17 }

ipse17-message OBJECT-TYPE
    SYNTAX DisplayString
    MAX-ACCESS accessible-for-notify
    STATUS current
    DESCRIPTION
        "Parameter 'message' in event IPSE.17"
    ::= { ipseEventObjects17 1 }

ipseEventObjects18 OBJECT-IDENTITY
    STATUS current
    DESCRIPTION
        "Event IPSE.18
        Incompatible IKE policies."
    ::= { ipseEventsGroup 18 }

ipse18-src-ip-addr OBJECT-TYPE
    SYNTAX IpAddress
    MAX-ACCESS accessible-for-notify
    STATUS current
    DESCRIPTION
        "Parameter 'src-ip-addr' in event IPSE.18"
    ::= { ipseEventObjects18 1 }

ipse18-dest-ip-addr OBJECT-TYPE
    SYNTAX IpAddress
    MAX-ACCESS accessible-for-notify
    STATUS current
    DESCRIPTION
        "Parameter 'dest-ip-addr' in event IPSE.18"
    ::= { ipseEventObjects18 2 }

ipseEventObjects19 OBJECT-IDENTITY
    STATUS current
    DESCRIPTION
        "Event IPSE.19
        Error building the message."
    ::= { ipseEventsGroup 19 }

ipse19-mes-number OBJECT-TYPE
    SYNTAX Integer32
    MAX-ACCESS accessible-for-notify
    STATUS current
    DESCRIPTION
        "Parameter 'mes-number' in event IPSE.19"
    ::= { ipseEventObjects19 1 }

ipse19-phase-number OBJECT-TYPE
    SYNTAX Integer32
    MAX-ACCESS accessible-for-notify
    STATUS current
    DESCRIPTION
        "Parameter 'phase-number' in event IPSE.19"
    ::= { ipseEventObjects19 2 }

ipse19-remote-peer-addr OBJECT-TYPE
    SYNTAX IpAddress
    MAX-ACCESS accessible-for-notify
    STATUS current
    DESCRIPTION
        "Parameter 'remote-peer-addr' in event IPSE.19"
    ::= { ipseEventObjects19 3 }

ipse19-local-ifc-addr OBJECT-TYPE
    SYNTAX IpAddress
    MAX-ACCESS accessible-for-notify
    STATUS current
    DESCRIPTION
        "Parameter 'local-ifc-addr' in event IPSE.19"
    ::= { ipseEventObjects19 4 }

ipseEventObjects20 OBJECT-IDENTITY
    STATUS current
    DESCRIPTION
        "Event IPSE.20
        Error inicializating IKE protocol."
    ::= { ipseEventsGroup 20 }

ipse20-message OBJECT-TYPE
    SYNTAX DisplayString
    MAX-ACCESS accessible-for-notify
    STATUS current
    DESCRIPTION
        "Parameter 'message' in event IPSE.20"
    ::= { ipseEventObjects20 1 }

ipseEventObjects21 OBJECT-IDENTITY
    STATUS current
    DESCRIPTION
        "Event IPSE.21
        IKE is active."
    ::= { ipseEventsGroup 21 }

ipse21-ike-port OBJECT-TYPE
    SYNTAX Integer32
    MAX-ACCESS accessible-for-notify
    STATUS current
    DESCRIPTION
        "Parameter 'ike-port' in event IPSE.21"
    ::= { ipseEventObjects21 1 }

ipseEventObjects22 OBJECT-IDENTITY
    STATUS current
    DESCRIPTION
        "Event IPSE.22
        A packet is received."
    ::= { ipseEventsGroup 22 }

ipse22-remote-addr OBJECT-TYPE
    SYNTAX IpAddress
    MAX-ACCESS accessible-for-notify
    STATUS current
    DESCRIPTION
        "Parameter 'remote-addr' in event IPSE.22"
    ::= { ipseEventObjects22 1 }

ipse22-message OBJECT-TYPE
    SYNTAX DisplayString
    MAX-ACCESS accessible-for-notify
    STATUS current
    DESCRIPTION
        "Parameter 'message' in event IPSE.22"
    ::= { ipseEventObjects22 2 }

ipseEventObjects23 OBJECT-IDENTITY
    STATUS current
    DESCRIPTION
        "Event IPSE.23
        An ISAKMP SA has been created."
    ::= { ipseEventsGroup 23 }

ipse23-local-addr OBJECT-TYPE
    SYNTAX IpAddress
    MAX-ACCESS accessible-for-notify
    STATUS current
    DESCRIPTION
        "Parameter 'local-addr' in event IPSE.23"
    ::= { ipseEventObjects23 1 }

ipse23-remote-addr OBJECT-TYPE
    SYNTAX IpAddress
    MAX-ACCESS accessible-for-notify
    STATUS current
    DESCRIPTION
        "Parameter 'remote-addr' in event IPSE.23"
    ::= { ipseEventObjects23 2 }

ipseEventObjects24 OBJECT-IDENTITY
    STATUS current
    DESCRIPTION
        "Event IPSE.24
        Error (free format)."
    ::= { ipseEventsGroup 24 }

ipse24-error OBJECT-TYPE
    SYNTAX DisplayString
    MAX-ACCESS accessible-for-notify
    STATUS current
    DESCRIPTION
        "Parameter 'error' in event IPSE.24"
    ::= { ipseEventObjects24 1 }

ipseEventObjects25 OBJECT-IDENTITY
    STATUS current
    DESCRIPTION
        "Event IPSE.25
        Leaving state in IPSec forwarder."
    ::= { ipseEventsGroup 25 }

ipse25-src-ip-addr OBJECT-TYPE
    SYNTAX IpAddress
    MAX-ACCESS accessible-for-notify
    STATUS current
    DESCRIPTION
        "Parameter 'src-ip-addr' in event IPSE.25"
    ::= { ipseEventObjects25 1 }

ipse25-dest-ip-addr OBJECT-TYPE
    SYNTAX IpAddress
    MAX-ACCESS accessible-for-notify
    STATUS current
    DESCRIPTION
        "Parameter 'dest-ip-addr' in event IPSE.25"
    ::= { ipseEventObjects25 2 }

ipse25-state OBJECT-TYPE
    SYNTAX DisplayString
    MAX-ACCESS accessible-for-notify
    STATUS current
    DESCRIPTION
        "Parameter 'state' in event IPSE.25"
    ::= { ipseEventObjects25 3 }

ipseEventObjects26 OBJECT-IDENTITY
    STATUS current
    DESCRIPTION
        "Event IPSE.26
        Checking output control access list in IPSec forwarder."
    ::= { ipseEventsGroup 26 }

ipse26-src-ip-addr OBJECT-TYPE
    SYNTAX IpAddress
    MAX-ACCESS accessible-for-notify
    STATUS current
    DESCRIPTION
        "Parameter 'src-ip-addr' in event IPSE.26"
    ::= { ipseEventObjects26 1 }

ipse26-dest-ip-addr OBJECT-TYPE
    SYNTAX IpAddress
    MAX-ACCESS accessible-for-notify
    STATUS current
    DESCRIPTION
        "Parameter 'dest-ip-addr' in event IPSE.26"
    ::= { ipseEventObjects26 2 }

ipse26-protocol OBJECT-TYPE
    SYNTAX Integer32
    MAX-ACCESS accessible-for-notify
    STATUS current
    DESCRIPTION
        "Parameter 'protocol' in event IPSE.26"
    ::= { ipseEventObjects26 3 }

ipseEventObjects27 OBJECT-IDENTITY
    STATUS current
    DESCRIPTION
        "Event IPSE.27
        Checking input control access list in IPSec forwarder."
    ::= { ipseEventsGroup 27 }

ipse27-src-ip-addr OBJECT-TYPE
    SYNTAX IpAddress
    MAX-ACCESS accessible-for-notify
    STATUS current
    DESCRIPTION
        "Parameter 'src-ip-addr' in event IPSE.27"
    ::= { ipseEventObjects27 1 }

ipse27-dest-ip-addr OBJECT-TYPE
    SYNTAX IpAddress
    MAX-ACCESS accessible-for-notify
    STATUS current
    DESCRIPTION
        "Parameter 'dest-ip-addr' in event IPSE.27"
    ::= { ipseEventObjects27 2 }

ipse27-protocol OBJECT-TYPE
    SYNTAX Integer32
    MAX-ACCESS accessible-for-notify
    STATUS current
    DESCRIPTION
        "Parameter 'protocol' in event IPSE.27"
    ::= { ipseEventObjects27 3 }

ipseEventObjects28 OBJECT-IDENTITY
    STATUS current
    DESCRIPTION
        "Event IPSE.28
        Searching the SA for an ESP packet."
    ::= { ipseEventsGroup 28 }

ipse28-src-ip-addr OBJECT-TYPE
    SYNTAX IpAddress
    MAX-ACCESS accessible-for-notify
    STATUS current
    DESCRIPTION
        "Parameter 'src-ip-addr' in event IPSE.28"
    ::= { ipseEventObjects28 1 }

ipse28-dest-ip-addr OBJECT-TYPE
    SYNTAX IpAddress
    MAX-ACCESS accessible-for-notify
    STATUS current
    DESCRIPTION
        "Parameter 'dest-ip-addr' in event IPSE.28"
    ::= { ipseEventObjects28 2 }

ipseEventObjects29 OBJECT-IDENTITY
    STATUS current
    DESCRIPTION
        "Event IPSE.29
        Decapsulation Id Checking Fail."
    ::= { ipseEventsGroup 29 }

ipse29-src-ip-addr OBJECT-TYPE
    SYNTAX IpAddress
    MAX-ACCESS accessible-for-notify
    STATUS current
    DESCRIPTION
        "Parameter 'src-ip-addr' in event IPSE.29"
    ::= { ipseEventObjects29 1 }

ipse29-dest-ip-addr OBJECT-TYPE
    SYNTAX IpAddress
    MAX-ACCESS accessible-for-notify
    STATUS current
    DESCRIPTION
        "Parameter 'dest-ip-addr' in event IPSE.29"
    ::= { ipseEventObjects29 2 }

ipseEventObjects30 OBJECT-IDENTITY
    STATUS current
    DESCRIPTION
        "Event IPSE.30
        LCA checking fail: packet not protected by IPSec."
    ::= { ipseEventsGroup 30 }

ipse30-src-ip-addr OBJECT-TYPE
    SYNTAX IpAddress
    MAX-ACCESS accessible-for-notify
    STATUS current
    DESCRIPTION
        "Parameter 'src-ip-addr' in event IPSE.30"
    ::= { ipseEventObjects30 1 }

ipse30-dest-ip-addr OBJECT-TYPE
    SYNTAX IpAddress
    MAX-ACCESS accessible-for-notify
    STATUS current
    DESCRIPTION
        "Parameter 'dest-ip-addr' in event IPSE.30"
    ::= { ipseEventObjects30 2 }

ipseEventObjects31 OBJECT-IDENTITY
    STATUS current
    DESCRIPTION
        "Event IPSE.31
        It is shown the source and destination direction, ports and protocols."
    ::= { ipseEventsGroup 31 }

ipse31-protocol-type OBJECT-TYPE
    SYNTAX Integer32
    MAX-ACCESS accessible-for-notify
    STATUS current
    DESCRIPTION
        "Parameter 'protocol-type' in event IPSE.31"
    ::= { ipseEventObjects31 1 }

ipse31-src-ip-addr OBJECT-TYPE
    SYNTAX IpAddress
    MAX-ACCESS accessible-for-notify
    STATUS current
    DESCRIPTION
        "Parameter 'src-ip-addr' in event IPSE.31"
    ::= { ipseEventObjects31 2 }

ipse31-src-port OBJECT-TYPE
    SYNTAX Integer32
    MAX-ACCESS accessible-for-notify
    STATUS current
    DESCRIPTION
        "Parameter 'src-port' in event IPSE.31"
    ::= { ipseEventObjects31 3 }

ipse31-dest-ip-addr OBJECT-TYPE
    SYNTAX IpAddress
    MAX-ACCESS accessible-for-notify
    STATUS current
    DESCRIPTION
        "Parameter 'dest-ip-addr' in event IPSE.31"
    ::= { ipseEventObjects31 4 }

ipse31-dest-port OBJECT-TYPE
    SYNTAX Integer32
    MAX-ACCESS accessible-for-notify
    STATUS current
    DESCRIPTION
        "Parameter 'dest-port' in event IPSE.31"
    ::= { ipseEventObjects31 5 }

ipse31-length OBJECT-TYPE
    SYNTAX Integer32
    MAX-ACCESS accessible-for-notify
    STATUS current
    DESCRIPTION
        "Parameter 'length' in event IPSE.31"
    ::= { ipseEventObjects31 6 }

ipseEventObjects32 OBJECT-IDENTITY
    STATUS current
    DESCRIPTION
        "Event IPSE.32
        The router received an ICMP Path MTU 'too big' message (RFC 1191),
        indicating that a sent packet was too big and was unable
        to be fragmented for some reason. The 'source' IP address indicates
        the router whose next hop MTU is too small for the packet."
    ::= { ipseEventsGroup 32 }

ipse32-rmtu OBJECT-TYPE
    SYNTAX Integer32
    MAX-ACCESS accessible-for-notify
    STATUS current
    DESCRIPTION
        "Parameter 'rmtu' in event IPSE.32"
    ::= { ipseEventObjects32 1 }

ipse32-spi OBJECT-TYPE
    SYNTAX Integer32
    MAX-ACCESS accessible-for-notify
    STATUS current
    DESCRIPTION
        "Parameter 'spi' in event IPSE.32"
    ::= { ipseEventObjects32 2 }

ipse32-src-ip-addr OBJECT-TYPE
    SYNTAX IpAddress
    MAX-ACCESS accessible-for-notify
    STATUS current
    DESCRIPTION
        "Parameter 'src-ip-addr' in event IPSE.32"
    ::= { ipseEventObjects32 3 }

ipse32-dest-ip-addr OBJECT-TYPE
    SYNTAX IpAddress
    MAX-ACCESS accessible-for-notify
    STATUS current
    DESCRIPTION
        "Parameter 'dest-ip-addr' in event IPSE.32"
    ::= { ipseEventObjects32 4 }

ipseEventObjects33 OBJECT-IDENTITY
    STATUS current
    DESCRIPTION
        "Event IPSE.33
        The router is trying to send an IPSec packet which exceeds
        the stored PMTU value for the associated bundle. Packet is dropped,
        and an ICMP PMTU packet is sent back to the source IP address."
    ::= { ipseEventsGroup 33 }

ipse33-mtu OBJECT-TYPE
    SYNTAX Integer32
    MAX-ACCESS accessible-for-notify
    STATUS current
    DESCRIPTION
        "Parameter 'mtu' in event IPSE.33"
    ::= { ipseEventObjects33 1 }

ipse33-spi OBJECT-TYPE
    SYNTAX Integer32
    MAX-ACCESS accessible-for-notify
    STATUS current
    DESCRIPTION
        "Parameter 'spi' in event IPSE.33"
    ::= { ipseEventObjects33 2 }

ipse33-src-ip-addr OBJECT-TYPE
    SYNTAX IpAddress
    MAX-ACCESS accessible-for-notify
    STATUS current
    DESCRIPTION
        "Parameter 'src-ip-addr' in event IPSE.33"
    ::= { ipseEventObjects33 3 }

ipse33-dest-ip-addr OBJECT-TYPE
    SYNTAX IpAddress
    MAX-ACCESS accessible-for-notify
    STATUS current
    DESCRIPTION
        "Parameter 'dest-ip-addr' in event IPSE.33"
    ::= { ipseEventObjects33 4 }

ipseEventObjects34 OBJECT-IDENTITY
    STATUS current
    DESCRIPTION
        "Event IPSE.34
        timestamp error"
    ::= { ipseEventsGroup 34 }

ipse34-rcvd-time OBJECT-TYPE
    SYNTAX Integer32
    MAX-ACCESS accessible-for-notify
    STATUS current
    DESCRIPTION
        "Parameter 'rcvd-time' in event IPSE.34"
    ::= { ipseEventObjects34 1 }

ipse34-expected-time OBJECT-TYPE
    SYNTAX Integer32
    MAX-ACCESS accessible-for-notify
    STATUS current
    DESCRIPTION
        "Parameter 'expected-time' in event IPSE.34"
    ::= { ipseEventObjects34 2 }

ipse34-windows OBJECT-TYPE
    SYNTAX Integer32
    MAX-ACCESS accessible-for-notify
    STATUS current
    DESCRIPTION
        "Parameter 'windows' in event IPSE.34"
    ::= { ipseEventObjects34 3 }

ipseEventObjects35 OBJECT-IDENTITY
    STATUS current
    DESCRIPTION
        "Event IPSE.35
        Usual operation trace (free format)."
    ::= { ipseEventsGroup 35 }

ipse35-trace OBJECT-TYPE
    SYNTAX DisplayString
    MAX-ACCESS accessible-for-notify
    STATUS current
    DESCRIPTION
        "Parameter 'trace' in event IPSE.35"
    ::= { ipseEventObjects35 1 }


ipseNotification1 NOTIFICATION-TYPE
    OBJECTS { 
              ipse1-packet-type, 
              ipse1-SPI 
            }
    STATUS current
    DESCRIPTION
        "Notification of Event IPSE.1

        Message: '$1, spi $2'

        Parameters list:
              $1: ipse1-packet-type
              $2: ipse1-SPI

        It is shown the protocol of the encapsulated packet and the SPI."
    ::= { ipseNotificationsPrefix 1 }

ipseNotification2 NOTIFICATION-TYPE
    OBJECTS { 
              ipse2-protocol-type 
            }
    STATUS current
    DESCRIPTION
        "Notification of Event IPSE.2

        Message: 'Error while unencapsulating packet $1, unknown'

        Parameters list:
              $1: ipse2-protocol-type

        The received encapsulated packet has an unknown protocol."
    ::= { ipseNotificationsPrefix 2 }

ipseNotification3 NOTIFICATION-TYPE
    OBJECTS { 
              ipse3-protocol-type, 
              ipse3-src-ip-addr,
              ipse3-dest-ip-addr,
              ipse3-SPI 
            }
    STATUS current
    DESCRIPTION
        "Notification of Event IPSE.3

        Message: 'Packet $1 successfully encapsulated (source $2 -> destination $3) spi $4'

        Parameters list:
              $1: ipse3-protocol-type
              $2: ipse3-src-ip-addr
              $3: ipse3-dest-ip-addr
              $4: ipse3-SPI

        The output function of the tunnel net has encapsulated a ESP or
        AH packet successfully. It is shown the protocol of the encapsulated
        packet, the source and destination direction and the SPI."
    ::= { ipseNotificationsPrefix 3 }

ipseNotification4 NOTIFICATION-TYPE
    OBJECTS { 
              ipse4-protocol-type, 
              ipse4-sa-number 
            }
    STATUS current
    DESCRIPTION
        "Notification of Event IPSE.4

        Message: 'Error in packet authentication $1 ,spi $2'

        Parameters list:
              $1: ipse4-protocol-type
              $2: ipse4-sa-number

        The authentication of an ESP or AH packet failed."
    ::= { ipseNotificationsPrefix 4 }

ipseNotification5 NOTIFICATION-TYPE
    OBJECTS { 
              ipse5-protocol-name, 
              ipse5-src-ip-addr,
              ipse5-dest-ip-addr 
            }
    STATUS current
    DESCRIPTION
        "Notification of Event IPSE.5

        Message: 'Packet discarded $1 received with delay, (source $2 -> destination $3)'

        Parameters list:
              $1: ipse5-protocol-name
              $2: ipse5-src-ip-addr
              $3: ipse5-dest-ip-addr

        A packet was discarded because its secuence number was below
        the minimum admited in the reception window."
    ::= { ipseNotificationsPrefix 5 }

ipseNotification6 NOTIFICATION-TYPE
    OBJECTS { 
              ipse6-protocol-name, 
              ipse6-src-ip-addr,
              ipse6-dest-ip-addr 
            }
    STATUS current
    DESCRIPTION
        "Notification of Event IPSE.6

        Message: 'Packet discarded $1 because repeated, (source $2 -> destination $3)'

        Parameters list:
              $1: ipse6-protocol-name
              $2: ipse6-src-ip-addr
              $3: ipse6-dest-ip-addr

        A packet was discarded because the antireplay options were active
        and it was already received."
    ::= { ipseNotificationsPrefix 6 }

ipseNotification7 NOTIFICATION-TYPE
    STATUS current
    DESCRIPTION
        "Notification of Event IPSE.7

        Message: 'Packet discarded because used a wrong padding'

        A packet was discarded because the padding had a wrong value."
    ::= { ipseNotificationsPrefix 7 }

ipseNotification8 NOTIFICATION-TYPE
    OBJECTS { 
              ipse8-protocol-type, 
              ipse8-src-ip-addr,
              ipse8-dest-ip-addr 
            }
    STATUS current
    DESCRIPTION
        "Notification of Event IPSE.8

        Message: 'Packet discarded because has a wrong length $1, not multiple of 32 bits (source $2-> destination $3)'

        Parameters list:
              $1: ipse8-protocol-type
              $2: ipse8-src-ip-addr
              $3: ipse8-dest-ip-addr

        A packet is discarded because it has a wrong length (it is not multiple
        of 32 bits)."
    ::= { ipseNotificationsPrefix 8 }

ipseNotification9 NOTIFICATION-TYPE
    OBJECTS { 
              ipse9-protocol-type, 
              ipse9-src-ip-addr,
              ipse9-dest-ip-addr 
            }
    STATUS current
    DESCRIPTION
        "Notification of Event IPSE.9

        Message: 'Packet with correct sequence number, protocol $1, (source $2 -> destination $3)'

        Parameters list:
              $1: ipse9-protocol-type
              $2: ipse9-src-ip-addr
              $3: ipse9-dest-ip-addr

        Packet with correct sequence number in window."
    ::= { ipseNotificationsPrefix 9 }

ipseNotification10 NOTIFICATION-TYPE
    OBJECTS { 
              ipse10-protocol-type, 
              ipse10-src-ip-addr,
              ipse10-dest-ip-addr 
            }
    STATUS current
    DESCRIPTION
        "Notification of Event IPSE.10

        Message: 'Packet discarded in window secuence because as 0 secuence number in protocol $1, source $2, destination $3'

        Parameters list:
              $1: ipse10-protocol-type
              $2: ipse10-src-ip-addr
              $3: ipse10-dest-ip-addr

        The packet has arrived to window secuence with 0 as secuence number."
    ::= { ipseNotificationsPrefix 10 }

ipseNotification11 NOTIFICATION-TYPE
    OBJECTS { 
              ipse11-protocol-type, 
              ipse11-spi,
              ipse11-sa-seq-num,
              ipse11-inbound-seq-num 
            }
    STATUS current
    DESCRIPTION
        "Notification of Event IPSE.11

        Message: 'Prot $1 spi $2 seq num SA $3, seq num pack $4'

        Parameters list:
              $1: ipse11-protocol-type
              $2: ipse11-spi
              $3: ipse11-sa-seq-num
              $4: ipse11-inbound-seq-num

        The protocol, the SA sequence number and the packet sequence number
        are shown."
    ::= { ipseNotificationsPrefix 11 }

ipseNotification12 NOTIFICATION-TYPE
    OBJECTS { 
              ipse12-spi, 
              ipse12-protocol,
              ipse12-remote-peer 
            }
    STATUS current
    DESCRIPTION
        "Notification of Event IPSE.12

        Message: 'SA not found, spi $1 protocol $2 remote peer $3'

        Parameters list:
              $1: ipse12-spi
              $2: ipse12-protocol
              $3: ipse12-remote-peer

        A packet has arrived with the SPI showed and there is not an
        static SA configured for it."
    ::= { ipseNotificationsPrefix 12 }

ipseNotification13 NOTIFICATION-TYPE
    OBJECTS { 
              ipse13-protocol-type 
            }
    STATUS current
    DESCRIPTION
        "Notification of Event IPSE.13

        Message: 'Warning! Overflow of seq num, prot $1'

        Parameters list:
              $1: ipse13-protocol-type

        Overflow in sequence number the next sequence number is 1."
    ::= { ipseNotificationsPrefix 13 }

ipseNotification14 NOTIFICATION-TYPE
    OBJECTS { 
              ipse14-spi, 
              ipse14-protocol,
              ipse14-remote-peer 
            }
    STATUS current
    DESCRIPTION
        "Notification of Event IPSE.14

        Message: 'SA is down, spi $1 protocol $2 remote peer $3'

        Parameters list:
              $1: ipse14-spi
              $2: ipse14-protocol
              $3: ipse14-remote-peer

        A packet has arrived with SPI %x and there is not an
        static SA configured for it."
    ::= { ipseNotificationsPrefix 14 }

ipseNotification15 NOTIFICATION-TYPE
    OBJECTS { 
              ipse15-src-ip-addr, 
              ipse15-dest-ip-addr 
            }
    STATUS current
    DESCRIPTION
        "Notification of Event IPSE.15

        Message: 'Policy not found for packet ($1->$2)'

        Parameters list:
              $1: ipse15-src-ip-addr
              $2: ipse15-dest-ip-addr

        Found entry hasn't policy assigned. (Debug)."
    ::= { ipseNotificationsPrefix 15 }

ipseNotification16 NOTIFICATION-TYPE
    OBJECTS { 
              ipse16-message, 
              ipse16-phase,
              ipse16-src-ip-addr,
              ipse16-dest-ip-addr 
            }
    STATUS current
    DESCRIPTION
        "Notification of Event IPSE.16

        Message: 'ISAKMP - Message $1 fase $2 INVALID ATTRIBUTES.  pack ($3->$4)'

        Parameters list:
              $1: ipse16-message
              $2: ipse16-phase
              $3: ipse16-src-ip-addr
              $4: ipse16-dest-ip-addr

        Attributes are wrong."
    ::= { ipseNotificationsPrefix 16 }

ipseNotification17 NOTIFICATION-TYPE
    OBJECTS { 
              ipse17-message 
            }
    STATUS current
    DESCRIPTION
        "Notification of Event IPSE.17

        Message: 'IKE - Allocating memory error. $1'

        Parameters list:
              $1: ipse17-message

        Error allocating memory."
    ::= { ipseNotificationsPrefix 17 }

ipseNotification18 NOTIFICATION-TYPE
    OBJECTS { 
              ipse18-src-ip-addr, 
              ipse18-dest-ip-addr 
            }
    STATUS current
    DESCRIPTION
        "Notification of Event IPSE.18

        Message: 'ISAKMP-SA proposal incompatible.  remote peer:$1 Local interface:$2'

        Parameters list:
              $1: ipse18-src-ip-addr
              $2: ipse18-dest-ip-addr

        Incompatible IKE policies."
    ::= { ipseNotificationsPrefix 18 }

ipseNotification19 NOTIFICATION-TYPE
    OBJECTS { 
              ipse19-mes-number, 
              ipse19-phase-number,
              ipse19-remote-peer-addr,
              ipse19-local-ifc-addr 
            }
    STATUS current
    DESCRIPTION
        "Notification of Event IPSE.19

        Message: 'IKE -Error building the $1 message in fase $2. remote peer:$3 Local interface:$4'

        Parameters list:
              $1: ipse19-mes-number
              $2: ipse19-phase-number
              $3: ipse19-remote-peer-addr
              $4: ipse19-local-ifc-addr

        Error building the message."
    ::= { ipseNotificationsPrefix 19 }

ipseNotification20 NOTIFICATION-TYPE
    OBJECTS { 
              ipse20-message 
            }
    STATUS current
    DESCRIPTION
        "Notification of Event IPSE.20

        Message: 'Error inicializating IKE protocol. $1'

        Parameters list:
              $1: ipse20-message

        Error inicializating IKE protocol."
    ::= { ipseNotificationsPrefix 20 }

ipseNotification21 NOTIFICATION-TYPE
    OBJECTS { 
              ipse21-ike-port 
            }
    STATUS current
    DESCRIPTION
        "Notification of Event IPSE.21

        Message: 'IKE protocol server active in port: $1'

        Parameters list:
              $1: ipse21-ike-port

        IKE is active."
    ::= { ipseNotificationsPrefix 21 }

ipseNotification22 NOTIFICATION-TYPE
    OBJECTS { 
              ipse22-remote-addr, 
              ipse22-message 
            }
    STATUS current
    DESCRIPTION
        "Notification of Event IPSE.22

        Message: 'IKE($1)$2'

        Parameters list:
              $1: ipse22-remote-addr
              $2: ipse22-message

        A packet is received."
    ::= { ipseNotificationsPrefix 22 }

ipseNotification23 NOTIFICATION-TYPE
    OBJECTS { 
              ipse23-local-addr, 
              ipse23-remote-addr 
            }
    STATUS current
    DESCRIPTION
        "Notification of Event IPSE.23

        Message: 'IKE - ISAKMP SA has been created ($1 <-> $2)'

        Parameters list:
              $1: ipse23-local-addr
              $2: ipse23-remote-addr

        An ISAKMP SA has been created."
    ::= { ipseNotificationsPrefix 23 }

ipseNotification24 NOTIFICATION-TYPE
    OBJECTS { 
              ipse24-error 
            }
    STATUS current
    DESCRIPTION
        "Notification of Event IPSE.24

        Message: 'ISAKMP Error - $1'

        Parameters list:
              $1: ipse24-error

        Error (free format)."
    ::= { ipseNotificationsPrefix 24 }

ipseNotification25 NOTIFICATION-TYPE
    OBJECTS { 
              ipse25-src-ip-addr, 
              ipse25-dest-ip-addr,
              ipse25-state 
            }
    STATUS current
    DESCRIPTION
        "Notification of Event IPSE.25

        Message: 'Packet ($1 -> $2) entered in IpSec Forwarder State $3.'

        Parameters list:
              $1: ipse25-src-ip-addr
              $2: ipse25-dest-ip-addr
              $3: ipse25-state

        Leaving state in IPSec forwarder."
    ::= { ipseNotificationsPrefix 25 }

ipseNotification26 NOTIFICATION-TYPE
    OBJECTS { 
              ipse26-src-ip-addr, 
              ipse26-dest-ip-addr,
              ipse26-protocol 
            }
    STATUS current
    DESCRIPTION
        "Notification of Event IPSE.26

        Message: 'Out.ACL($1->$2) ProtNum $3.'

        Parameters list:
              $1: ipse26-src-ip-addr
              $2: ipse26-dest-ip-addr
              $3: ipse26-protocol

        Checking output control access list in IPSec forwarder."
    ::= { ipseNotificationsPrefix 26 }

ipseNotification27 NOTIFICATION-TYPE
    OBJECTS { 
              ipse27-src-ip-addr, 
              ipse27-dest-ip-addr,
              ipse27-protocol 
            }
    STATUS current
    DESCRIPTION
        "Notification of Event IPSE.27

        Message: 'In.ACL($1->$2) ProtNum $3.'

        Parameters list:
              $1: ipse27-src-ip-addr
              $2: ipse27-dest-ip-addr
              $3: ipse27-protocol

        Checking input control access list in IPSec forwarder."
    ::= { ipseNotificationsPrefix 27 }

ipseNotification28 NOTIFICATION-TYPE
    OBJECTS { 
              ipse28-src-ip-addr, 
              ipse28-dest-ip-addr 
            }
    STATUS current
    DESCRIPTION
        "Notification of Event IPSE.28

        Message: 'Searching SA for an ESP/AH Packet directed to a Local Ifc. Packet ($1->$2).'

        Parameters list:
              $1: ipse28-src-ip-addr
              $2: ipse28-dest-ip-addr

        Searching the SA for an ESP packet."
    ::= { ipseNotificationsPrefix 28 }

ipseNotification29 NOTIFICATION-TYPE
    OBJECTS { 
              ipse29-src-ip-addr, 
              ipse29-dest-ip-addr 
            }
    STATUS current
    DESCRIPTION
        "Notification of Event IPSE.29

        Message: 'Packet ($1 -> $2) decapsulation Id checking Failure.'

        Parameters list:
              $1: ipse29-src-ip-addr
              $2: ipse29-dest-ip-addr

        Decapsulation Id Checking Fail."
    ::= { ipseNotificationsPrefix 29 }

ipseNotification30 NOTIFICATION-TYPE
    OBJECTS { 
              ipse30-src-ip-addr, 
              ipse30-dest-ip-addr 
            }
    STATUS current
    DESCRIPTION
        "Notification of Event IPSE.30

        Message: 'No Ipsec protected : packet ($1 -> $2) drop.'

        Parameters list:
              $1: ipse30-src-ip-addr
              $2: ipse30-dest-ip-addr

        LCA checking fail: packet not protected by IPSec."
    ::= { ipseNotificationsPrefix 30 }

ipseNotification31 NOTIFICATION-TYPE
    OBJECTS { 
              ipse31-protocol-type, 
              ipse31-src-ip-addr,
              ipse31-src-port,
              ipse31-dest-ip-addr,
              ipse31-dest-port,
              ipse31-length 
            }
    STATUS current
    DESCRIPTION
        "Notification of Event IPSE.31

        Message: 'protocol $1 (source $2 port $3-> destination $4 prot $5) length $6'

        Parameters list:
              $1: ipse31-protocol-type
              $2: ipse31-src-ip-addr
              $3: ipse31-src-port
              $4: ipse31-dest-ip-addr
              $5: ipse31-dest-port
              $6: ipse31-length

        It is shown the source and destination direction, ports and protocols."
    ::= { ipseNotificationsPrefix 31 }

ipseNotification32 NOTIFICATION-TYPE
    OBJECTS { 
              ipse32-rmtu, 
              ipse32-spi,
              ipse32-src-ip-addr,
              ipse32-dest-ip-addr 
            }
    STATUS current
    DESCRIPTION
        "Notification of Event IPSE.32

        Message: 'Rcvd ICMP PMTU: Next-hop mtu = $1 bytes. SPI $2, pkt $3 -> $4'

        Parameters list:
              $1: ipse32-rmtu
              $2: ipse32-spi
              $3: ipse32-src-ip-addr
              $4: ipse32-dest-ip-addr

        The router received an ICMP Path MTU 'too big' message (RFC 1191),
        indicating that a sent packet was too big and was unable
        to be fragmented for some reason. The 'source' IP address indicates
        the router whose next hop MTU is too small for the packet."
    ::= { ipseNotificationsPrefix 32 }

ipseNotification33 NOTIFICATION-TYPE
    OBJECTS { 
              ipse33-mtu, 
              ipse33-spi,
              ipse33-src-ip-addr,
              ipse33-dest-ip-addr 
            }
    STATUS current
    DESCRIPTION
        "Notification of Event IPSE.33

        Message: 'Sent ICMP PMTU: Path mtu = $1 bytes. SPI $2, pkt $3 -> $4'

        Parameters list:
              $1: ipse33-mtu
              $2: ipse33-spi
              $3: ipse33-src-ip-addr
              $4: ipse33-dest-ip-addr

        The router is trying to send an IPSec packet which exceeds
        the stored PMTU value for the associated bundle. Packet is dropped,
        and an ICMP PMTU packet is sent back to the source IP address."
    ::= { ipseNotificationsPrefix 33 }

ipseNotification34 NOTIFICATION-TYPE
    OBJECTS { 
              ipse34-rcvd-time, 
              ipse34-expected-time,
              ipse34-windows 
            }
    STATUS current
    DESCRIPTION
        "Notification of Event IPSE.34

        Message: 'GDOI timestamp error rcvd time $1 expected $2 window $3'

        Parameters list:
              $1: ipse34-rcvd-time
              $2: ipse34-expected-time
              $3: ipse34-windows

        timestamp error"
    ::= { ipseNotificationsPrefix 34 }

ipseNotification35 NOTIFICATION-TYPE
    OBJECTS { 
              ipse35-trace 
            }
    STATUS current
    DESCRIPTION
        "Notification of Event IPSE.35

        Message: 'Access list cache - $1'

        Parameters list:
              $1: ipse35-trace

        Usual operation trace (free format)."
    ::= { ipseNotificationsPrefix 35 }


END
