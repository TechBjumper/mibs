-- FH800u Stackable Dual-Speed Hub MIB Version 1.08    03/12/1999
-- FH800u Stackable Dual-Speed Hub MIB Version 1.01    07/13/1998
-- ( The change of equipment name from FH813E/FH825E to FH812u/FH824u)
-- (  The unification of sysObjectID. FH812u(1)/FH824u(2) to FH800u(1))
-- fh800u Stackable Dual-Speed Hub MIB Version 1.0    07/02/1998
-- (Original : Accton EH3524A Dual-Speed Hub (Tomcat) private MIB version 1.0)
--
-- Date released:    
--
-- Device supported: FH800u system
--
--
--
--
--
-- Development History
--
-- 1997/7/21 Created by Hans Chen
-- 1997/12/04 Added the rmonConfigTable by Hans Chen
-- 1998/2/10  Added current ip relatived information:( stackInusedIP,
--		   	stackInusedNetMask, stackInusedGateway, stackInusedSlipAddr,
--			stackInusedBootUpIP> and renamed the old ip information to
--			stackTemporalXXX:( stackTemporalIP,stackTemporalNetMask, 
--			stackTemporalGateway, stackTemporalSlipAddr,and stackTemporalBootUpIP)
-- 			and ipInformationReset in the eh3524aStackInfo group.
--1998/3/27 Changed the stackHealthMonitor with port 13 to 24 port to reserve for 12 
--			port hub.
--1998/5/22 Deleted the stackInusedSlipAddr. Added stackInusedHostSlipAddr and 
--			stackInusedServerSlipAddr. Deleted the stackTemporalSlipAddr .Added
--			the stackTemporalHostSlipAddr and stackTemporalServerSlipAddr.   
--1998/6/10 Removed stackCounterReset, groupBackplaneTable,portCounterReset, 
--			segmentCounterReset, eh3524aPerfMonStackInfo, eh3524aPerfMonGroupInfo
--			eh3524aSwitchInfo, eh3524aSwitchPortInfo,eh3524aSwitchPortStatsInfo			
--			securityPortEavesdrop, securityFunction, groupSecurityTable,
--			securityChangeEvent.
--1998/6/13 Deleted the warning in the node securityPortIntrusion.
-- 1998/ 7/ 2 Changed equipment name from EH3524A to fh800u by ATKK. 
--            Changed MIB tree from Accton's to ATKK's.
--               accton(259).products(5).cheetahHubsystem(7).eh3524a(1)
--               => alliedTelesyn(207).products(1).dualHub(10).fh813e(1)
--                                                             fh825e(2)
--               accton(259).snmpMgt(6) 
--               => alliedTelesyn(207).mibObject(8).repeaterMib(1)
--                                    .newRepeaterMib(20).acctonHubMIB(3)
--            Changed ENTERPRISE of TRAP from cheetahHubsystem to cheetahHubMgt.--
-- 1998/7/13 Changed equipment name from fh800u to FH800u by ATKK.
--            Changed MIB tree from fh800u to FH800u by ATKK.
--              (The unification of the sysObjectID)
--               alliedTelesyn(207).products(1).dualHub(10).fh813e(1)
--                                                          fh825e(2)
--
--               => alliedTelesyn(207).products(1).dualHub(10).fh812u(1)
--                                                             fh824u(2)
--
-- 1998/10/22 1) Changed masterLinkFailEvent's Trap code from 3 to 2 .
--            2) Changed ENTERPRISE of TRAP's name from cheetahHubMgt 
--                                                   to atactDualHubMgt.
--
-- 1999/02/04 Add the SwitchPortStatsTable 
--
-- 1999/03/12 By Zhou ,Delete the "Port Backup"
--

FH800u-MIB DEFINITIONS ::= BEGIN

IMPORTS
	TRAP-TYPE FROM RFC-1215
        enterprises,
        OBJECT-TYPE, Counter, TimeTicks ,IpAddress
        FROM RFC1155-SMI
        DisplayString,
        PhysAddress
        FROM RFC1213-MIB;

        alliedTelesyn   OBJECT IDENTIFIER ::= { enterprises 207 }
        products        OBJECT IDENTIFIER ::= { alliedTelesyn 1 }
        dualHub         OBJECT IDENTIFIER ::= { products 10 }
        fh812u          OBJECT IDENTIFIER ::= { dualHub 1 }
        fh824u          OBJECT IDENTIFIER ::= { dualHub 2 }
        mibObject       OBJECT IDENTIFIER ::= { alliedTelesyn 8 }
        repeaterMib     OBJECT IDENTIFIER ::= { mibObject 1 }
        newRepeaterMib  OBJECT IDENTIFIER ::= { repeaterMib 20 }
        acctonHubMIB    OBJECT IDENTIFIER ::= { newRepeaterMib 3 }


        atactDualHubMgt OBJECT IDENTIFIER ::=
                { acctonHubMIB 11 }

        fh800uMgt OBJECT IDENTIFIER ::=
                { atactDualHubMgt 1 }

        fh800uBasicCapability
                OBJECT IDENTIFIER ::=  { fh800uMgt  1 }

        fh800uPerfMonCapability
                OBJECT IDENTIFIER ::=  { fh800uMgt  2 }

        fh800uSwitchCapability
                OBJECT IDENTIFIER ::=  { fh800uMgt  3 }

--		fh800uBackupCapability
--                OBJECT IDENTIFIER ::=  { fh800uMgt  4 }

        fh800uSecurityCapability
                OBJECT IDENTIFIER ::=  { fh800uMgt  5 }


-- Dual-Speed Hub Basic Capability

        fh800uStackInfo       OBJECT IDENTIFIER ::=  { fh800uBasicCapability 1 }

        stackInusedIP                   OBJECT-TYPE
                SYNTAX  IpAddress
                ACCESS  read-only
                STATUS  mandatory
                DESCRIPTION
                        "The IP address currently used by the Dual-Speed Hub system. "
                        ::= { fh800uStackInfo 1 }

        stackInusedNetMask              OBJECT-TYPE
                SYNTAX  IpAddress
                ACCESS  read-only
                STATUS  mandatory
                DESCRIPTION
                        "The subnet maskcurrently used by the Dual-Speed Hub system. "                         
                ::= { fh800uStackInfo 2 }

        stackInusedGateway     OBJECT-TYPE
                SYNTAX  IpAddress
                ACCESS  read-only
                STATUS  mandatory
                DESCRIPTION
                        "The prefered gateway used to send traps."
                ::= { fh800uStackInfo 3 }		

		stackInusedServerSlipAddr	 OBJECT-TYPE
        		SYNTAX  IpAddress
       			ACCESS  read-only
       			STATUS  mandatory
        		DESCRIPTION  "The Server SLIP addresscurrently used by the Dual-Speed Hub
                        system."
        		::= { fh800uStackInfo 4 }
				
		stackInusedHostSlipAddr	 OBJECT-TYPE
        		SYNTAX  IpAddress
       			ACCESS  read-only
       			STATUS  mandatory
        		DESCRIPTION  "The Host SLIP address currently used by the Dual-Speed Hub
                        system."
        		::= { fh800uStackInfo 5 }	

		stackInusedBootUpIP 	OBJECT-TYPE
        		SYNTAX  IpAddress
       			ACCESS  read-only
       			STATUS  mandatory
        		DESCRIPTION  "The Bootup IP address currently used by the Dual-Speed Hub
                        system. The Bootup IP must reside in the same subnet as the stackIP."
        		::= { fh800uStackInfo 6 }

		stackTemporalIP                   OBJECT-TYPE
                SYNTAX  IpAddress
                ACCESS  read-write
                STATUS  mandatory
                DESCRIPTION
                        "Used to change the IP address of the Dual-Speed Hub
                        system. "
                        ::= { fh800uStackInfo 7 }

        stackTemporalNetMask              OBJECT-TYPE
                SYNTAX  IpAddress
                ACCESS  read-write
                STATUS  mandatory
                DESCRIPTION
                        "Used to change the subnet mask of the Dual-Speed Hub
                         system. "
                ::= { fh800uStackInfo 8 }

        stackTemporalGateway              OBJECT-TYPE
                SYNTAX  IpAddress
                ACCESS  read-write
                STATUS  mandatory
                DESCRIPTION
                        "Used to change the prefered gateway to send traps."
                ::= { fh800uStackInfo 9 }		

	    stackTemporalServerSlipAddr OBJECT-TYPE
        		SYNTAX  IpAddress
       			ACCESS  read-write
       			STATUS  mandatory
        		DESCRIPTION  "Used to change the Server SLIP address of the Dual-Speed Hub
                        system. The SLIP address must reside in the same subnet as the stackIP."
        		::= { fh800uStackInfo 10 }

		stackTemporalHostSlipAddr OBJECT-TYPE
        		SYNTAX  IpAddress
       			ACCESS  read-write
       			STATUS  mandatory
        		DESCRIPTION  "Used to change the Host SLIP address of the Dual-Speed Hub
                        system."
        		::= { fh800uStackInfo 11 }

		stackTemporalBootUpIP OBJECT-TYPE
        		SYNTAX  IpAddress
       			ACCESS  read-write
       			STATUS  mandatory
        		DESCRIPTION  "Used to change the Bootup IP address of the Dual-Speed Hub
                        system. The Bootup IP must reside in the same subnet as the stackIP."
        		::= { fh800uStackInfo 12 }

		ipInformationReset OBJECT-TYPE
                SYNTAX  INTEGER {
								  noReset(1),
                                  reset(2)
                                }
                ACCESS  read-write 
                STATUS  mandatory
                DESCRIPTION
                        "Setting the stackIP, stackNetMask,stackGateway,
               stackSlipAddr, and stackBootUpIP will not immediately enable parameters take 
               effect . They will take effect when ipInformationReset is set to reset(2)."
                ::= { fh800uStackInfo 13 }


        stackHealthMonitor        OBJECT-TYPE
              SYNTAX  OCTET STRING (SIZE (256) )
                ACCESS  read-only
                STATUS  mandatory
                DESCRIPTION "

             < FOR  fh800u Dual-Speed Hub DEFINITION : >

             There are two kinds of hubs : 12 ports  
                                          need (1+ 12 + 1 + 1 + 1 + 1 +1 +1 +1) 20 bytes
                                        and 24 ports
                                          need (1+ 24 + 1 + 1 + 1 + 1 +1 +1 +1) 32 bytes

             The maximun size :
             256 bytes (total for 8 hubs)=8 hub * (1+ 24 + 1 + 1 + 1 +1 +1 +1 +1) bytes
                 |
             byte256 byte255......................byte2 byte1
                                                        |
                                                      bit7 bit6 ... bit1 bit0

            Use the first byte of each hub to indicate whether 20 or 32 bytes is used.

             BYTE 1: total number of ports on a hub                     
                     00001100 : 12 ports
                     |      |
                  bit7...  bit0
                     00011000 : 24 ports
                     |      |
                  bit7...  bit0

           For 12-port hub
             BYTE 2 - 13 : port status for port 1 - 12

                     *BYTE 2 : port status for port 1

                        bit 0-4 : LED status
                                bit 0 : link status
                                        0 - no link; 1 - link
                                bit 1 : partition status
                                        0 - no part.; 1 - part.
                                bit 2 : port operation status
                                        0 - disabled; 1 - enabled
                                bit 3-4 : port type status   
                                        00 - not present
                                        01 - tenMb 
                                        10 - onehundredMb
                                        11 - reserved    
                          bit 5-7 : reserved

			BYTE 14-25 :reserved

 		 	BYTE 26 : Expansion Port (EP) status1

                      bit 0-2: EP Type
                              000 - not present
                              100 - 100BASE-TX(ST) FEM
                              010 - 100BASE-TX(SC) FEM
                              1001 to 1111 - reserved
                             
                      bit 3-4 : FEM forwarding mode status
                                Applicable only to FEM module
                             00 - adaptive cut through
                             01 - reserved
                             10 - reserved
                             11 - store and forward

                      bit 5: FEM back pressure status
                              0 - disabled; 1 - enabled

                      bit 6-7 : reserved

           BYTE 27 : Expansion Port (EP) status2

                      bit 0-1 : LED status
                              bit 0 : FEM link status
                                      0 - no link; 1 - link
                              bit 1 : FEM half/full duplex status
                                      0 - full duplex; 1 - half duplex
                             
                      bit 2  : EP collision led status
                              0 - off; 1 - on

                      bit 3-4 :
                              bit 3 : tx LED status
                                      0 - off; 1 - tx on
                              bit 4 : rx LED status
                                      0 - off; 1 - rx on

                      bit 5-7 : reserved

                          
		                                               
                                

             BYTE 28 : tenMb segment traffic/collision  
                       bit 0-1 : tenMb traffic LED status
                             00 - no traffic
					         01 - low traffic
					         10 - middle traffic
					         11 - high traffic
                              
                        bit 2-5 : tenMb collision LED status
                             0000 - none
				             0001 - 1 %
				             0010 - 3 %
				             0011 - 5 %
				             0100 - 10 %
				             0101 - >= 15 % 
                              
                        bit 6-7 : reserved

            BYTE 29 : onehundredMb segment traffic/collision /Power/Switch LED status

                      bit 0-1 : onehundredMb traffic LED status
                             00 - no traffic
					         01 - low traffic
					         10 - middle traffic
					         11 - high traffic
                              
                        bit 2-5 : onehundredMb collision LED status
                             0000 - none
				             0001 - 1 %
				             0010 - 3 %
				             0011 - 5 %
				             0100 - 10 %
				             0101 - >= 15 % 

                        bit 6 : Power LED
				              0 - OFF; 1 - ON 
                        bit 7 : Switch LED
				              0 - OFF; 1 - ON 


           
            BYTE 30 :SNMP agent & switch status

                      bit 0:  internal switch bit 
                              0 - not exist; 1 - exist
					  bit 1:  internal switch status
                              0 - inactive; 1 - active
                      bit 2:  expension switch bit
                      		  0 - bad; 1 - good
                      bit 3:  expension switch status
                              0 - inactive; 1 - active  
                      bit 4:  agent bit
                              0 - not exist; 1 - exist
                      bit 5 : master status
				              0 - Slave; 1 - Master 
                      bit 6 - 7 : reserved 						
                              
			BYTE 31 : Rmon status
					  bit 0 : rmon bit 
                              0 - not exist; 1 - exist                               
                      bit 1 - 2 :rmon segment
                              00 - all stack 
							  01 - segment tenMb
							  10 - segment onehundredMb
							  11 - reserved
							                                 
                      bit 3 - 5 : RMON group Status
                              000 - not-present
							  001 - disabled
                              010 - Rmon-4Group
                              011 - Rmon-7Group
                              100 - Rmon-all
							  101 to 111 - reserved

					  bit 6 -7 : reserved

                              

            BYTE 32 : Hub Position(Hub ID)/Bus Termination 

                     bit 0 - 3 : hub position 

                              0000 - invalid
                              0001 - 1
                              0010 - 2
                              0011 - 3
                              0100 - 4
                              0101 - 5
                              0110 - 6
                              0111 - 7
                              1000 - 8                              
                              1001 to 1111 - reserved

                     bit 4 : termination status
                              0 - not end hub
                              1 - end hub in the stack
                     
                     bit 5 - 7 : reserved

          For 24-port hub
             BYTE 2 - 25 : port status for port 1 - 24

                     *BYTE 2 : port status for port 1

                        bit 0-4 : LED status
                                bit 0 : link status
                                        0 - no link; 1 - link
                                bit 1 : partition status
                                        0 - no part.; 1 - part.
                                bit 2 : port operation status
                                        0 - disabled; 1 - enabled
                                bit 3-4 : port type status   
                                        00 - not present
                                        01 - tenMb 
                                        10 - onehundredMb
                                        11 - reserved    
                        bit 5-7 : reserved
                        
			 BYTE 26 : Expansion Port (EP) status1

                      bit 0-2: EP Type
                              000 - not present
                              100 - 100BASE-TX(ST) FEM
                              010 - 100BASE-TX(SC) FEM
                              1001 to 1111 - reserved
                             
                      bit 3-4 : FEM forwarding mode status
                                Applicable only to FEM module
                             00 - adaptive cut through
                             01 - reserved
                             10 - reserved
                             11 - store and forward

                      bit 5: FEM back pressure status
                              0 - disabled; 1 - enabled

                      bit 6-7 : reserved

           BYTE 27 : Expansion Port (EP) status2

                      bit 0-1 : LED status
                              bit 0 : FEM link status
                                      0 - no link; 1 - link
                              bit 1 : FEM half/full duplex status
                                      0 - full duplex; 1 - half duplex
                             
                      bit 2  : EP collision led status
                              0 - off; 1 - on

                      bit 3-4 :
                              bit 3 : tx LED status
                                      0 - off; 1 - tx on
                              bit 4 : rx LED status
                                      0 - off; 1 - rx on

                      bit 5-7 : reserved

                          
		                                               
                                

             BYTE 28 : tenMb segment traffic/collision  
                       bit 0-1 : tenMb traffic LED status
                             00 - no traffic
					         01 - low traffic
					         10 - middle traffic
					         11 - high traffic
                              
                        bit 2-5 : tenMb collision LED status
                             0000 - none
				             0001 - 1 %
				             0010 - 3 %
				             0011 - 5 %
				             0100 - 10 %
				             0101 - >= 15 % 
                              
                        bit 6-7 : reserved

            BYTE 29 : onehundredMb segment traffic/collision /Power/Switch LED status

                      bit 0-1 : onehundredMb traffic LED status
                             00 - no traffic
					         01 - low traffic
					         10 - middle traffic
					         11 - high traffic
                              
                        bit 2-5 : onehundredMb collision LED status
                             0000 - none
				             0001 - 1 %
				             0010 - 3 %
				             0011 - 5 %
				             0100 - 10 %
				             0101 - >= 15 % 

                        bit 6 : Power LED
				              0 - OFF; 1 - ON 
                        bit 7 : Switch LED
				              0 - OFF; 1 - ON 


           
            BYTE 30 :SNMP agent & switch status

                      bit 0:  internal switch bit 
                              0 - not exist; 1 - exist
					  bit 1:  internal switch status
                              0 - inactive; 1 - active
                      bit 2:  expension switch bit
                      		  0 - bad; 1 - good
                      bit 3:  expension switch status
                              0 - inactive; 1 - active  
                      bit 4:  agent bit
                              0 - not exist; 1 - exist
                      bit 5 : master status
				              0 - Slave; 1 - Master 
                      bit 6 - 7 : reserved 						
                              
			BYTE 31 : Rmon status
					  bit 0 : rmon bit 
                              0 - not exist; 1 - exist                               
                      bit 1 - 2 :rmon segment
                              00 - all stack 
							  01 - segment tenMb
							  10 - segment onehundredMb
							  11 - reserved
							                                 
                      bit 3 - 5 : RMON group Status
                              000 - not-present
							  001 - disabled
                              010 - Rmon-4Group
                              011 - Rmon-7Group
                              100 - Rmon-all
							  101 to 111 - reserved

					  bit 6 -7 : reserved

                              

            BYTE 32 : Hub Position(Hub ID)/Bus Termination 

                     bit 0 - 3 : hub position 

                              0000 - invalid
                              0001 - 1
                              0010 - 2
                              0011 - 3
                              0100 - 4
                              0101 - 5
                              0110 - 6
                              0111 - 7
                              1000 - 8                              
                              1001 to 1111 - reserved

                     bit 4 : termination status
                              0 - not end hub
                              1 - end hub in the stack
                     
                     bit 5 - 7 : reserved"

                ::= { fh800uStackInfo 14 }

--   Basic Group Object   --
--   Def                  --


fh800uGroupInfo       OBJECT IDENTIFIER ::=  { fh800uBasicCapability 2 }


        groupTable       OBJECT-TYPE
                SYNTAX  SEQUENCE OF GroupEntry
                ACCESS  not-accessible
                STATUS  mandatory
                DESCRIPTION   "A group means a hub unit"
                ::= { fh800uGroupInfo 1 }

        groupEntry       OBJECT-TYPE
                SYNTAX  GroupEntry
                ACCESS  not-accessible
                STATUS  mandatory
DESCRIPTION ""
                INDEX   { groupID }
                ::= { groupTable 1 }

        GroupEntry       ::= SEQUENCE {
                groupID
                        INTEGER,
                groupType
                        INTEGER,
                groupCounterReset
                        INTEGER,
                groupPosition
                        INTEGER,
                groupRptrHwVer
                        INTEGER,
				groupRptrSerialNo
						PhysAddress,
                groupSysMajorVer
                        INTEGER,
                groupSysMinorVer
                        INTEGER,
                groupPostCodeMajorVer
                        INTEGER,
                groupPostCodeMinorVer
                        INTEGER,
				groupAgentStatus
                        INTEGER,
				groupAgentHwVer
                        INTEGER,
				groupAgentSerialNo
						PhysAddress,
                groupAgentPhysAddr
                        PhysAddress,
                groupAgentBootupOption
                        INTEGER,
                groupAgentBaudrate
                        INTEGER
               }

        groupID                 OBJECT-TYPE
                SYNTAX  INTEGER (1..255)
                ACCESS  read-only
                STATUS  mandatory
                DESCRIPTION
                        "The ID number of a hub unit, used to select it"
                ::= { groupEntry 1 }

        groupType               OBJECT-TYPE
                SYNTAX  INTEGER {
                                fh824u(1),
                                fh812u(2),
                                eh3024a(3),
                                eh3012a(4) 
                        }
                ACCESS  read-only
                STATUS  mandatory
                DESCRIPTION
                        "Type of hub unit"
                ::= { groupEntry 2 }

        
         groupCounterReset        OBJECT-TYPE
                SYNTAX  INTEGER {
								  noReset(1),
                                  reset(2)
                                }
                ACCESS  read-write
                STATUS  mandatory
                DESCRIPTION
                        "Write any value to this variable to reset the
                         counters of the hub unit. 2 is a value commonly
                         used to reset things"
                ::= { groupEntry 3 }

         groupPosition           OBJECT-TYPE
                SYNTAX  INTEGER
                ACCESS  read-only
                STATUS  mandatory
                DESCRIPTION
                        "Physical position of a hub unit in top-down order,
                         only supported if hardware permits such as
                         Dual-Speed Hub systems"
                ::= { groupEntry 4 }

         groupRptrHwVer OBJECT-TYPE
                SYNTAX  INTEGER
                ACCESS  read-only
                STATUS  mandatory
                DESCRIPTION  "Hardware version of the repeater board."
                ::= { groupEntry 5 }

		groupRptrSerialNo OBJECT-TYPE
                SYNTAX  PhysAddress 
                ACCESS  read-only
                STATUS  mandatory
                DESCRIPTION  "Serial number of the repeater board."
                ::= { groupEntry 6 }

        groupSysMajorVer OBJECT-TYPE
                SYNTAX  INTEGER
                ACCESS  read-only
                STATUS  mandatory
                DESCRIPTION  "Microcode major version of this hub."
                ::= { groupEntry 7 }

        groupSysMinorVer OBJECT-TYPE
               SYNTAX  INTEGER
               ACCESS  read-only
               STATUS  mandatory
               DESCRIPTION  "Microcode minor version of this hub."
               ::= { groupEntry 8 }

    
        groupPostCodeMajorVer OBJECT-TYPE
              SYNTAX  INTEGER
              ACCESS  read-only
              STATUS  mandatory
              DESCRIPTION  "POST microcode major version of this hub."
              ::= { groupEntry 9 }

        groupPostCodeMinorVer OBJECT-TYPE
              SYNTAX  INTEGER
              ACCESS  read-only
              STATUS  mandatory
              DESCRIPTION  "POST microcode minor version of this hub."
              ::= { groupEntry 10 }


        groupAgentStatus OBJECT-TYPE
              SYNTAX  INTEGER {
                              not-present(1),
                              primary(2),
                              backup(3)
                              }
             ACCESS  read-only
             STATUS  mandatory
             DESCRIPTION  "Status of this hub agent.  Each stack allows
                           an SNMP primary agent.
                           primary(2): The agent in this stack is a primary agent.
                           backup(3): The agent in this stack is a backup agent."
             ::= { groupEntry 11 }

		groupAgentHwVer OBJECT-TYPE
                SYNTAX  INTEGER
                ACCESS  read-only
                STATUS  mandatory
                DESCRIPTION  "Hardware version of the agent board."
                ::= { groupEntry 12 }

		groupAgentSerialNo OBJECT-TYPE
                SYNTAX  PhysAddress 
                ACCESS  read-only
                STATUS  mandatory
                DESCRIPTION  "Serial number of the agent board."
                ::= { groupEntry 13 }

        groupAgentPhysAddr OBJECT-TYPE
              SYNTAX  PhysAddress
              ACCESS  read-only
              STATUS  mandatory
              DESCRIPTION  "MAC address of this hub agent"
             ::= { groupEntry 14 }

        groupAgentBootupOption OBJECT-TYPE
             SYNTAX  INTEGER {
                              normal(1),
                              tftp-download(2),
                              bootp-get-ip(3),
                              bootp-download(4),
                              bootp-upgrade(5) 
                             }
             ACCESS  read-write
             STATUS  mandatory
             DESCRIPTION  "This variable defines how to start the microcode
                           in the segment.
                           normal(1):  Use NVRAM information and flash ROM
                                       microcode to start up the system.
                           tftp-download(2):
                                       Always download the new version of
                                       microcode into RAM and start it.
                           bootp-get-ip(3):
                                       Get the IP information from the BootP                 
                                       server, and then start up the microcode in  
                                       flash ROM.
                           bootp-download(4):
                                       Get the IP information from the BootP 
                                       server, and then download the microcode from 
                                       the TFTP server.
                           bootp-upgrade(5):
                                       Get the IP information from the BootP 
                                       server, and then download the microcode from 
                                       the TFTP server.  After the download has 
                                       been completed, upgrade the microcode in  
                                       system flash ROM."


              ::= { groupEntry 15 }

         groupAgentBaudrate OBJECT-TYPE
              SYNTAX  INTEGER {
                               baud-9600(1),
						       baud-14400(2),
                               baud-19200(3),
                               baud-38400(4),
						       baud-57600(5),
						       baud-115200(6)
                               }
             ACCESS  read-write
             STATUS  mandatory
             DESCRIPTION  "Baud rate of the console port"
             ::= { groupEntry 16 } 

			

--   Port Object     --
--  Def                   --


fh800uPortInfo       OBJECT IDENTIFIER ::=  { fh800uBasicCapability 3 }


        portTable        OBJECT-TYPE
                SYNTAX  SEQUENCE OF PortEntry
                ACCESS  not-accessible
                STATUS  mandatory
                DESCRIPTION
                        " information about ports in a system.
                        Each port belongs to a group."
                ::= { fh800uPortInfo 1 }


        portEntry        OBJECT-TYPE
                SYNTAX  PortEntry
                ACCESS  not-accessible
                STATUS  mandatory
DESCRIPTION ""
                INDEX   { portGroupID, portID }
                ::= { portTable 1 }
						  
        PortEntry        ::= SEQUENCE {
                portGroupID
                        INTEGER,
                portID
                        INTEGER,
                portSpeed
                        INTEGER,
                portSpeedConfig
                        INTEGER,               
				portSegmtID
						INTEGER 
                }

-- Var

        portGroupID        OBJECT-TYPE
                SYNTAX  INTEGER ( 1..255 )
                ACCESS  read-only
                STATUS  mandatory
                DESCRIPTION
                        "ID of the hub unit"
                ::= { portEntry 1 }

        portID             OBJECT-TYPE
                SYNTAX  INTEGER ( 1..255 )
                ACCESS  read-only
                STATUS  mandatory
                DESCRIPTION
                        "ID of the port unit"
                ::= { portEntry 2 }

        portSpeed                OBJECT-TYPE
                SYNTAX  INTEGER {
								tenMb(1),        
                				onehundredMbClassI(2),     
                                onehundredMbClassII(3),
								other(4)
                                }
                ACCESS  read-only
                STATUS  mandatory
                DESCRIPTION
                        "Ethernet connector type of a port"
                ::= { portEntry 3 }

        portSpeedConfig                OBJECT-TYPE
                SYNTAX  INTEGER {
                                tenMb(1),        
								onehundredMbClassI(2),     
                                onehundredMbClassII(3),
                				autoDetected(4)
                                }
                ACCESS  read-write
                STATUS  mandatory
                DESCRIPTION
                        "Select the Ethernet connector type of a port"
                ::= { portEntry 4 }
								        
		portSegmtID             OBJECT-TYPE
                SYNTAX  INTEGER ( 1..255 )
                ACCESS  read-only
                STATUS  mandatory
                DESCRIPTION
                        " ID of the Segment unit"
                ::= { portEntry 5 }

--    Segment Object   --

--   Def		  --

fh800uSegmentInfo       OBJECT IDENTIFIER ::=  { fh800uBasicCapability 4 }

	    fh800uRmonConfig  OBJECT IDENTIFIER ::= { fh800uBasicCapability 5 }
	       	
    	nicAttachSegment OBJECT-TYPE
        		SYNTAX  INTEGER ( 0..255 )
        		ACCESS  read-write
        		STATUS  mandatory
        		DESCRIPTION  "The value represents the segment that the NIC is 
        				attached to."
        		::= { fh800uRmonConfig 1 }


    	fullRmonSegment OBJECT-TYPE
        		SYNTAX  INTEGER {
                         enabled(1),
                         disabled(2)
                        }

        		ACCESS  read-write
        		STATUS  mandatory
        		DESCRIPTION  "The value shows if the segment supports all rmon or 
        					only 4 rmon groups."
        		::= { fh800uRmonConfig 2 }

		rmonConfigTable OBJECT-TYPE
        		SYNTAX  SEQUENCE OF RmonConfigEntry
       			ACCESS  not-accessible
        		STATUS  mandatory
        		DESCRIPTION  "RMON configuration table information; the index is the 
        					ID of of the segment the rmon montioring ."

			  ::= { fh800uRmonConfig 3 }

		rmonConfigEntry OBJECT-TYPE
        		SYNTAX  RmonConfigEntry
        		ACCESS  not-accessible
        		STATUS  mandatory
DESCRIPTION ""
        		INDEX   { rmonConfigSegmtID }
        		::= { rmonConfigTable 1 }

		RmonConfigEntry ::= SEQUENCE
        {
            rmonConfigSegmtID
                INTEGER,
            rmonConfigStatus
                INTEGER
        }

		rmonConfigSegmtID             OBJECT-TYPE
                SYNTAX  INTEGER ( 1..255 )
                ACCESS  read-only
                STATUS  mandatory
                DESCRIPTION
                        " ID of the Segment rmon is montioring."
                ::= { rmonConfigEntry 1 }
		
		rmonConfigStatus OBJECT-TYPE
        		SYNTAX  INTEGER {
                         enabled(1),
                         disabled(2)
                        }
        		ACCESS  read-write
        		STATUS  mandatory
        		DESCRIPTION  "Status of this RMON segment."
        		::= { rmonConfigEntry 2 }



     	     
--  PERF MONITOR CAP GROUP --
-- Perf. Mon. Segment Table --

fh800uPerfMonSegmentInfo    OBJECT IDENTIFIER ::= { fh800uPerfMonCapability 3 }



		perfMonSegmentTable		OBJECT-TYPE
				SYNTAX	SEQUENCE OF PerfMonSegmentEntry
				ACCESS	not-accessible
				STATUS	optional
DESCRIPTION ""
				::= { fh800uPerfMonSegmentInfo 1 }

		perfMonSegmentEntry		OBJECT-TYPE
				SYNTAX	PerfMonSegmentEntry
				ACCESS	not-accessible
				STATUS	mandatory
DESCRIPTION ""
				INDEX	{ segmentPerfID }
				::= { perfMonSegmentTable 1 }

		PerfMonSegmentEntry	::= SEQUENCE {
	       		segmentPerfID
					INTEGER,
	       		segmentCRCErrors
					Counter,
	       		segmentAlignmentErrors
					Counter,
				segmentCollisions
					Counter,
	       		segmentTotalPortIsolates
					Counter,
				segmentSymbolErrors
					Counter
		}

		segmentPerfID		OBJECT-TYPE
				SYNTAX  INTEGER ( 1..255 )
				ACCESS	read-only
				STATUS	mandatory
				DESCRIPTION	"ID used to select a segment"
				::= { perfMonSegmentEntry 1 }

		segmentCRCErrors	OBJECT-TYPE
				SYNTAX	Counter
				ACCESS	read-only
				STATUS	mandatory
				DESCRIPTION  "Total CRC errors received by a segment."
				::= { perfMonSegmentEntry 2 }

		segmentAlignmentErrors	OBJECT-TYPE
				SYNTAX	Counter			
				ACCESS	read-only
				STATUS	mandatory
				DESCRIPTION  "Total frame alignment errors received by a
			      segment"
				::= { perfMonSegmentEntry 3 }

		segmentCollisions	OBJECT-TYPE
				SYNTAX	Counter
				ACCESS	read-only
				STATUS	mandatory
				DESCRIPTION	"Total collisions received in a segment"
			::= { perfMonSegmentEntry 4 }

		segmentTotalPortIsolates       OBJECT-TYPE
                SYNTAX  Counter
                ACCESS  read-only
                STATUS  mandatory
                DESCRIPTION     " Total isolated ports in a segment. "
                ::= { perfMonSegmentEntry 5 }

		segmentSymbolErrors   OBJECT-TYPE
                SYNTAX  Counter
                ACCESS  read-only
                STATUS  mandatory
                DESCRIPTION     "Total frame symbol errors received by a segment "
                ::= { perfMonSegmentEntry 6 }

-- -- -- -- -- -- -- -- -- -- -- -- -- -- -- -- -- -- -- -- -- -- -- -- -- --
-- -- -- -- -- -- -- -- -- -- -- -- -- -- -- -- -- -- -- -- -- -- -- -- -- --
--
--  SwitchPortStatsTable
--
-- -- -- -- -- -- -- -- -- -- -- -- -- -- -- -- -- -- -- -- -- -- -- -- -- --
-- -- -- -- -- -- -- -- -- -- -- -- -- -- -- -- -- -- -- -- -- -- -- -- -- --

fh800uSwitchStatsInfo    OBJECT IDENTIFIER ::=  { fh800uSwitchCapability 1 }

switchPortStatsTable OBJECT-TYPE
    SYNTAX      SEQUENCE OF SwitchPortStatsEntry
    ACCESS      not-accessible
    STATUS      mandatory
    DESCRIPTION
        "This table provides statistics on each port on each switch
        module in the stack.  Note that statistics for the external
        port on media and switch/media modules are unavailable to the
        agent and are reported as 0.  Statistics for port 2 (the internal
        10Mbps port) on media modules are also reported as 0."
    ::= { fh800uSwitchStatsInfo 1 }

switchPortStatsEntry OBJECT-TYPE
    SYNTAX      SwitchPortStatsEntry
    ACCESS      not-accessible
    STATUS      mandatory
DESCRIPTION ""
    INDEX       { switchPortStatsGroupID, switchPortStatsID }
    ::= { switchPortStatsTable 1 }

SwitchPortStatsEntry ::= SEQUENCE {
    switchPortStatsGroupID
        INTEGER,
    switchPortStatsID
        INTEGER,
    switchPortReadableFrames
        Counter,
    switchPortReadableOctets
        Counter,
    switchPortFCSErrors
        Counter,
    switchPortAlignmentErrors
        Counter,
    switchPortFramesTooLong
        Counter,
    switchPortShortEvents
        Counter,
    switchPortRunts
        Counter,
    switchPortCollisions
        Counter,
    switchPortLateEvents
        Counter,
    switchPortVeryLongEvents
        Counter,
    switchPortDataRateMismatches
        Counter,
    switchPortBroadcastPackets
        Counter,
    switchPortMulticastPackets
        Counter
}

switchPortStatsGroupID OBJECT-TYPE
    SYNTAX      INTEGER
    ACCESS      read-only
    STATUS      mandatory
    DESCRIPTION
        "The group ID of the switch module port being referenced.  If the
        group is not present, or if there is no switch module installed
        in the group, GetRequests and SetRequests are rejected with an
        error-status of noSuchName(2).  GetNextRequests skip entries for
        nonexistent modules."
    ::= { switchPortStatsEntry 1 }

switchPortStatsID OBJECT-TYPE
    SYNTAX      INTEGER (1..3)
    ACCESS      read-only
    STATUS      mandatory
    DESCRIPTION
        "The port ID of the switch module port being referenced.  Port 1 is
        always the internal 100Mbps port.  Port 2 is always the internal
        10Mbps port.  Port 3 is always the external port.  Note that port
        2 is inactive on media modules and port 3 is inactive on internal
        switch modules.

        Note:  Statistics for the external port are unavailable to the
        agent and are reported as 0."
    ::= { switchPortStatsEntry 2 }

switchPortReadableFrames OBJECT-TYPE
    SYNTAX      Counter
    ACCESS      read-only
    STATUS      mandatory
    DESCRIPTION
        "The number of valid frames received by the port."
    ::= { switchPortStatsEntry 3 }

switchPortReadableOctets OBJECT-TYPE
    SYNTAX      Counter
    ACCESS      read-only
    STATUS      mandatory
    DESCRIPTION
        "The number of octets (bytes) in all valid frames received
        by the port."
    ::= { switchPortStatsEntry 4 }

switchPortFCSErrors OBJECT-TYPE
    SYNTAX      Counter
    ACCESS      read-only
    STATUS      mandatory
    DESCRIPTION
        "The number of valid-length frames received by the port that
        had FCS (frame check sequence) errors."
    ::= { switchPortStatsEntry 5 }

switchPortAlignmentErrors OBJECT-TYPE
    SYNTAX      Counter
    ACCESS      read-only
    STATUS      mandatory
    DESCRIPTION
        "The number of valid-length frames received by the port that
        had alignment errors."
    ::= { switchPortStatsEntry 6 }

switchPortFramesTooLong OBJECT-TYPE
    SYNTAX      Counter
    ACCESS      read-only
    STATUS      mandatory
    DESCRIPTION
        "The number of frames received by the port that were longer
        than 1518 bytes."
    ::= { switchPortStatsEntry 7 }

switchPortShortEvents OBJECT-TYPE
    SYNTAX      Counter
    ACCESS      read-only
    STATUS      mandatory
    DESCRIPTION
        "The number of frames received by the port that were shorter
        than 82 bits."
    ::= { switchPortStatsEntry 8 }

switchPortRunts OBJECT-TYPE
    SYNTAX      Counter
    ACCESS      read-only
    STATUS      mandatory
    DESCRIPTION
        "The number of frames received by the port that were longer
        than 82 bits but shorter than 512 bits (64 bytes)."
    ::= { switchPortStatsEntry 9 }

switchPortCollisions OBJECT-TYPE
    SYNTAX      Counter
    ACCESS      read-only
    STATUS      mandatory
    DESCRIPTION
        "The number of collisions detected on the port."
    ::= { switchPortStatsEntry 10 }

switchPortLateEvents OBJECT-TYPE
    SYNTAX      Counter
    ACCESS      read-only
    STATUS      mandatory
    DESCRIPTION
        "The number of collisions detected on the port that occurred
        later than 512 bit-times into the transmission of a packet."
    ::= { switchPortStatsEntry 11 }

switchPortVeryLongEvents OBJECT-TYPE
    SYNTAX      Counter
    ACCESS      read-only
    STATUS      mandatory
    DESCRIPTION
        "The number of times any activity continued for more than
        4 to 7.5 milliseconds."
    ::= { switchPortStatsEntry 12 }

switchPortDataRateMismatches OBJECT-TYPE
    SYNTAX      Counter
    ACCESS      read-only
    STATUS      mandatory
    DESCRIPTION
        "The number of times the incoming data rate mismatched the local
        clock source enough to cause a FIFO overflow or underflow."
    ::= { switchPortStatsEntry 13 }

switchPortBroadcastPackets OBJECT-TYPE
    SYNTAX      Counter
    ACCESS      read-only
    STATUS      mandatory
    DESCRIPTION
        "The number of good broadcast frames received by the port."
    ::= { switchPortStatsEntry 14 }

switchPortMulticastPackets OBJECT-TYPE
    SYNTAX      Counter
    ACCESS      read-only
    STATUS      mandatory
    DESCRIPTION
        "The number of good multicast (not broadcast) frames received
        by the port."
    ::= { switchPortStatsEntry 15 }





--
--- backup port group
--

--fh800eBackupInfo OBJECT IDENTIFIER ::= { fh800eBackupCapability 1 }
--
--
--
--  backupPortTableSize OBJECT-TYPE
--      SYNTAX  INTEGER
--      ACCESS  read-only
--      STATUS  mandatory
--        DESCRIPTION  "Table size of backup port pairs."
--        ::= { fh800eBackupInfo 1 }
--
--    backupPortTable OBJECT-TYPE
--        SYNTAX  SEQUENCE OF BackupPortEntry
--        ACCESS  not-accessible
--        STATUS  mandatory
--        ::=  { fh800eBackupInfo 2 }
--
--    backupPortEntry OBJECT-TYPE
--        SYNTAX  BackupPortEntry
--        ACCESS  not-accessible
--        STATUS  mandatory
--        INDEX   { backupIndex }
--        ::=  { backupPortTable 1 }
--
--    BackupPortEntry ::= SEQUENCE
--        {
--            backupIndex
--                INTEGER,
--            backupPriPortGroup
--                INTEGER,
--            backupPriPortPort
--                INTEGER,
--            backupSecPortGroup
--                INTEGER,
--            backupSecPortPort
--                INTEGER,
--            backupPortAction
--                INTEGER
--        }
--
--    backupIndex OBJECT-TYPE
--        SYNTAX  INTEGER (1..18)
--        ACCESS  read-only
--        STATUS  mandatory
--        DESCRIPTION  "Backup table index."
--        ::= { backupPortEntry 1 }
--
--    backupPriPortGroup OBJECT-TYPE
--        SYNTAX  INTEGER (1..255)
--        ACCESS  read-write
--        STATUS  mandatory
--        DESCRIPTION  "Hub ID of the primary port."
--        ::= { backupPortEntry 2 }
--
--    backupPriPortPort OBJECT-TYPE
--        SYNTAX  INTEGER (1..255)
--        ACCESS  read-write
--        STATUS  mandatory
--        DESCRIPTION  "Port number of the primary port."
--        ::= { backupPortEntry 3 }
--
--    backupSecPortGroup OBJECT-TYPE
--        SYNTAX  INTEGER (1..255)
--        ACCESS  read-write
--        STATUS  mandatory
--        DESCRIPTION  "Hub ID of the secondary port."
--        ::= { backupPortEntry 4 }
--
--    backupSecPortPort OBJECT-TYPE
--        SYNTAX  INTEGER (1..255)
--       ACCESS  read-write
--        STATUS  mandatory
--        DESCRIPTION  "Port number of the secondary port."
--        ::= { backupPortEntry 5 }
--
--    backupPortAction OBJECT-TYPE
--        SYNTAX  INTEGER {
--                         inactive(1),
--                         active(2),
--                         stand-by(3),
--                         backup(4)
--                        }
--        ACCESS  read-write
--        STATUS  mandatory
--        DESCRIPTION "Setting this object to inactive(1) disables the backup
--              port function for this backup port pair.  Setting this object
--              to active(2) will disable the secondary port and enable the
--              primary port.
--
--              When the backup port pair is activated, the backup status of
--              this port pair is reflected as stand-by(3) or backup(4).
--              Value stand-by(3) indicates that the primary port is okay
--              and enabled.  Value backup(4) means that the primary port has
--              failed and the secondary port has taken over.  After the
--              secondary port has taken over, setting this object to
--              active(2) will attempt to recover the primary port and
--              disable the secondary port.  Success here depends on the
--              ability to establish a good link on the primary port.
--
--              The values stand-by(3) and backup(4) are read-only.
--              Attempting to set this object to either of these two values
--              is not valid.  The result 'snmpBadValue' will be returned."
--        ::= { backupPortEntry 6 }
--



-- security group
-- Implementation of the security group is available for
-- systems that implement the hub security function.

-- security port

fh800uSecurityInfo OBJECT IDENTIFIER ::= { fh800uSecurityCapability 3 }


		securityPortTable	OBJECT-TYPE
				SYNTAX	SEQUENCE OF SecurityPortEntry
				ACCESS	not-accessible
				STATUS	mandatory
DESCRIPTION ""
				::=  { fh800uSecurityInfo 3 }

		securityPortEntry    OBJECT-TYPE
				SYNTAX	SecurityPortEntry
				ACCESS	not-accessible
				STATUS	mandatory
DESCRIPTION ""
				INDEX	{ securityPortGroupID, securityPortID }
				::=  { securityPortTable  1 }

		SecurityPortEntry ::= SEQUENCE {
				securityPortGroupID
							INTEGER,
				securityPortID
							INTEGER,
				securityPortAddr
							PhysAddress,
				securityAutoLearnAction
                			INTEGER,
				securityPortIntrusion
							INTEGER  
				}

		securityPortGroupID	OBJECT-TYPE
				SYNTAX	INTEGER
				ACCESS	read-only
				STATUS	mandatory
				DESCRIPTION    "ID of a hub unit"
				::= { securityPortEntry 1 }

		securityPortID		OBJECT-TYPE
				SYNTAX	INTEGER
				ACCESS	read-only
				STATUS	mandatory
				DESCRIPTION    "Port ID in a hub unit"
				::= { securityPortEntry 2 }

		securityPortAddr	OBJECT-TYPE
				SYNTAX	PhysAddress
				ACCESS	read-write
				STATUS	mandatory
				DESCRIPTION    "MAC address"
				::= { securityPortEntry 3 }

		securityAutoLearnAction OBJECT-TYPE
        		SYNTAX  INTEGER {
                         inactive(1),
                         active(2),
                         learned(3)
                        }
       			ACCESS  read-write
        		STATUS  mandatory
       			DESCRIPTION "Setting this object to inactive(1) disables the
              				auto-learn function for the physical address authorized access
              				to this port.  Once this object is set to active(2), the agent
              				will set the authorized address to 0 first and then start the
              				auto-learn process, and the hub will begin to read the source
              				address of the first incoming error-free frame.  The source
              				address obtained will become the authorized address and the
              				object securityAuthorizedAddr will be changed accordingly.
              				When the authorized address has been learned successfully, the
              				status of this port will be reflected as learned(3).  Otherwise
              				the status will remain as active(2).
              				Setting to the last value, learned(3), is not acceptable;
              				'snmpBadValue' will be returned."
        				::= { securityPortEntry 5 }

		securityPortIntrusion OBJECT-TYPE
				SYNTAX	INTEGER   {
						inactive(1),
						warning-and-disable(2)
			   			}
				ACCESS	read-write
				STATUS	mandatory
				DESCRIPTION  "Set this variable to set function active
							or inactive"
				::= { securityPortEntry 6 }


	   	fh800uIntrusionHappen			TRAP-TYPE
		 		ENTERPRISE	atactDualHubMgt 
				VARIABLES	{ 
			 				securityPortIntrusion,
			  				securityPortGroupID,
			  				securityPortID 
			 				}
			  	DESCRIPTION	"There were some intruders on some port in this system"
		  		::= 1
 
--		masterLinkFailEvent TRAP-TYPE                
--        		ENTERPRISE  cheetahHubMgt
--        		VARIABLES   { 
--        					backupPriPortGroup, 
--        					backupPriPortPort,
--                      		backupSecPortGroup, 
--                      		backupSecPortPort 
--                      		}
--        		DESCRIPTION "The primary port has failed, and the secondary port
--                     		has been activated."
--        		::= 3


END
