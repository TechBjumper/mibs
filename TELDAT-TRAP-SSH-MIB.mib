-- file automatically created


TELDAT-TRAP-SSH-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sshTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SSH event subsystem."
    REVISION "201401200930Z"
    DESCRIPTION "Initial implementation"
        ::= { telEventTraps 215 }


sshEventsGroup	OBJECT IDENTIFIER	::= { sshTrapsMIB 1 }

sshNotifications	OBJECT IDENTIFIER	::= { sshTrapsMIB 2 }
sshNotificationsPrefix	OBJECT IDENTIFIER	::= { sshNotifications 0 }

sshEventObjects2 OBJECT-IDENTITY
    STATUS current
    DESCRIPTION
        "Event SSH.2
        Verbose info from a global SSH function."
    ::= { sshEventsGroup 2 }

ssh2-description OBJECT-TYPE
    SYNTAX DisplayString
    MAX-ACCESS accessible-for-notify
    STATUS current
    DESCRIPTION
        "Parameter 'description' in event SSH.2"
    ::= { sshEventObjects2 1 }

sshEventObjects3 OBJECT-IDENTITY
    STATUS current
    DESCRIPTION
        "Event SSH.3
        Error found in a global SSH function."
    ::= { sshEventsGroup 3 }

ssh3-description OBJECT-TYPE
    SYNTAX DisplayString
    MAX-ACCESS accessible-for-notify
    STATUS current
    DESCRIPTION
        "Parameter 'description' in event SSH.3"
    ::= { sshEventObjects3 1 }

sshEventObjects4 OBJECT-IDENTITY
    STATUS current
    DESCRIPTION
        "Event SSH.4
        Event related to task creation/deletion."
    ::= { sshEventsGroup 4 }

ssh4-description OBJECT-TYPE
    SYNTAX DisplayString
    MAX-ACCESS accessible-for-notify
    STATUS current
    DESCRIPTION
        "Parameter 'description' in event SSH.4"
    ::= { sshEventObjects4 1 }

ssh4-task OBJECT-TYPE
    SYNTAX DisplayString
    MAX-ACCESS accessible-for-notify
    STATUS current
    DESCRIPTION
        "Parameter 'task' in event SSH.4"
    ::= { sshEventObjects4 2 }

sshEventObjects5 OBJECT-IDENTITY
    STATUS current
    DESCRIPTION
        "Event SSH.5
        Error related to task creation/deletion."
    ::= { sshEventsGroup 5 }

ssh5-error OBJECT-TYPE
    SYNTAX DisplayString
    MAX-ACCESS accessible-for-notify
    STATUS current
    DESCRIPTION
        "Parameter 'error' in event SSH.5"
    ::= { sshEventObjects5 1 }

ssh5-task OBJECT-TYPE
    SYNTAX DisplayString
    MAX-ACCESS accessible-for-notify
    STATUS current
    DESCRIPTION
        "Parameter 'task' in event SSH.5"
    ::= { sshEventObjects5 2 }

sshEventObjects6 OBJECT-IDENTITY
    STATUS current
    DESCRIPTION
        "Event SSH.6
        Event related to server initialization."
    ::= { sshEventsGroup 6 }

ssh6-description OBJECT-TYPE
    SYNTAX DisplayString
    MAX-ACCESS accessible-for-notify
    STATUS current
    DESCRIPTION
        "Parameter 'description' in event SSH.6"
    ::= { sshEventObjects6 1 }

sshEventObjects7 OBJECT-IDENTITY
    STATUS current
    DESCRIPTION
        "Event SSH.7
        Error related to server initialization."
    ::= { sshEventsGroup 7 }

ssh7-description OBJECT-TYPE
    SYNTAX DisplayString
    MAX-ACCESS accessible-for-notify
    STATUS current
    DESCRIPTION
        "Parameter 'description' in event SSH.7"
    ::= { sshEventObjects7 1 }

sshEventObjects8 OBJECT-IDENTITY
    STATUS current
    DESCRIPTION
        "Event SSH.8
        Verbose event related to server initialization."
    ::= { sshEventsGroup 8 }

ssh8-description OBJECT-TYPE
    SYNTAX DisplayString
    MAX-ACCESS accessible-for-notify
    STATUS current
    DESCRIPTION
        "Parameter 'description' in event SSH.8"
    ::= { sshEventObjects8 1 }

sshEventObjects9 OBJECT-IDENTITY
    STATUS current
    DESCRIPTION
        "Event SSH.9
        Event related to hostkey loading/generation."
    ::= { sshEventsGroup 9 }

ssh9-hostkey-type OBJECT-TYPE
    SYNTAX DisplayString
    MAX-ACCESS accessible-for-notify
    STATUS current
    DESCRIPTION
        "Parameter 'hostkey-type' in event SSH.9"
    ::= { sshEventObjects9 1 }

ssh9-description OBJECT-TYPE
    SYNTAX DisplayString
    MAX-ACCESS accessible-for-notify
    STATUS current
    DESCRIPTION
        "Parameter 'description' in event SSH.9"
    ::= { sshEventObjects9 2 }

sshEventObjects10 OBJECT-IDENTITY
    STATUS current
    DESCRIPTION
        "Event SSH.10
        Warning: Hostkey not found in config."
    ::= { sshEventsGroup 10 }

ssh10-hostkey-type OBJECT-TYPE
    SYNTAX DisplayString
    MAX-ACCESS accessible-for-notify
    STATUS current
    DESCRIPTION
        "Parameter 'hostkey-type' in event SSH.10"
    ::= { sshEventObjects10 1 }

sshEventObjects11 OBJECT-IDENTITY
    STATUS current
    DESCRIPTION
        "Event SSH.11
        Verbose information about key generation process."
    ::= { sshEventsGroup 11 }

ssh11-description OBJECT-TYPE
    SYNTAX DisplayString
    MAX-ACCESS accessible-for-notify
    STATUS current
    DESCRIPTION
        "Parameter 'description' in event SSH.11"
    ::= { sshEventObjects11 1 }

sshEventObjects12 OBJECT-IDENTITY
    STATUS current
    DESCRIPTION
        "Event SSH.12
        Error found during key generation process."
    ::= { sshEventsGroup 12 }

ssh12-description OBJECT-TYPE
    SYNTAX DisplayString
    MAX-ACCESS accessible-for-notify
    STATUS current
    DESCRIPTION
        "Parameter 'description' in event SSH.12"
    ::= { sshEventObjects12 1 }

sshEventObjects15 OBJECT-IDENTITY
    STATUS current
    DESCRIPTION
        "Event SSH.15
        Important! Event related to a new connection with user id info."
    ::= { sshEventsGroup 15 }

ssh15-userid OBJECT-TYPE
    SYNTAX Integer32
    MAX-ACCESS accessible-for-notify
    STATUS current
    DESCRIPTION
        "Parameter 'userid' in event SSH.15"
    ::= { sshEventObjects15 1 }

ssh15-srvadd OBJECT-TYPE
    SYNTAX IpAddress
    MAX-ACCESS accessible-for-notify
    STATUS current
    DESCRIPTION
        "Parameter 'srvadd' in event SSH.15"
    ::= { sshEventObjects15 2 }

ssh15-srvport OBJECT-TYPE
    SYNTAX Integer32
    MAX-ACCESS accessible-for-notify
    STATUS current
    DESCRIPTION
        "Parameter 'srvport' in event SSH.15"
    ::= { sshEventObjects15 3 }

ssh15-cliadd OBJECT-TYPE
    SYNTAX IpAddress
    MAX-ACCESS accessible-for-notify
    STATUS current
    DESCRIPTION
        "Parameter 'cliadd' in event SSH.15"
    ::= { sshEventObjects15 4 }

ssh15-cliport OBJECT-TYPE
    SYNTAX Integer32
    MAX-ACCESS accessible-for-notify
    STATUS current
    DESCRIPTION
        "Parameter 'cliport' in event SSH.15"
    ::= { sshEventObjects15 5 }

sshEventObjects16 OBJECT-IDENTITY
    STATUS current
    DESCRIPTION
        "Event SSH.16
        A new connection was refused because of the reason"
    ::= { sshEventsGroup 16 }

ssh16-cliadd OBJECT-TYPE
    SYNTAX IpAddress
    MAX-ACCESS accessible-for-notify
    STATUS current
    DESCRIPTION
        "Parameter 'cliadd' in event SSH.16"
    ::= { sshEventObjects16 1 }

ssh16-cliport OBJECT-TYPE
    SYNTAX Integer32
    MAX-ACCESS accessible-for-notify
    STATUS current
    DESCRIPTION
        "Parameter 'cliport' in event SSH.16"
    ::= { sshEventObjects16 2 }

ssh16-reason OBJECT-TYPE
    SYNTAX DisplayString
    MAX-ACCESS accessible-for-notify
    STATUS current
    DESCRIPTION
        "Parameter 'reason' in event SSH.16"
    ::= { sshEventObjects16 3 }

sshEventObjects17 OBJECT-IDENTITY
    STATUS current
    DESCRIPTION
        "Event SSH.17
        Event related to a connection closing"
    ::= { sshEventsGroup 17 }

ssh17-userid OBJECT-TYPE
    SYNTAX Integer32
    MAX-ACCESS accessible-for-notify
    STATUS current
    DESCRIPTION
        "Parameter 'userid' in event SSH.17"
    ::= { sshEventObjects17 1 }

ssh17-srvadd OBJECT-TYPE
    SYNTAX IpAddress
    MAX-ACCESS accessible-for-notify
    STATUS current
    DESCRIPTION
        "Parameter 'srvadd' in event SSH.17"
    ::= { sshEventObjects17 2 }

ssh17-srvport OBJECT-TYPE
    SYNTAX Integer32
    MAX-ACCESS accessible-for-notify
    STATUS current
    DESCRIPTION
        "Parameter 'srvport' in event SSH.17"
    ::= { sshEventObjects17 3 }

ssh17-cliadd OBJECT-TYPE
    SYNTAX IpAddress
    MAX-ACCESS accessible-for-notify
    STATUS current
    DESCRIPTION
        "Parameter 'cliadd' in event SSH.17"
    ::= { sshEventObjects17 4 }

ssh17-cliport OBJECT-TYPE
    SYNTAX Integer32
    MAX-ACCESS accessible-for-notify
    STATUS current
    DESCRIPTION
        "Parameter 'cliport' in event SSH.17"
    ::= { sshEventObjects17 5 }

sshEventObjects18 OBJECT-IDENTITY
    STATUS current
    DESCRIPTION
        "Event SSH.18
        Verbose information about the connection."
    ::= { sshEventsGroup 18 }

ssh18-userid OBJECT-TYPE
    SYNTAX Integer32
    MAX-ACCESS accessible-for-notify
    STATUS current
    DESCRIPTION
        "Parameter 'userid' in event SSH.18"
    ::= { sshEventObjects18 1 }

ssh18-description OBJECT-TYPE
    SYNTAX DisplayString
    MAX-ACCESS accessible-for-notify
    STATUS current
    DESCRIPTION
        "Parameter 'description' in event SSH.18"
    ::= { sshEventObjects18 2 }

sshEventObjects19 OBJECT-IDENTITY
    STATUS current
    DESCRIPTION
        "Event SSH.19
        Error related to version incompatibility."
    ::= { sshEventsGroup 19 }

ssh19-userid OBJECT-TYPE
    SYNTAX Integer32
    MAX-ACCESS accessible-for-notify
    STATUS current
    DESCRIPTION
        "Parameter 'userid' in event SSH.19"
    ::= { sshEventObjects19 1 }

ssh19-description OBJECT-TYPE
    SYNTAX DisplayString
    MAX-ACCESS accessible-for-notify
    STATUS current
    DESCRIPTION
        "Parameter 'description' in event SSH.19"
    ::= { sshEventObjects19 2 }

sshEventObjects21 OBJECT-IDENTITY
    STATUS current
    DESCRIPTION
        "Event SSH.21
        SSH message received."
    ::= { sshEventsGroup 21 }

ssh21-userid OBJECT-TYPE
    SYNTAX Integer32
    MAX-ACCESS accessible-for-notify
    STATUS current
    DESCRIPTION
        "Parameter 'userid' in event SSH.21"
    ::= { sshEventObjects21 1 }

ssh21-msg-number OBJECT-TYPE
    SYNTAX Integer32
    MAX-ACCESS accessible-for-notify
    STATUS current
    DESCRIPTION
        "Parameter 'msg-number' in event SSH.21"
    ::= { sshEventObjects21 2 }

sshEventObjects22 OBJECT-IDENTITY
    STATUS current
    DESCRIPTION
        "Event SSH.22
        SSH message sent."
    ::= { sshEventsGroup 22 }

ssh22-userid OBJECT-TYPE
    SYNTAX Integer32
    MAX-ACCESS accessible-for-notify
    STATUS current
    DESCRIPTION
        "Parameter 'userid' in event SSH.22"
    ::= { sshEventObjects22 1 }

ssh22-msg-number OBJECT-TYPE
    SYNTAX Integer32
    MAX-ACCESS accessible-for-notify
    STATUS current
    DESCRIPTION
        "Parameter 'msg-number' in event SSH.22"
    ::= { sshEventObjects22 2 }

sshEventObjects23 OBJECT-IDENTITY
    STATUS current
    DESCRIPTION
        "Event SSH.23
        Message expected from peer."
    ::= { sshEventsGroup 23 }

ssh23-userid OBJECT-TYPE
    SYNTAX Integer32
    MAX-ACCESS accessible-for-notify
    STATUS current
    DESCRIPTION
        "Parameter 'userid' in event SSH.23"
    ::= { sshEventObjects23 1 }

ssh23-msg-number OBJECT-TYPE
    SYNTAX Integer32
    MAX-ACCESS accessible-for-notify
    STATUS current
    DESCRIPTION
        "Parameter 'msg-number' in event SSH.23"
    ::= { sshEventObjects23 2 }

sshEventObjects24 OBJECT-IDENTITY
    STATUS current
    DESCRIPTION
        "Event SSH.24
        Disconnection message received with reason code and explanation."
    ::= { sshEventsGroup 24 }

ssh24-userid OBJECT-TYPE
    SYNTAX Integer32
    MAX-ACCESS accessible-for-notify
    STATUS current
    DESCRIPTION
        "Parameter 'userid' in event SSH.24"
    ::= { sshEventObjects24 1 }

ssh24-reason-code OBJECT-TYPE
    SYNTAX Integer32
    MAX-ACCESS accessible-for-notify
    STATUS current
    DESCRIPTION
        "Parameter 'reason-code' in event SSH.24"
    ::= { sshEventObjects24 2 }

ssh24-description OBJECT-TYPE
    SYNTAX DisplayString
    MAX-ACCESS accessible-for-notify
    STATUS current
    DESCRIPTION
        "Parameter 'description' in event SSH.24"
    ::= { sshEventObjects24 3 }

sshEventObjects25 OBJECT-IDENTITY
    STATUS current
    DESCRIPTION
        "Event SSH.25
        Disconnection message sent with reason code and explanation."
    ::= { sshEventsGroup 25 }

ssh25-userid OBJECT-TYPE
    SYNTAX Integer32
    MAX-ACCESS accessible-for-notify
    STATUS current
    DESCRIPTION
        "Parameter 'userid' in event SSH.25"
    ::= { sshEventObjects25 1 }

ssh25-reason-code OBJECT-TYPE
    SYNTAX Integer32
    MAX-ACCESS accessible-for-notify
    STATUS current
    DESCRIPTION
        "Parameter 'reason-code' in event SSH.25"
    ::= { sshEventObjects25 2 }

ssh25-description OBJECT-TYPE
    SYNTAX DisplayString
    MAX-ACCESS accessible-for-notify
    STATUS current
    DESCRIPTION
        "Parameter 'description' in event SSH.25"
    ::= { sshEventObjects25 3 }

sshEventObjects26 OBJECT-IDENTITY
    STATUS current
    DESCRIPTION
        "Event SSH.26
        An ignore message has been rcvd/sent."
    ::= { sshEventsGroup 26 }

ssh26-userid OBJECT-TYPE
    SYNTAX Integer32
    MAX-ACCESS accessible-for-notify
    STATUS current
    DESCRIPTION
        "Parameter 'userid' in event SSH.26"
    ::= { sshEventObjects26 1 }

ssh26-description OBJECT-TYPE
    SYNTAX DisplayString
    MAX-ACCESS accessible-for-notify
    STATUS current
    DESCRIPTION
        "Parameter 'description' in event SSH.26"
    ::= { sshEventObjects26 2 }

sshEventObjects27 OBJECT-IDENTITY
    STATUS current
    DESCRIPTION
        "Event SSH.27
        A not implemented message has been received."
    ::= { sshEventsGroup 27 }

ssh27-userid OBJECT-TYPE
    SYNTAX Integer32
    MAX-ACCESS accessible-for-notify
    STATUS current
    DESCRIPTION
        "Parameter 'userid' in event SSH.27"
    ::= { sshEventObjects27 1 }

ssh27-direction OBJECT-TYPE
    SYNTAX DisplayString
    MAX-ACCESS accessible-for-notify
    STATUS current
    DESCRIPTION
        "Parameter 'direction' in event SSH.27"
    ::= { sshEventObjects27 2 }

sshEventObjects28 OBJECT-IDENTITY
    STATUS current
    DESCRIPTION
        "Event SSH.28
        Debug message rcvd/sent with debug info."
    ::= { sshEventsGroup 28 }

ssh28-userid OBJECT-TYPE
    SYNTAX Integer32
    MAX-ACCESS accessible-for-notify
    STATUS current
    DESCRIPTION
        "Parameter 'userid' in event SSH.28"
    ::= { sshEventObjects28 1 }

ssh28-rcvd-sent OBJECT-TYPE
    SYNTAX DisplayString
    MAX-ACCESS accessible-for-notify
    STATUS current
    DESCRIPTION
        "Parameter 'rcvd-sent' in event SSH.28"
    ::= { sshEventObjects28 2 }

ssh28-description OBJECT-TYPE
    SYNTAX DisplayString
    MAX-ACCESS accessible-for-notify
    STATUS current
    DESCRIPTION
        "Parameter 'description' in event SSH.28"
    ::= { sshEventObjects28 3 }

sshEventObjects31 OBJECT-IDENTITY
    STATUS current
    DESCRIPTION
        "Event SSH.31
        KEX proposal sent from server to client"
    ::= { sshEventsGroup 31 }

ssh31-userid OBJECT-TYPE
    SYNTAX Integer32
    MAX-ACCESS accessible-for-notify
    STATUS current
    DESCRIPTION
        "Parameter 'userid' in event SSH.31"
    ::= { sshEventObjects31 1 }

ssh31-proposal OBJECT-TYPE
    SYNTAX DisplayString
    MAX-ACCESS accessible-for-notify
    STATUS current
    DESCRIPTION
        "Parameter 'proposal' in event SSH.31"
    ::= { sshEventObjects31 2 }

sshEventObjects32 OBJECT-IDENTITY
    STATUS current
    DESCRIPTION
        "Event SSH.32
        KEX proposal sent from client to server"
    ::= { sshEventsGroup 32 }

ssh32-userid OBJECT-TYPE
    SYNTAX Integer32
    MAX-ACCESS accessible-for-notify
    STATUS current
    DESCRIPTION
        "Parameter 'userid' in event SSH.32"
    ::= { sshEventObjects32 1 }

ssh32-proposal OBJECT-TYPE
    SYNTAX DisplayString
    MAX-ACCESS accessible-for-notify
    STATUS current
    DESCRIPTION
        "Parameter 'proposal' in event SSH.32"
    ::= { sshEventObjects32 2 }

sshEventObjects33 OBJECT-IDENTITY
    STATUS current
    DESCRIPTION
        "Event SSH.33
        KEX decision made after comparing kexinit messages."
    ::= { sshEventsGroup 33 }

ssh33-userid OBJECT-TYPE
    SYNTAX Integer32
    MAX-ACCESS accessible-for-notify
    STATUS current
    DESCRIPTION
        "Parameter 'userid' in event SSH.33"
    ::= { sshEventObjects33 1 }

ssh33-decision OBJECT-TYPE
    SYNTAX DisplayString
    MAX-ACCESS accessible-for-notify
    STATUS current
    DESCRIPTION
        "Parameter 'decision' in event SSH.33"
    ::= { sshEventObjects33 2 }

sshEventObjects34 OBJECT-IDENTITY
    STATUS current
    DESCRIPTION
        "Event SSH.34
        Event related to verbose information about KEX."
    ::= { sshEventsGroup 34 }

ssh34-userid OBJECT-TYPE
    SYNTAX Integer32
    MAX-ACCESS accessible-for-notify
    STATUS current
    DESCRIPTION
        "Parameter 'userid' in event SSH.34"
    ::= { sshEventObjects34 1 }

ssh34-description OBJECT-TYPE
    SYNTAX DisplayString
    MAX-ACCESS accessible-for-notify
    STATUS current
    DESCRIPTION
        "Parameter 'description' in event SSH.34"
    ::= { sshEventObjects34 2 }

sshEventObjects35 OBJECT-IDENTITY
    STATUS current
    DESCRIPTION
        "Event SSH.35
        Event related to an error found during KEX."
    ::= { sshEventsGroup 35 }

ssh35-userid OBJECT-TYPE
    SYNTAX Integer32
    MAX-ACCESS accessible-for-notify
    STATUS current
    DESCRIPTION
        "Parameter 'userid' in event SSH.35"
    ::= { sshEventObjects35 1 }

ssh35-description OBJECT-TYPE
    SYNTAX DisplayString
    MAX-ACCESS accessible-for-notify
    STATUS current
    DESCRIPTION
        "Parameter 'description' in event SSH.35"
    ::= { sshEventObjects35 2 }

sshEventObjects36 OBJECT-IDENTITY
    STATUS current
    DESCRIPTION
        "Event SSH.36
        Diffie-Hellman message of a certain type has been received/sent."
    ::= { sshEventsGroup 36 }

ssh36-userid OBJECT-TYPE
    SYNTAX Integer32
    MAX-ACCESS accessible-for-notify
    STATUS current
    DESCRIPTION
        "Parameter 'userid' in event SSH.36"
    ::= { sshEventObjects36 1 }

ssh36-description OBJECT-TYPE
    SYNTAX DisplayString
    MAX-ACCESS accessible-for-notify
    STATUS current
    DESCRIPTION
        "Parameter 'description' in event SSH.36"
    ::= { sshEventObjects36 2 }

ssh36-direction OBJECT-TYPE
    SYNTAX DisplayString
    MAX-ACCESS accessible-for-notify
    STATUS current
    DESCRIPTION
        "Parameter 'direction' in event SSH.36"
    ::= { sshEventObjects36 3 }

sshEventObjects37 OBJECT-IDENTITY
    STATUS current
    DESCRIPTION
        "Event SSH.37
        SSHv1 Key Exchange message has been received/sent."
    ::= { sshEventsGroup 37 }

ssh37-userid OBJECT-TYPE
    SYNTAX Integer32
    MAX-ACCESS accessible-for-notify
    STATUS current
    DESCRIPTION
        "Parameter 'userid' in event SSH.37"
    ::= { sshEventObjects37 1 }

ssh37-direction OBJECT-TYPE
    SYNTAX DisplayString
    MAX-ACCESS accessible-for-notify
    STATUS current
    DESCRIPTION
        "Parameter 'direction' in event SSH.37"
    ::= { sshEventObjects37 2 }

ssh37-description OBJECT-TYPE
    SYNTAX DisplayString
    MAX-ACCESS accessible-for-notify
    STATUS current
    DESCRIPTION
        "Parameter 'description' in event SSH.37"
    ::= { sshEventObjects37 3 }

sshEventObjects38 OBJECT-IDENTITY
    STATUS current
    DESCRIPTION
        "Event SSH.38
        New keys are about to be used from now on."
    ::= { sshEventsGroup 38 }

ssh38-userid OBJECT-TYPE
    SYNTAX Integer32
    MAX-ACCESS accessible-for-notify
    STATUS current
    DESCRIPTION
        "Parameter 'userid' in event SSH.38"
    ::= { sshEventObjects38 1 }

ssh38-direction OBJECT-TYPE
    SYNTAX DisplayString
    MAX-ACCESS accessible-for-notify
    STATUS current
    DESCRIPTION
        "Parameter 'direction' in event SSH.38"
    ::= { sshEventObjects38 2 }

sshEventObjects39 OBJECT-IDENTITY
    STATUS current
    DESCRIPTION
        "Event SSH.39
        Periodic rekeying process after a period."
    ::= { sshEventsGroup 39 }

ssh39-userid OBJECT-TYPE
    SYNTAX Integer32
    MAX-ACCESS accessible-for-notify
    STATUS current
    DESCRIPTION
        "Parameter 'userid' in event SSH.39"
    ::= { sshEventObjects39 1 }

sshEventObjects41 OBJECT-IDENTITY
    STATUS current
    DESCRIPTION
        "Event SSH.41
        Service request name and direction."
    ::= { sshEventsGroup 41 }

ssh41-userid OBJECT-TYPE
    SYNTAX Integer32
    MAX-ACCESS accessible-for-notify
    STATUS current
    DESCRIPTION
        "Parameter 'userid' in event SSH.41"
    ::= { sshEventObjects41 1 }

ssh41-service OBJECT-TYPE
    SYNTAX DisplayString
    MAX-ACCESS accessible-for-notify
    STATUS current
    DESCRIPTION
        "Parameter 'service' in event SSH.41"
    ::= { sshEventObjects41 2 }

ssh41-direction OBJECT-TYPE
    SYNTAX DisplayString
    MAX-ACCESS accessible-for-notify
    STATUS current
    DESCRIPTION
        "Parameter 'direction' in event SSH.41"
    ::= { sshEventObjects41 3 }

sshEventObjects42 OBJECT-IDENTITY
    STATUS current
    DESCRIPTION
        "Event SSH.42
        Service request received/sent has not been accepted."
    ::= { sshEventsGroup 42 }

ssh42-userid OBJECT-TYPE
    SYNTAX Integer32
    MAX-ACCESS accessible-for-notify
    STATUS current
    DESCRIPTION
        "Parameter 'userid' in event SSH.42"
    ::= { sshEventObjects42 1 }

ssh42-service OBJECT-TYPE
    SYNTAX DisplayString
    MAX-ACCESS accessible-for-notify
    STATUS current
    DESCRIPTION
        "Parameter 'service' in event SSH.42"
    ::= { sshEventObjects42 2 }

sshEventObjects43 OBJECT-IDENTITY
    STATUS current
    DESCRIPTION
        "Event SSH.43
        Userauth request received/sent with parameters."
    ::= { sshEventsGroup 43 }

ssh43-userid OBJECT-TYPE
    SYNTAX Integer32
    MAX-ACCESS accessible-for-notify
    STATUS current
    DESCRIPTION
        "Parameter 'userid' in event SSH.43"
    ::= { sshEventObjects43 1 }

ssh43-direction OBJECT-TYPE
    SYNTAX DisplayString
    MAX-ACCESS accessible-for-notify
    STATUS current
    DESCRIPTION
        "Parameter 'direction' in event SSH.43"
    ::= { sshEventObjects43 2 }

ssh43-username OBJECT-TYPE
    SYNTAX DisplayString
    MAX-ACCESS accessible-for-notify
    STATUS current
    DESCRIPTION
        "Parameter 'username' in event SSH.43"
    ::= { sshEventObjects43 3 }

ssh43-service OBJECT-TYPE
    SYNTAX DisplayString
    MAX-ACCESS accessible-for-notify
    STATUS current
    DESCRIPTION
        "Parameter 'service' in event SSH.43"
    ::= { sshEventObjects43 4 }

ssh43-method OBJECT-TYPE
    SYNTAX DisplayString
    MAX-ACCESS accessible-for-notify
    STATUS current
    DESCRIPTION
        "Parameter 'method' in event SSH.43"
    ::= { sshEventObjects43 5 }

sshEventObjects44 OBJECT-IDENTITY
    STATUS current
    DESCRIPTION
        "Event SSH.44
        Register of userauth attempt and failures."
    ::= { sshEventsGroup 44 }

ssh44-userid OBJECT-TYPE
    SYNTAX Integer32
    MAX-ACCESS accessible-for-notify
    STATUS current
    DESCRIPTION
        "Parameter 'userid' in event SSH.44"
    ::= { sshEventObjects44 1 }

ssh44-attempt OBJECT-TYPE
    SYNTAX Integer32
    MAX-ACCESS accessible-for-notify
    STATUS current
    DESCRIPTION
        "Parameter 'attempt' in event SSH.44"
    ::= { sshEventObjects44 2 }

ssh44-failures OBJECT-TYPE
    SYNTAX Integer32
    MAX-ACCESS accessible-for-notify
    STATUS current
    DESCRIPTION
        "Parameter 'failures' in event SSH.44"
    ::= { sshEventObjects44 3 }

sshEventObjects45 OBJECT-IDENTITY
    STATUS current
    DESCRIPTION
        "Event SSH.45
        Userauth request postponed/accepted."
    ::= { sshEventsGroup 45 }

ssh45-userid OBJECT-TYPE
    SYNTAX Integer32
    MAX-ACCESS accessible-for-notify
    STATUS current
    DESCRIPTION
        "Parameter 'userid' in event SSH.45"
    ::= { sshEventObjects45 1 }

ssh45-operation OBJECT-TYPE
    SYNTAX DisplayString
    MAX-ACCESS accessible-for-notify
    STATUS current
    DESCRIPTION
        "Parameter 'operation' in event SSH.45"
    ::= { sshEventObjects45 2 }

sshEventObjects46 OBJECT-IDENTITY
    STATUS current
    DESCRIPTION
        "Event SSH.46
        Userauth request denied indicating available methods."
    ::= { sshEventsGroup 46 }

ssh46-userid OBJECT-TYPE
    SYNTAX Integer32
    MAX-ACCESS accessible-for-notify
    STATUS current
    DESCRIPTION
        "Parameter 'userid' in event SSH.46"
    ::= { sshEventObjects46 1 }

ssh46-methods OBJECT-TYPE
    SYNTAX DisplayString
    MAX-ACCESS accessible-for-notify
    STATUS current
    DESCRIPTION
        "Parameter 'methods' in event SSH.46"
    ::= { sshEventObjects46 2 }

sshEventObjects47 OBJECT-IDENTITY
    STATUS current
    DESCRIPTION
        "Event SSH.47
        Event related to information about SSHv1 authentication."
    ::= { sshEventsGroup 47 }

ssh47-userid OBJECT-TYPE
    SYNTAX Integer32
    MAX-ACCESS accessible-for-notify
    STATUS current
    DESCRIPTION
        "Parameter 'userid' in event SSH.47"
    ::= { sshEventObjects47 1 }

ssh47-description OBJECT-TYPE
    SYNTAX DisplayString
    MAX-ACCESS accessible-for-notify
    STATUS current
    DESCRIPTION
        "Parameter 'description' in event SSH.47"
    ::= { sshEventObjects47 2 }

sshEventObjects48 OBJECT-IDENTITY
    STATUS current
    DESCRIPTION
        "Event SSH.48
        Event related to further information about authentication."
    ::= { sshEventsGroup 48 }

ssh48-userid OBJECT-TYPE
    SYNTAX Integer32
    MAX-ACCESS accessible-for-notify
    STATUS current
    DESCRIPTION
        "Parameter 'userid' in event SSH.48"
    ::= { sshEventObjects48 1 }

ssh48-description OBJECT-TYPE
    SYNTAX DisplayString
    MAX-ACCESS accessible-for-notify
    STATUS current
    DESCRIPTION
        "Parameter 'description' in event SSH.48"
    ::= { sshEventObjects48 2 }

sshEventObjects49 OBJECT-IDENTITY
    STATUS current
    DESCRIPTION
        "Event SSH.49
        User authentication not completed before maximum allowed time expired."
    ::= { sshEventsGroup 49 }

ssh49-userid OBJECT-TYPE
    SYNTAX Integer32
    MAX-ACCESS accessible-for-notify
    STATUS current
    DESCRIPTION
        "Parameter 'userid' in event SSH.49"
    ::= { sshEventObjects49 1 }

sshEventObjects50 OBJECT-IDENTITY
    STATUS current
    DESCRIPTION
        "Event SSH.50
        Event related to an error found while user authentication."
    ::= { sshEventsGroup 50 }

ssh50-userid OBJECT-TYPE
    SYNTAX Integer32
    MAX-ACCESS accessible-for-notify
    STATUS current
    DESCRIPTION
        "Parameter 'userid' in event SSH.50"
    ::= { sshEventObjects50 1 }

ssh50-description OBJECT-TYPE
    SYNTAX DisplayString
    MAX-ACCESS accessible-for-notify
    STATUS current
    DESCRIPTION
        "Parameter 'description' in event SSH.50"
    ::= { sshEventObjects50 2 }

sshEventObjects51 OBJECT-IDENTITY
    STATUS current
    DESCRIPTION
        "Event SSH.51
        Banner message was received/sent."
    ::= { sshEventsGroup 51 }

ssh51-userid OBJECT-TYPE
    SYNTAX Integer32
    MAX-ACCESS accessible-for-notify
    STATUS current
    DESCRIPTION
        "Parameter 'userid' in event SSH.51"
    ::= { sshEventObjects51 1 }

ssh51-direction OBJECT-TYPE
    SYNTAX DisplayString
    MAX-ACCESS accessible-for-notify
    STATUS current
    DESCRIPTION
        "Parameter 'direction' in event SSH.51"
    ::= { sshEventObjects51 2 }

sshEventObjects54 OBJECT-IDENTITY
    STATUS current
    DESCRIPTION
        "Event SSH.54
        Global request was received/sent."
    ::= { sshEventsGroup 54 }

ssh54-userid OBJECT-TYPE
    SYNTAX Integer32
    MAX-ACCESS accessible-for-notify
    STATUS current
    DESCRIPTION
        "Parameter 'userid' in event SSH.54"
    ::= { sshEventObjects54 1 }

ssh54-request OBJECT-TYPE
    SYNTAX DisplayString
    MAX-ACCESS accessible-for-notify
    STATUS current
    DESCRIPTION
        "Parameter 'request' in event SSH.54"
    ::= { sshEventObjects54 2 }

ssh54-direction OBJECT-TYPE
    SYNTAX DisplayString
    MAX-ACCESS accessible-for-notify
    STATUS current
    DESCRIPTION
        "Parameter 'direction' in event SSH.54"
    ::= { sshEventObjects54 3 }

sshEventObjects55 OBJECT-IDENTITY
    STATUS current
    DESCRIPTION
        "Event SSH.55
        Global request was refused."
    ::= { sshEventsGroup 55 }

ssh55-userid OBJECT-TYPE
    SYNTAX Integer32
    MAX-ACCESS accessible-for-notify
    STATUS current
    DESCRIPTION
        "Parameter 'userid' in event SSH.55"
    ::= { sshEventObjects55 1 }

ssh55-request OBJECT-TYPE
    SYNTAX DisplayString
    MAX-ACCESS accessible-for-notify
    STATUS current
    DESCRIPTION
        "Parameter 'request' in event SSH.55"
    ::= { sshEventObjects55 2 }

sshEventObjects58 OBJECT-IDENTITY
    STATUS current
    DESCRIPTION
        "Event SSH.58
        Channel open message with sender parameters."
    ::= { sshEventsGroup 58 }

ssh58-userid OBJECT-TYPE
    SYNTAX Integer32
    MAX-ACCESS accessible-for-notify
    STATUS current
    DESCRIPTION
        "Parameter 'userid' in event SSH.58"
    ::= { sshEventObjects58 1 }

ssh58-direction OBJECT-TYPE
    SYNTAX DisplayString
    MAX-ACCESS accessible-for-notify
    STATUS current
    DESCRIPTION
        "Parameter 'direction' in event SSH.58"
    ::= { sshEventObjects58 2 }

ssh58-sndchan OBJECT-TYPE
    SYNTAX Integer32
    MAX-ACCESS accessible-for-notify
    STATUS current
    DESCRIPTION
        "Parameter 'sndchan' in event SSH.58"
    ::= { sshEventObjects58 3 }

ssh58-type OBJECT-TYPE
    SYNTAX DisplayString
    MAX-ACCESS accessible-for-notify
    STATUS current
    DESCRIPTION
        "Parameter 'type' in event SSH.58"
    ::= { sshEventObjects58 4 }

ssh58-win OBJECT-TYPE
    SYNTAX Integer32
    MAX-ACCESS accessible-for-notify
    STATUS current
    DESCRIPTION
        "Parameter 'win' in event SSH.58"
    ::= { sshEventObjects58 5 }

ssh58-maxpkt OBJECT-TYPE
    SYNTAX Integer32
    MAX-ACCESS accessible-for-notify
    STATUS current
    DESCRIPTION
        "Parameter 'maxpkt' in event SSH.58"
    ::= { sshEventObjects58 6 }

sshEventObjects59 OBJECT-IDENTITY
    STATUS current
    DESCRIPTION
        "Event SSH.59
        Association between channels and session for an authenticated connection."
    ::= { sshEventsGroup 59 }

ssh59-userid OBJECT-TYPE
    SYNTAX Integer32
    MAX-ACCESS accessible-for-notify
    STATUS current
    DESCRIPTION
        "Parameter 'userid' in event SSH.59"
    ::= { sshEventObjects59 1 }

ssh59-cliadd OBJECT-TYPE
    SYNTAX IpAddress
    MAX-ACCESS accessible-for-notify
    STATUS current
    DESCRIPTION
        "Parameter 'cliadd' in event SSH.59"
    ::= { sshEventObjects59 2 }

ssh59-cliport OBJECT-TYPE
    SYNTAX Integer32
    MAX-ACCESS accessible-for-notify
    STATUS current
    DESCRIPTION
        "Parameter 'cliport' in event SSH.59"
    ::= { sshEventObjects59 3 }

ssh59-srvadd OBJECT-TYPE
    SYNTAX IpAddress
    MAX-ACCESS accessible-for-notify
    STATUS current
    DESCRIPTION
        "Parameter 'srvadd' in event SSH.59"
    ::= { sshEventObjects59 4 }

ssh59-srvport OBJECT-TYPE
    SYNTAX Integer32
    MAX-ACCESS accessible-for-notify
    STATUS current
    DESCRIPTION
        "Parameter 'srvport' in event SSH.59"
    ::= { sshEventObjects59 5 }

ssh59-clichan OBJECT-TYPE
    SYNTAX Integer32
    MAX-ACCESS accessible-for-notify
    STATUS current
    DESCRIPTION
        "Parameter 'clichan' in event SSH.59"
    ::= { sshEventObjects59 6 }

ssh59-srvchan OBJECT-TYPE
    SYNTAX Integer32
    MAX-ACCESS accessible-for-notify
    STATUS current
    DESCRIPTION
        "Parameter 'srvchan' in event SSH.59"
    ::= { sshEventObjects59 7 }

ssh59-session OBJECT-TYPE
    SYNTAX Integer32
    MAX-ACCESS accessible-for-notify
    STATUS current
    DESCRIPTION
        "Parameter 'session' in event SSH.59"
    ::= { sshEventObjects59 8 }

sshEventObjects60 OBJECT-IDENTITY
    STATUS current
    DESCRIPTION
        "Event SSH.60
        Channel open confirmation message for receiver channel with sender parameters."
    ::= { sshEventsGroup 60 }

ssh60-userid OBJECT-TYPE
    SYNTAX Integer32
    MAX-ACCESS accessible-for-notify
    STATUS current
    DESCRIPTION
        "Parameter 'userid' in event SSH.60"
    ::= { sshEventObjects60 1 }

ssh60-direction OBJECT-TYPE
    SYNTAX DisplayString
    MAX-ACCESS accessible-for-notify
    STATUS current
    DESCRIPTION
        "Parameter 'direction' in event SSH.60"
    ::= { sshEventObjects60 2 }

ssh60-rcvchan OBJECT-TYPE
    SYNTAX Integer32
    MAX-ACCESS accessible-for-notify
    STATUS current
    DESCRIPTION
        "Parameter 'rcvchan' in event SSH.60"
    ::= { sshEventObjects60 3 }

ssh60-sndchan OBJECT-TYPE
    SYNTAX Integer32
    MAX-ACCESS accessible-for-notify
    STATUS current
    DESCRIPTION
        "Parameter 'sndchan' in event SSH.60"
    ::= { sshEventObjects60 4 }

ssh60-type OBJECT-TYPE
    SYNTAX DisplayString
    MAX-ACCESS accessible-for-notify
    STATUS current
    DESCRIPTION
        "Parameter 'type' in event SSH.60"
    ::= { sshEventObjects60 5 }

ssh60-win OBJECT-TYPE
    SYNTAX Integer32
    MAX-ACCESS accessible-for-notify
    STATUS current
    DESCRIPTION
        "Parameter 'win' in event SSH.60"
    ::= { sshEventObjects60 6 }

ssh60-maxpkt OBJECT-TYPE
    SYNTAX Integer32
    MAX-ACCESS accessible-for-notify
    STATUS current
    DESCRIPTION
        "Parameter 'maxpkt' in event SSH.60"
    ::= { sshEventObjects60 7 }

sshEventObjects61 OBJECT-IDENTITY
    STATUS current
    DESCRIPTION
        "Event SSH.61
        Channel open failure message for receiver channel."
    ::= { sshEventsGroup 61 }

ssh61-userid OBJECT-TYPE
    SYNTAX Integer32
    MAX-ACCESS accessible-for-notify
    STATUS current
    DESCRIPTION
        "Parameter 'userid' in event SSH.61"
    ::= { sshEventObjects61 1 }

ssh61-reason-code OBJECT-TYPE
    SYNTAX Integer32
    MAX-ACCESS accessible-for-notify
    STATUS current
    DESCRIPTION
        "Parameter 'reason-code' in event SSH.61"
    ::= { sshEventObjects61 2 }

ssh61-rcvchan OBJECT-TYPE
    SYNTAX Integer32
    MAX-ACCESS accessible-for-notify
    STATUS current
    DESCRIPTION
        "Parameter 'rcvchan' in event SSH.61"
    ::= { sshEventObjects61 3 }

ssh61-description OBJECT-TYPE
    SYNTAX DisplayString
    MAX-ACCESS accessible-for-notify
    STATUS current
    DESCRIPTION
        "Parameter 'description' in event SSH.61"
    ::= { sshEventObjects61 4 }

sshEventObjects62 OBJECT-IDENTITY
    STATUS current
    DESCRIPTION
        "Event SSH.62
        Client-alive message has been received/sent."
    ::= { sshEventsGroup 62 }

ssh62-userid OBJECT-TYPE
    SYNTAX Integer32
    MAX-ACCESS accessible-for-notify
    STATUS current
    DESCRIPTION
        "Parameter 'userid' in event SSH.62"
    ::= { sshEventObjects62 1 }

ssh62-direction OBJECT-TYPE
    SYNTAX DisplayString
    MAX-ACCESS accessible-for-notify
    STATUS current
    DESCRIPTION
        "Parameter 'direction' in event SSH.62"
    ::= { sshEventObjects62 2 }

sshEventObjects63 OBJECT-IDENTITY
    STATUS current
    DESCRIPTION
        "Event SSH.63
        Event related to authenticated SSHv1."
    ::= { sshEventsGroup 63 }

ssh63-userid OBJECT-TYPE
    SYNTAX Integer32
    MAX-ACCESS accessible-for-notify
    STATUS current
    DESCRIPTION
        "Parameter 'userid' in event SSH.63"
    ::= { sshEventObjects63 1 }

ssh63-description OBJECT-TYPE
    SYNTAX DisplayString
    MAX-ACCESS accessible-for-notify
    STATUS current
    DESCRIPTION
        "Parameter 'description' in event SSH.63"
    ::= { sshEventObjects63 2 }

sshEventObjects64 OBJECT-IDENTITY
    STATUS current
    DESCRIPTION
        "Event SSH.64
        Verbose information in authenticated connection."
    ::= { sshEventsGroup 64 }

ssh64-userid OBJECT-TYPE
    SYNTAX Integer32
    MAX-ACCESS accessible-for-notify
    STATUS current
    DESCRIPTION
        "Parameter 'userid' in event SSH.64"
    ::= { sshEventObjects64 1 }

ssh64-description OBJECT-TYPE
    SYNTAX DisplayString
    MAX-ACCESS accessible-for-notify
    STATUS current
    DESCRIPTION
        "Parameter 'description' in event SSH.64"
    ::= { sshEventObjects64 2 }

sshEventObjects65 OBJECT-IDENTITY
    STATUS current
    DESCRIPTION
        "Event SSH.65
        Error found in authenticated connection."
    ::= { sshEventsGroup 65 }

ssh65-userid OBJECT-TYPE
    SYNTAX Integer32
    MAX-ACCESS accessible-for-notify
    STATUS current
    DESCRIPTION
        "Parameter 'userid' in event SSH.65"
    ::= { sshEventObjects65 1 }

ssh65-description OBJECT-TYPE
    SYNTAX DisplayString
    MAX-ACCESS accessible-for-notify
    STATUS current
    DESCRIPTION
        "Parameter 'description' in event SSH.65"
    ::= { sshEventObjects65 2 }

sshEventObjects67 OBJECT-IDENTITY
    STATUS current
    DESCRIPTION
        "Event SSH.67
        Channel window adjust message received/sent indicating bytes to add."
    ::= { sshEventsGroup 67 }

ssh67-userid OBJECT-TYPE
    SYNTAX Integer32
    MAX-ACCESS accessible-for-notify
    STATUS current
    DESCRIPTION
        "Parameter 'userid' in event SSH.67"
    ::= { sshEventObjects67 1 }

ssh67-local-chan OBJECT-TYPE
    SYNTAX Integer32
    MAX-ACCESS accessible-for-notify
    STATUS current
    DESCRIPTION
        "Parameter 'local-chan' in event SSH.67"
    ::= { sshEventObjects67 2 }

ssh67-direction OBJECT-TYPE
    SYNTAX DisplayString
    MAX-ACCESS accessible-for-notify
    STATUS current
    DESCRIPTION
        "Parameter 'direction' in event SSH.67"
    ::= { sshEventObjects67 3 }

ssh67-bytes OBJECT-TYPE
    SYNTAX Integer32
    MAX-ACCESS accessible-for-notify
    STATUS current
    DESCRIPTION
        "Parameter 'bytes' in event SSH.67"
    ::= { sshEventObjects67 4 }

sshEventObjects68 OBJECT-IDENTITY
    STATUS current
    DESCRIPTION
        "Event SSH.68
        Channel data message received/sent."
    ::= { sshEventsGroup 68 }

ssh68-userid OBJECT-TYPE
    SYNTAX Integer32
    MAX-ACCESS accessible-for-notify
    STATUS current
    DESCRIPTION
        "Parameter 'userid' in event SSH.68"
    ::= { sshEventObjects68 1 }

ssh68-local-chan OBJECT-TYPE
    SYNTAX Integer32
    MAX-ACCESS accessible-for-notify
    STATUS current
    DESCRIPTION
        "Parameter 'local-chan' in event SSH.68"
    ::= { sshEventObjects68 2 }

ssh68-direction OBJECT-TYPE
    SYNTAX DisplayString
    MAX-ACCESS accessible-for-notify
    STATUS current
    DESCRIPTION
        "Parameter 'direction' in event SSH.68"
    ::= { sshEventObjects68 3 }

ssh68-len OBJECT-TYPE
    SYNTAX Integer32
    MAX-ACCESS accessible-for-notify
    STATUS current
    DESCRIPTION
        "Parameter 'len' in event SSH.68"
    ::= { sshEventObjects68 4 }

sshEventObjects69 OBJECT-IDENTITY
    STATUS current
    DESCRIPTION
        "Event SSH.69
        Extended channel data message received/sent."
    ::= { sshEventsGroup 69 }

ssh69-userid OBJECT-TYPE
    SYNTAX Integer32
    MAX-ACCESS accessible-for-notify
    STATUS current
    DESCRIPTION
        "Parameter 'userid' in event SSH.69"
    ::= { sshEventObjects69 1 }

ssh69-local-chan OBJECT-TYPE
    SYNTAX Integer32
    MAX-ACCESS accessible-for-notify
    STATUS current
    DESCRIPTION
        "Parameter 'local-chan' in event SSH.69"
    ::= { sshEventObjects69 2 }

ssh69-type OBJECT-TYPE
    SYNTAX Integer32
    MAX-ACCESS accessible-for-notify
    STATUS current
    DESCRIPTION
        "Parameter 'type' in event SSH.69"
    ::= { sshEventObjects69 3 }

ssh69-direction OBJECT-TYPE
    SYNTAX DisplayString
    MAX-ACCESS accessible-for-notify
    STATUS current
    DESCRIPTION
        "Parameter 'direction' in event SSH.69"
    ::= { sshEventObjects69 4 }

ssh69-len OBJECT-TYPE
    SYNTAX Integer32
    MAX-ACCESS accessible-for-notify
    STATUS current
    DESCRIPTION
        "Parameter 'len' in event SSH.69"
    ::= { sshEventObjects69 5 }

sshEventObjects70 OBJECT-IDENTITY
    STATUS current
    DESCRIPTION
        "Event SSH.70
        EOF message received/sent."
    ::= { sshEventsGroup 70 }

ssh70-userid OBJECT-TYPE
    SYNTAX Integer32
    MAX-ACCESS accessible-for-notify
    STATUS current
    DESCRIPTION
        "Parameter 'userid' in event SSH.70"
    ::= { sshEventObjects70 1 }

ssh70-local-chan OBJECT-TYPE
    SYNTAX Integer32
    MAX-ACCESS accessible-for-notify
    STATUS current
    DESCRIPTION
        "Parameter 'local-chan' in event SSH.70"
    ::= { sshEventObjects70 2 }

ssh70-direction OBJECT-TYPE
    SYNTAX DisplayString
    MAX-ACCESS accessible-for-notify
    STATUS current
    DESCRIPTION
        "Parameter 'direction' in event SSH.70"
    ::= { sshEventObjects70 3 }

sshEventObjects71 OBJECT-IDENTITY
    STATUS current
    DESCRIPTION
        "Event SSH.71
        Channel close message received/sent."
    ::= { sshEventsGroup 71 }

ssh71-userid OBJECT-TYPE
    SYNTAX Integer32
    MAX-ACCESS accessible-for-notify
    STATUS current
    DESCRIPTION
        "Parameter 'userid' in event SSH.71"
    ::= { sshEventObjects71 1 }

ssh71-local-chan OBJECT-TYPE
    SYNTAX Integer32
    MAX-ACCESS accessible-for-notify
    STATUS current
    DESCRIPTION
        "Parameter 'local-chan' in event SSH.71"
    ::= { sshEventObjects71 2 }

ssh71-direction OBJECT-TYPE
    SYNTAX DisplayString
    MAX-ACCESS accessible-for-notify
    STATUS current
    DESCRIPTION
        "Parameter 'direction' in event SSH.71"
    ::= { sshEventObjects71 3 }

sshEventObjects72 OBJECT-IDENTITY
    STATUS current
    DESCRIPTION
        "Event SSH.72
        Channel request message received/sent that may be confirmed, with extra data."
    ::= { sshEventsGroup 72 }

ssh72-userid OBJECT-TYPE
    SYNTAX Integer32
    MAX-ACCESS accessible-for-notify
    STATUS current
    DESCRIPTION
        "Parameter 'userid' in event SSH.72"
    ::= { sshEventObjects72 1 }

ssh72-local-chan OBJECT-TYPE
    SYNTAX Integer32
    MAX-ACCESS accessible-for-notify
    STATUS current
    DESCRIPTION
        "Parameter 'local-chan' in event SSH.72"
    ::= { sshEventObjects72 2 }

ssh72-request OBJECT-TYPE
    SYNTAX DisplayString
    MAX-ACCESS accessible-for-notify
    STATUS current
    DESCRIPTION
        "Parameter 'request' in event SSH.72"
    ::= { sshEventObjects72 3 }

ssh72-direction OBJECT-TYPE
    SYNTAX DisplayString
    MAX-ACCESS accessible-for-notify
    STATUS current
    DESCRIPTION
        "Parameter 'direction' in event SSH.72"
    ::= { sshEventObjects72 4 }

ssh72-confirm OBJECT-TYPE
    SYNTAX DisplayString
    MAX-ACCESS accessible-for-notify
    STATUS current
    DESCRIPTION
        "Parameter 'confirm' in event SSH.72"
    ::= { sshEventObjects72 5 }

ssh72-data OBJECT-TYPE
    SYNTAX DisplayString
    MAX-ACCESS accessible-for-notify
    STATUS current
    DESCRIPTION
        "Parameter 'data' in event SSH.72"
    ::= { sshEventObjects72 6 }

sshEventObjects73 OBJECT-IDENTITY
    STATUS current
    DESCRIPTION
        "Event SSH.73
        Channel failure message indicating that a previous request was refused."
    ::= { sshEventsGroup 73 }

ssh73-userid OBJECT-TYPE
    SYNTAX Integer32
    MAX-ACCESS accessible-for-notify
    STATUS current
    DESCRIPTION
        "Parameter 'userid' in event SSH.73"
    ::= { sshEventObjects73 1 }

ssh73-local-chan OBJECT-TYPE
    SYNTAX Integer32
    MAX-ACCESS accessible-for-notify
    STATUS current
    DESCRIPTION
        "Parameter 'local-chan' in event SSH.73"
    ::= { sshEventObjects73 2 }

ssh73-request OBJECT-TYPE
    SYNTAX DisplayString
    MAX-ACCESS accessible-for-notify
    STATUS current
    DESCRIPTION
        "Parameter 'request' in event SSH.73"
    ::= { sshEventObjects73 3 }

sshEventObjects74 OBJECT-IDENTITY
    STATUS current
    DESCRIPTION
        "Event SSH.74
        Event related to the allocation of a new pseudo-terminal."
    ::= { sshEventsGroup 74 }

ssh74-userid OBJECT-TYPE
    SYNTAX Integer32
    MAX-ACCESS accessible-for-notify
    STATUS current
    DESCRIPTION
        "Parameter 'userid' in event SSH.74"
    ::= { sshEventObjects74 1 }

ssh74-local-chan OBJECT-TYPE
    SYNTAX Integer32
    MAX-ACCESS accessible-for-notify
    STATUS current
    DESCRIPTION
        "Parameter 'local-chan' in event SSH.74"
    ::= { sshEventObjects74 2 }

sshEventObjects75 OBJECT-IDENTITY
    STATUS current
    DESCRIPTION
        "Event SSH.75
        Event related to the creation of a new console."
    ::= { sshEventsGroup 75 }

ssh75-userid OBJECT-TYPE
    SYNTAX Integer32
    MAX-ACCESS accessible-for-notify
    STATUS current
    DESCRIPTION
        "Parameter 'userid' in event SSH.75"
    ::= { sshEventObjects75 1 }

ssh75-local-chan OBJECT-TYPE
    SYNTAX Integer32
    MAX-ACCESS accessible-for-notify
    STATUS current
    DESCRIPTION
        "Parameter 'local-chan' in event SSH.75"
    ::= { sshEventObjects75 2 }

sshEventObjects76 OBJECT-IDENTITY
    STATUS current
    DESCRIPTION
        "Event SSH.76
        Event related to a SSHv1 channel."
    ::= { sshEventsGroup 76 }

ssh76-userid OBJECT-TYPE
    SYNTAX Integer32
    MAX-ACCESS accessible-for-notify
    STATUS current
    DESCRIPTION
        "Parameter 'userid' in event SSH.76"
    ::= { sshEventObjects76 1 }

ssh76-local-chan OBJECT-TYPE
    SYNTAX Integer32
    MAX-ACCESS accessible-for-notify
    STATUS current
    DESCRIPTION
        "Parameter 'local-chan' in event SSH.76"
    ::= { sshEventObjects76 2 }

ssh76-description OBJECT-TYPE
    SYNTAX DisplayString
    MAX-ACCESS accessible-for-notify
    STATUS current
    DESCRIPTION
        "Parameter 'description' in event SSH.76"
    ::= { sshEventObjects76 3 }

sshEventObjects77 OBJECT-IDENTITY
    STATUS current
    DESCRIPTION
        "Event SSH.77
        Verbose information about channel."
    ::= { sshEventsGroup 77 }

ssh77-userid OBJECT-TYPE
    SYNTAX Integer32
    MAX-ACCESS accessible-for-notify
    STATUS current
    DESCRIPTION
        "Parameter 'userid' in event SSH.77"
    ::= { sshEventObjects77 1 }

ssh77-local-chan OBJECT-TYPE
    SYNTAX Integer32
    MAX-ACCESS accessible-for-notify
    STATUS current
    DESCRIPTION
        "Parameter 'local-chan' in event SSH.77"
    ::= { sshEventObjects77 2 }

ssh77-description OBJECT-TYPE
    SYNTAX DisplayString
    MAX-ACCESS accessible-for-notify
    STATUS current
    DESCRIPTION
        "Parameter 'description' in event SSH.77"
    ::= { sshEventObjects77 3 }

sshEventObjects78 OBJECT-IDENTITY
    STATUS current
    DESCRIPTION
        "Event SSH.78
        Error found in channel."
    ::= { sshEventsGroup 78 }

ssh78-userid OBJECT-TYPE
    SYNTAX Integer32
    MAX-ACCESS accessible-for-notify
    STATUS current
    DESCRIPTION
        "Parameter 'userid' in event SSH.78"
    ::= { sshEventObjects78 1 }

ssh78-local-chan OBJECT-TYPE
    SYNTAX Integer32
    MAX-ACCESS accessible-for-notify
    STATUS current
    DESCRIPTION
        "Parameter 'local-chan' in event SSH.78"
    ::= { sshEventObjects78 2 }

ssh78-description OBJECT-TYPE
    SYNTAX DisplayString
    MAX-ACCESS accessible-for-notify
    STATUS current
    DESCRIPTION
        "Parameter 'description' in event SSH.78"
    ::= { sshEventObjects78 3 }


sshNotification1 NOTIFICATION-TYPE
    STATUS current
    DESCRIPTION
        "Notification of Event SSH.1

        Message: 'SSH server not enabled'

        SSH server not enabled in configuration."
    ::= { sshNotificationsPrefix 1 }

sshNotification2 NOTIFICATION-TYPE
    OBJECTS { 
              ssh2-description 
            }
    STATUS current
    DESCRIPTION
        "Notification of Event SSH.2

        Message: 'Global verbose: $1'

        Parameters list:
              $1: ssh2-description

        Verbose info from a global SSH function."
    ::= { sshNotificationsPrefix 2 }

sshNotification3 NOTIFICATION-TYPE
    OBJECTS { 
              ssh3-description 
            }
    STATUS current
    DESCRIPTION
        "Notification of Event SSH.3

        Message: 'Global error: $1'

        Parameters list:
              $1: ssh3-description

        Error found in a global SSH function."
    ::= { sshNotificationsPrefix 3 }

sshNotification4 NOTIFICATION-TYPE
    OBJECTS { 
              ssh4-description, 
              ssh4-task 
            }
    STATUS current
    DESCRIPTION
        "Notification of Event SSH.4

        Message: 'Task verbose: $1 $2'

        Parameters list:
              $1: ssh4-description
              $2: ssh4-task

        Event related to task creation/deletion."
    ::= { sshNotificationsPrefix 4 }

sshNotification5 NOTIFICATION-TYPE
    OBJECTS { 
              ssh5-error, 
              ssh5-task 
            }
    STATUS current
    DESCRIPTION
        "Notification of Event SSH.5

        Message: 'Task error: $1 $2'

        Parameters list:
              $1: ssh5-error
              $2: ssh5-task

        Error related to task creation/deletion."
    ::= { sshNotificationsPrefix 5 }

sshNotification6 NOTIFICATION-TYPE
    OBJECTS { 
              ssh6-description 
            }
    STATUS current
    DESCRIPTION
        "Notification of Event SSH.6

        Message: 'Server init: $1'

        Parameters list:
              $1: ssh6-description

        Event related to server initialization."
    ::= { sshNotificationsPrefix 6 }

sshNotification7 NOTIFICATION-TYPE
    OBJECTS { 
              ssh7-description 
            }
    STATUS current
    DESCRIPTION
        "Notification of Event SSH.7

        Message: 'Server init error: $1'

        Parameters list:
              $1: ssh7-description

        Error related to server initialization."
    ::= { sshNotificationsPrefix 7 }

sshNotification8 NOTIFICATION-TYPE
    OBJECTS { 
              ssh8-description 
            }
    STATUS current
    DESCRIPTION
        "Notification of Event SSH.8

        Message: 'Server init verbose: $1'

        Parameters list:
              $1: ssh8-description

        Verbose event related to server initialization."
    ::= { sshNotificationsPrefix 8 }

sshNotification9 NOTIFICATION-TYPE
    OBJECTS { 
              ssh9-hostkey-type, 
              ssh9-description 
            }
    STATUS current
    DESCRIPTION
        "Notification of Event SSH.9

        Message: 'Hostkey type $1: $2'

        Parameters list:
              $1: ssh9-hostkey-type
              $2: ssh9-description

        Event related to hostkey loading/generation."
    ::= { sshNotificationsPrefix 9 }

sshNotification10 NOTIFICATION-TYPE
    OBJECTS { 
              ssh10-hostkey-type 
            }
    STATUS current
    DESCRIPTION
        "Notification of Event SSH.10

        Message: 'Hostkey type $1: not found in config!'

        Parameters list:
              $1: ssh10-hostkey-type

        Warning: Hostkey not found in config."
    ::= { sshNotificationsPrefix 10 }

sshNotification11 NOTIFICATION-TYPE
    OBJECTS { 
              ssh11-description 
            }
    STATUS current
    DESCRIPTION
        "Notification of Event SSH.11

        Message: 'Key generation verbose: $1'

        Parameters list:
              $1: ssh11-description

        Verbose information about key generation process."
    ::= { sshNotificationsPrefix 11 }

sshNotification12 NOTIFICATION-TYPE
    OBJECTS { 
              ssh12-description 
            }
    STATUS current
    DESCRIPTION
        "Notification of Event SSH.12

        Message: 'Key generation error: $1'

        Parameters list:
              $1: ssh12-description

        Error found during key generation process."
    ::= { sshNotificationsPrefix 12 }

sshNotification13 NOTIFICATION-TYPE
    STATUS current
    DESCRIPTION
        "Notification of Event SSH.13

        Message: '----'

        Reserved for possible future use."
    ::= { sshNotificationsPrefix 13 }

sshNotification14 NOTIFICATION-TYPE
    STATUS current
    DESCRIPTION
        "Notification of Event SSH.14

        Message: '----'

        Reserved for possible future use."
    ::= { sshNotificationsPrefix 14 }

sshNotification15 NOTIFICATION-TYPE
    OBJECTS { 
              ssh15-userid, 
              ssh15-srvadd,
              ssh15-srvport,
              ssh15-cliadd,
              ssh15-cliport 
            }
    STATUS current
    DESCRIPTION
        "Notification of Event SSH.15

        Message: 'New connection!!! New user id is $1. Server: $2:$3 - Client: $4:$5'

        Parameters list:
              $1: ssh15-userid
              $2: ssh15-srvadd
              $3: ssh15-srvport
              $4: ssh15-cliadd
              $5: ssh15-cliport

        Important! Event related to a new connection with user id info."
    ::= { sshNotificationsPrefix 15 }

sshNotification16 NOTIFICATION-TYPE
    OBJECTS { 
              ssh16-cliadd, 
              ssh16-cliport,
              ssh16-reason 
            }
    STATUS current
    DESCRIPTION
        "Notification of Event SSH.16

        Message: 'New connection from $1:$2 refused: $3'

        Parameters list:
              $1: ssh16-cliadd
              $2: ssh16-cliport
              $3: ssh16-reason

        A new connection was refused because of the reason"
    ::= { sshNotificationsPrefix 16 }

sshNotification17 NOTIFICATION-TYPE
    OBJECTS { 
              ssh17-userid, 
              ssh17-srvadd,
              ssh17-srvport,
              ssh17-cliadd,
              ssh17-cliport 
            }
    STATUS current
    DESCRIPTION
        "Notification of Event SSH.17

        Message: 'U:$1. Connection closed!!! Server: $2:$3 - Client: $4:$5. User id free!'

        Parameters list:
              $1: ssh17-userid
              $2: ssh17-srvadd
              $3: ssh17-srvport
              $4: ssh17-cliadd
              $5: ssh17-cliport

        Event related to a connection closing"
    ::= { sshNotificationsPrefix 17 }

sshNotification18 NOTIFICATION-TYPE
    OBJECTS { 
              ssh18-userid, 
              ssh18-description 
            }
    STATUS current
    DESCRIPTION
        "Notification of Event SSH.18

        Message: 'U:$1. Connection verbose: $2'

        Parameters list:
              $1: ssh18-userid
              $2: ssh18-description

        Verbose information about the connection."
    ::= { sshNotificationsPrefix 18 }

sshNotification19 NOTIFICATION-TYPE
    OBJECTS { 
              ssh19-userid, 
              ssh19-description 
            }
    STATUS current
    DESCRIPTION
        "Notification of Event SSH.19

        Message: 'U:$1. Version incompatibility: $2'

        Parameters list:
              $1: ssh19-userid
              $2: ssh19-description

        Error related to version incompatibility."
    ::= { sshNotificationsPrefix 19 }

sshNotification20 NOTIFICATION-TYPE
    STATUS current
    DESCRIPTION
        "Notification of Event SSH.20

        Message: '----'

        Reserved for possible future use."
    ::= { sshNotificationsPrefix 20 }

sshNotification21 NOTIFICATION-TYPE
    OBJECTS { 
              ssh21-userid, 
              ssh21-msg-number 
            }
    STATUS current
    DESCRIPTION
        "Notification of Event SSH.21

        Message: 'U:$1. Message [$2] received'

        Parameters list:
              $1: ssh21-userid
              $2: ssh21-msg-number

        SSH message received."
    ::= { sshNotificationsPrefix 21 }

sshNotification22 NOTIFICATION-TYPE
    OBJECTS { 
              ssh22-userid, 
              ssh22-msg-number 
            }
    STATUS current
    DESCRIPTION
        "Notification of Event SSH.22

        Message: 'U:$1. Message [$2] sent'

        Parameters list:
              $1: ssh22-userid
              $2: ssh22-msg-number

        SSH message sent."
    ::= { sshNotificationsPrefix 22 }

sshNotification23 NOTIFICATION-TYPE
    OBJECTS { 
              ssh23-userid, 
              ssh23-msg-number 
            }
    STATUS current
    DESCRIPTION
        "Notification of Event SSH.23

        Message: 'U:$1. Message [$2] expected'

        Parameters list:
              $1: ssh23-userid
              $2: ssh23-msg-number

        Message expected from peer."
    ::= { sshNotificationsPrefix 23 }

sshNotification24 NOTIFICATION-TYPE
    OBJECTS { 
              ssh24-userid, 
              ssh24-reason-code,
              ssh24-description 
            }
    STATUS current
    DESCRIPTION
        "Notification of Event SSH.24

        Message: 'U:$1. Disconnection message (reason code: $2) received: $3'

        Parameters list:
              $1: ssh24-userid
              $2: ssh24-reason-code
              $3: ssh24-description

        Disconnection message received with reason code and explanation."
    ::= { sshNotificationsPrefix 24 }

sshNotification25 NOTIFICATION-TYPE
    OBJECTS { 
              ssh25-userid, 
              ssh25-reason-code,
              ssh25-description 
            }
    STATUS current
    DESCRIPTION
        "Notification of Event SSH.25

        Message: 'U:$1. Disconnection message (reason code:$2) sent: $3'

        Parameters list:
              $1: ssh25-userid
              $2: ssh25-reason-code
              $3: ssh25-description

        Disconnection message sent with reason code and explanation."
    ::= { sshNotificationsPrefix 25 }

sshNotification26 NOTIFICATION-TYPE
    OBJECTS { 
              ssh26-userid, 
              ssh26-description 
            }
    STATUS current
    DESCRIPTION
        "Notification of Event SSH.26

        Message: 'U:$1. Ignore message $2'

        Parameters list:
              $1: ssh26-userid
              $2: ssh26-description

        An ignore message has been rcvd/sent."
    ::= { sshNotificationsPrefix 26 }

sshNotification27 NOTIFICATION-TYPE
    OBJECTS { 
              ssh27-userid, 
              ssh27-direction 
            }
    STATUS current
    DESCRIPTION
        "Notification of Event SSH.27

        Message: 'U:$1. Unimplemented message $2'

        Parameters list:
              $1: ssh27-userid
              $2: ssh27-direction

        A not implemented message has been received."
    ::= { sshNotificationsPrefix 27 }

sshNotification28 NOTIFICATION-TYPE
    OBJECTS { 
              ssh28-userid, 
              ssh28-rcvd-sent,
              ssh28-description 
            }
    STATUS current
    DESCRIPTION
        "Notification of Event SSH.28

        Message: 'U:$1. Debug message $2: $3'

        Parameters list:
              $1: ssh28-userid
              $2: ssh28-rcvd-sent
              $3: ssh28-description

        Debug message rcvd/sent with debug info."
    ::= { sshNotificationsPrefix 28 }

sshNotification29 NOTIFICATION-TYPE
    STATUS current
    DESCRIPTION
        "Notification of Event SSH.29

        Message: '----'

        Reserved for possible future use."
    ::= { sshNotificationsPrefix 29 }

sshNotification30 NOTIFICATION-TYPE
    STATUS current
    DESCRIPTION
        "Notification of Event SSH.30

        Message: '----'

        Reserved for possible future use."
    ::= { sshNotificationsPrefix 30 }

sshNotification31 NOTIFICATION-TYPE
    OBJECTS { 
              ssh31-userid, 
              ssh31-proposal 
            }
    STATUS current
    DESCRIPTION
        "Notification of Event SSH.31

        Message: 'U:$1. Key Exchange. Kexinit server->client: $2'

        Parameters list:
              $1: ssh31-userid
              $2: ssh31-proposal

        KEX proposal sent from server to client"
    ::= { sshNotificationsPrefix 31 }

sshNotification32 NOTIFICATION-TYPE
    OBJECTS { 
              ssh32-userid, 
              ssh32-proposal 
            }
    STATUS current
    DESCRIPTION
        "Notification of Event SSH.32

        Message: 'U:$1. Key Exchange. Kexinit client->server: $2'

        Parameters list:
              $1: ssh32-userid
              $2: ssh32-proposal

        KEX proposal sent from client to server"
    ::= { sshNotificationsPrefix 32 }

sshNotification33 NOTIFICATION-TYPE
    OBJECTS { 
              ssh33-userid, 
              ssh33-decision 
            }
    STATUS current
    DESCRIPTION
        "Notification of Event SSH.33

        Message: 'U:$1. Key Exchange. Decision: $2'

        Parameters list:
              $1: ssh33-userid
              $2: ssh33-decision

        KEX decision made after comparing kexinit messages."
    ::= { sshNotificationsPrefix 33 }

sshNotification34 NOTIFICATION-TYPE
    OBJECTS { 
              ssh34-userid, 
              ssh34-description 
            }
    STATUS current
    DESCRIPTION
        "Notification of Event SSH.34

        Message: 'U:$1. Key Exchange. Verbose: $2'

        Parameters list:
              $1: ssh34-userid
              $2: ssh34-description

        Event related to verbose information about KEX."
    ::= { sshNotificationsPrefix 34 }

sshNotification35 NOTIFICATION-TYPE
    OBJECTS { 
              ssh35-userid, 
              ssh35-description 
            }
    STATUS current
    DESCRIPTION
        "Notification of Event SSH.35

        Message: 'U:$1. Key Exchange. Error: $2'

        Parameters list:
              $1: ssh35-userid
              $2: ssh35-description

        Event related to an error found during KEX."
    ::= { sshNotificationsPrefix 35 }

sshNotification36 NOTIFICATION-TYPE
    OBJECTS { 
              ssh36-userid, 
              ssh36-description,
              ssh36-direction 
            }
    STATUS current
    DESCRIPTION
        "Notification of Event SSH.36

        Message: 'U:$1. Key Exchange. Diffie-Hellman $2 $3'

        Parameters list:
              $1: ssh36-userid
              $2: ssh36-description
              $3: ssh36-direction

        Diffie-Hellman message of a certain type has been received/sent."
    ::= { sshNotificationsPrefix 36 }

sshNotification37 NOTIFICATION-TYPE
    OBJECTS { 
              ssh37-userid, 
              ssh37-direction,
              ssh37-description 
            }
    STATUS current
    DESCRIPTION
        "Notification of Event SSH.37

        Message: 'U:$1. Key Exchange. SSHv1: $2 $3'

        Parameters list:
              $1: ssh37-userid
              $2: ssh37-direction
              $3: ssh37-description

        SSHv1 Key Exchange message has been received/sent."
    ::= { sshNotificationsPrefix 37 }

sshNotification38 NOTIFICATION-TYPE
    OBJECTS { 
              ssh38-userid, 
              ssh38-direction 
            }
    STATUS current
    DESCRIPTION
        "Notification of Event SSH.38

        Message: 'U:$1. KEX. NEWKEYS message $2'

        Parameters list:
              $1: ssh38-userid
              $2: ssh38-direction

        New keys are about to be used from now on."
    ::= { sshNotificationsPrefix 38 }

sshNotification39 NOTIFICATION-TYPE
    OBJECTS { 
              ssh39-userid 
            }
    STATUS current
    DESCRIPTION
        "Notification of Event SSH.39

        Message: 'U:$1. KEX. Rekeying!'

        Parameters list:
              $1: ssh39-userid

        Periodic rekeying process after a period."
    ::= { sshNotificationsPrefix 39 }

sshNotification40 NOTIFICATION-TYPE
    STATUS current
    DESCRIPTION
        "Notification of Event SSH.40

        Message: '----'

        Reserved for possible future use."
    ::= { sshNotificationsPrefix 40 }

sshNotification41 NOTIFICATION-TYPE
    OBJECTS { 
              ssh41-userid, 
              ssh41-service,
              ssh41-direction 
            }
    STATUS current
    DESCRIPTION
        "Notification of Event SSH.41

        Message: 'U:$1. Service request $2 $3'

        Parameters list:
              $1: ssh41-userid
              $2: ssh41-service
              $3: ssh41-direction

        Service request name and direction."
    ::= { sshNotificationsPrefix 41 }

sshNotification42 NOTIFICATION-TYPE
    OBJECTS { 
              ssh42-userid, 
              ssh42-service 
            }
    STATUS current
    DESCRIPTION
        "Notification of Event SSH.42

        Message: 'U:$1. Service request $2 not accepted'

        Parameters list:
              $1: ssh42-userid
              $2: ssh42-service

        Service request received/sent has not been accepted."
    ::= { sshNotificationsPrefix 42 }

sshNotification43 NOTIFICATION-TYPE
    OBJECTS { 
              ssh43-userid, 
              ssh43-direction,
              ssh43-username,
              ssh43-service,
              ssh43-method 
            }
    STATUS current
    DESCRIPTION
        "Notification of Event SSH.43

        Message: 'U:$1. User authentication request $2: user $3 - service $4 - method $5'

        Parameters list:
              $1: ssh43-userid
              $2: ssh43-direction
              $3: ssh43-username
              $4: ssh43-service
              $5: ssh43-method

        Userauth request received/sent with parameters."
    ::= { sshNotificationsPrefix 43 }

sshNotification44 NOTIFICATION-TYPE
    OBJECTS { 
              ssh44-userid, 
              ssh44-attempt,
              ssh44-failures 
            }
    STATUS current
    DESCRIPTION
        "Notification of Event SSH.44

        Message: 'U:$1. User authentication attempt $2. Number of failures: $3'

        Parameters list:
              $1: ssh44-userid
              $2: ssh44-attempt
              $3: ssh44-failures

        Register of userauth attempt and failures."
    ::= { sshNotificationsPrefix 44 }

sshNotification45 NOTIFICATION-TYPE
    OBJECTS { 
              ssh45-userid, 
              ssh45-operation 
            }
    STATUS current
    DESCRIPTION
        "Notification of Event SSH.45

        Message: 'U:$1. User authentication request $2'

        Parameters list:
              $1: ssh45-userid
              $2: ssh45-operation

        Userauth request postponed/accepted."
    ::= { sshNotificationsPrefix 45 }

sshNotification46 NOTIFICATION-TYPE
    OBJECTS { 
              ssh46-userid, 
              ssh46-methods 
            }
    STATUS current
    DESCRIPTION
        "Notification of Event SSH.46

        Message: 'U:$1. User authentication request denied. Methods: $2'

        Parameters list:
              $1: ssh46-userid
              $2: ssh46-methods

        Userauth request denied indicating available methods."
    ::= { sshNotificationsPrefix 46 }

sshNotification47 NOTIFICATION-TYPE
    OBJECTS { 
              ssh47-userid, 
              ssh47-description 
            }
    STATUS current
    DESCRIPTION
        "Notification of Event SSH.47

        Message: 'U:$1. SSHv1 user authentication: $2'

        Parameters list:
              $1: ssh47-userid
              $2: ssh47-description

        Event related to information about SSHv1 authentication."
    ::= { sshNotificationsPrefix 47 }

sshNotification48 NOTIFICATION-TYPE
    OBJECTS { 
              ssh48-userid, 
              ssh48-description 
            }
    STATUS current
    DESCRIPTION
        "Notification of Event SSH.48

        Message: 'U:$1. User authentication verbose: $2'

        Parameters list:
              $1: ssh48-userid
              $2: ssh48-description

        Event related to further information about authentication."
    ::= { sshNotificationsPrefix 48 }

sshNotification49 NOTIFICATION-TYPE
    OBJECTS { 
              ssh49-userid 
            }
    STATUS current
    DESCRIPTION
        "Notification of Event SSH.49

        Message: 'U:$1. User authentication not completed before maximum allowed time expired!!'

        Parameters list:
              $1: ssh49-userid

        User authentication not completed before maximum allowed time expired."
    ::= { sshNotificationsPrefix 49 }

sshNotification50 NOTIFICATION-TYPE
    OBJECTS { 
              ssh50-userid, 
              ssh50-description 
            }
    STATUS current
    DESCRIPTION
        "Notification of Event SSH.50

        Message: 'U:$1. User authentication error: $2'

        Parameters list:
              $1: ssh50-userid
              $2: ssh50-description

        Event related to an error found while user authentication."
    ::= { sshNotificationsPrefix 50 }

sshNotification51 NOTIFICATION-TYPE
    OBJECTS { 
              ssh51-userid, 
              ssh51-direction 
            }
    STATUS current
    DESCRIPTION
        "Notification of Event SSH.51

        Message: 'U:$1. Banner message $2'

        Parameters list:
              $1: ssh51-userid
              $2: ssh51-direction

        Banner message was received/sent."
    ::= { sshNotificationsPrefix 51 }

sshNotification52 NOTIFICATION-TYPE
    STATUS current
    DESCRIPTION
        "Notification of Event SSH.52

        Message: '----'

        Reserved for possible future use."
    ::= { sshNotificationsPrefix 52 }

sshNotification53 NOTIFICATION-TYPE
    STATUS current
    DESCRIPTION
        "Notification of Event SSH.53

        Message: '----'

        Reserved for possible future use."
    ::= { sshNotificationsPrefix 53 }

sshNotification54 NOTIFICATION-TYPE
    OBJECTS { 
              ssh54-userid, 
              ssh54-request,
              ssh54-direction 
            }
    STATUS current
    DESCRIPTION
        "Notification of Event SSH.54

        Message: 'U:$1. Global request $2 $3'

        Parameters list:
              $1: ssh54-userid
              $2: ssh54-request
              $3: ssh54-direction

        Global request was received/sent."
    ::= { sshNotificationsPrefix 54 }

sshNotification55 NOTIFICATION-TYPE
    OBJECTS { 
              ssh55-userid, 
              ssh55-request 
            }
    STATUS current
    DESCRIPTION
        "Notification of Event SSH.55

        Message: 'U:$1. Global request $2 refused'

        Parameters list:
              $1: ssh55-userid
              $2: ssh55-request

        Global request was refused."
    ::= { sshNotificationsPrefix 55 }

sshNotification56 NOTIFICATION-TYPE
    STATUS current
    DESCRIPTION
        "Notification of Event SSH.56

        Message: '----'

        Reserved for possible future use."
    ::= { sshNotificationsPrefix 56 }

sshNotification57 NOTIFICATION-TYPE
    STATUS current
    DESCRIPTION
        "Notification of Event SSH.57

        Message: '----'

        Reserved for possible future use."
    ::= { sshNotificationsPrefix 57 }

sshNotification58 NOTIFICATION-TYPE
    OBJECTS { 
              ssh58-userid, 
              ssh58-direction,
              ssh58-sndchan,
              ssh58-type,
              ssh58-win,
              ssh58-maxpkt 
            }
    STATUS current
    DESCRIPTION
        "Notification of Event SSH.58

        Message: 'U:$1. Channel open $2: Sender-channel $3 - Type $4 - rcv-Window $5 - Max-packet $6'

        Parameters list:
              $1: ssh58-userid
              $2: ssh58-direction
              $3: ssh58-sndchan
              $4: ssh58-type
              $5: ssh58-win
              $6: ssh58-maxpkt

        Channel open message with sender parameters."
    ::= { sshNotificationsPrefix 58 }

sshNotification59 NOTIFICATION-TYPE
    OBJECTS { 
              ssh59-userid, 
              ssh59-cliadd,
              ssh59-cliport,
              ssh59-srvadd,
              ssh59-srvport,
              ssh59-clichan,
              ssh59-srvchan,
              ssh59-session 
            }
    STATUS current
    DESCRIPTION
        "Notification of Event SSH.59

        Message: 'U:$1. Socket c: $2:$3 -> s: $4:$5. Client-channel $6 - Server-channel $7 - Local-session $8'

        Parameters list:
              $1: ssh59-userid
              $2: ssh59-cliadd
              $3: ssh59-cliport
              $4: ssh59-srvadd
              $5: ssh59-srvport
              $6: ssh59-clichan
              $7: ssh59-srvchan
              $8: ssh59-session

        Association between channels and session for an authenticated connection."
    ::= { sshNotificationsPrefix 59 }

sshNotification60 NOTIFICATION-TYPE
    OBJECTS { 
              ssh60-userid, 
              ssh60-direction,
              ssh60-rcvchan,
              ssh60-sndchan,
              ssh60-type,
              ssh60-win,
              ssh60-maxpkt 
            }
    STATUS current
    DESCRIPTION
        "Notification of Event SSH.60

        Message: 'U:$1. Channel open confirmed $2: Receiver-channel $3 - Sender-channel $4 - Type $5 - rcv-Window $6 - Max-packet $7'

        Parameters list:
              $1: ssh60-userid
              $2: ssh60-direction
              $3: ssh60-rcvchan
              $4: ssh60-sndchan
              $5: ssh60-type
              $6: ssh60-win
              $7: ssh60-maxpkt

        Channel open confirmation message for receiver channel with sender parameters."
    ::= { sshNotificationsPrefix 60 }

sshNotification61 NOTIFICATION-TYPE
    OBJECTS { 
              ssh61-userid, 
              ssh61-reason-code,
              ssh61-rcvchan,
              ssh61-description 
            }
    STATUS current
    DESCRIPTION
        "Notification of Event SSH.61

        Message: 'U:$1. Channel open failure [$2] for rcvchan $3: $4'

        Parameters list:
              $1: ssh61-userid
              $2: ssh61-reason-code
              $3: ssh61-rcvchan
              $4: ssh61-description

        Channel open failure message for receiver channel."
    ::= { sshNotificationsPrefix 61 }

sshNotification62 NOTIFICATION-TYPE
    OBJECTS { 
              ssh62-userid, 
              ssh62-direction 
            }
    STATUS current
    DESCRIPTION
        "Notification of Event SSH.62

        Message: 'U:$1. Client-alive $2'

        Parameters list:
              $1: ssh62-userid
              $2: ssh62-direction

        Client-alive message has been received/sent."
    ::= { sshNotificationsPrefix 62 }

sshNotification63 NOTIFICATION-TYPE
    OBJECTS { 
              ssh63-userid, 
              ssh63-description 
            }
    STATUS current
    DESCRIPTION
        "Notification of Event SSH.63

        Message: 'U:$1. Authenticated SSHv1: $2'

        Parameters list:
              $1: ssh63-userid
              $2: ssh63-description

        Event related to authenticated SSHv1."
    ::= { sshNotificationsPrefix 63 }

sshNotification64 NOTIFICATION-TYPE
    OBJECTS { 
              ssh64-userid, 
              ssh64-description 
            }
    STATUS current
    DESCRIPTION
        "Notification of Event SSH.64

        Message: 'U:$1. Authenticated. Verbose: $2'

        Parameters list:
              $1: ssh64-userid
              $2: ssh64-description

        Verbose information in authenticated connection."
    ::= { sshNotificationsPrefix 64 }

sshNotification65 NOTIFICATION-TYPE
    OBJECTS { 
              ssh65-userid, 
              ssh65-description 
            }
    STATUS current
    DESCRIPTION
        "Notification of Event SSH.65

        Message: 'U:$1. Authenticated. Error: $2'

        Parameters list:
              $1: ssh65-userid
              $2: ssh65-description

        Error found in authenticated connection."
    ::= { sshNotificationsPrefix 65 }

sshNotification66 NOTIFICATION-TYPE
    STATUS current
    DESCRIPTION
        "Notification of Event SSH.66

        Message: '----'

        Reserved for possible future use."
    ::= { sshNotificationsPrefix 66 }

sshNotification67 NOTIFICATION-TYPE
    OBJECTS { 
              ssh67-userid, 
              ssh67-local-chan,
              ssh67-direction,
              ssh67-bytes 
            }
    STATUS current
    DESCRIPTION
        "Notification of Event SSH.67

        Message: 'U:$1.C:$2. Channel window adjust $3: $4 bytes'

        Parameters list:
              $1: ssh67-userid
              $2: ssh67-local-chan
              $3: ssh67-direction
              $4: ssh67-bytes

        Channel window adjust message received/sent indicating bytes to add."
    ::= { sshNotificationsPrefix 67 }

sshNotification68 NOTIFICATION-TYPE
    OBJECTS { 
              ssh68-userid, 
              ssh68-local-chan,
              ssh68-direction,
              ssh68-len 
            }
    STATUS current
    DESCRIPTION
        "Notification of Event SSH.68

        Message: 'U:$1.C:$2. Channel data $3 ($4 bytes)'

        Parameters list:
              $1: ssh68-userid
              $2: ssh68-local-chan
              $3: ssh68-direction
              $4: ssh68-len

        Channel data message received/sent."
    ::= { sshNotificationsPrefix 68 }

sshNotification69 NOTIFICATION-TYPE
    OBJECTS { 
              ssh69-userid, 
              ssh69-local-chan,
              ssh69-type,
              ssh69-direction,
              ssh69-len 
            }
    STATUS current
    DESCRIPTION
        "Notification of Event SSH.69

        Message: 'U:$1.C:$2. Extended channel data [type $3] $4 ($5 bytes)'

        Parameters list:
              $1: ssh69-userid
              $2: ssh69-local-chan
              $3: ssh69-type
              $4: ssh69-direction
              $5: ssh69-len

        Extended channel data message received/sent."
    ::= { sshNotificationsPrefix 69 }

sshNotification70 NOTIFICATION-TYPE
    OBJECTS { 
              ssh70-userid, 
              ssh70-local-chan,
              ssh70-direction 
            }
    STATUS current
    DESCRIPTION
        "Notification of Event SSH.70

        Message: 'U:$1.C:$2. EOF $3'

        Parameters list:
              $1: ssh70-userid
              $2: ssh70-local-chan
              $3: ssh70-direction

        EOF message received/sent."
    ::= { sshNotificationsPrefix 70 }

sshNotification71 NOTIFICATION-TYPE
    OBJECTS { 
              ssh71-userid, 
              ssh71-local-chan,
              ssh71-direction 
            }
    STATUS current
    DESCRIPTION
        "Notification of Event SSH.71

        Message: 'U:$1.C:$2. Channel close $3'

        Parameters list:
              $1: ssh71-userid
              $2: ssh71-local-chan
              $3: ssh71-direction

        Channel close message received/sent."
    ::= { sshNotificationsPrefix 71 }

sshNotification72 NOTIFICATION-TYPE
    OBJECTS { 
              ssh72-userid, 
              ssh72-local-chan,
              ssh72-request,
              ssh72-direction,
              ssh72-confirm,
              ssh72-data 
            }
    STATUS current
    DESCRIPTION
        "Notification of Event SSH.72

        Message: 'U:$1.C:$2. Channel request $3 $4. Confirm: $5. Data: $6'

        Parameters list:
              $1: ssh72-userid
              $2: ssh72-local-chan
              $3: ssh72-request
              $4: ssh72-direction
              $5: ssh72-confirm
              $6: ssh72-data

        Channel request message received/sent that may be confirmed, with extra data."
    ::= { sshNotificationsPrefix 72 }

sshNotification73 NOTIFICATION-TYPE
    OBJECTS { 
              ssh73-userid, 
              ssh73-local-chan,
              ssh73-request 
            }
    STATUS current
    DESCRIPTION
        "Notification of Event SSH.73

        Message: 'U:$1.C:$2. Channel request $3 failed'

        Parameters list:
              $1: ssh73-userid
              $2: ssh73-local-chan
              $3: ssh73-request

        Channel failure message indicating that a previous request was refused."
    ::= { sshNotificationsPrefix 73 }

sshNotification74 NOTIFICATION-TYPE
    OBJECTS { 
              ssh74-userid, 
              ssh74-local-chan 
            }
    STATUS current
    DESCRIPTION
        "Notification of Event SSH.74

        Message: 'U:$1.C:$2. New pty allocated'

        Parameters list:
              $1: ssh74-userid
              $2: ssh74-local-chan

        Event related to the allocation of a new pseudo-terminal."
    ::= { sshNotificationsPrefix 74 }

sshNotification75 NOTIFICATION-TYPE
    OBJECTS { 
              ssh75-userid, 
              ssh75-local-chan 
            }
    STATUS current
    DESCRIPTION
        "Notification of Event SSH.75

        Message: 'U:$1.C:$2. New console created'

        Parameters list:
              $1: ssh75-userid
              $2: ssh75-local-chan

        Event related to the creation of a new console."
    ::= { sshNotificationsPrefix 75 }

sshNotification76 NOTIFICATION-TYPE
    OBJECTS { 
              ssh76-userid, 
              ssh76-local-chan,
              ssh76-description 
            }
    STATUS current
    DESCRIPTION
        "Notification of Event SSH.76

        Message: 'U:$1.C:$2. SSHv1: $3'

        Parameters list:
              $1: ssh76-userid
              $2: ssh76-local-chan
              $3: ssh76-description

        Event related to a SSHv1 channel."
    ::= { sshNotificationsPrefix 76 }

sshNotification77 NOTIFICATION-TYPE
    OBJECTS { 
              ssh77-userid, 
              ssh77-local-chan,
              ssh77-description 
            }
    STATUS current
    DESCRIPTION
        "Notification of Event SSH.77

        Message: 'U:$1.C:$2. Channel verbose: $3'

        Parameters list:
              $1: ssh77-userid
              $2: ssh77-local-chan
              $3: ssh77-description

        Verbose information about channel."
    ::= { sshNotificationsPrefix 77 }

sshNotification78 NOTIFICATION-TYPE
    OBJECTS { 
              ssh78-userid, 
              ssh78-local-chan,
              ssh78-description 
            }
    STATUS current
    DESCRIPTION
        "Notification of Event SSH.78

        Message: 'U:$1.C:$2. Channel error: $3'

        Parameters list:
              $1: ssh78-userid
              $2: ssh78-local-chan
              $3: ssh78-description

        Error found in channel."
    ::= { sshNotificationsPrefix 78 }


END
