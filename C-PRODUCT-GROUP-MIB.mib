C-PRODUCT-GROUP-MIB DEFINITIONS ::= BEGIN

-- IMPORTS enterprises FROM RFC1155-SMI;
IMPORTS atm   FROM A3Com-products-MIB;

config      OBJECT IDENTIFIER ::= { atm 1 }
access9600  OBJECT IDENTIFIER ::= { atm 2 }
access9300  OBJECT IDENTIFIER ::= { atm 3 }
access9100  OBJECT IDENTIFIER ::= { atm 4 }
mojave      OBJECT IDENTIFIER ::= { atm 5 }

c-product   OBJECT IDENTIFIER ::= { config 1  }

-- groups in CS600
-- all enterprise-specific groups in cs600 are defined here

sys         OBJECT IDENTIFIER ::= { c-product 1  }
shelf       OBJECT IDENTIFIER ::= { c-product 2  }
card        OBJECT IDENTIFIER ::= { c-product 3  }
port        OBJECT IDENTIFIER ::= { c-product 4  }
circuit     OBJECT IDENTIFIER ::= { c-product 5  }
fault       OBJECT IDENTIFIER ::= { c-product 6  }

ds3card     OBJECT IDENTIFIER ::= { c-product 11 }
qsim        OBJECT IDENTIFIER ::= { c-product 12 }
e3card      OBJECT IDENTIFIER ::= { c-product 13 }
hssicard    OBJECT IDENTIFIER ::= { c-product 14 }
cbr    	    OBJECT IDENTIFIER ::= { c-product 15 }
oc3card	    OBJECT IDENTIFIER ::= { c-product 16 }
enetcard    OBJECT IDENTIFIER ::= { c-product 17 }
mcpu        OBJECT IDENTIFIER ::= { c-product 18 }
ima         OBJECT IDENTIFIER ::= { c-product 19 }
ctx         OBJECT IDENTIFIER ::= { c-product 20 }

END
