-- Teldat, S.A.

                -- Parque Tecnolgico de Madrid

                -- 28760, Tres Cantos (Madrid)

                -- Tlf: +34-918076565

                -- Fax: +34-918076521

                -- e-mail: id@teldat.com


            -- MIB privada de Teldat

            -- Monitorizacin del interfaz del switch


    -- Historial:
    --      07-02-14    M.A. Pastor     XH 3523. Errors with HP Openview 9.20
    -- 1.6  11-01-13    E. Amorena      XH 2610. MIBs compilation.
    -- 1.5  03/01/13  F. Hernandez     XH 2610. Compilation error
    -- 1.4  05-10-12   I. Munoz      XH-2345. Fix mib compilation error
    -- 1.3  27-09-12   I. Munoz      XH-2345. Imports the counter type
    -- 1.2  06-09-12   I. Munoz      XH-2345. Se ade campo teldatSwitchPortSpeed a
    --                   la tabla teldatSwitchPortTable y se cambian algunos
    --                   INTEGER por COUNTER
    -- 1.1  08-07-09   I. Munoz      Revisin de todas las MIB para evitar
    --                 M.A. Pastor   warnings y errores de compilacin
    -- 1.0  6-05-09    I. Munoz      Implementacin inicial
--------------------------------------------------------------------------------

TELDAT-MON-INTERF-SWITCH-MIB DEFINITIONS ::= BEGIN

IMPORTS
    IpAddress, Counter, Gauge
        FROM RFC1155-SMI
    OBJECT-TYPE
        FROM RFC-1212
    telProdNpMonInterfRouter
        FROM TELDAT-SW-STRUCTURE-MIB;


-- Monitorizacin privada del switch

telProdNpMonInterfSwitch OBJECT IDENTIFIER ::= { telProdNpMonInterfRouter 21 }


--  = = = = = = = = = = = = = = = = = = = = = = = = = = = = = = = = = = = = = =
--  Global Switch monitoring port variables
--  = = = = = = = = = = = = = = = = = = = = = = = = = = = = = = = = = = = = = =


--  = = = = = = = = = = = = = = = = = = = = = = = = = = = = = = = = = = = = = =
--  Global  monitoring port variables
--  = = = = = = = = = = = = = = = = = = = = = = = = = = = = = = = = = = = = = =

teldatSwitchPortTable OBJECT-TYPE
    SYNTAX  SEQUENCE OF TeldatSwitchPortEntry
    ACCESS  not-accessible
    STATUS  mandatory
    DESCRIPTION
        "Table of information available for switch ports.
        Each row represents an port"
    ::= { telProdNpMonInterfSwitch 1 }

teldatSwitchPortEntry OBJECT-TYPE
    SYNTAX  TeldatSwitchPortEntry
    ACCESS  not-accessible
    STATUS  mandatory
    DESCRIPTION
        "A base list of objects that are information about a switch port.
        The index is the number of port"
    INDEX   { teldatSwitchInterfaceIndex, teldatSwitchPortIndex}
    ::= { teldatSwitchPortTable 1 }

TeldatSwitchPortEntry ::= SEQUENCE
{
    teldatSwitchInterfaceIndex                          INTEGER,
    teldatSwitchPortIndex                               INTEGER,
    teldatSwitchOutTraffic                              Counter,
    teldatSwitchOutErrors                               Counter,
    teldatSwitchInDisPkts                               Counter,
    teldatSwitchOutDisPkts                              Counter,
    teldatSwitchOutBroadTraffic                         Counter,
    teldatSwitchPortSpeed                               Gauge
}

teldatSwitchInterfaceIndex OBJECT-TYPE
    SYNTAX  INTEGER
    ACCESS  read-only
    STATUS  mandatory
    DESCRIPTION
        "Interface index."
    ::= { teldatSwitchPortEntry 1 }

teldatSwitchPortIndex OBJECT-TYPE
    SYNTAX  INTEGER
    ACCESS  read-only
    STATUS  mandatory
    DESCRIPTION
        "Port index."
    ::={ teldatSwitchPortEntry 2 }

teldatSwitchOutTraffic OBJECT-TYPE
    SYNTAX  Counter
    ACCESS  read-only
    STATUS  mandatory
    DESCRIPTION
        "Output traffic on this port."
    ::={ teldatSwitchPortEntry 3 }

teldatSwitchOutErrors OBJECT-TYPE
    SYNTAX  Counter
    ACCESS  read-only
    STATUS  mandatory
    DESCRIPTION
        "Output errors on this port."
    ::={ teldatSwitchPortEntry 4 }

teldatSwitchInDisPkts OBJECT-TYPE
    SYNTAX  Counter
    ACCESS  read-only
    STATUS  mandatory
    DESCRIPTION
        "Input discard packets."
    ::={ teldatSwitchPortEntry 5 }

teldatSwitchOutDisPkts OBJECT-TYPE
    SYNTAX  Counter
    ACCESS  read-only
    STATUS  mandatory
    DESCRIPTION
        "Output discard packtes."
    ::={ teldatSwitchPortEntry 6}

teldatSwitchOutBroadTraffic OBJECT-TYPE
    SYNTAX  Counter
    ACCESS  read-only
    STATUS  mandatory
    DESCRIPTION
        "Output broadast traffic."
    ::={ teldatSwitchPortEntry 7 }

teldatSwitchPortSpeed OBJECT-TYPE
    SYNTAX  Gauge
    ACCESS  read-only
    STATUS  mandatory
    DESCRIPTION
        "Port's current speed in bits per second."
    ::={ teldatSwitchPortEntry 8 }

END
