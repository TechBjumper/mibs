--  ************************************************
--  $Id: ZXROSNG-L2L3VPN-BRIDGE-MIB.mib 12 2005-07-13 01:01:17Z taowq $
--
--  ZXR10-ETH-MGT.mib: ZXR10 ethnet query and  configuration MIB file
--  
--  Jun. 2005, Tao wenqiang
--   
--  Copyright(c) 2005 by ZTE Corporaton
--  All rights reservered
--
--  ************************************************

ZXROSNG-L2L3VPN-BRIDGE-MIB DEFINITIONS ::= BEGIN

IMPORTS
    MODULE-IDENTITY, 
    OBJECT-TYPE, enterprises
        FROM SNMPv2-SMI
   zxr10interfaces
        FROM ZXR10-SMI
   TimeStamp,
   DisplayString   
        FROM SNMPv2-TC 
  RowStatus                           
        FROM SNMPv2-TC;      
 -- MODULE
    zxL2L3VPNBridgeModule MODULE-IDENTITY
    LAST-UPDATED "200504120000Z"  -- Feb 12, 2010
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS v4.6.03 ethnet query and configuration MIB"

    REVISION "200504120000Z"  -- April 12, 2005
    DESCRIPTION
       ""

    ::= { zxr10RosngMIB 501 }

    zte   OBJECT IDENTIFIER ::= { enterprises 3902 }  
    zxr10 OBJECT IDENTIFIER ::= { zte 3 }
    zxr10RosngMIB OBJECT IDENTIFIER ::= { zxr10 6000 }

    zxL2L3VPNBridgeEanble       OBJECT IDENTIFIER ::= { zxL2L3VPNBridgeModule 1 }                    
                                 
    
    Link ::=INTEGER
              {
                 disable(0),
                 enable(1)
              } 
-- self define type 
 --   DisplayString ::= OCTET STRING
    --  This data type is used to model textual information taken
    --  from the NVT ASCII character set.  By convention, objects
    --  with this syntax are declared as having
    --  SIZE (0..255)
-- self define type               
-- Posnet physic interface configuration table       
        zxL2L3VPNBridgeEanble OBJECT-TYPE
             SYNTAX      Link
             MAX-ACCESS  read-write
             STATUS      current
             DESCRIPTION
               "L2L3vpnServicelink"
             ::= { zxL2L3VPNBridgeModule 1 }

 

     zxL2L3VPNVirLinkTable  OBJECT-TYPE
        SYNTAX  SEQUENCE OF ZxL2L3VPNVirLinkEntry
        MAX-ACCESS  not-accessible
        STATUS  current
        DESCRIPTION
            ""
        ::= { zxL2L3VPNBridgeModule 2 }

    zxL2L3VPNVirLinkEntry  OBJECT-TYPE
        SYNTAX  ZxL2L3VPNVirLinkEntry
        MAX-ACCESS  not-accessible
        STATUS  current
        DESCRIPTION
            ""
        INDEX  { zxL2L3VPNVirLinkSrcUleiIf }
        ::= { zxL2L3VPNVirLinkTable 1 }

    ZxL2L3VPNVirLinkEntry ::=
        SEQUENCE {
            zxL2L3VPNVirLinkSrcUleiIf
                DisplayString,
            zxL2L3VPNVirLinkDstUleiIf
                DisplayString,
            zxL2L3VPNVirLinkRowStatus
                RowStatus                             
                                                                                                                                                 
    }

    zxL2L3VPNVirLinkSrcUleiIf  OBJECT-TYPE
        SYNTAX  DisplayString(SIZE(0..32))
        MAX-ACCESS  not-accessible 
        STATUS  current
        DESCRIPTION
            "Source interface name"
        ::= { zxL2L3VPNVirLinkEntry 1 }    


    zxL2L3VPNVirLinkDstUleiIf OBJECT-TYPE
        SYNTAX   DisplayString(SIZE(0..32))
        MAX-ACCESS  read-create
        STATUS  current
        DESCRIPTION
            "Destination interface name"
        ::= { zxL2L3VPNVirLinkEntry 2 }          

    zxL2L3VPNVirLinkRowStatus OBJECT-TYPE
        SYNTAX  RowStatus
        MAX-ACCESS  read-create
        STATUS  current
        DESCRIPTION
            "VPN virtual link row status"
        ::= { zxL2L3VPNVirLinkEntry 3 } 
 END
