-- file automatically created


TELDAT-TRAP-SRVP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


srvpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SRVP event subsystem."
    REVISION "201401200930Z"
    DESCRIPTION "Initial implementation"
        ::= { telEventTraps 222 }


srvpEventsGroup	OBJECT IDENTIFIER	::= { srvpTrapsMIB 1 }

srvpNotifications	OBJECT IDENTIFIER	::= { srvpTrapsMIB 2 }
srvpNotificationsPrefix	OBJECT IDENTIFIER	::= { srvpNotifications 0 }

srvpEventObjects1 OBJECT-IDENTITY
    STATUS current
    DESCRIPTION
        "Event SRVP.1
        A packet has been classified in the class-map"
    ::= { srvpEventsGroup 1 }

srvp1-class-name OBJECT-TYPE
    SYNTAX DisplayString
    MAX-ACCESS accessible-for-notify
    STATUS current
    DESCRIPTION
        "Parameter 'class-name' in event SRVP.1"
    ::= { srvpEventObjects1 1 }

srvp1-interface-name OBJECT-TYPE
    SYNTAX DisplayString
    MAX-ACCESS accessible-for-notify
    STATUS current
    DESCRIPTION
        "Parameter 'interface-name' in event SRVP.1"
    ::= { srvpEventObjects1 2 }

srvpEventObjects2 OBJECT-IDENTITY
    STATUS current
    DESCRIPTION
        "Event SRVP.2
        A packet has been discarded by the class-map"
    ::= { srvpEventsGroup 2 }

srvp2-class-name OBJECT-TYPE
    SYNTAX DisplayString
    MAX-ACCESS accessible-for-notify
    STATUS current
    DESCRIPTION
        "Parameter 'class-name' in event SRVP.2"
    ::= { srvpEventObjects2 1 }

srvp2-interface-name OBJECT-TYPE
    SYNTAX DisplayString
    MAX-ACCESS accessible-for-notify
    STATUS current
    DESCRIPTION
        "Parameter 'interface-name' in event SRVP.2"
    ::= { srvpEventObjects2 2 }

srvpEventObjects3 OBJECT-IDENTITY
    STATUS current
    DESCRIPTION
        "Event SRVP.3
        A packet has not matched with an access-list"
    ::= { srvpEventsGroup 3 }

srvp3-prtcl-type OBJECT-TYPE
    SYNTAX DisplayString
    MAX-ACCESS accessible-for-notify
    STATUS current
    DESCRIPTION
        "Parameter 'prtcl-type' in event SRVP.3"
    ::= { srvpEventObjects3 1 }

srvp3-acl-num OBJECT-TYPE
    SYNTAX Integer32
    MAX-ACCESS accessible-for-notify
    STATUS current
    DESCRIPTION
        "Parameter 'acl-num' in event SRVP.3"
    ::= { srvpEventObjects3 2 }

srvp3-interface-name OBJECT-TYPE
    SYNTAX DisplayString
    MAX-ACCESS accessible-for-notify
    STATUS current
    DESCRIPTION
        "Parameter 'interface-name' in event SRVP.3"
    ::= { srvpEventObjects3 3 }

srvpEventObjects4 OBJECT-IDENTITY
    STATUS current
    DESCRIPTION
        "Event SRVP.4
        Notifies when service policy is started properly"
    ::= { srvpEventsGroup 4 }

srvp4-interface-name OBJECT-TYPE
    SYNTAX DisplayString
    MAX-ACCESS accessible-for-notify
    STATUS current
    DESCRIPTION
        "Parameter 'interface-name' in event SRVP.4"
    ::= { srvpEventObjects4 1 }

srvpEventObjects5 OBJECT-IDENTITY
    STATUS current
    DESCRIPTION
        "Event SRVP.5
        Notifies when service policy is disabled"
    ::= { srvpEventsGroup 5 }

srvp5-interface-name OBJECT-TYPE
    SYNTAX DisplayString
    MAX-ACCESS accessible-for-notify
    STATUS current
    DESCRIPTION
        "Parameter 'interface-name' in event SRVP.5"
    ::= { srvpEventObjects5 1 }

srvpEventObjects6 OBJECT-IDENTITY
    STATUS current
    DESCRIPTION
        "Event SRVP.6
        A packet has been transmitted to the protocol"
    ::= { srvpEventsGroup 6 }

srvp6-interface-name OBJECT-TYPE
    SYNTAX DisplayString
    MAX-ACCESS accessible-for-notify
    STATUS current
    DESCRIPTION
        "Parameter 'interface-name' in event SRVP.6"
    ::= { srvpEventObjects6 1 }

srvp6-prtcl OBJECT-TYPE
    SYNTAX DisplayString
    MAX-ACCESS accessible-for-notify
    STATUS current
    DESCRIPTION
        "Parameter 'prtcl' in event SRVP.6"
    ::= { srvpEventObjects6 2 }

srvpEventObjects7 OBJECT-IDENTITY
    STATUS current
    DESCRIPTION
        "Event SRVP.7
        A packet does not match with any class-map"
    ::= { srvpEventsGroup 7 }

srvp7-prtcl OBJECT-TYPE
    SYNTAX DisplayString
    MAX-ACCESS accessible-for-notify
    STATUS current
    DESCRIPTION
        "Parameter 'prtcl' in event SRVP.7"
    ::= { srvpEventObjects7 1 }

srvp7-interface-name OBJECT-TYPE
    SYNTAX DisplayString
    MAX-ACCESS accessible-for-notify
    STATUS current
    DESCRIPTION
        "Parameter 'interface-name' in event SRVP.7"
    ::= { srvpEventObjects7 2 }

srvpEventObjects8 OBJECT-IDENTITY
    STATUS current
    DESCRIPTION
        "Event SRVP.8
        A timer has been scheduled in a class-map"
    ::= { srvpEventsGroup 8 }

srvp8-timer-name OBJECT-TYPE
    SYNTAX DisplayString
    MAX-ACCESS accessible-for-notify
    STATUS current
    DESCRIPTION
        "Parameter 'timer-name' in event SRVP.8"
    ::= { srvpEventObjects8 1 }

srvp8-class-name OBJECT-TYPE
    SYNTAX DisplayString
    MAX-ACCESS accessible-for-notify
    STATUS current
    DESCRIPTION
        "Parameter 'class-name' in event SRVP.8"
    ::= { srvpEventObjects8 2 }

srvp8-new-time OBJECT-TYPE
    SYNTAX Integer32
    MAX-ACCESS accessible-for-notify
    STATUS current
    DESCRIPTION
        "Parameter 'new-time' in event SRVP.8"
    ::= { srvpEventObjects8 3 }

srvp8-new-time-out OBJECT-TYPE
    SYNTAX Integer32
    MAX-ACCESS accessible-for-notify
    STATUS current
    DESCRIPTION
        "Parameter 'new-time-out' in event SRVP.8"
    ::= { srvpEventObjects8 4 }

srvpEventObjects9 OBJECT-IDENTITY
    STATUS current
    DESCRIPTION
        "Event SRVP.9
        A timer has expired in a class-map"
    ::= { srvpEventsGroup 9 }

srvp9-timer-name OBJECT-TYPE
    SYNTAX DisplayString
    MAX-ACCESS accessible-for-notify
    STATUS current
    DESCRIPTION
        "Parameter 'timer-name' in event SRVP.9"
    ::= { srvpEventObjects9 1 }

srvp9-class-name OBJECT-TYPE
    SYNTAX DisplayString
    MAX-ACCESS accessible-for-notify
    STATUS current
    DESCRIPTION
        "Parameter 'class-name' in event SRVP.9"
    ::= { srvpEventObjects9 2 }

srvpEventObjects10 OBJECT-IDENTITY
    STATUS current
    DESCRIPTION
        "Event SRVP.10
        A packet has been tagged with a new label value"
    ::= { srvpEventsGroup 10 }

srvp10-class-name OBJECT-TYPE
    SYNTAX DisplayString
    MAX-ACCESS accessible-for-notify
    STATUS current
    DESCRIPTION
        "Parameter 'class-name' in event SRVP.10"
    ::= { srvpEventObjects10 1 }

srvp10-num-label OBJECT-TYPE
    SYNTAX Integer32
    MAX-ACCESS accessible-for-notify
    STATUS current
    DESCRIPTION
        "Parameter 'num-label' in event SRVP.10"
    ::= { srvpEventObjects10 2 }

srvpEventObjects12 OBJECT-IDENTITY
    STATUS current
    DESCRIPTION
        "Event SRVP.12
        A packet has not the same cos value"
    ::= { srvpEventsGroup 12 }

srvp12-cos-pkt OBJECT-TYPE
    SYNTAX Integer32
    MAX-ACCESS accessible-for-notify
    STATUS current
    DESCRIPTION
        "Parameter 'cos-pkt' in event SRVP.12"
    ::= { srvpEventObjects12 1 }

srvp12-cos-config OBJECT-TYPE
    SYNTAX Integer32
    MAX-ACCESS accessible-for-notify
    STATUS current
    DESCRIPTION
        "Parameter 'cos-config' in event SRVP.12"
    ::= { srvpEventObjects12 2 }

srvpEventObjects13 OBJECT-IDENTITY
    STATUS current
    DESCRIPTION
        "Event SRVP.13
        A packet has not the same src MAC addr value"
    ::= { srvpEventsGroup 13 }

srvp13-src-mac-addr-pkt OBJECT-TYPE
    SYNTAX DisplayString
    MAX-ACCESS accessible-for-notify
    STATUS current
    DESCRIPTION
        "Parameter 'src-mac-addr-pkt' in event SRVP.13"
    ::= { srvpEventObjects13 1 }

srvp13-src-mac-addr-config OBJECT-TYPE
    SYNTAX DisplayString
    MAX-ACCESS accessible-for-notify
    STATUS current
    DESCRIPTION
        "Parameter 'src-mac-addr-config' in event SRVP.13"
    ::= { srvpEventObjects13 2 }

srvpEventObjects14 OBJECT-IDENTITY
    STATUS current
    DESCRIPTION
        "Event SRVP.14
        A packet has not the same dst MAC addr value"
    ::= { srvpEventsGroup 14 }

srvp14-src-mac-addr-pkt OBJECT-TYPE
    SYNTAX DisplayString
    MAX-ACCESS accessible-for-notify
    STATUS current
    DESCRIPTION
        "Parameter 'src-mac-addr-pkt' in event SRVP.14"
    ::= { srvpEventObjects14 1 }

srvp14-src-mac-addr-config OBJECT-TYPE
    SYNTAX DisplayString
    MAX-ACCESS accessible-for-notify
    STATUS current
    DESCRIPTION
        "Parameter 'src-mac-addr-config' in event SRVP.14"
    ::= { srvpEventObjects14 2 }

srvpEventObjects15 OBJECT-IDENTITY
    STATUS current
    DESCRIPTION
        "Event SRVP.15
        A packet has the same [not] src/dst MAC address value, and then the packet is discarded"
    ::= { srvpEventsGroup 15 }

srvp15-mac-addr-type OBJECT-TYPE
    SYNTAX DisplayString
    MAX-ACCESS accessible-for-notify
    STATUS current
    DESCRIPTION
        "Parameter 'mac-addr-type' in event SRVP.15"
    ::= { srvpEventObjects15 1 }

srvp15-mac-addr-pkt OBJECT-TYPE
    SYNTAX DisplayString
    MAX-ACCESS accessible-for-notify
    STATUS current
    DESCRIPTION
        "Parameter 'mac-addr-pkt' in event SRVP.15"
    ::= { srvpEventObjects15 2 }

srvp15-mac-addr-type-config OBJECT-TYPE
    SYNTAX DisplayString
    MAX-ACCESS accessible-for-notify
    STATUS current
    DESCRIPTION
        "Parameter 'mac-addr-type-config' in event SRVP.15"
    ::= { srvpEventObjects15 3 }

srvp15-mac-addr-config OBJECT-TYPE
    SYNTAX DisplayString
    MAX-ACCESS accessible-for-notify
    STATUS current
    DESCRIPTION
        "Parameter 'mac-addr-config' in event SRVP.15"
    ::= { srvpEventObjects15 4 }

srvpEventObjects16 OBJECT-IDENTITY
    STATUS current
    DESCRIPTION
        "Event SRVP.16
        A packet has matched with an access-list"
    ::= { srvpEventsGroup 16 }

srvp16-msg-prtcl-type OBJECT-TYPE
    SYNTAX DisplayString
    MAX-ACCESS accessible-for-notify
    STATUS current
    DESCRIPTION
        "Parameter 'msg-prtcl-type' in event SRVP.16"
    ::= { srvpEventObjects16 1 }

srvp16-acl-num OBJECT-TYPE
    SYNTAX Integer32
    MAX-ACCESS accessible-for-notify
    STATUS current
    DESCRIPTION
        "Parameter 'acl-num' in event SRVP.16"
    ::= { srvpEventObjects16 2 }

srvp16-interface-name OBJECT-TYPE
    SYNTAX DisplayString
    MAX-ACCESS accessible-for-notify
    STATUS current
    DESCRIPTION
        "Parameter 'interface-name' in event SRVP.16"
    ::= { srvpEventObjects16 3 }

srvpEventObjects17 OBJECT-IDENTITY
    STATUS current
    DESCRIPTION
        "Event SRVP.17
        A packet has the same cos value src"
    ::= { srvpEventsGroup 17 }

srvp17-cos-pkt OBJECT-TYPE
    SYNTAX Integer32
    MAX-ACCESS accessible-for-notify
    STATUS current
    DESCRIPTION
        "Parameter 'cos-pkt' in event SRVP.17"
    ::= { srvpEventObjects17 1 }

srvpEventObjects18 OBJECT-IDENTITY
    STATUS current
    DESCRIPTION
        "Event SRVP.18
        A packet has the same src/dst MAC address value"
    ::= { srvpEventsGroup 18 }

srvp18-mac-addr-type OBJECT-TYPE
    SYNTAX DisplayString
    MAX-ACCESS accessible-for-notify
    STATUS current
    DESCRIPTION
        "Parameter 'mac-addr-type' in event SRVP.18"
    ::= { srvpEventObjects18 1 }

srvp18-mac-addr-pkt OBJECT-TYPE
    SYNTAX DisplayString
    MAX-ACCESS accessible-for-notify
    STATUS current
    DESCRIPTION
        "Parameter 'mac-addr-pkt' in event SRVP.18"
    ::= { srvpEventObjects18 2 }

srvp18-mac-addr-type-config OBJECT-TYPE
    SYNTAX DisplayString
    MAX-ACCESS accessible-for-notify
    STATUS current
    DESCRIPTION
        "Parameter 'mac-addr-type-config' in event SRVP.18"
    ::= { srvpEventObjects18 3 }

srvp18-mac-addr-config OBJECT-TYPE
    SYNTAX DisplayString
    MAX-ACCESS accessible-for-notify
    STATUS current
    DESCRIPTION
        "Parameter 'mac-addr-config' in event SRVP.18"
    ::= { srvpEventObjects18 4 }

srvpEventObjects19 OBJECT-IDENTITY
    STATUS current
    DESCRIPTION
        "Event SRVP.19
        A packet has a different src/dst MAC address value"
    ::= { srvpEventsGroup 19 }

srvp19-mac-addr-type OBJECT-TYPE
    SYNTAX DisplayString
    MAX-ACCESS accessible-for-notify
    STATUS current
    DESCRIPTION
        "Parameter 'mac-addr-type' in event SRVP.19"
    ::= { srvpEventObjects19 1 }

srvp19-mac-addr-pkt OBJECT-TYPE
    SYNTAX DisplayString
    MAX-ACCESS accessible-for-notify
    STATUS current
    DESCRIPTION
        "Parameter 'mac-addr-pkt' in event SRVP.19"
    ::= { srvpEventObjects19 2 }

srvp19-mac-addr-config OBJECT-TYPE
    SYNTAX DisplayString
    MAX-ACCESS accessible-for-notify
    STATUS current
    DESCRIPTION
        "Parameter 'mac-addr-config' in event SRVP.19"
    ::= { srvpEventObjects19 3 }

srvp19-mac-addr-type-config OBJECT-TYPE
    SYNTAX DisplayString
    MAX-ACCESS accessible-for-notify
    STATUS current
    DESCRIPTION
        "Parameter 'mac-addr-type-config' in event SRVP.19"
    ::= { srvpEventObjects19 4 }

srvpEventObjects20 OBJECT-IDENTITY
    STATUS current
    DESCRIPTION
        "Event SRVP.20
        A packet has been discarded by policing (rate-limit)"
    ::= { srvpEventsGroup 20 }

srvp20-protocol-type OBJECT-TYPE
    SYNTAX DisplayString
    MAX-ACCESS accessible-for-notify
    STATUS current
    DESCRIPTION
        "Parameter 'protocol-type' in event SRVP.20"
    ::= { srvpEventObjects20 1 }

srvp20-class-name OBJECT-TYPE
    SYNTAX DisplayString
    MAX-ACCESS accessible-for-notify
    STATUS current
    DESCRIPTION
        "Parameter 'class-name' in event SRVP.20"
    ::= { srvpEventObjects20 2 }

srvp20-interface-name OBJECT-TYPE
    SYNTAX DisplayString
    MAX-ACCESS accessible-for-notify
    STATUS current
    DESCRIPTION
        "Parameter 'interface-name' in event SRVP.20"
    ::= { srvpEventObjects20 3 }


srvpNotification1 NOTIFICATION-TYPE
    OBJECTS { 
              srvp1-class-name, 
              srvp1-interface-name 
            }
    STATUS current
    DESCRIPTION
        "Notification of Event SRVP.1

        Message: 'packet has been classified class-map $1 at interface $2'

        Parameters list:
              $1: srvp1-class-name
              $2: srvp1-interface-name

        A packet has been classified in the class-map"
    ::= { srvpNotificationsPrefix 1 }

srvpNotification2 NOTIFICATION-TYPE
    OBJECTS { 
              srvp2-class-name, 
              srvp2-interface-name 
            }
    STATUS current
    DESCRIPTION
        "Notification of Event SRVP.2

        Message: 'packet has been discarded by the class-map $1 at interface $2'

        Parameters list:
              $1: srvp2-class-name
              $2: srvp2-interface-name

        A packet has been discarded by the class-map"
    ::= { srvpNotificationsPrefix 2 }

srvpNotification3 NOTIFICATION-TYPE
    OBJECTS { 
              srvp3-prtcl-type, 
              srvp3-acl-num,
              srvp3-interface-name 
            }
    STATUS current
    DESCRIPTION
        "Notification of Event SRVP.3

        Message: 'a packet of protocol $1 does not match with ACL $2 at interface $3'

        Parameters list:
              $1: srvp3-prtcl-type
              $2: srvp3-acl-num
              $3: srvp3-interface-name

        A packet has not matched with an access-list"
    ::= { srvpNotificationsPrefix 3 }

srvpNotification4 NOTIFICATION-TYPE
    OBJECTS { 
              srvp4-interface-name 
            }
    STATUS current
    DESCRIPTION
        "Notification of Event SRVP.4

        Message: 'service policy is enabled at the interface $1'

        Parameters list:
              $1: srvp4-interface-name

        Notifies when service policy is started properly"
    ::= { srvpNotificationsPrefix 4 }

srvpNotification5 NOTIFICATION-TYPE
    OBJECTS { 
              srvp5-interface-name 
            }
    STATUS current
    DESCRIPTION
        "Notification of Event SRVP.5

        Message: 'service policy is disabled at the interface $1'

        Parameters list:
              $1: srvp5-interface-name

        Notifies when service policy is disabled"
    ::= { srvpNotificationsPrefix 5 }

srvpNotification6 NOTIFICATION-TYPE
    OBJECTS { 
              srvp6-interface-name, 
              srvp6-prtcl 
            }
    STATUS current
    DESCRIPTION
        "Notification of Event SRVP.6

        Message: 'packet transmitted from interface $1 to the protocol $2'

        Parameters list:
              $1: srvp6-interface-name
              $2: srvp6-prtcl

        A packet has been transmitted to the protocol"
    ::= { srvpNotificationsPrefix 6 }

srvpNotification7 NOTIFICATION-TYPE
    OBJECTS { 
              srvp7-prtcl, 
              srvp7-interface-name 
            }
    STATUS current
    DESCRIPTION
        "Notification of Event SRVP.7

        Message: 'packet of protocol $1 at interface $2 does not match with any class-map'

        Parameters list:
              $1: srvp7-prtcl
              $2: srvp7-interface-name

        A packet does not match with any class-map"
    ::= { srvpNotificationsPrefix 7 }

srvpNotification8 NOTIFICATION-TYPE
    OBJECTS { 
              srvp8-timer-name, 
              srvp8-class-name,
              srvp8-new-time,
              srvp8-new-time-out 
            }
    STATUS current
    DESCRIPTION
        "Notification of Event SRVP.8

        Message: 'timer '$1' launched on class-map $2 new time $3, new time-out $4'

        Parameters list:
              $1: srvp8-timer-name
              $2: srvp8-class-name
              $3: srvp8-new-time
              $4: srvp8-new-time-out

        A timer has been scheduled in a class-map"
    ::= { srvpNotificationsPrefix 8 }

srvpNotification9 NOTIFICATION-TYPE
    OBJECTS { 
              srvp9-timer-name, 
              srvp9-class-name 
            }
    STATUS current
    DESCRIPTION
        "Notification of Event SRVP.9

        Message: 'timer '$1' has expired in class-map $2'

        Parameters list:
              $1: srvp9-timer-name
              $2: srvp9-class-name

        A timer has expired in a class-map"
    ::= { srvpNotificationsPrefix 9 }

srvpNotification10 NOTIFICATION-TYPE
    OBJECTS { 
              srvp10-class-name, 
              srvp10-num-label 
            }
    STATUS current
    DESCRIPTION
        "Notification of Event SRVP.10

        Message: 'Packet of class-map $1, has been tagged with the label $2'

        Parameters list:
              $1: srvp10-class-name
              $2: srvp10-num-label

        A packet has been tagged with a new label value"
    ::= { srvpNotificationsPrefix 10 }

srvpNotification11 NOTIFICATION-TYPE
    STATUS current
    DESCRIPTION
        "Notification of Event SRVP.11

        Message: 'match criteria is pending to be checked, packet not match'

        A packet has not enough information to check the match criteria"
    ::= { srvpNotificationsPrefix 11 }

srvpNotification12 NOTIFICATION-TYPE
    OBJECTS { 
              srvp12-cos-pkt, 
              srvp12-cos-config 
            }
    STATUS current
    DESCRIPTION
        "Notification of Event SRVP.12

        Message: 'packet cos $1 does not match with cos config value $2'

        Parameters list:
              $1: srvp12-cos-pkt
              $2: srvp12-cos-config

        A packet has not the same cos value"
    ::= { srvpNotificationsPrefix 12 }

srvpNotification13 NOTIFICATION-TYPE
    OBJECTS { 
              srvp13-src-mac-addr-pkt, 
              srvp13-src-mac-addr-config 
            }
    STATUS current
    DESCRIPTION
        "Notification of Event SRVP.13

        Message: 'packet MAC source address $1 does not match with the config value $2'

        Parameters list:
              $1: srvp13-src-mac-addr-pkt
              $2: srvp13-src-mac-addr-config

        A packet has not the same src MAC addr value"
    ::= { srvpNotificationsPrefix 13 }

srvpNotification14 NOTIFICATION-TYPE
    OBJECTS { 
              srvp14-src-mac-addr-pkt, 
              srvp14-src-mac-addr-config 
            }
    STATUS current
    DESCRIPTION
        "Notification of Event SRVP.14

        Message: 'packet MAC destination address $1 does not match with the config value $2'

        Parameters list:
              $1: srvp14-src-mac-addr-pkt
              $2: srvp14-src-mac-addr-config

        A packet has not the same dst MAC addr value"
    ::= { srvpNotificationsPrefix 14 }

srvpNotification15 NOTIFICATION-TYPE
    OBJECTS { 
              srvp15-mac-addr-type, 
              srvp15-mac-addr-pkt,
              srvp15-mac-addr-type-config,
              srvp15-mac-addr-config 
            }
    STATUS current
    DESCRIPTION
        "Notification of Event SRVP.15

        Message: 'packet MAC $1 address $2 match with the unwanted MAC $3 address config $4, packet is discarded'

        Parameters list:
              $1: srvp15-mac-addr-type
              $2: srvp15-mac-addr-pkt
              $3: srvp15-mac-addr-type-config
              $4: srvp15-mac-addr-config

        A packet has the same [not] src/dst MAC address value, and then the packet is discarded"
    ::= { srvpNotificationsPrefix 15 }

srvpNotification16 NOTIFICATION-TYPE
    OBJECTS { 
              srvp16-msg-prtcl-type, 
              srvp16-acl-num,
              srvp16-interface-name 
            }
    STATUS current
    DESCRIPTION
        "Notification of Event SRVP.16

        Message: 'a packet of protocol $1 matchs with ACL $2 at interface $3'

        Parameters list:
              $1: srvp16-msg-prtcl-type
              $2: srvp16-acl-num
              $3: srvp16-interface-name

        A packet has matched with an access-list"
    ::= { srvpNotificationsPrefix 16 }

srvpNotification17 NOTIFICATION-TYPE
    OBJECTS { 
              srvp17-cos-pkt 
            }
    STATUS current
    DESCRIPTION
        "Notification of Event SRVP.17

        Message: 'packet cos $1 matchs with cos config value'

        Parameters list:
              $1: srvp17-cos-pkt

        A packet has the same cos value src"
    ::= { srvpNotificationsPrefix 17 }

srvpNotification18 NOTIFICATION-TYPE
    OBJECTS { 
              srvp18-mac-addr-type, 
              srvp18-mac-addr-pkt,
              srvp18-mac-addr-type-config,
              srvp18-mac-addr-config 
            }
    STATUS current
    DESCRIPTION
        "Notification of Event SRVP.18

        Message: 'packet MAC $1 address $2 matchs with the MAC $3 address config value $4'

        Parameters list:
              $1: srvp18-mac-addr-type
              $2: srvp18-mac-addr-pkt
              $3: srvp18-mac-addr-type-config
              $4: srvp18-mac-addr-config

        A packet has the same src/dst MAC address value"
    ::= { srvpNotificationsPrefix 18 }

srvpNotification19 NOTIFICATION-TYPE
    OBJECTS { 
              srvp19-mac-addr-type, 
              srvp19-mac-addr-pkt,
              srvp19-mac-addr-config,
              srvp19-mac-addr-type-config 
            }
    STATUS current
    DESCRIPTION
        "Notification of Event SRVP.19

        Message: 'packet MAC $1 address $2, has a different MAC $3 address of the config value $4'

        Parameters list:
              $1: srvp19-mac-addr-type
              $2: srvp19-mac-addr-pkt
              $3: srvp19-mac-addr-config
              $4: srvp19-mac-addr-type-config

        A packet has a different src/dst MAC address value"
    ::= { srvpNotificationsPrefix 19 }

srvpNotification20 NOTIFICATION-TYPE
    OBJECTS { 
              srvp20-protocol-type, 
              srvp20-class-name,
              srvp20-interface-name 
            }
    STATUS current
    DESCRIPTION
        "Notification of Event SRVP.20

        Message: 'packet of protocol $1 has been discarded by policing of class-map $2 at interface $3'

        Parameters list:
              $1: srvp20-protocol-type
              $2: srvp20-class-name
              $3: srvp20-interface-name

        A packet has been discarded by policing (rate-limit)"
    ::= { srvpNotificationsPrefix 20 }


END
