PEA-BRIDGE-IPDSLAM DEFINITIONS ::= BEGIN


IMPORTS
    peaIpDslam
       FROM DIESEL-SMI
 
    TruthValue, TEXTUAL-CONVENTION, MacAddress, RowStatus, DateAndTime  
       FROM SNMPv2-TC

    MODULE-IDENTITY, Unsigned32, IpAddress,  
    NOTIFICATION-TYPE, OBJECT-TYPE, Counter32,
    Counter64 ,TimeTicks
        FROM SNMPv2-SMI

    InetAddressType, 
    InetAddress,
    InetPortNumber
        FROM INET-ADDRESS-MIB;
        
peaBridgeIpDslam MODULE-IDENTITY
    LAST-UPDATED 
         "200604251200Z"  
    ORGANIZATION
         "Ericsson Danmark A/S"
    CONTACT-INFO
         "
         Ericsson Diax 
         Faelledvej 17
         DK-7600 Struer
         Denmark

         E-mail: diax.support@ericsson.com
         "       
   DESCRIPTION
         " 
         The IP DSLAM software supports a number of standard 
         and proprietary MIBs.
         This MIB module defines objects for the management via 
         SNMP of the bridge functionality in the IP DSLAM.
         The bridge filter functionality from the IP DSLAM is 
         configurable not only per subscriber but also per PVC for 
         a specific subscriber. 
         All the subscribers connected to a specific 
         IP DSLAM share the same physically Ethernet interface, 
         and to protect the subscribers from each other (e.g. from 
         hacking and spoofing) the bridge is implemented with some 
         proprietary filters.

         One of these filters is a VLAN ID filter. With the use of
         this filter it is possible to limit the VLAN IDs that a
         end-user is allowed to use. 

         The filter is implemented as Access Control Lists, so
         the same filter can be attached to several end-users.

         For further information about this filter please see the
         description of the following parameters:
         - vlanIdAclTable
         - vlanIdAclRuleTable
         - pvcUpstreamVlanIdAclId
         - pvcDownstreamVlanIdAclId

         This mib contains subscriberInfoTable which contains a list of
         subscriber information that the IP-DSLAM has dynamically learned.
         From the table it is possible to read out following information
         of the subscriber :
          - MAC address
          - IP address
          - virtual MAC address
          - DHCP lease time
          - whether subscriber uses fixed forwarding functionality
          - gateway IP address
          - gateway MAC address

         This mib contains the mcastFilterTable which contains multicast
         filter information for a PVC. Each entry describes a range of
         consecutive multicast group addresses which are allowed or disallowed.
         Each multicast group address range is mapped to a multicast Vlan and 
         priority.

         This mib contains the broadcastStormControl and multicastStormControl
         which protect the network from upstream broadcast/multicast storms.
         They will limit the traffic to the thresholds, broadcastStormControlThreshold
         multicastStormControlThreshold respectively.
         They can be enabled/disabled with broadcastStormControl
         multicastStormControl respectively
         Traffic with all 48 bits in MAC address set to 1 is checked
         by broadcastStormControl. Traffic that is not broadcast, but with ethernet
         multicast bit set, is checked by multicastStormControl.
		 "                                                           

    ::= {peaIpDslam 30 }
    
bridgeControl		OBJECT IDENTIFIER ::= { peaBridgeIpDslam 1 }
 
-- NEW TYPES (textual conventions)
EthernetTypeList ::= TEXTUAL-CONVENTION
    DISPLAY-HINT	"2x,"
    STATUS			current
    DESCRIPTION
		"A list of EthernetType entries, each two byte in network byte order (big endian).
		 Example: EthernetTypeIp=0x800 => '0x08 0x00'"
    SYNTAX			OCTET STRING

    
LineIndex ::= INTEGER(0..2147483646)

--  END
    
lineIndex OBJECT-TYPE
	SYNTAX     LineIndex
    MAX-ACCESS  not-accessible
    STATUS      current
    DESCRIPTION
    "The ADSL subscriber line index."
    ::= { bridgeControl 1 }   

pvcIndex OBJECT-TYPE
	SYNTAX      Unsigned32 
    MAX-ACCESS  not-accessible
    STATUS      current
    DESCRIPTION
    "The PVC index."
    ::= { bridgeControl 2 }   
    
pvcTable OBJECT-TYPE
	SYNTAX      SEQUENCE OF PVCEntry
  	MAX-ACCESS  not-accessible
    STATUS      current
    DESCRIPTION
    "A list of entries to the PVCs."
    ::= { bridgeControl 3 }   
    
pvcEntry OBJECT-TYPE
	SYNTAX      PVCEntry
    MAX-ACCESS  not-accessible
    STATUS      current
    DESCRIPTION
    "An entry containing PVCs objects for the 
     subscriber line identified by lineIndex."
    INDEX  {lineIndex, pvcIndex }
    ::= { pvcTable 1 }     
    
PVCEntry ::= 
	SEQUENCE {
        vlanID							Unsigned32,
        pvcStatus						INTEGER,
        accessMethod                    INTEGER,
        priority			        	Unsigned32,
        allowBroadcast           		TruthValue,
        gatewayFixedForwarding			TruthValue,
        gatewayIP						IpAddress,
        useDHCP							TruthValue,
        downstreamFrameCount        	Counter32,
        upstreamFrameCount          	Counter32,
        downstreamByteCount         	Counter64,
        upstreamByteCount           	Counter64,
		vpi 							Unsigned32,
        vci 		                	Unsigned32,
        sustainableCellRate         	Unsigned32,
        peakCellRate         			Unsigned32,
        transparentBridging         	TruthValue,
        relayAgentConfiguration     	INTEGER,
        relayAgentString            	OCTET STRING,
        useICMPSecurity             	TruthValue,
        atmServiceCategory				INTEGER,
        downstreamMaximumBurstSize		Unsigned32,
        upstreamPeakCellRate			Unsigned32,
        upstreamSustainableCellRate     Unsigned32,
        upstreamMaximumBurstSize		Unsigned32,
        virtualMacAdressesAllowed       Unsigned32,
        allowIgmpSnooping               TruthValue,
        encapsulationProtocol			INTEGER,
        pppVariant						INTEGER,
        multicastGroupsAllowed          OCTET STRING,
		discardedOversizedFrames		Counter32,
        upstreamPolicing				TruthValue,
        upstreamPolicingCntr			Counter32, 
        floodMulticastAddrs				OCTET STRING,
        pppMruSubstitution				Unsigned32, 
        virtualMacEnable                INTEGER,
        macAddressCountLimit 			Unsigned32,
        innerVlanID                     Unsigned32,
        innerVlanPriority               Unsigned32,
        dhcpStatus						INTEGER, 
        gatewayStatus					INTEGER,
        ipConnectivityTest				INTEGER,
        insertMacInDhcpOption			Unsigned32,
        multicastGroupsLimit  			INTEGER,
        vlanTag                         INTEGER,
        innerVlanTag                    INTEGER,
        vlanOperation                   INTEGER,
        vlanFilter                      BITS,
        vlanPrioMappingPrio0            Unsigned32,
        vlanPrioMappingPrio1            Unsigned32,
        vlanPrioMappingPrio2            Unsigned32,
        vlanPrioMappingPrio3            Unsigned32,
        vlanPrioMappingPrio4            Unsigned32,
        vlanPrioMappingPrio5            Unsigned32,
        vlanPrioMappingPrio6            Unsigned32,
        vlanPrioMappingPrio7            Unsigned32,
        downstreamFlows                 OCTET STRING,
        upstreamFlows                   OCTET STRING,
        flowIdentificationCriterionDownstream	INTEGER, 
        flowIdentificationCriterionUpstream		INTEGER, 
        schedulingScheme  				INTEGER,
        floodDownstreamUnknownDestMac   TruthValue,
        l2cpTunneling                   BITS,
        upstreamMcastEnable             TruthValue,
        clearDhcpLeaseTable             INTEGER,
        clearMACHistory					TruthValue,
        gatewayMacfilteringDirection    INTEGER,
        downstreamFramesPerSecond		Unsigned32,
        upstreamFramesPerSecond			Unsigned32,
        downstreamBitsPerSecond			Unsigned32,
        upstreamBitsPerSecond			Unsigned32,
        arpProxyConfig                  INTEGER,
        endUserVlanOperation            INTEGER,
        vlanIdFilter                    Unsigned32,
        pvcFilterVersion                INTEGER,
        pvcUpstreamVlanIdAclId          Unsigned32,
        pvcDownstreamVlanIdAclId        Unsigned32,
        pvcUpstreamEtherTypeAclId		Unsigned32,
        pvcDownstreamEtherTypeAclId		Unsigned32,
        pvcUpstreamIpAclId              Unsigned32,
        pvcDownstreamIpAclId  			Unsigned32,
        dhcpServerMacAddress			MacAddress,
        allowAnonymousMulticastSubscriber TruthValue
       }
                                          
vlanID OBJECT-TYPE
	SYNTAX      Unsigned32 (0..4095)
    MAX-ACCESS  read-write
    STATUS      current
    DESCRIPTION
    "This is the VLANID to be used for the Ethernet 
     traffic (accordingly to 802.1Q) from and 
     to the specified PVC.
     It is only used if vlanOperation is set to addonetags or addtwotags.
     The value can be between 0 and 4095."     
    ::= { pvcEntry 1 }     
    
priority OBJECT-TYPE
	SYNTAX      Unsigned32 (0..7)
    MAX-ACCESS  read-write
    STATUS      current
    DESCRIPTION
    "The priority (accordingly to 802.1Q) that should
     be used for the Ethernet frames to and from the 
     specified PVC.
     It is only used if vlanOperation is set to addonetags or addtwotags.
     The value can be between 0 and 7 (where 7 is the 
     highest priority)."     
    ::= { pvcEntry 2 }
           
pvcStatus OBJECT-TYPE
	SYNTAX      INTEGER {	notUsed		(0),
	                        lineDown	(1),
	                        testDisabled(2),
	                        testing 	(3),
	                        failedF5etoe(4),
	                        ok        	(5),
	                        createFailed(6) }
    MAX-ACCESS  read-only
    STATUS      current
    DESCRIPTION
    "Show the result of the latest 'ATM OAM F5 end-to-end loopback' test.
     - notUsed:      missing PVC configuration - at least peakCellRate has to be specified
     - lineDown:     line is down
     - testDisabled: by atmPvcTestOutputTable.atmF5EndToEndLoopbackInterval=0
     - testing:      until first test in a sequence has finished
     - failedF5etoe: no reply received on 'OAM F5 end-to-end loopback' cell
     - createFailed: due to configuration- or resource failure
     - ok:           test succeded for this PVC
     Please note that even when failed the PVC could still be usable -
     because the test might not be supported by all CPE's."
    ::= { pvcEntry 3 }          
    
accessMethod OBJECT-TYPE
	SYNTAX      INTEGER {	dhcp			(0),
	                        staticIp		(1),
	                        transparrentLan	(2),
	                        pppoe 			(3),
                            pppoa			(4),
                            pppox			(5),
                            staticIpoa      (6),
                            dhcpIpoa		(7),
                            transparentIpoa (8)
	                        }
    MAX-ACCESS  read-write
    STATUS      current
    DESCRIPTION
    "Determines which access method to use for the specific PVC.
	0 - DHCP = Use a dynamic IP address (using DHCP).
	1 - Static IP = Use a static IP address.
	2 - Transparrent LAN = Allow access from all kinds of ethernet 
		packets. All filtering is disabled - VLAN is only security mean.
	3 - PPPoE = Use PPPoE as access method.
	4 - PPPoA = Use PPPoA as access method. This is converted to
		PPPoE in the aggregate network.
    5 - PPPoX = Autodetect if PPPoE or PPPoA is used on tributary side.
	6 - StaticIPoA = Use a static IP address over ATM. This is converted to 
		IP over Ethernet in the aggregate network.
    7 - DHCPIPoA = Use a dynamic IP over ATM, which is converted to IP over
    	Ethernet in the aggregate network.
    8 - TransparentIPoA = Use a Transparent IP over ATM. This is converted to 
		IP over Ethernet in the aggregate network.
	"
    ::= { pvcEntry 4 }
    
allowBroadcast OBJECT-TYPE
	SYNTAX      TruthValue
    MAX-ACCESS  read-write
    STATUS      current
    DESCRIPTION
    "If True the subscriber is allowed to send and 
     receive all broadcasts on the specified PVC. 
     NOTE: Make special attention toward configuring 
     the correct VLANID for the PVC in order to 
     protect the IP DSLAM, network and subscribers. 
     The value can be either True(1) or False(2)." 
    ::= { pvcEntry 6 }

gatewayFixedForwarding OBJECT-TYPE
	SYNTAX      TruthValue
    MAX-ACCESS  read-write
    STATUS      current
    DESCRIPTION
    "If True the Ethernet frames originated from the 
     specified PVC will be forwarded to a gateway. 
     The value can be either True(1) or False(2)."
    ::= { pvcEntry 7 }

gatewayIP OBJECT-TYPE
	SYNTAX      IpAddress
    MAX-ACCESS  read-write
    STATUS      current
    DESCRIPTION
    "The IP Address of the gateway to be used.
     The value can be any IP address." 
    ::= { pvcEntry 8 }   
    
useDHCP OBJECT-TYPE
	SYNTAX      TruthValue
    MAX-ACCESS  read-write
    STATUS      obsolete
    DESCRIPTION
    "If True the DHCP server is used for allocation of IP address.
     The value can be either True(1) or False(2).
     If DHCP is not used, an IP address should be added to
     the filters manually."    
    ::= { pvcEntry 9 }   

downstreamFrameCount OBJECT-TYPE
	SYNTAX      Counter32
    MAX-ACCESS  read-only
    STATUS      current
    DESCRIPTION
    "The number of Ethernet frames sent downstream. 
     This equals the number of AAL5 frames transmitted. 
     The counter is stored in remotestorage and will survive
     a restart."    
    ::= { pvcEntry 10 }   
 
upstreamFrameCount OBJECT-TYPE
	SYNTAX      Counter32
    MAX-ACCESS  read-only
    STATUS      current
    DESCRIPTION
    "The number of Ethernet frames sent upstream. 
     This equals the number of AAL5 frames received. 
     The counter is stored in remotestorage and will survive
     a restart."    
    ::= { pvcEntry 11 }   

downstreamByteCount OBJECT-TYPE
	SYNTAX      Counter64
    MAX-ACCESS  read-only
    STATUS      current
    DESCRIPTION
    "The downstream traffic payload measured in bytes. 
     This counts the number of bytes transmitted within 
     AAL5 frames, excluding the 6 bytes overhead added 
     by AAL5 itself. The counter is stored in remotestorage
     and will survive a restart."    
    ::= { pvcEntry 12 }  

upstreamByteCount OBJECT-TYPE
	SYNTAX      Counter64
    MAX-ACCESS  read-only
    STATUS      current
    DESCRIPTION
    "The uptream traffic payload measured in bytes. This 
     counts the number of bytes received within AAL5 frames, 
     excluding the 6 bytes overhead added by AAL5 itself. 
	 The counter is stored in remotestorage and will survive
	 a restart."    
    ::= { pvcEntry 13 }      

vpi OBJECT-TYPE
	SYNTAX      Unsigned32 (0..15)
    MAX-ACCESS  read-write
    STATUS      current
    DESCRIPTION
    "The Virtual Path Identifier for the specified PVC 
     of a subscriber line. The VPI and VCI
     identifies the PVC (Permanent Virtual Circuit).
     The value can be between 0 and 15."      
    ::= { pvcEntry 14 } 
    
vci OBJECT-TYPE
	SYNTAX      Unsigned32 (0..255)
    MAX-ACCESS  read-write
    STATUS      current
    DESCRIPTION
    "The Virtual Chanel Identifier for the specified PVC
     of a subscriber line. The VCI and VPI
     identifies the PVC (Permanent Virtual Circuit).
     The value can be between 0 and 255." 
    ::= { pvcEntry 15 }     
    
sustainableCellRate OBJECT-TYPE
	SYNTAX      Unsigned32 (0|32000..196608000)
	UNITS       "bps"
    MAX-ACCESS  read-write
    STATUS      current
    DESCRIPTION
    "The average downstream PVC rate.
 	 The rate has to be lower or equal to the configured ADSL
 	 rate and in steps of 32000 bps.
 	 Notice: To carry telephony over IP, 192000 bps is needed and
 	 the ADSL line must be configured to at least 192000. (the upstream
	 must also be configured to 192000 for full duplex)." 
    ::= { pvcEntry 16 }   
    
peakCellRate OBJECT-TYPE
	SYNTAX      Unsigned32 (0|32000..196608000)
	UNITS       "bps"
    MAX-ACCESS  read-write
    STATUS      current
    DESCRIPTION
    "The peak downstream PVC rate.
 	 The rate has to be lower or equal to the configured ADSL
 	 rate and in steps of 32000 bps.
 	 Notice: To carry telephony over IP, 192000 bps is needed and
 	 the ADSL line must be configured to at least 192000. (the upstream
	 must also be configured to 192000 for full duplex)." 
    ::= { pvcEntry 17 }   

transparentBridging OBJECT-TYPE
	SYNTAX      TruthValue
    MAX-ACCESS  read-write
    STATUS      obsolete
    DESCRIPTION
    "If True NO filtering will be performed on the specific PVC.
     This option gives FULL Layer2 connectivity."    
    ::= { pvcEntry 18 }   
    
relayAgentConfiguration OBJECT-TYPE
	SYNTAX      INTEGER { notUsed (0), remoteIdString (1), remoteIdCisco (2), remoteIdCustomer (3),
    					  circuitIdString (4), circuitIdCustomer (5), remoteIdEda(6), circuitIdEda(7),
                          circuitIdTR101 (8)}
    MAX-ACCESS  read-write
    STATUS      current
    DESCRIPTION
    "Determines which Relay Agent configuration to use (DHCP or PPPoE).
     DHCP: The relay agent adds DHCP option 82 to upstream DHCP requests, 
     and removes the option 82 from downstream DHCP replies. See also RFC 3046.
     PPPoE: The relay agent adds a vendor specific option (AtmForum=353)
     to upstream PADR frames. The information is encoded similar to the suboptions
     in DHCP option 82. No standard currently exists (Juniper/BRAS interworking).
     0 - notused:           No relay-agent information will be added or removed from the frames.
     1 - remoteIdString:    A specified string will be inserted as 'Agent Remote ID' (sub-option 2).
                            The parameter relayAgentString has to be set with the string 
                            before using this configuration.
     2 - remoteIdCisco:     The 'Agent Remote ID' (sub-option 2), is encoded as 'Routed 
                            Bridge Encapsulation' specified by Cisco. 
     3 - remoteIdCustomer:  The customer Id will be inserted as a string in sub-option 2, 
                            Agent Remote ID, in the option 82 field.
                            The parameter relayAgentString has to be set with the correct 
                            customer Id before using this configuration.
     4 - circuitIdString:   Same as remoteIdString except that it will be encoded in
                            'Agent Circuit ID' (sub-option 1).
                            Example: '172.30.38.83 atm 0/1:100.33'
                            (relay-agent=172.30.38.83,slot=0,port=1,vpi=100,vci=33)
     5 - circuitIdCustomer: Same as remoteIdCustomer except that it will be encoded in
                            'Agent Circuit ID' (sub-option 1).
     6 - remoteIdEda:        EDA specified coding of the relay agent information (sub-option 2).
                             The parameters relayAgentEdaIp and relayAgentEdaNodeId have to be
                             set before using this option when the IP-DSLAM is running in managed
                             mode.
     7 - circuitIdEda:       EDA specified coding of the relay agent information (sub-option 1).
                             The parameters relayAgentEdaIp and relayAgentEdaNodeId have to be
                             set before using this option when the IP-DSLAM is running in managed
                             mode.
     8 - circuitIdTR101:     The standard TR-101 Access Loop Identification Syntax will be inserted as
                             'Agent Circuit ID' (sub-option 1).
                            
                             Example : 'Access-Node-Identifier atm slot/port:vpi.vci'.
                             Access-Node-Identifier: Is the IP address of the management interface.
                                                     For a stand-alone IP-DSLAM, the IP-DSLAM's own IP address is used,
                                                     for MSAN and EAN the IP address specified with MIB parameter relayAgentEdaIp is used.
                             atm/eth               : Layer-2 type currently used on the user interface.                      
                             slot                  : For the stand-alone IP-DSLAM slot value is 0 (zero),
                                                     for EAN and MSAN this value contains the first 3 bytes of parameter relayAgentEdaNodeId.
                             port                  : LineId + the last byte of relayAgentEdaNodeId.
    " 
    ::= { pvcEntry 19 }   

relayAgentString OBJECT-TYPE
	SYNTAX      OCTET STRING (SIZE(1..253))
    MAX-ACCESS  read-write
    STATUS      current
    DESCRIPTION
    "Specifies the string used in some relayAgentConfiguration's (see 'relayAgentConfiguration' description)."      
    ::= { pvcEntry 20 } 
 
useICMPSecurity OBJECT-TYPE
	SYNTAX      TruthValue
    MAX-ACCESS  read-write
    STATUS      current
    DESCRIPTION
    "If true upstream ICMP messages are filtered to avoid 
     denial of service attacks. The value can be either 
     True(1) or False(2)."      
    ::= { pvcEntry 21 }   
    
atmServiceCategory OBJECT-TYPE
	SYNTAX      INTEGER { ubr (0), vbrNrt (1), vbrRt(2), cbr(3)}
    MAX-ACCESS  read-write
    STATUS      current
    DESCRIPTION
    "Determines which atm service category to use for the PVC.
	 0 - UBR     = Unspecified bit rate. This is typically used for
			       data applications.
	 1 - VBR NRT = Variable bit rate - non real-time. (like VBR RT,
	               but not controlling cell delay variance)
	 2 - VBR RT  = Variable bit rate - real-time. This is typically 
			       used for multimedia applications.
	 3 - CBR     = Constant bit rate. This is typically used for telephony
	               applications.
	 " 
    ::= { pvcEntry 22 }   
    
downstreamMaximumBurstSize OBJECT-TYPE
	SYNTAX      Unsigned32 (0..65535)
	UNITS       "cells"
    MAX-ACCESS  read-write
    STATUS      current
    DESCRIPTION
    "The maximum number of cells in a burst.
 	 Notice: To allow a complete telephony over IP packet to be 
 	 included in one burst,	4 atm cells are needed.
	 Furthermore, if a VBR service category has been chosen, this
	 parameter cannot be 0." 
    ::= { pvcEntry 23 }     

upstreamPeakCellRate OBJECT-TYPE
	SYNTAX      Unsigned32 (0|32000..64000000)
	UNITS       "bps"
    MAX-ACCESS  read-write
    STATUS      current
    DESCRIPTION
    "The peak upstream PVC rate.
 	 The rate has to be lower or equal to the configured ADSL
 	 rate and in steps of 32000 bps.
 	 Notice: To carry telephony over IP, 192000 bps is needed and
 	 the ADSL line must be configured to at least 192000. (the 
 	 downstream must also be configured to 192000 for full duplex)." 
    ::= { pvcEntry 24 }   

upstreamSustainableCellRate OBJECT-TYPE
	SYNTAX      Unsigned32 (0|32000..64000000)
	UNITS       "bps"
    MAX-ACCESS  read-write
    STATUS      current
    DESCRIPTION
    "The average upstream PVC rate.
 	 The rate has to be lower or equal to the configured ADSL
 	 rate and in steps of 32000 bps.
 	 Notice: To carry telephony over IP, 192000 bps is needed and
 	 the ADSL line must be configured to at least 192000. (the 
 	 downstream must also be configured to 192000 for full duplex)." 
    ::= { pvcEntry 25 } 
    
upstreamMaximumBurstSize OBJECT-TYPE
	SYNTAX      Unsigned32 (0..65535)
	UNITS       "cells"
    MAX-ACCESS  read-write
    STATUS      current
    DESCRIPTION
    "The maximum number of cells in a burst.
 	 Notice: To allow a complete telephony over IP packet to be 
 	 included in one burst,	4 atm cells are needed.
	 Furthermore, if a VBR service category has been chosen, this
	 parameter cannot be 0." 
    ::= { pvcEntry 26 } 

virtualMacAdressesAllowed OBJECT-TYPE
    SYNTAX      Unsigned32 (0..252)
    MAX-ACCESS  read-write
    STATUS      deprecated
    DESCRIPTION
    "Use 1.3.6.1.4.1.193.72.300.30.1.3.1.38, macAddressCountLimit and
         1.3.6.1.4.1.193.72.300.30.1.3.1.37, virtualMacEnable
     in place of this.

     Deprecated from:                EDA 2.1R1A
    " 
    ::= { pvcEntry 27 }  

allowIgmpSnooping OBJECT-TYPE
	SYNTAX      TruthValue
    MAX-ACCESS  read-write
    STATUS      current
    DESCRIPTION
    "If True IGMP Snooping is enabled on the specified PVC. 
     The value can be either True(1) or False(2)." 
    ::= { pvcEntry 28 }

encapsulationProtocol OBJECT-TYPE
    SYNTAX      INTEGER {   llc             (0),
                            vcmux           (1)
                        }
	MAX-ACCESS  read-only
    STATUS      current
    DESCRIPTION
    "The encapsulation protocol used on top of the AAL5, according to RFC2684.
     The value is autodetected based on the packets received from the CPE modem."
    ::= { pvcEntry 29 }
    
pppVariant OBJECT-TYPE
    SYNTAX      INTEGER {   unknown			(0),
                            pppoe			(1),
                            pppoa			(2)
                            }
    MAX-ACCESS  read-only
    STATUS      current
    DESCRIPTION
    "The actual PPP variant chosen based on the packets received from the CPE modem.
     The value is only valid if accessMethod is set to pppox (5)."
	::= { pvcEntry 30 }

multicastGroupsAllowed OBJECT-TYPE
	SYNTAX      OCTET STRING
    MAX-ACCESS  read-write
    STATUS      deprecated
    DESCRIPTION
	"Multicast groups which are within the range are allowed.
     If the multicastGroupsAllowed string is empty, then all
     multicast groups are allowed. Each range is 8 bytes. 
     To represent the range >=224.10.10.10 <=224.10.10.40,
     then add: 0xe0 0xa0 0xa0 0xa0 0xe0 0xa0 0xa0 0x28"
	::= { pvcEntry 31 } 
                
discardedOversizedFrames OBJECT-TYPE
	SYNTAX      Counter32
    MAX-ACCESS  read-write
    STATUS      current
    DESCRIPTION
    "Counts the number of frames, which have been discarded, due to
     excessive frame length. The counter can be reset by writing a '0'.
	 (See also: MaximumEthernetFrameSize.)"
    ::= { pvcEntry 32 }

upstreamPolicing OBJECT-TYPE
	SYNTAX      TruthValue
    MAX-ACCESS  read-write
    STATUS      current
    DESCRIPTION
    "Upstream Policing can be enabled or disabled on the specific PVC
     True(1)  - ENABLED
     False(2) - DISABLED." 
    ::= { pvcEntry 33 }

upstreamPolicingCntr OBJECT-TYPE
	SYNTAX      Counter32
    MAX-ACCESS  read-write
    STATUS      current
    DESCRIPTION
    "Counts the number of frames, which have been discarded, due to
     Upstream Policing. The counter can be reset by writing a '0'."
    ::= { pvcEntry 34 } 

floodMulticastAddrs OBJECT-TYPE
	SYNTAX      OCTET STRING
    MAX-ACCESS  read-write
    STATUS      current
    DESCRIPTION
	"Multicast groups which are within the range are flooded on all member PVCs
     and LAN.
     If the floodMulticastAddrs string is empty, then all multicast packets are
     handled as video streaming packets.
	 If the floodMulticastAddrs string has the range of >=224.0.0.1 <=224.0.0.40
     on PVC1 and PVC9, then all multicast packets received form PVC1 with a dest.
     address in this range are flooded on PVC9. 
	 Each range is 8 bytes. To represent the range >=224.0.0.1 <=224.0.0.40,
     then add: 0xe0 0x00 0x00 0x01 0xe0 0x00 0x00 0x28

     Valid from:                EDA 1.3SP1
    " 
	::= { pvcEntry 35 }

pppMruSubstitution OBJECT-TYPE    
	SYNTAX      Unsigned32 (0..1530)
    MAX-ACCESS  read-write
    STATUS      current
    DESCRIPTION
	"Using this parameter it is possible to 'trick' the CPE modem to think the BRAS
     uses a MRU of for instance 1500 bytes (Which it usually can). 
     This can be used to get CPE modems, that discards packets that exceed the standard
     MRU of 1492, to forward the packets anyway.
                       
     Setting this value to zero (0) disables the function.

     This parameter is only valid if access method is set to PPPoA ()

     Valid from:                EDA 2.0R2A
    "
	::= { pvcEntry 36 }
                
virtualMacEnable OBJECT-TYPE
    SYNTAX      INTEGER {   mat-1-1			(1),
                            disabled		(2),
                            mat-N-1			(3),
                            mat-N-1-withLB	(4)
                            }
    MAX-ACCESS  read-write
    STATUS      current
    DESCRIPTION
    "Activates the function that exchanges the MAC addresses in the frames that
     pass, so that only virtual MAC addresses, chosen by the access network
     are used within the access network. 

	 mat-1-1         (1)  1:1 (one-to-one) MAC address translation
	 disabled        (2)  Original MAC addresses are used within the access
                          network (the use of virtual MAC addresses is disabled)
	 mat-N-1         (3)  N:1 (many-to-one) MAC address translation
	 mat-N-1-withLB  (4)  Like (3) - however extra virtual MAC addresses may
                          be used to provide better load balancing for the
                          Ethernet switches in the aggregation network

     If virtualMacEnable is not disabled while macAddressCountLimit is 0, then
     macAddressCountLimit is set to 253 (so that traffic is not stopped 
     inadvertently).

     Note: Disabling this parameter might jeopardize layer 2 security.

     Valid from:                EDA 3.1
	" 
    ::= { pvcEntry 37 }

macAddressCountLimit OBJECT-TYPE
	SYNTAX      Unsigned32 (0..252)
    MAX-ACCESS  read-write
    STATUS      current
    DESCRIPTION
    "A limit for the number of MAC addresses concurrently in use in PVC. Special
     rules apply when it is set to 0. If virtual MAC functionality is enabled when
     it is set to 0, then the maximum limit will be 251.
     If virtual MAC is not enabled when it is set to 0, then no limit is enforced.

     When virtual MAC addresses are enabled, the virtual Mac address reserved for
     PPPoA is allowed in addition to the limit set here.

     Valid from:                EDA 2.1R1A
	" 
    ::= { pvcEntry 38 }
    
innerVlanID OBJECT-TYPE
	SYNTAX      Unsigned32 (0..4095|65535)
    MAX-ACCESS  read-write
    STATUS      current
    DESCRIPTION
    "This is the VLAN identifier used only if vlanOperation is configured to
     addtwotags. This is the inner Vlan used on traffic from and to the
     specified PVC.
     The value can be between 0 and 4095. 65535 is a nil-value indicating
     that inner VLAN is not in use.

     Valid from:                EDA 2.1 SP1
    "  
    ::= { pvcEntry 39 }

innerVlanPriority OBJECT-TYPE
	SYNTAX      Unsigned32 (0..7|255)
    MAX-ACCESS  read-write
    STATUS      current
    DESCRIPTION
    "The VLAN priority used only if vlanOperation value is configured to
     addtwotags. This priority is associated with vlanInnerID accordingly
     to 802.1Q.
     The value can be between 0 and 7 (where 7 is the highest priority).
     255 is a nil-value indicating that inner VLAN is not in use.

     Valid from:                EDA 2.1 SP1
    "     
    ::= { pvcEntry 40 }

dhcpStatus OBJECT-TYPE 
    SYNTAX      INTEGER {   ok			(0),
                            notOk			(1),
                            notTested		(2)
                            }
    MAX-ACCESS  read-only 
    STATUS      current
    DESCRIPTION
    "Indicates the result of testing availability of DHCP Server support within
    connection. The value is updated only during an IP Connectivity Test,
    which runs upon initiation via other MIB parameter (ipConnectivityTest).

	Values: 
	ok		(0)	The DSLAM has communicated with DHCP server on behalf of 
				the user side and been able to obtain parameters as
                expected. 
	notOk	(1)	Communication with DHCP server has been attempted and 
				has failed. 
notTested	(2)	Communication with DHCP server has not been attempted, 
				because it was not needed or because test has not been 
				initiated. 

     Valid from:                EDA 2.1R1A
	" 
    ::= { pvcEntry 41 } 

gatewayStatus OBJECT-TYPE 
    SYNTAX      INTEGER {   ok			(0),
                            notOk		(1),
                            notTested	(2)
                            }
    MAX-ACCESS  read-only 
    STATUS      current
    DESCRIPTION
    "Indicates the result of testing reachability of default gateway for
    connection. The value is updated only during an IP Connectivity Test,
    which runs upon initiation via other MIB parameter (ipConnectivityTest).

	Values: 
Ok			(0)	The DSLAM has sent ICMP Echo Request (Ping) to the
				Default gateway and received a corresponding Echo Reply. 
notOk		(1)	The DSLAM has sent ICMP Echo Request (Ping) to the 
				default gateway but not received a corresponding Echo 
				Reply.
notTested	(2)	The reachability of the default gateway has not been 
				tested because IP Connectivity test has not been 
				initiated. 

     Valid from:                EDA 2.1R1A
	" 
    ::= { pvcEntry 42 } 

ipConnectivityTest OBJECT-TYPE 
    SYNTAX      INTEGER {   standBy			(0),
                            runTestVMac	    (1),
                            done			(2),
                            busy        	(3), 
                            runTestNoVMac   (4) 
                            }
    MAX-ACCESS  read-write
    STATUS      current
    DESCRIPTION
    "Control and state of IP Connectivity.

     Values: 
     standBy         (0)   DSLAM is between tests. This is the default value. This 
                           value is written by client when test is finished and when
                           client wishes to stop test prematurely. 
     runTestVMac     (1)   Written by client when test is to be started and the test may 
                           produce frames with Virtual MAC source addresses.  
     done            (2)   Written by DSLAM when test is completed.
     busy            (3)   Written by DSLAM. Whenever the value is ''runTest'' for a connection,
                           the value for any other connection is ''busy''.
     runTestNoVMac   (4)   Written by client when test is to be started and the test may not 
                           produce frames with Virtual MAC source addresses.  


    N.B. Values (2) done and (3) busy may not be written by client. 

    Normal intended sequence of states: 

    [standby(DSLAM is ready to start test] >>> (client writes) >>>
    [runTestX(test is being executed)] >>> DSLAM writes >>>
    [done] >>> (client writes) >>> 
    [standby]

    In case a test is running when the client writes the value ''runTest'', then the
    running test is aborted prematurely before the new test is started. This is done
    regardless of whether the running test is on the same or another connection.  

    Valid from:                EDA 2.1R1A
    " 
    ::= { pvcEntry 43 } 

insertMacInDhcpOption OBJECT-TYPE
	SYNTAX      Unsigned32 (0|128..254)
    MAX-ACCESS  read-write
    STATUS      current
    DESCRIPTION
    "DHCP option code to be used when inserting the end-user MAC address to DHCP messages
     from the end-user. The end-user MAC is inserted in a site-specific DHCP option, thus the
     valid range is 128 to 254. If set to zero the end-user MAC is not inserted as a
     site-specific option in DHCP messages.
     
     Valid from:                EDA 2.0SP3
     "     
    ::= { pvcEntry 44 }

multicastGroupsLimit OBJECT-TYPE
	SYNTAX      INTEGER (0..8)
    MAX-ACCESS  read-write
    STATUS      current
    DESCRIPTION
    "A parameter which gives the upper limit on the number of Multicast Groups a
     subscriber can join simultaneously. When exceeded the subscriber will be
     denied the membership to any new group.
     If set to zero no limit is enforced.
     
     Valid from:                EDA 2.1 SP1
     "     
    ::= { pvcEntry 45 }

vlanTag OBJECT-TYPE
    SYNTAX      INTEGER {  qtag           (0),
                           vmantag        (1),
                           extremevmantag (2) }
    MAX-ACCESS  read-write
    STATUS      current
    DESCRIPTION
    "Defines the VLAN tag type applied on upstream traffic if.
     In case of two VLAN tags applied the this VLAN tag type is
     applied to the outer VLAN tag
     - qtag:           Q/QinQ VLAN tagging. (Ethernet Type 0x8100)
     - vmantag:        VMAN VLAN tagging. (Ethernet Type 0x88A8)
     - extremevmantag: Extreme VMAN VLAN tagging. (Ethernet Type 0x9100)

    Valid from:                EDA 2.1 SP1
    "
    ::= { pvcEntry 46 }

innerVlanTag OBJECT-TYPE
    SYNTAX      INTEGER {  qtag           (0),
                           vmantag        (1),
                           extremevmantag (2) }
    MAX-ACCESS  read-write
    STATUS      current
    DESCRIPTION
    "Defines the inner VLAN tag type applied on upstream traffic if.
     - qtag:           Q/QinQ VLAN tagging. (Ethernet Type 0x8100)
     - vmantag:        VMAN VLAN tagging. (Ethernet Type 0x88A8)
     - extremevmantag: Extreme VMAN VLAN tagging. (Ethernet Type 0x9100)

    Valid from:                EDA 2.1 SP1
    "
    ::= { pvcEntry 47 }

vlanOperation OBJECT-TYPE
    SYNTAX      INTEGER { addonetag (0),
                          addtwotags(1),
                          addzerotags(2) }
    MAX-ACCESS  read-write
    STATUS      current
    DESCRIPTION
    "This parameter defines the VLAN operation for the specific PVC.
     The following values are supported:
     - addzerotags: The end-users VLAN tags are forwarded transparently without adding any
                    additional tags.
                    Therefore the vlanFilter parameter has to be set to allow tagged traffic
                    (Either Q-tagged or VMAN-tagged).
                    Furthermore a VLAN ID Access Control List is mandatory in order to ensure that
                    the end-user only uses allowed VLAN IDs and to ensure correct switching in the
                    IP-DSLAM. 
                    It's possible to associate several VLAN IDs with each end-user when using this
                    operation.
                    This option is valid from EDA 2.2 SP3.
     - addonetag:   The IP-DSLAM will add one VLAN tag. It will be added on top of the end-users
                    tags if any. A maximum of five tags are supported included the one added by the
                    IP-DSLAM.
     - addtwotags:  The IP-DSLAM will add two VLAN tag. They will be added on top of the end-users
                    tags if any. A maximum of five tags are supported included the two added by the
                    IP-DSLAM.
     
     Valid from:                EDA 2.1 SP1
    "
    ::= { pvcEntry 48 }

vlanFilter OBJECT-TYPE
    SYNTAX      BITS { untag          (0),
                       qtag           (1),
                       vmantag        (2),
                       extremevmantag (3) }
    MAX-ACCESS  read-write
    STATUS      current
    DESCRIPTION
    "Defines the types of VLAN tagging a user is allowed to use on upstream
     traffic. The upstream traffic passes a VLAN filter and if the outermost
     VLAN tag in the received packet is not allowed the packet is discarded.
     - untag:          Allow untagged traffic.
     - qtag:           Allow Q-tagged traffic.
     - vmantag:        Allow VMAN-tagged traffic.
     - extremevmantag: Allow Extreme VMAN-tagged traffic.

    Valid from:                EDA 2.1 SP1
    "
    ::= { pvcEntry 49 }

vlanPrioMappingPrio0 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 0 the VLAN(s) applied by the IP DSLAM will
     also be according to this mapping value regardless what is	specified in
     priority/innerVlanPriority.
     If this value is set to 255 no mapping will take place and the values
     specified in priority/innerVlanPriority are used.
     This object entry only handles priority 0.

    Valid from:                EDA 2.1 SP1
    Obsoleted from:			   EDA 2.2 R1A
    "
    ::= { pvcEntry 50 }

vlanPrioMappingPrio1 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 1 the VLAN(s) applied by the IP DSLAM will
     also be according to this mapping value regardless what is	specified in
     priority/innerVlanPriority.
     If this value is set to 255 no mapping will take place and the values
     specified in priority/innerVlanPriority are used.
     This object entry only handles priority 1.

    Valid from:                EDA 2.1 SP1
    Obsoleted from:			   EDA 2.2 R1A
    "
    ::= { pvcEntry 51 }

vlanPrioMappingPrio2 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 2 the VLAN(s) applied by the IP DSLAM will
     also be according to this mapping value regardless what is	specified in
     priority/innerVlanPriority.
     If this value is set to 255 no mapping will take place and the values
     specified in priority/innerVlanPriority are used.
     This object entry only handles priority 2.

    Valid from:                EDA 2.1 SP1
    Obsoleted from:			   EDA 2.2 R1A
    "
    ::= { pvcEntry 52 }

vlanPrioMappingPrio3 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 3 the VLAN(s) applied by the IP DSLAM will
     also be according to this mapping value regardless what is	specified in
     priority/innerVlanPriority.
     If this value is set to 255 no mapping will take place and the values
     specified in priority/innerVlanPriority are used.
     This object entry only handles priority 3.

    Valid from:                EDA 2.1 SP1
    Obsoleted from:			   EDA 2.2 R1A
    "
    ::= { pvcEntry 53 }

vlanPrioMappingPrio4 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 4 the VLAN(s) applied by the IP DSLAM will
     also be according to this mapping value regardless what is	specified in
     priority/innerVlanPriority.
     If this value is set to 255 no mapping will take place and the values
     specified in priority/innerVlanPriority are used.
     This object entry only handles priority 4.

    Valid from:                EDA 2.1 SP1
    Obsoleted from:			   EDA 2.2 R1A
    "
    ::= { pvcEntry 54 }

vlanPrioMappingPrio5 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 5 the VLAN(s) applied by the IP DSLAM will
     also be according to this mapping value regardless what is	specified in
     priority/innerVlanPriority.
     If this value is set to 255 no mapping will take place and the values
     specified in priority/innerVlanPriority are used.
     This object entry only handles priority 5.

    Valid from:                EDA 2.1 SP1
    Obsoleted from:			   EDA 2.2 R1A
    "
    ::= { pvcEntry 55 }

vlanPrioMappingPrio6 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 6 the VLAN(s) applied by the IP DSLAM will
     also be according to this mapping value regardless what is	specified in
     priority/innerVlanPriority.
     If this value is set to 255 no mapping will take place and the values
     specified in priority/innerVlanPriority are used.
     This object entry only handles priority 6.

    Valid from:                EDA 2.1 SP1
    Obsoleted from:			   EDA 2.2 R1A
    "
    ::= { pvcEntry 56 }

vlanPrioMappingPrio7 OBJECT-TYPE
    SYNTAX      Unsigned32 (0..7|255)
    MAX-ACCESS  read-write
    STATUS      obsolete
    DESCRIPTION
    "It is possible to map the priority in a user-provided VLAN to another or
     the priority in the VLAN(s) applied by the IP DSLAM e.g. if the priority
     in the user-provided VLAN is 7 the VLAN(s) applied by the IP DSLAM will
     also be according to this mapping value regardless what is	specified in
     priority/innerVlanPriority.
     If this value is set to 255 no mapping will take place and the values
     specified in priority/innerVlanPriority are used.
     This object entry only handles priority 7.

    Valid from:                EDA 2.1 SP1
    Obsoleted from:			   EDA 2.2 R1A
    "
    ::= { pvcEntry 57 }

downstreamFlows OBJECT-TYPE
	SYNTAX      OCTET STRING
    MAX-ACCESS  read-write
    STATUS      current
    DESCRIPTION
	"A list of downstream flows that are contained in/use this PVC.
    Each octet is a number of a flow that exists (is active). "          
	::= { pvcEntry 58 }

upstreamFlows OBJECT-TYPE
	SYNTAX      OCTET STRING
    MAX-ACCESS  read-write
    STATUS      current
    DESCRIPTION
	"A list of upstream flows that are contained in/use this PVC.
    Each octet is a number of a flow that exists (is active). "          
	::= { pvcEntry 59 } 

flowIdentificationCriterionDownstream OBJECT-TYPE 
    SYNTAX      INTEGER {   classic			(0),
                            pbit  	    	(1),
                            dscp			(2)
                            }
    MAX-ACCESS  read-write
    STATUS      current
    DESCRIPTION
    "When packets arrive on the uplink, the DSLAM needs to determine which flow the
    packet belongs to. This can be done in one of three ways. I.e by looking at ... 
classic	          (0)	VLAN and destination MAC address.  
pbit	      	  (1)	VLAN, destination MAC address and p-bit/CoS.  
dscp	          (2)	VLAN, destination MAC address and DSCP (part of ToS).  
	" 
    ::= { pvcEntry 60 } 

flowIdentificationCriterionUpstream OBJECT-TYPE 
    SYNTAX      INTEGER {   classic			(0),
                            pbit  	    	(1),
                            dscp			(2),
                            ethertype       (3)
                            }
    MAX-ACCESS  read-write
    STATUS      current
    DESCRIPTION
    "When packets arrive on a DSL line, the DSLAM needs to determine which flow the
     packet belongs to. This can be done in one of four ways. I.e by looking at ... 
     classic     (0)   PVC. (Only one flow may be associated with the PVC.)  
     pbit        (1)   PVC and p-bit/CoS.  
     dscp        (2)   PVC and DSCP (part of ToS).
     ethertype   (3)   PVC and Ethertype.  
	" 
    ::= { pvcEntry 61 }

schedulingScheme OBJECT-TYPE 
    SYNTAX      INTEGER {	none                        (0),
    						strictPriority				(1),
                            deficitRoundRobin    		(2),
                            modifiedDeficitRoundRobin   (3)
                            }
    MAX-ACCESS  read-write
    STATUS      current
    DESCRIPTION
    "The DSLAM may schedule packets in this flow in competition with packets in other
     flows in the same PVC.    
     none                       (0) There is only one flow, no scheduling needed.  
     strictPriority             (1) Strict Priority, the flow with flowIndex=0 has highest priority.  
     deficitRoundRobin          (2) Deficit Round Robin, dfcBytesPerRound determines how many
                                    bytes are sent from the flow for each turn of the Round Robin. 
     modifiedDeficitRoundRobin  (3) Modified Deficit Round Robin, the flow with flowIndex=0 has strict
                                    priority over the others. The other flows are scheduled according
                                    to DRR on what bandwidth remains.  
	" 
    ::= { pvcEntry 62 }

floodDownstreamUnknownDestMac OBJECT-TYPE
	SYNTAX      TruthValue
    MAX-ACCESS  read-write
    STATUS      current
    DESCRIPTION
    "Frames received from the aggregation network will be forwarded
     on this PVC if the destination MAC address is unknown to the DSLAM.
     The frame must be received in the same VLAN as associated with the PVC.
     
     Valid from:                EDA 2.1 SP2
     "     
    ::= { pvcEntry 63 }

l2cpTunneling OBJECT-TYPE
    SYNTAX      BITS {
                      stp(0),
                      pvstp(1),
                      cdp(2),
                      vtp(3)
                     }
    MAX-ACCESS  read-write
    STATUS      current
    DESCRIPTION
    "This parameter is used to enable Layer 2 Protocol Tunneling. The tunneling
     mechanism is a propritary solution specified by Cisco. The Layer 2 Control
     Protocol tunneling feature is only available when accessMethod is
     transparrentLan.
     
     Customers at different sites connected across a SP network need to use
     various Layer 2 protocols to scale their topologies to include all remote
     sites, as well as the local sites. STP must run properly, and every VLAN
     should build a proper spanning tree that includes the local site and all
     remote sites across the SP network. Cisco Discovery Protocol (CDP) must
     discover neighboring Cisco devices from local and remote sites. VLAN
     Trunking Protocol (VTP) must provide consistent VLAN configuration
     throughout all sites in the customer network.
     
     When protocol tunneling is enabled, DSLAM on the inbound side of the SP
     network encapsulate Layer 2 protocol packets with a special MAC address
     and send them across the SP network. Core switches in the network do not
     process these packets but forward them as normal packets. Layer 2 protocol
     data units (PDUs) for CDP, STP, or VTP cross the SP network and are
     delivered to customer switches on the outbound side of the SP network.
     Identical packets are received by all customer ports on the same VLANs
     with these results:
     Users on each of a customer's sites can properly run STP, and every VLAN
     can build a correct spanning tree, based on parameters from all sites and
     not just from the local site.
     CDP discovers and shows information about the other Cisco devices connected
     through the SP network.
     VTP provides consistent VLAN configuration throughout the customer network,
     propagating to all switches through the SP.
     
     When the Layer 2 PDUs that entered the DSLAM on the inbound side, the DSLAM
     overwrites the customer PDU-destination MAC address with a well-known Cisco
     proprietary multicast address (01-00-0c-cd-cd-d0).
     The DSLAM on the outbound side restore the proper Layer 2 protocol and MAC
     address information and forward the packets to all PVCs in the same VLAN.
     Therefore, the Layer 2 PDUs remain intact and are delivered across the SP
     network to the other side of the customer network.
    
     Tunneling of Layer 2 control protocols is enabled using this bit-map.

     The various bit positions are:
     0    stp      When set Layer 2 Control Protocol tunneling is enabled for
                   Spanning Tree Protocol (destination MAC = 01:80:c2:00:00:00)
     1    pvstp    When set Layer 2 Control Protocol tunneling is enabled for
                   Per VLAN Spanning Tree Protocol, a Cisco specified extension
                   to STP (destination MAC = 01:00:0c:cc:cc:cd).
     2    cdp      When set Layer 2 Control Protocol tunneling is enabled for
                   Cisco Discovery Protocol (destination MAC = 01:00:0c:cc:cc:cc).
     3    vtp      When set Layer 2 Control Protocol tunneling is enabled for
                   Virtual Trunking Protocol (destination MAC = 01:00:0c:cc:cc:cc).

     Valid from:                EDA 2.1 SP2
     "
    ::= { pvcEntry 64 }

upstreamMcastEnable OBJECT-TYPE
	SYNTAX      TruthValue
    MAX-ACCESS  read-write
    STATUS      current
    DESCRIPTION
    "Setting this parameter to True enables the end-user to send IGMP queries
     and multicast streams in the VLAN associated with the PVC.
     
     Valid from:                EDA 2.1 SP2
     "     
    ::= { pvcEntry 65 }

clearDhcpLeaseTable OBJECT-TYPE
    SYNTAX      INTEGER {clear(1)}
    MAX-ACCESS  read-write
    STATUS      current
    DESCRIPTION
    "When set to clear, all the DHCP Mapping entries for this Connection
     will be removed from the DHCP Mapping Table.
    "     
    ::= { pvcEntry 66 }
    
clearMACHistory OBJECT-TYPE
	SYNTAX      TruthValue
    MAX-ACCESS  read-write
    STATUS      current
    DESCRIPTION
    "If True Clear the Subscriber MAC History for this pCon(Line,Pvc). 
     The value can be either True(1) or False(2).
     Default Value will be false." 
    ::= { pvcEntry 67 }

gatewayMacfilteringDirection  OBJECT-TYPE
    SYNTAX      INTEGER {	 upstream (0),
                             updownstream (1)
                        }
    MAX-ACCESS  read-write
    STATUS      current
    DESCRIPTION
    "A parameter which gives on which traffic the Gateway Mac filtering needs to be done.
     If the value is set to 0 then the only in the upstream the Gateway Mac will be filtered.
     If the value is set to 1 then in both upstream and down stream the Gateway Mac will be filtered.     "
    ::={pvcEntry 68}

downstreamFramesPerSecond	OBJECT-TYPE
	SYNTAX		Unsigned32
    MAX-ACCESS	read-only
    STATUS		current
    DESCRIPTION
    "A parameter which gives the number of downstream frames received on the PVC
     per second.
    "
    ::={pvcEntry 69}

upstreamFramesPerSecond	OBJECT-TYPE
	SYNTAX		Unsigned32
    MAX-ACCESS	read-only
    STATUS		current
    DESCRIPTION
    "A parameter which gives the number of upstream frames received on the PVC
     per second.
    "
    ::={pvcEntry 70}

downstreamBitsPerSecond	OBJECT-TYPE
	SYNTAX		Unsigned32
    MAX-ACCESS	read-only
    STATUS		current
    DESCRIPTION
    "A parameter which gives the number of downstream bits received on the PVC
     per second.
    "
    ::={pvcEntry 71}

upstreamBitsPerSecond	OBJECT-TYPE
	SYNTAX		Unsigned32
    MAX-ACCESS	read-only
    STATUS		current
    DESCRIPTION
    "A parameter which gives the number of upstream bits received on the PVC
     per second.
    "
    ::={pvcEntry 72}

arpProxyConfig OBJECT-TYPE
    SYNTAX      INTEGER {    proxyAllArpRequests (0),
                             proxyNonGwArpRequests (1),
                             proxyNonGratuitousArpRequests (2)
                        }
    MAX-ACCESS  read-write
    STATUS      current
    DESCRIPTION
    "This parameter decides the behavior of the ArpProxy in the IP-DSLAM. It is only valid when forced
     forwarding is enabled (peaBridgeIpDslam::gatewayFixedForwarding set to true).

     The possible values are:
     0  proxyAllArpRequests            All ARP Requests from the end-user will always be replied 
                                       with the MAC address of the default gateway configured for
                                       the end-user, except gratuitous ARP Requests which will be
                                       dropped.
                                       This setting should be used when broadcast traffic should be
                                       kept to a minimum, for instance when running large L2
                                       networks.
     1  proxyNonGwArpRequests          All ARP Requests from the end-user to the default gateway are
                                       forwarded to the network. Gratuitous ARP Requests are also
                                       forwarded to the network. Any request to a non gateway IP
                                       will be replied the default gateway MAC address.
                                       This setting is needed when running 'Passive ARP Learning' in
                                       VRRP enabled routers, or other technologies where ARP from the
                                       end-users are needed.
     2  proxyNonGratuitousArpRequests  All ARP Requests from the end-user will be replied with the
                                       MAC address of the default gateway configured for the
                                       end-user. Except gratuitous ARP Requests which are forwarded
                                       to the network. 
                                       This setting should be used when broadcast traffic should be
                                       kept to a minimum, but the ARP cache timeout in the router
                                       is too long to detect end-user MAC replacement.
                                       This option is valid from EDA 2.2 SP3.

     ARP Requests from the network will always be proxied back.

     Terminology:
     Gratuitous ARP Request: A gratuitous ARP Request is an ARP Request where the Sender IP address
                             and Target IP address is the same. The ARP Requests is broadcasted to
                             other hosts in the same layer 2 network.
                             Hosts use this ARP Request for several reasons:
                             1) To detect IP address conflicts
                             2) To advertise the IP and MAC address to other hosts, switch's and
                                routers
     
     Valid from:               EDA 2.2 SP1
    "
    DEFVAL { proxyAllArpRequests }
    ::={pvcEntry 73}

endUserVlanOperation  OBJECT-TYPE
    SYNTAX      INTEGER {    endUserVLanForward (0),
                             endUserVLanFilterRemove (1)
                        }
    MAX-ACCESS  read-write
    STATUS      current
    DESCRIPTION
    "This parameter decides how the end-users VLAN tags should be handled.

     The possible values are
     0    endUserVLanForward            End-user VLANs are filtered according to the VLAN ID ACL
                                        and then forwarded. If the VLAN ID ACL is not defined
                                        all VLAN IDs will be allowed.
     1    endUserVLanFilterRemove       End-user VLANs are filtered and then removed/added
                                        Upstream traffic is first filtered according to the
                                        upstream VLAN ID ACL and then the VLAN is removed.
                                        On downstream traffic the VLAN is added to the frame
                                        before sending it to the end-user.
                                        The VLAN that is added is the first VLAN in the first
                                        range specified in the downstream VLAN ID ACL.
     
     Note: For this functionality to work it is required that vlanFilter is set to allow
           Q-Tagged traffic

     Valid from:                EDA 2.2 SP2
    "
    DEFVAL { endUserVLanForward }
    ::={pvcEntry 80}

vlanIdFilter OBJECT-TYPE
	SYNTAX      Unsigned32 (0..4095)
    MAX-ACCESS  read-write
    STATUS      deprecated
    DESCRIPTION
    "Defines the VLAN ID a user is allowed to use on upstream traffic.
     The upstream traffic passes a VLAN ID filter and if the outermost
     VLAN ID in the received packet is not allowed the packet is discarded.
     The value can be between 0 and 4095.

     This parameter is only valid if endUserVlanOperation is set to
     endUserVLanFilterRemove.

     This parameter is deprecated. Please use peaBridgeIpDslam::vlanIdAclTable instead.

     Valid from:                EDA 2.2 SP2
     Deprecated from:           EDA 2.2 R3A
    "
    DEFVAL { 0 }
    ::= { pvcEntry 85} 

pvcFilterVersion OBJECT-TYPE
    SYNTAX      INTEGER { pvcFilter(1), accessControlList(2) }
    MAX-ACCESS  read-write
    STATUS      current
    DESCRIPTION
    "Detemines which version of the IP filter to use for the specific PVC.
     1 - pvcFilter         = Use filters defined in pvcFiltersTable.
     2 - accessControlList = Use Access Control List.

     Valid from:                EDA 2.2 SP2
     " 
    DEFVAL { pvcFilter }
    ::= { pvcEntry 90 }    

pvcUpstreamVlanIdAclId  OBJECT-TYPE
    SYNTAX      Unsigned32
    MAX-ACCESS  read-write
    STATUS      current
    DESCRIPTION
    "Setting this value to non-zero will specify the VLAN ID ACL to be 
     used in the upstream direction. The value of zero means no
     VLAN ID ACL is used for this PVC.
     Default value will be zero

	 Valid from:                EDA 2.2 R3A
    " 
    DEFVAL {0}     
    ::= { pvcEntry 93 }

pvcDownstreamVlanIdAclId  OBJECT-TYPE
    SYNTAX      Unsigned32
    MAX-ACCESS  read-write
    STATUS      current
    DESCRIPTION
    "Setting this value to non-zero will specify the VLAN ID ACL to be
     used in the downstream direction. The value of zero means no
     VLAN ID ACL is used for this PVC.
     Default value will be zero

     Valid from:                EDA 2.2 R3A
    " 
    DEFVAL {0}     
    ::= { pvcEntry 94 }
    
pvcUpstreamEtherTypeAclId  OBJECT-TYPE
    SYNTAX      Unsigned32
    MAX-ACCESS  read-write
    STATUS      current
    DESCRIPTION
    "Setting this value to non-zero will specify the EtherType ACL to be 
     used in the upstream direction. The value of zero means no EtherType
     ACL is used for this PVC.
     Default value will be zero

     Valid from:                EDA 2.2 SP2
    " 
    DEFVAL {0}     
    ::= { pvcEntry 95 }

pvcDownstreamEtherTypeAclId  OBJECT-TYPE
    SYNTAX      Unsigned32
    MAX-ACCESS  read-write
    STATUS      current
    DESCRIPTION
    "Setting this value to non-zero will specify the EtherType ACL to be
     used in the downstream direction. The value of zero means no
     EtherType ACL is used for this PVC.
     Default value will be zero

     Valid from:                EDA 2.2 SP2
    " 
    DEFVAL {0}     
    ::= { pvcEntry 100 }

pvcUpstreamIpAclId  OBJECT-TYPE
    SYNTAX      Unsigned32
    MAX-ACCESS  read-write
    STATUS      current
    DESCRIPTION
    "Setting this value to non-zero will specify the IP ACL to be 
     used in the upstream direction. The value of zero means no   
     IP ACL is used for this PVC.
     Default value will be zero

     Valid from:                EDA 2.2 SP2
    " 
    DEFVAL {0}     
    ::= { pvcEntry 105 }

pvcDownstreamIpAclId  OBJECT-TYPE
    SYNTAX      Unsigned32
    MAX-ACCESS  read-write
    STATUS      current
    DESCRIPTION
    "Setting this value to non-zero will specify the IP ACL to be
     used in the downstream direction. The value of zero means 
     no IP ACL is used for this PVC.
     Default value will be zero

     Valid from:                EDA 2.2 SP2
    " 
    DEFVAL {0}     
    ::= { pvcEntry 110 }

dhcpServerMacAddress    OBJECT-TYPE
    SYNTAX      MacAddress
    MAX-ACCESS  read-write
    STATUS      current
    DESCRIPTION
    "Use this parameter to convert the end-users DHCP messages from broadcast to unicast.
     This is very usefull when trying to minimise the amount of broadcast in a L2 network.

     When the IP-DSLAM receives a DHCP Discover or a Request it will change the destination
     MAC address from the broadcast address to the configured DHCP Server Mac Address (This parameter).

     - To enable the functionality add the MAC address of the DHCP server
      (To configure 00-80-03-04-05-06 add 0x00 0x80 0x03 0x04 0x05 0x06)
     - To disable the functionality add MAC address 00-00-00-00-00-00

     Note: When using this function the end-user will no longer be able to select between
           different DHCP servers. This functionality is only valid if accessMethod is
           set to 'dhcp' or 'dhcpIpoa'.

     Valid from:            EDA 2.2 R3A
    "
    ::= { pvcEntry 115}

allowAnonymousMulticastSubscriber	OBJECT-TYPE
    SYNTAX		TruthValue
    MAX-ACCESS	read-write
    STATUS		current
    DESCRIPTION
    "Determines whether MAC and IP address validation is performed when a subscriber
     sends multicast frames upstream in the network.

     Example: If a subscriber is configured to access method DHCP and anonymous multicast
     subscriber is allowed for that subscriber, it is not validated that the subscriber
     has been assigned an IP address via DHCP, when the subscriber tries to join a
     multicast group.
     
     The possible values are
     TRUE (1) - Subscriber source IP and MAC addresses are not validated.
     FALSE(2) - Subscriber source IP and MAC addresses are validated.
     
     Valid from:            EDA 2.2 SP3
	"
    DEFVAL {false}
    ::= { pvcEntry 120}
    
pvcFiltersTable OBJECT-TYPE
	SYNTAX      SEQUENCE OF PVCFiltersEntry
  	MAX-ACCESS  not-accessible
    STATUS      current
    DESCRIPTION
    "A list of entries to the PVCs."
    ::= { bridgeControl 4 }   
    
pvcFiltersEntry OBJECT-TYPE
	SYNTAX      PVCFiltersEntry
    MAX-ACCESS  not-accessible
    STATUS      current
    DESCRIPTION
    "An entry containing the filters for a PVC 
     for the subscriber line identified by lineIndex."
    INDEX  {lineIndex, pvcIndex }
    ::= { pvcFiltersTable 1 }     
    
PVCFiltersEntry ::= 
	SEQUENCE {
		upsteamEthernetTypesFilterType			INTEGER,
		upsteamEthernetTypesFilterValue 		EthernetTypeList,
		upstreamDestinationIpFilterType			INTEGER,
		upstreamDestinationIpFilterValue		OCTET STRING,
		upstreamSourcePortFilterType			INTEGER,
		upstreamSourcePortFilterValue			OCTET STRING, 
		upstreamDestinationPortFilterType		INTEGER,
		upstreamDestinationPortFilterValue		OCTET STRING, 
		downsteamEthernetTypesFilterType		INTEGER,
		downsteamEthernetTypesFilterValue		EthernetTypeList,
		downstreamSourceIpFilterType			INTEGER,
		downstreamSourceIpFilterValue			OCTET STRING,
		downstreamSourcePortFilterType			INTEGER,
		downstreamSourcePortFilterValue			OCTET STRING, 
		downstreamDestinationPortFilterType		INTEGER,
		downstreamDestinationPortFilterValue	OCTET STRING,
		subscriberMACFilterType					INTEGER,
		subscriberMACFilterValue				OCTET STRING,
		subscriberIpFilterType					INTEGER, 
		subscriberIpFilterValue					OCTET STRING,
        upstreamPortIpFilterValue               OCTET STRING 
		}
                                          
upsteamEthernetTypesFilterType OBJECT-TYPE
	SYNTAX      INTEGER { positive (0), negative (1)}
    MAX-ACCESS  read-only
    STATUS      deprecated
    DESCRIPTION
    "The filter type can be positive(0) or negative(1).
     If positive all packets with EthernetType which are part of
     the filter entries are allowed by the filter.
     If negative the filter allows all packets except the packets
     with the EthernetType which are part of the filter entries.
     If no entries are specified, all types are allowed.

     When pvcFilterVersion is AccessControlList the upsteamEthernetTypesFilterType
     is determined by the EthernetType and MatchAction specified in the ACL Rules.

     This parameter is deprecated. Please use the Ethernet Type Access Control List instead.
     For more information please see the following parameters:
     peaBridgeIpDslam::pvcUpstreamEtherTypeAclId
     peaBridgeIpDslam::etherTypeAclTable
     peaBridgeIpDslam::etherTypeAclRuleTable

     Deprecated from:           EDA 2.2 SP3
    "
    ::= { pvcFiltersEntry 1 } 

upsteamEthernetTypesFilterValue OBJECT-TYPE
	SYNTAX      EthernetTypeList
    MAX-ACCESS  read-write
    STATUS      deprecated
    DESCRIPTION
    "Filter on Ethernet Type in packets from subscriber into network.
	 A list of EthernetType entries, each two byte in network byte order (big endian).
	 Example: EthernetTypeIp=0x800 => '0x08 0x00'

     This parameter is deprecated. Please use the Ethernet Type Access Control List instead.
     For more information please see the following parameters:
     peaBridgeIpDslam::pvcUpstreamEtherTypeAclId
     peaBridgeIpDslam::etherTypeAclTable
     peaBridgeIpDslam::etherTypeAclRuleTable

     Deprecated from:           EDA 2.2 SP3
    " 
    ::= { pvcFiltersEntry 2 } 

upstreamDestinationIpFilterType OBJECT-TYPE
	SYNTAX      INTEGER { positive (0), negative (1)}
    MAX-ACCESS  read-write
    STATUS      deprecated
    DESCRIPTION
    "The filter type can be positive(0) or negative (1).
     If positive all packets with the destination IP 
     which are part of the filter entries are allowed 
     by the filter.
     If negative the filter allows all packets except 
     the packets with the destination IP which are 
     part of the filter entries.

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
    ::= { pvcFiltersEntry 3 } 

upstreamDestinationIpFilterValue OBJECT-TYPE
	SYNTAX      OCTET STRING
    MAX-ACCESS  read-write
    STATUS      deprecated
    DESCRIPTION
	"Filter on destination IP in packets from subscriber
	 into network.
     Filter entries 8 bytes each, representing a range - 
     to represent the range >=10.0.0.0 <=16.0.0.0
     add 0x0a 0x00 0x00 0x00 0x10 0x00 0x00 0x00

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
	::= { pvcFiltersEntry 4 } 

upstreamSourcePortFilterType OBJECT-TYPE
	SYNTAX      INTEGER {negative (1)}
    MAX-ACCESS  read-only
    STATUS      deprecated
    DESCRIPTION
    "The filter type is negative (1).
     The filter allows all packets except the packets 
     with the IP source port number which are 
     part of the filter entries.

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
    ::= { pvcFiltersEntry 5 } 
    
upstreamSourcePortFilterValue OBJECT-TYPE
	SYNTAX      OCTET STRING
    MAX-ACCESS  read-write
    STATUS      deprecated
    DESCRIPTION
    "Filter on IP source port number in packets from
     subscriber into network.
     Filter entries 2 bytes each - to exclude FTP
     add 21 = 0x00 0x15

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
	::= { pvcFiltersEntry 6 } 

upstreamDestinationPortFilterType OBJECT-TYPE
	SYNTAX      INTEGER {negative (1)}
    MAX-ACCESS  read-only
    STATUS      deprecated
    DESCRIPTION
    "The filter type is negative (1).
     The filter allows all packets except the packets 
     with the IP destination port number which are 
     part of the filter entries.

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
    ::= { pvcFiltersEntry 7 } 

upstreamDestinationPortFilterValue OBJECT-TYPE
	SYNTAX      OCTET STRING
    MAX-ACCESS  read-write
    STATUS      deprecated
    DESCRIPTION
    "Filter on IP destination port number in packets from
     subscriber into network.
     Filter entries 2 bytes each - to exclude FTP
     add 21 = 0x00 0x15

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
    ::= { pvcFiltersEntry 8 }    
    
downsteamEthernetTypesFilterType OBJECT-TYPE
	SYNTAX      INTEGER { positive (0), negative (1)}
    MAX-ACCESS  read-only
    STATUS      deprecated
    DESCRIPTION
    "The filter type can be positive(0) or negative(1).
     If positive all packets with EthernetType which are part of
     the filter entries are allowed by the filter.
     If negative the filter allows all packets except the packets
     with the EthernetType which are part of the filter entries.
     If no entries are specified, all types are allowed.

     When pvcFilterVersion is AccessControlList the downsteamEthernetTypesFilterType
     is determined by the EthernetType and MatchAction specified in the ACL Rules.

     This parameter is deprecated. Please use the Ethernet Type Access Control List instead.
     For more information please see the following parameters:
     peaBridgeIpDslam::pvcDownstreamEtherTypeAclId
     peaBridgeIpDslam::etherTypeAclTable
     peaBridgeIpDslam::etherTypeAclRuleTable

     Deprecated from:           EDA 2.2 SP3
    " 
    ::= { pvcFiltersEntry 9 } 
     
downsteamEthernetTypesFilterValue OBJECT-TYPE
	SYNTAX      EthernetTypeList
    MAX-ACCESS  read-write
    STATUS      deprecated
    DESCRIPTION
    "Filter on Ethernet Type in packets from network to subscriber.
	 A list of EthernetType entries, each two byte in network byte order (big endian).
	 Example: EthernetTypeIp=0x800 => '0x08 0x00'

     This parameter is deprecated. Please use the Ethernet Type Access Control List instead.
     For more information please see the following parameters:
     peaBridgeIpDslam::pvcDownstreamEtherTypeAclId
     peaBridgeIpDslam::etherTypeAclTable
     peaBridgeIpDslam::etherTypeAclRuleTable

     Deprecated from:           EDA 2.2 SP3
    " 
    ::= { pvcFiltersEntry 10 } 
    
downstreamSourceIpFilterType OBJECT-TYPE
	SYNTAX      INTEGER { positive (0), negative (1)}
    MAX-ACCESS  read-write
    STATUS      deprecated
    DESCRIPTION
    "The filter type can be positive(0) or negative (1).
     If positive all packets with the source IP 
     which are part of the filter entries are allowed 
     by the filter.
     If negative the filter allows all packets except 
     the packets with the source IP which are 
     part of the filter entries.

     This parameter is deprecated. Please use the IP Access Control List instead.
     For more information please see the following parameters:
     peaBridgeIpDslam::pvcDownstreamIpAclId
     peaBridgeIpDslam::ipAclTable
     peaBridgeIpDslam::ipAclRuleTable

     Deprecated from:           EDA 2.2 SP3
    " 
    ::= { pvcFiltersEntry 11 } 

downstreamSourceIpFilterValue OBJECT-TYPE
	SYNTAX      OCTET STRING
    MAX-ACCESS  read-write
    STATUS      deprecated
    DESCRIPTION
    "Filter on source IP in packets from network
     to subscriber.
     Filter entries 4 bytes each, representing a
     single address. To represent the adress 10.0.0.0
     add 0x0a 0x00 0x00 0x00

     This parameter is deprecated. Please use the IP Access Control List instead.
     For more information please see the following parameters:
     peaBridgeIpDslam::pvcDownstreamIpAclId
     peaBridgeIpDslam::ipAclTable
     peaBridgeIpDslam::ipAclRuleTable

     Deprecated from:           EDA 2.2 SP3
    " 
    ::= { pvcFiltersEntry 12 } 

downstreamSourcePortFilterType OBJECT-TYPE
	SYNTAX      INTEGER {negative (1)}
    MAX-ACCESS  read-only
    STATUS      deprecated
    DESCRIPTION
    "The filter type is negative (1).
     The filter allows all packets except the packets 
     with the IP source port number which are 
     part of the filter entries.

     This parameter is deprecated. Please use the IP Access Control List instead.
     For more information please see the following parameters:
     peaBridgeIpDslam::pvcDownstreamIpAclId
     peaBridgeIpDslam::ipAclTable
     peaBridgeIpDslam::ipAclRuleTable

     Deprecated from:           EDA 2.2 SP3
    " 
    ::= { pvcFiltersEntry 13 } 

downstreamSourcePortFilterValue OBJECT-TYPE
	SYNTAX      OCTET STRING
    MAX-ACCESS  read-write
    STATUS      deprecated
    DESCRIPTION
    "Filter on IP source port number in packets from
     network to subscriber.
     Filter entries 2 bytes each - to exclude FTP
     add 21 = 0x00 0x15

     This parameter is deprecated. Please use the IP Access Control List instead.
     For more information please see the following parameters:
     peaBridgeIpDslam::pvcDownstreamIpAclId
     peaBridgeIpDslam::ipAclTable
     peaBridgeIpDslam::ipAclRuleTable

     Deprecated from:           EDA 2.2 SP3
    " 
    ::= { pvcFiltersEntry 14 } 

downstreamDestinationPortFilterType OBJECT-TYPE
	SYNTAX      INTEGER { negative (1)}
    MAX-ACCESS  read-only
    STATUS      deprecated
    DESCRIPTION
    "The filter type is negative (1).
     The filter allows all packets except the packets 
     with the IP destination port number which are 
     part of the filter entries.

     This parameter is deprecated. Please use the IP Access Control List instead.
     For more information please see the following parameters:
     peaBridgeIpDslam::pvcDownstreamIpAclId
     peaBridgeIpDslam::ipAclTable
     peaBridgeIpDslam::ipAclRuleTable

     Deprecated from:           EDA 2.2 SP3
    " 
    ::= { pvcFiltersEntry 15 } 

downstreamDestinationPortFilterValue OBJECT-TYPE
	SYNTAX      OCTET STRING
    MAX-ACCESS  read-write
    STATUS      deprecated
    DESCRIPTION
    "Filter on IP destination port number in packets from
     network to subscriber.
     Filter entries 2 bytes each - to exclude FTP
     add 21 = 0x00 0x15

     This parameter is deprecated. Please use the IP Access Control List instead.
     For more information please see the following parameters:
     peaBridgeIpDslam::pvcDownstreamIpAclId
     peaBridgeIpDslam::ipAclTable
     peaBridgeIpDslam::ipAclRuleTable

     Deprecated from:           EDA 2.2 SP3
    " 
    ::= { pvcFiltersEntry 16 } 

subscriberMACFilterType OBJECT-TYPE
	SYNTAX      INTEGER { positive (0)}
    MAX-ACCESS  read-only
    STATUS      current
    DESCRIPTION
    "The filter type is positive(0).
     All packets with the MAC addresses which are part of
     the filter entries are allowed by the filter."    
    ::= { pvcFiltersEntry 17 } 

subscriberMACFilterValue OBJECT-TYPE
	SYNTAX      OCTET STRING
    MAX-ACCESS  read-write
    STATUS      current
    DESCRIPTION
    "Filter on subscriber MAC addresses.
     At least one entry should apply here if DHCP is not used.
     Filter entries 6 bytes each - to include 00-80-03-04-05-06
     add 0x00 0x80 0x03 0x04 0x05 0x06"          
    ::= { pvcFiltersEntry 18 } 

subscriberIpFilterType OBJECT-TYPE
	SYNTAX      INTEGER { positive (0), disabled (2)}
    MAX-ACCESS  read-write
    STATUS      deprecated
    DESCRIPTION
    "The subscriber IP filter type can be either positive(0) or disabled(2).
     If positive all packets with the subscriber IP 
     which are part of the filter entries are allowed 
     by the filter.
     If disabled no filtering will be done on subscriber IP addresses
     and all packets will pass the filter.

     This parameter is deprecated. Please use peaBridgeIpDslam::subsIpFilterType
     instead.

     Deprecated from:                EDA 2.2 R3A
    "
    ::= { pvcFiltersEntry 19 } 

subscriberIpFilterValue OBJECT-TYPE
	SYNTAX      OCTET STRING
    MAX-ACCESS  read-write
    STATUS      deprecated
    DESCRIPTION
    "Filter on subscriber IP addresses.
     When using DHCP the entries in the filter are added
     automatically according to the DHCP leases. For other
     access methods IP addresses can be added for filtering
     purposes.
     Filter entries are 4 bytes each.
     - to include 10.2.3.4 add 0x0a 0x02 0x03 0x04

     This parameter is deprecated. Please use the
     peaBridgeIpDslam::subsIpFilterTable table instead.

     Deprecated from:                EDA 2.2 R3A
    "
    ::= { pvcFiltersEntry 20 } 

upstreamPortIpFilterValue OBJECT-TYPE
	SYNTAX      OCTET STRING
    MAX-ACCESS  read-write
    STATUS      deprecated
    DESCRIPTION
    "Filter on TCP/UDP destination port number as well as destination IP
     address in packets from subscriber into network. Filter entries
     are 10 bytes each. The first two bytes represent the port number
     and the ending 8 bytes of the entry represent an IP address range.
     To exclude all SMTP traffic (port 25) except traffic with
     destination IP address in the range 10.0.0.0 to 10.0.0.10 add
     0x00 0x19 0x0A 0x00 0x00 0x00 0x0A 0x00 0x00 0x0A.

     This parameter is deprecated. Please use the IP Access Control List instead.
     For more information please see the following parameters:
     peaBridgeIpDslam::pvcUpstreamIpAclId
     peaBridgeIpDslam::ipAclTable
     peaBridgeIpDslam::ipAclRuleTable

     Deprecated from:           EDA 2.2 SP3
    " 
    ::= { pvcFiltersEntry 21 } 


virtualMacAddressDomain OBJECT-TYPE
	SYNTAX      Unsigned32 (1..63)
    MAX-ACCESS  read-write
    STATUS      current
    DESCRIPTION
    "The virtual Mac address domain specifies 6 of the 8 bits in the
     first byte in the virtual Mac address. (The remaining two bits 
     are the multicast bit and the globally/locally administrated bits 
     which equals 01 to identify the locally administrated	unicast 
     address known as the virtual Mac address)
	 With the domain bits, it is possible to secure the uniqueness of 
	 Mac addresses using different virtual Mac address schemes." 
    ::= { bridgeControl 5 } 
      
maximumEthernetFrameSize OBJECT-TYPE
	SYNTAX      Unsigned32 (1400..1546)
    MAX-ACCESS  read-write
    STATUS      current
    DESCRIPTION
    "MaximumEthernetFrameSize specifies the maximum frame size that
     the IP DSLAM will send up-stream in the access network.
     Longer frames will be discarded!
     The specified size covers the whole frame, including
     Ethernet header, VLAN-tag(s) and 4 bytes of CRC.
	 (See also the counter: DiscardedOversizedFrames.)" 
    ::= { bridgeControl 6 } 

lineTable OBJECT-TYPE
	SYNTAX      SEQUENCE OF LineEntry
  	MAX-ACCESS  not-accessible
    STATUS      current
    DESCRIPTION
    "A list of entries to the Line Table."
    ::= { bridgeControl 7 }   

lineEntry OBJECT-TYPE
	SYNTAX      LineEntry
    MAX-ACCESS  not-accessible
    STATUS      current
    DESCRIPTION
    "An entry containing Line objects for the 
     subscriber line identified by lineIndex."
    INDEX  {lineIndex}
    ::= { lineTable 1 }     
    
LineEntry ::= 
    SEQUENCE {
             enableAutoConfiguration                    TruthValue, 
             broadcastStormControl                      INTEGER,
             broadcastStormControlThreshold             Unsigned32,
             multicastStormControl                      INTEGER,
             multicastStormControlThreshold             Unsigned32
             } 
                
enableAutoConfiguration OBJECT-TYPE
	SYNTAX      TruthValue
    MAX-ACCESS  read-write
    STATUS      current
    DESCRIPTION
    "Enable of ILMI Auto Configuration for the Line. If True,
    ILMI AC will try to configure the CPE with all existing PVC:s for the line." 
    ::= { lineEntry 1 } 
      
broadcastStormControl OBJECT-TYPE
    SYNTAX  INTEGER {
                    disable(0),
                    limitToThreshold(1)
                    }
    MAX-ACCESS  read-write
    STATUS      current
    DESCRIPTION
    "Broadcast Storm Control (BSC) function. The threshold is set using
     broadcastStormControlThreshold. The function is default disabled.
     
     The possible values are
     0 - BSC is disabled.
     1 - BSC is enabled - broadcast is limited to broadcastStormControlThreshold.
     
     Valid from:            EDA 4.0 R1A
     " 
    ::= { lineEntry 5 }

broadcastStormControlThreshold OBJECT-TYPE
	SYNTAX      Unsigned32	(1..500)
	UNITS       "broadcast packets/sec"
    MAX-ACCESS  read-write
    STATUS      current
    DESCRIPTION
    "When broadcastStormControlThreshold is passed and broadcastStormControl is enabled,
     all broadcast traffic is limited to broadcastStormControlThreshold. Broadcast traffic
     above broadcastStormControlThreshold is dropped. Default is 10.
    
     Valid from:            EDA 4.0 R1A
     "     
    ::= { lineEntry 10 }
           
multicastStormControl OBJECT-TYPE
    SYNTAX  INTEGER {
                    disable(0),
                    limitToThreshold(1)
                    }
    MAX-ACCESS  read-write
    STATUS      current
    DESCRIPTION
    "Multicast Storm Control (MSC) function. The threshold is set using
     multicastStormControlThreshold. The function is default disabled.
     
     The possible values are
     0 - MSC is disabled.
     1 - MSC is enabled - multicast is limited to multicastStormControlThreshold.
     
     Valid from:            EDA 4.0 R1A
     " 
    ::= { lineEntry 15 }

multicastStormControlThreshold OBJECT-TYPE
	SYNTAX      Unsigned32	(1..500)
	UNITS       "multicast packets/sec"
    MAX-ACCESS  read-write
    STATUS      current
    DESCRIPTION
    "When multicastStormControlThreshold is passed and multicastStormControl is enabled,
     all multicast traffic is limited to multicastStormControlThreshold. Multicast traffic
     above multicastStormControlThreshold is dropped. Default is 10.
    
     Valid from:            EDA 4.0 R1A
     "     
    ::= { lineEntry 20 }
           
virtualMacAddressNodeId OBJECT-TYPE
	SYNTAX      OCTET STRING (SIZE(3))
    MAX-ACCESS  read-write
    STATUS      current
    DESCRIPTION
    "The virtual Mac address Node ID specifies the last 3 bytes in the
     virtual Mac address. With the Node ID, it is possible to identify
     the origin of an ethernet frame, even when the IP DSLAM has been
     exhanged with a new IP DSLAM, with a new Mac address." 
    ::= { bridgeControl 8 } 
    
vlanTagType OBJECT-TYPE
	SYNTAX      INTEGER { single (1), qinq (2) }
    MAX-ACCESS  read-write
    STATUS      current
    DESCRIPTION
    "If 1, VLAN tagging is single.
     If 2, VLAN tagging is double.
     
     Valid from:                EDA 2.0SP2
    "   
    ::= { bridgeControl 9 } 

virtualMacAddressNodeIdEx OBJECT-TYPE
	SYNTAX      OCTET STRING (SIZE(4))
    MAX-ACCESS  read-write
    STATUS      current
    DESCRIPTION
    "The virtual Mac address 'Node ID Extended' specifies 26 bits in the
     virtual Mac address. With the Node ID Extended, it is possible to identify
     the origin of an ethernet frame, even when the IP DSLAM has been
     exhanged with a new IP DSLAM, with a new Mac address.

     From the virtualMacAddressNodeIdEx, the first 26 bits is used as shown here with X:
     XXXXXXXX XXXXXXXX XXXXXXXX XX000000, the unused bits are set to zero.

     The Node Id Extended is inserted in the Virtual MAC address, as shown here with X:
     ******** ******** XXXXXXXX XXXXXXXX XXXXXXXX XX******."
    ::= { bridgeControl 10 } 

relayAgentEdaIp OBJECT-TYPE
    SYNTAX      IpAddress
    MAX-ACCESS  read-write
    STATUS      current
    DESCRIPTION
    "IP address inserted in the relay agent information when remoteIdEda is used (see
     'relayAgentConfiguration' description).
     Zero must be used when the IP-DSLAM is running standalone, in this case the IP-DSLAM will
     insert its own IP address into the relay agent information. If the IP-DSLAM is not running
     standalone the IP address of the controlling node (e.g. EAN or MSAN) must be specified with
     this object. 
     "     
    ::= { bridgeControl 11 }

relayAgentEdaNodeId OBJECT-TYPE
    SYNTAX      Unsigned32
    MAX-ACCESS  read-write
    STATUS      current
    DESCRIPTION
    "Specifies the NodeId inserted in the relay agent information when remoteEdaId is used (see 
     'relayAgentConfiguration' description).
     The layout of the NodeId field is dependant on the IP-DSLAM configuration.

     Layout of relayAgentEdaNodeId when the IP-DSLAM is running standalone:
     |    MSB                                     LSB    |
     |   8-bit    |   8-bit    |   8-bit    |    8-bit   |
     -----------------------------------------------------
     |     0      |     0      |     0      |     0      |
     -----------------------------------------------------
     |     NA     |     NA     |     NA     |    Line    |
     
     Layout of relayAgentEdaNodeId when the IP-DSLAM is located under an EAN:
     |    MSB                                     LSB    |
     |   8-bit    |   8-bit    |   8-bit    |    8-bit   |
     -----------------------------------------------------
     |     0-8    |    1-24    |    1-24    |     0      |
     -----------------------------------------------------
     |    ExtNo   | PortLevel1 | PortLevel2 |    Line    |

     Layout of relayAgentEdaNodeId when the IP-DSLAM is located under an MSAN:
     |    MSB                                     LSB    |
     |   8-bit    |   8-bit    |   8-bit    |    8-bit   |
     -----------------------------------------------------
     |    1-20    |    1-30    |     0      |     0      |
     -----------------------------------------------------
     |   SubRack  |    Slot    |  Reserved  |    Line    |

     The field 'Line' is and offset to which the IP-DSLAM will add the actual line number in the relay  
     agent information. Care must be taken to ensure that the specified offset + actual line number 
     does not exceed 255."
    ::= { bridgeControl 12 }

flowIndex OBJECT-TYPE
	SYNTAX      Unsigned32 
    MAX-ACCESS  not-accessible
    STATUS      current
    DESCRIPTION
    "Unique number assigned to each flow within PVC. The highest index is 7 upstream and
    3 downstream. Please note that flowIndex affects priority scheduling and buffer arbitration.
    Even when DRR scheduling is requested, flowIndex determines probability of packets being
    discarded from queue during congestion. Higher flowIndex means higher probability of
    being discarded. Range 0-3 downstream, 0-7 upstream. In the upstream direction flowIndex
    is the outgoing p-bit value, with exception for the case that all p-bit values are collected
    in one flow, in which case the flowIndex value is 0."
    ::= { bridgeControl 13 }   

downstreamFlowConfigTable OBJECT-TYPE
	SYNTAX      SEQUENCE OF DownstreamFlowConfigEntry
  	MAX-ACCESS  not-accessible
    STATUS      current
    DESCRIPTION
    "A list of downstream flows"
    ::= { bridgeControl 14 }   	
        
downstreamFlowConfigEntry OBJECT-TYPE
	SYNTAX      DownstreamFlowConfigEntry
    MAX-ACCESS  not-accessible
    STATUS      current
    DESCRIPTION
    "An entry containing flows identified by lineIndex, 
     pvcIndex and flowIndex."
    INDEX  { lineIndex, pvcIndex, flowIndex }
    ::= { downstreamFlowConfigTable 1 }     
    
DownstreamFlowConfigEntry ::= 
	SEQUENCE {
        dfcFlowIdentifyingValues    OCTET STRING, 	 
        dfcPolicingEnable           TruthValue, 
        dfcSustainableDataRate      Unsigned32, 
        dfcMaxBurst                 Unsigned32, 
        dfcBytesPerRound            Unsigned32,
        dfcMaxQueueBuffers          Unsigned32
        }
        
dfcFlowIdentifyingValues OBJECT-TYPE
	SYNTAX      OCTET STRING
    MAX-ACCESS  read-write
    STATUS      current
    DESCRIPTION
    "What values (in CoS or DSCP field) signal that the packet
    belongs to this flow. One octet per value. A packet that contains one
    of these values is classified as belonging to this flow."          
    ::= { downstreamFlowConfigEntry 2 } 

dfcPolicingEnable OBJECT-TYPE
	SYNTAX      TruthValue
    MAX-ACCESS  read-write
    STATUS      current
    DESCRIPTION
    "Is this flow to be policed?" 
    ::= { downstreamFlowConfigEntry 3 }

dfcSustainableDataRate OBJECT-TYPE
	SYNTAX      Unsigned32 (0|32000..196608000)
	UNITS       "bps"
    MAX-ACCESS  read-write
    STATUS      current
    DESCRIPTION
    "The maximum allowed average information rate in the flow.
 	 The rate must be lower than or equal to the configured ADSL
 	 rate and in steps of 32000 bps.
 	 Notice: To carry telephony over IP, 192000 bps is needed and
 	 the ADSL line must be configured to at least 192000." 
    ::= { downstreamFlowConfigEntry 4 } 
    
dfcMaxBurst OBJECT-TYPE
	SYNTAX      Unsigned32 (64..65535)
	UNITS       "bytes"
    MAX-ACCESS  read-write
    STATUS      current
    DESCRIPTION
    "The maximum number of bytes in a burst.
 	 Notice: To allow a complete telephony over IP packet to be 
 	 included in one burst,	250 bytes are needed.
	 Furthermore, if a VBR service category has been chosen, this
	 parameter cannot be 0." 
    ::= { downstreamFlowConfigEntry 5 } 
  
dfcBytesPerRound OBJECT-TYPE
	SYNTAX      Unsigned32 (32..2048)
	UNITS       "packets"
    MAX-ACCESS  read-write
    STATUS      current
    DESCRIPTION
    "The DRR scheduling algorithm visits all the queues in the PVC in a
    circular fashion (round robin). For each turn of the circle it transfers
    dfcBytesPerRound bytes from this queue to the (HW) transmit queue." 
    ::= { downstreamFlowConfigEntry 6 }

dfcMaxQueueBuffers  OBJECT-TYPE
    SYNTAX      Unsigned32 (1..100)
    UNITS       "buffers"
    MAX-ACCESS  read-write
    STATUS      current
    DESCRIPTION
    "The maximum number of packet buffers allowed to be placed in queue for
     one downstream flow queue
    " 
    ::= { downstreamFlowConfigEntry 7 }
    

downstreamFlowStatsTable OBJECT-TYPE
	SYNTAX      SEQUENCE OF DownstreamFlowStatsEntry
  	MAX-ACCESS  not-accessible
    STATUS      current
    DESCRIPTION
    "Statistics information for a list of downstream flows"
    ::= { bridgeControl 15 }   	
    
downstreamFlowStatsEntry OBJECT-TYPE
	SYNTAX      DownstreamFlowStatsEntry
    MAX-ACCESS  not-accessible
    STATUS      current
    DESCRIPTION
    "An entry containing flows identified by lineIndex, 
     pvcIndex and flowIndex."
    AUGMENTS  { downstreamFlowConfigEntry }
    ::= { downstreamFlowStatsTable 1 }     
    
DownstreamFlowStatsEntry ::= 
	SEQUENCE {
        dfsPolicedPacketCount   Counter32,
        dfsFrameCount           Counter32,
        dfsByteCount            Counter64,
        dfsPolicedBytesCount    Counter64,
        dfsMaxQueueUsage        Unsigned32
        }
        
dfsPolicedPacketCount OBJECT-TYPE
	SYNTAX      Counter32
    MAX-ACCESS  read-only
    STATUS      current
    DESCRIPTION
    "The number of packets that have been discarded by the
	policing mechanism. "    
    ::= { downstreamFlowStatsEntry 1 }

dfsFrameCount OBJECT-TYPE
	SYNTAX      Counter32
    MAX-ACCESS  read-only
    STATUS      current
    DESCRIPTION
    "The number of Ethernet frames that have passed. "    
    ::= { downstreamFlowStatsEntry 2 }   

dfsByteCount OBJECT-TYPE
	SYNTAX      Counter64
    MAX-ACCESS  read-only
    STATUS      current
    DESCRIPTION
    "The number of bytes that have passed."    
    ::= { downstreamFlowStatsEntry 3 }    

dfsPolicedBytesCount OBJECT-TYPE
	SYNTAX      Counter64
    MAX-ACCESS  read-only
    STATUS      current
    DESCRIPTION
    "The number of bytes that have been discarded by the
	policing mechanism."    
    ::= { downstreamFlowStatsEntry 4 }   

dfsMaxQueueUsage OBJECT-TYPE
    SYNTAX      Unsigned32
    MAX-ACCESS  read-write
    STATUS      current
    DESCRIPTION
    "The maximum number of buffers stored in a downstream flow
     queue at any time since the counter was reset.
     
     Zero is the only value that can be written to dfsMaxQueueUsage
     to clear the counter.

     Valid from:                EDA 2.2 R3A
    "    
    ::= { downstreamFlowStatsEntry 5 }   
    
upstreamFlowConfigTable OBJECT-TYPE
	SYNTAX      SEQUENCE OF UpstreamFlowConfigEntry
  	MAX-ACCESS  not-accessible
    STATUS      current
    DESCRIPTION
    "A list of upstream flows"
    ::= { bridgeControl 16 }   	
    
upstreamFlowConfigEntry OBJECT-TYPE
	SYNTAX      UpstreamFlowConfigEntry
    MAX-ACCESS  not-accessible
    STATUS      current
    DESCRIPTION
    "An entry containing flows identified by lineIndex, 
     pvcIndex and flowIndex."
    INDEX  { lineIndex, pvcIndex, flowIndex }
    ::= { upstreamFlowConfigTable 1 }

UpstreamFlowConfigEntry ::= 
	SEQUENCE {
        ufcFlowIdentifyingValues		OCTET STRING, 
        ufcPolicingEnable				TruthValue, 
        ufcSustainableDataRate 			Unsigned32, 
        ufcMaxBurst 					Unsigned32,
        ufcCosRemarkEnable				TruthValue,
        ufcExceedingTrafficFlow   Unsigned32
        }

ufcFlowIdentifyingValues OBJECT-TYPE
	SYNTAX      OCTET STRING
    MAX-ACCESS  read-write
    STATUS      current
    DESCRIPTION
    "What values (in CoS or DSCP field) signal that the packet
    belongs to this flow. One octet per value. A packet that contains
    one of these values is classified as belonging to this flow."          
    ::= { upstreamFlowConfigEntry 2 } 

ufcPolicingEnable OBJECT-TYPE
	SYNTAX      TruthValue
    MAX-ACCESS  read-write
    STATUS      current
    DESCRIPTION
    "Is this flow to be policed?" 
    ::= { upstreamFlowConfigEntry 3 }

ufcSustainableDataRate OBJECT-TYPE
	SYNTAX      Unsigned32 (0|32000..12288000)
	UNITS       "bps"
    MAX-ACCESS  read-write
    STATUS      current
    DESCRIPTION
    "The maximum allowed average data rate in the flow. The rate must
    be lower than or equal to the configured ADSL rate and in steps of
    32000 bps. Notice: To carry telephony over IP, 192000 bps is needed
    and the ADSL line must be configured to at least 192000." 
    ::= { upstreamFlowConfigEntry 4 } 
    
ufcMaxBurst OBJECT-TYPE
	SYNTAX      Unsigned32 (64..65535)
	UNITS       "bytes"
    MAX-ACCESS  read-write
    STATUS      current
    DESCRIPTION
    "The maximum number of bytes in a burst.
 	 Notice: To allow a complete telephony over IP packet to be 
 	 included in one burst,	250 bytes are needed.
	 Furthermore, if a VBR service category has been chosen, this
	 parameter cannot be 0." 
    ::= { upstreamFlowConfigEntry 5 } 

ufcCosRemarkEnable OBJECT-TYPE
	SYNTAX      TruthValue
    MAX-ACCESS  read-write
    STATUS      obsolete
    DESCRIPTION
    "Is the CoS/p-bit value in the Ethernet header to be overwritten?
    This MIB object may be removed.

 	Obsoleted from:			   EDA 2.2 SP1
	" 
    ::= { upstreamFlowConfigEntry 6 }

ufcExceedingTrafficFlow OBJECT-TYPE
	  SYNTAX      Unsigned32 (0..8)
    MAX-ACCESS  read-write
    STATUS      current
    DESCRIPTION
    "One Flow has one VLAN priority value associated, that VLAN priority value will be
     written in the outer most VLAN tag of the Ethernet frame before the Ethernet frame
     is forwarded to the aggregation network. Traffic within the policed bandwidth is
     forwarded to the aggregation network while traffic exceeding the policed bandwidth
     is either dropped or remarked with another VLAN priority.

     The ufcExceedingTrafficFlow parameter is used to configure whether traffic exceeding
     the policed bandwidth should be dropped or remarked with another VLAN priority
     before forwarding the packet to the aggregation network.

     Remarking of traffic is done by redirecting traffic exceeding the policed bandwidth
     of the current flow to another flow as illustrated below.

                                         IP DSLAM
                       _______________________________________________________________
                      |              _________________                                |
                      |             (                 )                               |
                      |       /<--- ( Flow x policing ) <----\                        |
                      |      /      (_________________)       \                       |
                      |     /          |                       \                      |
                      |    /           | Remark / redirect      \                     |
                      |   /            | exceeding traffic       \                    |
                      |  /             |                          \                   |
                      | /            __V______________            _\____________      |
     Aggregation      |/            (                 )          (   Initial    )     |
       Network   <----|<----------- ( Flow y policing ) <--------(    flow      )<----|---- End-user
                      |\            (_________________)          (___selection__)     |
                      | \              |                           /                  |
                      |  \             | Remark / redirect        /                   |
                      |   \            | exceeding traffic       /                    |
                      |    \           |                        /                     |
                      |     \        __V______________         /                      |
                      |      \      (                 )       /                       |
                      |       \<--- ( Flow y policing ) <----/                        |
                      |             (_________________)                               |
                      |                |                                              |
                      |                |                                              |
                      |                X Discard exceeding traffic                    |
                      |_______________________________________________________________|
                                                                                      
     Set ufcExceedingTrafficFlow to zero to drop traffic exceeding the policed bandwidth rate
     for the flow.
     
     Set ufcExceedingTrafficFlow to a value in the range 1..8 to redirect excess traffic to
     another flow. The value written to ufcExceedingTrafficFlow is the flowIndex of the flow
     where traffic must be redirected to. ufcExceedingTrafficFlow can not be set to the same
     value as the flowIndex of the current flow.

     Note: Care must be taken to not configure an infinite redirect loop.
     
     Valid from:                EDA 2.2 R3A
    "
    DEFVAL {0}
    ::= { upstreamFlowConfigEntry 7 } 
    

upstreamFlowStatsTable OBJECT-TYPE
	SYNTAX      SEQUENCE OF UpstreamFlowStatsEntry
  	MAX-ACCESS  not-accessible
    STATUS      current
    DESCRIPTION
    "Statistics information for a list of upstream flows"
    ::= { bridgeControl 17 }   	
    
upstreamFlowStatsEntry OBJECT-TYPE
	SYNTAX      UpstreamFlowStatsEntry
    MAX-ACCESS  not-accessible
    STATUS      current
    DESCRIPTION
    "An entry containing flows identified by lineIndex, 
    pvcIndex and flowIndex."
    AUGMENTS  { upstreamFlowConfigEntry }
    ::= { upstreamFlowStatsTable 1 }

UpstreamFlowStatsEntry ::= 
	SEQUENCE {
        ufsPolicedPacketCount  			Counter32,
        ufsFrameCount					Counter32, 
        ufsByteCount					Counter64,
        ufsPolicedBytesCount			Counter64 
        }

ufsPolicedPacketCount OBJECT-TYPE
	SYNTAX      Counter32
    MAX-ACCESS  read-only
    STATUS      current
    DESCRIPTION
    "The number of packets that have been discarded by the
	policing mechanism."    
    ::= { upstreamFlowStatsEntry 1 }

ufsFrameCount OBJECT-TYPE
	SYNTAX      Counter32
    MAX-ACCESS  read-only
    STATUS      current
    DESCRIPTION
    "The number of Ethernet frames that have passed. "    
    ::= { upstreamFlowStatsEntry 2 }   

ufsByteCount OBJECT-TYPE
	SYNTAX      Counter64
    MAX-ACCESS  read-only
    STATUS      current
    DESCRIPTION
    "The number of bytes that have passed."    
    ::= { upstreamFlowStatsEntry 3 }

ufsPolicedBytesCount OBJECT-TYPE
	SYNTAX      Counter64
    MAX-ACCESS  read-only
    STATUS      current
    DESCRIPTION
    "The number of bytes that have been discarded by the
	policing mechanism."    
    ::= { upstreamFlowStatsEntry 4 }    

mcastFilter    OBJECT IDENTIFIER 
    ::= { bridgeControl 18 }

mcastFilterTypeTable OBJECT-TYPE    
	SYNTAX      SEQUENCE OF McastFilterTypeEntry
  	MAX-ACCESS  not-accessible
    STATUS      current
    DESCRIPTION
    "A list of entries to the multicast filter type list."
    ::= { mcastFilter 1 }

mcastFilterTypeEntry OBJECT-TYPE
	SYNTAX      McastFilterTypeEntry
    MAX-ACCESS  not-accessible
    STATUS      current
    DESCRIPTION
    "The lineIndex and pvcIndex pair forms a unique
     identification of a PVC in the managed device. A 
     mcastFilterTypeEntry contains multicast filter 
     type information for a PVC."
    INDEX  {lineIndex,
            pvcIndex}
    ::= { mcastFilterTypeTable 1 }         
    
McastFilterTypeEntry ::= 
	SEQUENCE {
        mcastFilterType      INTEGER
        }

mcastFilterType OBJECT-TYPE
    SYNTAX      INTEGER { positive(0), negative(1) }
    MAX-ACCESS  read-write
    STATUS      current
    DESCRIPTION
    "Specifies whether the multicast filter is positive or
     negative. If the multicast filter is positive, the 
     managed device is allowed to forward multicast group
     Internet addresses specified in mcastFilterTable. If
     the multicast filter is negative, the managed device
     is allowed to forward all multicast group Internet
     addresses except the ones specified in mcastFilterTable.
     Whether the multicast filter is positive or negative is
     specified per PVC."
    ::= { mcastFilterTypeEntry 1 }

mcastFilterTable OBJECT-TYPE
	SYNTAX      SEQUENCE OF McastFilterEntry
  	MAX-ACCESS  not-accessible
    STATUS      current
    DESCRIPTION
    "A list of entries to the multicast filter list."
    ::= { mcastFilter 2 }

mcastFilterEntry OBJECT-TYPE
	SYNTAX      McastFilterEntry
    MAX-ACCESS  not-accessible
    STATUS      current
    DESCRIPTION
    "The lineIndex and pvcIndex pair forms a unique
     identification of a PVC in the managed device. A 
     mcastFilterEntry contains multicast filter information
     for a PVC. Each entry describes a range of consecutive
     multicast group addresses which are allowed or disallowed,
     depending on the value of mcastFilterType,to be forwarded
     on the PVC.

     If the multicast filter is empty, then all the multicast
     groups are allowed irrespective of mcastFilterType.
     
     F.ex. if multicast group Internet addresses in the range
     224.10.10.10 to 224.10.10.40 are allowed to be forwarded
     on the PVC, a positive (0) multicast filter should be
     used, mcastFilterFirstAddress is set to 224.10.10.10 and
     mcastFilterLastAddress is set to 224.10.10.40.
     
     Multiple entries may be required to describe the complete
     multicast filter for one PVC."
    INDEX  {lineIndex,
            pvcIndex,
            mcastFilterAddressType,
            mcastFilterFirstAddress}
    ::= { mcastFilterTable 1 }     
    
McastFilterEntry ::= 
	SEQUENCE {
        mcastFilterAddressType      InetAddressType,
        mcastFilterFirstAddress     InetAddress,
        mcastFilterLastAddress      InetAddress,
        mcastFilterVlanID			INTEGER,
        mcastFilterVlanPriority		INTEGER,
        mcastFilterRowStatus        RowStatus
        }

mcastFilterAddressType OBJECT-TYPE
    SYNTAX      InetAddressType
    MAX-ACCESS  read-only
    STATUS      current
    DESCRIPTION
    "The type of Internet address used in the multicast
     filter address range."
    ::= { mcastFilterEntry 1 }

mcastFilterFirstAddress OBJECT-TYPE
    SYNTAX      InetAddress (SIZE (4..20))
    MAX-ACCESS  read-only
    STATUS      current
    DESCRIPTION
    "The first address in the multicast group Internet
     address range. The type of this address is determined
     by the value of the mcastFilterAddressType object.
     The mcastFilterFirstAddress may not be empty due to
     the SIZE restriction."
    ::= { mcastFilterEntry 2 }
        
mcastFilterLastAddress OBJECT-TYPE
    SYNTAX      InetAddress (SIZE (4..20))
    MAX-ACCESS  read-create
    STATUS      current
    DESCRIPTION
    "The last address in the multicast group Internet
     address range. The type of this address is determined
     by the value of the mcastFilterAddressType object.
     mcastFilterLastAddress must be a equal to or higher
     than mcastFilterFirstAddress before the settings are
     put into operation.
     The mcastFilterFirstAddress may not be empty due to
     the SIZE restriction.
     To modify the value of mcastFilterLastAddress, the
     conceptual row must be taken Out of Service"
    ::= { mcastFilterEntry 3 }

mcastFilterVlanID OBJECT-TYPE
	SYNTAX      INTEGER (-1..4095) 
    MAX-ACCESS  read-create
    STATUS      current
    DESCRIPTION
    "The Vlan ID to be used for the multicast traffic on a
     multicast group Internet address range, from and to
     the specified PVC.
     
     The value -1 is a nil-value indicating that the outer
     service VLAN ID (peaBridgeIpDslam::vlanID) is used for
     the multicast traffic.

     If the mcastFilterType is 'negative' this parameter has no
     effect, in this case the outer service VLAN ID is always
     used.

     Valid from:                EDA 2.2 SP3
     "     
    ::= { mcastFilterEntry 8 }    

mcastFilterVlanPriority OBJECT-TYPE
	SYNTAX      INTEGER (-1..7)
    MAX-ACCESS  read-create
    STATUS      current
    DESCRIPTION
    "The priority (accordingly to 802.1Q) that should be used for
     the multicast frames to and from the specified PVC. The value
     can be between 0 and 7 (where 7 is the highest priority).
     
     The value -1 is a nil-value indicating that the outer service
     VLAN priority (peaBridgeIpDslam::priority) is used for the
     multicast traffic.
     
     If the mcastFilterType is negative this parameter has no
     effect, in this case the outer service VLAN priority is always
     used.
     
     Valid from:                EDA 2.2 SP3
     "     
    ::= { mcastFilterEntry 13 }
    
mcastFilterRowStatus OBJECT-TYPE
    SYNTAX      RowStatus
    MAX-ACCESS  read-create
    STATUS      current
    DESCRIPTION
    "The mcastFilterRowStatus is used to manage the 
     creation and deletion of rows in mcastFilterTable." 
    ::= { mcastFilterEntry 99 }    
    

macHistoryTable OBJECT-TYPE
    SYNTAX      SEQUENCE OF MACHistoryEntry
    MAX-ACCESS  not-accessible
    STATUS      current
    DESCRIPTION
    "A list of MAC address entries of Subscribers disconnected/connected to IP DSLAM"
    ::= { bridgeControl 19 }   
    
macHistoryEntry OBJECT-TYPE
    SYNTAX      MACHistoryEntry
    MAX-ACCESS  not-accessible
    STATUS      current
    DESCRIPTION
    "An entry containing the Subscriber MAC address
     for each connection identified by the lineIndex and pvcIndex."
    INDEX  {lineIndex, pvcIndex, subscriberMacAddress }
    ::= { macHistoryTable 1 }     
    
MACHistoryEntry ::= 
	SEQUENCE {
		        subscriberMacAddress                   MacAddress,
                subscriberMacLastSeen                  TimeTicks, 
                subscriberMacStatus                    INTEGER
              }
              
subscriberMacAddress   OBJECT-TYPE
    SYNTAX      MacAddress
    MAX-ACCESS  read-only
    STATUS      current
    DESCRIPTION
     "MAC address of the subscriber."          
    ::= { macHistoryEntry 1  } 

subscriberMacLastSeen OBJECT-TYPE
    SYNTAX      TimeTicks
    MAX-ACCESS  read-only
    STATUS      current
    DESCRIPTION
    "The timestamp which indicates the time
     when the Subscriber MAC address was last seen."     
    ::= { macHistoryEntry 2 }     

subscriberMacStatus OBJECT-TYPE
    SYNTAX      INTEGER { inactive(0),
                          active(1)
                        }
    MAX-ACCESS  read-only
    STATUS      current
    DESCRIPTION
    "If Active indicates that the subscriber is currently connected
     and Inactive shows the MAC of a disconnected subscriber. 
     The value can be either Active(1) or Inactive(0)." 
    ::= { macHistoryEntry 3 }
    
macFilterAgedTime  OBJECT-TYPE
    SYNTAX      INTEGER
    MAX-ACCESS  read-write
    STATUS      current
    DESCRIPTION
    "macFilterAgedTime specifies in seconds the maximum age of inactive
     MAC address entries in the subscriber MAC filter for access
     methods PPPoE and TLS.
    " 
    ::= { bridgeControl 20 }

accessControlList    OBJECT IDENTIFIER
    ::= { bridgeControl 21 }

vlanIdAclTable OBJECT-TYPE
    SYNTAX      SEQUENCE OF VlanIdAclEntry
    MAX-ACCESS  not-accessible
    STATUS      current
    DESCRIPTION
    "This table maintains a list of VLAN ID Access Control Lists in the IPDSLAM.
     Each Access Control List is made up of a group of access rules. The
     access rules are stored in the vlanIdAclRuleTable. This table is used
     to add/delete VLAN ID Access Control Lists.

     ACL's are statements which are called rules of ACL that are grouped
     together by a number. Within this group of statements, when a packet
     is processed by an ACL on the IPDSLAM, the IPDSLAM will go through
     certain steps in finding a match against the ACL statements. ACL's are
     processed top-down by the IPDSLAM. Using a top-down approach, a packet
     is compared to the first statement in the ACL, and if the IPDSLAM finds
     a match between the packet and the statement, the IPDSLAM will execute
     one of two actions included with the statement:

     - Permit
     - Deny

     If the IPDSLAM doesn't find a match of packet contents to the first
     ACL statement, the IPDSLAM will proceed to the next statement in the list,
     again going through the same matching process If there isn't a match on
     this statement, the IPDSLAM will keep on going through the list until it
     finds a match. If the IPDSLAM goes through the entire list and doesn't
     find a match, the IPDSLAM will drop the packet.

     If there is a match on a statement, no further statements are processed.
     Therefore, the order of the statements is very important in an ACL.

     Valid from:                EDA 2.2 R3A
    "
    ::= { accessControlList 4 }

vlanIdAclEntry OBJECT-TYPE
    SYNTAX      VlanIdAclEntry
    MAX-ACCESS  not-accessible
    STATUS      current
    DESCRIPTION
    "An entry in the vlanIdAclTable.

     Valid from:                EDA 2.2 R3A
    "
    INDEX {vlanIdAclId}
    ::= { vlanIdAclTable 5 }

VlanIdAclEntry ::=
    SEQUENCE {
        vlanIdAclId             Unsigned32,
        vlanIdAclNumberOfRules  Unsigned32,
        vlanIdAclRowStatus      RowStatus
        }

vlanIdAclId OBJECT-TYPE
    SYNTAX      Unsigned32 (1..4294967295)
    MAX-ACCESS  read-only
    STATUS      current
    DESCRIPTION
    "Index of the VLAN ID Access Control List.

     Valid from:                EDA 2.2 R3A
    "
    ::= { vlanIdAclEntry 1 }

vlanIdAclNumberOfRules OBJECT-TYPE
    SYNTAX      Unsigned32
    MAX-ACCESS  read-only
    STATUS      current
    DESCRIPTION
    "Total number of rules in the VLAN ID Access Control List (ACL).

     Valid from:                EDA 2.2 R3A
    "
    ::= { vlanIdAclEntry 5 }

vlanIdAclRowStatus OBJECT-TYPE
    SYNTAX      RowStatus
    MAX-ACCESS  read-create
    STATUS      current
    DESCRIPTION
    "This object is used to manage the creation, deletion and modification
     of rows in the VLAN ID Access Control List Table.

     Due to the way SNMP is handled in the IPDSLAM and the configuration
     file verification, RowStatus is handled slightly different in the
     IPDSLAM compared to the way described in RFC 2579.

     Below is a state/event table describing how the RowStatus will be handled
     in the IPDSLAM. The action to take and the return value assumes that the
     index to the table is valid.

     +-------------+---------------+---------------+---------------+---------------+
     | Command     |       A       |      B        |      C        |      D        |
     |             | status column | status column | status column | status column |
     |             |does not exist |   notReady    | notInService  | is active     |
     +-------------+---------------+---------------+---------------+---------------+
     | Set status  |  Inconsistent |               |  Inconsistent |  Inconsistent |
     | column      |  Value        |               |  Value        |  Value        |
     | to          |  (1)          |    (9)        |  (1)          |  (1)          |
     | CreateAndGo |  State = A    |               |  State = C    |  State = D    |
     +-------------+---------------+---------------+---------------+---------------+
     | Set status  |  NoError      |               |  NoError      |  NoError      |
     | column to   |  (2)          |    (9)        |  (2)          |  (2)(3)       |
     |CreateAndWait|  State = C    |               |  State = C    |  State = C    |
     +-------------+---------------+---------------+---------------+---------------+
     | Set status  | Inconsistent  |               |  NoError      |  NoError      |
     | to          | Value         |               |               |               |
     |             | (4)           |    (9)        |  (5)          |               |
     | Active      | State = A     |               |   State = D   | State = D     |
     +-------------+---------------+---------------+---------------+---------------+
     | Set status  | Inconsistent  |               |  NoError      | NoError       |
     | column Value|               |               |               |               |
     | to          | (4)           |    (9)        |               |  (6)          |
     | NotInService| State = A     |               |  State = C    | State = C     |
     +-------------+---------------+---------------+---------------+---------------+
     | Set status  | Inconsistent  | Inconsistent  | Inconsistent  | Inconsistent  |
     | column      | Value         | Value         | Value         | Value         |
     | to          |               |               |               |               |
     | NotReady    | State = A     | State = B     | State = C     | state = D     |
     +-------------+---------------+---------------+---------------+---------------+
     | Set status  | NoError       |               | NoError       | NoError       |
     | column      |               |               |               |               |
     | to          |               |    (9)        |  (7)          |  (7)          |
     | Destroy     | State = A     |               | State = A     | State = A     |
     +-------------+---------------+---------------+---------------+---------------+
     | Get         | NoSuchInstance|               | NoError       |  NoError      |
     | any column  | (4)           |    (9)        | (8)           |  (8)          |
     | value       | State = A     |               | State = C     |  State = D    |
     +-------------+---------------+---------------+---------------+---------------+

     (1) CreateAndGo is not supported in the IPDSLAM because the application
         receiving the command does not receive all parameters for the conceptual row
         in the table simultaneously but as a series of commands.

     (2) Temporary instance of the conceptual row is created for the Management,
         and placed in state NotInService.

     (3) If an instance of the conceptual row exists in Runtime, then copy it to the
         temporary instance.

     (4) The instance of the conceptual row does not exist in the Management and Runtime.

     (5) Data from the temporary  instance of the conceptual row is copied to
         the runtime instance and  the conceptual row is set to state Active.
         The temporary instance is deleted.

     (6) Temporary instance of the conceptual row is created for the Management,
         and placed in state NotInService. Data from the runtime instance of the conceptual
         row is copied to the temporary instance and the runtime instance is deleted.

     (7) The conceptual row may exist is two instances,
         a temporary management instance and a  runtime instance.

         - Loop through all the connections and find for which connections ACL is being used
         - If the ACL is not used for any connection, then delete ACL
           (the management and runtime instance), otherwise return SnmpError.

     (8) If a temporary management instance of the row exists,
         then the read operation returns the variable value from that instance,
         otherwise the returned value is taken from the runtime instance.

     (9) The conceptual row will never exist in notReady state

     Valid from:                EDA 2.2 R3A
    "
    ::= { vlanIdAclEntry 999 }

vlanIdAclRuleTable OBJECT-TYPE
    SYNTAX      SEQUENCE OF VlanIdAclRuleEntry
    MAX-ACCESS  not-accessible
    STATUS      current
    DESCRIPTION
    "This table is used to add/delete individual access rule
     statement in an VLAN ID Access Control List. The order of the rules
     is very important. The rules are processed in a top down order.
     Once a match is found, no further rules are processed. If no
     match is found, the packet is dropped.

     Valid from:                EDA 2.2 R3A
    "
    ::= { accessControlList 6 }

vlanIdAclRuleEntry OBJECT-TYPE
    SYNTAX     VlanIdAclRuleEntry
    MAX-ACCESS not-accessible
    STATUS     current
    DESCRIPTION
    "An entry in the VLAN ID ACL Rule Table.

     Valid from:                EDA 2.2 R3A
    "
    INDEX {vlanIdAclId, vlanIdAclRuleIndex }
    ::= { vlanIdAclRuleTable 5 }

VlanIdAclRuleEntry ::=
    SEQUENCE {
        vlanIdAclRuleIndex            Unsigned32,
        vlanIdAclMatchAction          INTEGER,
        vlanIdAclVlanIdMin            Unsigned32,
        vlanIdAclVlanIdMax            Unsigned32,
        vlanIdAclRuleRowStatus        RowStatus
        }

vlanIdAclRuleIndex OBJECT-TYPE
    SYNTAX        Unsigned32(1..64)
    MAX-ACCESS    read-only
    STATUS        current
    DESCRIPTION
    "The Access Control List may have multiple rules.
     The vlanIdAclRuleIndex specifies the position of the
     particular rule in the ACL.

     Valid from:                EDA 2.2 R3A
    "
    ::= { vlanIdAclRuleEntry 1 }

vlanIdAclMatchAction OBJECT-TYPE
    SYNTAX      INTEGER { deny(0), permit(1)}
    MAX-ACCESS  read-create
    STATUS      current
    DESCRIPTION
    "Indicates the action to be taken when packet meets the filtering
     condition in an ACL Rule.

     permit: Every packet that matches rule condition is forwarded
             for further processing.
     deny:   Every packet that matches rule condition is discarded.

     The value cannot be changed while the Rule is Active.

     Valid from:                EDA 2.2 R3A
    "
    DEFVAL { permit }
    ::= { vlanIdAclRuleEntry 5 }

vlanIdAclVlanIdMin OBJECT-TYPE
    SYNTAX      Unsigned32 (0..4095)
    MAX-ACCESS  read-create
    STATUS      current
    DESCRIPTION
    "vlanIdAclVlanIdMin is 12 bit VLAN ID (0 to 4095) which defines
     the first element of the intended VLAN ID range.
     vlanIdAclVlanIdMin and vlanIdAclVlanIdMax together indicate a
     range of VLAN IDs. Packets from the host with a VLAN ID in the
     specified range will be filtered, depending on the value of the
     action field.

	 The value cannot be changed while the rule is active.

     The default value is 0.

     Valid from:                EDA 2.2 R3A
    "
    DEFVAL {0}
    ::= { vlanIdAclRuleEntry 10 }

vlanIdAclVlanIdMax OBJECT-TYPE
    SYNTAX      Unsigned32 (0..4095)
    MAX-ACCESS  read-create
    STATUS      current
    DESCRIPTION
    "vlanIdAclVlanIdMax is 12 bit VLAN ID (0 to 4095) which defines
     the last element of the intended VLAN ID range.
     vlanIdAclVlanIdMin and vlanIdAclVlanIdMax together indicate a
     range of VLAN IDs. Packets from the host with a VLAN ID in the
     specified range will be filtered, depending on the value of the
     action field.

	 The value cannot be changed while the rule is active.

     The default value is 4095.

     Valid from:                EDA 2.2 R3A
    "
    DEFVAL {4095}
    ::= { vlanIdAclRuleEntry 15 }

vlanIdAclRuleRowStatus OBJECT-TYPE
    SYNTAX      RowStatus
    MAX-ACCESS  read-create
    STATUS      current
    DESCRIPTION
    "This object is used to manage creation, deletion and modification of rows
     in the Access Control List Rule Table.

     Due to the way SNMP is handled in the IPDSLAM and the configuration file
     verification, RowStatus is handled slightly different in the IPDSLAM
     compared to the way described in RFC 2579.

     Below is a state/event table describing how the RowStatus will be handled
     in the IPDSLAM. The action to take and the return value assumes that the
     index to the table is valid.

     +-------------+---------------+---------------+---------------+---------------+
     | Command     |       A       |      B        |      C        |      D        |
     |             | status column | status column | status column | status column |
     |             |does not exist |   notReady    | notInService  | is active     |
     +-------------+---------------+---------------+---------------+---------------+
     | Set status  |  Inconsistent |               |  Inconsistent |  Inconsistent |
     | column      |  Value        |               |  Value        |  Value        |
     | to          |  (1)          |    (10)       |  (1)          |  (1)          |
     | CreateAndGo |  State = A    |               |  State = C    |  State = D    |
     +-------------+---------------+---------------+---------------+---------------+
     | Set status  |  NoError      |               |  NoError      |  NoError      |
     | column to   |  (2)          |    (10)       |  (2)          |  (2)(3)       |
     |CreateAndWait|  State = C    |               |  State = C    |  State = C    |
     +-------------+---------------+---------------+---------------+---------------+
     | Set status  | Inconsistent  |               |  NoError      |  NoError      |
     | to          | Value         |               |               |               |
     |             | (4)           |    (10)       |  (5)          |               |
     | Active      | State = A     |               |   State = D   | State = D     |
     +-------------+---------------+---------------+---------------+---------------+
     | Set status  | Inconsistent  |               |  NoError      | NoError       |
     | column      | Value         |               |               |               |
     | to          | (4)           |    (10)       |               |  (6)          |
     | NotInService| State = A     |               |  State = C    | State = C     |
     +-------------+---------------+---------------+---------------+---------------+
     | Set status  | Inconsistent  | Inconsistent  | Inconsistent  | Inconsistent  |
     | column      | Value         | Value         | Value         | Value         |
     | to          |               |               |               |               |
     | NotReady    | State = A     | State = B     | State = C     | state = D     |
     +-------------+---------------+---------------+---------------+---------------+
     | Set status  | NoError       |               | NoError       | NoError       |
     | column      |               |               |               |               |
     | to          |               |    (10)       |  (7)          |  (7)          |
     | Destroy     | State = A     |               | State = A     | State = A     |
     +-------------+---------------+---------------+---------------+---------------+
     |Set any other| Inconsistent  |               | NoError       | Inconsistent  |
     |column to    | Name          |    (10)       |               | Value         |
     |some value   | (4)           |               |               |  (8)          |
     |             | State = A     |               | State = C     | State = D     |
     +-------------+---------------+---------------+---------------+---------------+
     | Get         | NoSuchInstance|               | NoError       |  NoError      |
     | any column  | (4)           |    (10)       | (9)           |  (9)          |
     | value       | State = A     |               | State = C     |  State = D    |
     +-------------+---------------+---------------+---------------+---------------+

     (1) CreateAndGo is not supported in the IPDSLAM because the application receiving
         the command does not receive all parameters for the conceptual row in the table
         simultaneously but as a series of commands.

     (2) Temporary instance of the conceptual row is created for the management and
         placed in state NotInService.

     (3) If an instance of the conceptual row exists in runtime,
         it is copied to the temporary instance.

     (4) The instance of the conceptual row does not exists in management and runtime.

     (5) Data from the temporary  instance of the conceptual row is copied to the runtime
         instance and the conceptual row is set to state Active.
         The temporary instance is deleted.

     (6) Temporary instance of the conceptual row is created in the management and
         placed in state NotInService. Data from the runtime instance of the conceptual row
         is copied to the temporary instance and the runtime instance is deleted.

     (7) The conceptual row may exist is two instances, a temporary management instance and
         a runtime instance. Both instances are deleted.

     (8) The ACL rule cannot be edited when conceptual row is Active.

     (9) If a temporary management instance of the row exists, then the read operation returns
         the variable value from that instance, otherwise the returned value is taken from the
         runtime instance.

     (10) The conceptual row can never exist in state notReady.

     Valid from:                EDA 2.2 R3A
    "
    ::= { vlanIdAclRuleEntry 999 }

etherTypeAclTable OBJECT-TYPE
    SYNTAX   SEQUENCE OF EtherTypeAclEntry
    MAX-ACCESS not-accessible
    STATUS     current
    DESCRIPTION
    "This table maintains a list of EtherType Access Control Lists in the IPDSLAM.        
     Each Access Control List is made up of a group of access rules. The 
     access rules are stored in the etherTypeAclRuleTable. This table is used
     to add/delete EtherType Access Control Lists.

     ACL's are statements which are called rules of ACL that are grouped
     together by a number. Within this group of statements, when a packet
     is processed by an ACL on the IPDSLAM, the IPDSLAM will go through
     certain steps in finding a match against the ACL statements. ACL's are
     processed top-down by the IPDSLAM. Using a top-down approach, a packet
     is compared to the first statement in the ACL, and if the IPDSLAM finds
     a match between the packet and the statement, the IPDSLAM will execute
     one of two actions included with the statement:

     - Permit
     - Deny

     If the IPDSLAM doesn't find a match of packet contents to the first
     ACL statement, the IPDSLAM will proceed to the next statement in the list,
     again going through the same matching process If there isn't a match on
     this statement, the IPDSLAM will keep on going through the list until it
     finds a match. If the IPDSLAM goes through the entire list and doesn't
     find a match, the IPDSLAM will drop the packet.

     If there is a match on a statement, no further statements are processed.
     Therefore, the order of the statements is very important in an ACL.

     Valid from:                EDA 2.2 SP2
    "
     
     ::= { accessControlList 10 }

etherTypeAclEntry OBJECT-TYPE
    SYNTAX     EtherTypeAclEntry
    MAX-ACCESS not-accessible
    STATUS     current
    DESCRIPTION
    "An entry in the etherTypeAclTable.

     Valid from:                EDA 2.2 SP2
    "
    INDEX {etherTypeAclId}
    ::= { etherTypeAclTable 5 }

EtherTypeAclEntry ::=
        SEQUENCE {
	             etherTypeAclId             Unsigned32,
	             etherTypeAclNumberOfRules  Unsigned32,
	             etherTypeAclRowStatus      RowStatus	
    	          }

etherTypeAclId OBJECT-TYPE
    SYNTAX       Unsigned32 (1.. 4294967295)
    MAX-ACCESS   read-only
    STATUS       current
    DESCRIPTION
    "Index of the EtherType Access Control List.
   
     Valid from:                EDA 2.2 SP2
    "
   ::= { etherTypeAclEntry 1 }

etherTypeAclNumberOfRules OBJECT-TYPE
    SYNTAX       Unsigned32
    MAX-ACCESS   read-only
    STATUS       current
    DESCRIPTION
    "Total number of rules in the EtherType Access Control List (ACL).

     Valid from:                EDA 2.2 SP2
    "             
   ::= { etherTypeAclEntry 5 }

etherTypeAclRowStatus OBJECT-TYPE
    SYNTAX       RowStatus
    MAX-ACCESS   read-create
    STATUS       current
    DESCRIPTION
    "This object is used to manage the creation, deletion and modification
     of rows in the EtherType Access Control List Table. 

     Due to the way SNMP is handled in the IPDSLAM and the configuration
     file verification, RowStatus is handled slightly different in the
     IPDSLAM compared to the way described in RFC 2579.

     Below is a state/event table describing how the RowStatus will be handled
     in the IPDSLAM. The action to take and the return value assumes that the
     index to the table is valid.
     
     +-------------+---------------+---------------+---------------+---------------+
     | Command     |       A       |      B        |      C        |      D	       | 
     |             | status column | status column | status column | status column |
     |             |does not exist |   notReady    | notInService  | is active     |
     +-------------+---------------+---------------+---------------+---------------+
     | Set status  |  Inconsistent |               |  Inconsistent |  Inconsistent |
     | column      |  Value        |               |  Value        |  Value	       |
     | to          |  (1)          |    (9)        |  (1)          |  (1)          |
     | CreateAndGo |  State = A    |               |  State = C    |  State = D    |
     +-------------+---------------+---------------+---------------+---------------+
     | Set status  |  NoError      |               |  NoError      |  NoError      |
     | column to   |  (2)          |    (9)        |  (2)          |  (2)(3)       |
     |CreateAndWait|  State = C    |               |  State = C    |  State = C    |   
     +-------------+---------------+---------------+---------------+---------------+
     | Set status  | Inconsistent  |               |  NoError      |  NoError      |
     | to          | Value         |               |               |               |    
     |             | (4)           |    (9)        |  (5)          |               |
     | Active      | State = A     |               |   State = D   | State = D     |
     +-------------+---------------+---------------+---------------+---------------+
     | Set status  | Inconsistent  |               |  NoError      | NoError       |
     | column Value|               |               |               |               | 
     | to          | (4)           |    (9)        |               |  (6)          |
     | NotInService| State = A     |               |  State = C    | State = C     |
     +-------------+---------------+---------------+---------------+---------------+
     | Set status  | Inconsistent  | Inconsistent  | Inconsistent  | Inconsistent  |
     | column      | Value         | Value         | Value         | Value         |
     | to          |               |               |               |               |
     | NotReady    | State = A     | State = B     | State = C     | state = D     |
     +-------------+---------------+---------------+---------------+---------------+
     | Set status  | NoError       |               | NoError       | NoError       |
     | column      |               |               |               |               |
     | to          |               |    (9)        |  (7)          |  (7)          |
     | Destroy     | State = A     |               | State = A     | State = A     |
     +-------------+---------------+---------------+---------------+---------------+
     | Get         | NoSuchInstance|               | NoError       |  NoError      |
     | any column  | (4)           |    (9)        | (8)           |  (8)          |
     | value       | State = A     |               | State = C     |  State = D    |
     +-------------+---------------+---------------+---------------+---------------+
     
     (1) CreateAndGo is not supported in the IPDSLAM because the application
         receiving the command does not receive all parameters for the conceptual row
         in the table simultaneously but as a series of commands.

     (2) Temporary instance of the conceptual row is created for the Management,
         and placed in state NotInService.
         
     (3) If an instance of the conceptual row exists in Runtime, then copy it to the
         temporary instance.

     (4) The instance of the conceptual row does not exist in the Management and Runtime. 

     (5) Data from the temporary  instance of the conceptual row is copied to
         the runtime instance and  the conceptual row is set to state Active.
         The temporary instance is deleted.

     (6) Temporary instance of the conceptual row is created for the Management,
         and placed in state NotInService. Data from the runtime instance of the conceptual
         row is copied to the temporary instance and the runtime instance is deleted. 

     (7) The conceptual row may exist is two instances,
         a temporary management instance and a  runtime instance. 
    
         - Loop through all the connections and find for which connections ACL is being used
         - If the ACL is not used for any connection, then delete ACL
           (the management and runtime instance), otherwise return SnmpError.

     (8) If a temporary management instance of the row exists,
         then the read operation returns the variable value from that instance,
         otherwise the returned value is taken from the runtime instance.

     (9) The conceptual row will never exist in notReady state

     
     Valid from:                EDA 2.2 SP2
     "
    ::= { etherTypeAclEntry 999 }

etherTypeAclRuleTable OBJECT-TYPE
    SYNTAX   SEQUENCE OF EtherTypeAclRuleEntry
    MAX-ACCESS not-accessible
    STATUS   current
    DESCRIPTION
    "This table is used to add/delete individual access rule 
     statement in an EtherType Access Control List. The order of the rules 
     is very important. The rules are processed in a top down order. 
     Once a match is found, no further rules are processed. If no 
     match is found, the packet is dropped.

     Valid from:                EDA 2.2 SP2
    "
    ::= { accessControlList 15 }

etherTypeAclRuleEntry OBJECT-TYPE
    SYNTAX     EtherTypeAclRuleEntry
    MAX-ACCESS not-accessible
    STATUS     current
    DESCRIPTION
    "An entry in the EtherType ACL Rule Table.
    
     Valid from:                EDA 2.2 SP2
    "
    INDEX {etherTypeAclId, etherTypeAclRuleIndex }
    ::= { etherTypeAclRuleTable 5 }

EtherTypeAclRuleEntry ::=
        SEQUENCE {
     etherTypeAclRuleIndex            Unsigned32,
     etherTypeAclMatchAction          INTEGER,
     etherTypeAclEtherType            INTEGER,
     etherTypeAclRuleRowStatus        RowStatus
    	          }
etherTypeAclRuleIndex OBJECT-TYPE
    SYNTAX        Unsigned32(1..64)
    MAX-ACCESS    read-only
    STATUS        current
    DESCRIPTION
    "The Access Control List may have multiple rules.
     The ipAclRuleIndex specifies the position of the particular 
     rule in the ACL.
     
     Valid from:                EDA 2.2 SP2
     "
    ::= { etherTypeAclRuleEntry 1 }

etherTypeAclMatchAction OBJECT-TYPE
    SYNTAX	  INTEGER { deny(0), permit(1)}
    MAX-ACCESS   read-create
    STATUS       current
    DESCRIPTION
    "Indicates the action to be taken when packet meets the filtering 
     condition in an ACL Rule.
   
     permit: Every packet that matches rule condition is forwarded 
     for further processing.
     deny: Every packet that matches rule condition is discarded.

     The value cannot be changed while the Rule is Active.
     
     Valid from:                EDA 2.2 SP2
    "
     
    DEFVAL { permit }
    ::= { etherTypeAclRuleEntry 5 }

etherTypeAclEtherType OBJECT-TYPE
    SYNTAX	  INTEGER ('0000'H..'FFFF'H)
    MAX-ACCESS   read-create
    STATUS       current
    DESCRIPTION
    "This number indicates the Ethernet type to match to have a match
     on the rule. Zero means any Ethernet type will match the rule.

     A list of standardized Ethernet type numbers is maintained by
     IANA (Internet Assigned Numbers Authority).
    
     Valid from:                EDA 2.2 SP2
    "
     
    DEFVAL {'0000'H}
    ::= { etherTypeAclRuleEntry 10 }


etherTypeAclRuleRowStatus OBJECT-TYPE
    SYNTAX      RowStatus
    MAX-ACCESS  read-create
    STATUS      current
    DESCRIPTION
    "This object is used to manage creation, deletion and modification of rows
     in the Access Control List Rule Table.

     Due to the way SNMP is handled in the IPDSLAM and the configuration file
     verification, RowStatus is handled slightly different in the IPDSLAM
     compared to the way described in RFC 2579.

     Below is a state/event table describing how the RowStatus will be handled
     in the IPDSLAM. The action to take and the return value assumes that the
     index to the table is valid.

    +-------------+---------------+---------------+---------------+---------------+
    | Command     |       A       |      B        |      C        |      D	      | 
    |             | status column | status column | status column | status column |
    |             |does not exist |   notReady    | notInService  | is active     |
    +-------------+---------------+---------------+---------------+---------------+
    | Set status  |  Inconsistent |               |  Inconsistent |  Inconsistent |
    | column      |  Value        |               |  Value        |  Value	      |
    | to          |  (1)          |    (10)       |  (1)          |  (1)          |
    | CreateAndGo |  State = A    |               |  State = C    |  State = D    |
    +-------------+---------------+---------------+---------------+---------------+
    | Set status  |  NoError      |               |  NoError      |  NoError      |
    | column to   |  (2)          |    (10)       |  (2)          |  (2)(3)       |
    |CreateAndWait|  State = C    |               |  State = C    |  State = C    |   
    +-------------+---------------+---------------+---------------+---------------+
	| Set status  | Inconsistent  |               |  NoError      |  NoError      |
    | to          | Value         |               |               |               |    
    |             | (4)           |    (10)       |  (5)          |               |
    | Active      | State = A     |               |   State = D   | State = D     |
    +-------------+---------------+---------------+---------------+---------------+
    | Set status  | Inconsistent  |               |  NoError      | NoError       |
    | column      | Value         |               |               |               | 
    | to          | (4)           |    (10)       |               |  (6)          |
    | NotInService| State = A     |               |  State = C    | State = C     |
    +-------------+---------------+---------------+---------------+---------------+
    | Set status  | Inconsistent  | Inconsistent  | Inconsistent  | Inconsistent  |
    | column      | Value         | Value         | Value         | Value         |
    | to          |               |               |               |               |
    | NotReady    | State = A     | State = B     | State = C     | state = D     |
    +-------------+---------------+---------------+---------------+---------------+
    | Set status  | NoError       |               | NoError       | NoError       |
    | column      |               |               |               |               |
    | to          |               |    (10)       |  (7)          |  (7)          |
    | Destroy     | State = A     |               | State = A     | State = A     |
    +-------------+---------------+---------------+---------------+---------------+
    |Set any other| Inconsistent  |               | NoError       | Inconsistent  |
    |column to    | Name          |    (10)       |               | Value         |
    |some value   | (4)           |               |               |  (8)          |
    |             | State = A     |               | State = C     | State = D     |
    +-------------+---------------+---------------+---------------+---------------+
    | Get         | NoSuchInstance|               | NoError       |  NoError      |
    | any column  | (4)           |    (10)       | (9)           |  (9)          |
    | value       | State = A     |               | State = C     |  State = D    |
    +-------------+---------------+---------------+---------------+---------------+

    (1) CreateAndGo is not supported in the IPDSLAM because the application receiving
        the command does not receive all parameters for the conceptual row in the table
        simultaneously but as a series of commands.

    (2) Temporary instance of the conceptual row is created for the management and
        placed in state NotInService. 

    (3)	If an instance of the conceptual row exists in runtime,
        it is copied to the temporary instance.

    (4)	The instance of the conceptual row does not exists in management and runtime.

    (5)	Data from the temporary  instance of the conceptual row is copied to the runtime
        instance and the conceptual row is set to state Active.
        The temporary instance is deleted.

    (6)	Temporary instance of the conceptual row is created in the management and
        placed in state NotInService. Data from the runtime instance of the conceptual row
        is copied to the temporary instance and the runtime instance is deleted. 

    (7)	The conceptual row may exist is two instances, a temporary management instance and
        a runtime instance. Both instances are deleted. 

    (8)	The ACL rule cannot be edited when conceptual row is Active.

    (9)	If a temporary management instance of the row exists, then the read operation returns
        the variable value from that instance, otherwise the returned value is taken from the
        runtime instance.

    (10) The conceptual row can never exist in state notReady.
    
    Valid from:                EDA 2.2 SP2
    "

    ::= { etherTypeAclRuleEntry 999 }

ipAclTable OBJECT-TYPE
    SYNTAX   SEQUENCE OF IpAclEntry
    MAX-ACCESS not-accessible
    STATUS     current
    DESCRIPTION
    "This table maintains a list of IP Access Control Lists in the IPDSLAM.        
     Each Access Control List is made up of a group of access rules. The 
     access rules are stored in the ipAclRuleTable. This table is used
     to add/delete IP Access Control Lists.

     ACL's are statements which are called rules of ACL that are grouped
     together by a number. Within this group of statements, when a packet
     is processed by an ACL on the IPDSLAM, the IPDSLAM will go through
     certain steps in finding a match against the ACL statements. ACL's are
     processed top-down by the IPDSLAM. Using a top-down approach, a packet
     is compared to the first statement in the ACL, and if the IPDSLAM finds
     a match between the packet and the statement, the IPDSLAM will execute
     one of two actions included with the statement:

     - Permit
     - Deny

     If the IPDSLAM doesn't find a match of packet contents to the first
     ACL statement, the IPDSLAM will proceed to the next statement in the list,
     again going through the same matching process If there isn't a match on
     this statement, the IPDSLAM will keep on going through the list until it
     finds a match. If the IPDSLAM goes through the entire list and doesn't
     find a match, the IPDSLAM will drop the packet.

     If there is a match on a statement, no further statements are processed.
     Therefore, the order of the statements is very important in an ACL.

     Valid from:                EDA 2.2 SP2
     "
     
     ::= { accessControlList 30 }

ipAclEntry OBJECT-TYPE
    SYNTAX     IpAclEntry
    MAX-ACCESS not-accessible
    STATUS     current
    DESCRIPTION
    "An entry in the ipAclTable.
    
     Valid from:                EDA 2.2 SP2
    "
    INDEX {ipAclId}
    ::= { ipAclTable 5 }

IpAclEntry ::=
        SEQUENCE {
	             ipAclId             Unsigned32,
	             ipAclNumberOfRules  Unsigned32,
	             ipAclRowStatus      RowStatus	
    	          }

ipAclId OBJECT-TYPE
    SYNTAX       Unsigned32 (1.. 4294967295)
    MAX-ACCESS   read-only
    STATUS       current
    DESCRIPTION
    "Index of the IP Access Control List.
   
     Valid from:                EDA 2.2 SP2
    "
   ::= { ipAclEntry 1 }

ipAclNumberOfRules OBJECT-TYPE
   SYNTAX       Unsigned32
   MAX-ACCESS   read-only
   STATUS       current
   DESCRIPTION
   "Total number of rules in the IP Access Control List (ACL).
   
    Valid from:                EDA 2.2 SP2
   "             
   ::= { ipAclEntry 5 }

ipAclRowStatus OBJECT-TYPE
   SYNTAX       RowStatus
   MAX-ACCESS   read-create
   STATUS       current
   DESCRIPTION
   "This object is used to manage the creation, deletion and modification
    of rows in the IP Access Control List Table. 

    Due to the way SNMP is handled in the IPDSLAM and the configuration
    file verification, RowStatus is handled slightly different in the
    IPDSLAM compared to the way described in RFC 2579.

    Below is a state/event table describing how the RowStatus will be handled
    in the IPDSLAM. The action to take and the return value assumes that the
    index to the table is valid.
    
    +-------------+---------------+---------------+---------------+---------------+
    | Command     |       A       |      B        |      C        |      D	      | 
    |             | status column | status column | status column | status column |
    |             |does not exist |   notReady    | notInService  | is active     |
    +-------------+---------------+---------------+---------------+---------------+
    | Set status  |  Inconsistent |               |  Inconsistent |  Inconsistent |
    | column      |  Value        |               |  Value        |  Value	      |
    | to          |  (1)          |    (9)        |  (1)          |  (1)          |
    | CreateAndGo |  State = A    |               |  State = C    |  State = D    |
    +-------------+---------------+---------------+---------------+---------------+
    | Set status  |  NoError      |               |  NoError      |  NoError      |
    | column to   |  (2)          |    (9)        |  (2)          |  (2)(3)       |
    |CreateAndWait|  State = C    |               |  State = C    |  State = C    |   
    +-------------+---------------+---------------+---------------+---------------+
	| Set status  | Inconsistent  |               |  NoError      |  NoError      |
    | to          | Value         |               |               |               |    
    |             | (4)           |    (9)        |  (5)          |               |
    | Active      | State = A     |               |   State = D   | State = D     |
    +-------------+---------------+---------------+---------------+---------------+
    | Set status  | Inconsistent  |               |  NoError      | NoError       |
    | column Value|               |               |               |               | 
    | to          | (4)           |    (9)        |               |  (6)          |
    | NotInService| State = A     |               |  State = C    | State = C     |
    +-------------+---------------+---------------+---------------+---------------+
    | Set status  | Inconsistent  | Inconsistent  | Inconsistent  | Inconsistent  |
    | column      | Value         | Value         | Value         | Value         |
    | to          |               |               |               |               |
    | NotReady    | State = A     | State = B     | State = C     | state = D     |
    +-------------+---------------+---------------+---------------+---------------+
    | Set status  | NoError       |               | NoError       | NoError       |
    | column      |               |               |               |               |
    | to          |               |    (9)        |  (7)          |  (7)          |
    | Destroy     | State = A     |               | State = A     | State = A     |
    +-------------+---------------+---------------+---------------+---------------+
    | Get         | NoSuchInstance|               | NoError       |  NoError      |
    | any column  | (4)           |    (9)        | (8)           |  (8)          |
    | value       | State = A     |               | State = C     |  State = D    |
    +-------------+---------------+---------------+---------------+---------------+
    
    (1)	CreateAndGo is not supported in the IPDSLAM because the application
        receiving the command does not receive all parameters for the conceptual row
        in the table simultaneously but as a series of commands.

    (2)	Temporary instance of the conceptual row is created for the Management,
        and placed in state NotInService.
        
    (3)	If an instance of the conceptual row exists in Runtime, then copy it to the
        temporary instance.

    (4)	The instance of the conceptual row does not exist in the Management and Runtime. 

    (5)	Data from the temporary  instance of the conceptual row is copied to
        the runtime instance and  the conceptual row is set to state Active.
        The temporary instance is deleted.

    (6)	Temporary instance of the conceptual row is created for the Management,
        and placed in state NotInService. Data from the runtime instance of the conceptual
        row is copied to the temporary instance and the runtime instance is deleted. 


    (7)	The conceptual row may exist is two instances,
        a temporary management instance and a  runtime instance. 
   
        - Loop through all the connections and find for which connections ACL is being used
        - If the ACL is not used for any connection, then delete ACL
          (the management and runtime instance), otherwise return SnmpError.

    (8)	If a temporary management instance of the row exists,
        then the read operation returns the variable value from that instance,
        otherwise the returned value is taken from the runtime instance.

    (9)	The conceptual row will never exist in notReady state
    

    Valid from:                EDA 2.2 SP2
    "
    ::= { ipAclEntry 999 }
    
ipAclRuleTable OBJECT-TYPE
    SYNTAX   SEQUENCE OF IpAclRuleEntry
    MAX-ACCESS not-accessible
    STATUS   current
    DESCRIPTION
    "This table is used to add/delete individual access rule 
     statement in an IP Access Control List. The order of the rules 
     is very important. The rules are processed in a top down order. 
     Once a match is found, no further rules are processed. If no 
     match is found, the packet is dropped.
     
     Valid from:                EDA 2.2 SP2
     "
    ::= { accessControlList 35 }

ipAclRuleEntry OBJECT-TYPE
    SYNTAX     IpAclRuleEntry
    MAX-ACCESS not-accessible
    STATUS     current
    DESCRIPTION
    "An entry in the IP ACL Rule Table.
    
     Valid from:                EDA 2.2 SP2
    "
    INDEX {ipAclId, ipAclRuleIndex }
    ::= { ipAclRuleTable 5 }

IpAclRuleEntry ::=
        SEQUENCE {
     ipAclRuleIndex            Unsigned32,
     ipAclMatchAction          INTEGER,
     ipAclIpProtocol           INTEGER,
     ipAclIpAddrType           InetAddressType,
     ipAclSrcIpAddrMin         InetAddress,
     ipAclSrcIpAddrMax         InetAddress,
     ipAclDestIpAddrMin        InetAddress,
     ipAclDestIpAddrMax        InetAddress,
     ipAclSrcPortOp            INTEGER,
     ipAclSrcPort              InetPortNumber,
     ipAclSrcPortRange         InetPortNumber,
     ipAclDestPortOp           INTEGER,
     ipAclDestPort             InetPortNumber,
     ipAclDestPortRange        InetPortNumber,
     ipAclTcpFlags             Unsigned32,
     ipAclTcpFlagsMask         Unsigned32,
     ipAclTcpFlagsMatchMethod  INTEGER,
     ipAclIcmpType             INTEGER,
     ipAclIcmpCode             INTEGER,
     ipAclIgmpType             INTEGER,
     ipAclRuleRowStatus        RowStatus
    	          }
ipAclRuleIndex OBJECT-TYPE
    SYNTAX        Unsigned32(1..64)
    MAX-ACCESS    read-only
    STATUS        current
    DESCRIPTION
    "The Access Control List may have multiple rules.
     The ipAclRuleIndex specifies the position of the particular 
     rule in the ACL.
     
     Valid from:                EDA 2.2 SP2
     "
    ::= { ipAclRuleEntry 1 }

ipAclMatchAction OBJECT-TYPE
    SYNTAX	  INTEGER { deny(0), permit(1)}
    MAX-ACCESS   read-create
    STATUS       current
    DESCRIPTION
    "Indicates the action to be taken when packet meets the filtering 
     condition in an ACL Rule.
   
     permit: Every packet that matches rule condition is forwarded 
     for further processing.
     deny: Every packet that matches rule condition is discarded.

     The value cannot be changed while the Rule is Active.
     
     Valid from:                EDA 2.2 SP2
     "
     
    DEFVAL { permit }
    ::= { ipAclRuleEntry 5 }
    
ipAclIpProtocol OBJECT-TYPE
    SYNTAX	   INTEGER(-1..255)
    MAX-ACCESS   read-create
    STATUS       current
    DESCRIPTION
    "ipAclIpProtocol identifies the layer above IP to which the IP packet data
     should be passed. The numbers associated with some important transport
     protocols are 1(icmp),2(igmp),6(tcp),17(udp).

     The value cannot be changed while the Rule is Active.
     
     The default value of -1 is used to match on any IP protocol.
     
     Valid from:                EDA 2.2 SP2
     "
     
    DEFVAL {-1}
    ::= { ipAclRuleEntry 24 }

ipAclIpAddrType OBJECT-TYPE
    SYNTAX	     InetAddressType
    MAX-ACCESS   read-create
    STATUS       current
    DESCRIPTION
    "The type of Internet address used in the ACL Rule. 

     The ipAclIpAddrType will determine the value of ipAclSrcIpAddrMin, 
     ipAclSrcIpAddrMax, ipAclDestIpAddrMin and ipAclDestIpAddrMax.

     The value cannot be changed while the Rule is Active.

     Currently the IPDSLAM only supports Ipv4.
     
     Valid from:                EDA 2.2 SP2
     "
    
    DEFVAL { ipv4 } 
    ::= { ipAclRuleEntry 29 }
    
   
ipAclSrcIpAddrMin OBJECT-TYPE
    SYNTAX        InetAddress
    MAX-ACCESS    read-create
    STATUS        current
    DESCRIPTION
    "ipAclSrcIpAddrMin is a 32-bit IP address (0.0.0.0 through 255.255.255.255),
     which defines the first element of the intended IP source address range. 
     ipAclSrcIpAddrMin and ipAclSrcIpAddrMax together indicate a range of IP addresses
     of hosts. IP packets from hosts in that range will be filtered, depending 
     on the value of the action field.

     The value cannot be changed while the Rule is Active.

     The default value is 0.0.0.0 .
     
     Valid from:                EDA 2.2 SP2
     "
         
    DEFVAL {'00000000'h}
    ::= { ipAclRuleEntry 30 }


ipAclSrcIpAddrMax OBJECT-TYPE
    SYNTAX       InetAddress
    MAX-ACCESS   read-create
    STATUS       current
    DESCRIPTION
    "ipAclSrcIpAddrMax is a 32-bit IP address (0.0.0.0 through 255.255.255.255),
     which defines the last element of the intended IP source address range. 
     ipAclSrcIpAddrMin and ipAclSrcIpAddrMax together indicate a range of IP addresses
     of hosts. IP packets from hosts in that range will be filtered, depending 
     on the value of the action field.

     The value cannot be changed while the Rule is Active.

     The default value is 255.255.255.255.
     
     Valid from:                EDA 2.2 SP2
     "
          
    DEFVAL {'FFFFFFFF'h}
    ::= { ipAclRuleEntry 31 }

ipAclDestIpAddrMin OBJECT-TYPE
    SYNTAX       InetAddress
    MAX-ACCESS   read-create
    STATUS       current
    DESCRIPTION
    "ipAclDestIpAddrMin is a 32-bit IP address (0.0.0.0 through 255.255.255.255),
     which defines the first element of the intended IP destination address 
     range. 
     ipAclDestIpAddrMin and ipAclDestIpAddrMax together indicate a range of IP 
     addresses of hosts. IP packets to hosts in that range will be filtered, 
     depending on the value of the action field.

     The value cannot be changed while the Rule is Active.

     The default value is 0.0.0.0.
     
     Valid from:                EDA 2.2 SP2
     "

     DEFVAL {'00000000'h}
     ::= { ipAclRuleEntry 36 }

ipAclDestIpAddrMax  OBJECT-TYPE
      SYNTAX       InetAddress
      MAX-ACCESS   read-create
      STATUS       current
      DESCRIPTION
      "ipAclDestIpAddrMax is a 32-bit IP address (0.0.0.0 through 255.255.255.255),
       which defines the last element of the intended IP destination address 
       range. 
       ipAclDestIpAddrMin and ipAclDestIpAddrMax together indicate a range of IP 
       addresses of hosts. IP packets to hosts in that range will be filtered, 
       depending on the value of the action field.

       The value cannot be changed while the Rule is Active.
       
       The default value is 255.255.255.255.
       
       Valid from:                EDA 2.2 SP2
       "

      DEFVAL {'FFFFFFFF'h}
      ::= { ipAclRuleEntry 37 }

ipAclSrcPortOp  OBJECT-TYPE
    SYNTAX INTEGER {
         noOperator(1),
         lt(2),
         gt(3),
         eq(4),
         neq(5),
         range(6)
         }
    MAX-ACCESS  read-create
    STATUS      current
    DESCRIPTION
    "Indicates how a packet's source TCP/UDP port number is	to be compared.

     noOperator(1) which is the default value, means that no comparison is
     to be made with the source TCP/UDP port number.

     lt(2) means less than, gt(3) means greater than, eq(4) means equal,
     neq(5) means not equal. These 4 operators will use srcPort object
     as an operand which is the only one needed. 

     range(6) means that it compares the port value between two numbers, so this
     operator needs 2 operands. One operand is the starting port number of the
     range which is srcPort object, and the other operand is the ending port
     number of the range which is srcPortRange object.

     The value cannot be changed while the Rule is Active.
     
     Valid from:                EDA 2.2 SP2
     "
     
    DEFVAL { noOperator }
    ::= { ipAclRuleEntry 42 }

ipAclSrcPort  OBJECT-TYPE
    SYNTAX        InetPortNumber
    MAX-ACCESS    read-create
    STATUS        current
    DESCRIPTION
    "The source port number of the TCP or UDP protocol. If the ipAclSrcPortOp is
     set to range(6), this object will be the starting port number of the
     port range.

     The value cannot be changed while the Rule is Active.
     
     The default value for ipAclSrcPort is 0.
     
     Valid from:                EDA 2.2 SP2
     "

    DEFVAL {0}
    ::= { ipAclRuleEntry 43 }

ipAclSrcPortRange OBJECT-TYPE
    SYNTAX        InetPortNumber
    MAX-ACCESS    read-create
    STATUS        current
    DESCRIPTION
    "The source port number of the TCP or UDP protocol. If the ipAclSrcPortOp is
     set to range(6), this object will be the ending port number of the
     port range. 

     The value cannot be changed while the Rule is Active.
     
     The default value for ipAclSrcPortRange is 65535.
     
     Valid from:                EDA 2.2 SP2
     "
     
    DEFVAL {65535}
    ::= { ipAclRuleEntry 44 }

ipAclDestPortOp  OBJECT-TYPE
    SYNTAX INTEGER {
         noOperator(1),
         lt(2),
         gt(3),
         eq(4),
         neq(5),
         range(6)
         }
    MAX-ACCESS  read-create
    STATUS      current
    DESCRIPTION
    "Indicates how a packet's destination TCP/UDP port number is to be compared.

     noOperator(1) which is the default value, means that no comparison is
     to be made with the destination TCP/UDP port number.

     lt(2) means less than, gt(3) means greater than, eq(4) means equal,
     neq(5) means not equal. These 4 operators will use the destPort object
     as an operand which is the only one needed. 

     range(6) means that it compares the port value between two numbers, so this
     operator needs 2 operands. One operand is the starting port number of the
     range which is destPort object, and the other operand is the ending port
     number of the range which is destPortRange object.

     The value cannot be changed while the Rule is Active.
     
     Valid from:                EDA 2.2 SP2
     "
     
    DEFVAL { noOperator }
    ::= { ipAclRuleEntry 49 }
   
ipAclDestPort  OBJECT-TYPE
    SYNTAX       InetPortNumber
    MAX-ACCESS   read-create
    STATUS       current
    DESCRIPTION
    "The destination port number of the TCP or UDP protocol. If the ipAclDestPortOp
     is set to range(6), this object will be the starting port number of the
     port range.

     The value cannot be changed while the Rule is Active.
     
     The default value for ipAclDestPort is 0.
     
     Valid from:                EDA 2.2 SP2
     "

    DEFVAL {0}
    ::= { ipAclRuleEntry 50 }

ipAclDestPortRange  OBJECT-TYPE
    SYNTAX         InetPortNumber
    MAX-ACCESS     read-create
    STATUS         current
    DESCRIPTION
    "The destination port number of the TCP or UDP protocol. If the ipAclDestPortOp
     is set to range(6), this object will be the ending port number of the
     port range.

     The value cannot be changed while the Rule is Active.
     
     The default value for ipAclDestPortRange is 65535.
     
     Valid from:                EDA 2.2 SP2
     " 

    DEFVAL {65535}
    ::= { ipAclRuleEntry 51 }

ipAclTcpFlags OBJECT-TYPE
    SYNTAX       Unsigned32(0..255)
    MAX-ACCESS   read-create
    STATUS       current
    DESCRIPTION
    "Value of the TCP Control code/flags. The parameter specifies if a flag 
     must be set or cleared to have a match.

        ----------------------------------
        |MSB|   |   |   |   |   |   | LSB |
        | x | x | U | A | P | R | S |  F  |
        ----------------------------------

        The various bit positions are:
        1 - F,FIN End of data flag.
        2 - S,SYN Synchronize sequence numbers flag.
        3 - R,RST Reset connection flag.
        4 - P,PSH Push flag.
        5 - A,ACK Acknowledgment number valid flag.
        6 - U,URG Urgent pointer valid flag.

    For Example: To test on SYN flag set and ACK flag cleared, value should be
                 xxx1xx0x where x is don't care and can be set to either 0 or 1.
                 ipAclTcpFlagsMask specified for which of the flags the test is                
                 carried out.
            
    The ipAclTcpFlags is used in combination with ipAclTcpFlagsMask and 
    ipAclTcpFlagsMatchMethod.

    The value cannot be changed while the Rule is Active.
    
    Valid from:                EDA 2.2 SP2
    "

   DEFVAL {0}
   ::= { ipAclRuleEntry 56}

ipAclTcpFlagsMask OBJECT-TYPE
    SYNTAX       Unsigned32(0..255)
    MAX-ACCESS   read-create
    STATUS       current
    DESCRIPTION
    "Value of the TCP Control code/flags mask. The ipAclTcpFlagsMask specifies   
     which of the TCP Control flags specified in tcpFlags to match.

        ----------------------------------
        |MSB|   |   |   |   |   |   | LSB |
        | 0 | 0 | U | A | P | R | S |  F  |
        ----------------------------------

        The various bit positions are:
        1 - F,FIN End of data flag.
        2 - S,SYN Synchronize sequence numbers flag.
        3 - R,RST Reset connection flag.
        4 - P,PSH Push flag.
        5 - A,ACK Acknowledgment number valid flag.
        6 - U,URG Urgent pointer valid flag.

    For Example: To match on SYN and ACK flag, value should be 00010010, then 
                 the test will only be performed for SYN and ACK. Whether the 
                 flags must be set or cleared to have a match is specified in 
                 ipAclTcpFlags.

    The ipAclTcpFlagsMask is used in combination with ipAclTcpFlags and   
    ipAclTcpFlagsMatchMethod.

    The value cannot be changed while the Rule is Active.
    
    Valid from:                EDA 2.2 SP2
    "

   DEFVAL {0}
   ::= { ipAclRuleEntry 57}

ipAclTcpFlagsMatchMethod  OBJECT-TYPE
    SYNTAX       INTEGER { matchAny(0), matchAll(1) }
    MAX-ACCESS   read-create
    STATUS       current
    DESCRIPTION
    "The ipAclTcpFlagsMatchMethod specified whether all (matchAll) or just one or 
     more (matchAny) TCP flags must be correct to have a match in the TCP flags 
     part of the rule.

     The ipAclTcpFlagsMatchMethod is used in combination with ipAclTcpFlags and 
     ipAclTcpFlagsMask.

     The value cannot be changed while the Rule is Active.
     
     Valid from:                EDA 2.2 SP2
     "
     
    DEFVAL { matchAny }
    ::= { ipAclRuleEntry 58}


ipAclIcmpType OBJECT-TYPE
    SYNTAX       INTEGER(-1..255)
    MAX-ACCESS   read-create
    STATUS       current
    DESCRIPTION
    "Value of ICMP type. ICMP type defines the ICMP message that 
     is being passed. The default value of -1 for ipAclIcmpType is used
     to match on all the ICMP Types.

     The value cannot be changed while the Rule is Active.
     
     Valid from:                EDA 2.2 SP2
     "
     
    DEFVAL {-1}
    ::= { ipAclRuleEntry 63}

ipAclIcmpCode OBJECT-TYPE
    SYNTAX       INTEGER(-1..255)
    MAX-ACCESS   read-create
    STATUS       current
    DESCRIPTION
    "Value of ICMP code. In certain cases, an ICMP type may have
     several submessages. A submessage is called an ICMP code. 

     When an ICMP message requires only a type, the ICMP code will 
     be set to 0. The default value of -1 for ipAclIcmpCode is used to
     match on all ICMP Codes.

     The value cannot be changed while the Rule is Active.
     
     Valid from:                EDA 2.2 SP2
     "
     
    DEFVAL {-1}
    ::= { ipAclRuleEntry 64}

ipAclIgmpType OBJECT-TYPE
    SYNTAX       INTEGER(-1..255)
    MAX-ACCESS   read-create
    STATUS       current
    DESCRIPTION
    "Value of IGMP type. IGMP type defines the IGMP message that 
     is being passed.The default value of -1 for ipAclIgmpType is used
     to match on all the IGMP Types.

     The value cannot be changed while the Rule is Active.
     
     Valid from:                EDA 2.2 SP2
     "
     
    DEFVAL {-1}
    ::= { ipAclRuleEntry 69}

ipAclRuleRowStatus OBJECT-TYPE
    SYNTAX      RowStatus
    MAX-ACCESS  read-create
    STATUS      current
    DESCRIPTION
    "This object is used to manage creation, deletion and modification of rows
     in the Access Control List Rule Table.

    Due to the way SNMP is handled in the IPDSLAM and the configuration file
    verification, RowStatus is handled slightly different in the IPDSLAM
    compared to the way described in RFC 2579.

    Below is a state/event table describing how the RowStatus will be handled
    in the IPDSLAM. The action to take and the return value assumes that the
    index to the table is valid.

    +-------------+---------------+---------------+---------------+---------------+
    | Command     |       A       |      B        |      C        |      D	      | 
    |             | status column | status column | status column | status column |
    |             |does not exist |   notReady    | notInService  | is active     |
    +-------------+---------------+---------------+---------------+---------------+
    | Set status  |  Inconsistent |               |  Inconsistent |  Inconsistent |
    | column      |  Value        |               |  Value        |  Value	      |
    | to          |  (1)          |    (10)       |  (1)          |  (1)          |
    | CreateAndGo |  State = A    |               |  State = C    |  State = D    |
    +-------------+---------------+---------------+---------------+---------------+
    | Set status  |  NoError      |               |  NoError      |  NoError      |
    | column to   |  (2)          |    (10)       |  (2)          |  (2)(3)       |
    |CreateAndWait|  State = C    |               |  State = C    |  State = C    |   
    +-------------+---------------+---------------+---------------+---------------+
	| Set status  | Inconsistent  |               |  NoError      |  NoError      |
    | to          | Value         |               |               |               |    
    |             | (4)           |    (10)       |  (5)          |               |
    | Active      | State = A     |               |   State = D   | State = D     |
    +-------------+---------------+---------------+---------------+---------------+
    | Set status  | Inconsistent  |               |  NoError      | NoError       |
    | column      | Value         |               |               |               | 
    | to          | (4)           |    (10)       |               |  (6)          |
    | NotInService| State = A     |               |  State = C    | State = C     |
    +-------------+---------------+---------------+---------------+---------------+
    | Set status  | Inconsistent  | Inconsistent  | Inconsistent  | Inconsistent  |
    | column      | Value         | Value         | Value         | Value         |
    | to          |               |               |               |               |
    | NotReady    | State = A     | State = B     | State = C     | state = D     |
    +-------------+---------------+---------------+---------------+---------------+
    | Set status  | NoError       |               | NoError       | NoError       |
    | column      |               |               |               |               |
    | to          |               |    (10)       |  (7)          |  (7)          |
    | Destroy     | State = A     |               | State = A     | State = A     |
    +-------------+---------------+---------------+---------------+---------------+
    |Set any other| Inconsistent  |               | NoError       | Inconsistent  |
    |column to    | Name          |    (10)       |               | Value         |
    |some value   | (4)           |               |               |  (8)          |
    |             | State = A     |               | State = C     | State = D     |
    +-------------+---------------+---------------+---------------+---------------+
    | Get         | NoSuchInstance|               | NoError       |  NoError      |
    | any column  | (4)           |    (10)       | (9)           |  (9)          |
    | value       | State = A     |               | State = C     |  State = D    |
    +-------------+---------------+---------------+---------------+---------------+

    (1) CreateAndGo is not supported in the IPDSLAM because the application receiving
        the command does not receive all parameters for the conceptual row in the table
        simultaneously but as a series of commands.

    (2) Temporary instance of the conceptual row is created for the management and
        placed in state NotInService. 

    (3)	If an instance of the conceptual row exists in runtime,
        it is copied to the temporary instance.

    (4)	The instance of the conceptual row does not exists in management and runtime.

    (5)	Data from the temporary  instance of the conceptual row is copied to the runtime
        instance and the conceptual row is set to state Active.
        The temporary instance is deleted.

    (6)	Temporary instance of the conceptual row is created in the management and
        placed in state NotInService. Data from the runtime instance of the conceptual row
        is copied to the temporary instance and the runtime instance is deleted. 

    (7)	The conceptual row may exist is two instances, a temporary management instance and
        a runtime instance. Both instances are deleted. 

    (8)	The ACL rule cannot be edited when conceptual row is Active.

    (9)	If a temporary management instance of the row exists, then the read operation returns
        the variable value from that instance, otherwise the returned value is taken from the
        runtime instance.

    (10) The conceptual row can never exist in state notReady.
    
    Valid from:                EDA 2.2 SP2
    "
    
    ::= { ipAclRuleEntry 999 }

subsIpFilter    OBJECT IDENTIFIER 
    ::= { bridgeControl 22 }

subsIpFilterTypeTable OBJECT-TYPE    
	SYNTAX      SEQUENCE OF SubsIpFilterTypeEntry
  	MAX-ACCESS  not-accessible
    STATUS      current
    DESCRIPTION
    "A list of entries to the subscriber IP filter type list."
    ::= { subsIpFilter 1 }

subsIpFilterTypeEntry OBJECT-TYPE
	SYNTAX      SubsIpFilterTypeEntry
    MAX-ACCESS  not-accessible
    STATUS      current
    DESCRIPTION
    "The lineIndex and pvcIndex pair forms a unique
     identification of a PVC in the managed device. A 
     subsIpFilterTypeEntry contains subscriber IP filter 
     type information for a PVC."
    INDEX  {lineIndex,
            pvcIndex}
    ::= { subsIpFilterTypeTable 1 }         
    
SubsIpFilterTypeEntry ::= 
	SEQUENCE {
        subsIpFilterType      INTEGER
        }

subsIpFilterType OBJECT-TYPE
    SYNTAX      INTEGER { positive(0), disabled (2) }
    MAX-ACCESS  read-write
    STATUS      current
    DESCRIPTION
    "Specifies whether the subscriber IP filter is positive
     or disabled. If the filter is positive, the managed device
     is allowed to forward traffic from/to subscribers
     if their IP address is specified in the subsIpFilterTable.
     If the subscriber IP filter is disabled, the managed device
     will make no filtering on subscriber IP.
     Whether the subscriber IP filter is positive or disabled is
     specified per PVC.

     Valid from:                EDA 2.2 R3A
    "
    DEFVAL {0}
    ::= { subsIpFilterTypeEntry 5 }
    
subsIpFilterTable OBJECT-TYPE
	SYNTAX      SEQUENCE OF SubsIpFilterEntry
  	MAX-ACCESS  not-accessible
    STATUS      current
    DESCRIPTION
    "A list of entries to the subscriber IP filter list."
    ::= { subsIpFilter 2 }

subsIpFilterEntry OBJECT-TYPE
	SYNTAX      SubsIpFilterEntry
    MAX-ACCESS  not-accessible
    STATUS      current
    DESCRIPTION
    "The lineIndex and pvcIndex pair forms a unique
     identification of a PVC in the managed device. A 
     subsIpFilterEntry contains subscriber IP filter
     information for a PVC. Each entry describes a range of
     consecutive subscriber IP addresses which are allowed to
     forward traffic on the PVC.

     If the subscriber IP filter is empty, no traffic is allowed,
     
     F.ex. if subscriber Internet addresses in the range
     10.0.0.1 to 10.0.0.254 are allowed on the PVC, a positive (0)
     subscriber IP filter should be used, subsIpFilterFirstAddress
     is set to 10.0.0.1 and subsIpFilterLastAddress is set to
     10.0.0.254.
     
     Multiple entries may be required to describe the complete
     subscriber IP filter for one PVC.

     Valid from:                EDA 2.2 R3A
    "
    INDEX  {lineIndex,
            pvcIndex,
            subsIpFilterAddressType,
            subsIpFilterFirstAddress}
    ::= { subsIpFilterTable 1 }     
    
SubsIpFilterEntry ::= 
	SEQUENCE {
        subsIpFilterAddressType      InetAddressType,
        subsIpFilterFirstAddress     InetAddress,
        subsIpFilterLastAddress      InetAddress,
        subsIpFilterRowStatus        RowStatus
        }

subsIpFilterAddressType OBJECT-TYPE
    SYNTAX      InetAddressType
    MAX-ACCESS  read-only
    STATUS      current
    DESCRIPTION
    "The type of Internet address used in the subscriber IP
     filter address range.

     Valid from:                EDA 2.2 R3A
    "
    ::= { subsIpFilterEntry 5 }

subsIpFilterFirstAddress OBJECT-TYPE
    SYNTAX      InetAddress (SIZE (4..20))
    MAX-ACCESS  read-only
    STATUS      current
    DESCRIPTION
    "The first address in the subscriber Internet address
     range. The type of this address is determined by the
     value of the subsIpFilterAddressType object.
     The subsIpFilterFirstAddress may not be empty
     due to the SIZE restriction.

     Valid from:                EDA 2.2 R3A
    "
    ::= { subsIpFilterEntry 10 }
        
subsIpFilterLastAddress OBJECT-TYPE
    SYNTAX      InetAddress (SIZE (4..20))
    MAX-ACCESS  read-create
    STATUS      current
    DESCRIPTION
    "The last address in the subscriber Internet address
     range. The type of this address is determined by the
     value of the subsIpFilterAddressType object.
     subsIpFilterLastAddress must be a equal to or
     higher than subsIpFilterFirstAddress before the
     settings are put into operation.
     The subsIpFilterLastAddress may not be empty
     due to the SIZE restriction.
     To modify the value of subsIpFilterLastAddress,
     the conceptual row must be taken Out of Service

     Valid from:                EDA 2.2 R3A
    "
    ::= { subsIpFilterEntry 15 }
    
subsIpFilterRowStatus OBJECT-TYPE
    SYNTAX      RowStatus
    MAX-ACCESS  read-create
    STATUS      current
    DESCRIPTION
    "The subsIpFilterRowStatus is used to manage the 
     creation and deletion of rows in subsIpFilterTable.

     Valid from:                EDA 2.2 R3A
    " 
    ::= { subsIpFilterEntry 99 }    
    
priorityIndex    OBJECT-TYPE
    SYNTAX      Unsigned32(1..8)
    MAX-ACCESS  not-accessible
    STATUS      current
    DESCRIPTION
    "priorityIndex is used to access a number of tables regarding Weighted Random Early
     Discard (WRED). Those tables are indexed per line, PVC and VLAN priority index.

     The relation between priorityIndex and VLAN priority is: priorityIndex = VLAN priority + 1.
     
     Valid from:                EDA 2.2 R3A
     "
    ::= { bridgeControl 24 }

downstreamFlowWredConfigTable OBJECT-TYPE
	  SYNTAX      SEQUENCE OF DownstreamFlowWredConfigEntry
  	MAX-ACCESS  not-accessible
    STATUS      current
    DESCRIPTION
    "The IP-DSLAM flow implementation allows multiple VLAN priorities to be mapped to the same
     downstream flow queue (downstream flows are configured with downstreamFlowConfigTable).
     
     Parameters in the downstreamFlowWredConfigTable are used to configure the discard probability
     of packets with different VLAN priority in the same downstream flow. The mechanisms Weighted
     Random Early Discard (WRED) is implemented to allow configuration of discard probability of
     packet with different VLAN priority. The WRED mechanism works as an extention to the other
     flow mechanisms in the IP-DSLAM.

                                                    IP DSLAM
                       __________________________________________________________________
                      |                        ______                                    |
                      |                       (      )    ___  _ _ _ _                   |
                      |                  /--->( WRED )--->___Q3_|_|_|_|-->\              |
                      |                 /     (______)                     \             |
                      |                /       ______                       \            |
                      |               /       (      )    ___  _ _ _ _       \           |
                      |   ___________/___/--->( WRED )--->___Q2_|_|_|_|-->\___\_______   |
     Aggregation      |  ( VLAN priority )    (______)                    (           )  |
       Network   ---->|->(    to flow    )     ______                     ( Scheduler )->|--> End-user
                      |  (____mapping____)    (      )    ___  _ _ _ _    (___________)  |
                      |              \   \--->( WRED )--->___Q1_|_|_|_|-->/   /          |
                      |               \       (______)                       /           |
                      |                \       ______                       /            |
                      |                 \     (      )    ___  _ _ _ _     /             |
                      |                  \--->( WRED )--->___Q0_|_|_|_|-->/              |
                      |                       (______)                                   |
                      |                                                                  |
                      | WRED = Weighted Random Early Discard                             |
                      |__________________________________________________________________|
     
     The figure above illustrates where in the flow handling process the WRED is performed.
     
     Weighted Random Early Discard (WRED) is needed to ensure that high priority packets are
     favored over low priority packets when the downstream flow queue buffer usage gets close to
     the maximum buffer limit. Maximum buffer limit is configured with dfcMaxQueueBuffers.
     
     A flow has one downstream flow queue associated. All packets for this flow will be stored in
     the downstream flow queue, disregarding the packets VLAN priority, until they in turn are
     forwarded to the PVC in the subscriber line. The parameters wredBufferLimit and
     wredDropProbability are used to configure the WRED mechanism.

     dfcMaxQueueBuffers
             |
             V____________________________________________________________________________________
             | | | | | | | | | | | | | | | |                                | | | | | | | | | | | |
             | | | | | | | | | | | | | | | |     Downstream flow queue      | | | | | | | | | | | |
             |_|_|_|_|_|_|_|_|_|_|_|_|_|_|_|________________________________|_|_|_|_|_|_|_|_|_|_|_|
             ^                       ^                                               V
             |                       |                                               |
     wredBufferLimit(x)      wredBufferLimit(y)                             dfcMaxQueueBuffers
          (100%)                   (70%)                                    in steps of 1 buffer
     
     In the figure above is illustrated that packets with VLAN priority X will not be discarded
     until all buffers in the downstream flow queue are in use while the WRED mechanism will start
     discarding packets with VLAN priority Y when 70% of the buffers in the downstream flow queue
     are in use.

     Valid from:                EDA 2.2 R3A
    "                                               
    ::= { bridgeControl 30 }

downstreamFlowWredConfigEntry OBJECT-TYPE
    SYNTAX     DownstreamFlowWredConfigEntry
    MAX-ACCESS not-accessible
    STATUS     current
    DESCRIPTION
    "This is an entry in the downstreamFlowWredConfigTable and contains the parameters to configure
     the WRED mechanism for one VLAN priority in the downstream flows for one end-user connection.
    
     Valid from:                EDA 2.2 R3A
    "
    INDEX {lineIndex, pvcIndex, priorityIndex }
    ::= { downstreamFlowWredConfigTable 5 }

DownstreamFlowWredConfigEntry ::=
    SEQUENCE { wredBufferLimit           Unsigned32,
               wredDropProbability       Unsigned32
             }
             
wredBufferLimit OBJECT-TYPE
    SYNTAX      Unsigned32(1..100)
    MAX-ACCESS  read-write
    STATUS      current
    DESCRIPTION
    "Weighted Random Early Discard (WRED) buffer limit specifies the queue usages limit for traffic
     with a specific VLAN priority. The drop limit is specified as a percentage of the total queue
     length (dfcMaxQueueBuffers) for the Flow. F.ex. if the flow queue can contain 100 packets and
     wredBufferLimit is set to 70%, then the IP-DSLAM WRED mechanism will start dropping packets
     with the specific VLAN priority when more than 70 buffers from the queue is in use.
     
     Valid from:                EDA 2.2 R3A
     "
    ::= { downstreamFlowWredConfigEntry 5 }

wredDropProbability OBJECT-TYPE
    SYNTAX      Unsigned32(1..100)
    MAX-ACCESS  read-write
    STATUS      current
    DESCRIPTION
    "wredDropProbability is used to specify the probability that a packet with a specific VLAN
     priority will be dropped if the wredBufferLimit has been exceeded. wredDropProbability is
     configured as a percentage of all packets received with the VLAN priority, e.g. if 80%
     drop probability has been specified, 4 out of 5 packets with this VLAN priority will be
     dropped when wredBufferLimit has been exceeded.
    
     If wredBufferLimit is set to 100% wredDropProbability has no effect.
     
     Valid from:                EDA 2.2 R3A
     "
    ::= { downstreamFlowWredConfigEntry 10 }

downstreamFlowWredStatisticsTable OBJECT-TYPE
	  SYNTAX      SEQUENCE OF DownstreamFlowWredStatisticsEntry
  	MAX-ACCESS  not-accessible
    STATUS      current
    DESCRIPTION
    "The downstreamFlowWredStatisticsTable contains statistics counters for the
     Weighted Random Early Discard (WRED) mechanism.

     Valid from:                EDA 2.2 R3A
    "
    ::= { bridgeControl 31 }

subscriberInfoTable OBJECT-TYPE
    SYNTAX   SEQUENCE OF SubscriberInfoEntry
    MAX-ACCESS not-accessible
    STATUS   current
    DESCRIPTION
    "This table contains a list of subscriber information that the IP-DSLAM has
     dynamically learned. From the list it is possible to get the relationship
     between subscriber MAC and IP addresses. 
     When running DHCP it is also possible to readout the IP-DSLAM equivalent of
     the LeaseTime. This is the time where the IP-DSLAM will remove the IP address
     and MAC address from the filters.
     The learned gateway IP and MAC can also be readout from the IP-DSLAM.
 
     The table is indexed by lineIndex, pvcIndex, subscriberInfoMac and subscriberInfoIp.

     Valid from:   EDA 2.2 R3A
     "
     
    ::= { bridgeControl 32 }

subscriberInfoEntry OBJECT-TYPE
    SYNTAX     SubscriberInfoEntry
    MAX-ACCESS not-accessible
    STATUS     current
    DESCRIPTION
    "An entry containing the subscriber information identified by lineIndex, 
 	 pvcIndex, subscriberInfoMac and subscriberInfoIp address.

     Valid from:   EDA 2.2 R3A
     "
    
    INDEX {lineIndex, pvcIndex, subscriberInfoMac, subscriberInfoIp}
    ::= { subscriberInfoTable 5 }

SubscriberInfoEntry ::=
        SEQUENCE {
     subscriberInfoMac                    MacAddress,
     subscriberInfoIp                     InetAddress,
     subscriberInfoVirtualMac             MacAddress,
     subscriberInfoDhcpLeaseTime          DateAndTime,
     subscriberInfoGatewayFixedForwarding TruthValue,
     subscriberInfoGatewayIp              InetAddress,
     subscriberInfoGatewayMac             MacAddress
     }

subscriberInfoMac OBJECT-TYPE
	SYNTAX      MacAddress
    MAX-ACCESS  read-only
    STATUS      current
    DESCRIPTION
    "The MAC address of the subscriber which is learned by the IP-DSLAM.

     Valid from:   EDA 2.2 R3A
     " 
    ::= { subscriberInfoEntry 5 }   

subscriberInfoIp OBJECT-TYPE
	SYNTAX      InetAddress (SIZE (4..20))
    MAX-ACCESS  read-only
    STATUS      current
    DESCRIPTION
    "For StaticIP, DHCP and DHCPIP over ATM access methods, relationship
     between MAC address of the subscriber and IP address of the subscriber
     is maintained in the IP-DSLAM. For these three access methods,
     subscriberInfoIp will contain the IP address of the subscriber.

     For other access methods, the subscriberInfoIp will contain 0.0.0.0 value.
     
     Valid from:   EDA 2.2 R3A
     " 
    ::= { subscriberInfoEntry 10 }

subscriberInfoVirtualMac OBJECT-TYPE
	SYNTAX      MacAddress
    MAX-ACCESS  read-only
    STATUS      current
    DESCRIPTION
    "subscriberInfoVirtualMac will contain the virtual MAC address of the
     subscriber generated by the IP-DSLAM only when
     - peaBridgeIpDslam::virtualMacEnable is set to true for the PVC and
     - peaBridgeIpDslam::accessMethod is other than Transparent LAN,
       StaticIP over ATM or PPP over ATM. 
      
     subscriberInfoVirtualMac will contain 00:00:00:00:00:00 value when
     - peaBridgeIpDslam::virtualMacEnable is set to false for the PVC or
     - peaBridgeIpDslam::accessMethod is Transparent LAN, StaticIP over ATM
       or PPP over ATM. 

     Valid from:   EDA 2.2 R3A
     " 
    ::= { subscriberInfoEntry 15 }
    
subscriberInfoDhcpLeaseTime OBJECT-TYPE
	SYNTAX      DateAndTime
    MAX-ACCESS  read-only
    STATUS      current
    DESCRIPTION
    "The IP address lease time for the subscriber when DHCP is used
     as access method. For other access methods the DateAndTime string
     will be read out as empty.

     The lease time read out from IP-DSLAM will be the GMT time.
     
     The DateAndTime format:
     field  octets  contents                  range
     -----  ------  --------                  -----
       1      1-2   year                      0..65536
       2       3    month                     1..12
       3       4    day                       1..31
       4       5    hour                      0..23
       5       6    minutes                   0..59
       6       7    seconds                   0..60
                    (use 60 for leap-second)
       7       8    deci-seconds              0..9
       8       9    direction from UTC        '+' / '-'
       9       10   hours from UTC            0..11
       10      11   minutes from UTC          0..59
       For example, Tuesday May 26, 1992 at 1:30:15 PM EDT would be
       displayed as:
             1992-5-26,13:30:15.0,-4:0

       Valid from:   EDA 2.2 R3A
       "
     ::= { subscriberInfoEntry 20 }   

subscriberInfoGatewayFixedForwarding OBJECT-TYPE
	SYNTAX      TruthValue
    MAX-ACCESS  read-only
    STATUS      current
    DESCRIPTION
    "If True the Ethernet frames originated from the subscriber
 	 will be forwarded to a gateway. 
 	 The value can be either True(1) or False(2).

     Valid from:   EDA 2.2 R3A
     "
    ::= { subscriberInfoEntry 25 }   
     
subscriberInfoGatewayIp OBJECT-TYPE
	SYNTAX      InetAddress (SIZE (4..20))
    MAX-ACCESS  read-only
    STATUS      current
    DESCRIPTION
    "The IP address of the gateway used by the subscriber.

     The subscriberInfoGatewayIp will contain 0.0.0.0 value when
     peaBridgeIpDslam::gatewayIp is not set for the PVC or gateway IP
     address is not learned in case of DHCP or DHCPIP over ATM access
     methods.
     
     Valid from:   EDA 2.2 R3A
     " 
    ::= { subscriberInfoEntry 30 }   

subscriberInfoGatewayMac OBJECT-TYPE
	SYNTAX      MacAddress
    MAX-ACCESS  read-only
    STATUS      current
    DESCRIPTION
    "The MAC address of the gateway used by the subscriber which is
     learned by the IP-DSLAM.
     
     The subscriberInfoGatewayMac will contain 00:00:00:00:00:00 value when
     - peaBridgeIpDslam::gatewayIp is not set for the PVC or gatewayIp is not
       learned in case of DHCP or DHCPIP over ATM access methods.
     - peaBridgeIpDslam::gatewayFixedForwarding is set to false for the PVC.
     - IP-DSLAM is unable to resolve the peaBridgeIpDslam::gatewayIp. 

     Valid from:   EDA 2.2 R3A
     " 
    ::= { subscriberInfoEntry 35 }   

mcastGroupInfoTable OBJECT-TYPE
    SYNTAX      SEQUENCE OF McastGroupInfoEntry
    MAX-ACCESS  not-accessible
    STATUS      current
    DESCRIPTION
    "Table containing the IGMP membership information for each Multicast Group Address
     learned by IGMP Snooping.

     With IGMP Snooping enabled,the IP DSLAM can 'listen in' on the IGMP conversation
     between IP Multicast Hosts and Routers, to learn the group memberships.
     When it hears an IGMP Join/Report from a host for a given multicast group,
     the IP DSLAM adds the host's MAC address to the Source MAC Address List for that group.
     And, when the IP DSLAM hears an IGMP Leave, it removes the host's MAC address entry.

     Thus multicast traffic of a group is forwarded only to the members of that group,
     thereby reducing the network traffic."
     
     ::= { bridgeControl 36 }

mcastGroupInfoEntry OBJECT-TYPE
	SYNTAX      McastGroupInfoEntry
    MAX-ACCESS  not-accessible
    STATUS      current
    DESCRIPTION
    "A mcastGroupInfoEntry is created for each multicast group learned on a PVC,
     when any subscriber joins the multicast group.

     For an mcastGroupInfoEntry created by any IGMP Msg from Network,
     the lineIndex is 0 and the pvcIndex is 0."
     
    INDEX  {
            lineIndex,
            pvcIndex,
            mcastGroupVlanId,
            mcastGroupAddress,
            mcastGroupHostMACAddress,
            mcastGroupSourceFilterIPAddress
           }
    ::= { mcastGroupInfoTable 1 }     
    
McastGroupInfoEntry ::= 
	SEQUENCE
       {
        mcastGroupVlanId                     Unsigned32,
        mcastGroupAddress                    InetAddress,
        mcastGroupHostMACAddress             MacAddress,
        mcastGroupSourceFilterIPAddress      InetAddress,
        mcastGroupIgmpMsgType                Unsigned32,
        mcastGroupIgmpMsgUpTime              Unsigned32
       } 

mcastGroupVlanId OBJECT-TYPE
    SYNTAX      Unsigned32 
    MAX-ACCESS  read-only
    STATUS      current
    DESCRIPTION
    "This object indicates the VLAN in which the multicast group is learned."
    ::= { mcastGroupInfoEntry 1 }
           
mcastGroupAddress OBJECT-TYPE
    SYNTAX      InetAddress
    MAX-ACCESS  read-only
    STATUS      current
    DESCRIPTION
    "This object indicates the IP address of the multicast group learned."
    ::= { mcastGroupInfoEntry 5 }

mcastGroupHostMACAddress OBJECT-TYPE
    SYNTAX      MacAddress
    MAX-ACCESS  read-only
    STATUS      current
    DESCRIPTION
    "This object indicates the MAC address of the host which is a  member
     of the Muticast Group." 
    ::= { mcastGroupInfoEntry 9 } 

mcastGroupSourceFilterIPAddress OBJECT-TYPE
    SYNTAX      InetAddress 
    MAX-ACCESS  read-only
    STATUS      current
    DESCRIPTION
    "IGMP Version 3 (IGMPv3) adds support for 'source filtering', which enables a multicast
     receiver host to explicitly signal sources from which they want to receive traffic.

     mcastGroupSourceFilterIPAddress is specified in the IGMPv3 Membership Reports and
     indicates the source address from which traffic is expected.

     Groups for which IGMPv1/v2 Membership Reports are received are considered to have a
     mcastGroupSourceFilterIPAddress of 0.0.0.0 "
    ::= { mcastGroupInfoEntry 13 }
        
mcastGroupIgmpMsgType OBJECT-TYPE
    SYNTAX      Unsigned32
    MAX-ACCESS  read-only
    STATUS      current
    DESCRIPTION
    "This object indicates the type of IGMP messages that are transmitted and received
     for the Multicast Group. The values for different IGMP message types are :
     
     IGMP Message Type           Value
     -----------------           ------
     IGMP_QUERY                  0x0001
     IGMPv1_REPORT               0x0002
     IGMPv2_REPORT               0x0004
    " 
    ::= { mcastGroupInfoEntry 21 }

mcastGroupIgmpMsgUpTime OBJECT-TYPE
    SYNTAX      Unsigned32
    MAX-ACCESS  read-only
    STATUS      current
    DESCRIPTION
    "This object indicates the time elapsed since the mcastGroupIgmpMsgType was first
     received/transmitted." 
    ::= { mcastGroupInfoEntry 25 }
    
downstreamFlowWredStatisticsEntry OBJECT-TYPE
    SYNTAX     DownstreamFlowWredStatisticsEntry
    MAX-ACCESS not-accessible
    STATUS     current
    DESCRIPTION
    "The downstreamFlowWredStatisticsEntry contains Weighted Random Early Discard (WRED)
     statistics for one VLAN priority in a downstream flow.

     Valid from:                EDA 2.2 R3A
    "
    AUGMENTS  { downstreamFlowWredConfigEntry }
    ::= { downstreamFlowWredStatisticsTable 5 }

DownstreamFlowWredStatisticsEntry  ::=
    SEQUENCE { wredStatisticsPktsCount     Unsigned32,
               wredStatisticsDiscards      Unsigned32,
               wredStatisticsByteCount     Counter64,
               wredStatisticsByteDiscards  Counter64
             }

wredStatisticsPktsCount OBJECT-TYPE
    SYNTAX      Unsigned32
    MAX-ACCESS  read-only
    STATUS      current
    DESCRIPTION
    "The number of packets that have passed the Weighted Random
     Early Discard (WRED) mechanism.
     
     Valid from:                EDA 2.2 R3A
     "
    ::= { downstreamFlowWredStatisticsEntry 5 }

wredStatisticsDiscards OBJECT-TYPE
    SYNTAX      Unsigned32
    MAX-ACCESS  read-only
    STATUS      current
    DESCRIPTION
    "The number of packets that have been discarded by the Weighted Random
     Early Discard (WRED) mechanism.
     
     Valid from:                EDA 2.2 R3A
     "
    ::= { downstreamFlowWredStatisticsEntry 10 }
             
wredStatisticsByteCount OBJECT-TYPE
    SYNTAX      Counter64
    MAX-ACCESS  read-only
    STATUS      current
    DESCRIPTION
    "The number of bytes that have passed the Weighted Random
     Early Discard (WRED) mechanism.
     
     Valid from:                EDA 2.2 R3A
     "
    ::= { downstreamFlowWredStatisticsEntry 15 }

wredStatisticsByteDiscards OBJECT-TYPE
    SYNTAX      Counter64
    MAX-ACCESS  read-only
    STATUS      current
    DESCRIPTION
    "The number of bytes that have been discarded by the Weighted Random
     Early Discard (WRED) mechanism.
     
     Valid from:                EDA 2.2 R3A
     "
    ::= { downstreamFlowWredStatisticsEntry 20 }

trafficStatistics     OBJECT IDENTIFIER ::= { bridgeControl 40 }
trafStatNode          OBJECT IDENTIFIER ::= { trafficStatistics 2 }
trafStatLogiPort      OBJECT IDENTIFIER ::= { trafficStatistics 6 }

nodeId OBJECT-TYPE
    SYNTAX      Unsigned32
    MAX-ACCESS  not-accessible
    STATUS      current
    DESCRIPTION
    "The value of nodeId uniquely identifies the traffic
     statistics of the IPDSLAM.
     The default value for IPDSLAM is always one.

	 Valid from:   EDA 2.2 SP3"
    ::= { trafficStatistics 1 }   

trafStatNodeMainTable OBJECT-TYPE
    SYNTAX      SEQUENCE OF TrafStatNodeMainEntry
    MAX-ACCESS  not-accessible
    STATUS      current
    DESCRIPTION
    "This table contains list of upstream and downstream traffic
     statistics entries of IPDSLAM.

  	 Valid from:   EDA 2.2 SP3"
     ::= { trafStatNode 1 }

trafStatNodeMainEntry OBJECT-TYPE
    SYNTAX      TrafStatNodeMainEntry
    MAX-ACCESS  not-accessible
    STATUS      current
    DESCRIPTION
    "An entry is a collection of upstream and downstream traffic
     statistics kept for the IPDSLAM.

	 Valid from:   EDA 2.2 SP3"
    
    INDEX  {nodeId }
    ::= { trafStatNodeMainTable 1 }     
    
TrafStatNodeMainEntry ::= 
	SEQUENCE
       {
        tsnDsPkts                   Counter32,
        tsnDsUntaggedMgmtPkts       Counter32,
        tsnDsTaggedMgmtPkts         Counter32,
        tsnDsDhcpPkts               Counter32,
        tsnDsPppDiscoveryPkts       Counter32,
        tsnDsBcastPkts              Counter32,
        tsnDsArpPkts                Counter32,
        tsnDsL2cpPkts               Counter32,
        tsnDsPktsFlooded            Counter32,
        tsnUsPkts                   Counter32,
        tsnUsDhcpPkts               Counter32,
        tsnUsPppDiscoveryPkts       Counter32,
        tsnUsArpPkts                Counter32,
        tsnLocalSwitchPkts          Counter32,
        tsnMainClearStat            INTEGER          
       } 

tsnDsPkts    OBJECT-TYPE
    SYNTAX      Counter32
    MAX-ACCESS  read-only
    STATUS      current
    DESCRIPTION
    "Total number of Ethernet packets received from the network.

	 Valid from:   EDA 2.2 SP3" 
    ::= { trafStatNodeMainEntry  1 }

tsnDsUntaggedMgmtPkts OBJECT-TYPE
    SYNTAX      Counter32
    MAX-ACCESS  read-only
    STATUS      current
    DESCRIPTION
    "Total number of untagged management packets received from the network.

	 Valid from:   EDA 2.2 SP3" 
    ::= { trafStatNodeMainEntry  5 }

tsnDsTaggedMgmtPkts OBJECT-TYPE
    SYNTAX      Counter32
    MAX-ACCESS  read-only
    STATUS      current
    DESCRIPTION
    "Total number of tagged management packets received from the network.

	 Valid from:   EDA 2.2 SP3" 
    ::= { trafStatNodeMainEntry  10 }

tsnDsDhcpPkts OBJECT-TYPE
    SYNTAX      Counter32
    MAX-ACCESS  read-only
    STATUS      current
    DESCRIPTION
    "Total number of non-management DHCP packets received from the network.

	 Valid from:   EDA 2.2 SP3" 
    ::= { trafStatNodeMainEntry  15 }

tsnDsPppDiscoveryPkts OBJECT-TYPE
    SYNTAX      Counter32
    MAX-ACCESS  read-only
    STATUS      current
    DESCRIPTION
    "Total number of PPP discovery packets received from the network.

	 Valid from:   EDA 2.2 SP3" 
    ::= { trafStatNodeMainEntry  20 }

tsnDsBcastPkts OBJECT-TYPE
    SYNTAX      Counter32
    MAX-ACCESS  read-only
    STATUS      current
    DESCRIPTION
    "Total number of non-management broadcast packets received
     from the network.

	 Valid from:   EDA 2.2 SP3" 
    ::= { trafStatNodeMainEntry  25 }

tsnDsArpPkts OBJECT-TYPE
    SYNTAX      Counter32
    MAX-ACCESS  read-only
    STATUS      current
    DESCRIPTION
    "Total number of non-management ARP packets received from
     the network.

	 Valid from:   EDA 2.2 SP3" 
    ::= { trafStatNodeMainEntry  30 }

tsnDsL2cpPkts OBJECT-TYPE
    SYNTAX      Counter32
    MAX-ACCESS  read-only
    STATUS      current
    DESCRIPTION
    "Total number of L2CP packets received from the network.

	 Valid from:   EDA 2.2 SP3"
    ::= { trafStatNodeMainEntry  35 }

tsnDsPktsFlooded  OBJECT-TYPE
    SYNTAX      Counter32
    MAX-ACCESS  read-only
    STATUS      current
    DESCRIPTION
    "Total number of Ethernet packets from the network flooded to the
     subscribers in the same VLAN due to destination MAC address unknown
     in IPDSLAM.

	 Valid from:   EDA 2.2 SP3" 
    ::= { trafStatNodeMainEntry  40 }

tsnUsPkts    OBJECT-TYPE
    SYNTAX      Counter32
    MAX-ACCESS  read-only
    STATUS      current
    DESCRIPTION
    "Total number of packets received from the subscribers.

	 Valid from:   EDA 2.2 SP3" 
    ::= { trafStatNodeMainEntry 45 }

tsnUsDhcpPkts OBJECT-TYPE
    SYNTAX      Counter32
    MAX-ACCESS  read-only
    STATUS      current
    DESCRIPTION
    "Total number of DHCP packets received from the subscribers.

	 Valid from:   EDA 2.2 SP3" 
    ::= { trafStatNodeMainEntry 50 }

tsnUsPppDiscoveryPkts OBJECT-TYPE
    SYNTAX      Counter32
    MAX-ACCESS  read-only
    STATUS      current
    DESCRIPTION
    "Total number of PPP discovery packets received from the subscribers.

	 Valid from:   EDA 2.2 SP3" 
    ::= { trafStatNodeMainEntry 55 }

tsnUsArpPkts OBJECT-TYPE
    SYNTAX      Counter32
    MAX-ACCESS  read-only
    STATUS      current
    DESCRIPTION
    "Total number of ARP packets received from the subscribers.

	 Valid from:   EDA 2.2 SP3" 
    ::= { trafStatNodeMainEntry 60 }

tsnLocalSwitchPkts OBJECT-TYPE
    SYNTAX      Counter32
    MAX-ACCESS  read-only
    STATUS      current
    DESCRIPTION
    "Total number of Ethernet packets received from the subscriber and sent
     to other subscribers connected on the same IPDSLAM.

	 Valid from:   EDA 2.2 SP3" 
    ::= { trafStatNodeMainEntry 65 }
    
tsnMainClearStat OBJECT-TYPE
    SYNTAX      INTEGER { clear(1) }
    MAX-ACCESS  read-write
    STATUS      current
    DESCRIPTION
    "This parameter resets all the trafStatNodeMain traffic
     statistics of the IPDSLAM to zero.

	 Valid from:   EDA 2.2 SP3" 
    ::= { trafStatNodeMainEntry 999 }
        
trafStatNodeMcastMainTable OBJECT-TYPE
    SYNTAX      SEQUENCE OF TrafStatNodeMcastMainEntry
    MAX-ACCESS  not-accessible
    STATUS      current
    DESCRIPTION
    "This table contains list of upstream and downstream multicast
     traffic statistics entries of IPDSLAM.

	 Valid from:   EDA 2.2 SP3"
     ::= { trafStatNode 5 }

trafStatNodeMcastMainEntry OBJECT-TYPE
    SYNTAX      TrafStatNodeMcastMainEntry
    MAX-ACCESS  not-accessible
    STATUS      current
    DESCRIPTION
    "An entry is a collection of upstream and downstream multicast
     traffic statistics kept for the IPDSLAM.

	 Valid from:   EDA 2.2 SP3"
     
    INDEX  {nodeId }
    ::= { trafStatNodeMcastMainTable 1 }     
    
TrafStatNodeMcastMainEntry ::= 
	SEQUENCE
       {
        tsnDsMcastPkts            Counter32,
        tsnDsMcastCtrlPkts        Counter32,
        tsnUsMcastPkts            Counter32,
        tsnUsMcastCtrlPkts        Counter32,
        tsnMcastPktsFlooded       Counter32,
        tsnNoOfIgmpGroups         Counter32,
        tsnNoOfIgmpEntries        Counter32,
        tsnIgmpQueryPkts          Counter32,
        tsnIgmpReportPkts         Counter32,
        tsnIgmpLeavePkts          Counter32,
        tsnMcastMainClearStat     INTEGER          
       } 
    
tsnDsMcastPkts OBJECT-TYPE
    SYNTAX      Counter32
    MAX-ACCESS  read-only
    STATUS      current
    DESCRIPTION
    "Total number of IP multicast packets received from the network.

	 Valid from:   EDA 2.2 SP3" 
    ::= { trafStatNodeMcastMainEntry 1 }
    
tsnDsMcastCtrlPkts OBJECT-TYPE
    SYNTAX      Counter32
    MAX-ACCESS  read-only
    STATUS      current
    DESCRIPTION
    "Total number of multicast control (Non-UDP) packets
     received from the network.

	 Valid from:   EDA 2.2 SP3" 
    ::= { trafStatNodeMcastMainEntry 5 }

tsnUsMcastPkts OBJECT-TYPE
    SYNTAX      Counter32
    MAX-ACCESS  read-only
    STATUS      current
    DESCRIPTION
    "Total number of IP multicast packets received from the subscribers.

	 Valid from:   EDA 2.2 SP3" 
    ::= { trafStatNodeMcastMainEntry 10 }

tsnUsMcastCtrlPkts OBJECT-TYPE
    SYNTAX      Counter32
    MAX-ACCESS  read-only
    STATUS      current
    DESCRIPTION
    "Total number of multicast control (Non-UDP) packets
     received from the subscribers.

	 Valid from:   EDA 2.2 SP3" 
    ::= { trafStatNodeMcastMainEntry 15 } 

tsnMcastPktsFlooded OBJECT-TYPE
    SYNTAX      Counter32
    MAX-ACCESS  read-only
    STATUS      current
    DESCRIPTION
    "Total number of multicast packets received which gets flooded to
     the network and subscribers in same VLAN.

	 Valid from:   EDA 2.2 SP3" 
    ::= { trafStatNodeMcastMainEntry 20 }

tsnNoOfIgmpGroups OBJECT-TYPE
    SYNTAX      Counter32
    MAX-ACCESS  read-only
    STATUS      current
    DESCRIPTION
    "Total number of IGMP Groups which have atleast one active member.
     IGMP Group is identified by the multicast group address and vlan.
     e.g 1) If IGMP Group [G1,V1] and [G1,V2] have atleast one active member,
            then tsnNoOfIgmpGroups will be two.
         2) If IGMP Group [G1,V1],[G2,V1] and [G3,V2] have atleast one
            active member, then tsnNoOfIgmpGroups will be three.

	 Valid from:   EDA 2.2 SP3" 
    ::= { trafStatNodeMcastMainEntry 25 }

tsnNoOfIgmpEntries OBJECT-TYPE
    SYNTAX      Counter32
    MAX-ACCESS  read-only
    STATUS      current
    DESCRIPTION
    "Total number of IGMP entries for which there is
      - Atleast one active member.
      - Atleast one active querier.
     IGMP entry is identified by PVC, multicast group address and vlan.

	 Valid from:   EDA 2.2 SP3" 
    ::= { trafStatNodeMcastMainEntry 30 }      

tsnIgmpQueryPkts OBJECT-TYPE
    SYNTAX      Counter32
    MAX-ACCESS  read-only
    STATUS      current
    DESCRIPTION
    "Total number of IGMP Query packets received either from
     network or subscribers.

	 Valid from:   EDA 2.2 SP3" 
    ::= { trafStatNodeMcastMainEntry 35 }

tsnIgmpReportPkts OBJECT-TYPE
    SYNTAX      Counter32
    MAX-ACCESS  read-only
    STATUS      current
    DESCRIPTION
    "Total number of IGMP Report packets received either from
     network or subscribers.

	 Valid from:   EDA 2.2 SP3" 
    ::= { trafStatNodeMcastMainEntry 40 }

tsnIgmpLeavePkts OBJECT-TYPE
    SYNTAX      Counter32
    MAX-ACCESS  read-only
    STATUS      current
    DESCRIPTION
    "Total number of IGMP Leave packets received either from
     network or subscribers.

	 Valid from:   EDA 2.2 SP3" 
    ::= { trafStatNodeMcastMainEntry 45 }

tsnMcastMainClearStat OBJECT-TYPE
    SYNTAX      INTEGER { clear(1) }
    MAX-ACCESS  read-write
    STATUS      current
    DESCRIPTION
    "This parameter resets all the trafStatNodeMcastMain
     traffic statistics of the IPDSLAM to zero.

	 Valid from:   EDA 2.2 SP3" 
    ::= { trafStatNodeMcastMainEntry 999 }
    
trafStatNodeErrorsTable OBJECT-TYPE
    SYNTAX      SEQUENCE OF TrafStatNodeErrorsEntry
    MAX-ACCESS  not-accessible
    STATUS      current
    DESCRIPTION
    "This table contains list of upstream and downstream error
     traffic statistics of the IPDSLAM.

	 Valid from:   EDA 2.2 SP3"
     ::= { trafStatNode 9 }

trafStatNodeErrorsEntry OBJECT-TYPE
	SYNTAX      TrafStatNodeErrorsEntry
    MAX-ACCESS  not-accessible
    STATUS      current
    DESCRIPTION
    "An entry is a collection of upstream and downstream error
     traffic statistics kept for the IPDSLAM.

	 Valid from:   EDA 2.2 SP3"
     
    INDEX  {nodeId }
    ::= { trafStatNodeErrorsTable 1 }     
    
TrafStatNodeErrorsEntry ::= 
	SEQUENCE
       {
        tsnDsTotalDiscardPkts       Unsigned32,
        tsnDsUnknownDstPkts         Counter32,
        tsnDsGatewayErrPkts         Counter32,
        tsnDsVlanIdAclErrPkts       Counter32,
        tsnDsEthTypeAclErrPkts      Counter32,
        tsnDsIpAclFilterErrPkts     Counter32,
        tsnUsTotalDiscardPkts       Unsigned32,
        tsnUsVlanIdAclErrPkts       Counter32,
        tsnUsEthTypeAclErrPkts      Counter32,
        tsnUsIpAclFilterErrPkts     Counter32,
        tsnUsSrcMacErrPkts          Counter32,
        tsnUsSrcIpErrPkts           Counter32,
        tsnUsBcastErrPkts           Counter32,
        tsnUsVmacErrPkts            Counter32,
        tsnUsGatewayErrPkts         Counter32,
        tsnUsSendErrPkts            Counter32,
        tsnUsVlanTypeFltrErrPkts    Counter32,
        tsnErrorsClearStat          INTEGER
       } 
    
tsnDsTotalDiscardPkts OBJECT-TYPE
    SYNTAX      Unsigned32
    MAX-ACCESS  read-only
    STATUS      current
    DESCRIPTION
    "Total number of non-multicast Ethernet packets from the network
     discarded by IPDSLAM.

     tsnDsTotalDiscardPkts = SUM[tsnDsUnknownDstPkts, tsnDsGatewayErrPkts,
     tsnDsVlanIdAclErrPkts, tsnDsEthTypeAclErrPkts, tsnDsIpAclFilterErrPkts]

	 Valid from:   EDA 2.2 SP3" 
    ::= { trafStatNodeErrorsEntry 1 }

tsnDsUnknownDstPkts OBJECT-TYPE
    SYNTAX      Counter32
    MAX-ACCESS  read-only
    STATUS      current
    DESCRIPTION
    "Total number of Ethernet packets received from the network  
     with unknown destination MAC address.

	 Valid from:   EDA 2.2 SP3" 
    ::= { trafStatNodeErrorsEntry  5 }

tsnDsGatewayErrPkts OBJECT-TYPE
    SYNTAX      Counter32
    MAX-ACCESS  read-only
    STATUS      current
    DESCRIPTION
    "Total number of Ethernet packets received from the network and
     discarded due to :
     - gateway MAC address not resolved by the IPDSLAM
     - Source MAC address in the packet is not the gateway MAC address

	 Valid from:   EDA 2.2 SP3" 
    ::= { trafStatNodeErrorsEntry  10 }

tsnDsVlanIdAclErrPkts OBJECT-TYPE
    SYNTAX      Counter32
    MAX-ACCESS  read-only
    STATUS      current
    DESCRIPTION
    "Total number of Ethernet packets received from the network and discarded
     due to VLAN Id Access Control List filtering.

	 Valid from:   EDA 2.2 SP3" 
    ::= { trafStatNodeErrorsEntry  15 }

tsnDsEthTypeAclErrPkts OBJECT-TYPE
    SYNTAX      Counter32
    MAX-ACCESS  read-only
    STATUS      current
    DESCRIPTION
    "Total number of Ethernet packets received from the network and discarded
     due to Ethernet type Access Control List filtering.

	 Valid from:   EDA 2.2 SP3" 
    ::= { trafStatNodeErrorsEntry  20 }

tsnDsIpAclFilterErrPkts OBJECT-TYPE
    SYNTAX      Counter32
    MAX-ACCESS  read-only
    STATUS      current
    DESCRIPTION
    "Total number of IP packets received from the network and
     discarded due to IP Access Control List filtering.

	 Valid from:   EDA 2.2 SP3" 
    ::= { trafStatNodeErrorsEntry  25 }

tsnUsTotalDiscardPkts OBJECT-TYPE
    SYNTAX      Unsigned32
    MAX-ACCESS  read-only
    STATUS      current
    DESCRIPTION
    "Total number of non-multicast Ethernet packets from the subscribers
     discarded by IPDSLAM.

     tsnUsTotalDiscardPkts = SUM[tsnUsVlanIdAclErrPkts, tsnUsEthTypeAclErrPkts,
     tsnUsIpAclFilterErrPkts, tsnUsSrcMacErrPkts, tsnUsSrcIpErrPkts, tsnUsBcastErrPkts,
     tsnUsVmacErrPkts, tsnUsGatewayErrPkts, tsnUsSendErrPkts,tsnUsVlanTypeFltrErrPkts]

	 Valid from:   EDA 2.2 SP3" 
    ::= { trafStatNodeErrorsEntry 30 }

tsnUsVlanIdAclErrPkts OBJECT-TYPE
    SYNTAX      Counter32
    MAX-ACCESS  read-only
    STATUS      current
    DESCRIPTION
    "Total number of Ethernet packets received from the subscribers
     and discarded due to VLAN Id Access Control List filtering.

	 Valid from:   EDA 2.2 SP3" 
    ::= { trafStatNodeErrorsEntry  35 }

tsnUsEthTypeAclErrPkts OBJECT-TYPE
    SYNTAX      Counter32
    MAX-ACCESS  read-only
    STATUS      current
    DESCRIPTION
    "Total number of Ethernet packets received from the subscribers
     and discarded due to Ethernet type Access Control List filtering.

	 Valid from:   EDA 2.2 SP3" 
    ::= { trafStatNodeErrorsEntry  40 }

tsnUsIpAclFilterErrPkts OBJECT-TYPE
    SYNTAX      Counter32
    MAX-ACCESS  read-only
    STATUS      current
    DESCRIPTION
    "Total number of IP packets received from the subscribers and
     discarded due to IP Access Control List filtering.

	 Valid from:   EDA 2.2 SP3" 
    ::= { trafStatNodeErrorsEntry  45 }

tsnUsSrcMacErrPkts OBJECT-TYPE
    SYNTAX      Counter32
    MAX-ACCESS  read-only
    STATUS      current
    DESCRIPTION
    "Total number of Ethernet packets received from the subscribers
     and discarded due to :
      - source MAC not present in the subscriber MAC filter.
      - MAC limit exceeded on the PVC.

	 Valid from:   EDA 2.2 SP3" 
    ::= { trafStatNodeErrorsEntry 50 }

tsnUsSrcIpErrPkts OBJECT-TYPE
    SYNTAX      Counter32
    MAX-ACCESS  read-only
    STATUS      current
    DESCRIPTION
    "Total number of IP packets received from the subscribers and
     discarded due to source IP address filtering.

	 Valid from:   EDA 2.2 SP3" 
    ::= { trafStatNodeErrorsEntry 55 }

tsnUsBcastErrPkts OBJECT-TYPE
    SYNTAX      Counter32
    MAX-ACCESS  read-only
    STATUS      current
    DESCRIPTION
    "Total number of Ethernet packets received from the subscribers and
     discarded due to subscriber not allowed to send and receive Broadcast.

	 Valid from:   EDA 2.2 SP3" 
    ::= { trafStatNodeErrorsEntry 60 }

tsnUsVmacErrPkts OBJECT-TYPE
    SYNTAX      Counter32
    MAX-ACCESS  read-only
    STATUS      current
    DESCRIPTION
    "Total number of packets received from the subscribers and discarded 
     due to maximum limit reached for number of virtual MAC addresses.

	 Valid from:   EDA 2.2 SP3" 
    ::= { trafStatNodeErrorsEntry 65 }

tsnUsGatewayErrPkts OBJECT-TYPE
    SYNTAX      Counter32
    MAX-ACCESS  read-only
    STATUS      current
    DESCRIPTION
    "Total number of Ethernet packets received from the subscribers and
     discarded due to :
     - gateway MAC address not resolved by the IPDSLAM
     - Destination MAC address in the packet is not the gateway MAC address

	 Valid from:   EDA 2.2 SP3" 
    ::= { trafStatNodeErrorsEntry 70 }

tsnUsSendErrPkts OBJECT-TYPE
    SYNTAX      Counter32
    MAX-ACCESS  read-only
    STATUS      current
    DESCRIPTION
    "Total number of non-multicast Ethernet packets received from the
     subscribers and discarded due to :
      - upstream policing
      - packet size exceeding peaBridgeIpDslam::maximumEthernetFrameSize
      
	 Valid from:   EDA 2.2 SP3"
    ::= { trafStatNodeErrorsEntry 75 }

tsnUsVlanTypeFltrErrPkts OBJECT-TYPE
    SYNTAX      Counter32
    MAX-ACCESS  read-only
    STATUS      current
    DESCRIPTION
    "Total number of Ethernet packets received from the subscribers and
     discarded due to VLAN type filtering.

	 Valid from:   EDA 2.2 SP3" 
    ::= { trafStatNodeErrorsEntry 80 }

tsnErrorsClearStat OBJECT-TYPE
    SYNTAX      INTEGER { clear(1)}
    MAX-ACCESS  read-write
    STATUS      current
    DESCRIPTION
    "This parameter resets all the trafStatNodeErrors
     traffic statistics of the IPDSLAM to zero.

	 Valid from:   EDA 2.2 SP3" 
    ::= { trafStatNodeErrorsEntry 999 }     

trafStatNodeMcastErrorsTable OBJECT-TYPE
    SYNTAX      SEQUENCE OF TrafStatNodeMcastErrorsEntry
    MAX-ACCESS  not-accessible
    STATUS      current
    DESCRIPTION
    "This table contains list of upstream and downstream multicast
     error traffic statistics of the IPDSLAM.

	 Valid from:   EDA 2.2 SP3"
     ::= { trafStatNode 13 }

trafStatNodeMcastErrorsEntry OBJECT-TYPE
	SYNTAX      TrafStatNodeMcastErrorsEntry
    MAX-ACCESS  not-accessible
    STATUS      current
    DESCRIPTION
    "An entry is a collection of upstream and downstream multicast
     error traffic statistics kept for the IPDSLAM.

	 Valid from:   EDA 2.2 SP3"
    
    INDEX  {nodeId }
    ::= { trafStatNodeMcastErrorsTable 1 }     
    
TrafStatNodeMcastErrorsEntry ::= 
	SEQUENCE
       {
       	tsnDsMcastErrPkts               Counter32,
        tsnDsNoDestinationErrPkts       Counter32,
        tsnDsIpAclErrPkts               Counter32,
        tsnDsTxErrPkts                  Counter32,
        tsnUsMcastErrPkts               Counter32,
        tsnUsNoDestinationErrPkts       Counter32,
        tsnUsDisabledLogiPortErrPkts    Counter32,
        tsnUsIpAclErrPkts               Counter32,
        tsnUsTxErrPkts                  Counter32,
        tsnTooShortErrPkts              Counter32,
        tsnUnknownIgmpTypesErrPkts      Counter32,
        tsnPhyLayerNotRunningErrPkts    Counter32,
        tsnReportsNotAllowedErrPkts     Counter32,
        tsnLeavesNotAllowedErrPkts      Counter32,
        tsnMcastErrorsClearStat         INTEGER 
       } 

tsnDsMcastErrPkts OBJECT-TYPE
    SYNTAX      Counter32
    MAX-ACCESS  read-only
    STATUS      current
    DESCRIPTION
    "Total number of multicast packets received from the network and
     discarded due to :
      - Non-IP multicast packet 
      - Non-L2CP multicast packet 

	 Valid from:   EDA 2.2 SP3" 
    ::= { trafStatNodeMcastErrorsEntry 1 }
    
tsnDsNoDestinationErrPkts OBJECT-TYPE
    SYNTAX      Counter32
    MAX-ACCESS  read-only
    STATUS      current
    DESCRIPTION
    "Total number of multicast UDP packets received from network and
     discarded due to unknown destination multicast group address.

	 Valid from:   EDA 2.2 SP3" 
    ::= { trafStatNodeMcastErrorsEntry 5 }

tsnDsIpAclErrPkts OBJECT-TYPE
    SYNTAX      Counter32
    MAX-ACCESS  read-only
    STATUS      current
    DESCRIPTION
    "Total number of multicast non-UDP packets received from network
     and discarded due to IP Access Control List filtering.

	 Valid from:   EDA 2.2 SP3" 
    ::= { trafStatNodeMcastErrorsEntry 10 }

tsnDsTxErrPkts OBJECT-TYPE
    SYNTAX      Counter32
    MAX-ACCESS  read-only
    STATUS      current
    DESCRIPTION
    "Total number of multicast packets received from network and discarded
     due to following errors in sending the packets to the susbcribers :
      - Illegal P-bit
      - Downstream policing
      - Vlan type filtering
      - Vlan Id Access Control List filtering
      - ATM layer not running.

	 Valid from:   EDA 2.2 SP3" 
    ::= { trafStatNodeMcastErrorsEntry 15 }

tsnUsMcastErrPkts OBJECT-TYPE
    SYNTAX      Counter32
    MAX-ACCESS  read-only
    STATUS      current
    DESCRIPTION
    "Total number of multicast packets received from the subscribers
     and discarded due to :
      - Non-IP multicast packet
      - Non-L2CP multicast packet

	 Valid from:   EDA 2.2 SP3" 
    ::= { trafStatNodeMcastErrorsEntry 20 }
    
tsnUsNoDestinationErrPkts OBJECT-TYPE
    SYNTAX      Counter32
    MAX-ACCESS  read-only
    STATUS      current
    DESCRIPTION
    "Total number of multicast UDP packets received from the subscribers
     and discarded due to unknown destination multicast group address.

	 Valid from:   EDA 2.2 SP3" 
    ::= { trafStatNodeMcastErrorsEntry 25 }

tsnUsDisabledLogiPortErrPkts OBJECT-TYPE
    SYNTAX      Counter32
    MAX-ACCESS  read-only
    STATUS      current
    DESCRIPTION
    "Total number of multicast packets received from the susbcribers
     and discarded due to :
      - IGMP snooping disabled on the PVC.
      - Upstream multicast disabled on the PVC.

	 Valid from:   EDA 2.2 SP3" 
    ::= { trafStatNodeMcastErrorsEntry 30 }

tsnUsIpAclErrPkts OBJECT-TYPE
    SYNTAX      Counter32
    MAX-ACCESS  read-only
    STATUS      current
    DESCRIPTION
    "Total number of multicast non-UDP packets received from the subscribers
     and discarded due to IP Access Control List filtering.

	 Valid from:   EDA 2.2 SP3" 
    ::= { trafStatNodeMcastErrorsEntry 35 }

tsnUsTxErrPkts OBJECT-TYPE
    SYNTAX      Counter32
    MAX-ACCESS  read-only
    STATUS      current
    DESCRIPTION
    "Total number of multicast packets received from the subscribers and
     discarded due to following errors in sending the packets to network.
      - upstream policing
      - packet size exceeding peaBridgeIpDslam::maximumEthernetFrameSize

	 Valid from:   EDA 2.2 SP3" 
    ::= { trafStatNodeMcastErrorsEntry 40 }

tsnTooShortErrPkts OBJECT-TYPE
    SYNTAX      Counter32
    MAX-ACCESS  read-only
    STATUS      current
    DESCRIPTION
    "Total number of IGMP packets discarded due to packet size less than
     minimum IGMP packet length (Ethernet + IP + IGMP header).

	 Valid from:   EDA 2.2 SP3"
    ::= { trafStatNodeMcastErrorsEntry 45 }

tsnUnknownIgmpTypesErrPkts OBJECT-TYPE
    SYNTAX      Counter32
    MAX-ACCESS  read-only
    STATUS      current
    DESCRIPTION
    "Total number of IGMP packets discarded due to unknown IGMP type
     in the IGMP header.

	 Valid from:   EDA 2.2 SP3" 
    ::= { trafStatNodeMcastErrorsEntry 50 }

tsnPhyLayerNotRunningErrPkts OBJECT-TYPE
    SYNTAX      Counter32
    MAX-ACCESS  read-only
    STATUS      current
    DESCRIPTION
    "Total number of muticast packets received from the subscribers and
     discarded due to ADSL line being down.

	 Valid from:   EDA 2.2 SP3" 
    ::= { trafStatNodeMcastErrorsEntry 55 }

tsnReportsNotAllowedErrPkts OBJECT-TYPE
    SYNTAX      Counter32
    MAX-ACCESS  read-only
    STATUS      current
    DESCRIPTION
    "Total number of IGMP Report packets discarded due to :
      - IGMP Report received from the network and upstream multicast not
        enabled for any subscriber in same Vlan.
      -	Multicast group address not allowed for the subscriber by the multicast filter.
      - Multicast group limit (peaBridgeIpDslam::multicastGroupsLimit) exceeded for the subscriber.

	 Valid from:   EDA 2.2 SP3" 
    ::= { trafStatNodeMcastErrorsEntry 60 }

tsnLeavesNotAllowedErrPkts OBJECT-TYPE
    SYNTAX      Counter32
    MAX-ACCESS  read-only
    STATUS      current
    DESCRIPTION
    "Total number of IGMP Leave packets discarded due to :
      -	Multicast group address not allowed for the subscriber by the multicast filter.

	 Valid from:   EDA 2.2 SP3" 
    ::= { trafStatNodeMcastErrorsEntry 65 }

tsnMcastErrorsClearStat OBJECT-TYPE
    SYNTAX      INTEGER { clear(1)}
    MAX-ACCESS  read-write
    STATUS      current
    DESCRIPTION
    "This parameter resets all the trafStatNodeMcastErrors
     traffic statistics of the IPDSLAM to zero.

	 Valid from:   EDA 2.2 SP3" 
    ::= { trafStatNodeMcastErrorsEntry 999 }     
    
trafStatNodeClearTable OBJECT-TYPE
    SYNTAX      SEQUENCE OF TrafStatNodeClearEntry
    MAX-ACCESS  not-accessible
    STATUS      current
    DESCRIPTION
    "This table contains tsnClearStat parameter which resets the
     upstream and downstream traffic statistics of the IPDSLAM to zero.

     Valid from:   EDA 2.2 SP3"
     ::= { trafStatNode 17 }

trafStatNodeClearEntry OBJECT-TYPE
	SYNTAX      TrafStatNodeClearEntry
    MAX-ACCESS  not-accessible
    STATUS      current
    DESCRIPTION
    "An entry in the trafStatNodeClearTable.

	 Valid from:   EDA 2.2 SP3"
    
    INDEX  {nodeId }
    ::= { trafStatNodeClearTable 1 }     
    
TrafStatNodeClearEntry ::= 
	SEQUENCE
       {
       	tsnClearStat      INTEGER
       } 
    
tsnClearStat OBJECT-TYPE
    SYNTAX      INTEGER { clear(1)}
    MAX-ACCESS  read-write
    STATUS      current
    DESCRIPTION
    "This parameter resets all the following traffic statistics of
     the IPDSLAM to zero.
      - peaBridgeIpDslam::trafStatNodeMain
      - peaBridgeIpDslam::trafStatNodeMcastMain
      - peaBridgeIpDslam::trafStatNodeErrors
      - peaBridgeIpDslam::trafStatNodeMcastErrors

	 Valid from:   EDA 2.2 SP3" 
    ::= { trafStatNodeClearEntry 1 }

trafStatLogiPortMainTable OBJECT-TYPE
    SYNTAX      SEQUENCE OF TrafStatLogiPortMainEntry
    MAX-ACCESS  not-accessible
    STATUS      current
    DESCRIPTION
    "This table contains list of upstream and downstream traffic 
     statistics of the IPDSLAM for a specific PVC.

	 Valid from:   EDA 2.2 SP3"
     ::= { trafStatLogiPort 1 }

trafStatLogiPortMainEntry OBJECT-TYPE
	SYNTAX      TrafStatLogiPortMainEntry
    MAX-ACCESS  not-accessible
    STATUS      current
    DESCRIPTION
    "An entry is a collection of upstream and downstream traffic
     statistics kept for the IPDSLAM for a specific PVC.

	 Valid from:   EDA 2.2 SP3"
    
    INDEX  {nodeId, lineIndex, pvcIndex }
    ::= { trafStatLogiPortMainTable 1 }     
    
TrafStatLogiPortMainEntry ::= 
	SEQUENCE
       {
        tslpDsPkts                Counter32,
        tslpDsBytes               Counter64,
        tslpDsPktsPerSec          Unsigned32,
        tslpDsBitsPerSec          Unsigned32,
        tslpDsUcastPkts           Counter32,
        tslpDsBcastPkts           Counter32,
        tslpDsFromLocalSrcPkts    Counter32,
        tslpDsArpPkts             Counter32,
        tslpDsDhcpPkts            Counter32,
        tslpDsPppDiscoveryPkts    Counter32,
        tslpDsL2cpPkts            Counter32,
        tslpUsPkts                Counter32,
        tslpUsBytes               Counter64,
        tslpUsPktsPerSec          Unsigned32,
        tslpUsBitsPerSec          Unsigned32,
        tslpUsUcastPkts           Counter32,
        tslpUsBcastPkts           Counter32,
        tslpUsToLocalDestPkts     Counter32,
        tslpUsArpPkts             Counter32,
        tslpUsDhcpPkts            Counter32,
        tslpUsPppDiscoveryPkts    Counter32,
        tslpUsL2cpPkts            Counter32,
        tslpMainClearStat         INTEGER 
       } 

tslpDsPkts OBJECT-TYPE
    SYNTAX      Counter32
    MAX-ACCESS  read-only
    STATUS      current
    DESCRIPTION
    "Total number of Ethernet packets received from network and
     sent to the subscriber on the specified PVC.

     This parameter is an alias to pvcTable.downstreamFrameCount.

	 Valid from:   EDA 2.2 SP3" 
    ::= { trafStatLogiPortMainEntry 1 }

tslpDsBytes OBJECT-TYPE
    SYNTAX      Counter64
    MAX-ACCESS  read-only
    STATUS      current
    DESCRIPTION
    "Total number of bytes received from network and sent to
     the subscriber on the specified PVC.

     This parameter is an alias to pvcTable.downstreamByteCount.

	 Valid from:   EDA 2.2 SP3" 
    ::= { trafStatLogiPortMainEntry 5 }

tslpDsPktsPerSec OBJECT-TYPE
    SYNTAX      Unsigned32
    MAX-ACCESS  read-only
    STATUS      current
    DESCRIPTION
    "Total number of Ethernet packets per second received from
     network and sent to the subscriber on the specified PVC.

     This parameter is an alias to pvcTable.downstreamFramesPerSecond.

	 Valid from:   EDA 2.2 SP3" 
    ::= { trafStatLogiPortMainEntry 10 }

tslpDsBitsPerSec OBJECT-TYPE
    SYNTAX      Unsigned32
    MAX-ACCESS  read-only
    STATUS      current
    DESCRIPTION
    "Total number of bits per second received from network and
     sent to the subscriber on the specified PVC.

     This parameter is an alias to pvcTable.downstreamBitsPerSecond.

	 Valid from:   EDA 2.2 SP3" 
    ::= { trafStatLogiPortMainEntry 15 }

tslpDsUcastPkts OBJECT-TYPE
    SYNTAX      Counter32
    MAX-ACCESS  read-only
    STATUS      current
    DESCRIPTION
    "Total number of unicast packets received from the network
    and sent to the subscriber on the specified PVC.

	 Valid from:   EDA 2.2 SP3" 
    ::= { trafStatLogiPortMainEntry 20 }

tslpDsBcastPkts OBJECT-TYPE
    SYNTAX      Counter32
    MAX-ACCESS  read-only
    STATUS      current
    DESCRIPTION
    "Total numbers of broadcast packets received from the network
     and sent to the subscriber on the specified PVC.

	 Valid from:   EDA 2.2 SP3" 
    ::= { trafStatLogiPortMainEntry 25 }

tslpDsFromLocalSrcPkts OBJECT-TYPE
    SYNTAX      Counter32
    MAX-ACCESS  read-only
    STATUS      current
    DESCRIPTION
    "Total numbers of packets received from a subscriber connected
     on the same IPDSLAM and sent to subscriber on the specified PVC.

	 Valid from:   EDA 2.2 SP3" 
    ::= { trafStatLogiPortMainEntry 30 }

tslpDsArpPkts OBJECT-TYPE
    SYNTAX      Counter32
    MAX-ACCESS  read-only
    STATUS      current
    DESCRIPTION
    "Total number of ARP packets received from network and sent
     to the subscriber on the specified PVC.

	 Valid from:   EDA 2.2 SP3" 
    ::= { trafStatLogiPortMainEntry 35 }

tslpDsDhcpPkts OBJECT-TYPE
    SYNTAX      Counter32
    MAX-ACCESS  read-only
    STATUS      current
    DESCRIPTION
    "Total number of DHCP packets received from network and sent
     to the subscriber on the specified PVC

	 Valid from:   EDA 2.2 SP3"
    ::= { trafStatLogiPortMainEntry 40 }

tslpDsPppDiscoveryPkts OBJECT-TYPE
    SYNTAX      Counter32
    MAX-ACCESS  read-only
    STATUS      current
    DESCRIPTION
    "Total number of PPP discovery packets received from network
     and sent to the subscriber on the specified PVC.

	 Valid from:   EDA 2.2 SP3" 
    ::= { trafStatLogiPortMainEntry 45 }

tslpDsL2cpPkts OBJECT-TYPE
    SYNTAX      Counter32
    MAX-ACCESS  read-only
    STATUS      current
    DESCRIPTION
    "Total number of L2CP tunneling packets received from network
     and sent to the subscriber on the specified PVC.

	 Valid from:   EDA 2.2 SP3"
    ::= { trafStatLogiPortMainEntry 50 }
    
tslpUsPkts OBJECT-TYPE
    SYNTAX      Counter32
    MAX-ACCESS  read-only
    STATUS      current
    DESCRIPTION
    "Total number of Ethernet packets received from the subscriber
     on the specified PVC and sent to the network.

     This parameter is an alias to pvcTable.upstreamFrameCount.

	 Valid from:   EDA 2.2 SP3" 
    ::= { trafStatLogiPortMainEntry 55 }

tslpUsBytes OBJECT-TYPE
    SYNTAX      Counter64
    MAX-ACCESS  read-only
    STATUS      current
    DESCRIPTION
    "Total number of bytes received from the subscriber on the
     specified PVC and sent to network.

     This parameter is an alias to pvcTable.upstreamByteCount.

	 Valid from:   EDA 2.2 SP3"
    ::= { trafStatLogiPortMainEntry 60 }

tslpUsPktsPerSec OBJECT-TYPE
    SYNTAX      Unsigned32
    MAX-ACCESS  read-only
    STATUS      current
    DESCRIPTION
    "Total number of Ethernet packets per second received from the
     subscriber on the specified PVC and sent to the network.

     This parameter is an alias to pvcTable.upstreamFramesPerSecond.

	 Valid from:   EDA 2.2 SP3" 
    ::= { trafStatLogiPortMainEntry 65 }

tslpUsBitsPerSec OBJECT-TYPE
    SYNTAX      Unsigned32
    MAX-ACCESS  read-only
    STATUS      current
    DESCRIPTION
    "Total number of bits per second received from the subscriber
     on the specified PVC and sent to network.

     This parameter is an alias to pvcTable.upstreamBitsPerSecond.

	 Valid from:   EDA 2.2 SP3" 
    ::= { trafStatLogiPortMainEntry 70 }

tslpUsUcastPkts OBJECT-TYPE
    SYNTAX      Counter32
    MAX-ACCESS  read-only
    STATUS      current
    DESCRIPTION
    "Total number of unicast packets received from the subscriber
     on the specified PVC and sent to network.

	 Valid from:   EDA 2.2 SP3" 
    ::= { trafStatLogiPortMainEntry 75 }

tslpUsBcastPkts OBJECT-TYPE
    SYNTAX      Counter32
    MAX-ACCESS  read-only
    STATUS      current
    DESCRIPTION
    "Total number of broadcast packets received from the subscriber
     on the specified PVC and sent to network.

	 Valid from:   EDA 2.2 SP3" 
    ::= { trafStatLogiPortMainEntry 80 }

tslpUsToLocalDestPkts OBJECT-TYPE
    SYNTAX      Counter32
    MAX-ACCESS  read-only
    STATUS      current
    DESCRIPTION
    "Total numbers of packets received from the subscriber on the specified PVC
     and sent to another subscriber connected on same IPDSLAM.

	 Valid from:   EDA 2.2 SP3" 
    ::= { trafStatLogiPortMainEntry 85 }

tslpUsArpPkts OBJECT-TYPE
    SYNTAX      Counter32
    MAX-ACCESS  read-only
    STATUS      current
    DESCRIPTION
    "Total number of ARP packets received from the subscriber
     on the specified PVC and sent to network.

	 Valid from:   EDA 2.2 SP3" 
    ::= { trafStatLogiPortMainEntry 90 }

tslpUsDhcpPkts OBJECT-TYPE
    SYNTAX      Counter32
    MAX-ACCESS  read-only
    STATUS      current
    DESCRIPTION
    "Total number of DHCP packets received from the subscriber
     on the specified PVC and sent to network.

	 Valid from:   EDA 2.2 SP3"
    ::= { trafStatLogiPortMainEntry 95 }

tslpUsPppDiscoveryPkts OBJECT-TYPE
    SYNTAX      Counter32
    MAX-ACCESS  read-only
    STATUS      current
    DESCRIPTION
    "Total number of PPP discovery packets received from the
     subscriber on the specified PVC and sent to network.

	 Valid from:   EDA 2.2 SP3" 
    ::= { trafStatLogiPortMainEntry 100 }

tslpUsL2cpPkts OBJECT-TYPE
    SYNTAX      Counter32
    MAX-ACCESS  read-only
    STATUS      current
    DESCRIPTION
    "Total number of L2CP tunneling packets received from the
     subscriber on the specified PVC and sent to network.

	 Valid from:   EDA 2.2 SP3"
    ::= { trafStatLogiPortMainEntry 105 }

tslpMainClearStat OBJECT-TYPE
    SYNTAX      INTEGER { clear(1)}
    MAX-ACCESS  read-write
    STATUS      current
    DESCRIPTION
    "This parameter resets all the trafStatLogiPortMain
     traffic statistics of the IPDSLAM to zero.

	 Valid from:   EDA 2.2 SP3" 
    ::= { trafStatLogiPortMainEntry 999 }     
       
trafStatLogiPortErrorsTable OBJECT-TYPE
    SYNTAX      SEQUENCE OF TrafStatLogiPortErrorsEntry
    MAX-ACCESS  not-accessible
    STATUS      current
    DESCRIPTION
    "This table contains list of upstream and downstream error
     traffic statistics of the IPDSLAM for a specific PVC.

	 Valid from:   EDA 2.2 SP3"
     ::= { trafStatLogiPort 5 }

trafStatLogiPortErrorsEntry OBJECT-TYPE
    SYNTAX      TrafStatLogiPortErrorsEntry
    MAX-ACCESS  not-accessible
    STATUS      current
    DESCRIPTION
    "An entry is a collection of upstream and downstream error traffic
     statistics kept for the IPDSLAM for a specific PVC.

 	 Valid from:   EDA 2.2 SP3"
    
    INDEX  {nodeId, lineIndex, pvcIndex }
    ::= { trafStatLogiPortErrorsTable 1 }     
    
TrafStatLogiPortErrorsEntry ::= 
	SEQUENCE
       {
        tslpDsVlanIdAclErrPkts        Counter32,
        tslpDsEthTypeAclErrPkts       Counter32,
        tslpDsIpAclErrPkts            Counter32,
        tslpDsGatewayErrPkts          Counter32,
        tslpDsMacErrPkts              Counter32,
        tslpDsBcastErrPkts            Counter32,
        tslpDsL2cpErrPkts             Counter32,
        tslpUsVlanIdAclErrPkts        Counter32,
        tslpUsEthTypeAclErrPkts       Counter32,
        tslpUsIpAclErrPkts            Counter32,
        tslpUsMacErrPkts              Counter32,
        tslpUsSrcIpErrPkts            Counter32,
        tslpUsGatewayErrPkts          Counter32,
        tslpUsBcastErrPkts            Counter32,
        tslpUsL2cpErrPkts             Counter32,
        tslpUsIcmpErrPkts             Counter32,
        tslpUsOversizedFrameErrPkts   Counter32,
        tslpUsPvcPolicingErrPkts      Counter32,
        tslpErrorsClearStat           INTEGER   
       } 

tslpDsVlanIdAclErrPkts OBJECT-TYPE
    SYNTAX      Counter32
    MAX-ACCESS  read-only
    STATUS      current
    DESCRIPTION
    "Total number of Ethernet packets received from the network and
     discarded for the specified PVC due to VLAN Id Access Control
     List filtering.

	 Valid from:   EDA 2.2 SP3"
    ::= { trafStatLogiPortErrorsEntry 1 }

tslpDsEthTypeAclErrPkts OBJECT-TYPE
    SYNTAX      Counter32
    MAX-ACCESS  read-only
    STATUS      current
    DESCRIPTION
    "Total number of Ethernet packets received from the network and
     discarded for the specified PVC due to Ethernet type Access Control
     List filtering.

	 Valid from:   EDA 2.2 SP3"
    ::= { trafStatLogiPortErrorsEntry 5 }

tslpDsIpAclErrPkts OBJECT-TYPE
    SYNTAX      Counter32
    MAX-ACCESS  read-only
    STATUS      current
    DESCRIPTION
    "Total number of IP packets received from the network and discarded
     for the specified PVC due to IP Access Control List filtering.

	 Valid from:   EDA 2.2 SP3"
    ::= { trafStatLogiPortErrorsEntry 10 }

tslpDsGatewayErrPkts OBJECT-TYPE
    SYNTAX      Counter32
    MAX-ACCESS  read-only
    STATUS      current
    DESCRIPTION
    "Total number of Ethernet packets received from the network and
     discarded for the specified PVC due to
     - gateway MAC address not resolved by IPDSLAM
     - Source MAC address in the packet is not the gateway MAC address.

	 Valid from:   EDA 2.2 SP3" 
    ::= { trafStatLogiPortErrorsEntry 15 }

tslpDsMacErrPkts OBJECT-TYPE
    SYNTAX      Counter32
    MAX-ACCESS  read-only
    STATUS      current
    DESCRIPTION
    "Total number of packets received from the network and discarded
     for the specified PVC due to :
      - destination MAC address not present in the subscriber MAC filter
      - MAC limit exceeded on the PVC

	 Valid from:   EDA 2.2 SP3" 
    ::= { trafStatLogiPortErrorsEntry 20 }

tslpDsBcastErrPkts OBJECT-TYPE
    SYNTAX      Counter32
    MAX-ACCESS  read-only
    STATUS      current
    DESCRIPTION
    "Total number of broadcast packets received from the network and
     discarded for the specified PVC due to :
      - Gateway MAC address not resolved by IPDSLAM.
      - Broadcast is not allowed on the specified PVC.

	 Valid from:   EDA 2.2 SP3" 
    ::= { trafStatLogiPortErrorsEntry 25 }

tslpDsL2cpErrPkts OBJECT-TYPE
    SYNTAX      Counter32
    MAX-ACCESS  read-only
    STATUS      current
    DESCRIPTION
    "Total number of L2CP packets received by the subscriber on the
     specified PVC and discarded due to L2CP Tunneling not enabled for
     the received protocol.

	 Valid from:   EDA 2.2 SP3" 
    ::= { trafStatLogiPortErrorsEntry 30 }

tslpUsVlanIdAclErrPkts OBJECT-TYPE
    SYNTAX      Counter32
    MAX-ACCESS  read-only
    STATUS      current
    DESCRIPTION
    "Total number of Ethernet packets received from the subscriber
     on the specified PVC and discarded due to VLAN Id Access Control
     List filtering.

	 Valid from:   EDA 2.2 SP3"
    ::= { trafStatLogiPortErrorsEntry 35 }

tslpUsEthTypeAclErrPkts OBJECT-TYPE
    SYNTAX      Counter32
    MAX-ACCESS  read-only
    STATUS      current
    DESCRIPTION
    "Total number of Ethernet packets received from the subscriber
     on the specified PVC and discarded due to Ethernet type Access
     Control List filtering.

	 Valid from:   EDA 2.2 SP3"
    ::= { trafStatLogiPortErrorsEntry 40 }

tslpUsIpAclErrPkts OBJECT-TYPE
    SYNTAX      Counter32
    MAX-ACCESS  read-only
    STATUS      current
    DESCRIPTION
    "Total number of IP packets received from the subscriber on the
     specified PVC and discarded due to IP Access Control List filtering.

	 Valid from:   EDA 2.2 SP3"
    ::= { trafStatLogiPortErrorsEntry 45 }

tslpUsMacErrPkts OBJECT-TYPE
    SYNTAX      Counter32
    MAX-ACCESS  read-only
    STATUS      current
    DESCRIPTION
    "Total number of Ethernet packets received from the subscribers
     on the specified PVC and discarded due to :
      - source MAC not present in the subscriber MAC filter
      - MAC limit exceeded on the PVC

	 Valid from:   EDA 2.2 SP3" 
    ::= { trafStatLogiPortErrorsEntry 50 }

tslpUsSrcIpErrPkts OBJECT-TYPE
    SYNTAX      Counter32
    MAX-ACCESS  read-only
    STATUS      current
    DESCRIPTION
    "Total number of IP packets received from the subscriber on
     the specified PVC and discarded due to source IP address in
     the packet not present in the subscriber IP filter.

	 Valid from:   EDA 2.2 SP3" 
    ::= { trafStatLogiPortErrorsEntry 55 }

tslpUsGatewayErrPkts OBJECT-TYPE
    SYNTAX      Counter32
    MAX-ACCESS  read-only
    STATUS      current
    DESCRIPTION
    "Total number of Ethernet packets received from the subscriber on the
     specified PVC and discarded due to :
     - gateway MAC address not resolved by IPDSLAM 
     - Destination MAC address in the packet is not the gateway MAC address

	 Valid from:   EDA 2.2 SP3" 
    ::= { trafStatLogiPortErrorsEntry 60 }

tslpUsBcastErrPkts OBJECT-TYPE
    SYNTAX      Counter32
    MAX-ACCESS  read-only
    STATUS      current
    DESCRIPTION
    "Total number of broadcast packets received from the subscriber on the
     specified PVC and discarded due to subscriber not allowed to send broadcast.

	 Valid from:   EDA 2.2 SP3" 
    ::= { trafStatLogiPortErrorsEntry 65 }

tslpUsL2cpErrPkts OBJECT-TYPE
    SYNTAX      Counter32
    MAX-ACCESS  read-only
    STATUS      current
    DESCRIPTION
    "Total number of L2CP packets received from the subscriber on the
     specified PVC and discarded due to :
      - L2CP Tunneling not enabled for the received protocol.
      - Unsupported protocol by L2CP Tunnneling.

	 Valid from:   EDA 2.2 SP3" 
    ::= { trafStatLogiPortErrorsEntry 70 }
    
tslpUsIcmpErrPkts OBJECT-TYPE
    SYNTAX      Counter32
    MAX-ACCESS  read-only
    STATUS      current
    DESCRIPTION
    "Total number of ICMP packets received from the subscriber on the
     specified PVC and discarded due to ICMP security filtering.

	 Valid from:   EDA 2.2 SP3" 
    ::= { trafStatLogiPortErrorsEntry 75 }

tslpUsOversizedFrameErrPkts OBJECT-TYPE
    SYNTAX      Counter32
    MAX-ACCESS  read-only
    STATUS      current
    DESCRIPTION
    "Total number of Ethernet packets received from the subscriber
     on the specified PVC and discarded due to packet size exceeding
     peaBridgeIpDslam::maximumEthernetFrameSize.

 	 Valid from:   EDA 2.2 SP3" 
    ::= { trafStatLogiPortErrorsEntry 80 }
    
tslpUsPvcPolicingErrPkts OBJECT-TYPE
    SYNTAX      Counter32
    MAX-ACCESS  read-only
    STATUS      current
    DESCRIPTION
    "Total number of Ethernet packets received from the subscriber
     on the specified PVC and discarded due to upstream policing.

 	 Valid from:   EDA 2.2 SP3" 
    ::= { trafStatLogiPortErrorsEntry 85 }

tslpErrorsClearStat OBJECT-TYPE
    SYNTAX      INTEGER { clear(1)}
    MAX-ACCESS  read-write
    STATUS      current
    DESCRIPTION
    "This parameter resets all the trafStatLogiPortErrors
     traffic statistics of the IPDSLAM to zero.

	 Valid from:   EDA 2.2 SP3" 
    ::= { trafStatLogiPortErrorsEntry 999 }     
    
trafStatLogiPortClearTable OBJECT-TYPE
    SYNTAX      SEQUENCE OF TrafStatLogiPortClearEntry
    MAX-ACCESS  not-accessible
    STATUS      current
    DESCRIPTION
    "This table contains tslpClearStat parameter which resets the
     upstream and downstream Logical port traffic statistics of the
     IPDSLAM to zero.

     Valid from:   EDA 2.2 SP3"
     ::= { trafStatLogiPort 9 }

trafStatLogiPortClearEntry OBJECT-TYPE
    SYNTAX      TrafStatLogiPortClearEntry
    MAX-ACCESS  not-accessible
    STATUS      current
    DESCRIPTION
    "An entry in the trafStatLogiPortClearTable.

 	 Valid from:   EDA 2.2 SP3"
    
    INDEX  {nodeId, lineIndex, pvcIndex }
    ::= { trafStatLogiPortClearTable 1 }     
    
TrafStatLogiPortClearEntry ::= 
	SEQUENCE
       {
       	tslpClearStat      INTEGER
       } 
    
tslpClearStat OBJECT-TYPE
    SYNTAX      INTEGER { clear(1)}
    MAX-ACCESS  read-write
    STATUS      current
    DESCRIPTION
    "This parameter resets all the following Logical port traffic
     statistics of the IPDSLAM to zero.
      - peaBridgeIpDslam::trafStatLogiPortMain
      - peaBridgeIpDslam::trafStatLogiPortErrors.

	 Valid from:   EDA 2.2 SP3"
    ::= { trafStatLogiPortClearEntry 1 }
    
END
