FANS-POWER-MIB DEFINITIONS ::= BEGIN

   IMPORTS
       OBJECT-TYPE,enterprises                      
                         FROM SNMPv2-SMI;

   zte OBJECT IDENTIFIER ::= { enterprises 3902 }
   zxr10 OBJECT IDENTIFIER ::= { zte 3}

       -- LAST-UPDATED "0108230840Z"
       -- ORGANIZATION "ZTE"
       -- CONTACT-INFO

       -- Nanjing Institute of Telecom,ZTE Corporation
       -- Postal: 9F. No.54 Building, 301# East ZhongShan Rd.
       -- Nan Jing, China
       -- Tel:    86-25-4826606-3821
       -- E-Mail: li.xinshuang@mail.zte.com.cn
       -- DESCRIPTION
       -- The MIB module which descript the zxr10rack mib
       -- object which defined in enterprise's ZTE(3902)
    FanPosition ::= INTEGER
                       {
                         cabinet-fan-top(1),
                         trunk-fan-top(2),
                         trunk-fan-bottom(3)
                       }
                       
    FanStat ::= INTEGER
                 {
                    offline(0),
                    online(1)
                  }                   

    FanType ::= INTEGER
                 {
                    newfan(1),
                    oldfan(2)
                 }
                  
    PowerType ::= INTEGER
                 {
                    oldpower(2),
                    newpower(3)
                 }

    PowerAvailStatus ::= INTEGER
                 {
                    offline(0),
                    online(1),
                    null(2)
                 }
 
    PowerOperStatus ::= INTEGER
                 {
                    normal(0),
                    abnormal(1),
                    null(2)
                 }
                 
    NewFanStat ::= INTEGER
                 {
                    abnormal(0),
                    full-speed(1),
                    half-speed(2),
                    null(3)
                  }

    --  textual conventions

      DisplayString ::= OCTET STRING
          --  This data type is used to model textual information taken
          --  from the NVT ASCII character set.  By convention, objects
          --  with this syntax are declared as having
          --
          --       SIZE (0..255)
 
    fan OBJECT IDENTIFIER ::= { zxr10 4998 }
    
    fanType OBJECT-TYPE
              SYNTAX  FanType
              MAX-ACCESS  read-only
              STATUS  current
              DESCRIPTION
                      "the description of fans type."
              ::= { fan 1 }

    power OBJECT IDENTIFIER ::= { zxr10 4999 }
    
    powerType OBJECT-TYPE
              SYNTAX  PowerType
              MAX-ACCESS  read-only
              STATUS  current
              DESCRIPTION
                      "the description of power type."
              ::= { power 1 }
 
    fanTable OBJECT-TYPE
    
              SYNTAX  SEQUENCE OF FansEntry
              MAX-ACCESS  not-accessible
              STATUS  current
              DESCRIPTION
                      "the description of fans infomation."
               ::= { zxr10 5000 }
               
    fansEntry  OBJECT-TYPE
              SYNTAX  FansEntry
              MAX-ACCESS  not-accessible
              STATUS  current
              DESCRIPTION
                      ""
              INDEX  { 
                        fanPosition
                     }
              ::= { fanTable 1 }
              
    FansEntry ::=
              SEQUENCE {
                fansPositon
                    FanPosition,
                fansNumber
                    INTEGER,
                fansStatOfFan1
                    FanStat,
                fansStatOfFan2
                    FanStat,
                fansStatOfFan3
                    FanStat,
                fansStatOfFan4
                    FanStat,
                fansStatOfFan5
                    FanStat,
                fansStatOfFan6
                    FanStat,
                fansStatOfFan7
                    FanStat,
                fansStatOfFan8
                    FanStat                                        
                    }
                    
   fansPositon  OBJECT-TYPE
              SYNTAX  FanPosition
              MAX-ACCESS  read-only
              STATUS  current
              DESCRIPTION
                      ""
              ::= { fansEntry 1 }              

   fansNumber  OBJECT-TYPE
              SYNTAX  INTEGER
              MAX-ACCESS  read-only
              STATUS  current
              DESCRIPTION
                      ""
              ::= { fansEntry 2 }  

   fansStatOfFan1  OBJECT-TYPE
              SYNTAX  FanStat
              MAX-ACCESS  read-only
              STATUS  current
              DESCRIPTION
                      ""
              ::= { fansEntry 3 }  
              
   fansStatOfFan2  OBJECT-TYPE
              SYNTAX  FanStat
              MAX-ACCESS  read-only
              STATUS  current
              DESCRIPTION
                      ""
              ::= { fansEntry 4 }  
              
   fansStatOfFan3  OBJECT-TYPE
              SYNTAX  FanStat
              MAX-ACCESS  read-only
              STATUS  current
              DESCRIPTION
                      ""
              ::= { fansEntry 5 }  
              
   fansStatOfFan4  OBJECT-TYPE
              SYNTAX  FanStat
              MAX-ACCESS  read-only
              STATUS  current
              DESCRIPTION
                      ""
              ::= { fansEntry 6 }  
              
   fansStatOfFan5  OBJECT-TYPE
              SYNTAX  FanStat
              MAX-ACCESS  read-only
              STATUS  current
              DESCRIPTION
                      ""
              ::= { fansEntry 7 }  
              
   fansStatOfFan6  OBJECT-TYPE
              SYNTAX  FanStat
              MAX-ACCESS  read-only
              STATUS  current
              DESCRIPTION
                      ""
              ::= { fansEntry 8 }  
              
   fansStatOfFan7  OBJECT-TYPE
              SYNTAX  FanStat
              MAX-ACCESS  read-only
              STATUS  current
              DESCRIPTION
                      ""
              ::= { fansEntry 9 }  
              
   fansStatOfFan8  OBJECT-TYPE
              SYNTAX  FanStat
              MAX-ACCESS  read-only
              STATUS  current
              DESCRIPTION
                      ""
              ::= { fansEntry 10 }  

    powerStatInfo OBJECT IDENTIFIER ::= { zxr10 5001 }
    
    powerStatACVoltage OBJECT-TYPE
              SYNTAX  DisplayString
              MAX-ACCESS  read-only
              STATUS  current
              DESCRIPTION
                      ""
              ::= { powerStatInfo 1 }              

    powerStatACCurrent OBJECT-TYPE
              SYNTAX  DisplayString
              MAX-ACCESS  read-only
              STATUS  current
              DESCRIPTION
                      ""
              ::= { powerStatInfo 2 }      

    powerStatDCVoltage OBJECT-TYPE
              SYNTAX  DisplayString
              MAX-ACCESS  read-only
              STATUS  current
              DESCRIPTION
                      ""
              ::= { powerStatInfo 3 } 
                   
    powerStatDCCurrent OBJECT-TYPE
              SYNTAX  DisplayString
              MAX-ACCESS  read-only
              STATUS  current
              DESCRIPTION
                      ""
              ::= { powerStatInfo 4 }
                    
    powerStatACError OBJECT-TYPE
              SYNTAX  DisplayString(SIZE(0..64))
              MAX-ACCESS  read-only
              STATUS  current
              DESCRIPTION
                      ""
              ::= { powerStatInfo 5 }    
              
    powerStatRectifyError OBJECT-TYPE
              SYNTAX  DisplayString(SIZE(0..64))
              MAX-ACCESS  read-only
              STATUS  current
              DESCRIPTION
                      ""
              ::= { powerStatInfo 6 }      

    powerStatMod1AvailStatus OBJECT-TYPE
              SYNTAX  PowerAvailStatus
              MAX-ACCESS  read-only
              STATUS  current
              DESCRIPTION
                      ""
              ::= { powerStatInfo 7 }

    powerStatMod2AvailStatus OBJECT-TYPE
              SYNTAX  PowerAvailStatus
              MAX-ACCESS  read-only
              STATUS  current
              DESCRIPTION
                      ""
              ::= { powerStatInfo 8 }

    powerStatMod3AvailStatus OBJECT-TYPE
              SYNTAX  PowerAvailStatus
              MAX-ACCESS  read-only
              STATUS  current
              DESCRIPTION
                      ""
              ::= { powerStatInfo 9 }

    powerStatMod1OperStatus OBJECT-TYPE
              SYNTAX  PowerOperStatus
              MAX-ACCESS  read-only
              STATUS  current
              DESCRIPTION
                      ""
              ::= { powerStatInfo 10 }

    powerStatMod2OperStatus OBJECT-TYPE
              SYNTAX  PowerOperStatus
              MAX-ACCESS  read-only
              STATUS  current
              DESCRIPTION
                      ""
              ::= { powerStatInfo 11 }

    powerStatMod3OperStatus OBJECT-TYPE
              SYNTAX  PowerOperStatus
              MAX-ACCESS  read-only
              STATUS  current
              DESCRIPTION
                      ""
              ::= { powerStatInfo 12 }

   newFanStatInfo OBJECT IDENTIFIER ::= { zxr10 5002 }
               
   newFanTopFanStatus  OBJECT-TYPE
              SYNTAX  NewFanStat
              MAX-ACCESS  read-only
              STATUS  current
              DESCRIPTION
                      ""
              ::= { newFanStatInfo 1 }

   newFanBottomFanStatus  OBJECT-TYPE
              SYNTAX  NewFanStat
              MAX-ACCESS  read-only
              STATUS  current
              DESCRIPTION
                      ""
              ::= { newFanStatInfo 2 }

    newPowerStatInfo OBJECT IDENTIFIER ::= { zxr10 5003 }
    
    newPowerStatMod1AvailStatus OBJECT-TYPE
              SYNTAX  PowerAvailStatus
              MAX-ACCESS  read-only
              STATUS  current
              DESCRIPTION
                      ""
              ::= { newPowerStatInfo 1 }

    newPowerStatMod2AvailStatus OBJECT-TYPE
              SYNTAX  PowerAvailStatus
              MAX-ACCESS  read-only
              STATUS  current
              DESCRIPTION
                      ""
              ::= { newPowerStatInfo 2 }

    newPowerStatMod3AvailStatus OBJECT-TYPE
              SYNTAX  PowerAvailStatus
              MAX-ACCESS  read-only
              STATUS  current
              DESCRIPTION
                      ""
              ::= { newPowerStatInfo 3 }

    newPowerStatMod1OperStatus OBJECT-TYPE
              SYNTAX  PowerOperStatus
              MAX-ACCESS  read-only
              STATUS  current
              DESCRIPTION
                      ""
              ::= { newPowerStatInfo 4 }

    newPowerStatMod2OperStatus OBJECT-TYPE
              SYNTAX  PowerOperStatus
              MAX-ACCESS  read-only
              STATUS  current
              DESCRIPTION
                      ""
              ::= { newPowerStatInfo 5 }

    newPowerStatMod3OperStatus OBJECT-TYPE
              SYNTAX  PowerOperStatus
              MAX-ACCESS  read-only
              STATUS  current
              DESCRIPTION
                      ""
              ::= { newPowerStatInfo 6 }
      
END
