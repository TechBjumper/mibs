PBDG-MIB DEFINITIONS ::= BEGIN
IMPORTS
   Counter
      FROM RFC1155-SMI
   OBJECT-TYPE
      FROM RFC-1212
   nas
      FROM PB-MIB;
pbdg OBJECT IDENTIFIER ::= { nas 14 }
pbdgDatagram OBJECT IDENTIFIER ::= { pbdg 1 }
pbdgDatagramTable OBJECT-TYPE
SYNTAX SEQUENCE OF PbdgDatagramEntry
ACCESS not-accessible
STATUS mandatory
DESCRIPTION
"A table containing configuration information for each NAC 
in the NAS chassis that supports packet bus datagrams."
::= { pbdgDatagram 1 }
pbdgDatagramEntry OBJECT-TYPE
SYNTAX PbdgDatagramEntry
ACCESS not-accessible
STATUS mandatory
DESCRIPTION
"There is one Configuration row for each Card in the NAS 
chassis that supports packet bus datagrams."
INDEX { pbdgDatagramIndex }
::= { pbdgDatagramTable 1 }
PbdgDatagramEntry ::=
SEQUENCE {
pbdgDatagramIndex
    INTEGER,
pbdgDatagramSentPkts
    Counter,
pbdgDatagramRcvdPkts
    Counter,
pbdgDatagramBusTimeOuts
    Counter,
pbdgDatagramErrorStatus
    INTEGER,
pbdgDatagramClockStatus
    INTEGER
}
pbdgDatagramIndex OBJECT-TYPE
SYNTAX INTEGER
ACCESS read-only
STATUS mandatory
DESCRIPTION
"A unique value for each card in the chassis. The value of 
this object matches the value of the index of the 
corresponding card's entry in the entity table of the 
chassis MIB."
::= { pbdgDatagramEntry 1 }
pbdgDatagramSentPkts OBJECT-TYPE
SYNTAX Counter
ACCESS read-only
STATUS mandatory
DESCRIPTION
"This object contains the number of packet bus datagrams 
sent by this entity."
::= { pbdgDatagramEntry 2 }
pbdgDatagramRcvdPkts OBJECT-TYPE
SYNTAX Counter
ACCESS read-only
STATUS mandatory
DESCRIPTION
"This object contains the number of packet bus datagrams 
received by this entity."
::= { pbdgDatagramEntry 3 }
pbdgDatagramBusTimeOuts OBJECT-TYPE
SYNTAX Counter
ACCESS read-only
STATUS mandatory
DESCRIPTION
"This object contains the number of packet bus timeouts 
experienced by this entity."
::= { pbdgDatagramEntry 4 }
pbdgDatagramErrorStatus OBJECT-TYPE
SYNTAX INTEGER{
  noError(1),
  invalidParm(2),
  socketNotOpened(3),
  noMoreSocket(4),
  ackWaitTimeout(9),
  hwNakRcvd(10),
  otherBusError(11),
  noMemory(14),
  nullPointer(15),
  notInitialized(17),
  failedToRecv(18),
  invalidMsgType(19),
  socketClosed(22),
  noResponse(27),
  noDataToTx(29),
  txPreAck(30),
  txTardyAck(31),
  txBusTimeOut(32),
  rxBusTimeOut(33),
  txTAL(34),
  rxTAL(35),
  txMasterTimeOut(36),
  clkVanished(37),
  clkReturned(38),
  shutdown(39),
  frameError(40),
  xIDTimeOut(41),
  invalidAckMeRtnMarker(45),
  invalidFragmentOffset(46),
  maxRxMsgLengthExceeded(47)
}
ACCESS read-only
STATUS mandatory
DESCRIPTION
"This object reflects the current error status of this 
entity."
::= { pbdgDatagramEntry 5 }
pbdgDatagramClockStatus OBJECT-TYPE
SYNTAX INTEGER{
  notSupported(1),
  clockMaster(2),
  clockSlave(3),
  noClockPresent(4)
}
ACCESS read-only
STATUS mandatory
DESCRIPTION
"This object defines the current status of the packet bus 
clock."
::= { pbdgDatagramEntry 6 }
pbdgCfg OBJECT IDENTIFIER ::= { pbdg 2 }
pbdgCfgTable OBJECT-TYPE
SYNTAX SEQUENCE OF PbdgCfgEntry
ACCESS not-accessible
STATUS mandatory
DESCRIPTION
"A table containing configuration information for each NAC 
in the NAS chassis that supports packet bus datagrams."
::= { pbdgCfg 1 }
pbdgCfgEntry OBJECT-TYPE
SYNTAX PbdgCfgEntry
ACCESS not-accessible
STATUS mandatory
DESCRIPTION
"There is one Configuration row for each Card in the NAS 
chassis that supports packet bus datagrams."
INDEX { pbdgCfgIndex }
::= { pbdgCfgTable 1 }
PbdgCfgEntry ::=
SEQUENCE {
pbdgCfgIndex
    INTEGER,
pbdgCfgMasterClock
    INTEGER,
pbdgCfgClockLossEvent
    INTEGER,
pbdgCfgClockRestoreEvent
    INTEGER
}
pbdgCfgIndex OBJECT-TYPE
SYNTAX INTEGER
ACCESS read-only
STATUS mandatory
DESCRIPTION
"A unique value for each card in the chassis.  The value of 
this object matches the value of the index of the 
corresponding card's entry in the entity table of the 
chassis"
::= { pbdgCfgEntry 1 }
pbdgCfgMasterClock OBJECT-TYPE
SYNTAX INTEGER{
  notSupported(1),
  enable(2),
  disable(3)
}
ACCESS read-write
STATUS mandatory
DESCRIPTION
"This object is used to disable the ability for a NAC to act 
as packet bus clock master.Default =enable(2)."
::= { pbdgCfgEntry 2 }
pbdgCfgClockLossEvent OBJECT-TYPE
SYNTAX INTEGER{
  enableTrap(1),
  disableAll(2),
  enableLog(3),
  enableAll(4)
}
ACCESS read-write
STATUS mandatory
DESCRIPTION
"This object is used to disable the ability for a NAC to 
report when the packet bus clock has been lost.  Default = 
disableAll(2)."
::= { pbdgCfgEntry 3 }
pbdgCfgClockRestoreEvent OBJECT-TYPE
SYNTAX INTEGER{
  enableTrap(1),
  disableAll(2),
  enableLog(3),
  enableAll(4)
}
ACCESS read-write
STATUS mandatory
DESCRIPTION
"This object is used to disable the ability for a NAC to 
report when the packet bus clock has been restored.  
Default = disableAll(2)."
::= { pbdgCfgEntry 4 }
END
