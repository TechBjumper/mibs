-- file automatically created


TELDAT-TRAP-SRT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


srtTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SRT event subsystem."
    REVISION "201401200930Z"
    DESCRIPTION "Initial implementation"
        ::= { telEventTraps 72 }


srtEventsGroup	OBJECT IDENTIFIER	::= { srtTrapsMIB 1 }

srtNotifications	OBJECT IDENTIFIER	::= { srtTrapsMIB 2 }
srtNotificationsPrefix	OBJECT IDENTIFIER	::= { srtNotifications 0 }

srtEventObjects1 OBJECT-IDENTITY
    STATUS current
    DESCRIPTION
        "Event SRT.1
        No buffer available to copy a frame in order to send a bridged frame on
        multiple interfaces. Bridged packets are sent on multiple interfaces
        either for multicast destination addresses, or in the case of
        certain static entries. No copy of this frame will be sent on
        the specified port and interface."
    ::= { srtEventsGroup 1 }

srt1-source-mac OBJECT-TYPE
    SYNTAX DisplayString
    MAX-ACCESS accessible-for-notify
    STATUS current
    DESCRIPTION
        "Parameter 'source-mac' in event SRT.1"
    ::= { srtEventObjects1 1 }

srt1-dest-mac OBJECT-TYPE
    SYNTAX DisplayString
    MAX-ACCESS accessible-for-notify
    STATUS current
    DESCRIPTION
        "Parameter 'dest-mac' in event SRT.1"
    ::= { srtEventObjects1 2 }

srt1-port OBJECT-TYPE
    SYNTAX Integer32
    MAX-ACCESS accessible-for-notify
    STATUS current
    DESCRIPTION
        "Parameter 'port' in event SRT.1"
    ::= { srtEventObjects1 3 }

srt1-interface OBJECT-TYPE
    SYNTAX DisplayString
    MAX-ACCESS accessible-for-notify
    STATUS current
    DESCRIPTION
        "Parameter 'interface' in event SRT.1"
    ::= { srtEventObjects1 4 }

srt1-circuit-name OBJECT-TYPE
    SYNTAX DisplayString
    MAX-ACCESS accessible-for-notify
    STATUS current
    DESCRIPTION
        "Parameter 'circuit-name' in event SRT.1"
    ::= { srtEventObjects1 5 }

srtEventObjects2 OBJECT-IDENTITY
    STATUS current
    DESCRIPTION
        "Event SRT.2
        The Spanning Tree Protocol requested setting this network into
        Learning state, but the command to the device failed. The error-code is
        a device-specific error code that may indicate what the error is."
    ::= { srtEventsGroup 2 }

srt2-error-code OBJECT-TYPE
    SYNTAX Integer32
    MAX-ACCESS accessible-for-notify
    STATUS current
    DESCRIPTION
        "Parameter 'error-code' in event SRT.2"
    ::= { srtEventObjects2 1 }

srt2-interface OBJECT-TYPE
    SYNTAX DisplayString
    MAX-ACCESS accessible-for-notify
    STATUS current
    DESCRIPTION
        "Parameter 'interface' in event SRT.2"
    ::= { srtEventObjects2 2 }

srt2-circuit-name OBJECT-TYPE
    SYNTAX DisplayString
    MAX-ACCESS accessible-for-notify
    STATUS current
    DESCRIPTION
        "Parameter 'circuit-name' in event SRT.2"
    ::= { srtEventObjects2 3 }

srtEventObjects3 OBJECT-IDENTITY
    STATUS current
    DESCRIPTION
        "Event SRT.3
        An attempt to add a set of static entries to the internal database of
        a bridging interface having internal filtering failed.
        The error-code is a device-specific error code that may indicate
        what the error is."
    ::= { srtEventsGroup 3 }

srt3-error-code OBJECT-TYPE
    SYNTAX Integer32
    MAX-ACCESS accessible-for-notify
    STATUS current
    DESCRIPTION
        "Parameter 'error-code' in event SRT.3"
    ::= { srtEventObjects3 1 }

srt3-interface OBJECT-TYPE
    SYNTAX DisplayString
    MAX-ACCESS accessible-for-notify
    STATUS current
    DESCRIPTION
        "Parameter 'interface' in event SRT.3"
    ::= { srtEventObjects3 2 }

srt3-circuit-name OBJECT-TYPE
    SYNTAX DisplayString
    MAX-ACCESS accessible-for-notify
    STATUS current
    DESCRIPTION
        "Parameter 'circuit-name' in event SRT.3"
    ::= { srtEventObjects3 3 }

srtEventObjects4 OBJECT-IDENTITY
    STATUS current
    DESCRIPTION
        "Event SRT.4
        No buffer was available to send a command to the device.
        The possible command names are
        'D-CNFGSRB' (configure source-routing bridging),
        'SRT-ON' (promiscuous on),
        'SRT-INFORM' (learn capabilities of device),
        'SRT-SET-AGE' (set age for filtering database in device),
        'SRT-DECR-AGE' (do ageing pass on filtering database in device),
        'SRT-ADD-ENTRY' (add static entry),
        'SRT-DEL-ENTRY' (delete entry, from console),
        'SRT-SEARCH-ENTRY' (search for particular entry, from console) and
        'SRT-LIST-ENTRY' (list contents of learning database in card).
        For commands 'D-CNFGSRB' and 'SRT-ON' the result will be that
        the interface may remain in the wrong state. A failure on 'SRT-INFORM'
        could cause serious problems. For other commands the results will be
        less serious."
    ::= { srtEventsGroup 4 }

srt4-command-name OBJECT-TYPE
    SYNTAX DisplayString
    MAX-ACCESS accessible-for-notify
    STATUS current
    DESCRIPTION
        "Parameter 'command-name' in event SRT.4"
    ::= { srtEventObjects4 1 }

srt4-interface OBJECT-TYPE
    SYNTAX DisplayString
    MAX-ACCESS accessible-for-notify
    STATUS current
    DESCRIPTION
        "Parameter 'interface' in event SRT.4"
    ::= { srtEventObjects4 2 }

srtEventObjects5 OBJECT-IDENTITY
    STATUS current
    DESCRIPTION
        "Event SRT.5
        The sending of a packet being forwarded failed. The reason is
        the internal error code for the failure."
    ::= { srtEventsGroup 5 }

srt5-source-mac OBJECT-TYPE
    SYNTAX DisplayString
    MAX-ACCESS accessible-for-notify
    STATUS current
    DESCRIPTION
        "Parameter 'source-mac' in event SRT.5"
    ::= { srtEventObjects5 1 }

srt5-dest-mac OBJECT-TYPE
    SYNTAX DisplayString
    MAX-ACCESS accessible-for-notify
    STATUS current
    DESCRIPTION
        "Parameter 'dest-mac' in event SRT.5"
    ::= { srtEventObjects5 2 }

srt5-reason-code OBJECT-TYPE
    SYNTAX Integer32
    MAX-ACCESS accessible-for-notify
    STATUS current
    DESCRIPTION
        "Parameter 'reason-code' in event SRT.5"
    ::= { srtEventObjects5 3 }

srt5-port OBJECT-TYPE
    SYNTAX Integer32
    MAX-ACCESS accessible-for-notify
    STATUS current
    DESCRIPTION
        "Parameter 'port' in event SRT.5"
    ::= { srtEventObjects5 4 }

srt5-interface-name OBJECT-TYPE
    SYNTAX DisplayString
    MAX-ACCESS accessible-for-notify
    STATUS current
    DESCRIPTION
        "Parameter 'interface-name' in event SRT.5"
    ::= { srtEventObjects5 5 }

srt5-circuit-name OBJECT-TYPE
    SYNTAX DisplayString
    MAX-ACCESS accessible-for-notify
    STATUS current
    DESCRIPTION
        "Parameter 'circuit-name' in event SRT.5"
    ::= { srtEventObjects5 6 }

srtEventObjects6 OBJECT-IDENTITY
    STATUS current
    DESCRIPTION
        "Event SRT.6
        The input queue for frames to be forwarded is too long, and this frame
        has been dropped to attempt to alleviate the congestion."
    ::= { srtEventsGroup 6 }

srt6-source-mac OBJECT-TYPE
    SYNTAX DisplayString
    MAX-ACCESS accessible-for-notify
    STATUS current
    DESCRIPTION
        "Parameter 'source-mac' in event SRT.6"
    ::= { srtEventObjects6 1 }

srt6-dest-mac OBJECT-TYPE
    SYNTAX DisplayString
    MAX-ACCESS accessible-for-notify
    STATUS current
    DESCRIPTION
        "Parameter 'dest-mac' in event SRT.6"
    ::= { srtEventObjects6 2 }

srt6-interface OBJECT-TYPE
    SYNTAX DisplayString
    MAX-ACCESS accessible-for-notify
    STATUS current
    DESCRIPTION
        "Parameter 'interface' in event SRT.6"
    ::= { srtEventObjects6 3 }

srt6-circuit-name OBJECT-TYPE
    SYNTAX DisplayString
    MAX-ACCESS accessible-for-notify
    STATUS current
    DESCRIPTION
        "Parameter 'circuit-name' in event SRT.6"
    ::= { srtEventObjects6 4 }

srtEventObjects7 OBJECT-IDENTITY
    STATUS current
    DESCRIPTION
        "Event SRT.7
        The input queue for Spanning Tree Protocol Bridge Protocl Data Units
        is too long, and this frame has been dropped to attempt to alleviate
        the congestion."
    ::= { srtEventsGroup 7 }

srt7-source-mac OBJECT-TYPE
    SYNTAX DisplayString
    MAX-ACCESS accessible-for-notify
    STATUS current
    DESCRIPTION
        "Parameter 'source-mac' in event SRT.7"
    ::= { srtEventObjects7 1 }

srt7-interface OBJECT-TYPE
    SYNTAX DisplayString
    MAX-ACCESS accessible-for-notify
    STATUS current
    DESCRIPTION
        "Parameter 'interface' in event SRT.7"
    ::= { srtEventObjects7 2 }

srt7-circuit-name OBJECT-TYPE
    SYNTAX DisplayString
    MAX-ACCESS accessible-for-notify
    STATUS current
    DESCRIPTION
        "Parameter 'circuit-name' in event SRT.7"
    ::= { srtEventObjects7 3 }

srtEventObjects8 OBJECT-IDENTITY
    STATUS current
    DESCRIPTION
        "Event SRT.8
        The specified frame is too large to send on this outgoing port and
        interface. The reformatted-length is the size of the frame including
        MAC headers after any mapping of data link headers."
    ::= { srtEventsGroup 8 }

srt8-source-mac OBJECT-TYPE
    SYNTAX DisplayString
    MAX-ACCESS accessible-for-notify
    STATUS current
    DESCRIPTION
        "Parameter 'source-mac' in event SRT.8"
    ::= { srtEventObjects8 1 }

srt8-dest-mac OBJECT-TYPE
    SYNTAX DisplayString
    MAX-ACCESS accessible-for-notify
    STATUS current
    DESCRIPTION
        "Parameter 'dest-mac' in event SRT.8"
    ::= { srtEventObjects8 2 }

srt8-reformatted-length OBJECT-TYPE
    SYNTAX Integer32
    MAX-ACCESS accessible-for-notify
    STATUS current
    DESCRIPTION
        "Parameter 'reformatted-length' in event SRT.8"
    ::= { srtEventObjects8 3 }

srt8-output-maximum OBJECT-TYPE
    SYNTAX Integer32
    MAX-ACCESS accessible-for-notify
    STATUS current
    DESCRIPTION
        "Parameter 'output-maximum' in event SRT.8"
    ::= { srtEventObjects8 4 }

srt8-port OBJECT-TYPE
    SYNTAX Integer32
    MAX-ACCESS accessible-for-notify
    STATUS current
    DESCRIPTION
        "Parameter 'port' in event SRT.8"
    ::= { srtEventObjects8 5 }

srt8-interface OBJECT-TYPE
    SYNTAX DisplayString
    MAX-ACCESS accessible-for-notify
    STATUS current
    DESCRIPTION
        "Parameter 'interface' in event SRT.8"
    ::= { srtEventObjects8 6 }

srt8-circuit-name OBJECT-TYPE
    SYNTAX DisplayString
    MAX-ACCESS accessible-for-notify
    STATUS current
    DESCRIPTION
        "Parameter 'circuit-name' in event SRT.8"
    ::= { srtEventObjects8 7 }

srtEventObjects9 OBJECT-IDENTITY
    STATUS current
    DESCRIPTION
        "Event SRT.9
        A frame has been received for bridging on an interface that is down.
        It will be ignored."
    ::= { srtEventsGroup 9 }

srt9-source-mac OBJECT-TYPE
    SYNTAX DisplayString
    MAX-ACCESS accessible-for-notify
    STATUS current
    DESCRIPTION
        "Parameter 'source-mac' in event SRT.9"
    ::= { srtEventObjects9 1 }

srt9-dest-mac OBJECT-TYPE
    SYNTAX DisplayString
    MAX-ACCESS accessible-for-notify
    STATUS current
    DESCRIPTION
        "Parameter 'dest-mac' in event SRT.9"
    ::= { srtEventObjects9 2 }

srt9-interface OBJECT-TYPE
    SYNTAX DisplayString
    MAX-ACCESS accessible-for-notify
    STATUS current
    DESCRIPTION
        "Parameter 'interface' in event SRT.9"
    ::= { srtEventObjects9 3 }

srtEventObjects10 OBJECT-IDENTITY
    STATUS current
    DESCRIPTION
        "Event SRT.10
        A MAC frame has been received by the hardware, but is being dropped
        because the source MAC address is being administratively filtered
        by the bridge. The frame will be dropped."
    ::= { srtEventsGroup 10 }

srt10-source-mac OBJECT-TYPE
    SYNTAX DisplayString
    MAX-ACCESS accessible-for-notify
    STATUS current
    DESCRIPTION
        "Parameter 'source-mac' in event SRT.10"
    ::= { srtEventObjects10 1 }

srt10-dest-mac OBJECT-TYPE
    SYNTAX DisplayString
    MAX-ACCESS accessible-for-notify
    STATUS current
    DESCRIPTION
        "Parameter 'dest-mac' in event SRT.10"
    ::= { srtEventObjects10 2 }

srt10-port OBJECT-TYPE
    SYNTAX Integer32
    MAX-ACCESS accessible-for-notify
    STATUS current
    DESCRIPTION
        "Parameter 'port' in event SRT.10"
    ::= { srtEventObjects10 3 }

srt10-interface OBJECT-TYPE
    SYNTAX DisplayString
    MAX-ACCESS accessible-for-notify
    STATUS current
    DESCRIPTION
        "Parameter 'interface' in event SRT.10"
    ::= { srtEventObjects10 4 }

srt10-circuit-name OBJECT-TYPE
    SYNTAX DisplayString
    MAX-ACCESS accessible-for-notify
    STATUS current
    DESCRIPTION
        "Parameter 'circuit-name' in event SRT.10"
    ::= { srtEventObjects10 5 }

srtEventObjects11 OBJECT-IDENTITY
    STATUS current
    DESCRIPTION
        "Event SRT.11
        A MAC frame was received on a port that is still only in 'learning'
        state. Frames are only bridged when the input port is in 'forwarding'
        state. While the port is still in 'learning' state, they are only
        processed to learn the source addresses for the filtering database.
        The frame will not be bridged."
    ::= { srtEventsGroup 11 }

srt11-source-mac OBJECT-TYPE
    SYNTAX DisplayString
    MAX-ACCESS accessible-for-notify
    STATUS current
    DESCRIPTION
        "Parameter 'source-mac' in event SRT.11"
    ::= { srtEventObjects11 1 }

srt11-dest-mac OBJECT-TYPE
    SYNTAX DisplayString
    MAX-ACCESS accessible-for-notify
    STATUS current
    DESCRIPTION
        "Parameter 'dest-mac' in event SRT.11"
    ::= { srtEventObjects11 2 }

srt11-port OBJECT-TYPE
    SYNTAX Integer32
    MAX-ACCESS accessible-for-notify
    STATUS current
    DESCRIPTION
        "Parameter 'port' in event SRT.11"
    ::= { srtEventObjects11 3 }

srt11-interface OBJECT-TYPE
    SYNTAX DisplayString
    MAX-ACCESS accessible-for-notify
    STATUS current
    DESCRIPTION
        "Parameter 'interface' in event SRT.11"
    ::= { srtEventObjects11 4 }

srt11-circuit-name OBJECT-TYPE
    SYNTAX DisplayString
    MAX-ACCESS accessible-for-notify
    STATUS current
    DESCRIPTION
        "Parameter 'circuit-name' in event SRT.11"
    ::= { srtEventObjects11 5 }

srtEventObjects12 OBJECT-IDENTITY
    STATUS current
    DESCRIPTION
        "Event SRT.12
        A MAC frame was being bridged, but the destination port was not
        in 'forwarding' state. It will not be sent on that port."
    ::= { srtEventsGroup 12 }

srt12-source-mac OBJECT-TYPE
    SYNTAX DisplayString
    MAX-ACCESS accessible-for-notify
    STATUS current
    DESCRIPTION
        "Parameter 'source-mac' in event SRT.12"
    ::= { srtEventObjects12 1 }

srt12-dest-mac OBJECT-TYPE
    SYNTAX DisplayString
    MAX-ACCESS accessible-for-notify
    STATUS current
    DESCRIPTION
        "Parameter 'dest-mac' in event SRT.12"
    ::= { srtEventObjects12 2 }

srt12-port OBJECT-TYPE
    SYNTAX Integer32
    MAX-ACCESS accessible-for-notify
    STATUS current
    DESCRIPTION
        "Parameter 'port' in event SRT.12"
    ::= { srtEventObjects12 3 }

srt12-interface OBJECT-TYPE
    SYNTAX DisplayString
    MAX-ACCESS accessible-for-notify
    STATUS current
    DESCRIPTION
        "Parameter 'interface' in event SRT.12"
    ::= { srtEventObjects12 4 }

srt12-circuit-name OBJECT-TYPE
    SYNTAX DisplayString
    MAX-ACCESS accessible-for-notify
    STATUS current
    DESCRIPTION
        "Parameter 'circuit-name' in event SRT.12"
    ::= { srtEventObjects12 5 }

srtEventObjects13 OBJECT-IDENTITY
    STATUS current
    DESCRIPTION
        "Event SRT.13
        A MAC frame has been received whose destination address is known to be
        on the same side of the bridge as the packet came from. It is dropped
        by the filtering logic since it does not need to be bridged."
    ::= { srtEventsGroup 13 }

srt13-source-mac OBJECT-TYPE
    SYNTAX DisplayString
    MAX-ACCESS accessible-for-notify
    STATUS current
    DESCRIPTION
        "Parameter 'source-mac' in event SRT.13"
    ::= { srtEventObjects13 1 }

srt13-dest-mac OBJECT-TYPE
    SYNTAX DisplayString
    MAX-ACCESS accessible-for-notify
    STATUS current
    DESCRIPTION
        "Parameter 'dest-mac' in event SRT.13"
    ::= { srtEventObjects13 2 }

srt13-port OBJECT-TYPE
    SYNTAX Integer32
    MAX-ACCESS accessible-for-notify
    STATUS current
    DESCRIPTION
        "Parameter 'port' in event SRT.13"
    ::= { srtEventObjects13 3 }

srt13-interface OBJECT-TYPE
    SYNTAX DisplayString
    MAX-ACCESS accessible-for-notify
    STATUS current
    DESCRIPTION
        "Parameter 'interface' in event SRT.13"
    ::= { srtEventObjects13 4 }

srt13-circuit-name OBJECT-TYPE
    SYNTAX DisplayString
    MAX-ACCESS accessible-for-notify
    STATUS current
    DESCRIPTION
        "Parameter 'circuit-name' in event SRT.13"
    ::= { srtEventObjects13 5 }

srtEventObjects14 OBJECT-IDENTITY
    STATUS current
    DESCRIPTION
        "Event SRT.14
        A frame being bridged was destined for a port which is not running
        transparent bridging, or not in 'forwarding' state for transparent
        bridging."
    ::= { srtEventsGroup 14 }

srt14-source-mac OBJECT-TYPE
    SYNTAX DisplayString
    MAX-ACCESS accessible-for-notify
    STATUS current
    DESCRIPTION
        "Parameter 'source-mac' in event SRT.14"
    ::= { srtEventObjects14 1 }

srt14-dest-mac OBJECT-TYPE
    SYNTAX DisplayString
    MAX-ACCESS accessible-for-notify
    STATUS current
    DESCRIPTION
        "Parameter 'dest-mac' in event SRT.14"
    ::= { srtEventObjects14 2 }

srt14-port OBJECT-TYPE
    SYNTAX Integer32
    MAX-ACCESS accessible-for-notify
    STATUS current
    DESCRIPTION
        "Parameter 'port' in event SRT.14"
    ::= { srtEventObjects14 3 }

srt14-interface OBJECT-TYPE
    SYNTAX DisplayString
    MAX-ACCESS accessible-for-notify
    STATUS current
    DESCRIPTION
        "Parameter 'interface' in event SRT.14"
    ::= { srtEventObjects14 4 }

srt14-circuit-name OBJECT-TYPE
    SYNTAX DisplayString
    MAX-ACCESS accessible-for-notify
    STATUS current
    DESCRIPTION
        "Parameter 'circuit-name' in event SRT.14"
    ::= { srtEventObjects14 5 }

srtEventObjects15 OBJECT-IDENTITY
    STATUS current
    DESCRIPTION
        "Event SRT.15
        A frame is being bridged between these two interfaces. The destination
        address was known, so it was sent only to the correct destination
        network."
    ::= { srtEventsGroup 15 }

srt15-source-mac OBJECT-TYPE
    SYNTAX DisplayString
    MAX-ACCESS accessible-for-notify
    STATUS current
    DESCRIPTION
        "Parameter 'source-mac' in event SRT.15"
    ::= { srtEventObjects15 1 }

srt15-dest-mac OBJECT-TYPE
    SYNTAX DisplayString
    MAX-ACCESS accessible-for-notify
    STATUS current
    DESCRIPTION
        "Parameter 'dest-mac' in event SRT.15"
    ::= { srtEventObjects15 2 }

srt15-port OBJECT-TYPE
    SYNTAX Integer32
    MAX-ACCESS accessible-for-notify
    STATUS current
    DESCRIPTION
        "Parameter 'port' in event SRT.15"
    ::= { srtEventObjects15 3 }

srt15-interface OBJECT-TYPE
    SYNTAX DisplayString
    MAX-ACCESS accessible-for-notify
    STATUS current
    DESCRIPTION
        "Parameter 'interface' in event SRT.15"
    ::= { srtEventObjects15 4 }

srt15-circuit-name OBJECT-TYPE
    SYNTAX DisplayString
    MAX-ACCESS accessible-for-notify
    STATUS current
    DESCRIPTION
        "Parameter 'circuit-name' in event SRT.15"
    ::= { srtEventObjects15 5 }

srt15-out-port OBJECT-TYPE
    SYNTAX Integer32
    MAX-ACCESS accessible-for-notify
    STATUS current
    DESCRIPTION
        "Parameter 'out-port' in event SRT.15"
    ::= { srtEventObjects15 6 }

srt15-out-interface OBJECT-TYPE
    SYNTAX DisplayString
    MAX-ACCESS accessible-for-notify
    STATUS current
    DESCRIPTION
        "Parameter 'out-interface' in event SRT.15"
    ::= { srtEventObjects15 7 }

srt15-out-circuit-name OBJECT-TYPE
    SYNTAX DisplayString
    MAX-ACCESS accessible-for-notify
    STATUS current
    DESCRIPTION
        "Parameter 'out-circuit-name' in event SRT.15"
    ::= { srtEventObjects15 8 }

srtEventObjects16 OBJECT-IDENTITY
    STATUS current
    DESCRIPTION
        "Event SRT.16
        A frame is being transparently bridged to all active transparent
        bridging ports. This happens when the frame destination is a multicast,
        when the frame destination is not in the learning database, or when
        required by static entries in the learning database.
        There will be one message for each port the frame is sent on."
    ::= { srtEventsGroup 16 }

srt16-source-mac OBJECT-TYPE
    SYNTAX DisplayString
    MAX-ACCESS accessible-for-notify
    STATUS current
    DESCRIPTION
        "Parameter 'source-mac' in event SRT.16"
    ::= { srtEventObjects16 1 }

srt16-dest-mac OBJECT-TYPE
    SYNTAX DisplayString
    MAX-ACCESS accessible-for-notify
    STATUS current
    DESCRIPTION
        "Parameter 'dest-mac' in event SRT.16"
    ::= { srtEventObjects16 2 }

srt16-port OBJECT-TYPE
    SYNTAX Integer32
    MAX-ACCESS accessible-for-notify
    STATUS current
    DESCRIPTION
        "Parameter 'port' in event SRT.16"
    ::= { srtEventObjects16 3 }

srt16-interface OBJECT-TYPE
    SYNTAX DisplayString
    MAX-ACCESS accessible-for-notify
    STATUS current
    DESCRIPTION
        "Parameter 'interface' in event SRT.16"
    ::= { srtEventObjects16 4 }

srt16-circuit-name OBJECT-TYPE
    SYNTAX DisplayString
    MAX-ACCESS accessible-for-notify
    STATUS current
    DESCRIPTION
        "Parameter 'circuit-name' in event SRT.16"
    ::= { srtEventObjects16 5 }

srt16-out-port OBJECT-TYPE
    SYNTAX Integer32
    MAX-ACCESS accessible-for-notify
    STATUS current
    DESCRIPTION
        "Parameter 'out-port' in event SRT.16"
    ::= { srtEventObjects16 6 }

srt16-out-interface OBJECT-TYPE
    SYNTAX DisplayString
    MAX-ACCESS accessible-for-notify
    STATUS current
    DESCRIPTION
        "Parameter 'out-interface' in event SRT.16"
    ::= { srtEventObjects16 7 }

srt16-out-circuit-name OBJECT-TYPE
    SYNTAX DisplayString
    MAX-ACCESS accessible-for-notify
    STATUS current
    DESCRIPTION
        "Parameter 'out-circuit-name' in event SRT.16"
    ::= { srtEventObjects16 8 }

srtEventObjects17 OBJECT-IDENTITY
    STATUS current
    DESCRIPTION
        "Event SRT.17
        The SRT forwarder is starting the process of enabling bridging
        on the specified interface. This starts when the interface comes up
        from a self-test."
    ::= { srtEventsGroup 17 }

srt17-port OBJECT-TYPE
    SYNTAX Integer32
    MAX-ACCESS accessible-for-notify
    STATUS current
    DESCRIPTION
        "Parameter 'port' in event SRT.17"
    ::= { srtEventObjects17 1 }

srt17-interface OBJECT-TYPE
    SYNTAX DisplayString
    MAX-ACCESS accessible-for-notify
    STATUS current
    DESCRIPTION
        "Parameter 'interface' in event SRT.17"
    ::= { srtEventObjects17 2 }

srt17-circuit-name OBJECT-TYPE
    SYNTAX DisplayString
    MAX-ACCESS accessible-for-notify
    STATUS current
    DESCRIPTION
        "Parameter 'circuit-name' in event SRT.17"
    ::= { srtEventObjects17 3 }

srtEventObjects18 OBJECT-IDENTITY
    STATUS current
    DESCRIPTION
        "Event SRT.18
        The SRT forwarder has completed the process of enabling bridging
        on the specified interface. It will now enter 'blocking' state."
    ::= { srtEventsGroup 18 }

srt18-port OBJECT-TYPE
    SYNTAX Integer32
    MAX-ACCESS accessible-for-notify
    STATUS current
    DESCRIPTION
        "Parameter 'port' in event SRT.18"
    ::= { srtEventObjects18 1 }

srt18-interface OBJECT-TYPE
    SYNTAX DisplayString
    MAX-ACCESS accessible-for-notify
    STATUS current
    DESCRIPTION
        "Parameter 'interface' in event SRT.18"
    ::= { srtEventObjects18 2 }

srt18-circuit-name OBJECT-TYPE
    SYNTAX DisplayString
    MAX-ACCESS accessible-for-notify
    STATUS current
    DESCRIPTION
        "Parameter 'circuit-name' in event SRT.18"
    ::= { srtEventObjects18 3 }

srtEventObjects19 OBJECT-IDENTITY
    STATUS current
    DESCRIPTION
        "Event SRT.19
        The SRT forwarder had been enabled on a type of interface it does not
        support."
    ::= { srtEventsGroup 19 }

srt19-interface-name OBJECT-TYPE
    SYNTAX DisplayString
    MAX-ACCESS accessible-for-notify
    STATUS current
    DESCRIPTION
        "Parameter 'interface-name' in event SRT.19"
    ::= { srtEventObjects19 1 }

srtEventObjects20 OBJECT-IDENTITY
    STATUS current
    DESCRIPTION
        "Event SRT.20
        The user has configured the bridge to autoconfigure the bridge address
        based on the MAC address of the lowest number port. However, the lowest
        numbered port is of a type that does not have a MAC address, such as
        a serial line."
    ::= { srtEventsGroup 20 }

srt20-port OBJECT-TYPE
    SYNTAX Integer32
    MAX-ACCESS accessible-for-notify
    STATUS current
    DESCRIPTION
        "Parameter 'port' in event SRT.20"
    ::= { srtEventObjects20 1 }

srt20-interface OBJECT-TYPE
    SYNTAX DisplayString
    MAX-ACCESS accessible-for-notify
    STATUS current
    DESCRIPTION
        "Parameter 'interface' in event SRT.20"
    ::= { srtEventObjects20 2 }

srt20-circuit-name OBJECT-TYPE
    SYNTAX DisplayString
    MAX-ACCESS accessible-for-notify
    STATUS current
    DESCRIPTION
        "Parameter 'circuit-name' in event SRT.20"
    ::= { srtEventObjects20 3 }

srtEventObjects21 OBJECT-IDENTITY
    STATUS current
    DESCRIPTION
        "Event SRT.21
        Bridge frame received, but there is no bridging available in this load.
        The frame will be ignored."
    ::= { srtEventsGroup 21 }

srt21-source-mac OBJECT-TYPE
    SYNTAX DisplayString
    MAX-ACCESS accessible-for-notify
    STATUS current
    DESCRIPTION
        "Parameter 'source-mac' in event SRT.21"
    ::= { srtEventObjects21 1 }

srt21-dest-mac OBJECT-TYPE
    SYNTAX DisplayString
    MAX-ACCESS accessible-for-notify
    STATUS current
    DESCRIPTION
        "Parameter 'dest-mac' in event SRT.21"
    ::= { srtEventObjects21 2 }

srt21-interface OBJECT-TYPE
    SYNTAX DisplayString
    MAX-ACCESS accessible-for-notify
    STATUS current
    DESCRIPTION
        "Parameter 'interface' in event SRT.21"
    ::= { srtEventObjects21 3 }

srtEventObjects23 OBJECT-IDENTITY
    STATUS current
    DESCRIPTION
        "Event SRT.23
        The port has been configured to use an interface that has not been
        configured with the Config> ADD DEVICE command.
        This port of the bridge will be disabled."
    ::= { srtEventsGroup 23 }

srt23-port OBJECT-TYPE
    SYNTAX Integer32
    MAX-ACCESS accessible-for-notify
    STATUS current
    DESCRIPTION
        "Parameter 'port' in event SRT.23"
    ::= { srtEventObjects23 1 }

srt23-interface-number OBJECT-TYPE
    SYNTAX Integer32
    MAX-ACCESS accessible-for-notify
    STATUS current
    DESCRIPTION
        "Parameter 'interface-number' in event SRT.23"
    ::= { srtEventObjects23 2 }

srtEventObjects24 OBJECT-IDENTITY
    STATUS current
    DESCRIPTION
        "Event SRT.24
        Less than two (valid) ports have been configured on the bridge.
        There must be at least two ports."
    ::= { srtEventsGroup 24 }

srt24-existent-port-count OBJECT-TYPE
    SYNTAX Integer32
    MAX-ACCESS accessible-for-notify
    STATUS current
    DESCRIPTION
        "Parameter 'existent-port-count' in event SRT.24"
    ::= { srtEventObjects24 1 }

srtEventObjects25 OBJECT-IDENTITY
    STATUS current
    DESCRIPTION
        "Event SRT.25
        There is not enough free memory to allocate even a minimal size
        filtering database. The bridge will be disabled.
        The bridge starts by trying to allocate requested-size bytes, and then
        tries with progressively smaller sizes down to minimum-size.
        The minimum size is enough only for the registered and static entries."
    ::= { srtEventsGroup 25 }

srt25-requested-size OBJECT-TYPE
    SYNTAX Integer32
    MAX-ACCESS accessible-for-notify
    STATUS current
    DESCRIPTION
        "Parameter 'requested-size' in event SRT.25"
    ::= { srtEventObjects25 1 }

srt25-minimum-size OBJECT-TYPE
    SYNTAX Integer32
    MAX-ACCESS accessible-for-notify
    STATUS current
    DESCRIPTION
        "Parameter 'minimum-size' in event SRT.25"
    ::= { srtEventObjects25 2 }

srtEventObjects26 OBJECT-IDENTITY
    STATUS current
    DESCRIPTION
        "Event SRT.26
        Frames to and from the same address are not bridged by this bridge."
    ::= { srtEventsGroup 26 }

srt26-source-mac OBJECT-TYPE
    SYNTAX DisplayString
    MAX-ACCESS accessible-for-notify
    STATUS current
    DESCRIPTION
        "Parameter 'source-mac' in event SRT.26"
    ::= { srtEventObjects26 1 }

srt26-dest-mac OBJECT-TYPE
    SYNTAX DisplayString
    MAX-ACCESS accessible-for-notify
    STATUS current
    DESCRIPTION
        "Parameter 'dest-mac' in event SRT.26"
    ::= { srtEventObjects26 2 }

srt26-port OBJECT-TYPE
    SYNTAX Integer32
    MAX-ACCESS accessible-for-notify
    STATUS current
    DESCRIPTION
        "Parameter 'port' in event SRT.26"
    ::= { srtEventObjects26 3 }

srt26-interface OBJECT-TYPE
    SYNTAX DisplayString
    MAX-ACCESS accessible-for-notify
    STATUS current
    DESCRIPTION
        "Parameter 'interface' in event SRT.26"
    ::= { srtEventObjects26 4 }

srt26-circuit-name OBJECT-TYPE
    SYNTAX DisplayString
    MAX-ACCESS accessible-for-notify
    STATUS current
    DESCRIPTION
        "Parameter 'circuit-name' in event SRT.26"
    ::= { srtEventObjects26 5 }

srtEventObjects27 OBJECT-IDENTITY
    STATUS current
    DESCRIPTION
        "Event SRT.27
        The Spanning Tree Protocol has requested this state change for this port
        in the SRT bridge. The old-state and new-state are one of:
        FORWARDING (Spanning Tree Protocol Forwarding state),
        LEARNING (Spanning Tree Protocol Learning state),
        LISTENING (Spanning Tree Protocol Listening state),
        BLOCKED (Spanning Tree Protocol Blocking state),
        CONFIGURING (configuration of port device pending),
        POSTCONFIGURING (configuration of port device done),
        PRECONFIGURING (port enabled, configuration of port device to start) and
        DISABLED (port disabled)."
    ::= { srtEventsGroup 27 }

srt27-old-state OBJECT-TYPE
    SYNTAX DisplayString
    MAX-ACCESS accessible-for-notify
    STATUS current
    DESCRIPTION
        "Parameter 'old-state' in event SRT.27"
    ::= { srtEventObjects27 1 }

srt27-new-state OBJECT-TYPE
    SYNTAX DisplayString
    MAX-ACCESS accessible-for-notify
    STATUS current
    DESCRIPTION
        "Parameter 'new-state' in event SRT.27"
    ::= { srtEventObjects27 2 }

srt27-port OBJECT-TYPE
    SYNTAX Integer32
    MAX-ACCESS accessible-for-notify
    STATUS current
    DESCRIPTION
        "Parameter 'port' in event SRT.27"
    ::= { srtEventObjects27 3 }

srt27-interface OBJECT-TYPE
    SYNTAX DisplayString
    MAX-ACCESS accessible-for-notify
    STATUS current
    DESCRIPTION
        "Parameter 'interface' in event SRT.27"
    ::= { srtEventObjects27 4 }

srt27-circuit-name OBJECT-TYPE
    SYNTAX DisplayString
    MAX-ACCESS accessible-for-notify
    STATUS current
    DESCRIPTION
        "Parameter 'circuit-name' in event SRT.27"
    ::= { srtEventObjects27 5 }

srtEventObjects28 OBJECT-IDENTITY
    STATUS current
    DESCRIPTION
        "Event SRT.28
        There is no room for the permanent entry in the filtering database.
        The bridge will be disabled."
    ::= { srtEventsGroup 28 }

srt28-mac-address OBJECT-TYPE
    SYNTAX DisplayString
    MAX-ACCESS accessible-for-notify
    STATUS current
    DESCRIPTION
        "Parameter 'mac-address' in event SRT.28"
    ::= { srtEventObjects28 1 }

srtEventObjects29 OBJECT-IDENTITY
    STATUS current
    DESCRIPTION
        "Event SRT.29
        There is no room for the permanent entry in an auxiliary database.
        The bridge will be disabled."
    ::= { srtEventsGroup 29 }

srt29-mac-address OBJECT-TYPE
    SYNTAX DisplayString
    MAX-ACCESS accessible-for-notify
    STATUS current
    DESCRIPTION
        "Parameter 'mac-address' in event SRT.29"
    ::= { srtEventObjects29 1 }

srtEventObjects30 OBJECT-IDENTITY
    STATUS current
    DESCRIPTION
        "Event SRT.30
        A command to a network device failed.
        The possible command names are
        'SRT-ON' (promiscuous on),
        'SRT-OFF' (promiscuous off),
        'SRT-INFORM' (learn capabilities of device),
        'SRT-ADD-ENTRY' (add static entry in device),
        'SRT-SET-AGE' (set age for filtering database in device) and
        'SRT-DECR-AGE' (do ageing pass on filtering database in device).
        For commands 'SRT-ON' and 'SRT-OFF' the result will be that
        the interface may remain in the worong state. A failure on 'SRT-INFORM'
        could cause serious problems. For other commands the results will be
        less serious."
    ::= { srtEventsGroup 30 }

srt30-command OBJECT-TYPE
    SYNTAX DisplayString
    MAX-ACCESS accessible-for-notify
    STATUS current
    DESCRIPTION
        "Parameter 'command' in event SRT.30"
    ::= { srtEventObjects30 1 }

srt30-interface OBJECT-TYPE
    SYNTAX DisplayString
    MAX-ACCESS accessible-for-notify
    STATUS current
    DESCRIPTION
        "Parameter 'interface' in event SRT.30"
    ::= { srtEventObjects30 2 }

srtEventObjects31 OBJECT-IDENTITY
    STATUS current
    DESCRIPTION
        "Event SRT.31
        No buffer available to copy a frame in order to send an
        All Routes Explorer (ARE) or Spanning Tree Explorer (STE) routing-type
        frame on multiple interfaces. ARE frames are sent on all interfaces
        which are part of the SRT spanning tree, STE frames are sent
        on all interfaces running source-routing.
        No copy of this frame will be sent on the specified port and interface."
    ::= { srtEventsGroup 31 }

srt31-routing-type OBJECT-TYPE
    SYNTAX DisplayString
    MAX-ACCESS accessible-for-notify
    STATUS current
    DESCRIPTION
        "Parameter 'routing-type' in event SRT.31"
    ::= { srtEventObjects31 1 }

srt31-source-mac OBJECT-TYPE
    SYNTAX DisplayString
    MAX-ACCESS accessible-for-notify
    STATUS current
    DESCRIPTION
        "Parameter 'source-mac' in event SRT.31"
    ::= { srtEventObjects31 2 }

srt31-dest-mac OBJECT-TYPE
    SYNTAX DisplayString
    MAX-ACCESS accessible-for-notify
    STATUS current
    DESCRIPTION
        "Parameter 'dest-mac' in event SRT.31"
    ::= { srtEventObjects31 3 }

srt31-port OBJECT-TYPE
    SYNTAX Integer32
    MAX-ACCESS accessible-for-notify
    STATUS current
    DESCRIPTION
        "Parameter 'port' in event SRT.31"
    ::= { srtEventObjects31 4 }

srt31-interface OBJECT-TYPE
    SYNTAX DisplayString
    MAX-ACCESS accessible-for-notify
    STATUS current
    DESCRIPTION
        "Parameter 'interface' in event SRT.31"
    ::= { srtEventObjects31 5 }

srt31-circuit-name OBJECT-TYPE
    SYNTAX DisplayString
    MAX-ACCESS accessible-for-notify
    STATUS current
    DESCRIPTION
        "Parameter 'circuit-name' in event SRT.31"
    ::= { srtEventObjects31 6 }

srtEventObjects32 OBJECT-IDENTITY
    STATUS current
    DESCRIPTION
        "Event SRT.32
        The sending of a source routed frame being forwarded failed.
        The reason-code is the internal error code for the failure."
    ::= { srtEventsGroup 32 }

srt32-source-mac OBJECT-TYPE
    SYNTAX DisplayString
    MAX-ACCESS accessible-for-notify
    STATUS current
    DESCRIPTION
        "Parameter 'source-mac' in event SRT.32"
    ::= { srtEventObjects32 1 }

srt32-dest-mac OBJECT-TYPE
    SYNTAX DisplayString
    MAX-ACCESS accessible-for-notify
    STATUS current
    DESCRIPTION
        "Parameter 'dest-mac' in event SRT.32"
    ::= { srtEventObjects32 2 }

srt32-reason-code OBJECT-TYPE
    SYNTAX Integer32
    MAX-ACCESS accessible-for-notify
    STATUS current
    DESCRIPTION
        "Parameter 'reason-code' in event SRT.32"
    ::= { srtEventObjects32 3 }

srt32-port OBJECT-TYPE
    SYNTAX Integer32
    MAX-ACCESS accessible-for-notify
    STATUS current
    DESCRIPTION
        "Parameter 'port' in event SRT.32"
    ::= { srtEventObjects32 4 }

srt32-interface-name OBJECT-TYPE
    SYNTAX DisplayString
    MAX-ACCESS accessible-for-notify
    STATUS current
    DESCRIPTION
        "Parameter 'interface-name' in event SRT.32"
    ::= { srtEventObjects32 5 }

srt32-circuit-name OBJECT-TYPE
    SYNTAX DisplayString
    MAX-ACCESS accessible-for-notify
    STATUS current
    DESCRIPTION
        "Parameter 'circuit-name' in event SRT.32"
    ::= { srtEventObjects32 6 }

srtEventObjects33 OBJECT-IDENTITY
    STATUS current
    DESCRIPTION
        "Event SRT.33
        A source-routed frame having a All Routes Descriptor (ARE)
        or Spanning Tree Explorer (STE) routing-type in the RIF has a duplicate
        Routing Descriptor in the RIF. The frame will be dropped. This is
        a normal occurrence for ARE frames when there are any duplicate paths
        in the source routing domain. For STE frames, this indicates that
        there is an interface that is part of the source-routing spanning tree
        that should not be."
    ::= { srtEventsGroup 33 }

srt33-routing-type OBJECT-TYPE
    SYNTAX DisplayString
    MAX-ACCESS accessible-for-notify
    STATUS current
    DESCRIPTION
        "Parameter 'routing-type' in event SRT.33"
    ::= { srtEventObjects33 1 }

srt33-source-mac OBJECT-TYPE
    SYNTAX DisplayString
    MAX-ACCESS accessible-for-notify
    STATUS current
    DESCRIPTION
        "Parameter 'source-mac' in event SRT.33"
    ::= { srtEventObjects33 2 }

srt33-dest-mac OBJECT-TYPE
    SYNTAX DisplayString
    MAX-ACCESS accessible-for-notify
    STATUS current
    DESCRIPTION
        "Parameter 'dest-mac' in event SRT.33"
    ::= { srtEventObjects33 3 }

srt33-port OBJECT-TYPE
    SYNTAX Integer32
    MAX-ACCESS accessible-for-notify
    STATUS current
    DESCRIPTION
        "Parameter 'port' in event SRT.33"
    ::= { srtEventObjects33 4 }

srt33-interface OBJECT-TYPE
    SYNTAX DisplayString
    MAX-ACCESS accessible-for-notify
    STATUS current
    DESCRIPTION
        "Parameter 'interface' in event SRT.33"
    ::= { srtEventObjects33 5 }

srt33-circuit-name OBJECT-TYPE
    SYNTAX DisplayString
    MAX-ACCESS accessible-for-notify
    STATUS current
    DESCRIPTION
        "Parameter 'circuit-name' in event SRT.33"
    ::= { srtEventObjects33 6 }

srtEventObjects34 OBJECT-IDENTITY
    STATUS current
    DESCRIPTION
        "Event SRT.34
        A source-routed frame of Specifically-routed frame (SRF) type has
        a duplicate LOUT (outgoing LAN ID). This is illegal, and the frame
        will be dropped."
    ::= { srtEventsGroup 34 }

srt34-RIF OBJECT-TYPE
    SYNTAX DisplayString
    MAX-ACCESS accessible-for-notify
    STATUS current
    DESCRIPTION
        "Parameter 'RIF' in event SRT.34"
    ::= { srtEventObjects34 1 }

srt34-source-mac OBJECT-TYPE
    SYNTAX DisplayString
    MAX-ACCESS accessible-for-notify
    STATUS current
    DESCRIPTION
        "Parameter 'source-mac' in event SRT.34"
    ::= { srtEventObjects34 2 }

srt34-dest-mac OBJECT-TYPE
    SYNTAX DisplayString
    MAX-ACCESS accessible-for-notify
    STATUS current
    DESCRIPTION
        "Parameter 'dest-mac' in event SRT.34"
    ::= { srtEventObjects34 3 }

srt34-port OBJECT-TYPE
    SYNTAX Integer32
    MAX-ACCESS accessible-for-notify
    STATUS current
    DESCRIPTION
        "Parameter 'port' in event SRT.34"
    ::= { srtEventObjects34 4 }

srt34-interface OBJECT-TYPE
    SYNTAX DisplayString
    MAX-ACCESS accessible-for-notify
    STATUS current
    DESCRIPTION
        "Parameter 'interface' in event SRT.34"
    ::= { srtEventObjects34 5 }

srt34-circuit-name OBJECT-TYPE
    SYNTAX DisplayString
    MAX-ACCESS accessible-for-notify
    STATUS current
    DESCRIPTION
        "Parameter 'circuit-name' in event SRT.34"
    ::= { srtEventObjects34 6 }

srtEventObjects35 OBJECT-IDENTITY
    STATUS current
    DESCRIPTION
        "Event SRT.35
        An All Routes Explorer (ARE) source-routed frame has more Route
        Descriptors than this bridge is configured to allow for ARE frames.
        The frame will be dropped."
    ::= { srtEventsGroup 35 }

srt35-RIF OBJECT-TYPE
    SYNTAX DisplayString
    MAX-ACCESS accessible-for-notify
    STATUS current
    DESCRIPTION
        "Parameter 'RIF' in event SRT.35"
    ::= { srtEventObjects35 1 }

srt35-source-mac OBJECT-TYPE
    SYNTAX DisplayString
    MAX-ACCESS accessible-for-notify
    STATUS current
    DESCRIPTION
        "Parameter 'source-mac' in event SRT.35"
    ::= { srtEventObjects35 2 }

srt35-dest-mac OBJECT-TYPE
    SYNTAX DisplayString
    MAX-ACCESS accessible-for-notify
    STATUS current
    DESCRIPTION
        "Parameter 'dest-mac' in event SRT.35"
    ::= { srtEventObjects35 3 }

srt35-port OBJECT-TYPE
    SYNTAX Integer32
    MAX-ACCESS accessible-for-notify
    STATUS current
    DESCRIPTION
        "Parameter 'port' in event SRT.35"
    ::= { srtEventObjects35 4 }

srt35-interface OBJECT-TYPE
    SYNTAX DisplayString
    MAX-ACCESS accessible-for-notify
    STATUS current
    DESCRIPTION
        "Parameter 'interface' in event SRT.35"
    ::= { srtEventObjects35 5 }

srt35-circuit-name OBJECT-TYPE
    SYNTAX DisplayString
    MAX-ACCESS accessible-for-notify
    STATUS current
    DESCRIPTION
        "Parameter 'circuit-name' in event SRT.35"
    ::= { srtEventObjects35 6 }

srtEventObjects36 OBJECT-IDENTITY
    STATUS current
    DESCRIPTION
        "Event SRT.36
        A Spanning Tree Explorer (STE) source-routed frame has more Route
        Descriptors than this bridge is configured to allow for STE frames.
        The frame will be dropped."
    ::= { srtEventsGroup 36 }

srt36-RIF OBJECT-TYPE
    SYNTAX DisplayString
    MAX-ACCESS accessible-for-notify
    STATUS current
    DESCRIPTION
        "Parameter 'RIF' in event SRT.36"
    ::= { srtEventObjects36 1 }

srt36-source-mac OBJECT-TYPE
    SYNTAX DisplayString
    MAX-ACCESS accessible-for-notify
    STATUS current
    DESCRIPTION
        "Parameter 'source-mac' in event SRT.36"
    ::= { srtEventObjects36 2 }

srt36-dest-mac OBJECT-TYPE
    SYNTAX DisplayString
    MAX-ACCESS accessible-for-notify
    STATUS current
    DESCRIPTION
        "Parameter 'dest-mac' in event SRT.36"
    ::= { srtEventObjects36 3 }

srt36-port OBJECT-TYPE
    SYNTAX Integer32
    MAX-ACCESS accessible-for-notify
    STATUS current
    DESCRIPTION
        "Parameter 'port' in event SRT.36"
    ::= { srtEventObjects36 4 }

srt36-interface OBJECT-TYPE
    SYNTAX DisplayString
    MAX-ACCESS accessible-for-notify
    STATUS current
    DESCRIPTION
        "Parameter 'interface' in event SRT.36"
    ::= { srtEventObjects36 5 }

srt36-circuit-name OBJECT-TYPE
    SYNTAX DisplayString
    MAX-ACCESS accessible-for-notify
    STATUS current
    DESCRIPTION
        "Parameter 'circuit-name' in event SRT.36"
    ::= { srtEventObjects36 6 }

srtEventObjects37 OBJECT-IDENTITY
    STATUS current
    DESCRIPTION
        "Event SRT.37
        A source-routed frame of Specifically-routed frame (SRF) type has
        an outgoing LOUT (LAN ID Out) that does not match that of any active
        source-routing interface in the router. It will be dropped."
    ::= { srtEventsGroup 37 }

srt37-RIF OBJECT-TYPE
    SYNTAX DisplayString
    MAX-ACCESS accessible-for-notify
    STATUS current
    DESCRIPTION
        "Parameter 'RIF' in event SRT.37"
    ::= { srtEventObjects37 1 }

srt37-source-mac OBJECT-TYPE
    SYNTAX DisplayString
    MAX-ACCESS accessible-for-notify
    STATUS current
    DESCRIPTION
        "Parameter 'source-mac' in event SRT.37"
    ::= { srtEventObjects37 2 }

srt37-dest-mac OBJECT-TYPE
    SYNTAX DisplayString
    MAX-ACCESS accessible-for-notify
    STATUS current
    DESCRIPTION
        "Parameter 'dest-mac' in event SRT.37"
    ::= { srtEventObjects37 3 }

srt37-port OBJECT-TYPE
    SYNTAX Integer32
    MAX-ACCESS accessible-for-notify
    STATUS current
    DESCRIPTION
        "Parameter 'port' in event SRT.37"
    ::= { srtEventObjects37 4 }

srt37-interface OBJECT-TYPE
    SYNTAX DisplayString
    MAX-ACCESS accessible-for-notify
    STATUS current
    DESCRIPTION
        "Parameter 'interface' in event SRT.37"
    ::= { srtEventObjects37 5 }

srtEventObjects38 OBJECT-IDENTITY
    STATUS current
    DESCRIPTION
        "Event SRT.38
        An All Routes Explorer frame has been received on the specified port."
    ::= { srtEventsGroup 38 }

srt38-RIF OBJECT-TYPE
    SYNTAX DisplayString
    MAX-ACCESS accessible-for-notify
    STATUS current
    DESCRIPTION
        "Parameter 'RIF' in event SRT.38"
    ::= { srtEventObjects38 1 }

srt38-source-mac OBJECT-TYPE
    SYNTAX DisplayString
    MAX-ACCESS accessible-for-notify
    STATUS current
    DESCRIPTION
        "Parameter 'source-mac' in event SRT.38"
    ::= { srtEventObjects38 2 }

srt38-dest-mac OBJECT-TYPE
    SYNTAX DisplayString
    MAX-ACCESS accessible-for-notify
    STATUS current
    DESCRIPTION
        "Parameter 'dest-mac' in event SRT.38"
    ::= { srtEventObjects38 3 }

srt38-port OBJECT-TYPE
    SYNTAX Integer32
    MAX-ACCESS accessible-for-notify
    STATUS current
    DESCRIPTION
        "Parameter 'port' in event SRT.38"
    ::= { srtEventObjects38 4 }

srt38-interface OBJECT-TYPE
    SYNTAX DisplayString
    MAX-ACCESS accessible-for-notify
    STATUS current
    DESCRIPTION
        "Parameter 'interface' in event SRT.38"
    ::= { srtEventObjects38 5 }

srt38-circuit-name OBJECT-TYPE
    SYNTAX DisplayString
    MAX-ACCESS accessible-for-notify
    STATUS current
    DESCRIPTION
        "Parameter 'circuit-name' in event SRT.38"
    ::= { srtEventObjects38 6 }

srtEventObjects39 OBJECT-IDENTITY
    STATUS current
    DESCRIPTION
        "Event SRT.39
        An All Routes Explorer frame has been sent on the specified port."
    ::= { srtEventsGroup 39 }

srt39-RIF OBJECT-TYPE
    SYNTAX DisplayString
    MAX-ACCESS accessible-for-notify
    STATUS current
    DESCRIPTION
        "Parameter 'RIF' in event SRT.39"
    ::= { srtEventObjects39 1 }

srt39-source-mac OBJECT-TYPE
    SYNTAX DisplayString
    MAX-ACCESS accessible-for-notify
    STATUS current
    DESCRIPTION
        "Parameter 'source-mac' in event SRT.39"
    ::= { srtEventObjects39 2 }

srt39-dest-mac OBJECT-TYPE
    SYNTAX DisplayString
    MAX-ACCESS accessible-for-notify
    STATUS current
    DESCRIPTION
        "Parameter 'dest-mac' in event SRT.39"
    ::= { srtEventObjects39 3 }

srt39-port OBJECT-TYPE
    SYNTAX Integer32
    MAX-ACCESS accessible-for-notify
    STATUS current
    DESCRIPTION
        "Parameter 'port' in event SRT.39"
    ::= { srtEventObjects39 4 }

srt39-interface OBJECT-TYPE
    SYNTAX DisplayString
    MAX-ACCESS accessible-for-notify
    STATUS current
    DESCRIPTION
        "Parameter 'interface' in event SRT.39"
    ::= { srtEventObjects39 5 }

srt39-circuit-name OBJECT-TYPE
    SYNTAX DisplayString
    MAX-ACCESS accessible-for-notify
    STATUS current
    DESCRIPTION
        "Parameter 'circuit-name' in event SRT.39"
    ::= { srtEventObjects39 6 }

srtEventObjects40 OBJECT-IDENTITY
    STATUS current
    DESCRIPTION
        "Event SRT.40
        A Spanning Tree Explorer frame has been received on the specified port."
    ::= { srtEventsGroup 40 }

srt40-RIF OBJECT-TYPE
    SYNTAX DisplayString
    MAX-ACCESS accessible-for-notify
    STATUS current
    DESCRIPTION
        "Parameter 'RIF' in event SRT.40"
    ::= { srtEventObjects40 1 }

srt40-source-mac OBJECT-TYPE
    SYNTAX DisplayString
    MAX-ACCESS accessible-for-notify
    STATUS current
    DESCRIPTION
        "Parameter 'source-mac' in event SRT.40"
    ::= { srtEventObjects40 2 }

srt40-dest-mac OBJECT-TYPE
    SYNTAX DisplayString
    MAX-ACCESS accessible-for-notify
    STATUS current
    DESCRIPTION
        "Parameter 'dest-mac' in event SRT.40"
    ::= { srtEventObjects40 3 }

srt40-port OBJECT-TYPE
    SYNTAX Integer32
    MAX-ACCESS accessible-for-notify
    STATUS current
    DESCRIPTION
        "Parameter 'port' in event SRT.40"
    ::= { srtEventObjects40 4 }

srt40-interface OBJECT-TYPE
    SYNTAX DisplayString
    MAX-ACCESS accessible-for-notify
    STATUS current
    DESCRIPTION
        "Parameter 'interface' in event SRT.40"
    ::= { srtEventObjects40 5 }

srt40-circuit-name OBJECT-TYPE
    SYNTAX DisplayString
    MAX-ACCESS accessible-for-notify
    STATUS current
    DESCRIPTION
        "Parameter 'circuit-name' in event SRT.40"
    ::= { srtEventObjects40 6 }

srtEventObjects41 OBJECT-IDENTITY
    STATUS current
    DESCRIPTION
        "Event SRT.41
        A Spanning Tree Explorer frame has been sent on the specified port."
    ::= { srtEventsGroup 41 }

srt41-RIF OBJECT-TYPE
    SYNTAX DisplayString
    MAX-ACCESS accessible-for-notify
    STATUS current
    DESCRIPTION
        "Parameter 'RIF' in event SRT.41"
    ::= { srtEventObjects41 1 }

srt41-source-mac OBJECT-TYPE
    SYNTAX DisplayString
    MAX-ACCESS accessible-for-notify
    STATUS current
    DESCRIPTION
        "Parameter 'source-mac' in event SRT.41"
    ::= { srtEventObjects41 2 }

srt41-dest-mac OBJECT-TYPE
    SYNTAX DisplayString
    MAX-ACCESS accessible-for-notify
    STATUS current
    DESCRIPTION
        "Parameter 'dest-mac' in event SRT.41"
    ::= { srtEventObjects41 3 }

srt41-port OBJECT-TYPE
    SYNTAX Integer32
    MAX-ACCESS accessible-for-notify
    STATUS current
    DESCRIPTION
        "Parameter 'port' in event SRT.41"
    ::= { srtEventObjects41 4 }

srt41-interface OBJECT-TYPE
    SYNTAX DisplayString
    MAX-ACCESS accessible-for-notify
    STATUS current
    DESCRIPTION
        "Parameter 'interface' in event SRT.41"
    ::= { srtEventObjects41 5 }

srt41-circuit-name OBJECT-TYPE
    SYNTAX DisplayString
    MAX-ACCESS accessible-for-notify
    STATUS current
    DESCRIPTION
        "Parameter 'circuit-name' in event SRT.41"
    ::= { srtEventObjects41 6 }

srtEventObjects42 OBJECT-IDENTITY
    STATUS current
    DESCRIPTION
        "Event SRT.42
        A source-routing explorer (ARE or STE in routing-type) has had
        the Largest Frame (LF) field lowered in its RIF. This happens
        whenever a frame is received from a segment with a smaller maximum
        frame size than the one presently encoded in the LF bits. This is
        a normal part of the spanning tree protocol to determine the maximum
        frame size on all routes."
    ::= { srtEventsGroup 42 }

srt42-routing-type OBJECT-TYPE
    SYNTAX DisplayString
    MAX-ACCESS accessible-for-notify
    STATUS current
    DESCRIPTION
        "Parameter 'routing-type' in event SRT.42"
    ::= { srtEventObjects42 1 }

srt42-old-LF OBJECT-TYPE
    SYNTAX Integer32
    MAX-ACCESS accessible-for-notify
    STATUS current
    DESCRIPTION
        "Parameter 'old-LF' in event SRT.42"
    ::= { srtEventObjects42 2 }

srt42-new-LF OBJECT-TYPE
    SYNTAX Integer32
    MAX-ACCESS accessible-for-notify
    STATUS current
    DESCRIPTION
        "Parameter 'new-LF' in event SRT.42"
    ::= { srtEventObjects42 3 }

srt42-source-mac OBJECT-TYPE
    SYNTAX DisplayString
    MAX-ACCESS accessible-for-notify
    STATUS current
    DESCRIPTION
        "Parameter 'source-mac' in event SRT.42"
    ::= { srtEventObjects42 4 }

srt42-dest-mac OBJECT-TYPE
    SYNTAX DisplayString
    MAX-ACCESS accessible-for-notify
    STATUS current
    DESCRIPTION
        "Parameter 'dest-mac' in event SRT.42"
    ::= { srtEventObjects42 5 }

srt42-port OBJECT-TYPE
    SYNTAX Integer32
    MAX-ACCESS accessible-for-notify
    STATUS current
    DESCRIPTION
        "Parameter 'port' in event SRT.42"
    ::= { srtEventObjects42 6 }

srt42-interface OBJECT-TYPE
    SYNTAX DisplayString
    MAX-ACCESS accessible-for-notify
    STATUS current
    DESCRIPTION
        "Parameter 'interface' in event SRT.42"
    ::= { srtEventObjects42 7 }

srt42-circuit-name OBJECT-TYPE
    SYNTAX DisplayString
    MAX-ACCESS accessible-for-notify
    STATUS current
    DESCRIPTION
        "Parameter 'circuit-name' in event SRT.42"
    ::= { srtEventObjects42 8 }

srtEventObjects43 OBJECT-IDENTITY
    STATUS current
    DESCRIPTION
        "Event SRT.43
        A source-routing explorer (ARE or STE in routing-type) has had
        the Largest Frame (LF) field lowered in its RIF. This happens
        whenever a frame is sent to a segment with a smaller maximum frame size
        than the one presently encoded in the LF bits. This is a normal part of
        the spanning tree protocol to determine the maximum frame size
        on all routes."
    ::= { srtEventsGroup 43 }

srt43-routing-type OBJECT-TYPE
    SYNTAX DisplayString
    MAX-ACCESS accessible-for-notify
    STATUS current
    DESCRIPTION
        "Parameter 'routing-type' in event SRT.43"
    ::= { srtEventObjects43 1 }

srt43-old-LF OBJECT-TYPE
    SYNTAX Integer32
    MAX-ACCESS accessible-for-notify
    STATUS current
    DESCRIPTION
        "Parameter 'old-LF' in event SRT.43"
    ::= { srtEventObjects43 2 }

srt43-new-LF OBJECT-TYPE
    SYNTAX Integer32
    MAX-ACCESS accessible-for-notify
    STATUS current
    DESCRIPTION
        "Parameter 'new-LF' in event SRT.43"
    ::= { srtEventObjects43 3 }

srt43-source-mac OBJECT-TYPE
    SYNTAX DisplayString
    MAX-ACCESS accessible-for-notify
    STATUS current
    DESCRIPTION
        "Parameter 'source-mac' in event SRT.43"
    ::= { srtEventObjects43 4 }

srt43-dest-mac OBJECT-TYPE
    SYNTAX DisplayString
    MAX-ACCESS accessible-for-notify
    STATUS current
    DESCRIPTION
        "Parameter 'dest-mac' in event SRT.43"
    ::= { srtEventObjects43 5 }

srt43-port OBJECT-TYPE
    SYNTAX Integer32
    MAX-ACCESS accessible-for-notify
    STATUS current
    DESCRIPTION
        "Parameter 'port' in event SRT.43"
    ::= { srtEventObjects43 6 }

srt43-interface OBJECT-TYPE
    SYNTAX DisplayString
    MAX-ACCESS accessible-for-notify
    STATUS current
    DESCRIPTION
        "Parameter 'interface' in event SRT.43"
    ::= { srtEventObjects43 7 }

srt43-circuit-name OBJECT-TYPE
    SYNTAX DisplayString
    MAX-ACCESS accessible-for-notify
    STATUS current
    DESCRIPTION
        "Parameter 'circuit-name' in event SRT.43"
    ::= { srtEventObjects43 8 }

srtEventObjects44 OBJECT-IDENTITY
    STATUS current
    DESCRIPTION
        "Event SRT.44
        A Specifically-routed frame has been received on the specified port."
    ::= { srtEventsGroup 44 }

srt44-RIF OBJECT-TYPE
    SYNTAX DisplayString
    MAX-ACCESS accessible-for-notify
    STATUS current
    DESCRIPTION
        "Parameter 'RIF' in event SRT.44"
    ::= { srtEventObjects44 1 }

srt44-source-mac OBJECT-TYPE
    SYNTAX DisplayString
    MAX-ACCESS accessible-for-notify
    STATUS current
    DESCRIPTION
        "Parameter 'source-mac' in event SRT.44"
    ::= { srtEventObjects44 2 }

srt44-dest-mac OBJECT-TYPE
    SYNTAX DisplayString
    MAX-ACCESS accessible-for-notify
    STATUS current
    DESCRIPTION
        "Parameter 'dest-mac' in event SRT.44"
    ::= { srtEventObjects44 3 }

srt44-port OBJECT-TYPE
    SYNTAX Integer32
    MAX-ACCESS accessible-for-notify
    STATUS current
    DESCRIPTION
        "Parameter 'port' in event SRT.44"
    ::= { srtEventObjects44 4 }

srt44-interface OBJECT-TYPE
    SYNTAX DisplayString
    MAX-ACCESS accessible-for-notify
    STATUS current
    DESCRIPTION
        "Parameter 'interface' in event SRT.44"
    ::= { srtEventObjects44 5 }

srt44-circuit-name OBJECT-TYPE
    SYNTAX DisplayString
    MAX-ACCESS accessible-for-notify
    STATUS current
    DESCRIPTION
        "Parameter 'circuit-name' in event SRT.44"
    ::= { srtEventObjects44 6 }

srtEventObjects45 OBJECT-IDENTITY
    STATUS current
    DESCRIPTION
        "Event SRT.45
        A Specifically-routed frame is being sent on the specified port."
    ::= { srtEventsGroup 45 }

srt45-RIF OBJECT-TYPE
    SYNTAX DisplayString
    MAX-ACCESS accessible-for-notify
    STATUS current
    DESCRIPTION
        "Parameter 'RIF' in event SRT.45"
    ::= { srtEventObjects45 1 }

srt45-source-mac OBJECT-TYPE
    SYNTAX DisplayString
    MAX-ACCESS accessible-for-notify
    STATUS current
    DESCRIPTION
        "Parameter 'source-mac' in event SRT.45"
    ::= { srtEventObjects45 2 }

srt45-dest-mac OBJECT-TYPE
    SYNTAX DisplayString
    MAX-ACCESS accessible-for-notify
    STATUS current
    DESCRIPTION
        "Parameter 'dest-mac' in event SRT.45"
    ::= { srtEventObjects45 3 }

srt45-port OBJECT-TYPE
    SYNTAX Integer32
    MAX-ACCESS accessible-for-notify
    STATUS current
    DESCRIPTION
        "Parameter 'port' in event SRT.45"
    ::= { srtEventObjects45 4 }

srt45-interface OBJECT-TYPE
    SYNTAX DisplayString
    MAX-ACCESS accessible-for-notify
    STATUS current
    DESCRIPTION
        "Parameter 'interface' in event SRT.45"
    ::= { srtEventObjects45 5 }

srt45-circuit-name OBJECT-TYPE
    SYNTAX DisplayString
    MAX-ACCESS accessible-for-notify
    STATUS current
    DESCRIPTION
        "Parameter 'circuit-name' in event SRT.45"
    ::= { srtEventObjects45 6 }

srtEventObjects46 OBJECT-IDENTITY
    STATUS current
    DESCRIPTION
        "Event SRT.46
        A source-routed frame has been received on the specified port, but
        that port is not configured for bridging.
        The routing-type is one of SRF (Specifically-routed frame),
        STE (Spanning Tree Expolorer) or ARE (All Routes Explorer).
        This really should not happen on more than a transient basis, because
        ports that are not enabled for bridging should not be queueing packets
        to the source-routing forwarder."
    ::= { srtEventsGroup 46 }

srt46-routing-type OBJECT-TYPE
    SYNTAX DisplayString
    MAX-ACCESS accessible-for-notify
    STATUS current
    DESCRIPTION
        "Parameter 'routing-type' in event SRT.46"
    ::= { srtEventObjects46 1 }

srt46-source-mac OBJECT-TYPE
    SYNTAX DisplayString
    MAX-ACCESS accessible-for-notify
    STATUS current
    DESCRIPTION
        "Parameter 'source-mac' in event SRT.46"
    ::= { srtEventObjects46 2 }

srt46-dest-mac OBJECT-TYPE
    SYNTAX DisplayString
    MAX-ACCESS accessible-for-notify
    STATUS current
    DESCRIPTION
        "Parameter 'dest-mac' in event SRT.46"
    ::= { srtEventObjects46 3 }

srt46-port OBJECT-TYPE
    SYNTAX Integer32
    MAX-ACCESS accessible-for-notify
    STATUS current
    DESCRIPTION
        "Parameter 'port' in event SRT.46"
    ::= { srtEventObjects46 4 }

srt46-interface OBJECT-TYPE
    SYNTAX DisplayString
    MAX-ACCESS accessible-for-notify
    STATUS current
    DESCRIPTION
        "Parameter 'interface' in event SRT.46"
    ::= { srtEventObjects46 5 }

srt46-circuit-name OBJECT-TYPE
    SYNTAX DisplayString
    MAX-ACCESS accessible-for-notify
    STATUS current
    DESCRIPTION
        "Parameter 'circuit-name' in event SRT.46"
    ::= { srtEventObjects46 6 }

srtEventObjects47 OBJECT-IDENTITY
    STATUS current
    DESCRIPTION
        "Event SRT.47
        A source-routed frame has been received on the specified port, but
        that port is not configured for source-routing bridging.
        The routing-type is one of SRF (Specifically-routed frame),
        STE (Spanning Tree Expolorer) or ARE (All Routes Explorer).
        This really should not happen on more than a transient basis, because
        ports that are not enabled for bridging should not be queueing packets
        to the source-routing forwarder."
    ::= { srtEventsGroup 47 }

srt47-routing-type OBJECT-TYPE
    SYNTAX DisplayString
    MAX-ACCESS accessible-for-notify
    STATUS current
    DESCRIPTION
        "Parameter 'routing-type' in event SRT.47"
    ::= { srtEventObjects47 1 }

srt47-source-mac OBJECT-TYPE
    SYNTAX DisplayString
    MAX-ACCESS accessible-for-notify
    STATUS current
    DESCRIPTION
        "Parameter 'source-mac' in event SRT.47"
    ::= { srtEventObjects47 2 }

srt47-dest-mac OBJECT-TYPE
    SYNTAX DisplayString
    MAX-ACCESS accessible-for-notify
    STATUS current
    DESCRIPTION
        "Parameter 'dest-mac' in event SRT.47"
    ::= { srtEventObjects47 3 }

srt47-port OBJECT-TYPE
    SYNTAX Integer32
    MAX-ACCESS accessible-for-notify
    STATUS current
    DESCRIPTION
        "Parameter 'port' in event SRT.47"
    ::= { srtEventObjects47 4 }

srt47-interface OBJECT-TYPE
    SYNTAX DisplayString
    MAX-ACCESS accessible-for-notify
    STATUS current
    DESCRIPTION
        "Parameter 'interface' in event SRT.47"
    ::= { srtEventObjects47 5 }

srt47-circuit-name OBJECT-TYPE
    SYNTAX DisplayString
    MAX-ACCESS accessible-for-notify
    STATUS current
    DESCRIPTION
        "Parameter 'circuit-name' in event SRT.47"
    ::= { srtEventObjects47 6 }

srtEventObjects48 OBJECT-IDENTITY
    STATUS current
    DESCRIPTION
        "Event SRT.48
        A Spanning Tree Explorer (STE) frame was dropped, and not forwarded,
        because the incoming port is not part of the spanning tree, or has been
        configured not to forward STE frames."
    ::= { srtEventsGroup 48 }

srt48-RIF OBJECT-TYPE
    SYNTAX DisplayString
    MAX-ACCESS accessible-for-notify
    STATUS current
    DESCRIPTION
        "Parameter 'RIF' in event SRT.48"
    ::= { srtEventObjects48 1 }

srt48-source-mac OBJECT-TYPE
    SYNTAX DisplayString
    MAX-ACCESS accessible-for-notify
    STATUS current
    DESCRIPTION
        "Parameter 'source-mac' in event SRT.48"
    ::= { srtEventObjects48 2 }

srt48-dest-mac OBJECT-TYPE
    SYNTAX DisplayString
    MAX-ACCESS accessible-for-notify
    STATUS current
    DESCRIPTION
        "Parameter 'dest-mac' in event SRT.48"
    ::= { srtEventObjects48 3 }

srt48-port OBJECT-TYPE
    SYNTAX Integer32
    MAX-ACCESS accessible-for-notify
    STATUS current
    DESCRIPTION
        "Parameter 'port' in event SRT.48"
    ::= { srtEventObjects48 4 }

srt48-interface OBJECT-TYPE
    SYNTAX DisplayString
    MAX-ACCESS accessible-for-notify
    STATUS current
    DESCRIPTION
        "Parameter 'interface' in event SRT.48"
    ::= { srtEventObjects48 5 }

srt48-circuit-name OBJECT-TYPE
    SYNTAX DisplayString
    MAX-ACCESS accessible-for-notify
    STATUS current
    DESCRIPTION
        "Parameter 'circuit-name' in event SRT.48"
    ::= { srtEventObjects48 6 }

srtEventObjects49 OBJECT-IDENTITY
    STATUS current
    DESCRIPTION
        "Event SRT.49
        A Spanning Tree Explorer (STE) frame was not sent on the specified port
        because it is not part of the spanning tree, or has been configured
        not to forward STE frames."
    ::= { srtEventsGroup 49 }

srt49-RIF OBJECT-TYPE
    SYNTAX DisplayString
    MAX-ACCESS accessible-for-notify
    STATUS current
    DESCRIPTION
        "Parameter 'RIF' in event SRT.49"
    ::= { srtEventObjects49 1 }

srt49-source-mac OBJECT-TYPE
    SYNTAX DisplayString
    MAX-ACCESS accessible-for-notify
    STATUS current
    DESCRIPTION
        "Parameter 'source-mac' in event SRT.49"
    ::= { srtEventObjects49 2 }

srt49-dest-mac OBJECT-TYPE
    SYNTAX DisplayString
    MAX-ACCESS accessible-for-notify
    STATUS current
    DESCRIPTION
        "Parameter 'dest-mac' in event SRT.49"
    ::= { srtEventObjects49 3 }

srt49-port OBJECT-TYPE
    SYNTAX Integer32
    MAX-ACCESS accessible-for-notify
    STATUS current
    DESCRIPTION
        "Parameter 'port' in event SRT.49"
    ::= { srtEventObjects49 4 }

srt49-interface OBJECT-TYPE
    SYNTAX DisplayString
    MAX-ACCESS accessible-for-notify
    STATUS current
    DESCRIPTION
        "Parameter 'interface' in event SRT.49"
    ::= { srtEventObjects49 5 }

srt49-circuit-name OBJECT-TYPE
    SYNTAX DisplayString
    MAX-ACCESS accessible-for-notify
    STATUS current
    DESCRIPTION
        "Parameter 'circuit-name' in event SRT.49"
    ::= { srtEventObjects49 6 }

srtEventObjects50 OBJECT-IDENTITY
    STATUS current
    DESCRIPTION
        "Event SRT.50
        The bridge tried to enable source-routing bridging on this interface,
        but the interface refused the configuration command.
        Source-routing will be left disabled on this interface."
    ::= { srtEventsGroup 50 }

srt50-error-string OBJECT-TYPE
    SYNTAX DisplayString
    MAX-ACCESS accessible-for-notify
    STATUS current
    DESCRIPTION
        "Parameter 'error-string' in event SRT.50"
    ::= { srtEventObjects50 1 }

srt50-interface OBJECT-TYPE
    SYNTAX DisplayString
    MAX-ACCESS accessible-for-notify
    STATUS current
    DESCRIPTION
        "Parameter 'interface' in event SRT.50"
    ::= { srtEventObjects50 2 }

srtEventObjects51 OBJECT-IDENTITY
    STATUS current
    DESCRIPTION
        "Event SRT.51
        The specified Specifically-routed (source-routed) frame is too large
        to send on this outgoing port and interface. The reformatted-length is
        the size of the frame including MAC headers after any mapping of
        data link headers."
    ::= { srtEventsGroup 51 }

srt51-source-mac OBJECT-TYPE
    SYNTAX DisplayString
    MAX-ACCESS accessible-for-notify
    STATUS current
    DESCRIPTION
        "Parameter 'source-mac' in event SRT.51"
    ::= { srtEventObjects51 1 }

srt51-dest-mac OBJECT-TYPE
    SYNTAX DisplayString
    MAX-ACCESS accessible-for-notify
    STATUS current
    DESCRIPTION
        "Parameter 'dest-mac' in event SRT.51"
    ::= { srtEventObjects51 2 }

srt51-reformatted-length OBJECT-TYPE
    SYNTAX Integer32
    MAX-ACCESS accessible-for-notify
    STATUS current
    DESCRIPTION
        "Parameter 'reformatted-length' in event SRT.51"
    ::= { srtEventObjects51 3 }

srt51-output-maximum OBJECT-TYPE
    SYNTAX Integer32
    MAX-ACCESS accessible-for-notify
    STATUS current
    DESCRIPTION
        "Parameter 'output-maximum' in event SRT.51"
    ::= { srtEventObjects51 4 }

srt51-port OBJECT-TYPE
    SYNTAX Integer32
    MAX-ACCESS accessible-for-notify
    STATUS current
    DESCRIPTION
        "Parameter 'port' in event SRT.51"
    ::= { srtEventObjects51 5 }

srt51-interface OBJECT-TYPE
    SYNTAX DisplayString
    MAX-ACCESS accessible-for-notify
    STATUS current
    DESCRIPTION
        "Parameter 'interface' in event SRT.51"
    ::= { srtEventObjects51 6 }

srt51-circuit-name OBJECT-TYPE
    SYNTAX DisplayString
    MAX-ACCESS accessible-for-notify
    STATUS current
    DESCRIPTION
        "Parameter 'circuit-name' in event SRT.51"
    ::= { srtEventObjects51 7 }

srtEventObjects52 OBJECT-IDENTITY
    STATUS current
    DESCRIPTION
        "Event SRT.52
        The source-routed explorer (ARE or STE routing-type) frame is too large
        to send on this outgoing port and interface. The reformatted-length is
        the size of the frame including MAC headers after any mapping of
        data link headers."
    ::= { srtEventsGroup 52 }

srt52-routing-type OBJECT-TYPE
    SYNTAX DisplayString
    MAX-ACCESS accessible-for-notify
    STATUS current
    DESCRIPTION
        "Parameter 'routing-type' in event SRT.52"
    ::= { srtEventObjects52 1 }

srt52-source-mac OBJECT-TYPE
    SYNTAX DisplayString
    MAX-ACCESS accessible-for-notify
    STATUS current
    DESCRIPTION
        "Parameter 'source-mac' in event SRT.52"
    ::= { srtEventObjects52 2 }

srt52-dest-mac OBJECT-TYPE
    SYNTAX DisplayString
    MAX-ACCESS accessible-for-notify
    STATUS current
    DESCRIPTION
        "Parameter 'dest-mac' in event SRT.52"
    ::= { srtEventObjects52 3 }

srt52-reformatted-length OBJECT-TYPE
    SYNTAX Integer32
    MAX-ACCESS accessible-for-notify
    STATUS current
    DESCRIPTION
        "Parameter 'reformatted-length' in event SRT.52"
    ::= { srtEventObjects52 4 }

srt52-output-maximum OBJECT-TYPE
    SYNTAX Integer32
    MAX-ACCESS accessible-for-notify
    STATUS current
    DESCRIPTION
        "Parameter 'output-maximum' in event SRT.52"
    ::= { srtEventObjects52 5 }

srt52-port OBJECT-TYPE
    SYNTAX Integer32
    MAX-ACCESS accessible-for-notify
    STATUS current
    DESCRIPTION
        "Parameter 'port' in event SRT.52"
    ::= { srtEventObjects52 6 }

srt52-interface OBJECT-TYPE
    SYNTAX DisplayString
    MAX-ACCESS accessible-for-notify
    STATUS current
    DESCRIPTION
        "Parameter 'interface' in event SRT.52"
    ::= { srtEventObjects52 7 }

srt52-circuit-name OBJECT-TYPE
    SYNTAX DisplayString
    MAX-ACCESS accessible-for-notify
    STATUS current
    DESCRIPTION
        "Parameter 'circuit-name' in event SRT.52"
    ::= { srtEventObjects52 8 }

srtEventObjects53 OBJECT-IDENTITY
    STATUS current
    DESCRIPTION
        "Event SRT.53
        A source-routing frame was received with an invalid RIF length encoded
        in the Length bits of the RIF.
        The routing-type is one of SRF (Specifically-routed frame),
        STE (Spanning Tree Expolorer) or ARE (All Routes Explorer)."
    ::= { srtEventsGroup 53 }

srt53-routing-type OBJECT-TYPE
    SYNTAX DisplayString
    MAX-ACCESS accessible-for-notify
    STATUS current
    DESCRIPTION
        "Parameter 'routing-type' in event SRT.53"
    ::= { srtEventObjects53 1 }

srt53-RIF-length OBJECT-TYPE
    SYNTAX Integer32
    MAX-ACCESS accessible-for-notify
    STATUS current
    DESCRIPTION
        "Parameter 'RIF-length' in event SRT.53"
    ::= { srtEventObjects53 2 }

srt53-source-mac OBJECT-TYPE
    SYNTAX DisplayString
    MAX-ACCESS accessible-for-notify
    STATUS current
    DESCRIPTION
        "Parameter 'source-mac' in event SRT.53"
    ::= { srtEventObjects53 3 }

srt53-dest-mac OBJECT-TYPE
    SYNTAX DisplayString
    MAX-ACCESS accessible-for-notify
    STATUS current
    DESCRIPTION
        "Parameter 'dest-mac' in event SRT.53"
    ::= { srtEventObjects53 4 }

srt53-port OBJECT-TYPE
    SYNTAX Integer32
    MAX-ACCESS accessible-for-notify
    STATUS current
    DESCRIPTION
        "Parameter 'port' in event SRT.53"
    ::= { srtEventObjects53 5 }

srt53-interface OBJECT-TYPE
    SYNTAX DisplayString
    MAX-ACCESS accessible-for-notify
    STATUS current
    DESCRIPTION
        "Parameter 'interface' in event SRT.53"
    ::= { srtEventObjects53 6 }

srt53-circuit-name OBJECT-TYPE
    SYNTAX DisplayString
    MAX-ACCESS accessible-for-notify
    STATUS current
    DESCRIPTION
        "Parameter 'circuit-name' in event SRT.53"
    ::= { srtEventObjects53 7 }

srtEventObjects54 OBJECT-IDENTITY
    STATUS current
    DESCRIPTION
        "Event SRT.54
        There is not enough free memory to allocate the hash table for
        the filtering database. The bridge will be disabled."
    ::= { srtEventsGroup 54 }

srt54-requested-size OBJECT-TYPE
    SYNTAX Integer32
    MAX-ACCESS accessible-for-notify
    STATUS current
    DESCRIPTION
        "Parameter 'requested-size' in event SRT.54"
    ::= { srtEventObjects54 1 }

srtEventObjects55 OBJECT-IDENTITY
    STATUS current
    DESCRIPTION
        "Event SRT.55
        There is not enough free memory to allocate the hash table for
        the conversion database. The bridge will be disabled."
    ::= { srtEventsGroup 55 }

srt55-requested-size OBJECT-TYPE
    SYNTAX Integer32
    MAX-ACCESS accessible-for-notify
    STATUS current
    DESCRIPTION
        "Parameter 'requested-size' in event SRT.55"
    ::= { srtEventObjects55 1 }

srtEventObjects56 OBJECT-IDENTITY
    STATUS current
    DESCRIPTION
        "Event SRT.56
        The input queue for source-routed frames to be forwarded is too long,
        and this frame has been dropped to attempt to alleviate the congestion."
    ::= { srtEventsGroup 56 }

srt56-source-mac OBJECT-TYPE
    SYNTAX DisplayString
    MAX-ACCESS accessible-for-notify
    STATUS current
    DESCRIPTION
        "Parameter 'source-mac' in event SRT.56"
    ::= { srtEventObjects56 1 }

srt56-dest-mac OBJECT-TYPE
    SYNTAX DisplayString
    MAX-ACCESS accessible-for-notify
    STATUS current
    DESCRIPTION
        "Parameter 'dest-mac' in event SRT.56"
    ::= { srtEventObjects56 2 }

srt56-interface OBJECT-TYPE
    SYNTAX DisplayString
    MAX-ACCESS accessible-for-notify
    STATUS current
    DESCRIPTION
        "Parameter 'interface' in event SRT.56"
    ::= { srtEventObjects56 3 }

srt56-circuit-name OBJECT-TYPE
    SYNTAX DisplayString
    MAX-ACCESS accessible-for-notify
    STATUS current
    DESCRIPTION
        "Parameter 'circuit-name' in event SRT.56"
    ::= { srtEventObjects56 4 }

srtEventObjects57 OBJECT-IDENTITY
    STATUS current
    DESCRIPTION
        "Event SRT.57
        A frame is being bridged between these two interfaces.
        The destination address was known, so it was sent only to
        the correct destination network."
    ::= { srtEventsGroup 57 }

srt57-source-mac OBJECT-TYPE
    SYNTAX DisplayString
    MAX-ACCESS accessible-for-notify
    STATUS current
    DESCRIPTION
        "Parameter 'source-mac' in event SRT.57"
    ::= { srtEventObjects57 1 }

srt57-dest-mac OBJECT-TYPE
    SYNTAX DisplayString
    MAX-ACCESS accessible-for-notify
    STATUS current
    DESCRIPTION
        "Parameter 'dest-mac' in event SRT.57"
    ::= { srtEventObjects57 2 }

srt57-port OBJECT-TYPE
    SYNTAX Integer32
    MAX-ACCESS accessible-for-notify
    STATUS current
    DESCRIPTION
        "Parameter 'port' in event SRT.57"
    ::= { srtEventObjects57 3 }

srt57-interface OBJECT-TYPE
    SYNTAX DisplayString
    MAX-ACCESS accessible-for-notify
    STATUS current
    DESCRIPTION
        "Parameter 'interface' in event SRT.57"
    ::= { srtEventObjects57 4 }

srt57-circuit-name OBJECT-TYPE
    SYNTAX DisplayString
    MAX-ACCESS accessible-for-notify
    STATUS current
    DESCRIPTION
        "Parameter 'circuit-name' in event SRT.57"
    ::= { srtEventObjects57 5 }

srt57-out-port OBJECT-TYPE
    SYNTAX Integer32
    MAX-ACCESS accessible-for-notify
    STATUS current
    DESCRIPTION
        "Parameter 'out-port' in event SRT.57"
    ::= { srtEventObjects57 6 }

srt57-out-interface OBJECT-TYPE
    SYNTAX DisplayString
    MAX-ACCESS accessible-for-notify
    STATUS current
    DESCRIPTION
        "Parameter 'out-interface' in event SRT.57"
    ::= { srtEventObjects57 7 }

srt57-out-circuit-name OBJECT-TYPE
    SYNTAX DisplayString
    MAX-ACCESS accessible-for-notify
    STATUS current
    DESCRIPTION
        "Parameter 'out-circuit-name' in event SRT.57"
    ::= { srtEventObjects57 8 }

srtEventObjects58 OBJECT-IDENTITY
    STATUS current
    DESCRIPTION
        "Event SRT.58
        The specified transparent bridge frame is too large to send as
        a source-routed frame on this outgoing port and interface.
        The reformatted-length is the size of the frame including MAC headers
        and RIF after any mapping of data link headers."
    ::= { srtEventsGroup 58 }

srt58-source-mac OBJECT-TYPE
    SYNTAX DisplayString
    MAX-ACCESS accessible-for-notify
    STATUS current
    DESCRIPTION
        "Parameter 'source-mac' in event SRT.58"
    ::= { srtEventObjects58 1 }

srt58-dest-mac OBJECT-TYPE
    SYNTAX DisplayString
    MAX-ACCESS accessible-for-notify
    STATUS current
    DESCRIPTION
        "Parameter 'dest-mac' in event SRT.58"
    ::= { srtEventObjects58 2 }

srt58-reformatted-length OBJECT-TYPE
    SYNTAX Integer32
    MAX-ACCESS accessible-for-notify
    STATUS current
    DESCRIPTION
        "Parameter 'reformatted-length' in event SRT.58"
    ::= { srtEventObjects58 3 }

srt58-output-maximum OBJECT-TYPE
    SYNTAX Integer32
    MAX-ACCESS accessible-for-notify
    STATUS current
    DESCRIPTION
        "Parameter 'output-maximum' in event SRT.58"
    ::= { srtEventObjects58 4 }

srt58-port OBJECT-TYPE
    SYNTAX Integer32
    MAX-ACCESS accessible-for-notify
    STATUS current
    DESCRIPTION
        "Parameter 'port' in event SRT.58"
    ::= { srtEventObjects58 5 }

srt58-interface OBJECT-TYPE
    SYNTAX DisplayString
    MAX-ACCESS accessible-for-notify
    STATUS current
    DESCRIPTION
        "Parameter 'interface' in event SRT.58"
    ::= { srtEventObjects58 6 }

srt58-circuit-name OBJECT-TYPE
    SYNTAX DisplayString
    MAX-ACCESS accessible-for-notify
    STATUS current
    DESCRIPTION
        "Parameter 'circuit-name' in event SRT.58"
    ::= { srtEventObjects58 7 }

srtEventObjects59 OBJECT-IDENTITY
    STATUS current
    DESCRIPTION
        "Event SRT.59
        A frame is being conversion bridged between these two interfaces.
        The destination address and RIF were known, so it was sent only to
        the correct destination network."
    ::= { srtEventsGroup 59 }

srt59-source-mac OBJECT-TYPE
    SYNTAX DisplayString
    MAX-ACCESS accessible-for-notify
    STATUS current
    DESCRIPTION
        "Parameter 'source-mac' in event SRT.59"
    ::= { srtEventObjects59 1 }

srt59-dest-mac OBJECT-TYPE
    SYNTAX DisplayString
    MAX-ACCESS accessible-for-notify
    STATUS current
    DESCRIPTION
        "Parameter 'dest-mac' in event SRT.59"
    ::= { srtEventObjects59 2 }

srt59-RIF OBJECT-TYPE
    SYNTAX DisplayString
    MAX-ACCESS accessible-for-notify
    STATUS current
    DESCRIPTION
        "Parameter 'RIF' in event SRT.59"
    ::= { srtEventObjects59 3 }

srt59-port OBJECT-TYPE
    SYNTAX Integer32
    MAX-ACCESS accessible-for-notify
    STATUS current
    DESCRIPTION
        "Parameter 'port' in event SRT.59"
    ::= { srtEventObjects59 4 }

srt59-interface OBJECT-TYPE
    SYNTAX DisplayString
    MAX-ACCESS accessible-for-notify
    STATUS current
    DESCRIPTION
        "Parameter 'interface' in event SRT.59"
    ::= { srtEventObjects59 5 }

srt59-circuit-name OBJECT-TYPE
    SYNTAX DisplayString
    MAX-ACCESS accessible-for-notify
    STATUS current
    DESCRIPTION
        "Parameter 'circuit-name' in event SRT.59"
    ::= { srtEventObjects59 6 }

srt59-out-port OBJECT-TYPE
    SYNTAX Integer32
    MAX-ACCESS accessible-for-notify
    STATUS current
    DESCRIPTION
        "Parameter 'out-port' in event SRT.59"
    ::= { srtEventObjects59 7 }

srt59-out-interface OBJECT-TYPE
    SYNTAX DisplayString
    MAX-ACCESS accessible-for-notify
    STATUS current
    DESCRIPTION
        "Parameter 'out-interface' in event SRT.59"
    ::= { srtEventObjects59 8 }

srt59-out-circuit-name OBJECT-TYPE
    SYNTAX DisplayString
    MAX-ACCESS accessible-for-notify
    STATUS current
    DESCRIPTION
        "Parameter 'out-circuit-name' in event SRT.59"
    ::= { srtEventObjects59 9 }

srtEventObjects60 OBJECT-IDENTITY
    STATUS current
    DESCRIPTION
        "Event SRT.60
        A frame is being conversion bridged to all active source-routing ports.
        This happens when the frame destination is a multicast or when
        the frame destination is not in the source-routing learning database.
        There will be one message for each port the frame is sent on."
    ::= { srtEventsGroup 60 }

srt60-source-mac OBJECT-TYPE
    SYNTAX DisplayString
    MAX-ACCESS accessible-for-notify
    STATUS current
    DESCRIPTION
        "Parameter 'source-mac' in event SRT.60"
    ::= { srtEventObjects60 1 }

srt60-dest-mac OBJECT-TYPE
    SYNTAX DisplayString
    MAX-ACCESS accessible-for-notify
    STATUS current
    DESCRIPTION
        "Parameter 'dest-mac' in event SRT.60"
    ::= { srtEventObjects60 2 }

srt60-RIF OBJECT-TYPE
    SYNTAX Integer32
    MAX-ACCESS accessible-for-notify
    STATUS current
    DESCRIPTION
        "Parameter 'RIF' in event SRT.60"
    ::= { srtEventObjects60 3 }

srt60-port OBJECT-TYPE
    SYNTAX Integer32
    MAX-ACCESS accessible-for-notify
    STATUS current
    DESCRIPTION
        "Parameter 'port' in event SRT.60"
    ::= { srtEventObjects60 4 }

srt60-interface OBJECT-TYPE
    SYNTAX DisplayString
    MAX-ACCESS accessible-for-notify
    STATUS current
    DESCRIPTION
        "Parameter 'interface' in event SRT.60"
    ::= { srtEventObjects60 5 }

srt60-circuit-name OBJECT-TYPE
    SYNTAX DisplayString
    MAX-ACCESS accessible-for-notify
    STATUS current
    DESCRIPTION
        "Parameter 'circuit-name' in event SRT.60"
    ::= { srtEventObjects60 6 }

srt60-out-port OBJECT-TYPE
    SYNTAX Integer32
    MAX-ACCESS accessible-for-notify
    STATUS current
    DESCRIPTION
        "Parameter 'out-port' in event SRT.60"
    ::= { srtEventObjects60 7 }

srt60-out-interface OBJECT-TYPE
    SYNTAX DisplayString
    MAX-ACCESS accessible-for-notify
    STATUS current
    DESCRIPTION
        "Parameter 'out-interface' in event SRT.60"
    ::= { srtEventObjects60 8 }

srt60-out-circuit-name OBJECT-TYPE
    SYNTAX DisplayString
    MAX-ACCESS accessible-for-notify
    STATUS current
    DESCRIPTION
        "Parameter 'out-circuit-name' in event SRT.60"
    ::= { srtEventObjects60 9 }

srtEventObjects61 OBJECT-IDENTITY
    STATUS current
    DESCRIPTION
        "Event SRT.61
        A Specifically Routed frame has been received whose RIF would send it
        on the specified port, but that port is not configured for bridging."
    ::= { srtEventsGroup 61 }

srt61-source-mac OBJECT-TYPE
    SYNTAX DisplayString
    MAX-ACCESS accessible-for-notify
    STATUS current
    DESCRIPTION
        "Parameter 'source-mac' in event SRT.61"
    ::= { srtEventObjects61 1 }

srt61-dest-mac OBJECT-TYPE
    SYNTAX DisplayString
    MAX-ACCESS accessible-for-notify
    STATUS current
    DESCRIPTION
        "Parameter 'dest-mac' in event SRT.61"
    ::= { srtEventObjects61 2 }

srt61-RIF OBJECT-TYPE
    SYNTAX DisplayString
    MAX-ACCESS accessible-for-notify
    STATUS current
    DESCRIPTION
        "Parameter 'RIF' in event SRT.61"
    ::= { srtEventObjects61 3 }

srt61-port OBJECT-TYPE
    SYNTAX Integer32
    MAX-ACCESS accessible-for-notify
    STATUS current
    DESCRIPTION
        "Parameter 'port' in event SRT.61"
    ::= { srtEventObjects61 4 }

srt61-interface OBJECT-TYPE
    SYNTAX DisplayString
    MAX-ACCESS accessible-for-notify
    STATUS current
    DESCRIPTION
        "Parameter 'interface' in event SRT.61"
    ::= { srtEventObjects61 5 }

srt61-circuit-name OBJECT-TYPE
    SYNTAX DisplayString
    MAX-ACCESS accessible-for-notify
    STATUS current
    DESCRIPTION
        "Parameter 'circuit-name' in event SRT.61"
    ::= { srtEventObjects61 6 }

srtEventObjects62 OBJECT-IDENTITY
    STATUS current
    DESCRIPTION
        "Event SRT.62
        The specified source-routed frame is larger than that is allowed
        by LF-BIT configuration for the transparent bridge domain. After mapping
        to the MAC headers of the outgoing port, the packet may get dropped
        if it exceeds the MSDU limit of the port."
    ::= { srtEventsGroup 62 }

srt62-source-mac OBJECT-TYPE
    SYNTAX DisplayString
    MAX-ACCESS accessible-for-notify
    STATUS current
    DESCRIPTION
        "Parameter 'source-mac' in event SRT.62"
    ::= { srtEventObjects62 1 }

srt62-dest-mac OBJECT-TYPE
    SYNTAX DisplayString
    MAX-ACCESS accessible-for-notify
    STATUS current
    DESCRIPTION
        "Parameter 'dest-mac' in event SRT.62"
    ::= { srtEventObjects62 2 }

srt62-reformatted-length OBJECT-TYPE
    SYNTAX Integer32
    MAX-ACCESS accessible-for-notify
    STATUS current
    DESCRIPTION
        "Parameter 'reformatted-length' in event SRT.62"
    ::= { srtEventObjects62 3 }

srt62-output-maximum OBJECT-TYPE
    SYNTAX Integer32
    MAX-ACCESS accessible-for-notify
    STATUS current
    DESCRIPTION
        "Parameter 'output-maximum' in event SRT.62"
    ::= { srtEventObjects62 4 }

srt62-port OBJECT-TYPE
    SYNTAX Integer32
    MAX-ACCESS accessible-for-notify
    STATUS current
    DESCRIPTION
        "Parameter 'port' in event SRT.62"
    ::= { srtEventObjects62 5 }

srt62-interface OBJECT-TYPE
    SYNTAX DisplayString
    MAX-ACCESS accessible-for-notify
    STATUS current
    DESCRIPTION
        "Parameter 'interface' in event SRT.62"
    ::= { srtEventObjects62 6 }

srt62-circuit-name OBJECT-TYPE
    SYNTAX DisplayString
    MAX-ACCESS accessible-for-notify
    STATUS current
    DESCRIPTION
        "Parameter 'circuit-name' in event SRT.62"
    ::= { srtEventObjects62 7 }

srtEventObjects63 OBJECT-IDENTITY
    STATUS current
    DESCRIPTION
        "Event SRT.63
        No buffer available to copy a frame in order to send Routes Explorer
        (ARE) or Spanning Tree Explorer (STE) routing-type frame out as
        a transparent bridged frame in the transparent bridging domain.
        No copy of this frame will be sent into the transparent bridge domain."
    ::= { srtEventsGroup 63 }

srt63-routing-type OBJECT-TYPE
    SYNTAX DisplayString
    MAX-ACCESS accessible-for-notify
    STATUS current
    DESCRIPTION
        "Parameter 'routing-type' in event SRT.63"
    ::= { srtEventObjects63 1 }

srt63-source-mac OBJECT-TYPE
    SYNTAX DisplayString
    MAX-ACCESS accessible-for-notify
    STATUS current
    DESCRIPTION
        "Parameter 'source-mac' in event SRT.63"
    ::= { srtEventObjects63 2 }

srt63-dest-mac OBJECT-TYPE
    SYNTAX DisplayString
    MAX-ACCESS accessible-for-notify
    STATUS current
    DESCRIPTION
        "Parameter 'dest-mac' in event SRT.63"
    ::= { srtEventObjects63 3 }

srt63-port OBJECT-TYPE
    SYNTAX Integer32
    MAX-ACCESS accessible-for-notify
    STATUS current
    DESCRIPTION
        "Parameter 'port' in event SRT.63"
    ::= { srtEventObjects63 4 }

srt63-interface OBJECT-TYPE
    SYNTAX DisplayString
    MAX-ACCESS accessible-for-notify
    STATUS current
    DESCRIPTION
        "Parameter 'interface' in event SRT.63"
    ::= { srtEventObjects63 5 }

srt63-circuit-name OBJECT-TYPE
    SYNTAX DisplayString
    MAX-ACCESS accessible-for-notify
    STATUS current
    DESCRIPTION
        "Parameter 'circuit-name' in event SRT.63"
    ::= { srtEventObjects63 6 }

srtEventObjects64 OBJECT-IDENTITY
    STATUS current
    DESCRIPTION
        "Event SRT.64
        There is not enough free memory to allocate even a minimal size
        conversion database. The bridge will be disabled."
    ::= { srtEventsGroup 64 }

srt64-requested-size OBJECT-TYPE
    SYNTAX Integer32
    MAX-ACCESS accessible-for-notify
    STATUS current
    DESCRIPTION
        "Parameter 'requested-size' in event SRT.64"
    ::= { srtEventObjects64 1 }

srtEventObjects65 OBJECT-IDENTITY
    STATUS current
    DESCRIPTION
        "Event SRT.65
        An attempt to add a particular static entry to the internal database of
        a bridging interface having internal filtering failed."
    ::= { srtEventsGroup 65 }

srt65-MAC-address OBJECT-TYPE
    SYNTAX DisplayString
    MAX-ACCESS accessible-for-notify
    STATUS current
    DESCRIPTION
        "Parameter 'MAC-address' in event SRT.65"
    ::= { srtEventObjects65 1 }

srt65-interface OBJECT-TYPE
    SYNTAX DisplayString
    MAX-ACCESS accessible-for-notify
    STATUS current
    DESCRIPTION
        "Parameter 'interface' in event SRT.65"
    ::= { srtEventObjects65 2 }

srtEventObjects66 OBJECT-IDENTITY
    STATUS current
    DESCRIPTION
        "Event SRT.66
        The bridge has been configured to enable transparent bridging on
        an IEEE 802.5 Token-Ring interface that does not have the hardware
        to support transparent bridging. Transparent bridging will not be
        enabled on this interface."
    ::= { srtEventsGroup 66 }

srt66-interface OBJECT-TYPE
    SYNTAX DisplayString
    MAX-ACCESS accessible-for-notify
    STATUS current
    DESCRIPTION
        "Parameter 'interface' in event SRT.66"
    ::= { srtEventObjects66 1 }

srt66-circuit-name OBJECT-TYPE
    SYNTAX DisplayString
    MAX-ACCESS accessible-for-notify
    STATUS current
    DESCRIPTION
        "Parameter 'circuit-name' in event SRT.66"
    ::= { srtEventObjects66 2 }

srtEventObjects67 OBJECT-IDENTITY
    STATUS current
    DESCRIPTION
        "Event SRT.67
        A Specifically Routed frame has been sent on a port, but that port is
        not configured for bridging. This should never happen, since prior
        checks should prevent calling this code if the port is not configured
        for bridging."
    ::= { srtEventsGroup 67 }

srt67-source-mac OBJECT-TYPE
    SYNTAX DisplayString
    MAX-ACCESS accessible-for-notify
    STATUS current
    DESCRIPTION
        "Parameter 'source-mac' in event SRT.67"
    ::= { srtEventObjects67 1 }

srt67-dest-mac OBJECT-TYPE
    SYNTAX DisplayString
    MAX-ACCESS accessible-for-notify
    STATUS current
    DESCRIPTION
        "Parameter 'dest-mac' in event SRT.67"
    ::= { srtEventObjects67 2 }

srt67-RIF OBJECT-TYPE
    SYNTAX DisplayString
    MAX-ACCESS accessible-for-notify
    STATUS current
    DESCRIPTION
        "Parameter 'RIF' in event SRT.67"
    ::= { srtEventObjects67 3 }

srt67-port OBJECT-TYPE
    SYNTAX Integer32
    MAX-ACCESS accessible-for-notify
    STATUS current
    DESCRIPTION
        "Parameter 'port' in event SRT.67"
    ::= { srtEventObjects67 4 }

srt67-interface OBJECT-TYPE
    SYNTAX DisplayString
    MAX-ACCESS accessible-for-notify
    STATUS current
    DESCRIPTION
        "Parameter 'interface' in event SRT.67"
    ::= { srtEventObjects67 5 }

srt67-circuit-name OBJECT-TYPE
    SYNTAX DisplayString
    MAX-ACCESS accessible-for-notify
    STATUS current
    DESCRIPTION
        "Parameter 'circuit-name' in event SRT.67"
    ::= { srtEventObjects67 6 }

srtEventObjects68 OBJECT-IDENTITY
    STATUS current
    DESCRIPTION
        "Event SRT.68
        There is no space in the Ethernet type registration table for
        the specified ethernet-type. This happens when there are too many
        hash collisions, and there are not enough overflow buckets."
    ::= { srtEventsGroup 68 }

srt68-ethernet-type OBJECT-TYPE
    SYNTAX Integer32
    MAX-ACCESS accessible-for-notify
    STATUS current
    DESCRIPTION
        "Parameter 'ethernet-type' in event SRT.68"
    ::= { srtEventObjects68 1 }

srtEventObjects69 OBJECT-IDENTITY
    STATUS current
    DESCRIPTION
        "Event SRT.69
        There is no space in the SNAP PID registration table for
        the specified protocol. This happens when there are too many
        hash collisions, and there are not enough overflow buckets."
    ::= { srtEventsGroup 69 }

srt69-protocol OBJECT-TYPE
    SYNTAX Integer32
    MAX-ACCESS accessible-for-notify
    STATUS current
    DESCRIPTION
        "Parameter 'protocol' in event SRT.69"
    ::= { srtEventObjects69 1 }

srtEventObjects70 OBJECT-IDENTITY
    STATUS current
    DESCRIPTION
        "Event SRT.70
        A MAC frame has been received by the hardware, but is being dropped
        because the destination MAC address is being administratively filtered
        by the bridge. The frame will be dropped."
    ::= { srtEventsGroup 70 }

srt70-source-mac OBJECT-TYPE
    SYNTAX DisplayString
    MAX-ACCESS accessible-for-notify
    STATUS current
    DESCRIPTION
        "Parameter 'source-mac' in event SRT.70"
    ::= { srtEventObjects70 1 }

srt70-dest-mac OBJECT-TYPE
    SYNTAX DisplayString
    MAX-ACCESS accessible-for-notify
    STATUS current
    DESCRIPTION
        "Parameter 'dest-mac' in event SRT.70"
    ::= { srtEventObjects70 2 }

srt70-port OBJECT-TYPE
    SYNTAX Integer32
    MAX-ACCESS accessible-for-notify
    STATUS current
    DESCRIPTION
        "Parameter 'port' in event SRT.70"
    ::= { srtEventObjects70 3 }

srt70-interface OBJECT-TYPE
    SYNTAX DisplayString
    MAX-ACCESS accessible-for-notify
    STATUS current
    DESCRIPTION
        "Parameter 'interface' in event SRT.70"
    ::= { srtEventObjects70 4 }

srt70-circuit-name OBJECT-TYPE
    SYNTAX DisplayString
    MAX-ACCESS accessible-for-notify
    STATUS current
    DESCRIPTION
        "Parameter 'circuit-name' in event SRT.70"
    ::= { srtEventObjects70 5 }

srtEventObjects71 OBJECT-IDENTITY
    STATUS current
    DESCRIPTION
        "Event SRT.71
        Source Routing is configured on the port which is attached to an
        underlying network which inherently does not support source routing
        type of functionalities. Such networks are Ethernet and FDDI.
        Bridge disables source routing on the port."
    ::= { srtEventsGroup 71 }

srt71-port OBJECT-TYPE
    SYNTAX Integer32
    MAX-ACCESS accessible-for-notify
    STATUS current
    DESCRIPTION
        "Parameter 'port' in event SRT.71"
    ::= { srtEventObjects71 1 }

srt71-interface OBJECT-TYPE
    SYNTAX DisplayString
    MAX-ACCESS accessible-for-notify
    STATUS current
    DESCRIPTION
        "Parameter 'interface' in event SRT.71"
    ::= { srtEventObjects71 2 }

srt71-circuit-name OBJECT-TYPE
    SYNTAX DisplayString
    MAX-ACCESS accessible-for-notify
    STATUS current
    DESCRIPTION
        "Parameter 'circuit-name' in event SRT.71"
    ::= { srtEventObjects71 3 }

srtEventObjects74 OBJECT-IDENTITY
    STATUS current
    DESCRIPTION
        "Event SRT.74
        Source-routing bridging has been enabled, but that feature was not
        purchased as part of this software load. The source-routing bridging
        feature will not be enabled."
    ::= { srtEventsGroup 74 }

srt74-interface OBJECT-TYPE
    SYNTAX DisplayString
    MAX-ACCESS accessible-for-notify
    STATUS current
    DESCRIPTION
        "Parameter 'interface' in event SRT.74"
    ::= { srtEventObjects74 1 }

srt74-circuit-name OBJECT-TYPE
    SYNTAX DisplayString
    MAX-ACCESS accessible-for-notify
    STATUS current
    DESCRIPTION
        "Parameter 'circuit-name' in event SRT.74"
    ::= { srtEventObjects74 2 }

srtEventObjects75 OBJECT-IDENTITY
    STATUS current
    DESCRIPTION
        "Event SRT.75
        Spanning tree (transparent) bridging has been enabled, but that feature
        was not purchased as part of this software load.
        The spanning tree (transparent) bridging feature will not be enabled."
    ::= { srtEventsGroup 75 }

srt75-interface OBJECT-TYPE
    SYNTAX DisplayString
    MAX-ACCESS accessible-for-notify
    STATUS current
    DESCRIPTION
        "Parameter 'interface' in event SRT.75"
    ::= { srtEventObjects75 1 }

srt75-circuit-name OBJECT-TYPE
    SYNTAX DisplayString
    MAX-ACCESS accessible-for-notify
    STATUS current
    DESCRIPTION
        "Parameter 'circuit-name' in event SRT.75"
    ::= { srtEventObjects75 2 }

srtEventObjects77 OBJECT-IDENTITY
    STATUS current
    DESCRIPTION
        "Event SRT.77
        The user deleted a filter list, which was part of an already
        configured filter. The filter will not be enabled."
    ::= { srtEventsGroup 77 }

srt77-input-output OBJECT-TYPE
    SYNTAX DisplayString
    MAX-ACCESS accessible-for-notify
    STATUS current
    DESCRIPTION
        "Parameter 'input-output' in event SRT.77"
    ::= { srtEventObjects77 1 }

srt77-port-number OBJECT-TYPE
    SYNTAX Integer32
    MAX-ACCESS accessible-for-notify
    STATUS current
    DESCRIPTION
        "Parameter 'port-number' in event SRT.77"
    ::= { srtEventObjects77 2 }

srtEventObjects78 OBJECT-IDENTITY
    STATUS current
    DESCRIPTION
        "Event SRT.78
        The user configured a NETBIOS filter for a particular port, but that
        port number is not configured."
    ::= { srtEventsGroup 78 }

srt78-input-output OBJECT-TYPE
    SYNTAX DisplayString
    MAX-ACCESS accessible-for-notify
    STATUS current
    DESCRIPTION
        "Parameter 'input-output' in event SRT.78"
    ::= { srtEventObjects78 1 }

srt78-port-number OBJECT-TYPE
    SYNTAX Integer32
    MAX-ACCESS accessible-for-notify
    STATUS current
    DESCRIPTION
        "Parameter 'port-number' in event SRT.78"
    ::= { srtEventObjects78 2 }

srtEventObjects79 OBJECT-IDENTITY
    STATUS current
    DESCRIPTION
        "Event SRT.79
        A NETBIOS packet has matched the criteria specified in a NETBIOS Filter
        configuration record. The packet is dropped."
    ::= { srtEventsGroup 79 }

srt79-source-mac OBJECT-TYPE
    SYNTAX DisplayString
    MAX-ACCESS accessible-for-notify
    STATUS current
    DESCRIPTION
        "Parameter 'source-mac' in event SRT.79"
    ::= { srtEventObjects79 1 }

srt79-dest-mac OBJECT-TYPE
    SYNTAX DisplayString
    MAX-ACCESS accessible-for-notify
    STATUS current
    DESCRIPTION
        "Parameter 'dest-mac' in event SRT.79"
    ::= { srtEventObjects79 2 }

srt79-port OBJECT-TYPE
    SYNTAX Integer32
    MAX-ACCESS accessible-for-notify
    STATUS current
    DESCRIPTION
        "Parameter 'port' in event SRT.79"
    ::= { srtEventObjects79 3 }

srt79-interface OBJECT-TYPE
    SYNTAX DisplayString
    MAX-ACCESS accessible-for-notify
    STATUS current
    DESCRIPTION
        "Parameter 'interface' in event SRT.79"
    ::= { srtEventObjects79 4 }

srt79-circuit-name OBJECT-TYPE
    SYNTAX DisplayString
    MAX-ACCESS accessible-for-notify
    STATUS current
    DESCRIPTION
        "Parameter 'circuit-name' in event SRT.79"
    ::= { srtEventObjects79 5 }

srtEventObjects81 OBJECT-IDENTITY
    STATUS current
    DESCRIPTION
        "Event SRT.81
        A NETBIOS STE converted to SRF by NETBIOS Name Caching."
    ::= { srtEventsGroup 81 }

srt81-RIF OBJECT-TYPE
    SYNTAX DisplayString
    MAX-ACCESS accessible-for-notify
    STATUS current
    DESCRIPTION
        "Parameter 'RIF' in event SRT.81"
    ::= { srtEventObjects81 1 }

srt81-source-mac OBJECT-TYPE
    SYNTAX DisplayString
    MAX-ACCESS accessible-for-notify
    STATUS current
    DESCRIPTION
        "Parameter 'source-mac' in event SRT.81"
    ::= { srtEventObjects81 2 }

srt81-dest-mac OBJECT-TYPE
    SYNTAX DisplayString
    MAX-ACCESS accessible-for-notify
    STATUS current
    DESCRIPTION
        "Parameter 'dest-mac' in event SRT.81"
    ::= { srtEventObjects81 3 }

srt81-port OBJECT-TYPE
    SYNTAX Integer32
    MAX-ACCESS accessible-for-notify
    STATUS current
    DESCRIPTION
        "Parameter 'port' in event SRT.81"
    ::= { srtEventObjects81 4 }

srtEventObjects83 OBJECT-IDENTITY
    STATUS current
    DESCRIPTION
        "Event SRT.83
        A NETBIOS find-name STE has been filtered."
    ::= { srtEventsGroup 83 }

srt83-RIF OBJECT-TYPE
    SYNTAX DisplayString
    MAX-ACCESS accessible-for-notify
    STATUS current
    DESCRIPTION
        "Parameter 'RIF' in event SRT.83"
    ::= { srtEventObjects83 1 }

srt83-source-mac OBJECT-TYPE
    SYNTAX DisplayString
    MAX-ACCESS accessible-for-notify
    STATUS current
    DESCRIPTION
        "Parameter 'source-mac' in event SRT.83"
    ::= { srtEventObjects83 2 }

srt83-dest-mac OBJECT-TYPE
    SYNTAX DisplayString
    MAX-ACCESS accessible-for-notify
    STATUS current
    DESCRIPTION
        "Parameter 'dest-mac' in event SRT.83"
    ::= { srtEventObjects83 3 }

srt83-port OBJECT-TYPE
    SYNTAX Integer32
    MAX-ACCESS accessible-for-notify
    STATUS current
    DESCRIPTION
        "Parameter 'port' in event SRT.83"
    ::= { srtEventObjects83 4 }

srtEventObjects84 OBJECT-IDENTITY
    STATUS current
    DESCRIPTION
        "Event SRT.84
        A spanning tree BPDU frame was received on a port that has been
        disabled for spanning tree participation by the 'disable tree port#'
        command."
    ::= { srtEventsGroup 84 }

srt84-port OBJECT-TYPE
    SYNTAX Integer32
    MAX-ACCESS accessible-for-notify
    STATUS current
    DESCRIPTION
        "Parameter 'port' in event SRT.84"
    ::= { srtEventObjects84 1 }

srt84-interface OBJECT-TYPE
    SYNTAX DisplayString
    MAX-ACCESS accessible-for-notify
    STATUS current
    DESCRIPTION
        "Parameter 'interface' in event SRT.84"
    ::= { srtEventObjects84 2 }

srtEventObjects85 OBJECT-IDENTITY
    STATUS current
    DESCRIPTION
        "Event SRT.85
        The port has been configured to use a Frame Relay interface. However,
        subsequent to bridge configuration, device configuration changed such
        that the device is no longer configured to be a Frame Relay device.
        This could have happened if the user changed the data link support
        on the device, or re-ordered the device records."
    ::= { srtEventsGroup 85 }

srt85-port OBJECT-TYPE
    SYNTAX Integer32
    MAX-ACCESS accessible-for-notify
    STATUS current
    DESCRIPTION
        "Parameter 'port' in event SRT.85"
    ::= { srtEventObjects85 1 }

srt85-interface-number OBJECT-TYPE
    SYNTAX Integer32
    MAX-ACCESS accessible-for-notify
    STATUS current
    DESCRIPTION
        "Parameter 'interface-number' in event SRT.85"
    ::= { srtEventObjects85 2 }

srtEventObjects86 OBJECT-IDENTITY
    STATUS current
    DESCRIPTION
        "Event SRT.86
        During bridge initialization, ports are associated with Frame Relay
        registers with the Frame Relay interface. During registration, both let
        each other know about their existence and exchange some
        useful information to keep about each other."
    ::= { srtEventsGroup 86 }

srt86-port OBJECT-TYPE
    SYNTAX Integer32
    MAX-ACCESS accessible-for-notify
    STATUS current
    DESCRIPTION
        "Parameter 'port' in event SRT.86"
    ::= { srtEventObjects86 1 }

srt86-circuit-name OBJECT-TYPE
    SYNTAX DisplayString
    MAX-ACCESS accessible-for-notify
    STATUS current
    DESCRIPTION
        "Parameter 'circuit-name' in event SRT.86"
    ::= { srtEventObjects86 2 }

srt86-interface OBJECT-TYPE
    SYNTAX DisplayString
    MAX-ACCESS accessible-for-notify
    STATUS current
    DESCRIPTION
        "Parameter 'interface' in event SRT.86"
    ::= { srtEventObjects86 3 }

srt86-reason OBJECT-TYPE
    SYNTAX DisplayString
    MAX-ACCESS accessible-for-notify
    STATUS current
    DESCRIPTION
        "Parameter 'reason' in event SRT.86"
    ::= { srtEventObjects86 4 }

srtEventObjects87 OBJECT-IDENTITY
    STATUS current
    DESCRIPTION
        "Event SRT.87
        An All Routes Explorer (ARE) source-routed frame has more
        Route Descriptors than this bridge is configured to allow for
        ARE frames.
        The frame will be dropped."
    ::= { srtEventsGroup 87 }

srt87-source-mac OBJECT-TYPE
    SYNTAX DisplayString
    MAX-ACCESS accessible-for-notify
    STATUS current
    DESCRIPTION
        "Parameter 'source-mac' in event SRT.87"
    ::= { srtEventObjects87 1 }

srt87-dest-mac OBJECT-TYPE
    SYNTAX DisplayString
    MAX-ACCESS accessible-for-notify
    STATUS current
    DESCRIPTION
        "Parameter 'dest-mac' in event SRT.87"
    ::= { srtEventObjects87 2 }

srt87-port OBJECT-TYPE
    SYNTAX Integer32
    MAX-ACCESS accessible-for-notify
    STATUS current
    DESCRIPTION
        "Parameter 'port' in event SRT.87"
    ::= { srtEventObjects87 3 }

srt87-interface OBJECT-TYPE
    SYNTAX DisplayString
    MAX-ACCESS accessible-for-notify
    STATUS current
    DESCRIPTION
        "Parameter 'interface' in event SRT.87"
    ::= { srtEventObjects87 4 }

srt87-circuit-name OBJECT-TYPE
    SYNTAX DisplayString
    MAX-ACCESS accessible-for-notify
    STATUS current
    DESCRIPTION
        "Parameter 'circuit-name' in event SRT.87"
    ::= { srtEventObjects87 5 }

srtEventObjects89 OBJECT-IDENTITY
    STATUS current
    DESCRIPTION
        "Event SRT.89
        A frame is being bridged between these two interfaces. The destination
        address was broadcast or unregistered."
    ::= { srtEventsGroup 89 }

srt89-source-mac OBJECT-TYPE
    SYNTAX DisplayString
    MAX-ACCESS accessible-for-notify
    STATUS current
    DESCRIPTION
        "Parameter 'source-mac' in event SRT.89"
    ::= { srtEventObjects89 1 }

srt89-dest-mac OBJECT-TYPE
    SYNTAX DisplayString
    MAX-ACCESS accessible-for-notify
    STATUS current
    DESCRIPTION
        "Parameter 'dest-mac' in event SRT.89"
    ::= { srtEventObjects89 2 }

srt89-port OBJECT-TYPE
    SYNTAX Integer32
    MAX-ACCESS accessible-for-notify
    STATUS current
    DESCRIPTION
        "Parameter 'port' in event SRT.89"
    ::= { srtEventObjects89 3 }

srt89-interface OBJECT-TYPE
    SYNTAX DisplayString
    MAX-ACCESS accessible-for-notify
    STATUS current
    DESCRIPTION
        "Parameter 'interface' in event SRT.89"
    ::= { srtEventObjects89 4 }

srt89-circuit-name OBJECT-TYPE
    SYNTAX DisplayString
    MAX-ACCESS accessible-for-notify
    STATUS current
    DESCRIPTION
        "Parameter 'circuit-name' in event SRT.89"
    ::= { srtEventObjects89 5 }

srt89-out-port OBJECT-TYPE
    SYNTAX Integer32
    MAX-ACCESS accessible-for-notify
    STATUS current
    DESCRIPTION
        "Parameter 'out-port' in event SRT.89"
    ::= { srtEventObjects89 6 }

srt89-out-interface OBJECT-TYPE
    SYNTAX DisplayString
    MAX-ACCESS accessible-for-notify
    STATUS current
    DESCRIPTION
        "Parameter 'out-interface' in event SRT.89"
    ::= { srtEventObjects89 7 }

srt89-out-circuit-name OBJECT-TYPE
    SYNTAX DisplayString
    MAX-ACCESS accessible-for-notify
    STATUS current
    DESCRIPTION
        "Parameter 'out-circuit-name' in event SRT.89"
    ::= { srtEventObjects89 8 }

srtEventObjects90 OBJECT-IDENTITY
    STATUS current
    DESCRIPTION
        "Event SRT.90
        A VLAN tagged frame on a ethernet subinterface was received but bridging 
        is disabled for vlans.
        The frame will not be bridged."
    ::= { srtEventsGroup 90 }

srt90-source-mac OBJECT-TYPE
    SYNTAX DisplayString
    MAX-ACCESS accessible-for-notify
    STATUS current
    DESCRIPTION
        "Parameter 'source-mac' in event SRT.90"
    ::= { srtEventObjects90 1 }

srt90-dest-mac OBJECT-TYPE
    SYNTAX DisplayString
    MAX-ACCESS accessible-for-notify
    STATUS current
    DESCRIPTION
        "Parameter 'dest-mac' in event SRT.90"
    ::= { srtEventObjects90 2 }

srt90-vid OBJECT-TYPE
    SYNTAX Integer32
    MAX-ACCESS accessible-for-notify
    STATUS current
    DESCRIPTION
        "Parameter 'vid' in event SRT.90"
    ::= { srtEventObjects90 3 }


srtNotification1 NOTIFICATION-TYPE
    OBJECTS { 
              srt1-source-mac, 
              srt1-dest-mac,
              srt1-port,
              srt1-interface,
              srt1-circuit-name 
            }
    STATUS current
    DESCRIPTION
        "Notification of Event SRT.1

        Message: 'No buffer available to duplicate frame from $1 to $2 on port $3, interface $4$5'

        Parameters list:
              $1: srt1-source-mac
              $2: srt1-dest-mac
              $3: srt1-port
              $4: srt1-interface
              $5: srt1-circuit-name

        No buffer available to copy a frame in order to send a bridged frame on
        multiple interfaces. Bridged packets are sent on multiple interfaces
        either for multicast destination addresses, or in the case of
        certain static entries. No copy of this frame will be sent on
        the specified port and interface."
    ::= { srtNotificationsPrefix 1 }

srtNotification2 NOTIFICATION-TYPE
    OBJECTS { 
              srt2-error-code, 
              srt2-interface,
              srt2-circuit-name 
            }
    STATUS current
    DESCRIPTION
        "Notification of Event SRT.2

        Message: 'Error code $1 trying to set promiscuous mode on interface $2$3'

        Parameters list:
              $1: srt2-error-code
              $2: srt2-interface
              $3: srt2-circuit-name

        The Spanning Tree Protocol requested setting this network into
        Learning state, but the command to the device failed. The error-code is
        a device-specific error code that may indicate what the error is."
    ::= { srtNotificationsPrefix 2 }

srtNotification3 NOTIFICATION-TYPE
    OBJECTS { 
              srt3-error-code, 
              srt3-interface,
              srt3-circuit-name 
            }
    STATUS current
    DESCRIPTION
        "Notification of Event SRT.3

        Message: 'Error code $1 trying to add static entries on interface $2$3'

        Parameters list:
              $1: srt3-error-code
              $2: srt3-interface
              $3: srt3-circuit-name

        An attempt to add a set of static entries to the internal database of
        a bridging interface having internal filtering failed.
        The error-code is a device-specific error code that may indicate
        what the error is."
    ::= { srtNotificationsPrefix 3 }

srtNotification4 NOTIFICATION-TYPE
    OBJECTS { 
              srt4-command-name, 
              srt4-interface 
            }
    STATUS current
    DESCRIPTION
        "Notification of Event SRT.4

        Message: 'No buffer available for $1 command to interface $2'

        Parameters list:
              $1: srt4-command-name
              $2: srt4-interface

        No buffer was available to send a command to the device.
        The possible command names are
        'D-CNFGSRB' (configure source-routing bridging),
        'SRT-ON' (promiscuous on),
        'SRT-INFORM' (learn capabilities of device),
        'SRT-SET-AGE' (set age for filtering database in device),
        'SRT-DECR-AGE' (do ageing pass on filtering database in device),
        'SRT-ADD-ENTRY' (add static entry),
        'SRT-DEL-ENTRY' (delete entry, from console),
        'SRT-SEARCH-ENTRY' (search for particular entry, from console) and
        'SRT-LIST-ENTRY' (list contents of learning database in card).
        For commands 'D-CNFGSRB' and 'SRT-ON' the result will be that
        the interface may remain in the wrong state. A failure on 'SRT-INFORM'
        could cause serious problems. For other commands the results will be
        less serious."
    ::= { srtNotificationsPrefix 4 }

srtNotification5 NOTIFICATION-TYPE
    OBJECTS { 
              srt5-source-mac, 
              srt5-dest-mac,
              srt5-reason-code,
              srt5-port,
              srt5-interface-name,
              srt5-circuit-name 
            }
    STATUS current
    DESCRIPTION
        "Notification of Event SRT.5

        Message: 'Sending frame from $1 to $2 failed, reason $3, on port $4 interface $5$6'

        Parameters list:
              $1: srt5-source-mac
              $2: srt5-dest-mac
              $3: srt5-reason-code
              $4: srt5-port
              $5: srt5-interface-name
              $6: srt5-circuit-name

        The sending of a packet being forwarded failed. The reason is
        the internal error code for the failure."
    ::= { srtNotificationsPrefix 5 }

srtNotification6 NOTIFICATION-TYPE
    OBJECTS { 
              srt6-source-mac, 
              srt6-dest-mac,
              srt6-interface,
              srt6-circuit-name 
            }
    STATUS current
    DESCRIPTION
        "Notification of Event SRT.6

        Message: 'Input queue overflow on frame from $1 to $2, packet dropped interface $3$4'

        Parameters list:
              $1: srt6-source-mac
              $2: srt6-dest-mac
              $3: srt6-interface
              $4: srt6-circuit-name

        The input queue for frames to be forwarded is too long, and this frame
        has been dropped to attempt to alleviate the congestion."
    ::= { srtNotificationsPrefix 6 }

srtNotification7 NOTIFICATION-TYPE
    OBJECTS { 
              srt7-source-mac, 
              srt7-interface,
              srt7-circuit-name 
            }
    STATUS current
    DESCRIPTION
        "Notification of Event SRT.7

        Message: 'Bridge Protocol Data Unit input queue overflow on frame from $1, dropped from interface $2$3'

        Parameters list:
              $1: srt7-source-mac
              $2: srt7-interface
              $3: srt7-circuit-name

        The input queue for Spanning Tree Protocol Bridge Protocl Data Units
        is too long, and this frame has been dropped to attempt to alleviate
        the congestion."
    ::= { srtNotificationsPrefix 7 }

srtNotification8 NOTIFICATION-TYPE
    OBJECTS { 
              srt8-source-mac, 
              srt8-dest-mac,
              srt8-reformatted-length,
              srt8-output-maximum,
              srt8-port,
              srt8-interface,
              srt8-circuit-name 
            }
    STATUS current
    DESCRIPTION
        "Notification of Event SRT.8

        Message: 'Frame from $1 to $2 is too big (reformatted length $3 bytes > output maximum size $4 bytes) for port $5 interface $6$7, dropped'

        Parameters list:
              $1: srt8-source-mac
              $2: srt8-dest-mac
              $3: srt8-reformatted-length
              $4: srt8-output-maximum
              $5: srt8-port
              $6: srt8-interface
              $7: srt8-circuit-name

        The specified frame is too large to send on this outgoing port and
        interface. The reformatted-length is the size of the frame including
        MAC headers after any mapping of data link headers."
    ::= { srtNotificationsPrefix 8 }

srtNotification9 NOTIFICATION-TYPE
    OBJECTS { 
              srt9-source-mac, 
              srt9-dest-mac,
              srt9-interface 
            }
    STATUS current
    DESCRIPTION
        "Notification of Event SRT.9

        Message: 'Frame from $1 to $2 dropped, input interface $3 is down'

        Parameters list:
              $1: srt9-source-mac
              $2: srt9-dest-mac
              $3: srt9-interface

        A frame has been received for bridging on an interface that is down.
        It will be ignored."
    ::= { srtNotificationsPrefix 9 }

srtNotification10 NOTIFICATION-TYPE
    OBJECTS { 
              srt10-source-mac, 
              srt10-dest-mac,
              srt10-port,
              srt10-interface,
              srt10-circuit-name 
            }
    STATUS current
    DESCRIPTION
        "Notification of Event SRT.10

        Message: 'Frame from $1 to $2 dropped, source address filtered, port $3 interface $4$5'

        Parameters list:
              $1: srt10-source-mac
              $2: srt10-dest-mac
              $3: srt10-port
              $4: srt10-interface
              $5: srt10-circuit-name

        A MAC frame has been received by the hardware, but is being dropped
        because the source MAC address is being administratively filtered
        by the bridge. The frame will be dropped."
    ::= { srtNotificationsPrefix 10 }

srtNotification11 NOTIFICATION-TYPE
    OBJECTS { 
              srt11-source-mac, 
              srt11-dest-mac,
              srt11-port,
              srt11-interface,
              srt11-circuit-name 
            }
    STATUS current
    DESCRIPTION
        "Notification of Event SRT.11

        Message: 'Frame from $1 to $2 dropped, input port $3 interface $4$5 not in forwarding state'

        Parameters list:
              $1: srt11-source-mac
              $2: srt11-dest-mac
              $3: srt11-port
              $4: srt11-interface
              $5: srt11-circuit-name

        A MAC frame was received on a port that is still only in 'learning'
        state. Frames are only bridged when the input port is in 'forwarding'
        state. While the port is still in 'learning' state, they are only
        processed to learn the source addresses for the filtering database.
        The frame will not be bridged."
    ::= { srtNotificationsPrefix 11 }

srtNotification12 NOTIFICATION-TYPE
    OBJECTS { 
              srt12-source-mac, 
              srt12-dest-mac,
              srt12-port,
              srt12-interface,
              srt12-circuit-name 
            }
    STATUS current
    DESCRIPTION
        "Notification of Event SRT.12

        Message: 'Frame from $1 to $2 dropped, output port $3 interface $4$5 not in forwarding state'

        Parameters list:
              $1: srt12-source-mac
              $2: srt12-dest-mac
              $3: srt12-port
              $4: srt12-interface
              $5: srt12-circuit-name

        A MAC frame was being bridged, but the destination port was not
        in 'forwarding' state. It will not be sent on that port."
    ::= { srtNotificationsPrefix 12 }

srtNotification13 NOTIFICATION-TYPE
    OBJECTS { 
              srt13-source-mac, 
              srt13-dest-mac,
              srt13-port,
              srt13-interface,
              srt13-circuit-name 
            }
    STATUS current
    DESCRIPTION
        "Notification of Event SRT.13

        Message: 'Frame from $1 to $2 dropped, destination on same LAN, port $3 interface $4$5'

        Parameters list:
              $1: srt13-source-mac
              $2: srt13-dest-mac
              $3: srt13-port
              $4: srt13-interface
              $5: srt13-circuit-name

        A MAC frame has been received whose destination address is known to be
        on the same side of the bridge as the packet came from. It is dropped
        by the filtering logic since it does not need to be bridged."
    ::= { srtNotificationsPrefix 13 }

srtNotification14 NOTIFICATION-TYPE
    OBJECTS { 
              srt14-source-mac, 
              srt14-dest-mac,
              srt14-port,
              srt14-interface,
              srt14-circuit-name 
            }
    STATUS current
    DESCRIPTION
        "Notification of Event SRT.14

        Message: 'Frame from $1 to $2 dropped, destination port $3 not enabled, interface $4$5'

        Parameters list:
              $1: srt14-source-mac
              $2: srt14-dest-mac
              $3: srt14-port
              $4: srt14-interface
              $5: srt14-circuit-name

        A frame being bridged was destined for a port which is not running
        transparent bridging, or not in 'forwarding' state for transparent
        bridging."
    ::= { srtNotificationsPrefix 14 }

srtNotification15 NOTIFICATION-TYPE
    OBJECTS { 
              srt15-source-mac, 
              srt15-dest-mac,
              srt15-port,
              srt15-interface,
              srt15-circuit-name,
              srt15-out-port,
              srt15-out-interface,
              srt15-out-circuit-name 
            }
    STATUS current
    DESCRIPTION
        "Notification of Event SRT.15

        Message: 'Frame from $1 to $2 bridged from port number $3 interface $4$5 to port number $6 interface $7$8'

        Parameters list:
              $1: srt15-source-mac
              $2: srt15-dest-mac
              $3: srt15-port
              $4: srt15-interface
              $5: srt15-circuit-name
              $6: srt15-out-port
              $7: srt15-out-interface
              $8: srt15-out-circuit-name

        A frame is being bridged between these two interfaces. The destination
        address was known, so it was sent only to the correct destination
        network."
    ::= { srtNotificationsPrefix 15 }

srtNotification16 NOTIFICATION-TYPE
    OBJECTS { 
              srt16-source-mac, 
              srt16-dest-mac,
              srt16-port,
              srt16-interface,
              srt16-circuit-name,
              srt16-out-port,
              srt16-out-interface,
              srt16-out-circuit-name 
            }
    STATUS current
    DESCRIPTION
        "Notification of Event SRT.16

        Message: 'Frame from $1 to $2 bridged to all ports from port number $3 interface $4$5 to port number $6 interface $7$8'

        Parameters list:
              $1: srt16-source-mac
              $2: srt16-dest-mac
              $3: srt16-port
              $4: srt16-interface
              $5: srt16-circuit-name
              $6: srt16-out-port
              $7: srt16-out-interface
              $8: srt16-out-circuit-name

        A frame is being transparently bridged to all active transparent
        bridging ports. This happens when the frame destination is a multicast,
        when the frame destination is not in the learning database, or when
        required by static entries in the learning database.
        There will be one message for each port the frame is sent on."
    ::= { srtNotificationsPrefix 16 }

srtNotification17 NOTIFICATION-TYPE
    OBJECTS { 
              srt17-port, 
              srt17-interface,
              srt17-circuit-name 
            }
    STATUS current
    DESCRIPTION
        "Notification of Event SRT.17

        Message: 'Enabling SRT on port $1 interface $2$3'

        Parameters list:
              $1: srt17-port
              $2: srt17-interface
              $3: srt17-circuit-name

        The SRT forwarder is starting the process of enabling bridging
        on the specified interface. This starts when the interface comes up
        from a self-test."
    ::= { srtNotificationsPrefix 17 }

srtNotification18 NOTIFICATION-TYPE
    OBJECTS { 
              srt18-port, 
              srt18-interface,
              srt18-circuit-name 
            }
    STATUS current
    DESCRIPTION
        "Notification of Event SRT.18

        Message: 'SRT startup complete on port $1 interface $2$3'

        Parameters list:
              $1: srt18-port
              $2: srt18-interface
              $3: srt18-circuit-name

        The SRT forwarder has completed the process of enabling bridging
        on the specified interface. It will now enter 'blocking' state."
    ::= { srtNotificationsPrefix 18 }

srtNotification19 NOTIFICATION-TYPE
    OBJECTS { 
              srt19-interface-name 
            }
    STATUS current
    DESCRIPTION
        "Notification of Event SRT.19

        Message: 'Unsupported interface $1'

        Parameters list:
              $1: srt19-interface-name

        The SRT forwarder had been enabled on a type of interface it does not
        support."
    ::= { srtNotificationsPrefix 19 }

srtNotification20 NOTIFICATION-TYPE
    OBJECTS { 
              srt20-port, 
              srt20-interface,
              srt20-circuit-name 
            }
    STATUS current
    DESCRIPTION
        "Notification of Event SRT.20

        Message: 'Cannot autoconfigure the bridge address, the lowest numbered port $1 interface $2$3 has no MAC address'

        Parameters list:
              $1: srt20-port
              $2: srt20-interface
              $3: srt20-circuit-name

        The user has configured the bridge to autoconfigure the bridge address
        based on the MAC address of the lowest number port. However, the lowest
        numbered port is of a type that does not have a MAC address, such as
        a serial line."
    ::= { srtNotificationsPrefix 20 }

srtNotification21 NOTIFICATION-TYPE
    OBJECTS { 
              srt21-source-mac, 
              srt21-dest-mac,
              srt21-interface 
            }
    STATUS current
    DESCRIPTION
        "Notification of Event SRT.21

        Message: 'Bridge frame from $1 to $2, no forwarder, interface $3'

        Parameters list:
              $1: srt21-source-mac
              $2: srt21-dest-mac
              $3: srt21-interface

        Bridge frame received, but there is no bridging available in this load.
        The frame will be ignored."
    ::= { srtNotificationsPrefix 21 }

srtNotification22 NOTIFICATION-TYPE
    STATUS current
    DESCRIPTION
        "Notification of Event SRT.22

        Message: 'Bridge configured with no ports on it, disabling the bridge'

        The bridge has been enabled, but there are no ports configured
        on that bridge. The bridge will be left disabled.
        It takes at least two ports to be a bridge."
    ::= { srtNotificationsPrefix 22 }

srtNotification23 NOTIFICATION-TYPE
    OBJECTS { 
              srt23-port, 
              srt23-interface-number 
            }
    STATUS current
    DESCRIPTION
        "Notification of Event SRT.23

        Message: 'Port $1 configured on nonexistent interface number $2'

        Parameters list:
              $1: srt23-port
              $2: srt23-interface-number

        The port has been configured to use an interface that has not been
        configured with the Config> ADD DEVICE command.
        This port of the bridge will be disabled."
    ::= { srtNotificationsPrefix 23 }

srtNotification24 NOTIFICATION-TYPE
    OBJECTS { 
              srt24-existent-port-count 
            }
    STATUS current
    DESCRIPTION
        "Notification of Event SRT.24

        Message: '$1 existent ports is less than 2, disabling bridge'

        Parameters list:
              $1: srt24-existent-port-count

        Less than two (valid) ports have been configured on the bridge.
        There must be at least two ports."
    ::= { srtNotificationsPrefix 24 }

srtNotification25 NOTIFICATION-TYPE
    OBJECTS { 
              srt25-requested-size, 
              srt25-minimum-size 
            }
    STATUS current
    DESCRIPTION
        "Notification of Event SRT.25

        Message: 'No memory for filtering database (desired size $1 bytes, absolute minimum size $2 bytes), disabling bridge'

        Parameters list:
              $1: srt25-requested-size
              $2: srt25-minimum-size

        There is not enough free memory to allocate even a minimal size
        filtering database. The bridge will be disabled.
        The bridge starts by trying to allocate requested-size bytes, and then
        tries with progressively smaller sizes down to minimum-size.
        The minimum size is enough only for the registered and static entries."
    ::= { srtNotificationsPrefix 25 }

srtNotification26 NOTIFICATION-TYPE
    OBJECTS { 
              srt26-source-mac, 
              srt26-dest-mac,
              srt26-port,
              srt26-interface,
              srt26-circuit-name 
            }
    STATUS current
    DESCRIPTION
        "Notification of Event SRT.26

        Message: 'Frame from $1 to $2, source same as destination, dropping, from port $3 interface $4$5'

        Parameters list:
              $1: srt26-source-mac
              $2: srt26-dest-mac
              $3: srt26-port
              $4: srt26-interface
              $5: srt26-circuit-name

        Frames to and from the same address are not bridged by this bridge."
    ::= { srtNotificationsPrefix 26 }

srtNotification27 NOTIFICATION-TYPE
    OBJECTS { 
              srt27-old-state, 
              srt27-new-state,
              srt27-port,
              srt27-interface,
              srt27-circuit-name 
            }
    STATUS current
    DESCRIPTION
        "Notification of Event SRT.27

        Message: 'Changing port state from $1 to $2 for port $3, interface $4$5'

        Parameters list:
              $1: srt27-old-state
              $2: srt27-new-state
              $3: srt27-port
              $4: srt27-interface
              $5: srt27-circuit-name

        The Spanning Tree Protocol has requested this state change for this port
        in the SRT bridge. The old-state and new-state are one of:
        FORWARDING (Spanning Tree Protocol Forwarding state),
        LEARNING (Spanning Tree Protocol Learning state),
        LISTENING (Spanning Tree Protocol Listening state),
        BLOCKED (Spanning Tree Protocol Blocking state),
        CONFIGURING (configuration of port device pending),
        POSTCONFIGURING (configuration of port device done),
        PRECONFIGURING (port enabled, configuration of port device to start) and
        DISABLED (port disabled)."
    ::= { srtNotificationsPrefix 27 }

srtNotification28 NOTIFICATION-TYPE
    OBJECTS { 
              srt28-mac-address 
            }
    STATUS current
    DESCRIPTION
        "Notification of Event SRT.28

        Message: 'No room for permanent address $1 in filtering database, disabling bridge'

        Parameters list:
              $1: srt28-mac-address

        There is no room for the permanent entry in the filtering database.
        The bridge will be disabled."
    ::= { srtNotificationsPrefix 28 }

srtNotification29 NOTIFICATION-TYPE
    OBJECTS { 
              srt29-mac-address 
            }
    STATUS current
    DESCRIPTION
        "Notification of Event SRT.29

        Message: 'No memory for permanent address $1, disabling bridge'

        Parameters list:
              $1: srt29-mac-address

        There is no room for the permanent entry in an auxiliary database.
        The bridge will be disabled."
    ::= { srtNotificationsPrefix 29 }

srtNotification30 NOTIFICATION-TYPE
    OBJECTS { 
              srt30-command, 
              srt30-interface 
            }
    STATUS current
    DESCRIPTION
        "Notification of Event SRT.30

        Message: '$1 command failed to interface $2'

        Parameters list:
              $1: srt30-command
              $2: srt30-interface

        A command to a network device failed.
        The possible command names are
        'SRT-ON' (promiscuous on),
        'SRT-OFF' (promiscuous off),
        'SRT-INFORM' (learn capabilities of device),
        'SRT-ADD-ENTRY' (add static entry in device),
        'SRT-SET-AGE' (set age for filtering database in device) and
        'SRT-DECR-AGE' (do ageing pass on filtering database in device).
        For commands 'SRT-ON' and 'SRT-OFF' the result will be that
        the interface may remain in the worong state. A failure on 'SRT-INFORM'
        could cause serious problems. For other commands the results will be
        less serious."
    ::= { srtNotificationsPrefix 30 }

srtNotification31 NOTIFICATION-TYPE
    OBJECTS { 
              srt31-routing-type, 
              srt31-source-mac,
              srt31-dest-mac,
              srt31-port,
              srt31-interface,
              srt31-circuit-name 
            }
    STATUS current
    DESCRIPTION
        "Notification of Event SRT.31

        Message: 'No buffer available to duplicate $1 frame from $2 to $3 on port $4, interface $5$6'

        Parameters list:
              $1: srt31-routing-type
              $2: srt31-source-mac
              $3: srt31-dest-mac
              $4: srt31-port
              $5: srt31-interface
              $6: srt31-circuit-name

        No buffer available to copy a frame in order to send an
        All Routes Explorer (ARE) or Spanning Tree Explorer (STE) routing-type
        frame on multiple interfaces. ARE frames are sent on all interfaces
        which are part of the SRT spanning tree, STE frames are sent
        on all interfaces running source-routing.
        No copy of this frame will be sent on the specified port and interface."
    ::= { srtNotificationsPrefix 31 }

srtNotification32 NOTIFICATION-TYPE
    OBJECTS { 
              srt32-source-mac, 
              srt32-dest-mac,
              srt32-reason-code,
              srt32-port,
              srt32-interface-name,
              srt32-circuit-name 
            }
    STATUS current
    DESCRIPTION
        "Notification of Event SRT.32

        Message: 'Sending source routed frame from $1 to $2 failed, reason $3, on port $4 interface $5$6'

        Parameters list:
              $1: srt32-source-mac
              $2: srt32-dest-mac
              $3: srt32-reason-code
              $4: srt32-port
              $5: srt32-interface-name
              $6: srt32-circuit-name

        The sending of a source routed frame being forwarded failed.
        The reason-code is the internal error code for the failure."
    ::= { srtNotificationsPrefix 32 }

srtNotification33 NOTIFICATION-TYPE
    OBJECTS { 
              srt33-routing-type, 
              srt33-source-mac,
              srt33-dest-mac,
              srt33-port,
              srt33-interface,
              srt33-circuit-name 
            }
    STATUS current
    DESCRIPTION
        "Notification of Event SRT.33

        Message: '$1 with duplicate Route Descriptor from $2 to $3 from port $4, interface $5$6'

        Parameters list:
              $1: srt33-routing-type
              $2: srt33-source-mac
              $3: srt33-dest-mac
              $4: srt33-port
              $5: srt33-interface
              $6: srt33-circuit-name

        A source-routed frame having a All Routes Descriptor (ARE)
        or Spanning Tree Explorer (STE) routing-type in the RIF has a duplicate
        Routing Descriptor in the RIF. The frame will be dropped. This is
        a normal occurrence for ARE frames when there are any duplicate paths
        in the source routing domain. For STE frames, this indicates that
        there is an interface that is part of the source-routing spanning tree
        that should not be."
    ::= { srtNotificationsPrefix 33 }

srtNotification34 NOTIFICATION-TYPE
    OBJECTS { 
              srt34-RIF, 
              srt34-source-mac,
              srt34-dest-mac,
              srt34-port,
              srt34-interface,
              srt34-circuit-name 
            }
    STATUS current
    DESCRIPTION
        "Notification of Event SRT.34

        Message: 'SRF with duplicate LOUT (RIF $1) from $2 to $3 from port $4, interface $5$6'

        Parameters list:
              $1: srt34-RIF
              $2: srt34-source-mac
              $3: srt34-dest-mac
              $4: srt34-port
              $5: srt34-interface
              $6: srt34-circuit-name

        A source-routed frame of Specifically-routed frame (SRF) type has
        a duplicate LOUT (outgoing LAN ID). This is illegal, and the frame
        will be dropped."
    ::= { srtNotificationsPrefix 34 }

srtNotification35 NOTIFICATION-TYPE
    OBJECTS { 
              srt35-RIF, 
              srt35-source-mac,
              srt35-dest-mac,
              srt35-port,
              srt35-interface,
              srt35-circuit-name 
            }
    STATUS current
    DESCRIPTION
        "Notification of Event SRT.35

        Message: 'All Routes Explorer exceeds maximum Route Descriptors (RIF $1) from $2 to $3 from port $4, interface $5$6, dropped'

        Parameters list:
              $1: srt35-RIF
              $2: srt35-source-mac
              $3: srt35-dest-mac
              $4: srt35-port
              $5: srt35-interface
              $6: srt35-circuit-name

        An All Routes Explorer (ARE) source-routed frame has more Route
        Descriptors than this bridge is configured to allow for ARE frames.
        The frame will be dropped."
    ::= { srtNotificationsPrefix 35 }

srtNotification36 NOTIFICATION-TYPE
    OBJECTS { 
              srt36-RIF, 
              srt36-source-mac,
              srt36-dest-mac,
              srt36-port,
              srt36-interface,
              srt36-circuit-name 
            }
    STATUS current
    DESCRIPTION
        "Notification of Event SRT.36

        Message: 'Spanning Tree Explorer exceeds maximum Route Descriptors (RIF $1) from $2 to $3 from port $4, interface $5$6'

        Parameters list:
              $1: srt36-RIF
              $2: srt36-source-mac
              $3: srt36-dest-mac
              $4: srt36-port
              $5: srt36-interface
              $6: srt36-circuit-name

        A Spanning Tree Explorer (STE) source-routed frame has more Route
        Descriptors than this bridge is configured to allow for STE frames.
        The frame will be dropped."
    ::= { srtNotificationsPrefix 36 }

srtNotification37 NOTIFICATION-TYPE
    OBJECTS { 
              srt37-RIF, 
              srt37-source-mac,
              srt37-dest-mac,
              srt37-port,
              srt37-interface 
            }
    STATUS current
    DESCRIPTION
        "Notification of Event SRT.37

        Message: 'SRF with unknown LOUT (RIF $1) from $2 to $3 from port $4, interface $5'

        Parameters list:
              $1: srt37-RIF
              $2: srt37-source-mac
              $3: srt37-dest-mac
              $4: srt37-port
              $5: srt37-interface

        A source-routed frame of Specifically-routed frame (SRF) type has
        an outgoing LOUT (LAN ID Out) that does not match that of any active
        source-routing interface in the router. It will be dropped."
    ::= { srtNotificationsPrefix 37 }

srtNotification38 NOTIFICATION-TYPE
    OBJECTS { 
              srt38-RIF, 
              srt38-source-mac,
              srt38-dest-mac,
              srt38-port,
              srt38-interface,
              srt38-circuit-name 
            }
    STATUS current
    DESCRIPTION
        "Notification of Event SRT.38

        Message: 'All Routes Explorer received (RIF $1) from $2 to $3 from port $4, interface $5$6'

        Parameters list:
              $1: srt38-RIF
              $2: srt38-source-mac
              $3: srt38-dest-mac
              $4: srt38-port
              $5: srt38-interface
              $6: srt38-circuit-name

        An All Routes Explorer frame has been received on the specified port."
    ::= { srtNotificationsPrefix 38 }

srtNotification39 NOTIFICATION-TYPE
    OBJECTS { 
              srt39-RIF, 
              srt39-source-mac,
              srt39-dest-mac,
              srt39-port,
              srt39-interface,
              srt39-circuit-name 
            }
    STATUS current
    DESCRIPTION
        "Notification of Event SRT.39

        Message: 'All Routes Explorer sent (RIF $1) from $2 to $3 to port $4, interface $5$6'

        Parameters list:
              $1: srt39-RIF
              $2: srt39-source-mac
              $3: srt39-dest-mac
              $4: srt39-port
              $5: srt39-interface
              $6: srt39-circuit-name

        An All Routes Explorer frame has been sent on the specified port."
    ::= { srtNotificationsPrefix 39 }

srtNotification40 NOTIFICATION-TYPE
    OBJECTS { 
              srt40-RIF, 
              srt40-source-mac,
              srt40-dest-mac,
              srt40-port,
              srt40-interface,
              srt40-circuit-name 
            }
    STATUS current
    DESCRIPTION
        "Notification of Event SRT.40

        Message: 'Spanning Tree Explorer received (RIF $1) from $2 to $3 from port $4, interface $5$6'

        Parameters list:
              $1: srt40-RIF
              $2: srt40-source-mac
              $3: srt40-dest-mac
              $4: srt40-port
              $5: srt40-interface
              $6: srt40-circuit-name

        A Spanning Tree Explorer frame has been received on the specified port."
    ::= { srtNotificationsPrefix 40 }

srtNotification41 NOTIFICATION-TYPE
    OBJECTS { 
              srt41-RIF, 
              srt41-source-mac,
              srt41-dest-mac,
              srt41-port,
              srt41-interface,
              srt41-circuit-name 
            }
    STATUS current
    DESCRIPTION
        "Notification of Event SRT.41

        Message: 'Spanning Tree Explorer sent (RIF $1) from $2 to $3 to port $4, interface $5$6'

        Parameters list:
              $1: srt41-RIF
              $2: srt41-source-mac
              $3: srt41-dest-mac
              $4: srt41-port
              $5: srt41-interface
              $6: srt41-circuit-name

        A Spanning Tree Explorer frame has been sent on the specified port."
    ::= { srtNotificationsPrefix 41 }

srtNotification42 NOTIFICATION-TYPE
    OBJECTS { 
              srt42-routing-type, 
              srt42-old-LF,
              srt42-new-LF,
              srt42-source-mac,
              srt42-dest-mac,
              srt42-port,
              srt42-interface,
              srt42-circuit-name 
            }
    STATUS current
    DESCRIPTION
        "Notification of Event SRT.42

        Message: '$1 Largest Frame size lowered (from $2 bytes to $3 bytes) from $4 to $5 from port $6, interface $7$8'

        Parameters list:
              $1: srt42-routing-type
              $2: srt42-old-LF
              $3: srt42-new-LF
              $4: srt42-source-mac
              $5: srt42-dest-mac
              $6: srt42-port
              $7: srt42-interface
              $8: srt42-circuit-name

        A source-routing explorer (ARE or STE in routing-type) has had
        the Largest Frame (LF) field lowered in its RIF. This happens
        whenever a frame is received from a segment with a smaller maximum
        frame size than the one presently encoded in the LF bits. This is
        a normal part of the spanning tree protocol to determine the maximum
        frame size on all routes."
    ::= { srtNotificationsPrefix 42 }

srtNotification43 NOTIFICATION-TYPE
    OBJECTS { 
              srt43-routing-type, 
              srt43-old-LF,
              srt43-new-LF,
              srt43-source-mac,
              srt43-dest-mac,
              srt43-port,
              srt43-interface,
              srt43-circuit-name 
            }
    STATUS current
    DESCRIPTION
        "Notification of Event SRT.43

        Message: '$1 Largest Frame size lowered (from $2 bytes to $3 bytes) from $4 to $5 to port $6, interface $7$8'

        Parameters list:
              $1: srt43-routing-type
              $2: srt43-old-LF
              $3: srt43-new-LF
              $4: srt43-source-mac
              $5: srt43-dest-mac
              $6: srt43-port
              $7: srt43-interface
              $8: srt43-circuit-name

        A source-routing explorer (ARE or STE in routing-type) has had
        the Largest Frame (LF) field lowered in its RIF. This happens
        whenever a frame is sent to a segment with a smaller maximum frame size
        than the one presently encoded in the LF bits. This is a normal part of
        the spanning tree protocol to determine the maximum frame size
        on all routes."
    ::= { srtNotificationsPrefix 43 }

srtNotification44 NOTIFICATION-TYPE
    OBJECTS { 
              srt44-RIF, 
              srt44-source-mac,
              srt44-dest-mac,
              srt44-port,
              srt44-interface,
              srt44-circuit-name 
            }
    STATUS current
    DESCRIPTION
        "Notification of Event SRT.44

        Message: 'Specifically-routed frame received (RIF $1) from $2 to $3 from port $4, interface $5$6'

        Parameters list:
              $1: srt44-RIF
              $2: srt44-source-mac
              $3: srt44-dest-mac
              $4: srt44-port
              $5: srt44-interface
              $6: srt44-circuit-name

        A Specifically-routed frame has been received on the specified port."
    ::= { srtNotificationsPrefix 44 }

srtNotification45 NOTIFICATION-TYPE
    OBJECTS { 
              srt45-RIF, 
              srt45-source-mac,
              srt45-dest-mac,
              srt45-port,
              srt45-interface,
              srt45-circuit-name 
            }
    STATUS current
    DESCRIPTION
        "Notification of Event SRT.45

        Message: 'Sending Specifically-routed frame (RIF $1) from $2 to $3 to port $4, interface $5$6'

        Parameters list:
              $1: srt45-RIF
              $2: srt45-source-mac
              $3: srt45-dest-mac
              $4: srt45-port
              $5: srt45-interface
              $6: srt45-circuit-name

        A Specifically-routed frame is being sent on the specified port."
    ::= { srtNotificationsPrefix 45 }

srtNotification46 NOTIFICATION-TYPE
    OBJECTS { 
              srt46-routing-type, 
              srt46-source-mac,
              srt46-dest-mac,
              srt46-port,
              srt46-interface,
              srt46-circuit-name 
            }
    STATUS current
    DESCRIPTION
        "Notification of Event SRT.46

        Message: '$1 frame received from $2 to $3 on disabled port $4, interface $5$6, discarded'

        Parameters list:
              $1: srt46-routing-type
              $2: srt46-source-mac
              $3: srt46-dest-mac
              $4: srt46-port
              $5: srt46-interface
              $6: srt46-circuit-name

        A source-routed frame has been received on the specified port, but
        that port is not configured for bridging.
        The routing-type is one of SRF (Specifically-routed frame),
        STE (Spanning Tree Expolorer) or ARE (All Routes Explorer).
        This really should not happen on more than a transient basis, because
        ports that are not enabled for bridging should not be queueing packets
        to the source-routing forwarder."
    ::= { srtNotificationsPrefix 46 }

srtNotification47 NOTIFICATION-TYPE
    OBJECTS { 
              srt47-routing-type, 
              srt47-source-mac,
              srt47-dest-mac,
              srt47-port,
              srt47-interface,
              srt47-circuit-name 
            }
    STATUS current
    DESCRIPTION
        "Notification of Event SRT.47

        Message: '$1 frame received from $2 to $3 on non-source-routing port $4, interface $5$6, discarded'

        Parameters list:
              $1: srt47-routing-type
              $2: srt47-source-mac
              $3: srt47-dest-mac
              $4: srt47-port
              $5: srt47-interface
              $6: srt47-circuit-name

        A source-routed frame has been received on the specified port, but
        that port is not configured for source-routing bridging.
        The routing-type is one of SRF (Specifically-routed frame),
        STE (Spanning Tree Expolorer) or ARE (All Routes Explorer).
        This really should not happen on more than a transient basis, because
        ports that are not enabled for bridging should not be queueing packets
        to the source-routing forwarder."
    ::= { srtNotificationsPrefix 47 }

srtNotification48 NOTIFICATION-TYPE
    OBJECTS { 
              srt48-RIF, 
              srt48-source-mac,
              srt48-dest-mac,
              srt48-port,
              srt48-interface,
              srt48-circuit-name 
            }
    STATUS current
    DESCRIPTION
        "Notification of Event SRT.48

        Message: 'Spanning Tree Explorer dropped (RIF $1) from $2 to $3 from blocked port $4, interface $5$6'

        Parameters list:
              $1: srt48-RIF
              $2: srt48-source-mac
              $3: srt48-dest-mac
              $4: srt48-port
              $5: srt48-interface
              $6: srt48-circuit-name

        A Spanning Tree Explorer (STE) frame was dropped, and not forwarded,
        because the incoming port is not part of the spanning tree, or has been
        configured not to forward STE frames."
    ::= { srtNotificationsPrefix 48 }

srtNotification49 NOTIFICATION-TYPE
    OBJECTS { 
              srt49-RIF, 
              srt49-source-mac,
              srt49-dest-mac,
              srt49-port,
              srt49-interface,
              srt49-circuit-name 
            }
    STATUS current
    DESCRIPTION
        "Notification of Event SRT.49

        Message: 'Spanning Tree Explorer not sent (RIF $1) from $2 to $3 to blocked port $4, interface $5$6'

        Parameters list:
              $1: srt49-RIF
              $2: srt49-source-mac
              $3: srt49-dest-mac
              $4: srt49-port
              $5: srt49-interface
              $6: srt49-circuit-name

        A Spanning Tree Explorer (STE) frame was not sent on the specified port
        because it is not part of the spanning tree, or has been configured
        not to forward STE frames."
    ::= { srtNotificationsPrefix 49 }

srtNotification50 NOTIFICATION-TYPE
    OBJECTS { 
              srt50-error-string, 
              srt50-interface 
            }
    STATUS current
    DESCRIPTION
        "Notification of Event SRT.50

        Message: 'Got $1 error trying to enable source-routing on interface $2'

        Parameters list:
              $1: srt50-error-string
              $2: srt50-interface

        The bridge tried to enable source-routing bridging on this interface,
        but the interface refused the configuration command.
        Source-routing will be left disabled on this interface."
    ::= { srtNotificationsPrefix 50 }

srtNotification51 NOTIFICATION-TYPE
    OBJECTS { 
              srt51-source-mac, 
              srt51-dest-mac,
              srt51-reformatted-length,
              srt51-output-maximum,
              srt51-port,
              srt51-interface,
              srt51-circuit-name 
            }
    STATUS current
    DESCRIPTION
        "Notification of Event SRT.51

        Message: 'Specifically-routed frame from $1 to $2 is too big (reformatted length $3 > output maximum size $4) for port $5 interface $6$7, dropped'

        Parameters list:
              $1: srt51-source-mac
              $2: srt51-dest-mac
              $3: srt51-reformatted-length
              $4: srt51-output-maximum
              $5: srt51-port
              $6: srt51-interface
              $7: srt51-circuit-name

        The specified Specifically-routed (source-routed) frame is too large
        to send on this outgoing port and interface. The reformatted-length is
        the size of the frame including MAC headers after any mapping of
        data link headers."
    ::= { srtNotificationsPrefix 51 }

srtNotification52 NOTIFICATION-TYPE
    OBJECTS { 
              srt52-routing-type, 
              srt52-source-mac,
              srt52-dest-mac,
              srt52-reformatted-length,
              srt52-output-maximum,
              srt52-port,
              srt52-interface,
              srt52-circuit-name 
            }
    STATUS current
    DESCRIPTION
        "Notification of Event SRT.52

        Message: '$1 frame from $2 to $3 is too big (reformatted length $4 > output maximum size $5) for port $6 interface $7$8, dropped'

        Parameters list:
              $1: srt52-routing-type
              $2: srt52-source-mac
              $3: srt52-dest-mac
              $4: srt52-reformatted-length
              $5: srt52-output-maximum
              $6: srt52-port
              $7: srt52-interface
              $8: srt52-circuit-name

        The source-routed explorer (ARE or STE routing-type) frame is too large
        to send on this outgoing port and interface. The reformatted-length is
        the size of the frame including MAC headers after any mapping of
        data link headers."
    ::= { srtNotificationsPrefix 52 }

srtNotification53 NOTIFICATION-TYPE
    OBJECTS { 
              srt53-routing-type, 
              srt53-RIF-length,
              srt53-source-mac,
              srt53-dest-mac,
              srt53-port,
              srt53-interface,
              srt53-circuit-name 
            }
    STATUS current
    DESCRIPTION
        "Notification of Event SRT.53

        Message: '$1 with invalid RIF lenth $2 from $3 to $4 from port $5, interface $6$7, discarded'

        Parameters list:
              $1: srt53-routing-type
              $2: srt53-RIF-length
              $3: srt53-source-mac
              $4: srt53-dest-mac
              $5: srt53-port
              $6: srt53-interface
              $7: srt53-circuit-name

        A source-routing frame was received with an invalid RIF length encoded
        in the Length bits of the RIF.
        The routing-type is one of SRF (Specifically-routed frame),
        STE (Spanning Tree Expolorer) or ARE (All Routes Explorer)."
    ::= { srtNotificationsPrefix 53 }

srtNotification54 NOTIFICATION-TYPE
    OBJECTS { 
              srt54-requested-size 
            }
    STATUS current
    DESCRIPTION
        "Notification of Event SRT.54

        Message: 'No memory for hash table (desired size $1 bytes), disabling bridge'

        Parameters list:
              $1: srt54-requested-size

        There is not enough free memory to allocate the hash table for
        the filtering database. The bridge will be disabled."
    ::= { srtNotificationsPrefix 54 }

srtNotification55 NOTIFICATION-TYPE
    OBJECTS { 
              srt55-requested-size 
            }
    STATUS current
    DESCRIPTION
        "Notification of Event SRT.55

        Message: 'No memory for conversion hash table (desired size $1 bytes), disabling bridge'

        Parameters list:
              $1: srt55-requested-size

        There is not enough free memory to allocate the hash table for
        the conversion database. The bridge will be disabled."
    ::= { srtNotificationsPrefix 55 }

srtNotification56 NOTIFICATION-TYPE
    OBJECTS { 
              srt56-source-mac, 
              srt56-dest-mac,
              srt56-interface,
              srt56-circuit-name 
            }
    STATUS current
    DESCRIPTION
        "Notification of Event SRT.56

        Message: 'Input source-routing queue overflow on frame from $1 to $2, packet dropped from interface $3$4'

        Parameters list:
              $1: srt56-source-mac
              $2: srt56-dest-mac
              $3: srt56-interface
              $4: srt56-circuit-name

        The input queue for source-routed frames to be forwarded is too long,
        and this frame has been dropped to attempt to alleviate the congestion."
    ::= { srtNotificationsPrefix 56 }

srtNotification57 NOTIFICATION-TYPE
    OBJECTS { 
              srt57-source-mac, 
              srt57-dest-mac,
              srt57-port,
              srt57-interface,
              srt57-circuit-name,
              srt57-out-port,
              srt57-out-interface,
              srt57-out-circuit-name 
            }
    STATUS current
    DESCRIPTION
        "Notification of Event SRT.57

        Message: 'Frame from $1 to $2 bridged from port number $3 interface $4$5 to port number $6 interface $7$8'

        Parameters list:
              $1: srt57-source-mac
              $2: srt57-dest-mac
              $3: srt57-port
              $4: srt57-interface
              $5: srt57-circuit-name
              $6: srt57-out-port
              $7: srt57-out-interface
              $8: srt57-out-circuit-name

        A frame is being bridged between these two interfaces.
        The destination address was known, so it was sent only to
        the correct destination network."
    ::= { srtNotificationsPrefix 57 }

srtNotification58 NOTIFICATION-TYPE
    OBJECTS { 
              srt58-source-mac, 
              srt58-dest-mac,
              srt58-reformatted-length,
              srt58-output-maximum,
              srt58-port,
              srt58-interface,
              srt58-circuit-name 
            }
    STATUS current
    DESCRIPTION
        "Notification of Event SRT.58

        Message: 'Transparent frame converted to source-routed frame from $1 to $2 is too big (reformatted length $3 bytes > output maximum size $4 bytes) for port $5 interface $6$7, dropped'

        Parameters list:
              $1: srt58-source-mac
              $2: srt58-dest-mac
              $3: srt58-reformatted-length
              $4: srt58-output-maximum
              $5: srt58-port
              $6: srt58-interface
              $7: srt58-circuit-name

        The specified transparent bridge frame is too large to send as
        a source-routed frame on this outgoing port and interface.
        The reformatted-length is the size of the frame including MAC headers
        and RIF after any mapping of data link headers."
    ::= { srtNotificationsPrefix 58 }

srtNotification59 NOTIFICATION-TYPE
    OBJECTS { 
              srt59-source-mac, 
              srt59-dest-mac,
              srt59-RIF,
              srt59-port,
              srt59-interface,
              srt59-circuit-name,
              srt59-out-port,
              srt59-out-interface,
              srt59-out-circuit-name 
            }
    STATUS current
    DESCRIPTION
        "Notification of Event SRT.59

        Message: 'Transparent frame converted to source-routed frame from $1 to $2 (RIF $3) bridged from port number $4 interface $5$6 to port number $7 interface $8$9'

        Parameters list:
              $1: srt59-source-mac
              $2: srt59-dest-mac
              $3: srt59-RIF
              $4: srt59-port
              $5: srt59-interface
              $6: srt59-circuit-name
              $7: srt59-out-port
              $8: srt59-out-interface
              $9: srt59-out-circuit-name

        A frame is being conversion bridged between these two interfaces.
        The destination address and RIF were known, so it was sent only to
        the correct destination network."
    ::= { srtNotificationsPrefix 59 }

srtNotification60 NOTIFICATION-TYPE
    OBJECTS { 
              srt60-source-mac, 
              srt60-dest-mac,
              srt60-RIF,
              srt60-RIF,
              srt60-port,
              srt60-interface,
              srt60-circuit-name,
              srt60-out-port,
              srt60-out-interface,
              srt60-out-circuit-name 
            }
    STATUS current
    DESCRIPTION
        "Notification of Event SRT.60

        Message: 'Transparent frame converted to source-routed frame from $1 to $2 (RIF $3$4) bridged to all ports from port number $5 interface $6$7 to port number $8 interface $9$10'

        Parameters list:
              $1: srt60-source-mac
              $2: srt60-dest-mac
              $3: srt60-RIF
              $4: srt60-RIF
              $5: srt60-port
              $6: srt60-interface
              $7: srt60-circuit-name
              $8: srt60-out-port
              $9: srt60-out-interface
              $10: srt60-out-circuit-name

        A frame is being conversion bridged to all active source-routing ports.
        This happens when the frame destination is a multicast or when
        the frame destination is not in the source-routing learning database.
        There will be one message for each port the frame is sent on."
    ::= { srtNotificationsPrefix 60 }

srtNotification61 NOTIFICATION-TYPE
    OBJECTS { 
              srt61-source-mac, 
              srt61-dest-mac,
              srt61-RIF,
              srt61-port,
              srt61-interface,
              srt61-circuit-name 
            }
    STATUS current
    DESCRIPTION
        "Notification of Event SRT.61

        Message: 'Specifically routed frame received from $1 to $2 (RIF $3) to disabled port $4, interface $5$6, discarded'

        Parameters list:
              $1: srt61-source-mac
              $2: srt61-dest-mac
              $3: srt61-RIF
              $4: srt61-port
              $5: srt61-interface
              $6: srt61-circuit-name

        A Specifically Routed frame has been received whose RIF would send it
        on the specified port, but that port is not configured for bridging."
    ::= { srtNotificationsPrefix 61 }

srtNotification62 NOTIFICATION-TYPE
    OBJECTS { 
              srt62-source-mac, 
              srt62-dest-mac,
              srt62-reformatted-length,
              srt62-output-maximum,
              srt62-port,
              srt62-interface,
              srt62-circuit-name 
            }
    STATUS current
    DESCRIPTION
        "Notification of Event SRT.62

        Message: 'Source-routed frame converted to transparent frame from $1 to $2 is too big (reformatted length $3 bytes > output maximum size $4 bytes) from port $5 interface $6$7, may get dropped'

        Parameters list:
              $1: srt62-source-mac
              $2: srt62-dest-mac
              $3: srt62-reformatted-length
              $4: srt62-output-maximum
              $5: srt62-port
              $6: srt62-interface
              $7: srt62-circuit-name

        The specified source-routed frame is larger than that is allowed
        by LF-BIT configuration for the transparent bridge domain. After mapping
        to the MAC headers of the outgoing port, the packet may get dropped
        if it exceeds the MSDU limit of the port."
    ::= { srtNotificationsPrefix 62 }

srtNotification63 NOTIFICATION-TYPE
    OBJECTS { 
              srt63-routing-type, 
              srt63-source-mac,
              srt63-dest-mac,
              srt63-port,
              srt63-interface,
              srt63-circuit-name 
            }
    STATUS current
    DESCRIPTION
        "Notification of Event SRT.63

        Message: 'No buffer available to duplicate $1 frame from $2 to $3 for source-routing to transparent bridging conversion from port $4 interface $5$6'

        Parameters list:
              $1: srt63-routing-type
              $2: srt63-source-mac
              $3: srt63-dest-mac
              $4: srt63-port
              $5: srt63-interface
              $6: srt63-circuit-name

        No buffer available to copy a frame in order to send Routes Explorer
        (ARE) or Spanning Tree Explorer (STE) routing-type frame out as
        a transparent bridged frame in the transparent bridging domain.
        No copy of this frame will be sent into the transparent bridge domain."
    ::= { srtNotificationsPrefix 63 }

srtNotification64 NOTIFICATION-TYPE
    OBJECTS { 
              srt64-requested-size 
            }
    STATUS current
    DESCRIPTION
        "Notification of Event SRT.64

        Message: 'No memory for conversion database (desired size $1 bytes), disabling bridge'

        Parameters list:
              $1: srt64-requested-size

        There is not enough free memory to allocate even a minimal size
        conversion database. The bridge will be disabled."
    ::= { srtNotificationsPrefix 64 }

srtNotification65 NOTIFICATION-TYPE
    OBJECTS { 
              srt65-MAC-address, 
              srt65-interface 
            }
    STATUS current
    DESCRIPTION
        "Notification of Event SRT.65

        Message: 'Cannot add static entry for address $1 on interface $2'

        Parameters list:
              $1: srt65-MAC-address
              $2: srt65-interface

        An attempt to add a particular static entry to the internal database of
        a bridging interface having internal filtering failed."
    ::= { srtNotificationsPrefix 65 }

srtNotification66 NOTIFICATION-TYPE
    OBJECTS { 
              srt66-interface, 
              srt66-circuit-name 
            }
    STATUS current
    DESCRIPTION
        "Notification of Event SRT.66

        Message: 'Cannot enable transparent bridging on interface $1$2'

        Parameters list:
              $1: srt66-interface
              $2: srt66-circuit-name

        The bridge has been configured to enable transparent bridging on
        an IEEE 802.5 Token-Ring interface that does not have the hardware
        to support transparent bridging. Transparent bridging will not be
        enabled on this interface."
    ::= { srtNotificationsPrefix 66 }

srtNotification67 NOTIFICATION-TYPE
    OBJECTS { 
              srt67-source-mac, 
              srt67-dest-mac,
              srt67-RIF,
              srt67-port,
              srt67-interface,
              srt67-circuit-name 
            }
    STATUS current
    DESCRIPTION
        "Notification of Event SRT.67

        Message: 'Specifically routed frame frame from $1 to $2 (RIF $3) forwarded to disabled port $4, interface $5$6, discarded'

        Parameters list:
              $1: srt67-source-mac
              $2: srt67-dest-mac
              $3: srt67-RIF
              $4: srt67-port
              $5: srt67-interface
              $6: srt67-circuit-name

        A Specifically Routed frame has been sent on a port, but that port is
        not configured for bridging. This should never happen, since prior
        checks should prevent calling this code if the port is not configured
        for bridging."
    ::= { srtNotificationsPrefix 67 }

srtNotification68 NOTIFICATION-TYPE
    OBJECTS { 
              srt68-ethernet-type 
            }
    STATUS current
    DESCRIPTION
        "Notification of Event SRT.68

        Message: 'Ethernet type table full for Ethernet type $1'

        Parameters list:
              $1: srt68-ethernet-type

        There is no space in the Ethernet type registration table for
        the specified ethernet-type. This happens when there are too many
        hash collisions, and there are not enough overflow buckets."
    ::= { srtNotificationsPrefix 68 }

srtNotification69 NOTIFICATION-TYPE
    OBJECTS { 
              srt69-protocol, 
              srt69-protocol,
              srt69-protocol,
              srt69-protocol,
              srt69-protocol 
            }
    STATUS current
    DESCRIPTION
        "Notification of Event SRT.69

        Message: 'Subnetwork Access Protocol table full for Protocol Identifier type $1-$2-$3-$4-$5'

        Parameters list:
              $1: srt69-protocol
              $2: srt69-protocol
              $3: srt69-protocol
              $4: srt69-protocol
              $5: srt69-protocol

        There is no space in the SNAP PID registration table for
        the specified protocol. This happens when there are too many
        hash collisions, and there are not enough overflow buckets."
    ::= { srtNotificationsPrefix 69 }

srtNotification70 NOTIFICATION-TYPE
    OBJECTS { 
              srt70-source-mac, 
              srt70-dest-mac,
              srt70-port,
              srt70-interface,
              srt70-circuit-name 
            }
    STATUS current
    DESCRIPTION
        "Notification of Event SRT.70

        Message: 'Frame from $1 to $2 dropped, destination address filtered, port $3 interface $4$5'

        Parameters list:
              $1: srt70-source-mac
              $2: srt70-dest-mac
              $3: srt70-port
              $4: srt70-interface
              $5: srt70-circuit-name

        A MAC frame has been received by the hardware, but is being dropped
        because the destination MAC address is being administratively filtered
        by the bridge. The frame will be dropped."
    ::= { srtNotificationsPrefix 70 }

srtNotification71 NOTIFICATION-TYPE
    OBJECTS { 
              srt71-port, 
              srt71-interface,
              srt71-circuit-name 
            }
    STATUS current
    DESCRIPTION
        "Notification of Event SRT.71

        Message: 'Source Routing not supported on port $1, interface $2$3'

        Parameters list:
              $1: srt71-port
              $2: srt71-interface
              $3: srt71-circuit-name

        Source Routing is configured on the port which is attached to an
        underlying network which inherently does not support source routing
        type of functionalities. Such networks are Ethernet and FDDI.
        Bridge disables source routing on the port."
    ::= { srtNotificationsPrefix 71 }

srtNotification72 NOTIFICATION-TYPE
    STATUS current
    DESCRIPTION
        "Notification of Event SRT.72

        Message: 'Conversion bridging (Adaptive or SR-TB) enabled, but not licensed, disabling'

        Conversion bridging has been enabled, but that feature was not purchased
        as part of this software load. The conversion bridging feature will not
        be enabled."
    ::= { srtNotificationsPrefix 72 }

srtNotification73 NOTIFICATION-TYPE
    STATUS current
    DESCRIPTION
        "Notification of Event SRT.73

        Message: 'Source-routing bridging enabled, but not licensed, disabling'

        Source-routing bridging has been enabled, but that feature was not
        purchased as part of this software load. The source-routing bridging
        feature will not be enabled."
    ::= { srtNotificationsPrefix 73 }

srtNotification74 NOTIFICATION-TYPE
    OBJECTS { 
              srt74-interface, 
              srt74-circuit-name 
            }
    STATUS current
    DESCRIPTION
        "Notification of Event SRT.74

        Message: 'Source-routing bridging enabled on interface $1$2, but not licensed, disabling'

        Parameters list:
              $1: srt74-interface
              $2: srt74-circuit-name

        Source-routing bridging has been enabled, but that feature was not
        purchased as part of this software load. The source-routing bridging
        feature will not be enabled."
    ::= { srtNotificationsPrefix 74 }

srtNotification75 NOTIFICATION-TYPE
    OBJECTS { 
              srt75-interface, 
              srt75-circuit-name 
            }
    STATUS current
    DESCRIPTION
        "Notification of Event SRT.75

        Message: 'Spanning tree (transparent) bridging enabled on interface $1$2, but not licensed, disabling'

        Parameters list:
              $1: srt75-interface
              $2: srt75-circuit-name

        Spanning tree (transparent) bridging has been enabled, but that feature
        was not purchased as part of this software load.
        The spanning tree (transparent) bridging feature will not be enabled."
    ::= { srtNotificationsPrefix 75 }

srtNotification76 NOTIFICATION-TYPE
    STATUS current
    DESCRIPTION
        "Notification of Event SRT.76

        Message: 'No memory to allocate a NETBIOS Filter'

        At least one configured NETBIOS Filter will not be enabled, because
        there is not enough memory."
    ::= { srtNotificationsPrefix 76 }

srtNotification77 NOTIFICATION-TYPE
    OBJECTS { 
              srt77-input-output, 
              srt77-port-number 
            }
    STATUS current
    DESCRIPTION
        "Notification of Event SRT.77

        Message: '$1 NETBIOS filter list, for port $2, deleted by user. Filter will not be enabled'

        Parameters list:
              $1: srt77-input-output
              $2: srt77-port-number

        The user deleted a filter list, which was part of an already
        configured filter. The filter will not be enabled."
    ::= { srtNotificationsPrefix 77 }

srtNotification78 NOTIFICATION-TYPE
    OBJECTS { 
              srt78-input-output, 
              srt78-port-number 
            }
    STATUS current
    DESCRIPTION
        "Notification of Event SRT.78

        Message: '$1 NETBIOS filter for port $2 is configured, but that port number is not configured'

        Parameters list:
              $1: srt78-input-output
              $2: srt78-port-number

        The user configured a NETBIOS filter for a particular port, but that
        port number is not configured."
    ::= { srtNotificationsPrefix 78 }

srtNotification79 NOTIFICATION-TYPE
    OBJECTS { 
              srt79-source-mac, 
              srt79-dest-mac,
              srt79-port,
              srt79-interface,
              srt79-circuit-name 
            }
    STATUS current
    DESCRIPTION
        "Notification of Event SRT.79

        Message: 'NETBIOS Output Packet Filtered - $1->$2, port $3, interface $4$5'

        Parameters list:
              $1: srt79-source-mac
              $2: srt79-dest-mac
              $3: srt79-port
              $4: srt79-interface
              $5: srt79-circuit-name

        A NETBIOS packet has matched the criteria specified in a NETBIOS Filter
        configuration record. The packet is dropped."
    ::= { srtNotificationsPrefix 79 }

srtNotification80 NOTIFICATION-TYPE
    STATUS current
    DESCRIPTION
        "Notification of Event SRT.80

        Message: 'No memory to allocate information for NETBIOS Filter console display'

        The part of the router that handles NETBIOS console display cannot
        allocate enough memory to do the complete display. Some part of the
        NETBIOS console display will not be shown from the T 5 process."
    ::= { srtNotificationsPrefix 80 }

srtNotification81 NOTIFICATION-TYPE
    OBJECTS { 
              srt81-RIF, 
              srt81-source-mac,
              srt81-dest-mac,
              srt81-port 
            }
    STATUS current
    DESCRIPTION
        "Notification of Event SRT.81

        Message: 'NETBIOS STE converted to SRF (RIF $1) $2->$3 from port $4'

        Parameters list:
              $1: srt81-RIF
              $2: srt81-source-mac
              $3: srt81-dest-mac
              $4: srt81-port

        A NETBIOS STE converted to SRF by NETBIOS Name Caching."
    ::= { srtNotificationsPrefix 81 }

srtNotification82 NOTIFICATION-TYPE
    STATUS current
    DESCRIPTION
        "Notification of Event SRT.82

        Message: 'NETBIOS STE not converted, RIF too long'

        NETBIOS STE not converted, RIF too long."
    ::= { srtNotificationsPrefix 82 }

srtNotification83 NOTIFICATION-TYPE
    OBJECTS { 
              srt83-RIF, 
              srt83-source-mac,
              srt83-dest-mac,
              srt83-port 
            }
    STATUS current
    DESCRIPTION
        "Notification of Event SRT.83

        Message: 'NETBIOS find-name STE filtered (RIF $1) $2->$3 from port $4'

        Parameters list:
              $1: srt83-RIF
              $2: srt83-source-mac
              $3: srt83-dest-mac
              $4: srt83-port

        A NETBIOS find-name STE has been filtered."
    ::= { srtNotificationsPrefix 83 }

srtNotification84 NOTIFICATION-TYPE
    OBJECTS { 
              srt84-port, 
              srt84-interface 
            }
    STATUS current
    DESCRIPTION
        "Notification of Event SRT.84

        Message: 'BPDU dropped because STP disabled on port $1, interface $2'

        Parameters list:
              $1: srt84-port
              $2: srt84-interface

        A spanning tree BPDU frame was received on a port that has been
        disabled for spanning tree participation by the 'disable tree port#'
        command."
    ::= { srtNotificationsPrefix 84 }

srtNotification85 NOTIFICATION-TYPE
    OBJECTS { 
              srt85-port, 
              srt85-interface-number 
            }
    STATUS current
    DESCRIPTION
        "Notification of Event SRT.85

        Message: 'Frame relay Port $1 configured on non-Frame relay interface $2'

        Parameters list:
              $1: srt85-port
              $2: srt85-interface-number

        The port has been configured to use a Frame Relay interface. However,
        subsequent to bridge configuration, device configuration changed such
        that the device is no longer configured to be a Frame Relay device.
        This could have happened if the user changed the data link support
        on the device, or re-ordered the device records."
    ::= { srtNotificationsPrefix 85 }

srtNotification86 NOTIFICATION-TYPE
    OBJECTS { 
              srt86-port, 
              srt86-circuit-name,
              srt86-interface,
              srt86-reason 
            }
    STATUS current
    DESCRIPTION
        "Notification of Event SRT.86

        Message: 'Bridge port $1 with circuit=$2 registration with interface $3 failed, reason=$4'

        Parameters list:
              $1: srt86-port
              $2: srt86-circuit-name
              $3: srt86-interface
              $4: srt86-reason

        During bridge initialization, ports are associated with Frame Relay
        registers with the Frame Relay interface. During registration, both let
        each other know about their existence and exchange some
        useful information to keep about each other."
    ::= { srtNotificationsPrefix 86 }

srtNotification87 NOTIFICATION-TYPE
    OBJECTS { 
              srt87-source-mac, 
              srt87-dest-mac,
              srt87-port,
              srt87-interface,
              srt87-circuit-name 
            }
    STATUS current
    DESCRIPTION
        "Notification of Event SRT.87

        Message: 'All Routes Explorer exceeds maximum Route Descriptors from $1 to $2 from port $3, interface $4$5'

        Parameters list:
              $1: srt87-source-mac
              $2: srt87-dest-mac
              $3: srt87-port
              $4: srt87-interface
              $5: srt87-circuit-name

        An All Routes Explorer (ARE) source-routed frame has more
        Route Descriptors than this bridge is configured to allow for
        ARE frames.
        The frame will be dropped."
    ::= { srtNotificationsPrefix 87 }

srtNotification88 NOTIFICATION-TYPE
    STATUS current
    DESCRIPTION
        "Notification of Event SRT.88

        Message: 'Cannot autoconfigure the bridge address, there is no available MAC address'

        The user has configured the bridge to autoconfigure the bridge address.
        However, there is no port with a configured MAC address and it is no
        possible to get one from BIOS."
    ::= { srtNotificationsPrefix 88 }

srtNotification89 NOTIFICATION-TYPE
    OBJECTS { 
              srt89-source-mac, 
              srt89-dest-mac,
              srt89-port,
              srt89-interface,
              srt89-circuit-name,
              srt89-out-port,
              srt89-out-interface,
              srt89-out-circuit-name 
            }
    STATUS current
    DESCRIPTION
        "Notification of Event SRT.89

        Message: 'Frame from $1 to $2 bridged from port number $3 interface $4$5 to port number $6 interface $7$8'

        Parameters list:
              $1: srt89-source-mac
              $2: srt89-dest-mac
              $3: srt89-port
              $4: srt89-interface
              $5: srt89-circuit-name
              $6: srt89-out-port
              $7: srt89-out-interface
              $8: srt89-out-circuit-name

        A frame is being bridged between these two interfaces. The destination
        address was broadcast or unregistered."
    ::= { srtNotificationsPrefix 89 }

srtNotification90 NOTIFICATION-TYPE
    OBJECTS { 
              srt90-source-mac, 
              srt90-dest-mac,
              srt90-vid 
            }
    STATUS current
    DESCRIPTION
        "Notification of Event SRT.90

        Message: 'Frame from $1 to $2 for vlan $3 not bridged because vlan bridging is disabled'

        Parameters list:
              $1: srt90-source-mac
              $2: srt90-dest-mac
              $3: srt90-vid

        A VLAN tagged frame on a ethernet subinterface was received but bridging 
        is disabled for vlans.
        The frame will not be bridged."
    ::= { srtNotificationsPrefix 90 }


END
