--
-- ADICLIBMIB-v2.mib
-- MIB generated by MG-SOFT Visual MIB Builder Version 2.1 Build 199
-- Friday, May 11, 2001 at 09:38:35
--

  ADICLIBMIB-v2 DEFINITIONS ::= BEGIN

    IMPORTS 
      OBJECT-TYPE      
        FROM RFC-1212      
      TRAP-TYPE      
        FROM RFC-1215      
      enterprises      
        FROM RFC1155-SMI      
      DisplayString      
        FROM RFC1213-MIB;
  
  
  
--
-- Node definitions
--
  
    adic OBJECT IDENTIFIER ::= { enterprises 3764 }
    
    library OBJECT IDENTIFIER ::= { adic 3 }
    
    timeStamp OBJECT-TYPE
      SYNTAX INTEGER
      ACCESS read-only
      STATUS mandatory
      DESCRIPTION
        "The last time that the agent values have been updated.
        Universal time in sec since UTC 1/1/70."
      ::= { library 1 }
    
    globalStatus OBJECT-TYPE
      SYNTAX INTEGER
        {
        unknown(1),
        ok(2),
        degraded(3),
        failure(4)
        }
      ACCESS read-only
      STATUS mandatory
      DESCRIPTION
        "Current status of the entire library system (including
        all attached drives)."
      ::= { library 2 }
    
    prevGlobalStatus OBJECT-TYPE
      SYNTAX INTEGER
        {
        unknown(1),
        ok(2),
        degraded(3),
        failure(4)
        }
      ACCESS read-only
      STATUS mandatory
      DESCRIPTION
        "Previous status of the entire library system (including
        all attached drives).  This is the last value of the overall
        status."
      ::= { library 3 }
    
    description OBJECT-TYPE
      SYNTAX DisplayString
      ACCESS read-only
      STATUS mandatory
      DESCRIPTION
        "A short description of this agent."
      ::= { library 4 }
    
    displayName OBJECT-TYPE
      SYNTAX DisplayString
      ACCESS read-only
      STATUS mandatory
      DESCRIPTION
        "Name of this agent for display purposes."
      ::= { library 5 }
    
    getTimeOut OBJECT-TYPE
      SYNTAX INTEGER (1..10000)
      ACCESS read-only
      STATUS mandatory
      DESCRIPTION
        "Suggested time out value in milleseconds for how long the SNMP getter
        should wait while attempting to poll the SNMP agent."
      ::= { library 6 }
    
    refreshRate OBJECT-TYPE
      SYNTAX INTEGER (-1..1000000000)
      ACCESS read-only
      STATUS mandatory
      DESCRIPTION
        "Rate in milliseconds at which the agent cached data is being updated. If the
        value is 0 then the data is not cached. If the value is -1 then the value does
        not apply."
      ::= { library 7 }
    
    ipAddress OBJECT-TYPE
      SYNTAX DisplayString
      ACCESS read-only
      STATUS optional
      DESCRIPTION
        "The IP address in the form of xxx.xxx.xxx.xxx for this SNMP agent."
      ::= { library 8 }
    
    hostName OBJECT-TYPE
      SYNTAX DisplayString
      ACCESS read-only
      STATUS optional
      DESCRIPTION
        "The host name, if it exists, for the system hosting the SNMP agent."
      ::= { library 9 }
    
    rmuVersion OBJECT-TYPE
      SYNTAX DisplayString
      ACCESS read-only
      STATUS optional
      DESCRIPTION
        "The version of the system hosting the SNMP agent."
      ::= { library 10 }
    
    startupState OBJECT-TYPE
      SYNTAX INTEGER
        {
        other(1),
        unknown(2),
        normal(3),
        powerfail(4),
        errorreboot(5)
        }
      ACCESS read-only
      STATUS mandatory
      DESCRIPTION
        "Startup state of the device.  This is also the shutdown
        state from the last shutdown. "
      ::= { library 11 }
    
    shutdownState OBJECT-TYPE
      SYNTAX INTEGER
        {
        other(1),
        unknown(2),
        normal(3),
        powerfail(4),
        errorreboot(5)
        }
      ACCESS read-only
      STATUS mandatory
      DESCRIPTION
        "Shutdown state of the device.  If combined with a startup
        trap, this is the shutdown state of the last shutdown. "
      ::= { library 12 }
    
    serviceActionCode OBJECT-TYPE
      SYNTAX INTEGER
      ACCESS read-only
      STATUS mandatory
      DESCRIPTION
        "Service Action Code for the device."
      ::= { library 13 }
    
    errorCode OBJECT-TYPE
      SYNTAX INTEGER
      ACCESS read-only
      STATUS mandatory
      DESCRIPTION
        "Error code for the device."
      ::= { library 14 }
    
    errorModifier OBJECT-TYPE
      SYNTAX INTEGER
      ACCESS read-only
      STATUS mandatory
      DESCRIPTION
        "Error modifier for the device."
      ::= { library 15 }
    
    physicalDevices OBJECT IDENTIFIER ::= { library 16 }
    
    numMovers OBJECT-TYPE
      SYNTAX INTEGER
      ACCESS read-only
      STATUS mandatory
      DESCRIPTION
        "Number of movers."
      ::= { physicalDevices 1 }
    
    numDrives OBJECT-TYPE
      SYNTAX INTEGER
      ACCESS read-only
      STATUS mandatory
      DESCRIPTION
        "Number of drives."
      ::= { physicalDevices 2 }
    
    moverTable OBJECT-TYPE
      SYNTAX SEQUENCE OF MoverEntry
      ACCESS not-accessible
      STATUS mandatory
      DESCRIPTION
        "A table of SCSI media movers (libraries or autoloaders) 
        found in the local system."
      ::= { physicalDevices 3 }
    
    moverEntry OBJECT-TYPE
      SYNTAX MoverEntry
      ACCESS not-accessible
      STATUS mandatory
      DESCRIPTION
        "Entry in the mover Table. Each entry contains
        an index (moverEntryId), and the values associated 
        with the SCSI mover device."
      INDEX { moverEntryId }
      ::= { moverTable 1 }
    
    MoverEntry ::=
      SEQUENCE { 
        moverEntryId
          INTEGER,
        moverTimeStamp
          INTEGER,
        moverState
          INTEGER,
        moverVendor
          DisplayString,
        moverModel
          DisplayString,
        moverFwlevel
          DisplayString,
        moverSerNum
          DisplayString,
        moverScsiId
          INTEGER,
        moverScsiLun
          INTEGER,
        moverDrvCnt
          INTEGER,
        moverSlotCnt
          INTEGER,
        moverIECnt
          INTEGER,
        moverPickerCnt
          INTEGER,
        moverPicks
          INTEGER,
        moverPickRetries
          INTEGER,
        moverPlaceRetries
          INTEGER,
        moverLoadRetries
          INTEGER,
        moverScanRetries
          INTEGER,
        moverDoorState
          INTEGER,
        moverMailboxState
          INTEGER
       }

    moverEntryId OBJECT-TYPE
      SYNTAX INTEGER (1..256)
      ACCESS read-only
      STATUS mandatory
      DESCRIPTION
        "Table entry index value. Each unique physical device has a unique moverEntryId."
      ::= { moverEntry 1 }
    
    moverTimeStamp OBJECT-TYPE
      SYNTAX INTEGER
      ACCESS read-only
      STATUS mandatory
      DESCRIPTION
        "Universal time in sec since UTC 1/1/70 when the device data was last updated."
      ::= { moverEntry 2 }
    
    moverState OBJECT-TYPE
      SYNTAX INTEGER
      ACCESS read-only
      STATUS mandatory
      DESCRIPTION
        "Device SCSI state."
      ::= { moverEntry 3 }
    
    moverVendor OBJECT-TYPE
      SYNTAX DisplayString
      ACCESS read-only
      STATUS mandatory
      DESCRIPTION
        "Device Vendor as would be reported in a SCSI Inquiry command."
      ::= { moverEntry 4 }
    
    moverModel OBJECT-TYPE
      SYNTAX DisplayString
      ACCESS read-only
      STATUS mandatory
      DESCRIPTION
        "Device Model as would be reported in a SCSI Inquiry command."
      ::= { moverEntry 5 }
    
    moverFwlevel OBJECT-TYPE
      SYNTAX DisplayString
      ACCESS read-only
      STATUS mandatory
      DESCRIPTION
        "Device firmware level as would be reported in a SCSI Inquiry command."
      ::= { moverEntry 6 }
    
    moverSerNum OBJECT-TYPE
      SYNTAX DisplayString
      ACCESS read-only
      STATUS mandatory
      DESCRIPTION
        "Device serial number as reported in SCSI Inquiry command, page 0x80."
      ::= { moverEntry 7 }
    
    moverScsiId OBJECT-TYPE
      SYNTAX INTEGER
      ACCESS read-only
      STATUS mandatory
      DESCRIPTION
        "SCSI ID of the device."
      ::= { moverEntry 8 }
    
    moverScsiLun OBJECT-TYPE
      SYNTAX INTEGER
      ACCESS read-only
      STATUS mandatory
      DESCRIPTION
        "SCSI Lun of the device."
      ::= { moverEntry 9 }
    
    moverDrvCnt OBJECT-TYPE
      SYNTAX INTEGER
      ACCESS read-only
      STATUS mandatory
      DESCRIPTION
        "Number of drives contained in this media mover."
      ::= { moverEntry 10 }
    
    moverSlotCnt OBJECT-TYPE
      SYNTAX INTEGER
      ACCESS read-only
      STATUS mandatory
      DESCRIPTION
        "Number of cartridge slots contained in this media mover"
      ::= { moverEntry 11 }
    
    moverIECnt OBJECT-TYPE
      SYNTAX INTEGER
      ACCESS read-only
      STATUS mandatory
      DESCRIPTION
        "Number of import-export ports contained in this media mover"
      ::= { moverEntry 12 }
    
    moverPickerCnt OBJECT-TYPE
      SYNTAX INTEGER
      ACCESS read-only
      STATUS mandatory
      DESCRIPTION
        "Number of robotic pickers contained in this media mover."
      ::= { moverEntry 13 }
    
    moverPicks OBJECT-TYPE
      SYNTAX INTEGER
      ACCESS read-only
      STATUS mandatory
      DESCRIPTION
        "Total number of picks done by this media mover."
      ::= { moverEntry 14 }
    
    moverPickRetries OBJECT-TYPE
      SYNTAX INTEGER
      ACCESS read-only
      STATUS optional
      DESCRIPTION
        "Total number of pick retries by this media mover."
      ::= { moverEntry 15 }
    
    moverPlaceRetries OBJECT-TYPE
      SYNTAX INTEGER
      ACCESS read-only
      STATUS optional
      DESCRIPTION
        "Total number of place retries by this media mover."
      ::= { moverEntry 16 }
    
    moverLoadRetries OBJECT-TYPE
      SYNTAX INTEGER
      ACCESS read-only
      STATUS optional
      DESCRIPTION
        "Total number of load retries by this media mover."
      ::= { moverEntry 17 }
    
    moverScanRetries OBJECT-TYPE
      SYNTAX INTEGER
      ACCESS read-only
      STATUS optional
      DESCRIPTION
        "Total number of scan retries by this media mover."
      ::= { moverEntry 18 }
    
    moverDoorState OBJECT-TYPE
      SYNTAX INTEGER
        {
        unknown(1),
        open(2),
        closed(3),
        locked(4)
        }
      ACCESS read-only
      STATUS mandatory
      DESCRIPTION
        "Door State of the device. The interpretation of this value is vendor specific."
      ::= { moverEntry 19 }
    
    moverMailboxState OBJECT-TYPE
      SYNTAX INTEGER
        {
        unknown(1),
        open(2),
        closed(3),
        locked(4)
        }
      ACCESS read-only
      STATUS mandatory
      DESCRIPTION
        "Mailbox State of the device. The interpretation of this value is vendor specific."
      ::= { moverEntry 20 }
    
    driveTable OBJECT-TYPE
      SYNTAX SEQUENCE OF DriveEntry
      ACCESS not-accessible
      STATUS mandatory
      DESCRIPTION
        "A table of all tape drive devices in the domain of this SNMP agent."
      ::= { physicalDevices 4 }
    
    driveEntry OBJECT-TYPE
      SYNTAX DriveEntry
      ACCESS not-accessible
      STATUS mandatory
      DESCRIPTION
        "Entry in the device Table. Each entry contains
        an index (tapeEntryId), and the values associated 
        with the device."
      INDEX { driveEntryId }
      ::= { driveTable 1 }
    
    DriveEntry ::=
      SEQUENCE { 
        driveEntryId
          INTEGER,
        driveTimeStamp
          INTEGER,
        driveState
          INTEGER,
        driveVendor
          DisplayString,
        driveModel
          DisplayString,
        driveFwlevel
          DisplayString,
        driveSerNum
          DisplayString,
        driveScsiId
          INTEGER,
        driveScsiLun
          INTEGER,
        driveLibrarySN
          DisplayString,
        driveClean
          INTEGER,
        driveLoads
          INTEGER
       }

    driveEntryId OBJECT-TYPE
      SYNTAX INTEGER (1..512)
      ACCESS read-only
      STATUS mandatory
      DESCRIPTION
        "Table entry index value. Each unique physical device has a unique tapeEntryId."
      ::= { driveEntry 1 }
    
    driveTimeStamp OBJECT-TYPE
      SYNTAX INTEGER
      ACCESS read-only
      STATUS mandatory
      DESCRIPTION
        "Universal time in sec since UTC 1/1/70 when the device data was last updated."
      ::= { driveEntry 2 }
    
    driveState OBJECT-TYPE
      SYNTAX INTEGER
      ACCESS read-only
      STATUS mandatory
      DESCRIPTION
        "Device SCSI State."
      ::= { driveEntry 3 }
    
    driveVendor OBJECT-TYPE
      SYNTAX DisplayString
      ACCESS read-only
      STATUS mandatory
      DESCRIPTION
        "Device Vendor as would be reported in a SCSI Inquiry command."
      ::= { driveEntry 4 }
    
    driveModel OBJECT-TYPE
      SYNTAX DisplayString
      ACCESS read-only
      STATUS mandatory
      DESCRIPTION
        "Device Model as would be reported in a SCSI Inquiry command."
      ::= { driveEntry 5 }
    
    driveFwlevel OBJECT-TYPE
      SYNTAX DisplayString
      ACCESS read-only
      STATUS mandatory
      DESCRIPTION
        "Device firmware level as would be reported in a SCSI Inquiry command."
      ::= { driveEntry 6 }
    
    driveSerNum OBJECT-TYPE
      SYNTAX DisplayString
      ACCESS read-only
      STATUS mandatory
      DESCRIPTION
        "Device serial number as reported in SCSI Inquiry command, page 0x80."
      ::= { driveEntry 7 }
    
    driveScsiId OBJECT-TYPE
      SYNTAX INTEGER
      ACCESS read-only
      STATUS mandatory
      DESCRIPTION
        "SCSI ID of the device."
      ::= { driveEntry 8 }
    
    driveScsiLun OBJECT-TYPE
      SYNTAX INTEGER
      ACCESS read-only
      STATUS mandatory
      DESCRIPTION
        "SCSI Lun of the device."
      ::= { driveEntry 9 }
    
    driveLibrarySN OBJECT-TYPE
      SYNTAX DisplayString
      ACCESS read-only
      STATUS mandatory
      DESCRIPTION
        "Serial Number of the library that this drive is in as reported in SCSI Inquiry command, page 0x80, for the media mover device."
      ::= { driveEntry 10 }
    
    driveClean OBJECT-TYPE
      SYNTAX INTEGER
      ACCESS read-only
      STATUS mandatory
      DESCRIPTION
        "Cleaning State of the device. The interpretation of this value is vendor specific."
      ::= { driveEntry 11 }
    
    driveLoads OBJECT-TYPE
      SYNTAX INTEGER
      ACCESS read-only
      STATUS mandatory
      DESCRIPTION
        "Total cartridge loads for the drive."
      ::= { driveEntry 12 }
    
  
--
-- Trap definitions
--
  
    statusChange TRAP-TYPE
      ENTERPRISE library
      VARIABLES { displayName, globalStatus, prevGlobalStatus }
      DESCRIPTION
        "The %s status has changed to %s.  Previous status was %s."
      ::=  1
      
    doorStateChange TRAP-TYPE
      ENTERPRISE library
      VARIABLES { displayName, moverDoorState }
      DESCRIPTION
        "The %s door state has changed to %s."
      ::=  2
      
    mailboxStateChange TRAP-TYPE
      ENTERPRISE library
      VARIABLES { displayName, moverMailboxState }
      DESCRIPTION
        "The %s mailbox state has changed to %s."
      ::=  3
      
    startup TRAP-TYPE
      ENTERPRISE library
      VARIABLES { displayName, startupState }
      DESCRIPTION
        "The %s device has started.  The shutdown state was %s."
      ::=  4
      
    shutdown TRAP-TYPE
      ENTERPRISE library
      VARIABLES { displayName, shutdownState }
      DESCRIPTION
        "The %s device has shut down.  The shutdown state is %s."
      ::=  5
      
    error TRAP-TYPE
      ENTERPRISE library
      VARIABLES { displayName, errorCode, errorModifier }
      DESCRIPTION
        "The %s device had an error.  Error code is %s.  Error data is %s."
      ::=  6
      
    sac TRAP-TYPE
      ENTERPRISE library
      VARIABLES { displayName, serviceActionCode }
      DESCRIPTION
        "The %s device generated a SAC code of %s."
      ::=  7
      
  
  END

--
-- ADICLIBMIB-v2.mib
--
