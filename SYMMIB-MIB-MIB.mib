-- MIB generated by mibgen version 1.0

SYMMIB-MIB-MIB DEFINITIONS ::= BEGIN

IMPORTS
	enterprises, Counter64
		FROM RFC1155-SMI
	InternationalDisplayString
		FROM HOST-RESOURCES-MIB
	OBJECT-TYPE
		FROM RFC-1212
	Counter,Gauge,
	DisplayString
		FROM RFC1213-MIB
	Dmi-Date,Dmi-Integer64,
	dmiEventDateTime,dmiCompId,dmiEventSeverity,
	dmiEventStateKey,dmiEventAssociatedGroup,
	dmiEventSystem,dmiEventSubSystem
		FROM DMTF-DMI-MIB; -- DMTF-DMI;

DmiCounter			::= Counter
DmiCounter64		::= Counter64
DmiGauge			::= Gauge
DmiInteger			::= INTEGER
DmiOctetstring		::= OCTET STRING
DmiDisplaystring	::= DisplayString
DmiCompId	::= INTEGER
DmiGroupId	::= INTEGER

dmtf        	OBJECT IDENTIFIER ::= { enterprises 412 }
dmtfStdMifs     	OBJECT IDENTIFIER ::= { dmtf 2 }
dmtfDynOids     	OBJECT IDENTIFIER ::= { dmtf 3 }
symbios        OBJECT IDENTIFIER ::= { enterprises 1123 } -- adj: ipMonitor Corp
symbios-3-1-2     OBJECT IDENTIFIER ::= { symbios 3 1 2 } -- adj: ipMonitor Corp

SsYMBIOSSymbiosEventPolling ::= SEQUENCE {
	symbiosFlagAtt1	DmiInteger,
	sMARTEventPollingAtt2	DmiInteger,
	scanEventPollingAtt3	DmiInteger,
	sAFTEEventPollingAtt4	DmiInteger,
	eventPollingPeriodAtt5	DmiInteger
}

sYMBIOSSymbiosEventPollingTable OBJECT-TYPE
	SYNTAX		SEQUENCE OF SsYMBIOSSymbiosEventPolling
	ACCESS		not-accessible
	STATUS		mandatory
	DESCRIPTION	"This group is the Symbios Vendor unique group for dealing
with Event Polling."
	::= { enterprises symbios(1123) symbios-3(3) symbios-3-1(1) symbios-3-1-2(2) 5 }

sYMBIOSSymbiosEventPollingEntry OBJECT-TYPE
	SYNTAX		SsYMBIOSSymbiosEventPolling
	ACCESS		not-accessible
	STATUS		mandatory
	DESCRIPTION	"This group is the Symbios Vendor unique group for dealing
with Event Polling."
	--INDEX		{ DmiCompId,DmiGroupId }
	::= { sYMBIOSSymbiosEventPollingTable 1 }

symbiosFlagAtt1 OBJECT-TYPE
	SYNTAX		DmiInteger
	ACCESS		read-write
	STATUS		mandatory
	DESCRIPTION	"An Symbios Vendor Unique Flag."
	REFERENCE "'SYMBIOS|Symbios Event Polling|001' 1"
	::= { sYMBIOSSymbiosEventPollingEntry 1 }

sMARTEventPollingAtt2 OBJECT-TYPE
	SYNTAX		INTEGER {
		disabled(0),
		enabled(1),
		unknown(2),
		notApplicable(3)
	}
	ACCESS		read-write
	STATUS		mandatory
	DESCRIPTION	"A flag indicating whether or not the CI will poll for SMART
events."
	REFERENCE "'SYMBIOS|Symbios Event Polling|001' 2"
	::= { sYMBIOSSymbiosEventPollingEntry 2 }

scanEventPollingAtt3 OBJECT-TYPE
	SYNTAX		INTEGER {
		disabled(0),
		enabled(1),
		unknown(2),
		notApplicable(3)
	}
	ACCESS		read-write
	STATUS		mandatory
	DESCRIPTION	"A flag indicating whether or not the CI will scan for a change
in Devices and Controllers."
	REFERENCE "'SYMBIOS|Symbios Event Polling|001' 3"
	::= { sYMBIOSSymbiosEventPollingEntry 3 }

sAFTEEventPollingAtt4 OBJECT-TYPE
	SYNTAX		INTEGER {
		disabled(0),
		enabled(1),
		unknown(2),
		notApplicable(3)
	}
	ACCESS		read-write
	STATUS		mandatory
	DESCRIPTION	"A flag indicating whether or not the CI will poll for SAF-TE
events."
	REFERENCE "'SYMBIOS|Symbios Event Polling|001' 4"
	::= { sYMBIOSSymbiosEventPollingEntry 4 }

eventPollingPeriodAtt5 OBJECT-TYPE
	SYNTAX		DmiInteger
	ACCESS		read-write
	STATUS		mandatory
	DESCRIPTION	"The event poll period in number of minutes."
	REFERENCE "'SYMBIOS|Symbios Event Polling|001' 5"
	::= { sYMBIOSSymbiosEventPollingEntry 5 }

SsYMBIOSSymbiosSmartDevice ::= SEQUENCE {
	sYMBIOSSymbiosSmartDeviceState INTEGER,
	symSMARTDeviceIndexAtt1	DmiInteger,
	sMARTReportingCapabilityAtt2	DmiInteger
}

sYMBIOSSymbiosSmartDeviceTable OBJECT-TYPE
	SYNTAX		SEQUENCE OF SsYMBIOSSymbiosSmartDevice
	ACCESS		not-accessible
	STATUS		mandatory
	DESCRIPTION	"This group is a Symbios Vendor unique group for dealing with
Smart Storage Devices."
	::= { symbios-3-1-2 6 }

sYMBIOSSymbiosSmartDeviceEntry OBJECT-TYPE
	SYNTAX		SsYMBIOSSymbiosSmartDevice
	ACCESS		not-accessible
	STATUS		mandatory
	DESCRIPTION	"This group is a Symbios Vendor unique group for dealing with
Smart Storage Devices."
	--INDEX		{ DmiCompId,DmiGroupId, symSMARTDeviceIndexAtt1 }
	::= { sYMBIOSSymbiosSmartDeviceTable 1 }


sYMBIOSSymbiosSmartDeviceState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|Symbios Smart Device|001' 0"
	::= { sYMBIOSSymbiosSmartDeviceEntry 0 }

symSMARTDeviceIndexAtt1 OBJECT-TYPE
	SYNTAX		DmiInteger
	ACCESS		read-only
	STATUS		mandatory
	DESCRIPTION	"An index into the Symbios Vendor Unique Device info table.
This index corresponds to the Storage Device index."
	REFERENCE "'SYMBIOS|Symbios Smart Device|001' 1"
	::= { sYMBIOSSymbiosSmartDeviceEntry 1 }

sMARTReportingCapabilityAtt2 OBJECT-TYPE
	SYNTAX		INTEGER {
		disabled(0),
		enabled(1),
		unknown(2),
		notSupported(3)
	}
	ACCESS		read-write
	STATUS		mandatory
	DESCRIPTION	"A flag indicating the state of a Devices's SMART reporting
capability."
	REFERENCE "'SYMBIOS|Symbios Smart Device|001' 2"
	::= { sYMBIOSSymbiosSmartDeviceEntry 2 }

SsYMBIOSSAFTEProcessor ::= SEQUENCE {
	sYMBIOSSAFTEProcessorState INTEGER,
	sAFTEProcessorIndexAtt1	DmiInteger,
	storageControllerIndexAtt2	DmiInteger,
	sCSIIDAtt3	Dmi-Integer64,
	sCSILUNAtt4	Dmi-Integer64,
	vendorIDAtt5	DmiDisplaystring,
	productIDAtt6	DmiDisplaystring,
	firmwareRevisionLevelAtt7	DmiDisplaystring,
	enclosureUniqueIdentifierAtt8	DmiDisplaystring,
	sAFTESpecificationRevisionLevelAtt9	DmiDisplaystring,
	hasLocksAtt10	DmiInteger,
	hasSpeakersAtt11	DmiInteger,
	doorLockedAtt12	DmiInteger,
	speakerStatusAtt13	DmiInteger,
	powerOnMinutesAtt14	DmiInteger,
	powerOnCyclesAtt15	DmiInteger,
	temperatureOutOfRangeAtt16	DmiInteger
}

sYMBIOSSAFTEProcessorTable OBJECT-TYPE
	SYNTAX		SEQUENCE OF SsYMBIOSSAFTEProcessor
	ACCESS		not-accessible
	STATUS		mandatory
	DESCRIPTION	"This group defines a SAF-TE Processor"
	::= { symbios-3-1-2 7 }

sYMBIOSSAFTEProcessorEntry OBJECT-TYPE
	SYNTAX		SsYMBIOSSAFTEProcessor
	ACCESS		not-accessible
	STATUS		mandatory
	DESCRIPTION	"This group defines a SAF-TE Processor"
	--INDEX		{ DmiCompId,DmiGroupId, sAFTEProcessorIndexAtt1 }
	::= { sYMBIOSSAFTEProcessorTable 1 }


sYMBIOSSAFTEProcessorState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|SAF-TE Processor|001' 0"
	::= { sYMBIOSSAFTEProcessorEntry 0 }

sAFTEProcessorIndexAtt1 OBJECT-TYPE
	SYNTAX		DmiInteger
	ACCESS		read-only
	STATUS		mandatory
	DESCRIPTION	"An index into the SAF-TE processor table."
	REFERENCE "'SYMBIOS|SAF-TE Processor|001' 1"
	::= { sYMBIOSSAFTEProcessorEntry 1 }

storageControllerIndexAtt2 OBJECT-TYPE
	SYNTAX		DmiInteger
	ACCESS		read-only
	STATUS		mandatory
	DESCRIPTION	"An index into the Storage Controller table."
	REFERENCE "'SYMBIOS|SAF-TE Processor|001' 2"
	::= { sYMBIOSSAFTEProcessorEntry 2 }

sCSIIDAtt3 OBJECT-TYPE
	SYNTAX		Dmi-Integer64
	ACCESS		read-only
	STATUS		mandatory
	DESCRIPTION	"The SCSI target/initiator identifier."
	REFERENCE "'SYMBIOS|SAF-TE Processor|001' 3"
	::= { sYMBIOSSAFTEProcessorEntry 3 }

sCSILUNAtt4 OBJECT-TYPE
	SYNTAX		Dmi-Integer64
	ACCESS		read-only
	STATUS		mandatory
	DESCRIPTION	"The SCSI logical unit number."
	REFERENCE "'SYMBIOS|SAF-TE Processor|001' 4"
	::= { sYMBIOSSAFTEProcessorEntry 4 }

vendorIDAtt5 OBJECT-TYPE
	SYNTAX		DmiDisplaystring
	ACCESS		read-only
	STATUS		mandatory
	DESCRIPTION	"The vendor ID that is returned in the Inquiry command"
	REFERENCE "'SYMBIOS|SAF-TE Processor|001' 5"
	::= { sYMBIOSSAFTEProcessorEntry 5 }

productIDAtt6 OBJECT-TYPE
	SYNTAX		DmiDisplaystring
	ACCESS		read-only
	STATUS		mandatory
	DESCRIPTION	"The product ID that is returned in the Inquiry command"
	REFERENCE "'SYMBIOS|SAF-TE Processor|001' 6"
	::= { sYMBIOSSAFTEProcessorEntry 6 }

firmwareRevisionLevelAtt7 OBJECT-TYPE
	SYNTAX		DmiDisplaystring
	ACCESS		read-only
	STATUS		mandatory
	DESCRIPTION	"Identifies the current firmware revision of the SAF-TE processor
"
	REFERENCE "'SYMBIOS|SAF-TE Processor|001' 7"
	::= { sYMBIOSSAFTEProcessorEntry 7 }

enclosureUniqueIdentifierAtt8 OBJECT-TYPE
	SYNTAX		DmiDisplaystring
	ACCESS		read-only
	STATUS		mandatory
	DESCRIPTION	"This field specifies the unique unit number for the SAF-TE
processor."
	REFERENCE "'SYMBIOS|SAF-TE Processor|001' 8"
	::= { sYMBIOSSAFTEProcessorEntry 8 }

sAFTESpecificationRevisionLevelAtt9 OBJECT-TYPE
	SYNTAX		DmiDisplaystring
	ACCESS		read-only
	STATUS		mandatory
	DESCRIPTION	"Identifies the revision of the SAF-TE interface specification
to which this device claims compliance."
	REFERENCE "'SYMBIOS|SAF-TE Processor|001' 9"
	::= { sYMBIOSSAFTEProcessorEntry 9 }

hasLocksAtt10 OBJECT-TYPE
	SYNTAX		INTEGER {
		false(0),
		true(1),
		unknown(2)
	}
	ACCESS		read-only
	STATUS		mandatory
	DESCRIPTION	"If true, then this SAF-TE processor is contained within an
enclosure that has locks."
	REFERENCE "'SYMBIOS|SAF-TE Processor|001' 10"
	::= { sYMBIOSSAFTEProcessorEntry 10 }

hasSpeakersAtt11 OBJECT-TYPE
	SYNTAX		INTEGER {
		false(0),
		true(1),
		unknown(2)
	}
	ACCESS		read-only
	STATUS		mandatory
	DESCRIPTION	"If true, then this SAF-TE processor is contained within an
enclosure that has speakers."
	REFERENCE "'SYMBIOS|SAF-TE Processor|001' 11"
	::= { sYMBIOSSAFTEProcessorEntry 11 }

doorLockedAtt12 OBJECT-TYPE
	SYNTAX		INTEGER {
		false(0),
		true(1),
		unknown(2)
	}
	ACCESS		read-only
	STATUS		mandatory
	DESCRIPTION	"If true, then this SAF-TE processor enclosure is locked."
	REFERENCE "'SYMBIOS|SAF-TE Processor|001' 12"
	::= { sYMBIOSSAFTEProcessorEntry 12 }

speakerStatusAtt13 OBJECT-TYPE
	SYNTAX		INTEGER {
		false(0),
		true(1),
		unknown(2)
	}
	ACCESS		read-only
	STATUS		mandatory
	DESCRIPTION	"If true, then this SAF-TE processor enclsoure speakers are
turned on. If false, then the speakers are off or not installed."
	REFERENCE "'SYMBIOS|SAF-TE Processor|001' 13"
	::= { sYMBIOSSAFTEProcessorEntry 13 }

powerOnMinutesAtt14 OBJECT-TYPE
	SYNTAX		DmiInteger
	ACCESS		read-only
	STATUS		mandatory
	DESCRIPTION	"Total number of power on minutes."
	REFERENCE "'SYMBIOS|SAF-TE Processor|001' 14"
	::= { sYMBIOSSAFTEProcessorEntry 14 }

powerOnCyclesAtt15 OBJECT-TYPE
	SYNTAX		DmiInteger
	ACCESS		read-only
	STATUS		mandatory
	DESCRIPTION	"Total number of times the SAF-TE enclosure has been power
on."
	REFERENCE "'SYMBIOS|SAF-TE Processor|001' 15"
	::= { sYMBIOSSAFTEProcessorEntry 15 }

temperatureOutOfRangeAtt16 OBJECT-TYPE
	SYNTAX		INTEGER {
		false(0),
		true(1),
		unknown(2)
	}
	ACCESS		read-only
	STATUS		mandatory
	DESCRIPTION	"If true, then the temperature is out of range."
	REFERENCE "'SYMBIOS|SAF-TE Processor|001' 16"
	::= { sYMBIOSSAFTEProcessorEntry 16 }

SsYMBIOSSAFTEControlledFan ::= SEQUENCE {
	sYMBIOSSAFTEControlledFanState INTEGER,
	sAFTEControlledFanIndexAtt1	DmiInteger,
	sAFTEProcessorIndexAtt2	DmiInteger,
	statusAtt3	DmiInteger
}

sYMBIOSSAFTEControlledFanTable OBJECT-TYPE
	SYNTAX		SEQUENCE OF SsYMBIOSSAFTEControlledFan
	ACCESS		not-accessible
	STATUS		mandatory
	DESCRIPTION	"This group defines status of a fan controlled by a SAF-TE
Processor"
	::= { symbios-3-1-2 8 }

sYMBIOSSAFTEControlledFanEntry OBJECT-TYPE
	SYNTAX		SsYMBIOSSAFTEControlledFan
	ACCESS		not-accessible
	STATUS		mandatory
	DESCRIPTION	"This group defines status of a fan controlled by a SAF-TE
Processor"
	--INDEX		{ DmiCompId,DmiGroupId, sAFTEControlledFanIndexAtt1 }
	::= { sYMBIOSSAFTEControlledFanTable 1 }


sYMBIOSSAFTEControlledFanState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|SAF-TE Controlled Fan|001' 0"
	::= { sYMBIOSSAFTEControlledFanEntry 0 }

sAFTEControlledFanIndexAtt1 OBJECT-TYPE
	SYNTAX		DmiInteger
	ACCESS		read-only
	STATUS		mandatory
	DESCRIPTION	"An index into the SAF-TE controlled fan table."
	REFERENCE "'SYMBIOS|SAF-TE Controlled Fan|001' 1"
	::= { sYMBIOSSAFTEControlledFanEntry 1 }

sAFTEProcessorIndexAtt2 OBJECT-TYPE
	SYNTAX		DmiInteger
	ACCESS		read-only
	STATUS		mandatory
	DESCRIPTION	"The Index to the SAF-TE proccessor that is controlling this
fan."
	REFERENCE "'SYMBIOS|SAF-TE Controlled Fan|001' 2"
	::= { sYMBIOSSAFTEControlledFanEntry 2 }

statusAtt3 OBJECT-TYPE
	SYNTAX		INTEGER {
		fanIsOperational(0),
		fanIsMalfunctioning(1),
		fanIsNotInstalled(2),
		unknownStatus(128)
	}
	ACCESS		read-only
	STATUS		mandatory
	DESCRIPTION	"The fan status."
	REFERENCE "'SYMBIOS|SAF-TE Controlled Fan|001' 3"
	::= { sYMBIOSSAFTEControlledFanEntry 3 }

SsYMBIOSSAFTEControlledPowerSupply ::= SEQUENCE {
	sYMBIOSSAFTEControlledPowerSupplyState INTEGER,
	sAFTEControlledPowerSupplyIndexAtt1	DmiInteger,
	sAFTEProcessorIndexAtt2	DmiInteger,
	statusAtt3	DmiInteger
}

sYMBIOSSAFTEControlledPowerSupplyTable OBJECT-TYPE
	SYNTAX		SEQUENCE OF SsYMBIOSSAFTEControlledPowerSupply
	ACCESS		not-accessible
	STATUS		mandatory
	DESCRIPTION	"This group defines status of a Power Supply controlled by
a SAF-TE Processor"
	::= { symbios-3-1-2 9 }

sYMBIOSSAFTEControlledPowerSupplyEntry OBJECT-TYPE
	SYNTAX		SsYMBIOSSAFTEControlledPowerSupply
	ACCESS		not-accessible
	STATUS		mandatory
	DESCRIPTION	"This group defines status of a Power Supply controlled by
a SAF-TE Processor"
	--INDEX		{ DmiCompId,DmiGroupId, sAFTEControlledPowerSupplyIndexAtt1 }
	::= { sYMBIOSSAFTEControlledPowerSupplyTable 1 }


sYMBIOSSAFTEControlledPowerSupplyState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|SAF-TE Controlled Power Supply|001' 0"
	::= { sYMBIOSSAFTEControlledPowerSupplyEntry 0 }

sAFTEControlledPowerSupplyIndexAtt1 OBJECT-TYPE
	SYNTAX		DmiInteger
	ACCESS		read-only
	STATUS		mandatory
	DESCRIPTION	"An index into the SAF-TE controlled Power Supply table."
	REFERENCE "'SYMBIOS|SAF-TE Controlled Power Supply|001' 1"
	::= { sYMBIOSSAFTEControlledPowerSupplyEntry 1 }

sAFTEProcessorIndexAtt2 OBJECT-TYPE
	SYNTAX		DmiInteger
	ACCESS		read-only
	STATUS		mandatory
	DESCRIPTION	"The Index to the SAF-TE proccessor that is controlling this
Power Supply."
	REFERENCE "'SYMBIOS|SAF-TE Controlled Power Supply|001' 2"
	::= { sYMBIOSSAFTEControlledPowerSupplyEntry 2 }

statusAtt3 OBJECT-TYPE
	SYNTAX		INTEGER {
		powerSupplyIsOperationalAndOn(0),
		powerSupplyIsOperationalAndOff(1),
		powerSupplyIsMalfunctioningAndCommandedOn(16),
		powerSupplyIsMalfunctioningAndCommandedOff(17),
		powerSupplyIsNotPresent(32),
		powerSupplyIsPresent(33),
		unknownStatus(128)
	}
	ACCESS		read-only
	STATUS		mandatory
	DESCRIPTION	"The Power Supply status."
	REFERENCE "'SYMBIOS|SAF-TE Controlled Power Supply|001' 3"
	::= { sYMBIOSSAFTEControlledPowerSupplyEntry 3 }

SsYMBIOSSAFTEControlledSlot ::= SEQUENCE {
	sYMBIOSSAFTEControlledSlotState INTEGER,
	sAFTEControlledSlotIndexAtt1	DmiInteger,
	sAFTEProcessorIndexAtt2	DmiInteger,
	sCSIIDAtt3	Dmi-Integer64,
	numberOfInsertionsAtt4	DmiInteger,
	stateAtt5	DmiInteger,
	rebuildAtt6	DmiInteger,
	deviceFaultAtt7	DmiInteger,
	inFailedArrayAtt8	DmiInteger,
	inCriticalArrayAtt9	DmiInteger,
	parityCheckAtt10	DmiInteger,
	predictedFaultAtt11	DmiInteger
}

sYMBIOSSAFTEControlledSlotTable OBJECT-TYPE
	SYNTAX		SEQUENCE OF SsYMBIOSSAFTEControlledSlot
	ACCESS		not-accessible
	STATUS		mandatory
	DESCRIPTION	"This group defines status of a Slot controlled by a SAF-TE
Processor"
	::= { symbios-3-1-2 10 }

sYMBIOSSAFTEControlledSlotEntry OBJECT-TYPE
	SYNTAX		SsYMBIOSSAFTEControlledSlot
	ACCESS		not-accessible
	STATUS		mandatory
	DESCRIPTION	"This group defines status of a Slot controlled by a SAF-TE
Processor"
	--INDEX		{ DmiCompId,DmiGroupId, sAFTEControlledSlotIndexAtt1 }
	::= { sYMBIOSSAFTEControlledSlotTable 1 }


sYMBIOSSAFTEControlledSlotState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|SAF-TE Controlled Slot|001' 0"
	::= { sYMBIOSSAFTEControlledSlotEntry 0 }

sAFTEControlledSlotIndexAtt1 OBJECT-TYPE
	SYNTAX		DmiInteger
	ACCESS		read-only
	STATUS		mandatory
	DESCRIPTION	"An index into the SAF-TE controlled Slot table."
	REFERENCE "'SYMBIOS|SAF-TE Controlled Slot|001' 1"
	::= { sYMBIOSSAFTEControlledSlotEntry 1 }

sAFTEProcessorIndexAtt2 OBJECT-TYPE
	SYNTAX		DmiInteger
	ACCESS		read-only
	STATUS		mandatory
	DESCRIPTION	"The Index to the SAF-TE proccessor table that is controlling
this Slot."
	REFERENCE "'SYMBIOS|SAF-TE Controlled Slot|001' 2"
	::= { sYMBIOSSAFTEControlledSlotEntry 2 }

sCSIIDAtt3 OBJECT-TYPE
	SYNTAX		Dmi-Integer64
	ACCESS		read-only
	STATUS		mandatory
	DESCRIPTION	"The SCSI target/initiator identifier for this slot."
	REFERENCE "'SYMBIOS|SAF-TE Controlled Slot|001' 3"
	::= { sYMBIOSSAFTEControlledSlotEntry 3 }

numberOfInsertionsAtt4 OBJECT-TYPE
	SYNTAX		DmiInteger
	ACCESS		read-only
	STATUS		mandatory
	DESCRIPTION	"The total number of device insertions for this slot while
the enclosure is powered on."
	REFERENCE "'SYMBIOS|SAF-TE Controlled Slot|001' 4"
	::= { sYMBIOSSAFTEControlledSlotEntry 4 }

stateAtt5 OBJECT-TYPE
	SYNTAX		INTEGER {
		devicePresentReady(1),
		devicePresentNotReady(2),
		devicePresentHotSpare(3),
		devicePresentReadyForRemoval(4),
		deviceNotPresent(5),
		deviceNotPresentReadyForInsertion(6),
		unconfigured(7),
		unknownState(8)
	}
	ACCESS		read-only
	STATUS		mandatory
	DESCRIPTION	"The slot state."
	REFERENCE "'SYMBIOS|SAF-TE Controlled Slot|001' 5"
	::= { sYMBIOSSAFTEControlledSlotEntry 5 }

rebuildAtt6 OBJECT-TYPE
	SYNTAX		INTEGER {
		notRebuilding(0),
		rebuildInProcess(1),
		rebuildStopped(2),
		unknownStatus(3)
	}
	ACCESS		read-only
	STATUS		mandatory
	DESCRIPTION	"Rebuild status"
	REFERENCE "'SYMBIOS|SAF-TE Controlled Slot|001' 6"
	::= { sYMBIOSSAFTEControlledSlotEntry 6 }

deviceFaultAtt7 OBJECT-TYPE
	SYNTAX		INTEGER {
		false(0),
		true(1),
		unknown(2)
	}
	ACCESS		read-only
	STATUS		mandatory
	DESCRIPTION	"If true, the device has exhibited some hardware or data fault."
	REFERENCE "'SYMBIOS|SAF-TE Controlled Slot|001' 7"
	::= { sYMBIOSSAFTEControlledSlotEntry 7 }

inFailedArrayAtt8 OBJECT-TYPE
	SYNTAX		INTEGER {
		false(0),
		true(1),
		unknown(2)
	}
	ACCESS		read-only
	STATUS		mandatory
	DESCRIPTION	"If true, the device is in an array and an error has occurred
on any member of the array."
	REFERENCE "'SYMBIOS|SAF-TE Controlled Slot|001' 8"
	::= { sYMBIOSSAFTEControlledSlotEntry 8 }

inCriticalArrayAtt9 OBJECT-TYPE
	SYNTAX		INTEGER {
		false(0),
		true(1),
		unknown(2)
	}
	ACCESS		read-only
	STATUS		mandatory
	DESCRIPTION	"If true, the device is in an array that is non fault-tolerant."
	REFERENCE "'SYMBIOS|SAF-TE Controlled Slot|001' 9"
	::= { sYMBIOSSAFTEControlledSlotEntry 9 }

parityCheckAtt10 OBJECT-TYPE
	SYNTAX		INTEGER {
		false(0),
		true(1),
		unknown(2)
	}
	ACCESS		read-only
	STATUS		mandatory
	DESCRIPTION	"If true, the device is in an array that is undergoing a parity
check operation."
	REFERENCE "'SYMBIOS|SAF-TE Controlled Slot|001' 10"
	::= { sYMBIOSSAFTEControlledSlotEntry 10 }

predictedFaultAtt11 OBJECT-TYPE
	SYNTAX		INTEGER {
		false(0),
		true(1),
		unknown(2)
	}
	ACCESS		read-only
	STATUS		mandatory
	DESCRIPTION	"If true, the device has been tagged by a fault prediction
algorithm as being likely to fail in the near future."
	REFERENCE "'SYMBIOS|SAF-TE Controlled Slot|001' 11"
	::= { sYMBIOSSAFTEControlledSlotEntry 11 }

SsYMBIOSSAFTEControlledTemperatureSensor ::= SEQUENCE {
	sYMBIOSSAFTEControlledTemperatureSensorState INTEGER,
	sAFTEControlledTemperatureSensorIndexAtt1	DmiInteger,
	sAFTEProcessorIndexAtt2	DmiInteger,
	temperatureAtt3	DmiInteger
}

sYMBIOSSAFTEControlledTemperatureSensorTable OBJECT-TYPE
	SYNTAX		SEQUENCE OF SsYMBIOSSAFTEControlledTemperatureSensor
	ACCESS		not-accessible
	STATUS		mandatory
	DESCRIPTION	"This group defines status of a Temperature sensor controlled
by a SAF-TE Processor"
	::= { symbios-3-1-2 11 }

sYMBIOSSAFTEControlledTemperatureSensorEntry OBJECT-TYPE
	SYNTAX		SsYMBIOSSAFTEControlledTemperatureSensor
	ACCESS		not-accessible
	STATUS		mandatory
	DESCRIPTION	"This group defines status of a Temperature sensor controlled
by a SAF-TE Processor"
	--INDEX		{ DmiCompId,DmiGroupId, sAFTEControlledTemperatureSensorIndexAtt1 }
	::= { sYMBIOSSAFTEControlledTemperatureSensorTable 1 }


sYMBIOSSAFTEControlledTemperatureSensorState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|SAF-TE Controlled Temperature sensor|001' 0"
	::= { sYMBIOSSAFTEControlledTemperatureSensorEntry 0 }

sAFTEControlledTemperatureSensorIndexAtt1 OBJECT-TYPE
	SYNTAX		DmiInteger
	ACCESS		read-only
	STATUS		mandatory
	DESCRIPTION	"An index into the SAF-TE controlled Temperature sensor table."
	REFERENCE "'SYMBIOS|SAF-TE Controlled Temperature sensor|001' 1"
	::= { sYMBIOSSAFTEControlledTemperatureSensorEntry 1 }

sAFTEProcessorIndexAtt2 OBJECT-TYPE
	SYNTAX		DmiInteger
	ACCESS		read-only
	STATUS		mandatory
	DESCRIPTION	"The Index to the SAF-TE proccessor that is controlling this
Temperature sensor."
	REFERENCE "'SYMBIOS|SAF-TE Controlled Temperature sensor|001' 2"
	::= { sYMBIOSSAFTEControlledTemperatureSensorEntry 2 }

temperatureAtt3 OBJECT-TYPE
	SYNTAX		DmiInteger
	ACCESS		read-only
	STATUS		mandatory
	DESCRIPTION	"The current temperature in degrees Fahrenheit."
	REFERENCE "'SYMBIOS|SAF-TE Controlled Temperature sensor|001' 3"
	::= { sYMBIOSSAFTEControlledTemperatureSensorEntry 3 }

SsYMBIOSNetworkAdapter802Port ::= SEQUENCE {
	sYMBIOSNetworkAdapter802PortState INTEGER,
	portIndexAtt1	DmiInteger,
	permanentNetworkAddressAtt2	DmiDisplaystring,
	currentNetworkAddressAtt3	DmiDisplaystring,
	connectorTypeAtt4	DmiInteger,
	dataRateAtt5	DmiInteger
}

sYMBIOSNetworkAdapter802PortTable OBJECT-TYPE
	SYNTAX		SEQUENCE OF SsYMBIOSNetworkAdapter802Port
	ACCESS		not-accessible
	STATUS		mandatory
	DESCRIPTION	"Contains objects related to each of the network ports on
the network adapter."
	::= { symbios-3-1-2 12 }

sYMBIOSNetworkAdapter802PortEntry OBJECT-TYPE
	SYNTAX		SsYMBIOSNetworkAdapter802Port
	ACCESS		not-accessible
	STATUS		mandatory
	DESCRIPTION	"Contains objects related to each of the network ports on
the network adapter."
	--INDEX		{ DmiCompId,DmiGroupId, portIndexAtt1 }
	::= { sYMBIOSNetworkAdapter802PortTable 1 }


sYMBIOSNetworkAdapter802PortState OBJECT-TYPE
	SYNTAX		INTEGER {
		active(1),
		notInService(2),
		notReady(3),
		createAndGo(4),
		createAndWait(5),
		destroy(6)
	}
	ACCESS		read-write
	STATUS		mandatory
DESCRIPTION ""
	REFERENCE "'SYMBIOS|Network Adapter 802 Port|001' 0"
	::= { sYMBIOSNetworkAdapter802PortEntry 0 }

portIndexAtt1 OBJECT-TYPE
	SYNTAX		DmiInteger
	ACCESS		read-only
	STATUS		mandatory
	DESCRIPTION	"This attribute is the ordinal of the network port within
the network adapter, i.e. the 'port number'."
	REFERENCE "'SYMBIOS|Network Adapter 802 Port|001' 1"
	::= { sYMBIOSNetworkAdapter802PortEntry 1 }

permanentNetworkAddressAtt2 OBJECT-TYPE
	SYNTAX		DmiDisplaystring
	ACCESS		read-only
	STATUS		mandatory
	DESCRIPTION	"This is the node address stored permanently in the adapter."
	REFERENCE "'SYMBIOS|Network Adapter 802 Port|001' 2"
	::= { sYMBIOSNetworkAdapter802PortEntry 2 }

currentNetworkAddressAtt3 OBJECT-TYPE
	SYNTAX		DmiDisplaystring
	ACCESS		read-only
	STATUS		mandatory
	DESCRIPTION	"This is the node address that can be modified by software,
sometimes referred to as the Locally Administered Address (LAA)."
	REFERENCE "'SYMBIOS|Network Adapter 802 Port|001' 3"
	::= { sYMBIOSNetworkAdapter802PortEntry 3 }

connectorTypeAtt4 OBJECT-TYPE
	SYNTAX		INTEGER {
		unknown(1),
		aUI(2),
		uTPCategory3(3),
		uTPCategory4(4),
		uTPCategory5(5),
		bNC(6),
		sTPRJ45(7),
		sTPDB9(8),
		fiberMIC(9),
		appleAUI(10)
	}
	ACCESS		read-only
	STATUS		mandatory
	DESCRIPTION	"This is the type of connector currently being used to physically
attach this port to the LAN."
	REFERENCE "'SYMBIOS|Network Adapter 802 Port|001' 4"
	::= { sYMBIOSNetworkAdapter802PortEntry 4 }

dataRateAtt5 OBJECT-TYPE
	SYNTAX		DmiInteger
	ACCESS		read-only
	STATUS		mandatory
	DESCRIPTION	"This is the rate at which data is transferred over the LAN
in Mbps."
	REFERENCE "'SYMBIOS|Network Adapter 802 Port|001' 5"
	::= { sYMBIOSNetworkAdapter802PortEntry 5 }

SdMTFNetworkAdapterHardware ::= SEQUENCE {
	networkTopologyAtt1	DmiInteger,
	transmissionCapabilityAtt2	DmiInteger,
	networkAdapterRAMSizeAtt3	DmiInteger,
	busTypeAtt4	DmiInteger,
	busWidthAtt5	DmiInteger
}
dmtfLANAdapterMIF	OBJECT IDENTIFIER ::= { dmtfStdMifs 2 }

dMTFNetworkAdapterHardwareTable OBJECT-TYPE
	SYNTAX		SEQUENCE OF SdMTFNetworkAdapterHardware
	ACCESS		not-accessible
	STATUS		mandatory
	DESCRIPTION	"Contains objects related to the network adapter hardware."
	::= { dmtfLANAdapterMIF 4 }

dMTFNetworkAdapterHardwareEntry OBJECT-TYPE
	SYNTAX		SdMTFNetworkAdapterHardware
	ACCESS		not-accessible
	STATUS		mandatory
	DESCRIPTION	"Contains objects related to the network adapter hardware."
	--INDEX		{ DmiCompId,DmiGroupId }
	::= { dMTFNetworkAdapterHardwareTable 1 }


networkTopologyAtt1 OBJECT-TYPE
	SYNTAX		INTEGER {
		other(1),
		x10MbpsEthernet(2),
		x100MbpsEthernet(3),
		x10010MbpsEthernet(4),
		x100MbpsVGAnyLAN(5),
		x4MbpsTokenRing(6),
		x16MbpsTokenRing(7),
		x164MbpsTokenRing(8),
		x2MbpsArcnet(9),
		x20MbpsArcnet(10),
		fDDI(11),
		aTM(12),
		appleTalk(13)
	}
	ACCESS		read-only
	STATUS		mandatory
	DESCRIPTION	"This is the network media access method/topology supported
by this adapter."
	REFERENCE "'DMTF|Network Adapter Hardware|001' 1"
	::= { dMTFNetworkAdapterHardwareEntry 1 }

transmissionCapabilityAtt2 OBJECT-TYPE
	SYNTAX		INTEGER {
		normal(1),
		fullDuplex(2)
	}
	ACCESS		read-only
	STATUS		mandatory
	DESCRIPTION	"The transmission capabilities of the adapter."
	REFERENCE "'DMTF|Network Adapter Hardware|001' 2"
	::= { dMTFNetworkAdapterHardwareEntry 2 }

networkAdapterRAMSizeAtt3 OBJECT-TYPE
	SYNTAX		DmiInteger
	ACCESS		read-only
	STATUS		mandatory
	DESCRIPTION	"This is the total size of adapter RAM in Kb."
	REFERENCE "'DMTF|Network Adapter Hardware|001' 3"
	::= { dMTFNetworkAdapterHardwareEntry 3 }

busTypeAtt4 OBJECT-TYPE
	SYNTAX		INTEGER {
		other(1),
		iSA(2),
		eISA(3),
		mCA(4),
		pCI(5),
		vL(6),
		pCMCIA(7),
		parallel(8),
		nEC98(9),
		motherboard(256)
	}
	ACCESS		read-only
	STATUS		mandatory
	DESCRIPTION	"This is the type of bus used to interface the adapter to
the host."
	REFERENCE "'DMTF|Network Adapter Hardware|001' 4"
	::= { dMTFNetworkAdapterHardwareEntry 4 }

busWidthAtt5 OBJECT-TYPE
	SYNTAX		INTEGER {
		other(1),
		unknown(2),
		x8BitCard(3),
		x16BitCard(4),
		x32BitCard(5),
		x64BitCard(6),
		x128BitCard(7)
	}
	ACCESS		read-only
	STATUS		mandatory
	DESCRIPTION	"This is the width (in bits) of the data path used to interface
the adapter with the host."
	REFERENCE "'DMTF|Network Adapter Hardware|001' 5"
	::= { dMTFNetworkAdapterHardwareEntry 5 }

SsYMBIOSSymbiosHealth ::= SEQUENCE {
	overallHealthStatusAtt1	DmiInteger,
	overallControllerHealthStatusAtt2	DmiInteger,
	nonRecoverableControllersAtt3	DmiInteger,
	degradedControllersAtt4	DmiInteger,
	overallDeviceHealthStatusAtt5	DmiInteger,
	nonRecoverableDevicesAtt6	DmiInteger,
	degradedDevicesAtt7	DmiInteger
}

sYMBIOSSymbiosHealthTable OBJECT-TYPE
	SYNTAX		SEQUENCE OF SsYMBIOSSymbiosHealth
	ACCESS		not-accessible
	STATUS		mandatory
	DESCRIPTION	"This group is the Symbios Vendor unique group for reporting
the health."
	::= { symbios-3-1-2 17 }

sYMBIOSSymbiosHealthEntry OBJECT-TYPE
	SYNTAX		SsYMBIOSSymbiosHealth
	ACCESS		not-accessible
	STATUS		mandatory
	DESCRIPTION	"This group is the Symbios Vendor unique group for reporting
the health."
	--INDEX		{ DmiCompId,DmiGroupId }
	::= { sYMBIOSSymbiosHealthTable 1 }


overallHealthStatusAtt1 OBJECT-TYPE
	SYNTAX		INTEGER {
		other(1),
		unknown(2),
		oK(3),
		degraded(4),
		nonRecoverable(5)
	}
	ACCESS		read-only
	STATUS		mandatory
	DESCRIPTION	"Status indicating the overall health."
	REFERENCE "'SYMBIOS|Symbios Health|001' 1"
	::= { sYMBIOSSymbiosHealthEntry 1 }

overallControllerHealthStatusAtt2 OBJECT-TYPE
	SYNTAX		INTEGER {
		other(1),
		unknown(2),
		oK(3),
		degraded(4),
		nonRecoverable(5)
	}
	ACCESS		read-only
	STATUS		mandatory
	DESCRIPTION	"Status indicating the overall health of the controllers."
	REFERENCE "'SYMBIOS|Symbios Health|001' 2"
	::= { sYMBIOSSymbiosHealthEntry 2 }

nonRecoverableControllersAtt3 OBJECT-TYPE
	SYNTAX		DmiInteger
	ACCESS		read-only
	STATUS		mandatory
	DESCRIPTION	"The number of controllers reporting a non-recoverable status."
	REFERENCE "'SYMBIOS|Symbios Health|001' 3"
	::= { sYMBIOSSymbiosHealthEntry 3 }

degradedControllersAtt4 OBJECT-TYPE
	SYNTAX		DmiInteger
	ACCESS		read-only
	STATUS		mandatory
	DESCRIPTION	"The number of controllers reporting a degraded status."
	REFERENCE "'SYMBIOS|Symbios Health|001' 4"
	::= { sYMBIOSSymbiosHealthEntry 4 }

overallDeviceHealthStatusAtt5 OBJECT-TYPE
	SYNTAX		INTEGER {
		other(1),
		unknown(2),
		oK(3),
		degraded(4),
		nonRecoverable(5)
	}
	ACCESS		read-only
	STATUS		mandatory
	DESCRIPTION	"Status indicating the overall health of the devices."
	REFERENCE "'SYMBIOS|Symbios Health|001' 5"
	::= { sYMBIOSSymbiosHealthEntry 5 }

nonRecoverableDevicesAtt6 OBJECT-TYPE
	SYNTAX		DmiInteger
	ACCESS		read-only
	STATUS		mandatory
	DESCRIPTION	"The number of devices reporting a non-recoverable status."
	REFERENCE "'SYMBIOS|Symbios Health|001' 6"
	::= { sYMBIOSSymbiosHealthEntry 6 }

degradedDevicesAtt7 OBJECT-TYPE
	SYNTAX		DmiInteger
	ACCESS		read-only
	STATUS		mandatory
	DESCRIPTION	"The number of devices reporting a degraded status."
	REFERENCE "'SYMBIOS|Symbios Health|001' 7"
	::= { sYMBIOSSymbiosHealthEntry 7 }

SiNTELMIFTOMIB ::= SEQUENCE {
	mIBNameAtt1	DmiDisplaystring,
	mIBOIDAtt2	DmiDisplaystring,
	disableTrapAtt3	DmiInteger
}

iNTELMIFTOMIBTable OBJECT-TYPE
	SYNTAX		SEQUENCE OF SiNTELMIFTOMIB
	ACCESS		not-accessible
	STATUS		mandatory
	DESCRIPTION	"This group defines attributes required for DMI to SNMP translati
n."
	::= { dmtfDynOids dmiDynOid386845712(386845712) dmiDynOid73111109(73111109) dmiDynOid3922453424(3922453424) 1737102472 }

iNTELMIFTOMIBEntry OBJECT-TYPE
	SYNTAX		SiNTELMIFTOMIB
	ACCESS		not-accessible
	STATUS		mandatory
	DESCRIPTION	"This group defines attributes required for DMI to SNMP translati
n."
	--INDEX		{ DmiCompId,DmiGroupId }
	::= { iNTELMIFTOMIBTable 1 }


mIBNameAtt1 OBJECT-TYPE
	SYNTAX		DmiDisplaystring
	ACCESS		read-only
	STATUS		mandatory
	DESCRIPTION	"The MIB name that defines this MIF"
	REFERENCE "'INTEL|MIFTOMIB|1.0' 1"
	::= { iNTELMIFTOMIBEntry 1 }

mIBOIDAtt2 OBJECT-TYPE
	SYNTAX		DmiDisplaystring
	ACCESS		read-only
	STATUS		mandatory
	DESCRIPTION	"The MIB OID that corresponds to this MIF"
	REFERENCE "'INTEL|MIFTOMIB|1.0' 2"
	::= { iNTELMIFTOMIBEntry 2 }

disableTrapAtt3 OBJECT-TYPE
	SYNTAX		DmiInteger
	ACCESS		read-write
	STATUS		mandatory
	DESCRIPTION	"This attribute can be changed to disable sending oftraps
from this component"
	REFERENCE "'INTEL|MIFTOMIB|1.0' 3"
	::= { iNTELMIFTOMIBEntry 3 }

END
