--
-- --------------------------------------------------------------
-- 


--
-- ------------------------------------------------------------------
-- 
 
   
  
   
   HWMD5500-ServiceAdmin-mib  DEFINITIONS ::= BEGIN
   
   -- 
   
   
   
   IMPORTS
          
          MODULE-IDENTITY,OBJECT-TYPE,Counter32, Unsigned32
                 FROM SNMPv2-SMI            
          RowStatus, DisplayString, TruthValue,TEXTUAL-CONVENTION 
	      	FROM SNMPv2-TC              
                    
          hwMd5500Mib
	      FROM HUAWEI-MIB;
         
      
     hwMD5500ServiceAdminMIB   MODULE-IDENTITY
        LAST-UPDATED      "0006141450Z"
        ORGANIZATION      "HUAWEI MUSA MD5500 Working Group"
        CONTACT-INFO
           "        MUSA  Dep.
           Postal:  Shenzhen
                    KeFa Road,ShenNan guarden
                    China
           Tel:     +1 086 0755 6594131
           Fax:     +1 086 0755 6544552"
         DESCRIPTION
                 "This is the MIB Module for huawei musa md5500  
                 private objects for service information."
      ::= {  hwMd5500Mib 2 }
         
  
       AtmOamConfigType ::= TEXTUAL-CONVENTION
            STATUS      current
            DESCRIPTION
                    "The config type used on OAM CC/PM configuration."
            SYNTAX      INTEGER {
                                autoConfig(1),
                                manualConfig(2),
                                other(3)
                                }
     
  
    --------------------------------------------
    -- 
    --------------------------------------------
    hwMD5500AtmOam    OBJECT IDENTIFIER ::= { hwMD5500ServiceAdminMIB 2 }
    --------------------------------------------
    -- 
    --------------------------------------------
    hwAtmOamCelCapTable           OBJECT-TYPE
        SYNTAX                    SEQUENCE OF HwAtmOamCelCapEntry
        MAX-ACCESS                not-accessible
        STATUS                    current
        DESCRIPTION               "
        		          " 
    ::={ hwMD5500AtmOam 1}
    
    hwAtmOamCelCapEntry           OBJECT-TYPE
        SYNTAX                    HwAtmOamCelCapEntry
        MAX-ACCESS                not-accessible
        STATUS                    current
        DESCRIPTION               "
        			  "
        INDEX                     {
                                      hwAtmOamFrame,
                                      hwAtmOamSlot,
                                      hwAtmOamChipNo
                                  }
    
    ::= { hwAtmOamCelCapTable  1 }
    
    HwAtmOamCelCapEntry       ::= SEQUENCE
        {
            hwAtmOamFrame                        INTEGER,
            hwAtmOamSlot                         INTEGER,
            hwAtmOamChipNo                       INTEGER,
            hwAtmOamCelCapCrcErrCell             Counter32,
            hwAtmOamCelCapUndefineCell           Counter32,
            hwAtmOamCelCapUnsuportCell           Counter32
        }

    hwAtmOamFrame                OBJECT-TYPE
        SYNTAX                   INTEGER(0..63)
        MAX-ACCESS               not-accessible
        STATUS                   current
        DESCRIPTION              "
        			 
        			 "
    ::= { hwAtmOamCelCapEntry  1 }
      
    hwAtmOamSlot                 OBJECT-TYPE
        SYNTAX                   INTEGER(0..63)
        MAX-ACCESS               not-accessible
        STATUS                   current
        DESCRIPTION              "
        			 
        			 "
    ::= { hwAtmOamCelCapEntry  2 }
          
    hwAtmOamChipNo               OBJECT-TYPE
        SYNTAX                   INTEGER(0..3)
        MAX-ACCESS               not-accessible
        STATUS                   current
        DESCRIPTION              "
        			 , 
        			 "
    ::= { hwAtmOamCelCapEntry  3 }
          
    hwAtmOamCelCapCrcErrCell     OBJECT-TYPE
        SYNTAX                   Counter32
        MAX-ACCESS               read-only
        STATUS                   current
        DESCRIPTION              "
        			 
        			 "
    ::= { hwAtmOamCelCapEntry  4 }     
     
    hwAtmOamCelCapUndefineCell   OBJECT-TYPE
        SYNTAX                   Counter32
        MAX-ACCESS               read-only
        STATUS                   current
        DESCRIPTION              "
        			 
        			 "
    ::= { hwAtmOamCelCapEntry  5 }      
    
    hwAtmOamCelCapUnsuportCell   OBJECT-TYPE
        SYNTAX                   Counter32
        MAX-ACCESS               read-only
        STATUS                   current
        DESCRIPTION              "
        			 
        			 "
    ::= { hwAtmOamCelCapEntry  6 }

    --------------------------------------------
    -- 
    --------------------------------------------
    hwAtmOamCfgUpStreamTable      OBJECT-TYPE
        SYNTAX                    SEQUENCE OF HwAtmOamCfgUpStreamEntry
        MAX-ACCESS                not-accessible
        STATUS                    current
        DESCRIPTION               "
        		          
        		          " 
    ::={ hwMD5500AtmOam 2}
    
    hwAtmOamCfgUpStreamEntry      OBJECT-TYPE
        SYNTAX                    HwAtmOamCfgUpStreamEntry
        MAX-ACCESS                not-accessible
        STATUS                    current
        DESCRIPTION               "
         			  
         			  "
        INDEX                     {
                                      hwAtmOamFrame,
                                      hwAtmOamSlot,
                                      hwAtmOamPort,
                                      hwAtmOamVPI,
                                      hwAtmOamVCI
                                  }    
    ::= { hwAtmOamCfgUpStreamTable  1 }
    
    HwAtmOamCfgUpStreamEntry       ::= SEQUENCE
        {
            hwAtmOamPort                         INTEGER,
            hwAtmOamVPI                          INTEGER,
            hwAtmOamVCI                          INTEGER,
            hwAtmOamCfgUpStreamSegment           INTEGER,
            hwAtmOamCfgUpStreamRowStatus         RowStatus
        }

    hwAtmOamPort                 OBJECT-TYPE
        SYNTAX                   INTEGER(0..63)
        MAX-ACCESS               not-accessible
        STATUS                   current
        DESCRIPTION              "
                                 
                                 "
    ::= { hwAtmOamCfgUpStreamEntry  1 }
      
    hwAtmOamVPI                  OBJECT-TYPE
        SYNTAX                   INTEGER(0..4095)
        MAX-ACCESS               not-accessible
        STATUS                   current
        DESCRIPTION              "
        			 
        			 "
    ::= { hwAtmOamCfgUpStreamEntry  2 }
          
    hwAtmOamVCI                  OBJECT-TYPE
        SYNTAX                   INTEGER(0 | 32..65535)
        MAX-ACCESS               not-accessible
        STATUS                   current
        DESCRIPTION              " 

                                 "
    ::= { hwAtmOamCfgUpStreamEntry  3 }
          
    hwAtmOamCfgUpStreamSegment   OBJECT-TYPE
        SYNTAX                   INTEGER
                                 {
                                     segment(1),
                                     endtoend(2),
                                     intermediate(3)
                                 }
        MAX-ACCESS               read-write
        STATUS                   current
        DESCRIPTION              ""
    ::= { hwAtmOamCfgUpStreamEntry  4 }     
    
    hwAtmOamCfgUpStreamRowStatus OBJECT-TYPE
        SYNTAX                   RowStatus
        MAX-ACCESS               read-write
        STATUS                   current
        DESCRIPTION              "
        			 "
    ::= { hwAtmOamCfgUpStreamEntry  5 }
    
    --------------------------------------------
    -- 
    --------------------------------------------
    hwAtmOamADConfigUpStreamTable OBJECT-TYPE
        SYNTAX                    SEQUENCE OF HwAtmOamADConfigUpStreamEntry
        MAX-ACCESS                not-accessible
        STATUS                    current
        DESCRIPTION               "
        			  " 
    ::={ hwMD5500AtmOam 3}
    
    hwAtmOamADConfigUpStreamEntry OBJECT-TYPE
        SYNTAX                    HwAtmOamADConfigUpStreamEntry
        MAX-ACCESS                not-accessible
        STATUS                    current
        DESCRIPTION               "
        			  "
        INDEX                     {
                                      hwAtmOamFrame,
                                      hwAtmOamSlot,
                                      hwAtmOamPort,
                                      hwAtmOamVPI,
                                      hwAtmOamVCI,
                                      hwAtmOamADType
                                  }    
    ::= { hwAtmOamADConfigUpStreamTable  1 }
    
    HwAtmOamADConfigUpStreamEntry       ::= SEQUENCE
        {
            hwAtmOamADType                           INTEGER,
            hwAtmOamADConfigUpStreamADDirection      INTEGER,
            hwAtmOamADConfigUpStreamADCellType       INTEGER,
            hwAtmOamADConfigUpStreamPMBlockSize                  INTEGER,
            hwAtmOamADConfigUpStreamRowStatus        RowStatus
        }

    hwAtmOamADType               OBJECT-TYPE
        SYNTAX                   INTEGER
                                 {
                                     cc(1),
                                     pm(2)
                                 }
        MAX-ACCESS               not-accessible
        STATUS                   current
        DESCRIPTION              ""
    ::= { hwAtmOamADConfigUpStreamEntry  1 }

    hwAtmOamADConfigUpStreamADDirection   OBJECT-TYPE
        SYNTAX                   INTEGER
                                 {
                                     btoa(1),
                                     atob(2),
                                     atob-and-btoa(3)
                                 }
        MAX-ACCESS               read-write
        STATUS                   current
        DESCRIPTION              ""
    ::= { hwAtmOamADConfigUpStreamEntry  2 }

    hwAtmOamADConfigUpStreamADCellType   OBJECT-TYPE
        SYNTAX                   INTEGER
                                 {
                                     segment(1),
                                     endtoend(2)
                                 }
        MAX-ACCESS               read-write
        STATUS                   current
        DESCRIPTION              ""
    ::= { hwAtmOamADConfigUpStreamEntry  3 }

    hwAtmOamADConfigUpStreamPMBlockSize   OBJECT-TYPE
        SYNTAX                   INTEGER
                                 {
                                     size128(128),
                                     size256(256),
                                     size512(512),
                                     size1024(1024),
                                     size2048(2048),
                                     size4096(4096),
                                     size8192(8192),
                                     size16384(16384),
                                     size32768(32768)
                                 }
        MAX-ACCESS               read-write
        STATUS                   current
        DESCRIPTION              ""
    ::= { hwAtmOamADConfigUpStreamEntry  4 }

    hwAtmOamADConfigUpStreamRowStatus    OBJECT-TYPE
        SYNTAX                   RowStatus
        MAX-ACCESS               read-write
        STATUS                   current
        DESCRIPTION              ""
    ::= { hwAtmOamADConfigUpStreamEntry  5 }

    --------------------------------------------
    -- 
    --------------------------------------------
    hwAtmOamLBUpStreamTable       OBJECT-TYPE
        SYNTAX                    SEQUENCE OF HwAtmOamLBUpStreamEntry
        MAX-ACCESS                not-accessible
        STATUS                    current
        DESCRIPTION               "" 
    ::={ hwMD5500AtmOam 4}
    
    hwAtmOamLBUpStreamEntry       OBJECT-TYPE
        SYNTAX                    HwAtmOamLBUpStreamEntry
        MAX-ACCESS                not-accessible
        STATUS                    current
        DESCRIPTION               "
        			  "
        INDEX                     {
                                      hwAtmOamFrame,
                                      hwAtmOamSlot,
                                      hwAtmOamPort,
                                      hwAtmOamVPI,
                                      hwAtmOamVCI
                                  }    
    ::= { hwAtmOamLBUpStreamTable  1 }
    
    HwAtmOamLBUpStreamEntry       ::= SEQUENCE
        {
            hwAtmOamLBUpStreamLBType                       INTEGER,
            hwAtmOamLBUpStreamLLId                         DisplayString
        }

    hwAtmOamLBUpStreamLBType     OBJECT-TYPE
        SYNTAX                   INTEGER
                                 {
                                     segment(1),
                                     endtoend(2)
                                 }
        MAX-ACCESS               read-write
        STATUS                   current
        DESCRIPTION              "
        			 "
    ::= { hwAtmOamLBUpStreamEntry  1 }

    hwAtmOamLBUpStreamLLId       OBJECT-TYPE
        SYNTAX                   DisplayString(SIZE(20))
        MAX-ACCESS               read-write
        STATUS                   current
        DESCRIPTION              ""
    ::= { hwAtmOamLBUpStreamEntry  2 }
	      
    
    -- ----------------------
    -- 
    -- ----------------------
    hwMD5500ApsService  OBJECT IDENTIFIER ::={ hwMD5500ServiceAdminMIB 7}

    -- ----------------------
    --  hwAtmApsVpRingTable
    -- ----------------------    
    hwAtmApsVpRingTable             OBJECT-TYPE
        SYNTAX                      SEQUENCE OF HwAtmApsVpRingEntry
        MAX-ACCESS                  not-accessible
        STATUS                      current
        DESCRIPTION                 "
        			    "
    ::= { hwMD5500ApsService 1 }
        
    hwAtmApsVpRingEntry             OBJECT-TYPE 
        SYNTAX                      HwAtmApsVpRingEntry
        MAX-ACCESS                  not-accessible
        STATUS                      current
        DESCRIPTION                 "
        			    "
        INDEX                       {
                                        hwAtmApsVpRingIndex
                                    } 
        ::={ hwAtmApsVpRingTable 1 }           

    HwAtmApsVpRingEntry ::= SEQUENCE
    {
        hwAtmApsVpRingIndex                    INTEGER,
        hwAtmApsVpRingPosition                 INTEGER,
        hwAtmApsVpRingFrameID1                 INTEGER,
        hwAtmApsVpRingSlotID1                  INTEGER,
        hwAtmApsVpRingPortID1                  INTEGER,
        hwAtmApsVpRingFrameID2                 INTEGER,
        hwAtmApsVpRingSlotID2                  INTEGER,
        hwAtmApsVpRingPortID2                  INTEGER,
        hwAtmApsVpRingRowStatus                RowStatus
    }

    hwAtmApsVpRingIndex             OBJECT-TYPE
        SYNTAX                      INTEGER(0..15)
        MAX-ACCESS                  not-accessible
        STATUS                      current
        DESCRIPTION                 "
        			    "
    ::= { hwAtmApsVpRingEntry  1 }         

    hwAtmApsVpRingPosition          OBJECT-TYPE
        SYNTAX                      INTEGER(0..15)
        MAX-ACCESS                  read-write
        STATUS                      current
        DESCRIPTION                 "
        			    "
    ::= { hwAtmApsVpRingEntry  2 }         

    hwAtmApsVpRingFrameID1          OBJECT-TYPE
        SYNTAX                      INTEGER(0..63)
        MAX-ACCESS                  read-write
        STATUS                      current
        DESCRIPTION                 "
        			    "
    ::= { hwAtmApsVpRingEntry  3 }         

    hwAtmApsVpRingSlotID1           OBJECT-TYPE
        SYNTAX                      INTEGER(0..63)
        MAX-ACCESS                  read-write
        STATUS                      current
        DESCRIPTION                 "
        			    "
    ::= { hwAtmApsVpRingEntry  4 }         

    hwAtmApsVpRingPortID1           OBJECT-TYPE
        SYNTAX                      INTEGER(0..63)
        MAX-ACCESS                  read-write
        STATUS                      current
        DESCRIPTION                 "
        			    "
    ::= { hwAtmApsVpRingEntry  5 }         

    hwAtmApsVpRingFrameID2          OBJECT-TYPE
        SYNTAX                      INTEGER(0..63)
        MAX-ACCESS                  read-write
        STATUS                      current
        DESCRIPTION                 "
        			    "
    ::= { hwAtmApsVpRingEntry  6 }         

    hwAtmApsVpRingSlotID2           OBJECT-TYPE
        SYNTAX                      INTEGER(0..63)
        MAX-ACCESS                  read-write
        STATUS                      current
        DESCRIPTION                 "
        			    "
    ::= { hwAtmApsVpRingEntry  7 }         

    hwAtmApsVpRingPortID2           OBJECT-TYPE
        SYNTAX                      INTEGER(0..63)
        MAX-ACCESS                  read-write
        STATUS                      current
        DESCRIPTION                 "
                                    "
    ::= { hwAtmApsVpRingEntry  8 }         

    hwAtmApsVpRingRowStatus         OBJECT-TYPE
        SYNTAX                      RowStatus
        MAX-ACCESS                  read-write
        STATUS                      current
        DESCRIPTION                 "
                                    "
    ::= { hwAtmApsVpRingEntry  9 }         

    -- ----------------------
    --  hwAtmApsVPGConfigTable
    -- ----------------------

    hwAtmApsVPGConfigTable          OBJECT-TYPE
        SYNTAX                      SEQUENCE OF HwAtmApsVPGConfigEntry
        MAX-ACCESS                  not-accessible
        STATUS                      current
        DESCRIPTION                 "
                                     "
    ::= { hwMD5500ApsService 2 }
        
    hwAtmApsVPGConfigEntry          OBJECT-TYPE 
        SYNTAX                      HwAtmApsVPGConfigEntry
        MAX-ACCESS                  not-accessible
        STATUS                      current
        DESCRIPTION                 "
                                    "
        INDEX                       {
                                        hwAtmApsVPGIndex
                                    } 
        ::={ hwAtmApsVPGConfigTable 1 }           

    HwAtmApsVPGConfigEntry ::= SEQUENCE
    {
        hwAtmApsVPGIndex                        INTEGER,
        hwAtmApsVPGName                         DisplayString,
        hwAtmApsVPGWorkingFrameID               INTEGER,
        hwAtmApsVPGWorkingSlotID                INTEGER,
        hwAtmApsVPGWorkingPhyportID             INTEGER,
        hwAtmApsVPGProtectionFrameID            INTEGER,
        hwAtmApsVPGProtectionSlotID             INTEGER,
        hwAtmApsVPGProtectionPhyportID          INTEGER,
        hwAtmApsVPGMode                         INTEGER,
        hwAtmApsVPGWTRTime                      INTEGER,
        hwAtmApsVPGExternalCommands             INTEGER,
        hwAtmApsVPGProtectK1K2Rcv               INTEGER,
        hwAtmApsVPGProtectK1K2Trans             INTEGER,
        hwAtmApsVPGWorkingEntityStatus          BITS,
        hwAtmApsVPGProtectionEntityStatus       BITS,
        hwAtmApsVPGCurrEntity                   INTEGER,
        hwAtmApsVPGApsStatus                    INTEGER,
        hwAtmApsVPGVplIsInUse                   TruthValue,
        hwAtmApsVPGVpRingIndex                  INTEGER,
        hwAtmApsVPGRevertive                    TruthValue,
        hwAtmApsVPGRowStatus                    RowStatus
    }

    hwAtmApsVPGIndex                OBJECT-TYPE
        SYNTAX                      INTEGER(1..256)
        MAX-ACCESS                  not-accessible
        STATUS                      current
        DESCRIPTION                 "
                                     "
    ::= { hwAtmApsVPGConfigEntry  1 }         

    hwAtmApsVPGName                 OBJECT-TYPE
        SYNTAX                      DisplayString(SIZE(0..51))
        MAX-ACCESS                  read-write
        STATUS                      current
        DESCRIPTION                 ""
    ::= { hwAtmApsVPGConfigEntry  2 }         

    hwAtmApsVPGWorkingFrameID       OBJECT-TYPE
        SYNTAX                      INTEGER(0..63)
        MAX-ACCESS                  read-write
        STATUS                      current
        DESCRIPTION                 "
                                    "
    ::= { hwAtmApsVPGConfigEntry  3 }         

    hwAtmApsVPGWorkingSlotID        OBJECT-TYPE
        SYNTAX                      INTEGER(0..63)
        MAX-ACCESS                  read-write
        STATUS                      current
        DESCRIPTION                 "
        			    "
    ::= { hwAtmApsVPGConfigEntry  4 }         

    hwAtmApsVPGWorkingPhyportID     OBJECT-TYPE
        SYNTAX                      INTEGER(0..63)
        MAX-ACCESS                  read-write
        STATUS                      current
        DESCRIPTION                 "
        			    "
    ::= { hwAtmApsVPGConfigEntry  5 }         

    hwAtmApsVPGProtectionFrameID    OBJECT-TYPE
        SYNTAX                      INTEGER(0..63)
        MAX-ACCESS                  read-write
        STATUS                      current
        DESCRIPTION                 "
                                    "
    ::= { hwAtmApsVPGConfigEntry  6 }         

    hwAtmApsVPGProtectionSlotID     OBJECT-TYPE
        SYNTAX                      INTEGER(0..63)
        MAX-ACCESS                  read-write
        STATUS                      current
        DESCRIPTION                 "
                                    "
    ::= { hwAtmApsVPGConfigEntry  7 }         

    hwAtmApsVPGProtectionPhyportID  OBJECT-TYPE
        SYNTAX                      INTEGER(0..63)
        MAX-ACCESS                  read-write
        STATUS                      current
        DESCRIPTION                 "
        			    "
    ::= { hwAtmApsVPGConfigEntry  8 }         

    hwAtmApsVPGMode                 OBJECT-TYPE
        SYNTAX                      INTEGER
                                    {
                                        onePlusOneUnidirection(1),
                                        onePlusOneBidirection(2)
                                    }
        MAX-ACCESS                  read-write
        STATUS                      current
        DESCRIPTION                 ""
    ::= { hwAtmApsVPGConfigEntry  9 }         

    hwAtmApsVPGWTRTime              OBJECT-TYPE
        SYNTAX                      INTEGER(1..30)
        MAX-ACCESS                  read-write
        STATUS                      current
        DESCRIPTION                 ""
    ::= { hwAtmApsVPGConfigEntry  10 }         

    hwAtmApsVPGExternalCommands     OBJECT-TYPE
        SYNTAX                      INTEGER
                                    {
                                         clear(1),
                                         freeze(2),
                                         lockoutOfProtection(3),
                                         forcedSwitchForWorking(4),
                                         manualSwitchForWorking(5),
                                         manualSwitchForProtection(6)
                                    }
        MAX-ACCESS                  read-write
        STATUS                      current
        DESCRIPTION                 ""
    ::= { hwAtmApsVPGConfigEntry  11 }         

    hwAtmApsVPGProtectK1K2Rcv       OBJECT-TYPE
        SYNTAX                      INTEGER(0..65535)
        MAX-ACCESS                  read-only
        STATUS                      current
        DESCRIPTION                 ""
    ::= { hwAtmApsVPGConfigEntry  12 }         

    hwAtmApsVPGProtectK1K2Trans     OBJECT-TYPE
        SYNTAX                      INTEGER(0..65535)
        MAX-ACCESS                  read-only
        STATUS                      current
        DESCRIPTION                 ""
    ::= { hwAtmApsVPGConfigEntry  13 }         


    hwAtmApsVPGWorkingEntityStatus  OBJECT-TYPE
        SYNTAX                      BITS
                                    {
                                        lof(1),
                                        los(2),
                                        sd(3),
                                        rdi(4),
                                        ais(5),
                                        rsd(6)
                                   }
        MAX-ACCESS                  read-only
        STATUS                      current
        DESCRIPTION                 "
                                     0x00000002-RSD
                                     0x00000004-AIS,
                                     0x00000008-RDI,
                                     0x00000010-SD,
                                     0x00000020-LOS,
                                     0x00000040-LOF"
    ::= { hwAtmApsVPGConfigEntry  14 }              

    hwAtmApsVPGProtectionEntityStatus     OBJECT-TYPE
        SYNTAX                      BITS
                                    {
                                        lof(1),
                                        los(2),
                                        sd(3),
                                        rdi(4),
                                        ais(5),
                                        rsd(6)
                                    }        
        MAX-ACCESS                  read-only
        STATUS                      current
        DESCRIPTION                 "
                                     0x00000002-RSD
                                     0x00000004-AIS,
                                     0x00000008-RDI,
                                     0x00000010-SD,
                                     0x00000020-LOS,
                                     0x00000040-LOF"
    ::= { hwAtmApsVPGConfigEntry  15 }         

    hwAtmApsVPGCurrEntity           OBJECT-TYPE
        SYNTAX                      INTEGER
                                    {
                                        work(1),
                                        protect(2)
                                    }
        MAX-ACCESS                  read-only
        STATUS                      current
        DESCRIPTION                 ""
    ::= { hwAtmApsVPGConfigEntry  16 }         

    hwAtmApsVPGApsStatus            OBJECT-TYPE
        SYNTAX                      INTEGER
        MAX-ACCESS                  read-only
        STATUS                      current
        DESCRIPTION                 "
                                        Bidirectional APSC:
                                        0x00000080-DNR,
                                        0x00000100-rsv1,
                                        0x00000200-WTR,
                                        0x00000400-rsv2,
                                        0x00000800-MS-W,
                                        0x00001000-MS-P,
                                        0x00002000-rsv3,
                                        0x00004000-SD-W,
                                        0x00008000-SD-P,
                                        0x00010000-rsv4,
                                        0x00020000-SF-W,
                                        0x00040000-rsv5,
                                        0x00080000-FS-W,
                                        0x00100000-SF-P,
                                        0x00200000-LOP,
                                        0x00400000-FREEZE,
                                        0x00800000-CLEAR,
                                        Unidirectional APSC:
                                        0x01000000-WTR,
                                        0x02000000-MS_P,
                                        0x04000000-MS_W,
                                        0x08000000-SD,
                                        0x10000000-SF,
                                        0x20000000-FS,
                                        0x40000000-LOP,
                                        0x80000000-CLEAR "
    ::= { hwAtmApsVPGConfigEntry  17 }    
    
    hwAtmApsVPGVplIsInUse           OBJECT-TYPE
        SYNTAX                      TruthValue
        MAX-ACCESS                  read-write
        STATUS                      current
        DESCRIPTION                 "
                                         enable(1),
                                         disable(2)"
    ::= { hwAtmApsVPGConfigEntry  18 }         

    hwAtmApsVPGVpRingIndex          OBJECT-TYPE
        SYNTAX                      INTEGER(0..15)
        MAX-ACCESS                  read-only
        STATUS                      current
        DESCRIPTION                 "
        			    "
    ::= { hwAtmApsVPGConfigEntry  19 }         

    hwAtmApsVPGRevertive            OBJECT-TYPE
        SYNTAX                      TruthValue
        MAX-ACCESS                  read-write
        STATUS                      current
        DESCRIPTION                 "
                                     revertible(1),
                                     non-revertible(2)"
    ::= { hwAtmApsVPGConfigEntry  20 }         

    hwAtmApsVPGRowStatus            OBJECT-TYPE
        SYNTAX                      RowStatus
        MAX-ACCESS                  read-write
        STATUS                      current
        DESCRIPTION                 "
        			    "
    ::= { hwAtmApsVPGConfigEntry  21 }         


    -- ----------------------
    --  hwAtmApsVPGVplTable
    -- ----------------------
    hwAtmApsVPGVplTable             OBJECT-TYPE
        SYNTAX                      SEQUENCE OF HwAtmApsVPGVplEntry
        MAX-ACCESS                  not-accessible
        STATUS                      current
        DESCRIPTION                 "
        			    "
    ::= { hwMD5500ApsService 3 }
        
    hwAtmApsVPGVplEntry             OBJECT-TYPE 
        SYNTAX                      HwAtmApsVPGVplEntry
        MAX-ACCESS                  not-accessible
        STATUS                      current
        DESCRIPTION                 "
         			    "
        INDEX                       {
                                        hwAtmApsVPGIndex,
                                        hwAtmApsVPGVplWorkingVpi
                                    } 
        ::={ hwAtmApsVPGVplTable 1 } 

    HwAtmApsVPGVplEntry ::= SEQUENCE
    {
        hwAtmApsVPGVplWorkingVpi              INTEGER,
        hwAtmApsVPGVplProtectionVpi           INTEGER,
        hwAtmApsVPGVplServiceClass            INTEGER,
        hwAtmApsVPGVplRowStaus                RowStatus,
        hwAtmApsVPGVplTrafficTableIndex       INTEGER
    }
    
    hwAtmApsVPGVplWorkingVpi        OBJECT-TYPE
        SYNTAX                      INTEGER(1..255)
        MAX-ACCESS                  not-accessible
        STATUS                      current
        DESCRIPTION                 "
        			    "
    ::= { hwAtmApsVPGVplEntry  1 }         
    
    hwAtmApsVPGVplProtectionVpi     OBJECT-TYPE
        SYNTAX                      INTEGER(1..255)
        MAX-ACCESS                  read-write
        STATUS                      current
        DESCRIPTION                 "
        			    "
    ::= { hwAtmApsVPGVplEntry  2 }         
    
    hwAtmApsVPGVplServiceClass      OBJECT-TYPE
        SYNTAX                      INTEGER
                                    {
                                        cbr(1),
                                        rtvbr(2),
                                        nrtvbr(3),
                                        abr(4),
                                        ubr(5)
                                    }
        MAX-ACCESS                  read-only
        STATUS                      deprecated
        DESCRIPTION                 "
        			    "
    ::= { hwAtmApsVPGVplEntry  3 }         
    
    hwAtmApsVPGVplRowStaus          OBJECT-TYPE
        SYNTAX                      RowStatus
        MAX-ACCESS                  read-write
        STATUS                      current
        DESCRIPTION                 "
        			    "
    ::= { hwAtmApsVPGVplEntry  4 }         
    
    hwAtmApsVPGVplTrafficTableIndex OBJECT-TYPE
			SYNTAX INTEGER (0..511)
			MAX-ACCESS read-create
			STATUS current
			DESCRIPTION
				"
				"
			::= { hwAtmApsVPGVplEntry 5 }

    -- ----------------------
    --  hwAtmApsAPSChannelTable
    -- ----------------------
    hwAtmApsAPSChannelTable         OBJECT-TYPE
        SYNTAX                      SEQUENCE OF HwAtmApsAPSChannelEntry
        MAX-ACCESS                  not-accessible
        STATUS                      current
        DESCRIPTION                 "
         			    "
    ::= { hwMD5500ApsService 4 }

    hwAtmApsAPSChannelEntry         OBJECT-TYPE 
        SYNTAX                      HwAtmApsAPSChannelEntry
        MAX-ACCESS                  not-accessible
        STATUS                      current
        DESCRIPTION                 "
        			    "
        INDEX                       {
                                        hwAtmApsAPSChannelFrameID,
                                        hwAtmApsAPSChannelSlotID,
                                        hwAtmApsAPSChannelPhyport,
                                        hwAtmApsAPSChannelVpi
                                    } 
        ::={ hwAtmApsAPSChannelTable 1 }           

    HwAtmApsAPSChannelEntry ::= SEQUENCE
    {
        hwAtmApsAPSChannelFrameID             INTEGER,
        hwAtmApsAPSChannelSlotID              INTEGER,
        hwAtmApsAPSChannelPhyport             INTEGER,
        hwAtmApsAPSChannelVpi                 INTEGER,
        hwAtmApsAPSChannelGroupIndex          INTEGER,
        hwAtmApsAPSChannelVlType              INTEGER,
        hwAtmApsAPSChannelRowStaus            RowStatus
    }

    hwAtmApsAPSChannelFrameID       OBJECT-TYPE
        SYNTAX                      INTEGER(0..63)
        MAX-ACCESS                  not-accessible
        STATUS                      current
        DESCRIPTION                 "
        			    "
    ::= { hwAtmApsAPSChannelEntry  1 }         

    hwAtmApsAPSChannelSlotID        OBJECT-TYPE
        SYNTAX                      INTEGER(0..63)
        MAX-ACCESS                  not-accessible
        STATUS                      current
        DESCRIPTION                 "
        			    "
    ::= { hwAtmApsAPSChannelEntry  2 }         
        
    hwAtmApsAPSChannelPhyport       OBJECT-TYPE
        SYNTAX                      INTEGER(0..63)
        MAX-ACCESS                  not-accessible
        STATUS                      current
        DESCRIPTION                 "
        			    "
    ::= { hwAtmApsAPSChannelEntry  3 }         

    hwAtmApsAPSChannelVpi           OBJECT-TYPE
        SYNTAX                      INTEGER(1..255)
        MAX-ACCESS                  not-accessible
        STATUS                      current
        DESCRIPTION                 "
        			    "
    ::= { hwAtmApsAPSChannelEntry  4 }         

    hwAtmApsAPSChannelGroupIndex    OBJECT-TYPE
        SYNTAX                      INTEGER(1..256)
        MAX-ACCESS                  read-write
        STATUS                      current
        DESCRIPTION                 ""
    ::= { hwAtmApsAPSChannelEntry  5 }         

    hwAtmApsAPSChannelVlType        OBJECT-TYPE
        SYNTAX                      INTEGER
                                    {
                                        p2p(1),
                                        w-leaf(2),
                                        p-leaf(3)
                                    }
        MAX-ACCESS                  read-write
        STATUS                      current
        DESCRIPTION                 ""
    ::= { hwAtmApsAPSChannelEntry  6 }         

    hwAtmApsAPSChannelRowStaus      OBJECT-TYPE
        SYNTAX                      RowStatus
        MAX-ACCESS                  read-write
        STATUS                      current
        DESCRIPTION                 "
        			    "
    ::= { hwAtmApsAPSChannelEntry  7 }         



hwMD5500V5IfManage  OBJECT IDENTIFIER ::={ hwMD5500ServiceAdminMIB 9 }

-- V5InterfaceConfigTable


 hwV5InterfaceConfigTable     OBJECT-TYPE
        SYNTAX         SEQUENCE OF HwV5InterfaceConfigEntry
        MAX-ACCESS     not-accessible
        STATUS         current
    DESCRIPTION
           "The table lists the V5 groups that have been
            configured on the system."
    ::= { hwMD5500V5IfManage 1 }

    hwV5InterfaceConfigEntry         OBJECT-TYPE
       SYNTAX         HwV5InterfaceConfigEntry
       MAX-ACCESS     not-accessible
       STATUS         current
       DESCRIPTION    ""
          INDEX    { hwV5cfgV5InterfaceID }
    ::= { hwV5InterfaceConfigTable  1 }

     HwV5InterfaceConfigEntry ::= SEQUENCE 
     {
        hwV5cfgV5InterfaceID                    INTEGER,
	hwV5cfgUpperV5InterfaceID               INTEGER,
	hwV5cfgV5InterfaceType                  INTEGER,
	hwV5cfgV5InterfaceVersion               INTEGER,
	hwV5cfgPSTNlogicCID                     INTEGER, 
	hwV5cfgV5Variable                       INTEGER,
	hwV5cfgLinkIDIdentify0                  TruthValue,
	hwV5cfgLinkIDIdentify1                  TruthValue,
	hwV5cfgLinkIDIdentify2                  TruthValue,
	hwV5cfgLinkIDIdentify3                  TruthValue,
	hwV5cfgRowStatus                        RowStatus,
	hwV5UsableTs			 			    INTEGER,
	hwV5PhoneUsableTs	    			    INTEGER,
	hwV5PstnUser		    			    INTEGER,
	hwV5IsdnUser		    			    INTEGER,
	hwV5cfgV5InterfaceDesc                  OCTET STRING
     }
     
    hwV5cfgV5InterfaceID         OBJECT-TYPE
        SYNTAX      INTEGER(0..16777215)
        MAX-ACCESS  not-accessible
        STATUS      current
        DESCRIPTION
         " "
    ::= { hwV5InterfaceConfigEntry 1 }
     
    hwV5cfgUpperV5InterfaceID       OBJECT-TYPE
        SYNTAX      INTEGER(0..16777215)
        MAX-ACCESS  read-write
        STATUS      current
        DESCRIPTION
         " "
    ::= { hwV5InterfaceConfigEntry 2 }

    hwV5cfgV5InterfaceType       OBJECT-TYPE
        SYNTAX      INTEGER{
                            an(1),
                            le(2)
                           } 
        MAX-ACCESS  read-write
        STATUS      current
        DESCRIPTION
         " "
    ::= { hwV5InterfaceConfigEntry 3 }

    hwV5cfgV5InterfaceVersion       OBJECT-TYPE
        SYNTAX      INTEGER{
                             v51(1),
                             v52(2)
                           }  
        MAX-ACCESS  read-write
        STATUS      current
        DESCRIPTION
         " "
    ::= { hwV5InterfaceConfigEntry 4 }

    hwV5cfgPSTNlogicCID       OBJECT-TYPE
        SYNTAX      INTEGER(0..65535)
        MAX-ACCESS  read-write
        STATUS      current
        DESCRIPTION
         " "
    ::= { hwV5InterfaceConfigEntry 5 }

    hwV5cfgV5Variable       OBJECT-TYPE
        SYNTAX      INTEGER(0..127)
        MAX-ACCESS  read-write
        STATUS      current
        DESCRIPTION
         " "
    ::= { hwV5InterfaceConfigEntry 6 }

    hwV5cfgLinkIDIdentify0       OBJECT-TYPE
        SYNTAX      TruthValue
        MAX-ACCESS  read-write
        STATUS      current
        DESCRIPTION
         " "
    ::= { hwV5InterfaceConfigEntry 7 }

    hwV5cfgLinkIDIdentify1       OBJECT-TYPE
        SYNTAX      TruthValue
        MAX-ACCESS  read-write
        STATUS      current
        DESCRIPTION
         " "
    ::= { hwV5InterfaceConfigEntry 8 }

    hwV5cfgLinkIDIdentify2       OBJECT-TYPE
        SYNTAX   TruthValue
        MAX-ACCESS  read-write
        STATUS      current
        DESCRIPTION
         " "
    ::= { hwV5InterfaceConfigEntry 9 }

    hwV5cfgLinkIDIdentify3       OBJECT-TYPE
        SYNTAX      TruthValue
        MAX-ACCESS  read-write
        STATUS      current
        DESCRIPTION
         " "
    ::= { hwV5InterfaceConfigEntry 10 }

    hwV5cfgRowStatus       OBJECT-TYPE
         SYNTAX                 RowStatus                      
                         
        MAX-ACCESS  read-write
        STATUS      current
        DESCRIPTION
         " "
    ::= { hwV5InterfaceConfigEntry 11 }
    
    hwV5UsableTs  OBJECT-TYPE
   		SYNTAX INTEGER
   		MAX-ACCESS read-only
   		STATUS current
		DESCRIPTION
			" "
		::= { hwV5InterfaceConfigEntry 12 }
			
    hwV5PhoneUsableTs   OBJECT-TYPE
   		SYNTAX INTEGER
   		MAX-ACCESS read-only
   		STATUS current
		DESCRIPTION
			" "
		::= { hwV5InterfaceConfigEntry 13 }

    hwV5PstnUser   OBJECT-TYPE
   		SYNTAX INTEGER
   		MAX-ACCESS read-only
   		STATUS current
		DESCRIPTION
			" "
		::= { hwV5InterfaceConfigEntry 14 }

    hwV5IsdnUser   OBJECT-TYPE
   		SYNTAX INTEGER
   		MAX-ACCESS read-only
   		STATUS current
		DESCRIPTION
			" "
		::= { hwV5InterfaceConfigEntry 15 }

    hwV5cfgV5InterfaceDesc   OBJECT-TYPE
   		SYNTAX OCTET STRING	(SIZE (0..32))
   		MAX-ACCESS read-write
   		STATUS current
		DESCRIPTION
			"description of v5 interface
			      "
		::= { hwV5InterfaceConfigEntry 16 }  
      
  --    v5InterfaceLinkConfigTable
    
    
     hwV5InterfaceLinkConfigTable     OBJECT-TYPE
        SYNTAX         SEQUENCE OF HwV5InterfaceLinkConfigEntry
        MAX-ACCESS     not-accessible
        STATUS         current
    DESCRIPTION
           "The table lists the V5 groups that have been
            configured on the system."
    ::= { hwMD5500V5IfManage 2 }

    hwV5InterfaceLinkConfigEntry         OBJECT-TYPE
       SYNTAX         HwV5InterfaceLinkConfigEntry
       MAX-ACCESS     not-accessible
       STATUS         current
       DESCRIPTION    ""
          INDEX    { hwV5cfgV5InterfaceID,
                     hwV5FrameID,
                     hwV5SlotID,
                     hwV5PortID
                   }
    ::= { hwV5InterfaceLinkConfigTable  1 }

     HwV5InterfaceLinkConfigEntry ::= SEQUENCE 
     {
	hwV5FrameID                             INTEGER,            	
        hwV5SlotID                              INTEGER,
	hwV5PortID                              INTEGER, 
	hwV5LinkID                              INTEGER,
	hwV5RowStatus                           RowStatus
     }
     
    hwV5FrameID         OBJECT-TYPE
        SYNTAX      INTEGER(0..63)
        MAX-ACCESS  not-accessible
        STATUS      current
        DESCRIPTION
         " "
    ::= { hwV5InterfaceLinkConfigEntry 1 }

    hwV5SlotID         OBJECT-TYPE
        SYNTAX      INTEGER(0..63)
        MAX-ACCESS  not-accessible
        STATUS      current
        DESCRIPTION
         " "
    ::= { hwV5InterfaceLinkConfigEntry 2 }

    hwV5PortID         OBJECT-TYPE
        SYNTAX      INTEGER(0..63)
        MAX-ACCESS  not-accessible
        STATUS      current
        DESCRIPTION
         " "
    ::= { hwV5InterfaceLinkConfigEntry 3 }

    hwV5LinkID         OBJECT-TYPE
        SYNTAX      INTEGER(0..255)
        MAX-ACCESS  read-write
        STATUS      current
        DESCRIPTION
         " "
    ::= { hwV5InterfaceLinkConfigEntry 4 }

    hwV5RowStatus         OBJECT-TYPE
        SYNTAX                 RowStatus
        MAX-ACCESS  read-write
        STATUS      current
        DESCRIPTION
         " "
    ::= { hwV5InterfaceLinkConfigEntry 5 }
    
    
 
  --   V5CChannelConfigManage 
    hwV5CChannelConfigManage  OBJECT IDENTIFIER ::={ hwMD5500V5IfManage 3  }

  --    v5channelNextAllocPhyNo
    hwV5channelNextAllocPhyCNo    OBJECT-TYPE
        SYNTAX      INTEGER(0..255)
        MAX-ACCESS  read-only
        STATUS      current
    DESCRIPTION
         " "
    ::= { hwV5CChannelConfigManage 1 }

 --   V5CChannelConfigTable
    hwV5CChannelConfigTable     OBJECT-TYPE
        SYNTAX         SEQUENCE OF HwV5CChannelConfigEntry
        MAX-ACCESS     not-accessible
        STATUS         current
    DESCRIPTION
           "The table lists the V5 groups that have been
            configured on the system."
    ::= { hwV5CChannelConfigManage 2 }

    hwV5CChannelConfigEntry         OBJECT-TYPE
       SYNTAX         HwV5CChannelConfigEntry
       MAX-ACCESS     not-accessible
       STATUS         current
       DESCRIPTION    ""
          INDEX    { hwV5cfgV5InterfaceID,
                     hwV5channelPhyCNo
                   }
    ::= { hwV5CChannelConfigTable  1 }

     HwV5CChannelConfigEntry ::= SEQUENCE 
     {
	hwV5channelPhyCNo                              INTEGER,   
	hwV5channelFrameID         	            INTEGER,
        hwV5channelSlotID                              INTEGER,
	hwV5channelPortID                              INTEGER, 
	hwV5channelTsNo                                INTEGER,
	hwV5channelProtectType                         INTEGER,
	hwV5channelLogicCChannelID                     INTEGER,
	hwV5channelRowStatus                           RowStatus
     }
     
    hwV5channelPhyCNo         OBJECT-TYPE
        SYNTAX      INTEGER(0..255)
        MAX-ACCESS  not-accessible
        STATUS      current
        DESCRIPTION
         " "
    ::= { hwV5CChannelConfigEntry 1 }

    hwV5channelFrameID         OBJECT-TYPE
        SYNTAX      INTEGER(0..63)
        MAX-ACCESS  read-write
        STATUS      current
        DESCRIPTION
         " "
    ::= { hwV5CChannelConfigEntry 2 }

    hwV5channelSlotID         OBJECT-TYPE
        SYNTAX      INTEGER(0..63)
        MAX-ACCESS  read-write
        STATUS      current
        DESCRIPTION
         " "
    ::= { hwV5CChannelConfigEntry 3 }

    hwV5channelPortID         OBJECT-TYPE
        SYNTAX      INTEGER(0..63)
        MAX-ACCESS  read-write
        STATUS      current
        DESCRIPTION
         " "
    ::= { hwV5CChannelConfigEntry 4 }

    hwV5channelTsNo         OBJECT-TYPE
        SYNTAX      INTEGER{
                             t15(1),
                             t16(2),
                             t31(3)
                           }  
        MAX-ACCESS  read-write
        STATUS      current
        DESCRIPTION
         " "
    ::= { hwV5CChannelConfigEntry 5 }


    hwV5channelProtectType         OBJECT-TYPE
        SYNTAX      INTEGER{
                             p1master(1),
                             p1slaver(2),
                             p2master(3),
                             p2slaver(4)
                           }  
        MAX-ACCESS  read-write
        STATUS      current
        DESCRIPTION
         " "
    ::= { hwV5CChannelConfigEntry 6 }

    hwV5channelLogicCChannelID         OBJECT-TYPE
        SYNTAX      INTEGER(0..65535)
        MAX-ACCESS  read-write
        STATUS      current
        DESCRIPTION
         " "
    ::= { hwV5CChannelConfigEntry 7 }

    hwV5channelRowStatus         OBJECT-TYPE
       SYNTAX                RowStatus
        MAX-ACCESS  read-write
        STATUS      current
        DESCRIPTION
         " "
    ::= { hwV5CChannelConfigEntry 8 }
    
     
  --   V5ProtSwitchOprTable
  
    hwV5ProtSwitchOprTable     OBJECT-TYPE
        SYNTAX         SEQUENCE OF HwV5ProtSwitchOprEntry
        MAX-ACCESS     not-accessible
        STATUS         current
    DESCRIPTION
           "The table lists the V5 groups that have been
            configured on the system."
    ::= { hwMD5500V5IfManage 4 }

    hwV5ProtSwitchOprEntry         OBJECT-TYPE
       SYNTAX         HwV5ProtSwitchOprEntry
       MAX-ACCESS     not-accessible
       STATUS         current
       DESCRIPTION    ""
          INDEX    { 
                     hwV5cfgV5InterfaceID,
                     hwV5SwitchLogicCchannelID
                   }
    ::= { hwV5ProtSwitchOprTable  1 }

     HwV5ProtSwitchOprEntry ::= SEQUENCE 
     {
    hwV5SwitchLogicCchannelID                     INTEGER,
	hwV5SwitchPhyCLinkID                          INTEGER, 
	hwV5SwitchPhyCTsNo                            INTEGER,
	hwV5SwitchSwitchover                          INTEGER
     }
     
    hwV5SwitchLogicCchannelID         OBJECT-TYPE
        SYNTAX      INTEGER(0..65535)
        MAX-ACCESS  not-accessible
        STATUS      current
        DESCRIPTION
         " "
    ::= { hwV5ProtSwitchOprEntry 1 }

    hwV5SwitchPhyCLinkID         OBJECT-TYPE
        SYNTAX      INTEGER(0..255)
        MAX-ACCESS  read-write
        STATUS      current
        DESCRIPTION
         " "
    ::= { hwV5ProtSwitchOprEntry 2 }

    hwV5SwitchPhyCTsNo         OBJECT-TYPE
        SYNTAX      INTEGER{
                             t15(1),
                             t16(2),
                             t31(3)
                           }  
        MAX-ACCESS  read-write
        STATUS      current
        DESCRIPTION
         " "
    ::= { hwV5ProtSwitchOprEntry 3 }

    hwV5SwitchSwitchover         OBJECT-TYPE
        SYNTAX      INTEGER{
                             yes(1)
                           }  
        MAX-ACCESS  read-write
        STATUS      current
        DESCRIPTION
         " "
    ::= { hwV5ProtSwitchOprEntry 4 }
    
    
   --  V5InterfaceTable 
   
   
    hwV5InterfaceTable     OBJECT-TYPE
        SYNTAX         SEQUENCE OF HwV5InterfaceEntry
        MAX-ACCESS     not-accessible
        STATUS         current
    DESCRIPTION
           "The table lists the V5 groups that have been
            configured on the system."
    ::= { hwMD5500V5IfManage 5 }

    hwV5InterfaceEntry         OBJECT-TYPE
       SYNTAX         HwV5InterfaceEntry
       MAX-ACCESS     not-accessible
       STATUS         current
       DESCRIPTION    ""
          INDEX    { 
                     hwV5cfgV5InterfaceID
                   }
    ::= { hwV5InterfaceTable  1 }

     HwV5InterfaceEntry ::= SEQUENCE 
     {
	hwV5IfInterfaceType                     INTEGER,            	
    hwV5IfcurrentVarIdx                     INTEGER,
	hwV5IfPrimaryLinkid                     INTEGER, 
	hwV5IfSecondaryLinkid                   INTEGER,
	hwV5IfLinkNum                           INTEGER,  
	hwV5IfLinkIDIdentify0                   TruthValue,
	hwV5IfLinkIDIdentify1                   TruthValue,
	hwV5IfLinkIDIdentify2                   TruthValue,
	hwV5IfLinkIDIdentify3                   TruthValue,
	hwV5IfInterfacestate                    INTEGER,
	hwV5IfPstnDataLinkState                 INTEGER,
	hwV5IfBccDataLinkState                  INTEGER,
	hwV5IfCtrlDataLinkState                 INTEGER,
	hwV5IfProtectDataLink1State             INTEGER,
	hwV5IfProtectDataLink2state             INTEGER, 
	hwV5IfLinkCtrlDataLinkState             INTEGER,
	hwV5IfOprtype                           INTEGER,	
	hwV5IfOprResult                         INTEGER
     }
     
    hwV5IfInterfaceType         OBJECT-TYPE
        SYNTAX      INTEGER{
                            an(1),
                            le(2)
                           } 
        MAX-ACCESS  read-only
        STATUS      current
        DESCRIPTION
         " "
    ::= { hwV5InterfaceEntry 1 }

    hwV5IfcurrentVarIdx         OBJECT-TYPE
        SYNTAX      INTEGER(0..127) 
        MAX-ACCESS  read-only
        STATUS      current
        DESCRIPTION
         " "
    ::= { hwV5InterfaceEntry 2 }

    hwV5IfPrimaryLinkid         OBJECT-TYPE
        SYNTAX      INTEGER(0..255) 
        MAX-ACCESS  read-only
        STATUS      current
        DESCRIPTION
         " "
    ::= { hwV5InterfaceEntry 3 }

    hwV5IfSecondaryLinkid         OBJECT-TYPE
        SYNTAX      INTEGER(0..255) 
        MAX-ACCESS  read-only
        STATUS      current
        DESCRIPTION
         " "
    ::= { hwV5InterfaceEntry 4 }

    hwV5IfLinkNum         OBJECT-TYPE
        SYNTAX      INTEGER(0..16) 
        MAX-ACCESS  read-only
        STATUS      current
        DESCRIPTION
         " "
    ::= { hwV5InterfaceEntry 5 }

    hwV5IfLinkIDIdentify0         OBJECT-TYPE
        SYNTAX       TruthValue 
        MAX-ACCESS  read-only
        STATUS      current
        DESCRIPTION
         " "
    ::= { hwV5InterfaceEntry 6 }

    hwV5IfLinkIDIdentify1         OBJECT-TYPE
        SYNTAX     TruthValue
        MAX-ACCESS  read-only
        STATUS      current
        DESCRIPTION
         " "
    ::= { hwV5InterfaceEntry 7 }

    hwV5IfLinkIDIdentify2         OBJECT-TYPE  
        SYNTAX   TruthValue 
        MAX-ACCESS read-only
        STATUS      current
        DESCRIPTION
         " "
    ::= { hwV5InterfaceEntry 8 }

    hwV5IfLinkIDIdentify3         OBJECT-TYPE
        SYNTAX      TruthValue
        MAX-ACCESS  read-only
        STATUS      current
        DESCRIPTION
         " "
    ::= { hwV5InterfaceEntry 9 }

    hwV5IfInterfacestate         OBJECT-TYPE
        SYNTAX      INTEGER{
                             nostartif(1),
                             iffree(2)   ,
                             wait2buildlink(3),
                             reqifvar(4),      
                             reqlinkid(5),
                             waitrestart(6),
                             ifnormal(7),
                             ifclose(8)
                           }  
        MAX-ACCESS  read-only
        STATUS      current
        DESCRIPTION
         " "
    ::= { hwV5InterfaceEntry 10 }

    hwV5IfPstnDataLinkState         OBJECT-TYPE
        SYNTAX      INTEGER{
                             linknormal(1),
                             linkwaitbuild(2),
                             linknouse(3), 
                             linknocfg(4)
                           }  
        MAX-ACCESS  read-only
        STATUS      current
        DESCRIPTION
         " "
    ::= { hwV5InterfaceEntry 11 }

    hwV5IfBccDataLinkState         OBJECT-TYPE
        SYNTAX      INTEGER{
                             linknormal(1),
                             linkwaitbuild(2),
                             linknouse(3),  
                             linknocfg(4)
                           }  
        MAX-ACCESS  read-only
        STATUS      current
        DESCRIPTION
         " "
    ::= { hwV5InterfaceEntry 12 }

    hwV5IfCtrlDataLinkState         OBJECT-TYPE
        SYNTAX      INTEGER{
                             linknormal(1),
                             linkwaitbuild(2),
                             linknouse(3),  
                             linknocfg(4)
                           }  
        MAX-ACCESS  read-only
        STATUS      current
        DESCRIPTION
         " "
    ::= { hwV5InterfaceEntry 13 }

    hwV5IfProtectDataLink1State         OBJECT-TYPE
        SYNTAX      INTEGER{
                             linknormal(1),
                             linkwaitbuild(2),
                             linknouse(3), 
                             linknocfg(4)
                           }  
        MAX-ACCESS  read-only
        STATUS      current
        DESCRIPTION
         " "
    ::= { hwV5InterfaceEntry 14 }

    hwV5IfProtectDataLink2state         OBJECT-TYPE
        SYNTAX      INTEGER{
                             linknormal(1),
                             linkwaitbuild(2),
                             linknouse(3), 
                            linknocfg(4)
                           }  
        MAX-ACCESS  read-only
        STATUS      current
        DESCRIPTION
         " "
    ::= { hwV5InterfaceEntry 15 }

    hwV5IfLinkCtrlDataLinkState         OBJECT-TYPE
        SYNTAX      INTEGER{
                             linknormal(1),
                             linkwaitbuild(2),
                             linknouse(3),  
                             linknocfg(4)
                           }  
        MAX-ACCESS  read-only
        STATUS      current
        DESCRIPTION
         " "
    ::= { hwV5InterfaceEntry 16 }


    hwV5IfOprtype         OBJECT-TYPE
        SYNTAX      INTEGER{
                             reset(1),
                             restart(2),
                             close(3)
                           }  
        MAX-ACCESS read-write
        STATUS      current
        DESCRIPTION
         " "
    ::= { hwV5InterfaceEntry 18 }
    
    hwV5IfOprResult         OBJECT-TYPE
        SYNTAX      INTEGER{
                               success(1),
                               failure(2)
                               }
                            
        MAX-ACCESS     read-only
        STATUS      current
        DESCRIPTION
         " "
    ::= { hwV5InterfaceEntry 19 }
    
  --   V5LogicCChannelTable


hwV5LogicCChannelTable     OBJECT-TYPE
        SYNTAX         SEQUENCE OF HwV5LogicCChannelEntry
        MAX-ACCESS     not-accessible
        STATUS         current
    DESCRIPTION
           "The table lists the V5 groups that have been
            configured on the system."
    ::= { hwMD5500V5IfManage 6 }

    hwV5LogicCChannelEntry         OBJECT-TYPE
       SYNTAX         HwV5LogicCChannelEntry
       MAX-ACCESS     not-accessible
       STATUS         current
       DESCRIPTION    ""
          INDEX    { 
                     hwV5cfgV5InterfaceID,
                     hwV5LCChannelLogicCID
                   }
    ::= { hwV5LogicCChannelTable  1 }

     HwV5LogicCChannelEntry ::= SEQUENCE 
     {
	hwV5LCChannelLogicCID                     INTEGER, 
	hwV5LCChanneLogicCLinkID           	INTEGER,
        hwV5LCChannelFrameID                      INTEGER,
	hwV5LCChannelSlotID                       INTEGER, 
	hwV5LCChannelPortID                       INTEGER,
	hwV5LCChannelTsNo                         INTEGER,  
	hwV5LCChannelProtectGroup                 INTEGER,
	hwV5LCChannelPSTNProtocolBear             TruthValue,
	hwV5LCChannelCTRLProtocolBear             TruthValue,
	hwV5LCChannelBCCProtocolBear              TruthValue,
	hwV5LCChannelPROTProtocolBear             TruthValue,
	hwV5LCChannelLCTRLProtocolBear            TruthValue,
	hwV5LCChannelISDNDsProtocolBear           TruthValue,
	hwV5LCChannelISDNpProtocolBear            TruthValue, 
	hwV5LCChannelISDNfProtocolBear            TruthValue
     }
     
    hwV5LCChannelLogicCID         OBJECT-TYPE
        SYNTAX      INTEGER(0..65535) 
        MAX-ACCESS  not-accessible
        STATUS      current
        DESCRIPTION
         " "
    ::= { hwV5LogicCChannelEntry 1 }

    hwV5LCChanneLogicCLinkID         OBJECT-TYPE
        SYNTAX      INTEGER(0..255) 
        MAX-ACCESS  read-only
        STATUS      current
        DESCRIPTION
         " "
    ::= { hwV5LogicCChannelEntry 2 }

    hwV5LCChannelFrameID         OBJECT-TYPE
        SYNTAX      INTEGER(0..63) 
        MAX-ACCESS  read-only
        STATUS      current
        DESCRIPTION
         " "
    ::= { hwV5LogicCChannelEntry 3 }

    hwV5LCChannelSlotID         OBJECT-TYPE
        SYNTAX      INTEGER(0..63) 
        MAX-ACCESS  read-only
        STATUS      current
        DESCRIPTION
         " "
    ::= { hwV5LogicCChannelEntry 4 }

    hwV5LCChannelPortID         OBJECT-TYPE
        SYNTAX      INTEGER(0..63) 
        MAX-ACCESS  read-only
        STATUS      current
        DESCRIPTION
         " "
    ::= { hwV5LogicCChannelEntry 5 }

    hwV5LCChannelTsNo         OBJECT-TYPE
        SYNTAX      INTEGER{
                             t15(1),
                             t16(2),
                             t31(3)
                           }   
        MAX-ACCESS  read-only
        STATUS      current
        DESCRIPTION
         " "
    ::= { hwV5LogicCChannelEntry 6 }

    hwV5LCChannelProtectGroup         OBJECT-TYPE
        SYNTAX      INTEGER{
                             pm(1),
                             ps(2),
                             p2m(3),
                             p2s(4)
                           }   
        MAX-ACCESS  read-only
        STATUS      current
        DESCRIPTION
         " "
    ::= { hwV5LogicCChannelEntry 7 }

    hwV5LCChannelPSTNProtocolBear         OBJECT-TYPE
        SYNTAX      TruthValue   
        MAX-ACCESS  read-only
        STATUS      current
        DESCRIPTION
         " "
    ::= { hwV5LogicCChannelEntry 8 }

    hwV5LCChannelCTRLProtocolBear         OBJECT-TYPE
        SYNTAX     TruthValue
        MAX-ACCESS  read-only
        STATUS      current
        DESCRIPTION
         " "
    ::= { hwV5LogicCChannelEntry 9 }

    hwV5LCChannelBCCProtocolBear         OBJECT-TYPE
        SYNTAX      TruthValue
        MAX-ACCESS  read-only
        STATUS      current
        DESCRIPTION
         " "
    ::= { hwV5LogicCChannelEntry 10 }

    hwV5LCChannelPROTProtocolBear         OBJECT-TYPE
        SYNTAX     TruthValue
        MAX-ACCESS  read-only
        STATUS      current
        DESCRIPTION
         " "
    ::= { hwV5LogicCChannelEntry 11 }

    hwV5LCChannelLCTRLProtocolBear         OBJECT-TYPE
        SYNTAX      TruthValue
        MAX-ACCESS  read-only
        STATUS      current
        DESCRIPTION
         " "
    ::= { hwV5LogicCChannelEntry 12 }

    hwV5LCChannelISDNDsProtocolBear         OBJECT-TYPE
        SYNTAX    TruthValue
        MAX-ACCESS  read-only
        STATUS      current
        DESCRIPTION
         " "
    ::= { hwV5LogicCChannelEntry 13 }

    hwV5LCChannelISDNpProtocolBear         OBJECT-TYPE
        SYNTAX     TruthValue
        MAX-ACCESS  read-only
        STATUS      current
        DESCRIPTION
         " "
    ::= { hwV5LogicCChannelEntry 14 }

    hwV5LCChannelISDNfProtocolBear         OBJECT-TYPE
        SYNTAX     TruthValue
        MAX-ACCESS  read-only
        STATUS      current
        DESCRIPTION
         " "
    ::= { hwV5LogicCChannelEntry 15 }
    
    
--     V5StandbyPhyCChannelTable

hwV5StandbyPhyCChannelTable     OBJECT-TYPE
        SYNTAX         SEQUENCE OF HwV5StandbyPhyCChannelEntry
        MAX-ACCESS     not-accessible
        STATUS         current
    DESCRIPTION
           "The table lists the V5 groups that have been
            configured on the system."
    ::= { hwMD5500V5IfManage 7 }

    hwV5StandbyPhyCChannelEntry         OBJECT-TYPE
       SYNTAX         HwV5StandbyPhyCChannelEntry
       MAX-ACCESS     not-accessible
       STATUS         current
       DESCRIPTION    ""
          INDEX    { 
                     hwV5cfgV5InterfaceID,
                     hwV5StandbyPhyLogicStdPhyCNo
                   }
    ::= { hwV5StandbyPhyCChannelTable  1 }

     HwV5StandbyPhyCChannelEntry ::= SEQUENCE 
     {
	hwV5StandbyPhyLogicStdPhyCNo               INTEGER,           	     
	hwV5StandbyPhyPhyCLinkID                   INTEGER, 
        hwV5StandbyPhyFrameID                      INTEGER,
	hwV5StandbyPhySlotID                       INTEGER, 
	hwV5StandbyPhyPortID                       INTEGER,
	hwV5StandbyPhyTsNo                         INTEGER,  
	hwV5StandbyPhyPhyCProtectGroup             INTEGER
     }

    hwV5StandbyPhyLogicStdPhyCNo         OBJECT-TYPE
        SYNTAX      INTEGER {
                             protectgroup1(1),
                             protectgroup2(2),
                             protectgroup3(3),
                             protectgroup4(4)
                             }
        MAX-ACCESS  not-accessible
        STATUS      current
        DESCRIPTION
         " "
    ::= { hwV5StandbyPhyCChannelEntry 1 }
     
    hwV5StandbyPhyPhyCLinkID         OBJECT-TYPE
        SYNTAX      INTEGER(0..255) 
        MAX-ACCESS  read-only
        STATUS      current
        DESCRIPTION
         " "
    ::= { hwV5StandbyPhyCChannelEntry 2 }

    hwV5StandbyPhyFrameID         OBJECT-TYPE
        SYNTAX      INTEGER(0..63) 
        MAX-ACCESS  read-only
        STATUS      current
        DESCRIPTION
         " "
    ::= { hwV5StandbyPhyCChannelEntry 3 }

    hwV5StandbyPhySlotID         OBJECT-TYPE
        SYNTAX      INTEGER(0..63) 
        MAX-ACCESS  read-only
        STATUS      current
        DESCRIPTION
         " "
    ::= { hwV5StandbyPhyCChannelEntry 4 }

    hwV5StandbyPhyPortID         OBJECT-TYPE
        SYNTAX      INTEGER(0..63) 
        MAX-ACCESS  read-only
        STATUS      current
        DESCRIPTION
         " "
    ::= { hwV5StandbyPhyCChannelEntry 5 }

    hwV5StandbyPhyTsNo         OBJECT-TYPE
        SYNTAX      INTEGER{
                              t15(1),
                              t16(2),
                              t31(3)
                           }    
        MAX-ACCESS  read-only
        STATUS      current
        DESCRIPTION
         " "
    ::= { hwV5StandbyPhyCChannelEntry 6 }

    hwV5StandbyPhyPhyCProtectGroup         OBJECT-TYPE
        SYNTAX      INTEGER{
                             pm(1),
                             ps(2),
                             p2m(3),
                             p2s(4)
                           }        
        MAX-ACCESS  read-only
        STATUS      current
        DESCRIPTION
         " "
    ::= { hwV5StandbyPhyCChannelEntry 7 }
    
  --   V5LinkTable
  
   hwV5LinkTable     OBJECT-TYPE
        SYNTAX         SEQUENCE OF HwV5LinkEntry
        MAX-ACCESS     not-accessible
        STATUS         current
    DESCRIPTION
           "The table lists the V5 groups that have been
            configured on the system."
    ::= { hwMD5500V5IfManage 8 }

    hwV5LinkEntry         OBJECT-TYPE
       SYNTAX         HwV5LinkEntry
       MAX-ACCESS     not-accessible
       STATUS         current
       DESCRIPTION    ""
          INDEX    { 
                     hwV5cfgV5InterfaceID,
                     hwV5LinkLinkID
                   }
    ::= { hwV5LinkTable  1 }

     HwV5LinkEntry ::= SEQUENCE 
     {
	hwV5LinkLinkID                           INTEGER,            	
	hwV5LinkLinkState                        INTEGER, 
	hwV5LinkCRC4                             TruthValue,
	hwV5LinkLIDState                         INTEGER,  
	hwV5LinkOprType                          INTEGER,
	hwV5LinkTsState                          Unsigned32	
     }
     
    hwV5LinkLinkID         OBJECT-TYPE
        SYNTAX      INTEGER(0..255) 
        MAX-ACCESS  not-accessible
        STATUS      current
        DESCRIPTION
         " "
    ::= { hwV5LinkEntry 1 }


    hwV5LinkLinkState         OBJECT-TYPE
        SYNTAX      INTEGER{
                               linkfail(1),
                               linkfailblock(2),
                               linkblock(3),
                               linlockunblock(4),
                               linremkunblock(5),
                               linknomal(6),
                               remotelinkid(7),
                               locallinkid(8),
                               linknotcfged(9) 
                            }          
        MAX-ACCESS  read-only
        STATUS      current
        DESCRIPTION
         " "
    ::= { hwV5LinkEntry 3 }

    hwV5LinkCRC4         OBJECT-TYPE
        SYNTAX      TruthValue
        MAX-ACCESS  read-only
        STATUS      current
        DESCRIPTION
         " "
    ::= { hwV5LinkEntry 4 }

    hwV5LinkLIDState         OBJECT-TYPE
        SYNTAX      INTEGER{
                               linkidnoreq(1),
                               linkidsuccess(2),
                               linkidfail(3),
                               linkidreject(4),
                               linkid(5),
                               linkidlenores(6),
                               linkidgiveinres(7)
                           }               
        MAX-ACCESS  read-only
        STATUS      current
        DESCRIPTION
         " "
    ::= { hwV5LinkEntry 5 }

    hwV5LinkOprType         OBJECT-TYPE
        SYNTAX      INTEGER{
                             imclose(1),
                             delayclose(2),
                             nodeclose(3),
                             unclose(4),
                             linkidoper(5)
                            }  
        MAX-ACCESS  read-write
        STATUS      current
        DESCRIPTION
         " "
    ::= { hwV5LinkEntry 6 }

    hwV5LinkTsState         OBJECT-TYPE
        SYNTAX      Unsigned32(0..4294967295)  
        MAX-ACCESS  read-write
        STATUS      current
        DESCRIPTION
         " "
    ::= { hwV5LinkEntry 7 }    
    
 --    V5ReProvisionOperatorTable
 
   hwV5ReProvisionOperatorTable     OBJECT-TYPE
        SYNTAX         SEQUENCE OF HwV5ReProvisionOperatorEntry
        MAX-ACCESS     not-accessible
        STATUS         current
    DESCRIPTION
           "The table lists the V5 groups that have been
            configured on the system."
    ::= { hwMD5500V5IfManage 9 }

    hwV5ReProvisionOperatorEntry         OBJECT-TYPE
       SYNTAX         HwV5ReProvisionOperatorEntry
       MAX-ACCESS     not-accessible
       STATUS         current
       DESCRIPTION    ""
          INDEX    { 
                     hwV5cfgV5InterfaceID
                   }
    ::= { hwV5ReProvisionOperatorTable  1 }

     HwV5ReProvisionOperatorEntry ::= SEQUENCE 
     {
	hwV5ReProvisionv5variable                      INTEGER,            	
        hwV5ReProvisionrejectreason                    INTEGER,
	hwV5ReProvisionOperType                        INTEGER 
     }
     
    hwV5ReProvisionv5variable         OBJECT-TYPE
        SYNTAX      INTEGER(0..127) 
        MAX-ACCESS  read-write
        STATUS      current
        DESCRIPTION
         " "
    ::= { hwV5ReProvisionOperatorEntry 1 }

    hwV5ReProvisionrejectreason         OBJECT-TYPE
        SYNTAX      INTEGER{
                             varunkown(1),
                             varunprepare(2),
                             provision(3)
                           }          
        MAX-ACCESS  read-write
        STATUS      current
        DESCRIPTION
         " "
    ::= { hwV5ReProvisionOperatorEntry 2 }

    hwV5ReProvisionOperType         OBJECT-TYPE
        SYNTAX      INTEGER{
                             dateuse(1),
                             checkre(2),
                             changevar(3),
                             reqvarifid(4),
                             reprovision(5),
                             reprovisionunprepare(6),
                             reprovisionstart(7),
                             unablereprovision(8) 
                            }         
        MAX-ACCESS  read-write
        STATUS      current
        DESCRIPTION
         " "
    ::= { hwV5ReProvisionOperatorEntry 3 }
    
  
  --    V5IsdnCChannelConfigManage
    hwV5IsdnCChannelConfigManage  OBJECT IDENTIFIER ::={ hwMD5500V5IfManage 10  }

  --  ?v5IsdnNextAllocPortGroup
    hwV5IsdnNextAllocPortGroup    OBJECT-TYPE
        SYNTAX      INTEGER(0..254)
        MAX-ACCESS  read-only
        STATUS      current
    DESCRIPTION
         " "
    ::= { hwV5IsdnCChannelConfigManage  1 }

--   V5IsdnCChannelConfigTable
  hwV5IsdnCChannelConfigTable     OBJECT-TYPE
        SYNTAX         SEQUENCE OF HwV5IsdnCChannelConfigEntry
        MAX-ACCESS     not-accessible
        STATUS         current
    DESCRIPTION
           "The table lists the V5 groups that have been
            configured on the system."
    ::= { hwV5IsdnCChannelConfigManage 2 }

    hwV5IsdnCChannelConfigEntry         OBJECT-TYPE
       SYNTAX         HwV5IsdnCChannelConfigEntry
       MAX-ACCESS     not-accessible
       STATUS         current
       DESCRIPTION    " "
          INDEX    { 
                     hwV5cfgV5InterfaceID,
                     hwV5IsdnCCIsdnPortGroupNo                    
                   }
    ::= { hwV5IsdnCChannelConfigTable  1 }

     HwV5IsdnCChannelConfigEntry ::= SEQUENCE 
     {
        hwV5IsdnCCIsdnPortGroupNo       INTEGER,
        hwV5IsdnCCLogicCID              INTEGER,
        hwV5IsdnCCDChannelType          INTEGER,
        hwV5IsdnCCUpperIsdnPortGroupNo  INTEGER,
        hwV5IsdnCCRowStatus             RowStatus
     }

    hwV5IsdnCCIsdnPortGroupNo         OBJECT-TYPE
        SYNTAX      INTEGER(0..254) 
        MAX-ACCESS  not-accessible
        STATUS      current
        DESCRIPTION
         " "
    ::= { hwV5IsdnCChannelConfigEntry 1 }

    hwV5IsdnCCLogicCID         OBJECT-TYPE
        SYNTAX      INTEGER(0..65535) 
        MAX-ACCESS  read-write
        STATUS      current
        DESCRIPTION
         " "
    ::= { hwV5IsdnCChannelConfigEntry 2 }

    hwV5IsdnCCDChannelType         OBJECT-TYPE
        SYNTAX      INTEGER{
                             d(1),
                             f(2),
                             p(3)
                           }  
        MAX-ACCESS  read-write
        STATUS      current
        DESCRIPTION
         " "
    ::= { hwV5IsdnCChannelConfigEntry 3 }

    hwV5IsdnCCUpperIsdnPortGroupNo         OBJECT-TYPE
        SYNTAX      INTEGER(0..254)
        MAX-ACCESS  read-write
        STATUS      current
        DESCRIPTION
         " "
    ::= { hwV5IsdnCChannelConfigEntry 4 }

    hwV5IsdnCCRowStatus         OBJECT-TYPE
       SYNTAX                      RowStatus
        MAX-ACCESS  read-write
        STATUS      current
        DESCRIPTION
         " "
    ::= { hwV5IsdnCChannelConfigEntry 5 }
    
   --  V5RingTypeMapConfigTable
    hwV5RingTypeMapConfigTable     OBJECT-TYPE
        SYNTAX         SEQUENCE OF HwV5RingTypeMapConfigEntry
        MAX-ACCESS     not-accessible
        STATUS         current
        DESCRIPTION
           "The table lists the V5 groups that have been
            configured on the system."
    ::= { hwMD5500V5IfManage 11 }

    hwV5RingTypeMapConfigEntry         OBJECT-TYPE
       SYNTAX         HwV5RingTypeMapConfigEntry
       MAX-ACCESS     not-accessible
       STATUS         current
       DESCRIPTION    " "
          INDEX    { 
                     hwV5cfgV5InterfaceID,
                     hwV5RingPeerRingType                    
                   }
    ::= { hwV5RingTypeMapConfigTable  1 }

     HwV5RingTypeMapConfigEntry ::= SEQUENCE 
     {
        hwV5RingPeerRingType       INTEGER,
        hwV5RingCascadeRingType    INTEGER,
        hwV5RingInitRingType       INTEGER,
        hwV5RingRowStatus          RowStatus
     }

    hwV5RingPeerRingType         OBJECT-TYPE
        SYNTAX      INTEGER(0..127) 
        MAX-ACCESS  not-accessible
        STATUS      current
        DESCRIPTION
         " "
    ::= { hwV5RingTypeMapConfigEntry 1 }

    hwV5RingCascadeRingType         OBJECT-TYPE
        SYNTAX      INTEGER{                   
                                                 r1(1),
                                                 r2(2),
                                                 r3(3),
                                                 r4(4),
                                                 r5(5),
                                                 r6(6),
                                                 r7(7),
                                                 r8(8),
                                                 r9(9),
                                                 r10(10),
                                                 r11(11),
                                                 r12(12),
                                                 r13(13),
                                                 r14(14),
                                                 r15(15),
                                                 r16(16),
                                                 r17(17),
                                                 r18(18),
                                                 r19(19),
                                                 r20(20),
                                                 r21(21),
                                                 r22(22),
                                                 r23(23),
                                                 r24(24),
                                                 r25(25),
                                                 r26(26),
                                                 r27(27),
                                                 r28(28),
                                                 r29(29),
                                                 r30(30)                                                   

                                             }    
        
        MAX-ACCESS  read-write
        STATUS      current
        DESCRIPTION
         " "
    ::= { hwV5RingTypeMapConfigEntry 2 }

    hwV5RingInitRingType         OBJECT-TYPE
        SYNTAX      INTEGER{                     r1(1),
                                                 r2(2),
                                                 r3(3),
                                                 r4(4),
                                                 r5(5),
                                                 r6(6),
                                                 r7(7),
                                                 r8(8),
                                                 r9(9),
                                                 r10(10),
                                                 r11(11),
                                                 r12(12),
                                                 r13(13),
                                                 r14(14),
                                                 r15(15),
                                                 r16(16),
                                                 r17(17),
                                                 r18(18),
                                                 r19(19),
                                                 r20(20),
                                                 r21(21),
                                                 r22(22),
                                                 r23(23),
                                                 r24(24),
                                                 r25(25),
                                                 r26(26),
                                                 r27(27) 
                                                 
                              }        
        MAX-ACCESS  read-write
        STATUS      current
        DESCRIPTION
         " "
    ::= { hwV5RingTypeMapConfigEntry 3 }

    hwV5RingRowStatus         OBJECT-TYPE
       SYNTAX               RowStatus
        MAX-ACCESS  read-write
        STATUS      current
        DESCRIPTION
         " "
    ::= { hwV5RingTypeMapConfigEntry 4 }
    
  --   UserDefineRingTypeTable
     hwUserDefineRingTypeTable     OBJECT-TYPE
        SYNTAX         SEQUENCE OF HwUserDefineRingTypeEntry
        MAX-ACCESS     not-accessible
        STATUS         current
        DESCRIPTION
           "The table lists the V5 groups that have been
            configured on the system."
    ::= { hwMD5500V5IfManage 12 }

    hwUserDefineRingTypeEntry         OBJECT-TYPE
       SYNTAX         HwUserDefineRingTypeEntry
       MAX-ACCESS     not-accessible
       STATUS         current
       DESCRIPTION    " "
          INDEX    { 
                     hwV5UserTypeRingType
                   }
    ::= { hwUserDefineRingTypeTable  1 }

     HwUserDefineRingTypeEntry ::= SEQUENCE 
     {
        hwV5UserTypeRingType       INTEGER,
        hwV5UserTypePara1          INTEGER,
        hwV5UserTypePara2          INTEGER,
        hwV5UserTypePara3          INTEGER,
        hwV5UserTypePara4          INTEGER,
        hwV5UserTypePara5          INTEGER,
        hwV5UserTypePara6          INTEGER     
           
     }

    hwV5UserTypeRingType         OBJECT-TYPE
        SYNTAX      INTEGER(0..15) 
        MAX-ACCESS  not-accessible
        STATUS      current
        DESCRIPTION
         " "
    ::= { hwUserDefineRingTypeEntry 1 }

    hwV5UserTypePara1         OBJECT-TYPE
        SYNTAX      INTEGER(0..65534) 
        MAX-ACCESS  read-write
        STATUS      current
        DESCRIPTION
         " "
    ::= { hwUserDefineRingTypeEntry 2 }


    hwV5UserTypePara2         OBJECT-TYPE
        SYNTAX      INTEGER(0..65534) 
        MAX-ACCESS  read-write
        STATUS      current
        DESCRIPTION
         " "
    ::= { hwUserDefineRingTypeEntry 3 }

    hwV5UserTypePara3         OBJECT-TYPE
        SYNTAX      INTEGER(0..65534) 
        MAX-ACCESS  read-write
        STATUS      current
        DESCRIPTION
         " "
    ::= { hwUserDefineRingTypeEntry 4 }

    hwV5UserTypePara4         OBJECT-TYPE
        SYNTAX      INTEGER(0..65534) 
        MAX-ACCESS  read-write
        STATUS      current
        DESCRIPTION
         " "
    ::= { hwUserDefineRingTypeEntry 5 }

    hwV5UserTypePara5         OBJECT-TYPE
        SYNTAX      INTEGER(0..65535) 
        MAX-ACCESS  read-write
        STATUS      current
        DESCRIPTION
         " "
    ::= { hwUserDefineRingTypeEntry 6 }

    hwV5UserTypePara6         OBJECT-TYPE
        SYNTAX      INTEGER(0..65534) 
        MAX-ACCESS  read-write
        STATUS      current
        DESCRIPTION
         " "
    ::= { hwUserDefineRingTypeEntry 7 }
    
    
    
hwMD5500SPCMIfManage  OBJECT IDENTIFIER ::={ hwMD5500ServiceAdminMIB 12 }

-- SPCMInterfaceTable


 hwSPCMInterfaceTable     OBJECT-TYPE
        SYNTAX         SEQUENCE OF HwSPCMInterfaceEntry
        MAX-ACCESS     not-accessible
        STATUS         current
    DESCRIPTION
           "The table lists the SPCM groups that have been
            configured on the system."
    ::= { hwMD5500SPCMIfManage 1 }

    hwSPCMInterfaceEntry         OBJECT-TYPE
       SYNTAX         HwSPCMInterfaceEntry
       MAX-ACCESS     not-accessible
       STATUS         current
       DESCRIPTION    ""
          INDEX    { hwSPCMInterfaceID }
    ::= { hwSPCMInterfaceTable  1 }

     HwSPCMInterfaceEntry ::= SEQUENCE 
     {
        hwSPCMInterfaceID                   INTEGER,
		hwSPCMCASE1PortFrameID              INTEGER,
		hwSPCMCASE1PortSlotID				INTEGER,
		hwSPCMCASE1PortPortID				INTEGER,
		hwSPCMRingModeID					INTEGER,
		hwSPCMInitRingModeID					INTEGER,
		hwSPCMRowStatus                     RowStatus,
		hwSPCMState							INTEGER
     }
     
    hwSPCMInterfaceID         OBJECT-TYPE
        SYNTAX      INTEGER(0..254)
        MAX-ACCESS  not-accessible
        STATUS      current
        DESCRIPTION
         " "
    ::= { hwSPCMInterfaceEntry 1 }

    hwSPCMCASE1PortFrameID       OBJECT-TYPE
        SYNTAX      INTEGER(0..240)
        MAX-ACCESS  read-write
        STATUS      current
        DESCRIPTION
         " "
    ::= { hwSPCMInterfaceEntry 2 }

    hwSPCMCASE1PortSlotID       OBJECT-TYPE
        SYNTAX      INTEGER(0..63)
        MAX-ACCESS  read-write
        STATUS      current
        DESCRIPTION
         " "
    ::= { hwSPCMInterfaceEntry 3 }
    
    hwSPCMCASE1PortPortID       OBJECT-TYPE
        SYNTAX      INTEGER(0..63)
        MAX-ACCESS  read-write
        STATUS      current
        DESCRIPTION
         " "
    ::= { hwSPCMInterfaceEntry 4 }    

    hwSPCMRingModeID       OBJECT-TYPE
        SYNTAX      INTEGER{                   
                              r1(1),
                              r2(2),
                              r3(3),
                              r4(4),
                              r5(5),
                              r6(6),
                              r7(7),
                              r8(8),
                              r9(9),
                              r10(10),
                              r11(11),
                              r12(12),
                              r13(13),
                              r14(14),
                              r15(15),
                              r16(16),
                              r17(17),
                              r18(18),
                              r19(19),
                              r20(20),
                              r21(21),
                              r22(22),
                              r23(23),
                              r24(24),
                              r25(25),
                              r26(26),
                              r27(27),
                              r28(28),
                              r29(29),
                              r30(30) 
                         } 
        MAX-ACCESS  read-write
        STATUS      current
        DESCRIPTION
         " "
    ::= { hwSPCMInterfaceEntry 5 }    

    hwSPCMInitRingModeID       OBJECT-TYPE
        SYNTAX      INTEGER{                     r1(1),
                                                 r2(2),
                                                 r3(3),
                                                 r4(4),
                                                 r5(5),
                                                 r6(6),
                                                 r7(7),
                                                 r8(8),
                                                 r9(9),
                                                 r10(10),
                                                 r11(11),
                                                 r12(12),
                                                 r13(13),
                                                 r14(14),
                                                 r15(15),
                                                 r16(16),
                                                 r17(17),
                                                 r18(18),
                                                 r19(19),
                                                 r20(20),
                                                 r21(21),
                                                 r22(22),
                                                 r23(23),
                                                 r24(24),
                                                 r25(25),
                                                 r26(26),
                                                 r27(27) 
                         } 
        MAX-ACCESS  read-write
        STATUS      current
        DESCRIPTION
         " "
    ::= { hwSPCMInterfaceEntry 6 }    
    hwSPCMRowStatus          OBJECT-TYPE
        SYNTAX             RowStatus
        MAX-ACCESS  read-write
        STATUS      current
        DESCRIPTION
         " "
    ::= { hwSPCMInterfaceEntry 7 }
    

    hwSPCMState       OBJECT-TYPE
         SYNTAX          INTEGER{
         					normal(1),
         					fault(2)
         				}
                         
        MAX-ACCESS  read-only
        STATUS      current
        DESCRIPTION
         " "
    ::= { hwSPCMInterfaceEntry 8 }
    
END
