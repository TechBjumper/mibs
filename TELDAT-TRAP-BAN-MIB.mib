-- file automatically created


TELDAT-TRAP-BAN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


banTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BAN event subsystem."
    REVISION "201401200930Z"
    DESCRIPTION "Initial implementation"
        ::= { telEventTraps 109 }


banEventsGroup	OBJECT IDENTIFIER	::= { banTrapsMIB 1 }

banNotifications	OBJECT IDENTIFIER	::= { banTrapsMIB 2 }
banNotificationsPrefix	OBJECT IDENTIFIER	::= { banNotifications 0 }

banEventObjects1 OBJECT-IDENTITY
    STATUS current
    DESCRIPTION
        "Event BAN.1
        I-frame packet. Direction is 'in' or 'out' of the router. Shows the
        bridge port number. Shows the full RIF (routing information field) of
        the packet. Shows up to 20 bytes of the packet after the SSAP field.
        The length is the amount of data in the packet after the SSAP field in
        the packet."
    ::= { banEventsGroup 1 }

ban1-direction OBJECT-TYPE
    SYNTAX DisplayString
    MAX-ACCESS accessible-for-notify
    STATUS current
    DESCRIPTION
        "Parameter 'direction' in event BAN.1"
    ::= { banEventObjects1 1 }

ban1-bridge-port OBJECT-TYPE
    SYNTAX Integer32
    MAX-ACCESS accessible-for-notify
    STATUS current
    DESCRIPTION
        "Parameter 'bridge-port' in event BAN.1"
    ::= { banEventObjects1 2 }

ban1-len OBJECT-TYPE
    SYNTAX Integer32
    MAX-ACCESS accessible-for-notify
    STATUS current
    DESCRIPTION
        "Parameter 'len' in event BAN.1"
    ::= { banEventObjects1 3 }

ban1-source-mac-address OBJECT-TYPE
    SYNTAX DisplayString
    MAX-ACCESS accessible-for-notify
    STATUS current
    DESCRIPTION
        "Parameter 'source-mac-address' in event BAN.1"
    ::= { banEventObjects1 4 }

ban1-dest-mac-address OBJECT-TYPE
    SYNTAX DisplayString
    MAX-ACCESS accessible-for-notify
    STATUS current
    DESCRIPTION
        "Parameter 'dest-mac-address' in event BAN.1"
    ::= { banEventObjects1 5 }

ban1-source-sap OBJECT-TYPE
    SYNTAX Integer32
    MAX-ACCESS accessible-for-notify
    STATUS current
    DESCRIPTION
        "Parameter 'source-sap' in event BAN.1"
    ::= { banEventObjects1 6 }

ban1-dest-sap OBJECT-TYPE
    SYNTAX Integer32
    MAX-ACCESS accessible-for-notify
    STATUS current
    DESCRIPTION
        "Parameter 'dest-sap' in event BAN.1"
    ::= { banEventObjects1 7 }

ban1-rif-data OBJECT-TYPE
    SYNTAX DisplayString
    MAX-ACCESS accessible-for-notify
    STATUS current
    DESCRIPTION
        "Parameter 'rif-data' in event BAN.1"
    ::= { banEventObjects1 8 }

banEventObjects2 OBJECT-IDENTITY
    STATUS current
    DESCRIPTION
        "Event BAN.2
        RR packet."
    ::= { banEventsGroup 2 }

ban2-direction OBJECT-TYPE
    SYNTAX DisplayString
    MAX-ACCESS accessible-for-notify
    STATUS current
    DESCRIPTION
        "Parameter 'direction' in event BAN.2"
    ::= { banEventObjects2 1 }

ban2-bridge-port OBJECT-TYPE
    SYNTAX Integer32
    MAX-ACCESS accessible-for-notify
    STATUS current
    DESCRIPTION
        "Parameter 'bridge-port' in event BAN.2"
    ::= { banEventObjects2 2 }

ban2-len OBJECT-TYPE
    SYNTAX Integer32
    MAX-ACCESS accessible-for-notify
    STATUS current
    DESCRIPTION
        "Parameter 'len' in event BAN.2"
    ::= { banEventObjects2 3 }

ban2-source-mac-address OBJECT-TYPE
    SYNTAX DisplayString
    MAX-ACCESS accessible-for-notify
    STATUS current
    DESCRIPTION
        "Parameter 'source-mac-address' in event BAN.2"
    ::= { banEventObjects2 4 }

ban2-dest-mac-address OBJECT-TYPE
    SYNTAX DisplayString
    MAX-ACCESS accessible-for-notify
    STATUS current
    DESCRIPTION
        "Parameter 'dest-mac-address' in event BAN.2"
    ::= { banEventObjects2 5 }

ban2-source-sap OBJECT-TYPE
    SYNTAX Integer32
    MAX-ACCESS accessible-for-notify
    STATUS current
    DESCRIPTION
        "Parameter 'source-sap' in event BAN.2"
    ::= { banEventObjects2 6 }

ban2-dest-sap OBJECT-TYPE
    SYNTAX Integer32
    MAX-ACCESS accessible-for-notify
    STATUS current
    DESCRIPTION
        "Parameter 'dest-sap' in event BAN.2"
    ::= { banEventObjects2 7 }

ban2-rif-data OBJECT-TYPE
    SYNTAX DisplayString
    MAX-ACCESS accessible-for-notify
    STATUS current
    DESCRIPTION
        "Parameter 'rif-data' in event BAN.2"
    ::= { banEventObjects2 8 }

banEventObjects3 OBJECT-IDENTITY
    STATUS current
    DESCRIPTION
        "Event BAN.3
        The configured BAN bridge port is not a bridge port."
    ::= { banEventsGroup 3 }

ban3-bridge-port OBJECT-TYPE
    SYNTAX Integer32
    MAX-ACCESS accessible-for-notify
    STATUS current
    DESCRIPTION
        "Parameter 'bridge-port' in event BAN.3"
    ::= { banEventObjects3 1 }

banEventObjects4 OBJECT-IDENTITY
    STATUS current
    DESCRIPTION
        "Event BAN.4
        The configured BAN bridge port has been initialized from a BAN point of view."
    ::= { banEventsGroup 4 }

ban4-bridge-port OBJECT-TYPE
    SYNTAX Integer32
    MAX-ACCESS accessible-for-notify
    STATUS current
    DESCRIPTION
        "Parameter 'bridge-port' in event BAN.4"
    ::= { banEventObjects4 1 }

banEventObjects5 OBJECT-IDENTITY
    STATUS current
    DESCRIPTION
        "Event BAN.5
        Every frame sent by the NCP must match the configured Boundary Node
        Identifier (BNI) MAC address."
    ::= { banEventsGroup 5 }

ban5-source-mac-address OBJECT-TYPE
    SYNTAX DisplayString
    MAX-ACCESS accessible-for-notify
    STATUS current
    DESCRIPTION
        "Parameter 'source-mac-address' in event BAN.5"
    ::= { banEventObjects5 1 }

ban5-dest-mac-address OBJECT-TYPE
    SYNTAX DisplayString
    MAX-ACCESS accessible-for-notify
    STATUS current
    DESCRIPTION
        "Parameter 'dest-mac-address' in event BAN.5"
    ::= { banEventObjects5 2 }

ban5-bni-mac OBJECT-TYPE
    SYNTAX DisplayString
    MAX-ACCESS accessible-for-notify
    STATUS current
    DESCRIPTION
        "Parameter 'bni-mac' in event BAN.5"
    ::= { banEventObjects5 3 }

ban5-bridge-port OBJECT-TYPE
    SYNTAX Integer32
    MAX-ACCESS accessible-for-notify
    STATUS current
    DESCRIPTION
        "Parameter 'bridge-port' in event BAN.5"
    ::= { banEventObjects5 4 }

banEventObjects6 OBJECT-IDENTITY
    STATUS current
    DESCRIPTION
        "Event BAN.6
        The configured BAN bridge port is not a Frame Relay DLCI bridge port."
    ::= { banEventsGroup 6 }

ban6-bridge-port OBJECT-TYPE
    SYNTAX Integer32
    MAX-ACCESS accessible-for-notify
    STATUS current
    DESCRIPTION
        "Parameter 'bridge-port' in event BAN.6"
    ::= { banEventObjects6 1 }

banEventObjects8 OBJECT-IDENTITY
    STATUS current
    DESCRIPTION
        "Event BAN.8
        The outgoing frame was filtered by BAN because it was NOT an RFC 1490
        bridged Token-Ring frame, without preserved FCS, which is OUI type 9.
        This is the only type of frame expected by the NCP. Another bridge type
        frame is being sent: 1 and 7 are Ethernet, 2 and 8 are 802.4, 3 is
        Token-Ring with FCS, 4 and 10 are FDDI, 11 is 802.6, 14 is
        802.1d Hello BPDU, 15 is SRB Hello BPDU."
    ::= { banEventsGroup 8 }

ban8-bridge-port OBJECT-TYPE
    SYNTAX Integer32
    MAX-ACCESS accessible-for-notify
    STATUS current
    DESCRIPTION
        "Parameter 'bridge-port' in event BAN.8"
    ::= { banEventObjects8 1 }

ban8-oui-type OBJECT-TYPE
    SYNTAX Integer32
    MAX-ACCESS accessible-for-notify
    STATUS current
    DESCRIPTION
        "Parameter 'oui-type' in event BAN.8"
    ::= { banEventObjects8 2 }

banEventObjects9 OBJECT-IDENTITY
    STATUS current
    DESCRIPTION
        "Event BAN.9
        The outgoing frame was filtered by BAN because the frame's destination
        address did not equal the BAN DLCI address. This is done to protect
        the NCP."
    ::= { banEventsGroup 9 }

ban9-source-mac-address OBJECT-TYPE
    SYNTAX DisplayString
    MAX-ACCESS accessible-for-notify
    STATUS current
    DESCRIPTION
        "Parameter 'source-mac-address' in event BAN.9"
    ::= { banEventObjects9 1 }

ban9-dest-mac-address OBJECT-TYPE
    SYNTAX DisplayString
    MAX-ACCESS accessible-for-notify
    STATUS current
    DESCRIPTION
        "Parameter 'dest-mac-address' in event BAN.9"
    ::= { banEventObjects9 2 }

ban9-bridge-port OBJECT-TYPE
    SYNTAX Integer32
    MAX-ACCESS accessible-for-notify
    STATUS current
    DESCRIPTION
        "Parameter 'bridge-port' in event BAN.9"
    ::= { banEventObjects9 3 }

ban9-ban-dlci-address OBJECT-TYPE
    SYNTAX DisplayString
    MAX-ACCESS accessible-for-notify
    STATUS current
    DESCRIPTION
        "Parameter 'ban-dlci-address' in event BAN.9"
    ::= { banEventObjects9 4 }

banEventObjects10 OBJECT-IDENTITY
    STATUS current
    DESCRIPTION
        "Event BAN.10
        The BAN bridge port behavior is being dynamically forced to transparent
        bridging off, spanning tree off. This is required for BAN."
    ::= { banEventsGroup 10 }

ban10-bridge-port OBJECT-TYPE
    SYNTAX Integer32
    MAX-ACCESS accessible-for-notify
    STATUS current
    DESCRIPTION
        "Parameter 'bridge-port' in event BAN.10"
    ::= { banEventObjects10 1 }

banEventObjects11 OBJECT-IDENTITY
    STATUS current
    DESCRIPTION
        "Event BAN.11
        The BAN bridge port is configured for DLSw terminated. However, DLSw
        is not in this build."
    ::= { banEventsGroup 11 }

ban11-bridge-port OBJECT-TYPE
    SYNTAX Integer32
    MAX-ACCESS accessible-for-notify
    STATUS current
    DESCRIPTION
        "Parameter 'bridge-port' in event BAN.11"
    ::= { banEventObjects11 1 }

banEventObjects13 OBJECT-IDENTITY
    STATUS current
    DESCRIPTION
        "Event BAN.13
        The outgoing frame was filtered by BAN because the BAN port is set to
        DLSw switching, but the frame was not a DLSw frame since the DLSw
        source routing segment and bridge number were not in the RIF (routing
        information field) of the frame. This is done to protect the NCP."
    ::= { banEventsGroup 13 }

ban13-source-mac-address OBJECT-TYPE
    SYNTAX DisplayString
    MAX-ACCESS accessible-for-notify
    STATUS current
    DESCRIPTION
        "Parameter 'source-mac-address' in event BAN.13"
    ::= { banEventObjects13 1 }

ban13-dest-mac-address OBJECT-TYPE
    SYNTAX DisplayString
    MAX-ACCESS accessible-for-notify
    STATUS current
    DESCRIPTION
        "Parameter 'dest-mac-address' in event BAN.13"
    ::= { banEventObjects13 2 }

ban13-bridge-port OBJECT-TYPE
    SYNTAX Integer32
    MAX-ACCESS accessible-for-notify
    STATUS current
    DESCRIPTION
        "Parameter 'bridge-port' in event BAN.13"
    ::= { banEventObjects13 3 }

ban13-segment-ban OBJECT-TYPE
    SYNTAX Integer32
    MAX-ACCESS accessible-for-notify
    STATUS current
    DESCRIPTION
        "Parameter 'segment-ban' in event BAN.13"
    ::= { banEventObjects13 4 }

ban13-rif-data OBJECT-TYPE
    SYNTAX DisplayString
    MAX-ACCESS accessible-for-notify
    STATUS current
    DESCRIPTION
        "Parameter 'rif-data' in event BAN.13"
    ::= { banEventObjects13 5 }

banEventObjects14 OBJECT-IDENTITY
    STATUS current
    DESCRIPTION
        "Event BAN.14
        RNR packet."
    ::= { banEventsGroup 14 }

ban14-direction OBJECT-TYPE
    SYNTAX DisplayString
    MAX-ACCESS accessible-for-notify
    STATUS current
    DESCRIPTION
        "Parameter 'direction' in event BAN.14"
    ::= { banEventObjects14 1 }

ban14-bridge-port OBJECT-TYPE
    SYNTAX Integer32
    MAX-ACCESS accessible-for-notify
    STATUS current
    DESCRIPTION
        "Parameter 'bridge-port' in event BAN.14"
    ::= { banEventObjects14 2 }

ban14-len OBJECT-TYPE
    SYNTAX Integer32
    MAX-ACCESS accessible-for-notify
    STATUS current
    DESCRIPTION
        "Parameter 'len' in event BAN.14"
    ::= { banEventObjects14 3 }

ban14-source-mac-address OBJECT-TYPE
    SYNTAX DisplayString
    MAX-ACCESS accessible-for-notify
    STATUS current
    DESCRIPTION
        "Parameter 'source-mac-address' in event BAN.14"
    ::= { banEventObjects14 4 }

ban14-dest-mac-address OBJECT-TYPE
    SYNTAX DisplayString
    MAX-ACCESS accessible-for-notify
    STATUS current
    DESCRIPTION
        "Parameter 'dest-mac-address' in event BAN.14"
    ::= { banEventObjects14 5 }

ban14-source-sap OBJECT-TYPE
    SYNTAX Integer32
    MAX-ACCESS accessible-for-notify
    STATUS current
    DESCRIPTION
        "Parameter 'source-sap' in event BAN.14"
    ::= { banEventObjects14 6 }

ban14-dest-sap OBJECT-TYPE
    SYNTAX Integer32
    MAX-ACCESS accessible-for-notify
    STATUS current
    DESCRIPTION
        "Parameter 'dest-sap' in event BAN.14"
    ::= { banEventObjects14 7 }

ban14-rif-data OBJECT-TYPE
    SYNTAX DisplayString
    MAX-ACCESS accessible-for-notify
    STATUS current
    DESCRIPTION
        "Parameter 'rif-data' in event BAN.14"
    ::= { banEventObjects14 8 }

banEventObjects15 OBJECT-IDENTITY
    STATUS current
    DESCRIPTION
        "Event BAN.15
        REJ packet."
    ::= { banEventsGroup 15 }

ban15-direction OBJECT-TYPE
    SYNTAX DisplayString
    MAX-ACCESS accessible-for-notify
    STATUS current
    DESCRIPTION
        "Parameter 'direction' in event BAN.15"
    ::= { banEventObjects15 1 }

ban15-bridge-port OBJECT-TYPE
    SYNTAX Integer32
    MAX-ACCESS accessible-for-notify
    STATUS current
    DESCRIPTION
        "Parameter 'bridge-port' in event BAN.15"
    ::= { banEventObjects15 2 }

ban15-len OBJECT-TYPE
    SYNTAX Integer32
    MAX-ACCESS accessible-for-notify
    STATUS current
    DESCRIPTION
        "Parameter 'len' in event BAN.15"
    ::= { banEventObjects15 3 }

ban15-source-mac-address OBJECT-TYPE
    SYNTAX DisplayString
    MAX-ACCESS accessible-for-notify
    STATUS current
    DESCRIPTION
        "Parameter 'source-mac-address' in event BAN.15"
    ::= { banEventObjects15 4 }

ban15-dest-mac-address OBJECT-TYPE
    SYNTAX DisplayString
    MAX-ACCESS accessible-for-notify
    STATUS current
    DESCRIPTION
        "Parameter 'dest-mac-address' in event BAN.15"
    ::= { banEventObjects15 5 }

ban15-source-sap OBJECT-TYPE
    SYNTAX Integer32
    MAX-ACCESS accessible-for-notify
    STATUS current
    DESCRIPTION
        "Parameter 'source-sap' in event BAN.15"
    ::= { banEventObjects15 6 }

ban15-dest-sap OBJECT-TYPE
    SYNTAX Integer32
    MAX-ACCESS accessible-for-notify
    STATUS current
    DESCRIPTION
        "Parameter 'dest-sap' in event BAN.15"
    ::= { banEventObjects15 7 }

ban15-rif-data OBJECT-TYPE
    SYNTAX DisplayString
    MAX-ACCESS accessible-for-notify
    STATUS current
    DESCRIPTION
        "Parameter 'rif-data' in event BAN.15"
    ::= { banEventObjects15 8 }

banEventObjects16 OBJECT-IDENTITY
    STATUS current
    DESCRIPTION
        "Event BAN.16
        TEST-C (Test command) packet."
    ::= { banEventsGroup 16 }

ban16-direction OBJECT-TYPE
    SYNTAX DisplayString
    MAX-ACCESS accessible-for-notify
    STATUS current
    DESCRIPTION
        "Parameter 'direction' in event BAN.16"
    ::= { banEventObjects16 1 }

ban16-bridge-port OBJECT-TYPE
    SYNTAX Integer32
    MAX-ACCESS accessible-for-notify
    STATUS current
    DESCRIPTION
        "Parameter 'bridge-port' in event BAN.16"
    ::= { banEventObjects16 2 }

ban16-len OBJECT-TYPE
    SYNTAX Integer32
    MAX-ACCESS accessible-for-notify
    STATUS current
    DESCRIPTION
        "Parameter 'len' in event BAN.16"
    ::= { banEventObjects16 3 }

ban16-source-mac-address OBJECT-TYPE
    SYNTAX DisplayString
    MAX-ACCESS accessible-for-notify
    STATUS current
    DESCRIPTION
        "Parameter 'source-mac-address' in event BAN.16"
    ::= { banEventObjects16 4 }

ban16-dest-mac-address OBJECT-TYPE
    SYNTAX DisplayString
    MAX-ACCESS accessible-for-notify
    STATUS current
    DESCRIPTION
        "Parameter 'dest-mac-address' in event BAN.16"
    ::= { banEventObjects16 5 }

ban16-source-sap OBJECT-TYPE
    SYNTAX Integer32
    MAX-ACCESS accessible-for-notify
    STATUS current
    DESCRIPTION
        "Parameter 'source-sap' in event BAN.16"
    ::= { banEventObjects16 6 }

ban16-dest-sap OBJECT-TYPE
    SYNTAX Integer32
    MAX-ACCESS accessible-for-notify
    STATUS current
    DESCRIPTION
        "Parameter 'dest-sap' in event BAN.16"
    ::= { banEventObjects16 7 }

ban16-rif-data OBJECT-TYPE
    SYNTAX DisplayString
    MAX-ACCESS accessible-for-notify
    STATUS current
    DESCRIPTION
        "Parameter 'rif-data' in event BAN.16"
    ::= { banEventObjects16 8 }

banEventObjects17 OBJECT-IDENTITY
    STATUS current
    DESCRIPTION
        "Event BAN.17
        TEST-R (Test response) packet."
    ::= { banEventsGroup 17 }

ban17-direction OBJECT-TYPE
    SYNTAX DisplayString
    MAX-ACCESS accessible-for-notify
    STATUS current
    DESCRIPTION
        "Parameter 'direction' in event BAN.17"
    ::= { banEventObjects17 1 }

ban17-bridge-port OBJECT-TYPE
    SYNTAX Integer32
    MAX-ACCESS accessible-for-notify
    STATUS current
    DESCRIPTION
        "Parameter 'bridge-port' in event BAN.17"
    ::= { banEventObjects17 2 }

ban17-len OBJECT-TYPE
    SYNTAX Integer32
    MAX-ACCESS accessible-for-notify
    STATUS current
    DESCRIPTION
        "Parameter 'len' in event BAN.17"
    ::= { banEventObjects17 3 }

ban17-source-mac-address OBJECT-TYPE
    SYNTAX DisplayString
    MAX-ACCESS accessible-for-notify
    STATUS current
    DESCRIPTION
        "Parameter 'source-mac-address' in event BAN.17"
    ::= { banEventObjects17 4 }

ban17-dest-mac-address OBJECT-TYPE
    SYNTAX DisplayString
    MAX-ACCESS accessible-for-notify
    STATUS current
    DESCRIPTION
        "Parameter 'dest-mac-address' in event BAN.17"
    ::= { banEventObjects17 5 }

ban17-source-sap OBJECT-TYPE
    SYNTAX Integer32
    MAX-ACCESS accessible-for-notify
    STATUS current
    DESCRIPTION
        "Parameter 'source-sap' in event BAN.17"
    ::= { banEventObjects17 6 }

ban17-dest-sap OBJECT-TYPE
    SYNTAX Integer32
    MAX-ACCESS accessible-for-notify
    STATUS current
    DESCRIPTION
        "Parameter 'dest-sap' in event BAN.17"
    ::= { banEventObjects17 7 }

ban17-rif-data OBJECT-TYPE
    SYNTAX DisplayString
    MAX-ACCESS accessible-for-notify
    STATUS current
    DESCRIPTION
        "Parameter 'rif-data' in event BAN.17"
    ::= { banEventObjects17 8 }

banEventObjects18 OBJECT-IDENTITY
    STATUS current
    DESCRIPTION
        "Event BAN.18
        XID-C (XID command) packet."
    ::= { banEventsGroup 18 }

ban18-direction OBJECT-TYPE
    SYNTAX DisplayString
    MAX-ACCESS accessible-for-notify
    STATUS current
    DESCRIPTION
        "Parameter 'direction' in event BAN.18"
    ::= { banEventObjects18 1 }

ban18-bridge-port OBJECT-TYPE
    SYNTAX Integer32
    MAX-ACCESS accessible-for-notify
    STATUS current
    DESCRIPTION
        "Parameter 'bridge-port' in event BAN.18"
    ::= { banEventObjects18 2 }

ban18-len OBJECT-TYPE
    SYNTAX Integer32
    MAX-ACCESS accessible-for-notify
    STATUS current
    DESCRIPTION
        "Parameter 'len' in event BAN.18"
    ::= { banEventObjects18 3 }

ban18-source-mac-address OBJECT-TYPE
    SYNTAX DisplayString
    MAX-ACCESS accessible-for-notify
    STATUS current
    DESCRIPTION
        "Parameter 'source-mac-address' in event BAN.18"
    ::= { banEventObjects18 4 }

ban18-dest-mac-address OBJECT-TYPE
    SYNTAX DisplayString
    MAX-ACCESS accessible-for-notify
    STATUS current
    DESCRIPTION
        "Parameter 'dest-mac-address' in event BAN.18"
    ::= { banEventObjects18 5 }

ban18-source-sap OBJECT-TYPE
    SYNTAX Integer32
    MAX-ACCESS accessible-for-notify
    STATUS current
    DESCRIPTION
        "Parameter 'source-sap' in event BAN.18"
    ::= { banEventObjects18 6 }

ban18-dest-sap OBJECT-TYPE
    SYNTAX Integer32
    MAX-ACCESS accessible-for-notify
    STATUS current
    DESCRIPTION
        "Parameter 'dest-sap' in event BAN.18"
    ::= { banEventObjects18 7 }

ban18-rif-data OBJECT-TYPE
    SYNTAX DisplayString
    MAX-ACCESS accessible-for-notify
    STATUS current
    DESCRIPTION
        "Parameter 'rif-data' in event BAN.18"
    ::= { banEventObjects18 8 }

banEventObjects19 OBJECT-IDENTITY
    STATUS current
    DESCRIPTION
        "Event BAN.19
        XID-R (XID response) packet."
    ::= { banEventsGroup 19 }

ban19-direction OBJECT-TYPE
    SYNTAX DisplayString
    MAX-ACCESS accessible-for-notify
    STATUS current
    DESCRIPTION
        "Parameter 'direction' in event BAN.19"
    ::= { banEventObjects19 1 }

ban19-bridge-port OBJECT-TYPE
    SYNTAX Integer32
    MAX-ACCESS accessible-for-notify
    STATUS current
    DESCRIPTION
        "Parameter 'bridge-port' in event BAN.19"
    ::= { banEventObjects19 2 }

ban19-len OBJECT-TYPE
    SYNTAX Integer32
    MAX-ACCESS accessible-for-notify
    STATUS current
    DESCRIPTION
        "Parameter 'len' in event BAN.19"
    ::= { banEventObjects19 3 }

ban19-source-mac-address OBJECT-TYPE
    SYNTAX DisplayString
    MAX-ACCESS accessible-for-notify
    STATUS current
    DESCRIPTION
        "Parameter 'source-mac-address' in event BAN.19"
    ::= { banEventObjects19 4 }

ban19-dest-mac-address OBJECT-TYPE
    SYNTAX DisplayString
    MAX-ACCESS accessible-for-notify
    STATUS current
    DESCRIPTION
        "Parameter 'dest-mac-address' in event BAN.19"
    ::= { banEventObjects19 5 }

ban19-source-sap OBJECT-TYPE
    SYNTAX Integer32
    MAX-ACCESS accessible-for-notify
    STATUS current
    DESCRIPTION
        "Parameter 'source-sap' in event BAN.19"
    ::= { banEventObjects19 6 }

ban19-dest-sap OBJECT-TYPE
    SYNTAX Integer32
    MAX-ACCESS accessible-for-notify
    STATUS current
    DESCRIPTION
        "Parameter 'dest-sap' in event BAN.19"
    ::= { banEventObjects19 7 }

ban19-rif-data OBJECT-TYPE
    SYNTAX DisplayString
    MAX-ACCESS accessible-for-notify
    STATUS current
    DESCRIPTION
        "Parameter 'rif-data' in event BAN.19"
    ::= { banEventObjects19 8 }

banEventObjects20 OBJECT-IDENTITY
    STATUS current
    DESCRIPTION
        "Event BAN.20
        SABME packet."
    ::= { banEventsGroup 20 }

ban20-direction OBJECT-TYPE
    SYNTAX DisplayString
    MAX-ACCESS accessible-for-notify
    STATUS current
    DESCRIPTION
        "Parameter 'direction' in event BAN.20"
    ::= { banEventObjects20 1 }

ban20-bridge-port OBJECT-TYPE
    SYNTAX Integer32
    MAX-ACCESS accessible-for-notify
    STATUS current
    DESCRIPTION
        "Parameter 'bridge-port' in event BAN.20"
    ::= { banEventObjects20 2 }

ban20-len OBJECT-TYPE
    SYNTAX Integer32
    MAX-ACCESS accessible-for-notify
    STATUS current
    DESCRIPTION
        "Parameter 'len' in event BAN.20"
    ::= { banEventObjects20 3 }

ban20-source-mac-address OBJECT-TYPE
    SYNTAX DisplayString
    MAX-ACCESS accessible-for-notify
    STATUS current
    DESCRIPTION
        "Parameter 'source-mac-address' in event BAN.20"
    ::= { banEventObjects20 4 }

ban20-dest-mac-address OBJECT-TYPE
    SYNTAX DisplayString
    MAX-ACCESS accessible-for-notify
    STATUS current
    DESCRIPTION
        "Parameter 'dest-mac-address' in event BAN.20"
    ::= { banEventObjects20 5 }

ban20-source-sap OBJECT-TYPE
    SYNTAX Integer32
    MAX-ACCESS accessible-for-notify
    STATUS current
    DESCRIPTION
        "Parameter 'source-sap' in event BAN.20"
    ::= { banEventObjects20 6 }

ban20-dest-sap OBJECT-TYPE
    SYNTAX Integer32
    MAX-ACCESS accessible-for-notify
    STATUS current
    DESCRIPTION
        "Parameter 'dest-sap' in event BAN.20"
    ::= { banEventObjects20 7 }

ban20-rif-data OBJECT-TYPE
    SYNTAX DisplayString
    MAX-ACCESS accessible-for-notify
    STATUS current
    DESCRIPTION
        "Parameter 'rif-data' in event BAN.20"
    ::= { banEventObjects20 8 }

banEventObjects21 OBJECT-IDENTITY
    STATUS current
    DESCRIPTION
        "Event BAN.21
        UA packet."
    ::= { banEventsGroup 21 }

ban21-direction OBJECT-TYPE
    SYNTAX DisplayString
    MAX-ACCESS accessible-for-notify
    STATUS current
    DESCRIPTION
        "Parameter 'direction' in event BAN.21"
    ::= { banEventObjects21 1 }

ban21-bridge-port OBJECT-TYPE
    SYNTAX Integer32
    MAX-ACCESS accessible-for-notify
    STATUS current
    DESCRIPTION
        "Parameter 'bridge-port' in event BAN.21"
    ::= { banEventObjects21 2 }

ban21-len OBJECT-TYPE
    SYNTAX Integer32
    MAX-ACCESS accessible-for-notify
    STATUS current
    DESCRIPTION
        "Parameter 'len' in event BAN.21"
    ::= { banEventObjects21 3 }

ban21-source-mac-address OBJECT-TYPE
    SYNTAX DisplayString
    MAX-ACCESS accessible-for-notify
    STATUS current
    DESCRIPTION
        "Parameter 'source-mac-address' in event BAN.21"
    ::= { banEventObjects21 4 }

ban21-dest-mac-address OBJECT-TYPE
    SYNTAX DisplayString
    MAX-ACCESS accessible-for-notify
    STATUS current
    DESCRIPTION
        "Parameter 'dest-mac-address' in event BAN.21"
    ::= { banEventObjects21 5 }

ban21-source-sap OBJECT-TYPE
    SYNTAX Integer32
    MAX-ACCESS accessible-for-notify
    STATUS current
    DESCRIPTION
        "Parameter 'source-sap' in event BAN.21"
    ::= { banEventObjects21 6 }

ban21-dest-sap OBJECT-TYPE
    SYNTAX Integer32
    MAX-ACCESS accessible-for-notify
    STATUS current
    DESCRIPTION
        "Parameter 'dest-sap' in event BAN.21"
    ::= { banEventObjects21 7 }

ban21-rif-data OBJECT-TYPE
    SYNTAX DisplayString
    MAX-ACCESS accessible-for-notify
    STATUS current
    DESCRIPTION
        "Parameter 'rif-data' in event BAN.21"
    ::= { banEventObjects21 8 }

banEventObjects22 OBJECT-IDENTITY
    STATUS current
    DESCRIPTION
        "Event BAN.22
        DM packet."
    ::= { banEventsGroup 22 }

ban22-direction OBJECT-TYPE
    SYNTAX DisplayString
    MAX-ACCESS accessible-for-notify
    STATUS current
    DESCRIPTION
        "Parameter 'direction' in event BAN.22"
    ::= { banEventObjects22 1 }

ban22-bridge-port OBJECT-TYPE
    SYNTAX Integer32
    MAX-ACCESS accessible-for-notify
    STATUS current
    DESCRIPTION
        "Parameter 'bridge-port' in event BAN.22"
    ::= { banEventObjects22 2 }

ban22-len OBJECT-TYPE
    SYNTAX Integer32
    MAX-ACCESS accessible-for-notify
    STATUS current
    DESCRIPTION
        "Parameter 'len' in event BAN.22"
    ::= { banEventObjects22 3 }

ban22-source-mac-address OBJECT-TYPE
    SYNTAX DisplayString
    MAX-ACCESS accessible-for-notify
    STATUS current
    DESCRIPTION
        "Parameter 'source-mac-address' in event BAN.22"
    ::= { banEventObjects22 4 }

ban22-dest-mac-address OBJECT-TYPE
    SYNTAX DisplayString
    MAX-ACCESS accessible-for-notify
    STATUS current
    DESCRIPTION
        "Parameter 'dest-mac-address' in event BAN.22"
    ::= { banEventObjects22 5 }

ban22-source-sap OBJECT-TYPE
    SYNTAX Integer32
    MAX-ACCESS accessible-for-notify
    STATUS current
    DESCRIPTION
        "Parameter 'source-sap' in event BAN.22"
    ::= { banEventObjects22 6 }

ban22-dest-sap OBJECT-TYPE
    SYNTAX Integer32
    MAX-ACCESS accessible-for-notify
    STATUS current
    DESCRIPTION
        "Parameter 'dest-sap' in event BAN.22"
    ::= { banEventObjects22 7 }

ban22-rif-data OBJECT-TYPE
    SYNTAX DisplayString
    MAX-ACCESS accessible-for-notify
    STATUS current
    DESCRIPTION
        "Parameter 'rif-data' in event BAN.22"
    ::= { banEventObjects22 8 }

banEventObjects23 OBJECT-IDENTITY
    STATUS current
    DESCRIPTION
        "Event BAN.23
        DISC packet."
    ::= { banEventsGroup 23 }

ban23-direction OBJECT-TYPE
    SYNTAX DisplayString
    MAX-ACCESS accessible-for-notify
    STATUS current
    DESCRIPTION
        "Parameter 'direction' in event BAN.23"
    ::= { banEventObjects23 1 }

ban23-bridge-port OBJECT-TYPE
    SYNTAX Integer32
    MAX-ACCESS accessible-for-notify
    STATUS current
    DESCRIPTION
        "Parameter 'bridge-port' in event BAN.23"
    ::= { banEventObjects23 2 }

ban23-len OBJECT-TYPE
    SYNTAX Integer32
    MAX-ACCESS accessible-for-notify
    STATUS current
    DESCRIPTION
        "Parameter 'len' in event BAN.23"
    ::= { banEventObjects23 3 }

ban23-source-mac-address OBJECT-TYPE
    SYNTAX DisplayString
    MAX-ACCESS accessible-for-notify
    STATUS current
    DESCRIPTION
        "Parameter 'source-mac-address' in event BAN.23"
    ::= { banEventObjects23 4 }

ban23-dest-mac-address OBJECT-TYPE
    SYNTAX DisplayString
    MAX-ACCESS accessible-for-notify
    STATUS current
    DESCRIPTION
        "Parameter 'dest-mac-address' in event BAN.23"
    ::= { banEventObjects23 5 }

ban23-source-sap OBJECT-TYPE
    SYNTAX Integer32
    MAX-ACCESS accessible-for-notify
    STATUS current
    DESCRIPTION
        "Parameter 'source-sap' in event BAN.23"
    ::= { banEventObjects23 6 }

ban23-dest-sap OBJECT-TYPE
    SYNTAX Integer32
    MAX-ACCESS accessible-for-notify
    STATUS current
    DESCRIPTION
        "Parameter 'dest-sap' in event BAN.23"
    ::= { banEventObjects23 7 }

ban23-rif-data OBJECT-TYPE
    SYNTAX DisplayString
    MAX-ACCESS accessible-for-notify
    STATUS current
    DESCRIPTION
        "Parameter 'rif-data' in event BAN.23"
    ::= { banEventObjects23 8 }

banEventObjects24 OBJECT-IDENTITY
    STATUS current
    DESCRIPTION
        "Event BAN.24
        FRMR packet."
    ::= { banEventsGroup 24 }

ban24-direction OBJECT-TYPE
    SYNTAX DisplayString
    MAX-ACCESS accessible-for-notify
    STATUS current
    DESCRIPTION
        "Parameter 'direction' in event BAN.24"
    ::= { banEventObjects24 1 }

ban24-bridge-port OBJECT-TYPE
    SYNTAX Integer32
    MAX-ACCESS accessible-for-notify
    STATUS current
    DESCRIPTION
        "Parameter 'bridge-port' in event BAN.24"
    ::= { banEventObjects24 2 }

ban24-len OBJECT-TYPE
    SYNTAX Integer32
    MAX-ACCESS accessible-for-notify
    STATUS current
    DESCRIPTION
        "Parameter 'len' in event BAN.24"
    ::= { banEventObjects24 3 }

ban24-source-mac-address OBJECT-TYPE
    SYNTAX DisplayString
    MAX-ACCESS accessible-for-notify
    STATUS current
    DESCRIPTION
        "Parameter 'source-mac-address' in event BAN.24"
    ::= { banEventObjects24 4 }

ban24-dest-mac-address OBJECT-TYPE
    SYNTAX DisplayString
    MAX-ACCESS accessible-for-notify
    STATUS current
    DESCRIPTION
        "Parameter 'dest-mac-address' in event BAN.24"
    ::= { banEventObjects24 5 }

ban24-source-sap OBJECT-TYPE
    SYNTAX Integer32
    MAX-ACCESS accessible-for-notify
    STATUS current
    DESCRIPTION
        "Parameter 'source-sap' in event BAN.24"
    ::= { banEventObjects24 6 }

ban24-dest-sap OBJECT-TYPE
    SYNTAX Integer32
    MAX-ACCESS accessible-for-notify
    STATUS current
    DESCRIPTION
        "Parameter 'dest-sap' in event BAN.24"
    ::= { banEventObjects24 7 }

ban24-rif-data OBJECT-TYPE
    SYNTAX DisplayString
    MAX-ACCESS accessible-for-notify
    STATUS current
    DESCRIPTION
        "Parameter 'rif-data' in event BAN.24"
    ::= { banEventObjects24 8 }

banEventObjects25 OBJECT-IDENTITY
    STATUS current
    DESCRIPTION
        "Event BAN.25
        Other packet than those specifically called out above. Look at the data
        shown to determine exactly what type of frame it is."
    ::= { banEventsGroup 25 }

ban25-direction OBJECT-TYPE
    SYNTAX DisplayString
    MAX-ACCESS accessible-for-notify
    STATUS current
    DESCRIPTION
        "Parameter 'direction' in event BAN.25"
    ::= { banEventObjects25 1 }

ban25-bridge-port OBJECT-TYPE
    SYNTAX Integer32
    MAX-ACCESS accessible-for-notify
    STATUS current
    DESCRIPTION
        "Parameter 'bridge-port' in event BAN.25"
    ::= { banEventObjects25 2 }

ban25-len OBJECT-TYPE
    SYNTAX Integer32
    MAX-ACCESS accessible-for-notify
    STATUS current
    DESCRIPTION
        "Parameter 'len' in event BAN.25"
    ::= { banEventObjects25 3 }

ban25-source-mac-address OBJECT-TYPE
    SYNTAX DisplayString
    MAX-ACCESS accessible-for-notify
    STATUS current
    DESCRIPTION
        "Parameter 'source-mac-address' in event BAN.25"
    ::= { banEventObjects25 4 }

ban25-dest-mac-address OBJECT-TYPE
    SYNTAX DisplayString
    MAX-ACCESS accessible-for-notify
    STATUS current
    DESCRIPTION
        "Parameter 'dest-mac-address' in event BAN.25"
    ::= { banEventObjects25 5 }

ban25-source-sap OBJECT-TYPE
    SYNTAX Integer32
    MAX-ACCESS accessible-for-notify
    STATUS current
    DESCRIPTION
        "Parameter 'source-sap' in event BAN.25"
    ::= { banEventObjects25 6 }

ban25-dest-sap OBJECT-TYPE
    SYNTAX Integer32
    MAX-ACCESS accessible-for-notify
    STATUS current
    DESCRIPTION
        "Parameter 'dest-sap' in event BAN.25"
    ::= { banEventObjects25 7 }

ban25-rif-data OBJECT-TYPE
    SYNTAX DisplayString
    MAX-ACCESS accessible-for-notify
    STATUS current
    DESCRIPTION
        "Parameter 'rif-data' in event BAN.25"
    ::= { banEventObjects25 8 }

banEventObjects26 OBJECT-IDENTITY
    STATUS current
    DESCRIPTION
        "Event BAN.26
        All frames are being dropped. The port has been configured for DLSw
        termination, but DLSw is not running."
    ::= { banEventsGroup 26 }

ban26-bridge-port OBJECT-TYPE
    SYNTAX Integer32
    MAX-ACCESS accessible-for-notify
    STATUS current
    DESCRIPTION
        "Parameter 'bridge-port' in event BAN.26"
    ::= { banEventObjects26 1 }

banEventObjects27 OBJECT-IDENTITY
    STATUS current
    DESCRIPTION
        "Event BAN.27
        The configured BAN bridge port is not a source routing bridge port."
    ::= { banEventsGroup 27 }

ban27-bridge-port OBJECT-TYPE
    SYNTAX Integer32
    MAX-ACCESS accessible-for-notify
    STATUS current
    DESCRIPTION
        "Parameter 'bridge-port' in event BAN.27"
    ::= { banEventObjects27 1 }

banEventObjects28 OBJECT-IDENTITY
    STATUS current
    DESCRIPTION
        "Event BAN.28
        All bridged frames, in and out, are being dropped. The BAN port did not
        initialize."
    ::= { banEventsGroup 28 }

ban28-bridge-port OBJECT-TYPE
    SYNTAX Integer32
    MAX-ACCESS accessible-for-notify
    STATUS current
    DESCRIPTION
        "Parameter 'bridge-port' in event BAN.28"
    ::= { banEventObjects28 1 }

banEventObjects29 OBJECT-IDENTITY
    STATUS current
    DESCRIPTION
        "Event BAN.29
        When SR-TB conversion is enabled on the bridge, the BAN DLCI MAC address
        of the bridging DLCI must be unique. This restriction does not apply if
        SR-TB is disabled."
    ::= { banEventsGroup 29 }

ban29-bridge-port OBJECT-TYPE
    SYNTAX Integer32
    MAX-ACCESS accessible-for-notify
    STATUS current
    DESCRIPTION
        "Parameter 'bridge-port' in event BAN.29"
    ::= { banEventObjects29 1 }

ban29-ban-dlci-address OBJECT-TYPE
    SYNTAX DisplayString
    MAX-ACCESS accessible-for-notify
    STATUS current
    DESCRIPTION
        "Parameter 'ban-dlci-address' in event BAN.29"
    ::= { banEventObjects29 2 }


banNotification1 NOTIFICATION-TYPE
    OBJECTS { 
              ban1-direction, 
              ban1-bridge-port,
              ban1-len,
              ban1-source-mac-address,
              ban1-dest-mac-address,
              ban1-source-sap,
              ban1-dest-sap,
              ban1-rif-data 
            }
    STATUS current
    DESCRIPTION
        "Notification of Event BAN.1

        Message: 'T$1:I-FRAME port=$2 len=$3 $4->$5 $6->$7 $8'

        Parameters list:
              $1: ban1-direction
              $2: ban1-bridge-port
              $3: ban1-len
              $4: ban1-source-mac-address
              $5: ban1-dest-mac-address
              $6: ban1-source-sap
              $7: ban1-dest-sap
              $8: ban1-rif-data

        I-frame packet. Direction is 'in' or 'out' of the router. Shows the
        bridge port number. Shows the full RIF (routing information field) of
        the packet. Shows up to 20 bytes of the packet after the SSAP field.
        The length is the amount of data in the packet after the SSAP field in
        the packet."
    ::= { banNotificationsPrefix 1 }

banNotification2 NOTIFICATION-TYPE
    OBJECTS { 
              ban2-direction, 
              ban2-bridge-port,
              ban2-len,
              ban2-source-mac-address,
              ban2-dest-mac-address,
              ban2-source-sap,
              ban2-dest-sap,
              ban2-rif-data 
            }
    STATUS current
    DESCRIPTION
        "Notification of Event BAN.2

        Message: 'T$1:RR port=$2 len=$3 $4->$5 $6->$7 $8'

        Parameters list:
              $1: ban2-direction
              $2: ban2-bridge-port
              $3: ban2-len
              $4: ban2-source-mac-address
              $5: ban2-dest-mac-address
              $6: ban2-source-sap
              $7: ban2-dest-sap
              $8: ban2-rif-data

        RR packet."
    ::= { banNotificationsPrefix 2 }

banNotification3 NOTIFICATION-TYPE
    OBJECTS { 
              ban3-bridge-port 
            }
    STATUS current
    DESCRIPTION
        "Notification of Event BAN.3

        Message: 'port $1 is not a bridge port'

        Parameters list:
              $1: ban3-bridge-port

        The configured BAN bridge port is not a bridge port."
    ::= { banNotificationsPrefix 3 }

banNotification4 NOTIFICATION-TYPE
    OBJECTS { 
              ban4-bridge-port 
            }
    STATUS current
    DESCRIPTION
        "Notification of Event BAN.4

        Message: 'port $1 initialized'

        Parameters list:
              $1: ban4-bridge-port

        The configured BAN bridge port has been initialized from a BAN point of view."
    ::= { banNotificationsPrefix 4 }

banNotification5 NOTIFICATION-TYPE
    OBJECTS { 
              ban5-source-mac-address, 
              ban5-dest-mac-address,
              ban5-bni-mac,
              ban5-bridge-port 
            }
    STATUS current
    DESCRIPTION
        "Notification of Event BAN.5

        Message: 'frame dropped $1->$2, not BNI source address $3, port $4'

        Parameters list:
              $1: ban5-source-mac-address
              $2: ban5-dest-mac-address
              $3: ban5-bni-mac
              $4: ban5-bridge-port

        Every frame sent by the NCP must match the configured Boundary Node
        Identifier (BNI) MAC address."
    ::= { banNotificationsPrefix 5 }

banNotification6 NOTIFICATION-TYPE
    OBJECTS { 
              ban6-bridge-port 
            }
    STATUS current
    DESCRIPTION
        "Notification of Event BAN.6

        Message: 'port $1 is not a Frame Relay bridge port'

        Parameters list:
              $1: ban6-bridge-port

        The configured BAN bridge port is not a Frame Relay DLCI bridge port."
    ::= { banNotificationsPrefix 6 }

banNotification7 NOTIFICATION-TYPE
    STATUS current
    DESCRIPTION
        "Notification of Event BAN.7

        Message: '---'

        Reserved for possible future use."
    ::= { banNotificationsPrefix 7 }

banNotification8 NOTIFICATION-TYPE
    OBJECTS { 
              ban8-bridge-port, 
              ban8-oui-type 
            }
    STATUS current
    DESCRIPTION
        "Notification of Event BAN.8

        Message: 'frame filtered, port $1, OUI bridge type $2'

        Parameters list:
              $1: ban8-bridge-port
              $2: ban8-oui-type

        The outgoing frame was filtered by BAN because it was NOT an RFC 1490
        bridged Token-Ring frame, without preserved FCS, which is OUI type 9.
        This is the only type of frame expected by the NCP. Another bridge type
        frame is being sent: 1 and 7 are Ethernet, 2 and 8 are 802.4, 3 is
        Token-Ring with FCS, 4 and 10 are FDDI, 11 is 802.6, 14 is
        802.1d Hello BPDU, 15 is SRB Hello BPDU."
    ::= { banNotificationsPrefix 8 }

banNotification9 NOTIFICATION-TYPE
    OBJECTS { 
              ban9-source-mac-address, 
              ban9-dest-mac-address,
              ban9-bridge-port,
              ban9-ban-dlci-address 
            }
    STATUS current
    DESCRIPTION
        "Notification of Event BAN.9

        Message: 'frame filtered $1->$2, port $3, da not BAN DLCI address $4'

        Parameters list:
              $1: ban9-source-mac-address
              $2: ban9-dest-mac-address
              $3: ban9-bridge-port
              $4: ban9-ban-dlci-address

        The outgoing frame was filtered by BAN because the frame's destination
        address did not equal the BAN DLCI address. This is done to protect
        the NCP."
    ::= { banNotificationsPrefix 9 }

banNotification10 NOTIFICATION-TYPE
    OBJECTS { 
              ban10-bridge-port 
            }
    STATUS current
    DESCRIPTION
        "Notification of Event BAN.10

        Message: 'port $1 forcing: TB,STP off'

        Parameters list:
              $1: ban10-bridge-port

        The BAN bridge port behavior is being dynamically forced to transparent
        bridging off, spanning tree off. This is required for BAN."
    ::= { banNotificationsPrefix 10 }

banNotification11 NOTIFICATION-TYPE
    OBJECTS { 
              ban11-bridge-port 
            }
    STATUS current
    DESCRIPTION
        "Notification of Event BAN.11

        Message: 'port $1 DLSw term but DLSw is not in the build'

        Parameters list:
              $1: ban11-bridge-port

        The BAN bridge port is configured for DLSw terminated. However, DLSw
        is not in this build."
    ::= { banNotificationsPrefix 11 }

banNotification12 NOTIFICATION-TYPE
    STATUS current
    DESCRIPTION
        "Notification of Event BAN.12

        Message: '---'

        Reserved for possible future use."
    ::= { banNotificationsPrefix 12 }

banNotification13 NOTIFICATION-TYPE
    OBJECTS { 
              ban13-source-mac-address, 
              ban13-dest-mac-address,
              ban13-bridge-port,
              ban13-segment-ban,
              ban13-rif-data 
            }
    STATUS current
    DESCRIPTION
        "Notification of Event BAN.13

        Message: 'frame filtered $1->$2, port $3, DLSw snbn $4 not in RIF $5'

        Parameters list:
              $1: ban13-source-mac-address
              $2: ban13-dest-mac-address
              $3: ban13-bridge-port
              $4: ban13-segment-ban
              $5: ban13-rif-data

        The outgoing frame was filtered by BAN because the BAN port is set to
        DLSw switching, but the frame was not a DLSw frame since the DLSw
        source routing segment and bridge number were not in the RIF (routing
        information field) of the frame. This is done to protect the NCP."
    ::= { banNotificationsPrefix 13 }

banNotification14 NOTIFICATION-TYPE
    OBJECTS { 
              ban14-direction, 
              ban14-bridge-port,
              ban14-len,
              ban14-source-mac-address,
              ban14-dest-mac-address,
              ban14-source-sap,
              ban14-dest-sap,
              ban14-rif-data 
            }
    STATUS current
    DESCRIPTION
        "Notification of Event BAN.14

        Message: 'T$1:RNR port=$2 len=$3 $4->$5 $6->$7 $8'

        Parameters list:
              $1: ban14-direction
              $2: ban14-bridge-port
              $3: ban14-len
              $4: ban14-source-mac-address
              $5: ban14-dest-mac-address
              $6: ban14-source-sap
              $7: ban14-dest-sap
              $8: ban14-rif-data

        RNR packet."
    ::= { banNotificationsPrefix 14 }

banNotification15 NOTIFICATION-TYPE
    OBJECTS { 
              ban15-direction, 
              ban15-bridge-port,
              ban15-len,
              ban15-source-mac-address,
              ban15-dest-mac-address,
              ban15-source-sap,
              ban15-dest-sap,
              ban15-rif-data 
            }
    STATUS current
    DESCRIPTION
        "Notification of Event BAN.15

        Message: 'T$1:REJ port=$2 len=$3 $4->$5 $6->$7 $8'

        Parameters list:
              $1: ban15-direction
              $2: ban15-bridge-port
              $3: ban15-len
              $4: ban15-source-mac-address
              $5: ban15-dest-mac-address
              $6: ban15-source-sap
              $7: ban15-dest-sap
              $8: ban15-rif-data

        REJ packet."
    ::= { banNotificationsPrefix 15 }

banNotification16 NOTIFICATION-TYPE
    OBJECTS { 
              ban16-direction, 
              ban16-bridge-port,
              ban16-len,
              ban16-source-mac-address,
              ban16-dest-mac-address,
              ban16-source-sap,
              ban16-dest-sap,
              ban16-rif-data 
            }
    STATUS current
    DESCRIPTION
        "Notification of Event BAN.16

        Message: 'T$1:TST-C port=$2 len=$3 $4->$5 $6->$7 $8'

        Parameters list:
              $1: ban16-direction
              $2: ban16-bridge-port
              $3: ban16-len
              $4: ban16-source-mac-address
              $5: ban16-dest-mac-address
              $6: ban16-source-sap
              $7: ban16-dest-sap
              $8: ban16-rif-data

        TEST-C (Test command) packet."
    ::= { banNotificationsPrefix 16 }

banNotification17 NOTIFICATION-TYPE
    OBJECTS { 
              ban17-direction, 
              ban17-bridge-port,
              ban17-len,
              ban17-source-mac-address,
              ban17-dest-mac-address,
              ban17-source-sap,
              ban17-dest-sap,
              ban17-rif-data 
            }
    STATUS current
    DESCRIPTION
        "Notification of Event BAN.17

        Message: 'T$1:TST-R port=$2 len=$3 $4->$5 $6->$7 $8'

        Parameters list:
              $1: ban17-direction
              $2: ban17-bridge-port
              $3: ban17-len
              $4: ban17-source-mac-address
              $5: ban17-dest-mac-address
              $6: ban17-source-sap
              $7: ban17-dest-sap
              $8: ban17-rif-data

        TEST-R (Test response) packet."
    ::= { banNotificationsPrefix 17 }

banNotification18 NOTIFICATION-TYPE
    OBJECTS { 
              ban18-direction, 
              ban18-bridge-port,
              ban18-len,
              ban18-source-mac-address,
              ban18-dest-mac-address,
              ban18-source-sap,
              ban18-dest-sap,
              ban18-rif-data 
            }
    STATUS current
    DESCRIPTION
        "Notification of Event BAN.18

        Message: 'T$1:XID-C port=$2 len=$3 $4->$5 $6->$7 $8'

        Parameters list:
              $1: ban18-direction
              $2: ban18-bridge-port
              $3: ban18-len
              $4: ban18-source-mac-address
              $5: ban18-dest-mac-address
              $6: ban18-source-sap
              $7: ban18-dest-sap
              $8: ban18-rif-data

        XID-C (XID command) packet."
    ::= { banNotificationsPrefix 18 }

banNotification19 NOTIFICATION-TYPE
    OBJECTS { 
              ban19-direction, 
              ban19-bridge-port,
              ban19-len,
              ban19-source-mac-address,
              ban19-dest-mac-address,
              ban19-source-sap,
              ban19-dest-sap,
              ban19-rif-data 
            }
    STATUS current
    DESCRIPTION
        "Notification of Event BAN.19

        Message: 'T$1:XID-R port=$2 len=$3 $4->$5 $6->$7 $8'

        Parameters list:
              $1: ban19-direction
              $2: ban19-bridge-port
              $3: ban19-len
              $4: ban19-source-mac-address
              $5: ban19-dest-mac-address
              $6: ban19-source-sap
              $7: ban19-dest-sap
              $8: ban19-rif-data

        XID-R (XID response) packet."
    ::= { banNotificationsPrefix 19 }

banNotification20 NOTIFICATION-TYPE
    OBJECTS { 
              ban20-direction, 
              ban20-bridge-port,
              ban20-len,
              ban20-source-mac-address,
              ban20-dest-mac-address,
              ban20-source-sap,
              ban20-dest-sap,
              ban20-rif-data 
            }
    STATUS current
    DESCRIPTION
        "Notification of Event BAN.20

        Message: 'T$1:SABME port=$2 len=$3 $4->$5 $6->$7 $8'

        Parameters list:
              $1: ban20-direction
              $2: ban20-bridge-port
              $3: ban20-len
              $4: ban20-source-mac-address
              $5: ban20-dest-mac-address
              $6: ban20-source-sap
              $7: ban20-dest-sap
              $8: ban20-rif-data

        SABME packet."
    ::= { banNotificationsPrefix 20 }

banNotification21 NOTIFICATION-TYPE
    OBJECTS { 
              ban21-direction, 
              ban21-bridge-port,
              ban21-len,
              ban21-source-mac-address,
              ban21-dest-mac-address,
              ban21-source-sap,
              ban21-dest-sap,
              ban21-rif-data 
            }
    STATUS current
    DESCRIPTION
        "Notification of Event BAN.21

        Message: 'T$1:UA port=$2 len=$3 $4->$5 $6->$7 $8'

        Parameters list:
              $1: ban21-direction
              $2: ban21-bridge-port
              $3: ban21-len
              $4: ban21-source-mac-address
              $5: ban21-dest-mac-address
              $6: ban21-source-sap
              $7: ban21-dest-sap
              $8: ban21-rif-data

        UA packet."
    ::= { banNotificationsPrefix 21 }

banNotification22 NOTIFICATION-TYPE
    OBJECTS { 
              ban22-direction, 
              ban22-bridge-port,
              ban22-len,
              ban22-source-mac-address,
              ban22-dest-mac-address,
              ban22-source-sap,
              ban22-dest-sap,
              ban22-rif-data 
            }
    STATUS current
    DESCRIPTION
        "Notification of Event BAN.22

        Message: 'T$1:DM port=$2 len=$3 $4->$5 $6->$7 $8'

        Parameters list:
              $1: ban22-direction
              $2: ban22-bridge-port
              $3: ban22-len
              $4: ban22-source-mac-address
              $5: ban22-dest-mac-address
              $6: ban22-source-sap
              $7: ban22-dest-sap
              $8: ban22-rif-data

        DM packet."
    ::= { banNotificationsPrefix 22 }

banNotification23 NOTIFICATION-TYPE
    OBJECTS { 
              ban23-direction, 
              ban23-bridge-port,
              ban23-len,
              ban23-source-mac-address,
              ban23-dest-mac-address,
              ban23-source-sap,
              ban23-dest-sap,
              ban23-rif-data 
            }
    STATUS current
    DESCRIPTION
        "Notification of Event BAN.23

        Message: 'T$1:DISC port=$2 len=$3 $4->$5 $6->$7 $8'

        Parameters list:
              $1: ban23-direction
              $2: ban23-bridge-port
              $3: ban23-len
              $4: ban23-source-mac-address
              $5: ban23-dest-mac-address
              $6: ban23-source-sap
              $7: ban23-dest-sap
              $8: ban23-rif-data

        DISC packet."
    ::= { banNotificationsPrefix 23 }

banNotification24 NOTIFICATION-TYPE
    OBJECTS { 
              ban24-direction, 
              ban24-bridge-port,
              ban24-len,
              ban24-source-mac-address,
              ban24-dest-mac-address,
              ban24-source-sap,
              ban24-dest-sap,
              ban24-rif-data 
            }
    STATUS current
    DESCRIPTION
        "Notification of Event BAN.24

        Message: 'T$1:FRMR port=$2 len=$3 $4->$5 $6->$7 $8'

        Parameters list:
              $1: ban24-direction
              $2: ban24-bridge-port
              $3: ban24-len
              $4: ban24-source-mac-address
              $5: ban24-dest-mac-address
              $6: ban24-source-sap
              $7: ban24-dest-sap
              $8: ban24-rif-data

        FRMR packet."
    ::= { banNotificationsPrefix 24 }

banNotification25 NOTIFICATION-TYPE
    OBJECTS { 
              ban25-direction, 
              ban25-bridge-port,
              ban25-len,
              ban25-source-mac-address,
              ban25-dest-mac-address,
              ban25-source-sap,
              ban25-dest-sap,
              ban25-rif-data 
            }
    STATUS current
    DESCRIPTION
        "Notification of Event BAN.25

        Message: 'T$1:OTHER port=$2 len=$3 $4->$5 $6->$7 $8'

        Parameters list:
              $1: ban25-direction
              $2: ban25-bridge-port
              $3: ban25-len
              $4: ban25-source-mac-address
              $5: ban25-dest-mac-address
              $6: ban25-source-sap
              $7: ban25-dest-sap
              $8: ban25-rif-data

        Other packet than those specifically called out above. Look at the data
        shown to determine exactly what type of frame it is."
    ::= { banNotificationsPrefix 25 }

banNotification26 NOTIFICATION-TYPE
    OBJECTS { 
              ban26-bridge-port 
            }
    STATUS current
    DESCRIPTION
        "Notification of Event BAN.26

        Message: 'frame dropped, port $1, port is DLSw term, but DLSw is not initialized'

        Parameters list:
              $1: ban26-bridge-port

        All frames are being dropped. The port has been configured for DLSw
        termination, but DLSw is not running."
    ::= { banNotificationsPrefix 26 }

banNotification27 NOTIFICATION-TYPE
    OBJECTS { 
              ban27-bridge-port 
            }
    STATUS current
    DESCRIPTION
        "Notification of Event BAN.27

        Message: 'port $1 is not a source routing bridge port'

        Parameters list:
              $1: ban27-bridge-port

        The configured BAN bridge port is not a source routing bridge port."
    ::= { banNotificationsPrefix 27 }

banNotification28 NOTIFICATION-TYPE
    OBJECTS { 
              ban28-bridge-port 
            }
    STATUS current
    DESCRIPTION
        "Notification of Event BAN.28

        Message: 'frame dropped, port $1, port is not initialized'

        Parameters list:
              $1: ban28-bridge-port

        All bridged frames, in and out, are being dropped. The BAN port did not
        initialize."
    ::= { banNotificationsPrefix 28 }

banNotification29 NOTIFICATION-TYPE
    OBJECTS { 
              ban29-bridge-port, 
              ban29-ban-dlci-address 
            }
    STATUS current
    DESCRIPTION
        "Notification of Event BAN.29

        Message: 'port $1, BAN DLCI address $2 is a duplicate with SR-TB enabled'

        Parameters list:
              $1: ban29-bridge-port
              $2: ban29-ban-dlci-address

        When SR-TB conversion is enabled on the bridge, the BAN DLCI MAC address
        of the bridging DLCI must be unique. This restriction does not apply if
        SR-TB is disabled."
    ::= { banNotificationsPrefix 29 }


END
