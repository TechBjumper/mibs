FN10-MIB DEFINITIONS ::= BEGIN

        --  ctFN10-mib.txt
        --  Revision: 01.01.00
        --  Part Number:
        --  Date: March 26, 1997

        --  Cabletron Systems, Inc.
        --  35 Industrial Way, P.O. Box 5005
        --  Rochester, NH 03867-0505
        --  (603) 332-9400
        --  support@ctron.com

        --  This module provides authoritative definitions for Cabletron's
        --  FastNET 10 mib.
        --
        --  This module will be extended, as required.
        --

        --  Cabletron Systems reserves the right to make changes in
        --  specification and other information contained in this document
        --  without prior notice.  The reader should consult Cabletron Systems
        --  to determine whether any such changes have been made.
        --
        --  In no event shall Cabletron Systems be liable for any incidental,
        --  indirect, special, or consequential damages whatsoever (including
        --  but not limited to lost profits) arising out of or related to this
        --  document or the information contained in it, even if Cabletron
        --  Systems has been advised of, known, or should have known, the
        --  possibility of such damages.
        --
        --  Cabletron grants vendors, end-users, and other interested parties
        --  a non-exclusive license to use this Specification in connection
        --  with the management of Cabletron products.

        --  Copyright (c)1996 Cabletron Systems


IMPORTS

      OBJECT-TYPE
                FROM RFC-1212

      DisplayString, ifOutDiscards, ifInErrors, ifOutErrors
                FROM RFC1213-MIB

      TRAP-TYPE
                FROM RFC-1215

      dot1dStpDesignatedRoot, dot1dStpRootCost, dot1dStpRootPort,
      dot1dStpMaxAge, dot1dStpHelloTime, dot1dStpForwardDelay,
      dot1dStpPortDesignatedRoot, dot1dStpPortDesignatedBridge,
      dot1dStpPortDesignatedCost, dot1dStpPortDesignatedPort,
      dot1dStpPortState
                FROM BRIDGE-MIB

      Counter, Gauge, IpAddress,
      TimeTicks, enterprises
                FROM RFC1155-SMI;


     cmu                OBJECT IDENTIFIER ::= { enterprises 3 }
     sigma              OBJECT IDENTIFIER ::= { enterprises 97 }
     sys                OBJECT IDENTIFIER ::= { sigma 1 }
     es-1xe             OBJECT IDENTIFIER ::= { sigma 2 }
     sxhw               OBJECT IDENTIFIER ::= { es-1xe 1 }
     sxsw               OBJECT IDENTIFIER ::= { es-1xe 2 }
     sxadmin            OBJECT IDENTIFIER ::= { es-1xe 3 }
     sxswdis            OBJECT IDENTIFIER ::= { es-1xe 4 }
     sxaddr             OBJECT IDENTIFIER ::= { es-1xe 5 }
     sxif               OBJECT IDENTIFIER ::= { es-1xe 6 }
     sxdot3             OBJECT IDENTIFIER ::= { es-1xe 7 }
     sxuart             OBJECT IDENTIFIER ::= { es-1xe 8 }
     sxfilter           OBJECT IDENTIFIER ::= { es-1xe 9 }
     sxdebug            OBJECT IDENTIFIER ::= { es-1xe 10 }
     sxlpbk             OBJECT IDENTIFIER ::= { es-1xe 11 }
     sxproto 		OBJECT IDENTIFIER ::= { es-1xe 12 }
     sxtrunk 		OBJECT IDENTIFIER ::= { es-1xe 13 }
     sxworkgroup 	OBJECT IDENTIFIER ::= { es-1xe 14 }
     sxtrapMgt 		OBJECT IDENTIFIER ::= { es-1xe 15 }
     systems            OBJECT IDENTIFIER ::= { cmu 1 }
     mibs               OBJECT IDENTIFIER ::= { cmu 2 }
     cmuSNMP            OBJECT IDENTIFIER ::= { systems 1 }
     cmuKip             OBJECT IDENTIFIER ::= { systems 2 }
     cmuRouter          OBJECT IDENTIFIER ::= { systems 3 }

     sysID OBJECT-TYPE
             SYNTAX  INTEGER {
              es-1xe-bridge(2)
             }
             ACCESS  read-only
             STATUS  mandatory
DESCRIPTION ""
             ::= { sys 1 }

     sysReset        OBJECT-TYPE
             SYNTAX  TimeTicks
             ACCESS  read-write
             STATUS  mandatory
DESCRIPTION ""
             ::= { sys 2 }

     sysTrapAck      OBJECT-TYPE
     SYNTAX  INTEGER {
                 traps-need-acks(1),
                 traps-not-acked(2)
             }
             ACCESS  read-only
             STATUS  mandatory
DESCRIPTION ""
             ::= { sys 3 }

     sysTrapTime     OBJECT-TYPE
             SYNTAX  TimeTicks
             ACCESS  read-only
             STATUS  mandatory
DESCRIPTION ""
             ::= { sys 4 }

     sysTrapRetry OBJECT-TYPE
             SYNTAX  TimeTicks
             ACCESS  read-only
             STATUS  mandatory
DESCRIPTION ""
             ::= { sys 5 }

     sysTrapPort OBJECT-TYPE
             SYNTAX  INTEGER
             ACCESS  read-write
             STATUS  mandatory
DESCRIPTION ""
             ::= { sys 6 }


     -- Trojan HW Configuration Group


     sxhwDiagCode    OBJECT-TYPE
             SYNTAX  OCTET STRING
             ACCESS  read-only
             STATUS  mandatory
DESCRIPTION ""
             ::= { sxhw 1 }

     sxhwManufData   OBJECT-TYPE
             SYNTAX  OCTET STRING
             ACCESS  read-only
             STATUS  mandatory
DESCRIPTION ""
             ::= { sxhw 2 }

     sxhwPortCount   OBJECT-TYPE
             SYNTAX  INTEGER
             ACCESS  read-only
             STATUS  mandatory
DESCRIPTION ""
             ::= { sxhw 3 }

     sxhwPortTable   OBJECT-TYPE
             SYNTAX  SEQUENCE OF SxhwPortEntry
             ACCESS  not-accessible
             STATUS  mandatory
DESCRIPTION ""
             ::= { sxhw 4 }

     sxhwUpLink  OBJECT-TYPE
             SYNTAX  INTEGER { true(1), false(2) }
             ACCESS  read-only
             STATUS  mandatory
             DESCRIPTION
             "Specifies whether the Up-Link I/O module is existed"
             ::= { sxhw 5 }

     sxhwUpLinkManufData OBJECT-TYPE
             SYNTAX  OCTET STRING
             ACCESS  read-only
             STATUS  mandatory
             DESCRIPTION
             "This is a 32-byte array which contains the part number,
             serial number, and hardware revision level of the Up-Link
             I/O module. This array is valid only when the sxhwUplink
             is true. If sxhwUplink is false, it returns an error"
             ::= { sxhw 6 }

     sxhwPortEntry   OBJECT-TYPE
             SYNTAX  SxhwPortEntry
             ACCESS          not-accessible
             STATUS  mandatory
DESCRIPTION ""
     INDEX     { sxhwPortIndex }
             ::= { sxhwPortTable 1 }

     SxhwPortEntry ::= SEQUENCE {
                     sxhwPortIndex
                             INTEGER,
                     sxhwPortType
                             INTEGER,
                     sxhwPortSubType
                             INTEGER,
                     sxhwPortDiagPassed
                             INTEGER,
                     sxhwAddr
                             OCTET STRING
                     }

     sxhwPortIndex   OBJECT-TYPE
             SYNTAX  INTEGER
             ACCESS  read-only
             STATUS  mandatory
DESCRIPTION ""
             ::= { sxhwPortEntry 1 }

     sxhwPortType    OBJECT-TYPE
             SYNTAX  INTEGER {
                     port-csma(1),
                     port-uart(6),
                     port-none(255)
                     }
             ACCESS  read-only
             STATUS  mandatory
DESCRIPTION ""
             ::= { sxhwPortEntry 2 }

     sxhwPortSubType OBJECT-TYPE
             SYNTAX  INTEGER {
                     csmacd-tpx(13),
                     csmacd-aui-tpx(14),
                     csmacd-100-tpx(16),
                     csmacd-100-fx(17),
                     csmacd-100-tp4(18),
                     uart-female-9pin(80),
                     no-information(255)
                     }
             ACCESS  read-only
             STATUS  mandatory
DESCRIPTION ""
             ::= { sxhwPortEntry 3 }

     sxhwPortDiagPassed      OBJECT-TYPE
             SYNTAX  INTEGER {
                     diag-passed(1),
                     diag-failed(2)
                     }
             ACCESS  read-only
             STATUS  mandatory
DESCRIPTION ""
             ::= { sxhwPortEntry 4 }

     sxhwAddr        OBJECT-TYPE
             SYNTAX  OCTET STRING
             ACCESS  read-only
             STATUS  mandatory
DESCRIPTION ""
             ::= { sxhwPortEntry 5 }


-- Trojan SXSW Configuration Group

     sxswNumber      OBJECT-TYPE
             SYNTAX  INTEGER
             ACCESS  read-only
             STATUS  mandatory
DESCRIPTION ""
             ::= { sxsw 1 }

     sxswFilesetTable        OBJECT-TYPE
             SYNTAX  SEQUENCE OF SxswFileset
             ACCESS  not-accessible
             STATUS  mandatory
DESCRIPTION ""
             ::= { sxsw 2 }

     sxswFileset     OBJECT-TYPE
             SYNTAX  SxswFileset
             ACCESS  not-accessible
             STATUS  mandatory
DESCRIPTION ""
     INDEX { sxswIndex }
             ::= { sxswFilesetTable 1 }

     SxswFileset ::= SEQUENCE {
                     sxswIndex     INTEGER,
                     sxswDesc      DisplayString,
                     sxswCount     INTEGER,
                     sxswType      OCTET STRING,
                     sxswSizes     OCTET STRING,
                     sxswStarts    OCTET STRING,
                     sxswBases     OCTET STRING,
                     sxswFlashBank INTEGER
                     }

     sxswIndex       OBJECT-TYPE
             SYNTAX  INTEGER
                        {
                        currently-executing(1),
                        next-boot(2)
                        }
             ACCESS  read-only
             STATUS  mandatory
DESCRIPTION ""
             ::= { sxswFileset 1 }

     sxswDesc        OBJECT-TYPE
             SYNTAX  DisplayString
             ACCESS  read-only
             STATUS  mandatory
DESCRIPTION ""
             ::= { sxswFileset 2 }

     sxswCount       OBJECT-TYPE
             SYNTAX  INTEGER
             ACCESS  read-only
             STATUS  mandatory
DESCRIPTION ""
             ::= { sxswFileset 3 }

     sxswType                OBJECT-TYPE
             SYNTAX  OCTET STRING
          --   { file-nam(1),
          --     file-be(2),
          --     file-powerup(10),
          --     file-diagnostics(11)
          --   }
             ACCESS  read-only
             STATUS  mandatory
DESCRIPTION ""
             ::= { sxswFileset 4 }

     sxswSizes       OBJECT-TYPE
             SYNTAX  OCTET STRING
             ACCESS  read-only
             STATUS  mandatory
DESCRIPTION ""
             ::= { sxswFileset 5 }

     sxswStarts      OBJECT-TYPE
             SYNTAX  OCTET STRING
             ACCESS  read-only
             STATUS  mandatory
DESCRIPTION ""
             ::= { sxswFileset 6 }

     sxswBases       OBJECT-TYPE
             SYNTAX  OCTET STRING
             ACCESS  read-only
             STATUS  mandatory
DESCRIPTION ""
             ::= { sxswFileset 7 }

     sxswFlashBank   OBJECT-TYPE
             SYNTAX  INTEGER
                     {
                     first-bank(1),
                     second-bank(2)
                     }
             ACCESS  read-only
             STATUS  mandatory
DESCRIPTION ""
             ::= { sxswFileset 8 }



	-- SXADMIN Group

     sxadminFatalErr         OBJECT-TYPE
             SYNTAX  OCTET STRING
             ACCESS  read-only
             STATUS  mandatory
DESCRIPTION ""
             ::= { sxadmin 1 }

     sxadminAnyPass  OBJECT-TYPE
             SYNTAX   OCTET STRING
             ACCESS   read-write
             STATUS   mandatory
DESCRIPTION ""
             ::= { sxadmin 2 }

     sxadminGetPass  OBJECT-TYPE
             SYNTAX   OCTET STRING
             ACCESS   read-write
             STATUS   mandatory
DESCRIPTION ""
             ::= { sxadmin 3 }

     sxadminNMSIPAddr OBJECT-TYPE
             SYNTAX  IpAddress
             ACCESS  read-write
             STATUS  mandatory
DESCRIPTION ""
             ::= { sxadmin 4 }

     sxadminAlarmDynamic OBJECT-TYPE
             SYNTAX  INTEGER { true(1), false(2) }
             ACCESS  read-only
             STATUS  mandatory
DESCRIPTION ""
             ::= { sxadmin 5 }

     sxadminAlarmAddressChange OBJECT-TYPE
             SYNTAX  INTEGER { true(1), false(2) }
             ACCESS  read-only
             STATUS  mandatory
DESCRIPTION ""
             ::= { sxadmin 6 }

     sxadminStorageFailure OBJECT-TYPE
             SYNTAX  INTEGER { true(1), false(2) }
             ACCESS   read-only
             STATUS   mandatory
DESCRIPTION ""
             ::= { sxadmin 7 }

     sxadminAuthenticationFailure OBJECT-TYPE
             SYNTAX   IpAddress
             ACCESS   read-only
             STATUS   mandatory
DESCRIPTION ""
             ::= { sxadmin 8 }

     sxadminStatsExtended OBJECT-TYPE
             SYNTAX  INTEGER { true(1), false(2) }
             ACCESS   read-write
             STATUS   mandatory
DESCRIPTION ""
             ::= { sxadmin 9 }

     sxadminNAMReceiveCongests  OBJECT-TYPE
             SYNTAX   Counter
             ACCESS   read-only
             STATUS   mandatory
DESCRIPTION ""
             ::= { sxadmin 10 }

     sxadminArpEntries  OBJECT-TYPE
             SYNTAX   Counter
             ACCESS   read-only
             STATUS   mandatory
DESCRIPTION ""
             ::= { sxadmin 11 }

     sxadminArpStatics OBJECT-TYPE
             SYNTAX  Counter
             ACCESS  read-only
             STATUS  mandatory
DESCRIPTION ""
             ::= { sxadmin 12 }

     sxadminArpOverflows   OBJECT-TYPE
             SYNTAX   Counter
             ACCESS   read-only
             STATUS   mandatory
DESCRIPTION ""
             ::= { sxadmin 13 }

     sxadminIpEntries   OBJECT-TYPE
             SYNTAX   Counter
             ACCESS   read-only
             STATUS   mandatory
DESCRIPTION ""
             ::= { sxadmin 14 }

     sxadminIpStatics   OBJECT-TYPE
             SYNTAX   Counter
             ACCESS   read-only
             STATUS   mandatory
DESCRIPTION ""
             ::= { sxadmin 15 }

     sxadminStaticPreference  OBJECT-TYPE
             SYNTAX  INTEGER
             ACCESS  read-write
             STATUS  mandatory
DESCRIPTION ""
             ::= { sxadmin 16 }

     sxadminRipPreference  OBJECT-TYPE
             SYNTAX   INTEGER
             ACCESS   read-write
             STATUS   mandatory
DESCRIPTION ""
             ::= { sxadmin 17 }

     sxadminRipRouteDiscards  OBJECT-TYPE
             SYNTAX   Counter
             ACCESS   read-only
             STATUS   mandatory
DESCRIPTION ""
             ::= { sxadmin 18 }

     sxadminRebootConfig   OBJECT-TYPE
             SYNTAX  INTEGER
                     {
                     no-change(1),
                     tftp-config(2),
                     revert-to-defaults(3)
                     }
             ACCESS  read-write
             STATUS  mandatory
DESCRIPTION ""
             ::= { sxadmin 19 }

     sxadminTempOK OBJECT-TYPE
             SYNTAX  INTEGER
                     {
                     temperature-normal(1),
                     temperature-too-hot(2)
                     }
             ACCESS   read-only
             STATUS  mandatory
DESCRIPTION ""
             ::= { sxadmin 20 }

     sxadminDisableButton    OBJECT-TYPE
             SYNTAX  INTEGER  { true(1), false(2) }
             ACCESS  read-write
             STATUS  mandatory
DESCRIPTION ""
             ::= { sxadmin 21 }

     sxadminButtonSelection  OBJECT-TYPE
             SYNTAX  INTEGER
                     {
                     led-any-activity(1),
                     led-rx-activity(2),
                     led-tx-activity(3),
                     led-any-collision(4),
                     led-programmed(5)
                     }
             ACCESS  read-write
             STATUS  mandatory
DESCRIPTION ""
             ::= { sxadmin 22 }

     sxadminLEDProgramOption OBJECT-TYPE
             SYNTAX  INTEGER
                     {
                     program-led-any-error(1)
                     }
             ACCESS  read-write
             STATUS  mandatory
DESCRIPTION ""
             ::= { sxadmin 23 }

     sxadminNAMTxBufferCount         OBJECT-TYPE
             SYNTAX  INTEGER
             ACCESS  read-write
             STATUS  mandatory
DESCRIPTION ""
             ::= { sxadmin 24 }

     sxadminNAMRxBufferSize  OBJECT-TYPE
             SYNTAX   INTEGER
             ACCESS   read-write
             STATUS   mandatory
DESCRIPTION ""
             ::= { sxadmin 25 }

     sxadminCpuUtilization OBJECT-TYPE
             SYNTAX   INTEGER { low-cpu(1), medium-cpu(2), high-cpu(3) }
             ACCESS   read-only
             STATUS   mandatory
DESCRIPTION ""
             ::= { sxadmin 26 }

     sxadminExtraTrunkGrouping  OBJECT-TYPE
             SYNTAX   INTEGER { true(1), false(2) }
             ACCESS   read-write
             STATUS   mandatory
             DESCRIPTION
             "If true(1), then as many as 8 trunk groups may be created,
              rather than the default limit of 4 trunk groups.  When true(1),
              fewer links will be allowed in each trunk group, i.e., a maximum
              of 4 links will be used in each trunk group, instead of the
              default limit of 8 links per trunk group."
             ::= { sxadmin 27 }

-- Software Distribution Group

     sxswdisDesc     OBJECT-TYPE
             SYNTAX  OCTET STRING
             ACCESS  read-only
             STATUS  mandatory
             DESCRIPTION
             "The description (0-32 bytes) of the software set currently
             being downloaded, or a description of the software set last
             downloaded since the last boot."
             ::= { sxswdis 1 }

     sxswdisAccess   OBJECT-TYPE
             SYNTAX  INTEGER
                     {
                     protected(1),
                     any-software(2)
                     }
             ACCESS  read-write
             STATUS  mandatory
             DESCRIPTION
             "The version of software that may be downloaded. Attempts to
             download other versions of software will be rejected. The
             value for swdisAccess is embedded within the software files
             that are to be distributed via TFTP. Its value may be
             derived from the names of the software files. the NMS operator
             may wish to use the following special values:
             protected (1)  No software downloads will be accepted
             any-software (2)  A software download of any version of new
             software will be accepted - this is the factory default"
             ::= { sxswdis 2 }

     sxswdisWriteStatus      OBJECT-TYPE
             SYNTAX  INTEGER
                     {
                     in-progress(1),
                     success(2),
                     config-error(3),
                     flash-error(4),
                     config-and-flash-errors(5)
                     }
             ACCESS  read-only
             STATUS  mandatory
             DESCRIPTION
             "The status of the erase/write operation."
             ::= { sxswdis 3 }

     sxswdisConfigIp OBJECT-TYPE
             SYNTAX  IpAddress
             ACCESS  read-write
             STATUS  mandatory
             DESCRIPTION
             "The IP address of the NMS (i.e., any IP host) that is allowed
             to use TFTP to send/retrieve the configuration file of the
             device. A value of 0.0.0.0 (which is the factory specified
             default) prevents any NMS from obtaining access, while a
             value of 255.255.255.255 gives every NMS permission."
             ::= { sxswdis 4 }

     sxswdisConfigRetryTime  OBJECT-TYPE
             SYNTAX  INTEGER
             ACCESS  read-write
             STATUS  mandatory
             DESCRIPTION
             "The number of seconds that the device will wait for an
              acknowledgment before it retransmits an unacknowledged TFTP
              data block. The factory specified default is 5 seconds."
             ::= { sxswdis 5 }

     sxswdisConfigTotalTimeout       OBJECT-TYPE
             SYNTAX  INTEGER
             ACCESS  read-write
             STATUS  mandatory
             DESCRIPTION
             "The number of seconds that the device will wait for an
              acknowledgment to a data block before it cancels a TFTP
              session. The factory specified default is 25 seconds."
             ::= { sxswdis 6 }

-- Address Configuration

     sxaddrStatics   OBJECT-TYPE
             SYNTAX   Counter
             ACCESS  read-only
             STATUS  mandatory
DESCRIPTION ""
             ::= { sxaddr 1 }

     sxaddrDynamics  OBJECT-TYPE
             SYNTAX  Counter
             ACCESS  read-only
             STATUS  mandatory
DESCRIPTION ""
             ::= { sxaddr 2 }

     sxaddrDynamicMax        OBJECT-TYPE
             SYNTAX  Gauge
             ACCESS  read-write
             STATUS  mandatory
DESCRIPTION ""
             ::= { sxaddr 3 }

     sxaddrDynamicOverflows  OBJECT-TYPE
             SYNTAX  Counter
             ACCESS  read-only
             STATUS  mandatory
DESCRIPTION ""
             ::= { sxaddr 4 }

     sxaddrFlags     OBJECT-TYPE
             SYNTAX  INTEGER
             ACCESS  read-write
             STATUS  mandatory
DESCRIPTION ""
             ::= { sxaddr 5 }

     sxaddrMAC       OBJECT-TYPE
             SYNTAX  OCTET STRING
             ACCESS  read-write
             STATUS  mandatory
DESCRIPTION ""
             ::= { sxaddr 6 }

     sxaddrPort      OBJECT-TYPE
             SYNTAX  INTEGER
             ACCESS  read-write
             STATUS  mandatory
DESCRIPTION ""
             ::= { sxaddr 7 }


     sxaddrOperation OBJECT-TYPE
     SYNTAX  INTEGER {
                 read-random(1),
                 read-next(2),
                 zero-stats(3),
                 update(4),
                 delete(5),
                 read-block(6)
             }
             ACCESS  read-write
             STATUS  mandatory
DESCRIPTION ""
             ::= { sxaddr 8 }

     sxaddrIndex     OBJECT-TYPE
             SYNTAX  INTEGER
             ACCESS  read-write
             STATUS  mandatory
DESCRIPTION ""
             ::= { sxaddr 9 }

     sxaddrNext      OBJECT-TYPE
             SYNTAX  INTEGER
             ACCESS  read-write
             STATUS  mandatory
DESCRIPTION ""
             ::= { sxaddr 10 }

     sxaddrAge       OBJECT-TYPE
             SYNTAX  TimeTicks
             ACCESS  read-write
             STATUS  mandatory
DESCRIPTION ""
             ::= { sxaddr 11 }

     sxaddrDestAge   OBJECT-TYPE
             SYNTAX  TimeTicks
             ACCESS  read-write
             STATUS  mandatory
DESCRIPTION ""
             ::= { sxaddr 12 }

     sxaddrRxPkts    OBJECT-TYPE
             SYNTAX  Counter
             ACCESS  read-write
             STATUS  mandatory
DESCRIPTION ""
             ::= { sxaddr 13 }

     sxaddrRxChars   OBJECT-TYPE
             SYNTAX  Counter
             ACCESS  read-write
             STATUS  mandatory
DESCRIPTION ""
             ::= { sxaddr 14 }

     sxaddrRxMultiPkts       OBJECT-TYPE
             SYNTAX  Counter
             ACCESS  read-write
             STATUS  mandatory
DESCRIPTION ""
             ::= { sxaddr 15 }

     sxaddrRxFwdPkts OBJECT-TYPE
             SYNTAX  Counter
             ACCESS  read-write
             STATUS  mandatory
DESCRIPTION ""
             ::= { sxaddr 16 }

     sxaddrTxPkts    OBJECT-TYPE
             SYNTAX  Counter
             ACCESS  read-write
             STATUS  mandatory
DESCRIPTION ""
             ::= { sxaddr 17 }

     sxaddrTxChars   OBJECT-TYPE
             SYNTAX  Counter
             ACCESS  read-write
             STATUS  mandatory
DESCRIPTION ""
             ::= { sxaddr 18 }

     sxaddrBlockSize OBJECT-TYPE
             SYNTAX  INTEGER
             ACCESS  read-write
             STATUS  mandatory
DESCRIPTION ""
             ::= { sxaddr 19 }

     sxaddrBlock     OBJECT-TYPE
             SYNTAX  OCTET STRING
             ACCESS  read-write
             STATUS  mandatory
DESCRIPTION ""
             ::= { sxaddr 20 }

     sxaddrAlarmMAC  OBJECT-TYPE
             SYNTAX  OCTET STRING
             ACCESS  read-only
             STATUS  mandatory
DESCRIPTION ""
             ::= { sxaddr 21 }


-- SMC Interfaces (sxif) Group


     sxifTable       OBJECT-TYPE
             SYNTAX  SEQUENCE OF SxifEntry
             ACCESS  not-accessible
             STATUS  mandatory
DESCRIPTION ""
             ::= { sxif 1  }

     sxifEntry       OBJECT-TYPE
             SYNTAX  SxifEntry
             ACCESS  not-accessible
             STATUS  mandatory
DESCRIPTION ""
     INDEX { sxifIndex }
             ::= { sxifTable 1 }

     SxifEntry ::= SEQUENCE {
                   sxifIndex                  INTEGER,
                   sxifRxCnt                  INTEGER,
                   sxifTxCnt                  INTEGER,
                   sxifThreshold              INTEGER,
                   sxifThresholdTime          TimeTicks,
                   sxifRxQueueThresh          INTEGER,
                   sxifRxQueueThreshTime      TimeTicks,
                   sxifTxStormCnt             INTEGER,
                   sxifTxStormTime            TimeTicks,
                   sxifFilterFloodSourceSame  INTEGER,
                   sxifFilterAllSourceLearned INTEGER,
                   sxifFilterNoLearning       INTEGER,
                   sxifFilterAllDestLearned   INTEGER,
                   sxifCongestTime            TimeTicks,
                   sxifQueueTime              TimeTicks,
                   sxifFunction               INTEGER,
                   sxifRxPacket               OCTET STRING,
                   sxifRxHwFCSs               Counter,
                   sxifRxQueues               Counter,
                   sxifTxPacket               OCTET STRING,
                   sxifTxStorms               Counter,
                   sxifTxDests                Counter,
                   sxifLan1                   INTEGER,
                   sxifLan2                   INTEGER,
                   sxifLan3                   INTEGER,
                   sxifLan4                   INTEGER,
                   sxifStatisticsTime         TimeTicks,
                   sxifIpAddr                 IpAddress,
                   sxifIpGroupAddr            IpAddress,
                   sxifForwardedChars         Counter,
                   sxifFilteredChars          Counter,
                   sxifDescr                  DisplayString
                   }

     sxifIndex       OBJECT-TYPE
             SYNTAX  INTEGER
             ACCESS  read-only
             STATUS  mandatory
DESCRIPTION ""
             ::= { sxifEntry 1 }

     sxifRxCnt       OBJECT-TYPE
             SYNTAX  INTEGER
             ACCESS  read-only
             STATUS  mandatory
DESCRIPTION ""
             ::= { sxifEntry 2 }

     sxifTxCnt       OBJECT-TYPE
             SYNTAX  INTEGER
             ACCESS  read-only
             STATUS  mandatory
DESCRIPTION ""
             ::= { sxifEntry 3 }

     sxifThreshold   OBJECT-TYPE
             SYNTAX  INTEGER
             ACCESS  read-write
             STATUS  mandatory
DESCRIPTION ""
             ::= { sxifEntry 4 }

     sxifThresholdTime       OBJECT-TYPE
             SYNTAX  TimeTicks
             ACCESS  read-write
             STATUS  mandatory
DESCRIPTION ""
             ::= { sxifEntry 5 }

     sxifRxQueueThresh       OBJECT-TYPE
             SYNTAX  INTEGER
             ACCESS  read-write
             STATUS  mandatory
DESCRIPTION ""
             ::= { sxifEntry 6 }

     sxifRxQueueThreshTime   OBJECT-TYPE
             SYNTAX  TimeTicks
             ACCESS  read-write
             STATUS  mandatory
DESCRIPTION ""
             ::= { sxifEntry 7 }

     sxifTxStormCnt  OBJECT-TYPE
             SYNTAX  INTEGER
             ACCESS  read-write
             STATUS  mandatory
DESCRIPTION ""
             ::= { sxifEntry 8 }

     sxifTxStormTime OBJECT-TYPE
             SYNTAX  TimeTicks
             ACCESS  read-write
             STATUS  mandatory
DESCRIPTION ""
             ::= { sxifEntry 9 }

     sxifFilterFloodSourceSame       OBJECT-TYPE
             SYNTAX  INTEGER { true(1), false(2) }
             ACCESS  read-write
             STATUS  mandatory
DESCRIPTION ""
             ::= { sxifEntry 10 }

     sxifFilterAllSourceLearned      OBJECT-TYPE
             SYNTAX  INTEGER { true(1), false(2) }
             ACCESS  read-write
             STATUS  mandatory
DESCRIPTION ""
             ::= { sxifEntry 11 }

     sxifFilterNoLearning    OBJECT-TYPE
             SYNTAX  INTEGER { true(1), false(2) }
             ACCESS  read-write
             STATUS  mandatory
DESCRIPTION ""
             ::= { sxifEntry 12 }

     sxifFilterAllDestLearned        OBJECT-TYPE
             SYNTAX  INTEGER { true(1), false(2) }
             ACCESS  read-write
             STATUS  mandatory
DESCRIPTION ""
             ::= { sxifEntry 13 }

     sxifCongestTime OBJECT-TYPE
             SYNTAX  TimeTicks
             ACCESS  read-write
             STATUS  mandatory
DESCRIPTION ""
             ::= { sxifEntry 14 }

     sxifQueueTime   OBJECT-TYPE
             SYNTAX  TimeTicks
             ACCESS  read-write
             STATUS  mandatory
DESCRIPTION ""
             ::= { sxifEntry 15 }

     sxifFunction    OBJECT-TYPE
             SYNTAX  INTEGER
             ACCESS  read-only
             STATUS  mandatory
DESCRIPTION ""
             ::= { sxifEntry 16 }

     sxifRxPacket    OBJECT-TYPE
             SYNTAX  OCTET STRING
             ACCESS  read-only
             STATUS  mandatory
DESCRIPTION ""
             ::= { sxifEntry 17 }

     sxifRxHwFCSs    OBJECT-TYPE
             SYNTAX  Counter
             ACCESS  read-only
             STATUS  mandatory
DESCRIPTION ""
             ::= { sxifEntry 18 }

     sxifRxQueues    OBJECT-TYPE
             SYNTAX  Counter
             ACCESS  read-only
             STATUS  mandatory
DESCRIPTION ""
             ::= { sxifEntry 19 }

     sxifTxPacket    OBJECT-TYPE
             SYNTAX  OCTET STRING
             ACCESS  read-only
             STATUS  mandatory
DESCRIPTION ""
             ::= { sxifEntry 20 }

     sxifTxStorms    OBJECT-TYPE
             SYNTAX  Counter
             ACCESS  read-only
             STATUS  mandatory
DESCRIPTION ""
             ::= { sxifEntry 21 }

     sxifTxDests     OBJECT-TYPE
             SYNTAX  Counter
             ACCESS  read-only
             STATUS  mandatory
DESCRIPTION ""
             ::= { sxifEntry 22 }

     sxifLan1        OBJECT-TYPE
             SYNTAX  INTEGER
             ACCESS  read-write
             STATUS  mandatory
DESCRIPTION ""
             ::= { sxifEntry 23 }

     sxifLan2        OBJECT-TYPE
             SYNTAX  INTEGER
             ACCESS  read-write
             STATUS  mandatory
DESCRIPTION ""
             ::= { sxifEntry 24 }

     sxifLan3        OBJECT-TYPE
             SYNTAX  INTEGER
             ACCESS  read-write
             STATUS  mandatory
DESCRIPTION ""
             ::= { sxifEntry 25 }

     sxifLan4        OBJECT-TYPE
             SYNTAX  INTEGER
             ACCESS  read-write
             STATUS  mandatory
DESCRIPTION ""
             ::= { sxifEntry 26 }

     sxifStatisticsTime      OBJECT-TYPE
             SYNTAX  TimeTicks
             ACCESS  read-only
             STATUS  mandatory
DESCRIPTION ""
             ::= { sxifEntry 27 }

     sxifIpAddr      OBJECT-TYPE
             SYNTAX  IpAddress
             ACCESS  read-write
             STATUS  mandatory
DESCRIPTION ""
             ::= { sxifEntry 28 }

     sxifIpGroupAddr OBJECT-TYPE
             SYNTAX  IpAddress
             ACCESS  read-write
             STATUS  mandatory
DESCRIPTION ""
             ::= { sxifEntry 29 }

     sxifForwardedChars      OBJECT-TYPE
     SYNTAX  Counter
             ACCESS  read-only
             STATUS  mandatory
DESCRIPTION ""
             ::= { sxifEntry 30 }

     sxifFilteredChars       OBJECT-TYPE
     SYNTAX  Counter
             ACCESS  read-only
             STATUS  mandatory
DESCRIPTION ""
             ::= { sxifEntry 31 }

     sxifDescr OBJECT-TYPE
     SYNTAX  DisplayString
     ACCESS  read-write
     STATUS  mandatory
DESCRIPTION ""
     ::= { sxifEntry 32 }

-- SMC Dot3 Group

     sxdot3Table     OBJECT-TYPE
             SYNTAX  SEQUENCE OF Sxdot3Entry
             ACCESS  not-accessible
             STATUS  mandatory
DESCRIPTION ""
             ::= { sxdot3 1 }

     sxdot3Entry     OBJECT-TYPE
             SYNTAX  Sxdot3Entry
             ACCESS  not-accessible
             STATUS  mandatory
DESCRIPTION ""
     INDEX { sxdot3Index }
             ::= { sxdot3Table 1 }


     Sxdot3Entry ::= SEQUENCE {
                     sxdot3Index          INTEGER,
                     sxdot3TPLinkOK       INTEGER,
                     sxdot3LedOn          INTEGER,
                     sxdot3RxCollisions   Counter,
                     sxdot3RxRunts        Counter,
                     sxdot3RxLateColls    Counter,
                     sxdot3TxJabbers      Counter,
                     sxdot3TxBabbles      Counter,
                     sxdot3TxCollisions   Counter,
                     sxdot3RxErrInfo      OCTET STRING,
                     sxdot3TxErrInfo      OCTET STRING,
                     sxdot3FuseOkay       INTEGER,
                     sxdot3SpeedSelection INTEGER
                     }

     sxdot3Index     OBJECT-TYPE
             SYNTAX  INTEGER
             ACCESS  read-only
             STATUS  mandatory
DESCRIPTION ""
             ::= { sxdot3Entry 1 }

     sxdot3TPLinkOK  OBJECT-TYPE
             SYNTAX  INTEGER { true(1), false(2) }
             ACCESS  read-only
             STATUS  mandatory
DESCRIPTION ""
             ::= { sxdot3Entry 2 }

     sxdot3LedOn     OBJECT-TYPE
             SYNTAX  INTEGER { led-on(1), led-off(2) }
             ACCESS  read-only
             STATUS  mandatory
DESCRIPTION ""
             ::= { sxdot3Entry 3 }

     sxdot3RxCollisions      OBJECT-TYPE
             SYNTAX  Counter
             ACCESS  read-only
             STATUS  mandatory
DESCRIPTION ""
             ::= { sxdot3Entry 4 }

     sxdot3RxRunts   OBJECT-TYPE
             SYNTAX  Counter
             ACCESS  read-only
             STATUS  mandatory
DESCRIPTION ""
             ::= { sxdot3Entry 5 }

     sxdot3RxLateColls       OBJECT-TYPE
             SYNTAX  Counter
             ACCESS  read-only
             STATUS  mandatory
DESCRIPTION ""
             ::= { sxdot3Entry 6 }

     sxdot3TxJabbers OBJECT-TYPE
             SYNTAX  Counter
             ACCESS  read-only
             STATUS  mandatory
DESCRIPTION ""
             ::= { sxdot3Entry 7 }

     sxdot3TxBabbles OBJECT-TYPE
             SYNTAX  Counter
             ACCESS  read-only
             STATUS  mandatory
DESCRIPTION ""
             ::= { sxdot3Entry 8 }

     sxdot3TxCollisions      OBJECT-TYPE
             SYNTAX  Counter
             ACCESS  read-only
             STATUS  mandatory
DESCRIPTION ""
             ::= { sxdot3Entry 9 }

     sxdot3RxErrInfo OBJECT-TYPE
             SYNTAX  OCTET STRING
             ACCESS  read-only
             STATUS  mandatory
DESCRIPTION ""
             ::= { sxdot3Entry 10 }

     sxdot3TxErrInfo OBJECT-TYPE
             SYNTAX  OCTET STRING
             ACCESS  read-only
             STATUS  mandatory
DESCRIPTION ""
             ::= { sxdot3Entry 11 }

     sxdot3FuseOkay  OBJECT-TYPE
             SYNTAX  INTEGER { true(1), false(2) }
             ACCESS  read-only
             STATUS  mandatory
DESCRIPTION ""
             ::= { sxdot3Entry 12 }

     sxdot3SpeedSelection    OBJECT-TYPE
             SYNTAX  INTEGER { speed-10mbit(1), speed-100mbit(2) }
             ACCESS  read-write
             STATUS  mandatory
DESCRIPTION ""
             ::= { sxdot3Entry 13 }

-- SMC SXUART Interface Group

     sxuartTable     OBJECT-TYPE
             SYNTAX  SEQUENCE OF SxuartEntry
             ACCESS  not-accessible
             STATUS  mandatory
DESCRIPTION ""
             ::= { sxuart 1 }

     sxuartEntry     OBJECT-TYPE
             SYNTAX  SxuartEntry
             ACCESS  not-accessible
             STATUS  mandatory
DESCRIPTION ""
     INDEX { sxuartIndex }
             ::= { sxuartTable 1 }

     SxuartEntry ::= SEQUENCE {
                     sxuartIndex           INTEGER,
                     sxuartBaud            INTEGER,
                     sxuartAlignmentErrors Counter,
                     sxuartOverrunErrors   Counter
                     }

     sxuartIndex     OBJECT-TYPE
             SYNTAX  INTEGER
             ACCESS  read-only
             STATUS  mandatory
DESCRIPTION ""
             ::= { sxuartEntry 1 }

     sxuartBaud      OBJECT-TYPE
     SYNTAX  INTEGER {
                 external-clock(1),
                 b1200-baud(2),
                 b2400-baud(3),
                 b4800-baud(4),
                 b9600-baud(5),
                 b19200-baud(6),
                 b38400-baud(7),
                 b56-kilobits(8),
                 b1544-kilobits(9),
                 b2048-kilobits(10),
                 b45-megabits(11)
             }
             ACCESS  read-write
             STATUS  mandatory
DESCRIPTION ""
             ::= { sxuartEntry 2 }

     sxuartAlignmentErrors   OBJECT-TYPE
             SYNTAX  Counter
             ACCESS  read-only
             STATUS  mandatory
DESCRIPTION ""
             ::= { sxuartEntry 3 }

     sxuartOverrunErrors     OBJECT-TYPE
             SYNTAX  Counter
             ACCESS  read-only
             STATUS  mandatory
DESCRIPTION ""
             ::= { sxuartEntry 4 }

     -- sxFilter Group

     sxfilterMaxCount        OBJECT-TYPE
             SYNTAX  INTEGER
             ACCESS  read-only
             STATUS  mandatory
DESCRIPTION ""
             ::= { sxfilter 1 }

     sxfilterCurrentCount    OBJECT-TYPE
             SYNTAX  INTEGER
             ACCESS  read-only
             STATUS  mandatory
DESCRIPTION ""
             ::= { sxfilter 2 }

     sxfilterDeleteID        OBJECT-TYPE
             SYNTAX  INTEGER
             ACCESS  read-write
             STATUS  mandatory
DESCRIPTION ""
             ::= { sxfilter 3 }

     sxfilterNextID  OBJECT-TYPE
             SYNTAX  INTEGER
             ACCESS  read-only
             STATUS  mandatory
DESCRIPTION ""
             ::= { sxfilter 4 }

     sxfilterAddID   OBJECT-TYPE
             SYNTAX  INTEGER
             ACCESS  read-write
             STATUS  mandatory
DESCRIPTION ""
             ::= { sxfilter 5 }

     sxfilterAddIndex        OBJECT-TYPE
             SYNTAX  INTEGER
             ACCESS  read-write
             STATUS  mandatory
DESCRIPTION ""
             ::= { sxfilter 6 }

     sxfilterTable   OBJECT-TYPE
             SYNTAX  SEQUENCE OF SxfilterEntry
             ACCESS  not-accessible
             STATUS  mandatory
DESCRIPTION ""
             ::= { sxfilter 7 }

     sxfilterEntry   OBJECT-TYPE
             SYNTAX  SxfilterEntry
             ACCESS  not-accessible
             STATUS  mandatory
DESCRIPTION ""
     INDEX { sxfilterIndex }
             ::= { sxfilterTable 1 }

     SxfilterEntry ::= SEQUENCE {
                     sxfilterIndex      INTEGER,
                     sxfilterID         INTEGER,
                     sxfilterPortNo     INTEGER,
                     sxfilterComboType  INTEGER,
                     sxfilterFlags      INTEGER,
                     sxfilterFrame      INTEGER,
                     sxfilterSource     OCTET STRING,
                     sxfilterSourceEnd  OCTET STRING,
                     sxfilterDest       OCTET STRING,
                     sxfilterDestEnd    OCTET STRING,
                     sxfilterSourceMask OCTET STRING,
                     sxfilterDestMask   OCTET STRING,
                     sxfilterSrcLan     INTEGER,
                     sxfilterOffset     INTEGER,
                     sxfilterField      OCTET STRING,
                     sxfilterMask       OCTET STRING,
                     sxfilterThreshold  INTEGER,
                     sxfilterThreshTime INTEGER,
                     sxfilterThreshFlag INTEGER,
                     sxfilterPktCnts    Counter,
                     sxfilterLastSrc    OCTET STRING,
                     sxfilterByteCnts   Counter
                     }

     sxfilterIndex   OBJECT-TYPE
             SYNTAX  INTEGER
             ACCESS  read-only
             STATUS  mandatory
DESCRIPTION ""
             ::= { sxfilterEntry 1 }

     sxfilterID      OBJECT-TYPE
             SYNTAX  INTEGER
             ACCESS  read-only
             STATUS  mandatory
DESCRIPTION ""
             ::= { sxfilterEntry 2 }

     sxfilterPortNo  OBJECT-TYPE
             SYNTAX  INTEGER
             ACCESS  read-write
             STATUS  mandatory
DESCRIPTION ""
             ::= { sxfilterEntry 3 }

     sxfilterComboType       OBJECT-TYPE
             SYNTAX  INTEGER
             ACCESS  read-write
             STATUS  mandatory
DESCRIPTION ""
             ::= { sxfilterEntry 4 }

     sxfilterFlags   OBJECT-TYPE
             SYNTAX  INTEGER
             ACCESS  read-write
             STATUS  mandatory
DESCRIPTION ""
             ::= { sxfilterEntry 5 }

     sxfilterFrame   OBJECT-TYPE
     SYNTAX  INTEGER { any-llc(1), any-ethernet(2) }
             ACCESS  read-write
             STATUS  mandatory
DESCRIPTION ""
             ::= { sxfilterEntry 6 }

     sxfilterSource  OBJECT-TYPE
             SYNTAX  OCTET STRING
             ACCESS  read-write
             STATUS  mandatory
DESCRIPTION ""
             ::= { sxfilterEntry 7 }

     sxfilterSourceEnd       OBJECT-TYPE
             SYNTAX  OCTET STRING
             ACCESS  read-write
             STATUS  mandatory
DESCRIPTION ""
             ::= { sxfilterEntry 8 }

     sxfilterDest    OBJECT-TYPE
             SYNTAX  OCTET STRING
             ACCESS  read-write
             STATUS  mandatory
DESCRIPTION ""
             ::= { sxfilterEntry 9 }

     sxfilterDestEnd OBJECT-TYPE
             SYNTAX  OCTET STRING
             ACCESS  read-write
             STATUS  mandatory
DESCRIPTION ""
             ::= { sxfilterEntry 10 }

     sxfilterSourceMask      OBJECT-TYPE
             SYNTAX  OCTET STRING
             ACCESS  read-write
             STATUS  mandatory
DESCRIPTION ""
             ::= { sxfilterEntry 11 }

     sxfilterDestMask        OBJECT-TYPE
             SYNTAX  OCTET STRING
             ACCESS  read-write
             STATUS  mandatory
DESCRIPTION ""
             ::= { sxfilterEntry 12 }

     sxfilterSrcLan  OBJECT-TYPE
             SYNTAX  INTEGER
             ACCESS  read-write
             STATUS  mandatory
DESCRIPTION ""
             ::= { sxfilterEntry 13 }

     sxfilterOffset  OBJECT-TYPE
             SYNTAX  INTEGER
             ACCESS  read-write
             STATUS  mandatory
DESCRIPTION ""
             ::= { sxfilterEntry 14 }

     sxfilterField   OBJECT-TYPE
             SYNTAX  OCTET STRING
             ACCESS  read-write
             STATUS  mandatory
DESCRIPTION ""
             ::= { sxfilterEntry 15 }

     sxfilterMask    OBJECT-TYPE
             SYNTAX  OCTET STRING
             ACCESS  read-write
             STATUS  mandatory
DESCRIPTION ""
             ::= { sxfilterEntry 16 }

     sxfilterThreshold       OBJECT-TYPE
             SYNTAX  INTEGER
             ACCESS  read-write
             STATUS  mandatory
DESCRIPTION ""
             ::= { sxfilterEntry 17 }

     sxfilterThreshTime      OBJECT-TYPE
             SYNTAX  INTEGER
             ACCESS  read-write
             STATUS  mandatory
DESCRIPTION ""
             ::= { sxfilterEntry 18 }

     sxfilterThreshFlag      OBJECT-TYPE
             SYNTAX  INTEGER { true(1), false(2) }
             ACCESS  read-only
             STATUS  mandatory
DESCRIPTION ""
             ::= { sxfilterEntry 19 }

     sxfilterPktCnts OBJECT-TYPE
             SYNTAX  Counter
             ACCESS  read-only
             STATUS  mandatory
DESCRIPTION ""
             ::= { sxfilterEntry 20 }

     sxfilterLastSrc OBJECT-TYPE
             SYNTAX  OCTET STRING
             ACCESS  read-only
             STATUS  mandatory
DESCRIPTION ""
             ::= { sxfilterEntry 21 }

     sxfilterByteCnts        OBJECT-TYPE
             SYNTAX  Counter
             ACCESS  read-only
             STATUS  mandatory
DESCRIPTION ""
             ::= { sxfilterEntry 22 }


-- Debug Command Group

     sxdebugStringID OBJECT-TYPE
             SYNTAX  INTEGER
             ACCESS  read-only
             STATUS  mandatory
DESCRIPTION ""
             ::= { sxdebug 1 }

     sxdebugString   OBJECT-TYPE
             SYNTAX  OCTET STRING
             ACCESS  read-only
             STATUS  mandatory
DESCRIPTION ""
             ::= { sxdebug 2 }

     sxdebugTable    OBJECT-TYPE
             SYNTAX  SEQUENCE OF SxdebugEntry
             ACCESS  not-accessible
             STATUS  mandatory
DESCRIPTION ""
             ::= { sxdebug 3 }

     sxdebugEntry    OBJECT-TYPE
             SYNTAX  SxdebugEntry
             ACCESS  not-accessible
             STATUS  mandatory
DESCRIPTION ""
     INDEX { sxdebugIndex }
             ::= { sxdebugTable 1 }

     SxdebugEntry ::= SEQUENCE {
                      sxdebugIndex     INTEGER,
                      sxdebugOperation INTEGER,
                      sxdebugBase      INTEGER,
                      sxdebugLength    INTEGER,
                      sxdebugData      OCTET STRING
                      }

     sxdebugIndex    OBJECT-TYPE
             SYNTAX  INTEGER
             ACCESS  read-only
             STATUS  mandatory
DESCRIPTION ""
             ::= { sxdebugEntry 1 }

     sxdebugOperation        OBJECT-TYPE
             SYNTAX  INTEGER
                     {
                     examine(1),
                     modify(2)
                     }
             ACCESS  read-write
             STATUS  mandatory
DESCRIPTION ""
             ::= { sxdebugEntry 2 }

     sxdebugBase     OBJECT-TYPE
             SYNTAX  INTEGER
             ACCESS  read-write
             STATUS  mandatory
DESCRIPTION ""
             ::= { sxdebugEntry 3 }

     sxdebugLength   OBJECT-TYPE
             SYNTAX  INTEGER
             ACCESS  read-write
             STATUS  mandatory
DESCRIPTION ""
             ::= { sxdebugEntry 4 }

     sxdebugData     OBJECT-TYPE
             SYNTAX  OCTET STRING
             ACCESS  read-write
             STATUS  mandatory
DESCRIPTION ""
             ::= { sxdebugEntry 5 }

-- Loopback Command Group

     sxlpbkTable     OBJECT-TYPE
             SYNTAX  SEQUENCE OF SxlpbkEntry
             ACCESS  not-accessible
             STATUS  mandatory
DESCRIPTION ""
             ::= { sxlpbk 1 }

     sxlpbkEntry     OBJECT-TYPE
             SYNTAX  SxlpbkEntry
             ACCESS  not-accessible
             STATUS  mandatory
DESCRIPTION ""
     INDEX { sxlpbkIndex }
             ::= { sxlpbkTable 1 }

     SxlpbkEntry ::= SEQUENCE {
                     sxlpbkIndex            INTEGER,
                     sxlpbkOperation        INTEGER,
                     sxlpbkDestAddr         OCTET STRING,
                     sxlpbkPktNum           INTEGER,
                     sxlpbkInterval         TimeTicks,
                     sxlpbkPktLength        INTEGER,
                     sxlpbkIncrements       INTEGER,
                     sxlpbkGoods            Counter,
                     sxlpbkErrorNoReceives  Counter,
                     sxlpbkErrorBadReceives Counter,
                     sxlpbkErrorSize        INTEGER,
                     sxlpbkErrorSent        OCTET STRING,
                     sxlpbkErrorReceived    OCTET STRING,
                     sxlpbkErrorOffset      INTEGER
                     }

     sxlpbkIndex     OBJECT-TYPE
             SYNTAX  INTEGER
             ACCESS  read-only
             STATUS  mandatory
DESCRIPTION ""
             ::= { sxlpbkEntry 1 }

     sxlpbkOperation OBJECT-TYPE
     SYNTAX  INTEGER {
                 loopback-off(1),
                 loopback-local(2),
                 loopback-remote(3)
             }
             ACCESS  read-write
             STATUS  mandatory
DESCRIPTION ""
             ::= { sxlpbkEntry 2 }

     sxlpbkDestAddr  OBJECT-TYPE
             SYNTAX  OCTET STRING
             ACCESS  read-write
             STATUS  mandatory
DESCRIPTION ""
             ::= { sxlpbkEntry 3 }

     sxlpbkPktNum    OBJECT-TYPE
             SYNTAX  INTEGER
             ACCESS  read-write
             STATUS  mandatory
DESCRIPTION ""
             ::= { sxlpbkEntry 4 }

     sxlpbkInterval  OBJECT-TYPE
             SYNTAX  TimeTicks
             ACCESS  read-write
             STATUS  mandatory
DESCRIPTION ""
             ::= { sxlpbkEntry 5 }

     sxlpbkPktLength OBJECT-TYPE
             SYNTAX  INTEGER
             ACCESS  read-write
             STATUS  mandatory
DESCRIPTION ""
             ::= { sxlpbkEntry 6 }

     sxlpbkIncrements        OBJECT-TYPE
             SYNTAX  INTEGER
             ACCESS  read-write
             STATUS  mandatory
DESCRIPTION ""
             ::= { sxlpbkEntry 7 }

     sxlpbkGoods     OBJECT-TYPE
             SYNTAX  Counter
             ACCESS  read-only
             STATUS  mandatory
DESCRIPTION ""
             ::= { sxlpbkEntry 8 }

     sxlpbkErrorNoReceives   OBJECT-TYPE
             SYNTAX  Counter
             ACCESS  read-only
             STATUS  mandatory
DESCRIPTION ""
             ::= { sxlpbkEntry 9 }

     sxlpbkErrorBadReceives  OBJECT-TYPE
             SYNTAX  Counter
             ACCESS  read-only
             STATUS  mandatory
DESCRIPTION ""
             ::= { sxlpbkEntry 10 }

     sxlpbkErrorSize OBJECT-TYPE
             SYNTAX  INTEGER
             ACCESS  read-only
             STATUS  mandatory
DESCRIPTION ""
             ::= { sxlpbkEntry 11 }

     sxlpbkErrorSent OBJECT-TYPE
             SYNTAX  OCTET STRING
             ACCESS  read-only
             STATUS  mandatory
DESCRIPTION ""
             ::= { sxlpbkEntry 12 }

     sxlpbkErrorReceived     OBJECT-TYPE
             SYNTAX  OCTET STRING
             ACCESS  read-only
             STATUS  mandatory
DESCRIPTION ""
             ::= { sxlpbkEntry 13 }

     sxlpbkErrorOffset       OBJECT-TYPE
             SYNTAX  INTEGER
             ACCESS  read-only
             STATUS  mandatory
DESCRIPTION ""
             ::= { sxlpbkEntry 14 }



-- SMC Protocols Group

     sxprotoTable OBJECT-TYPE
             SYNTAX  SEQUENCE OF SxprotoEntry
             ACCESS  not-accessible
             STATUS  mandatory
             DESCRIPTION
             "This table contains configuration information specify-
              ing the types of protocols used to bridge, route,
              translate, and filter frames for each port."
             ::= { sxproto 1 }

     sxprotoEntry OBJECT-TYPE
             SYNTAX  SxprotoEntry
             ACCESS  not-accessible
             STATUS  mandatory
             DESCRIPTION
             "Each entry in this table specifies which protocols are
             used by a particular port in the ES/1."
     INDEX { sxprotoIfIndex }
             ::= { sxprotoTable 1 }

     SxprotoEntry ::= SEQUENCE {
                      sxprotoIfIndex           INTEGER,
                      sxprotoBridge            INTEGER,
                      sxprotoSuppressBpdu      INTEGER,
                      sxprotoRipListen         INTEGER,
                      sxprotoTrunking          INTEGER,
                      sxsprotoCollisionRelief  INTEGER
                      }

     sxprotoIfIndex OBJECT-TYPE
             SYNTAX  INTEGER
             ACCESS  read-only
             STATUS  mandatory
             DESCRIPTION
             "Identifies the interface (port) to which this entry's
              information belongs. The value of this variable
              corresponds to ifIndex, as well as most of the other
              port identification values in related MIBs."
             ::= { sxprotoEntry 1 }

     sxprotoBridge OBJECT-TYPE
             SYNTAX  INTEGER { transparent(1), none(4) }
             ACCESS  read-write
             STATUS  mandatory
             DESCRIPTION
             "Defines the bridging method to be applied to frames
             received at, or destined for, this port. Ethernet and
             FDDI ports may be configured for transparent, srt, or
             none.  Token Ring ports may be configured for any of
             the four options. The UART may only be configured to
             none."
             ::= { sxprotoEntry 2 }

     sxprotoSuppressBpdu OBJECT-TYPE
             SYNTAX  INTEGER { normal(1), suppressed(2) }
             ACCESS  read-write
             STATUS  mandatory
             DESCRIPTION
             "Allows transmission of spanning tree protocol packets
              to be suppressed.  If normal(1), 802.1d spanning tree
              packets and source-routing spanning tree packets are
              transmitted as usual. If suppressed(2), these packets
              are not transmitted. This option may be needed for in-
              teroperability with non-802.1d spanning tree protocols
              (e.g., DEC LanBridge 100)."
             ::= { sxprotoEntry 3 }

     sxprotoRipListen OBJECT-TYPE
             SYNTAX  INTEGER { enabled(1), disabled(2) }
             ACCESS  read-write
             STATUS  mandatory
             DESCRIPTION
             "Specifies whether the port should listen for internet
              Routing Information Protocol (RFC-1058) packets, in order to
              build the routing table for the unit."
             ::= { sxprotoEntry 4 }

     sxprotoTrunking OBJECT-TYPE
             SYNTAX  INTEGER { enabled(1), disabled(2) }
             ACCESS  read-write
             STATUS  mandatory
             DESCRIPTION
             "Specifies whether SMC's trunking protocol (an extension
              to the standard Spanning Tree) is to be used over this port."
             ::= { sxprotoEntry 5 }

     sxsprotoCollisionRelief OBJECT-TYPE
             SYNTAX  INTEGER { enabled(1), disabled(2) }
             ACCESS  read-write
             STATUS  mandatory
             DESCRIPTION
             "Specifies whether the 10 Mbits Ethernet modified back-off
              algorithm is to be used. This option forces Ethernet port
              to stop the back-off timer when a transmit collision occured.
              It will start the timer again until no carrier on the wire.
              This option can reduce the number of transmit collisions. It
              may also slow down the transmit process under heavy loaded
              network."
             ::= { sxprotoEntry 6 }

-- SMC Trunking Group


     sxtrunkTable OBJECT-TYPE
             SYNTAX  SEQUENCE OF SxtrunkEntry
             ACCESS  not-accessible
             STATUS  mandatory
             DESCRIPTION
                     "This table describes the trunking status and attributes of
                      the interfaces that are configured for bridge trunking."
             ::= { sxtrunk 1 }

     sxtrunkEntry OBJECT-TYPE
             SYNTAX  SxtrunkEntry
             ACCESS  not-accessible
             STATUS  mandatory
             DESCRIPTION
                     "An entry exists in this table for each physical interface
                      (port) that is configured for trunking."
             INDEX { sxtrunkIfIndex }
             ::= { sxtrunkTable 1 }

     SxtrunkEntry ::= SEQUENCE {
                      sxtrunkIfIndex           INTEGER,
                      sxtrunkState             INTEGER,
                      sxtrunkRemoteBridgeAddr  OCTET STRING,
                      sxtrunkRemoteIp          IpAddress,
                      sxtrunkLastError         INTEGER,
                      sxtrunkLinkOrdinal       INTEGER,
                      sxtrunkLinkCount         INTEGER,
                      sxtrunkLastChange        INTEGER
                      }

     sxtrunkIfIndex OBJECT-TYPE
             SYNTAX  INTEGER
             ACCESS  read-only
             STATUS  mandatory
             DESCRIPTION
             "Identifies a physical interface (port) which is
              configured for LAN trunking. The value of this variable
              corresponds to ifIndex, as well as most of the other
              port identification values in related MIBs."
             ::= { sxtrunkEntry 1 }

     sxtrunkState OBJECT-TYPE
             SYNTAX  INTEGER
                     {
                     off(1),
                     closed(2),
                     oneway(3),
                     joined(4),
                     perturbed(5),
                     helddown(6),
                     broken(7)
                     }
             ACCESS  read-only
             STATUS  mandatory
             DESCRIPTION
             "If off(1) then this link has not been enabled for trunking.
              If closed(2) then this link has not yet received any Trunking
              PDUs. If oneway(3) then incoming Trunking PDUs do not indicate
              that our PDUs are being successfully received by the far end.
              If joined(4) then this link is actively participating in the
              trunk group. If perturbed(5) then this link is actively
              participating in the trunk group;  however, the transmission of
              data packets has been temporarily stopped due to a change in
              membership of the group.  If helddown(6) then an error has been
              detected and the link is being held out-of-service until the error
              clears.  If broken(7) then this link has been configured for trunking,
              but the port is physically non-operational."
             ::= { sxtrunkEntry 2 }

     sxtrunkRemoteBridgeAddr OBJECT-TYPE
             SYNTAX  OCTET STRING
             ACCESS  read-only
             STATUS  mandatory
             DESCRIPTION
             "The MAC address portion of the bridge ID of the remote bridge."
             ::= { sxtrunkEntry 3 }

     sxtrunkRemoteIp OBJECT-TYPE
             SYNTAX  IpAddress
             ACCESS  read-only
             STATUS  mandatory
             DESCRIPTION
             "The IP address of the remote bridge, as reported by that
              bridge for administrative purposes."
             ::= { sxtrunkEntry 4 }

     sxtrunkLastError OBJECT-TYPE
             SYNTAX  INTEGER
                     {
                     none(1),
                     in-bpdu(2),
                     multiple-bridges(3),
                     ack-lost(4),
                     standby(5),
                     too-many-groups(6),
                     no-ack(7),
                     perturbed-threshold(8),
                     self-connect(9),
                     port-moved(10),
                     multiple-lan-types(11)
                     }
             ACCESS  read-only
             STATUS  mandatory
             DESCRIPTION
                     "The last reason for failure when the link is in closed, oneway, or helddown state."
             ::= { sxtrunkEntry 5 }

     sxtrunkLinkOrdinal OBJECT-TYPE
             SYNTAX  INTEGER
             ACCESS  read-only
             STATUS  mandatory
             DESCRIPTION
                     "The position of this link within the trunk group."
             ::= { sxtrunkEntry 6 }

     sxtrunkLinkCount OBJECT-TYPE
             SYNTAX  INTEGER
             ACCESS  read-only
             STATUS  mandatory
             DESCRIPTION
                     "The number of links within the trunk group."
             ::= { sxtrunkEntry 7 }

     sxtrunkLastChange OBJECT-TYPE
             SYNTAX  INTEGER
             ACCESS  read-only
             STATUS  mandatory
             DESCRIPTION
                     "The number of seconds since sxtrunkState changed."
             ::= { sxtrunkEntry 8 }

-- SMC Workgroup Group

     sxWorkGroupNextNumber OBJECT-TYPE
             SYNTAX  INTEGER
             ACCESS  read-only
             STATUS  mandatory
             DESCRIPTION
                 "The next available workgroup number to be used.  When creating
                  a new workgroup, it is recommended to read the value of the variable
                  and use it to key into the workgroup table."
             ::= { sxworkgroup 1 }

     sxWorkGroupCurrentCount OBJECT-TYPE
             SYNTAX  INTEGER
             ACCESS  read-only
             STATUS  mandatory
             DESCRIPTION
                 "The total number of workgroups currently defined."
             ::= { sxworkgroup 2 }

     sxWorkGroupMaxCount OBJECT-TYPE
             SYNTAX  INTEGER
             ACCESS  read-only
             STATUS  mandatory
             DESCRIPTION
             "The maximum number of workgroups allowed."
             ::= { sxworkgroup 3 }

     sxWorkGroupTable OBJECT-TYPE
             SYNTAX  SEQUENCE OF SxWorkGroupEntry
             ACCESS  not-accessible
             STATUS  mandatory
             DESCRIPTION
             "This table contains work group definitions for the interfaces."
             ::= { sxworkgroup 4 }

     sxWorkGroupEntry OBJECT-TYPE
             SYNTAX  SxWorkGroupEntry
             ACCESS  not-accessible
             STATUS  mandatory
             DESCRIPTION
             "Each entry in this table contains a definition of a work group."
         INDEX   { sxWorkGroupNumber }
             ::= { sxWorkGroupTable 1 }

     SxWorkGroupEntry ::=
             SEQUENCE {
                 sxWorkGroupNumber      INTEGER,
                 sxWorkGroupName        DisplayString,
                 sxWorkGroupPorts       OCTET STRING,
                 sxWorkGroupType        INTEGER,
                 sxWorkGroupIpAddress   IpAddress,
                 sxWorkGroupIpMask      IpAddress,
                 sxWorkGroupIpxNetwork  OCTET STRING
                 }

     sxWorkGroupNumber OBJECT-TYPE
             SYNTAX  INTEGER
             ACCESS  read-write
             STATUS  mandatory
             DESCRIPTION
             "An integer that identifies the work group, used as an index
              to this table."
             ::= { sxWorkGroupEntry 1 }

     sxWorkGroupName OBJECT-TYPE
             SYNTAX  DisplayString
             ACCESS  read-write
             STATUS  mandatory
             DESCRIPTION
             "A 1-16 character work group name."
             ::= { sxWorkGroupEntry 2 }

     sxWorkGroupPorts OBJECT-TYPE
             SYNTAX  OCTET STRING
             ACCESS  read-write
             STATUS  mandatory
             DESCRIPTION
             "A list of all ports within the group.  The first
              octet specified ports 1-8, the second 9-16, etc."
             ::= { sxWorkGroupEntry 3 }

     sxWorkGroupType OBJECT-TYPE
             SYNTAX  INTEGER
                     {
                     ip(1),
                     ipx(2),
                     all(3),    -- all broadcast packets
                     invalid(4)
                     }          -- to delete this group
             ACCESS  read-write
             STATUS  mandatory
             DESCRIPTION
             "The type of work group:
              all - no additional information needs to be supplied.
              ip - the IP network (and optionally, IP mask) must be supplied.
              ipx - the IPX network number may be supplied, or else all IPX
              network number will be assumed."
             ::= { sxWorkGroupEntry 4 }


     sxWorkGroupIpAddress OBJECT-TYPE
             SYNTAX  IpAddress
             ACCESS  read-write
             STATUS  mandatory
             DESCRIPTION
             "The IP network address."
             ::= { sxWorkGroupEntry 5 }

     sxWorkGroupIpMask OBJECT-TYPE
             SYNTAX  IpAddress
             ACCESS  read-write
             STATUS  mandatory
             DESCRIPTION
             "The IP network mask, if set to 0, the default network mask is
              applied."
             ::= { sxWorkGroupEntry 6 }

     sxWorkGroupIpxNetwork OBJECT-TYPE
             SYNTAX  OCTET STRING
             ACCESS  read-write
             STATUS  mandatory
             DESCRIPTION
             "The IPX network number, 0 means all networks."
             ::= { sxWorkGroupEntry 7 }

-- SMC Trap Group

     sxtrapControlTable OBJECT-TYPE
             SYNTAX  SEQUENCE OF SxtrapControl
             ACCESS  not-accessible
             STATUS  mandatory
             DESCRIPTION
             "This table contains information about the severity of each trap
              and whether the trap is currently enable."
             ::= { sxtrapMgt 1 }

     sxtrapControl OBJECT-TYPE
             SYNTAX  SxtrapControl
             ACCESS  not-accessible
             STATUS  mandatory
DESCRIPTION ""
     INDEX   { sxtrapIndex }
             ::= { sxtrapControlTable 1 }

    SxtrapControl ::=
        SEQUENCE {
            sxtrapIndex      INTEGER,
            sxtrapEnabled    INTEGER,
            sxtrapSeverity   INTEGER,
            sxtrapText       DisplayString
            }

     sxtrapIndex OBJECT-TYPE
             SYNTAX  INTEGER
             ACCESS  read-only
             STATUS  mandatory
             DESCRIPTION
             "The specific trap number."
             ::= { sxtrapControl 1 }

     sxtrapEnabled OBJECT-TYPE
             SYNTAX  INTEGER { true(1), false(2) }
             ACCESS  read-write
             STATUS  mandatory
             DESCRIPTION
             "Enable or disable the generation of this trap."
             ::= { sxtrapControl 2 }

     sxtrapSeverity OBJECT-TYPE
             SYNTAX  INTEGER
                     {
                     informational(1),
                     warning(2),
                     minor(3),
                     major(4),
                     critical(5)
                     }
             ACCESS  read-write
             STATUS  mandatory
             DESCRIPTION
             "A user-definable severity, indicating the importance of the
              trap."
             ::= { sxtrapControl 3 }

     sxtrapText OBJECT-TYPE
             SYNTAX  DisplayString
             ACCESS  read-only
             STATUS  mandatory
             DESCRIPTION
             "A description of the trap."
             ::= { sxtrapControl 4 }

     sxtrapSeverityControlTable OBJECT-TYPE
             SYNTAX  SEQUENCE OF SxtrapSeverityControl
             ACCESS  not-accessible
             STATUS  mandatory
             DESCRIPTION
             "This table contains information about whether a class of
              traps of a particular severity are enabled or disabled."
             ::= { sxtrapMgt 2 }

    sxtrapSeverityControl OBJECT-TYPE
             SYNTAX  SxtrapSeverityControl
             ACCESS  not-accessible
             STATUS  mandatory
DESCRIPTION ""
    INDEX   { sxtrapSeverityControlSeverity }
            ::= { sxtrapSeverityControlTable 1 }

    SxtrapSeverityControl ::= SEQUENCE {
            sxtrapSeverityControlSeverity  INTEGER,
            sxtrapSeverityEnable INTEGER
            }

    sxtrapSeverityControlSeverity  OBJECT-TYPE
            SYNTAX  INTEGER
                    {
                    informational(1),
                    warning(2),
                    minor(3),
                    major(4),
                    critical(5)
                    }
            ACCESS  read-write
            STATUS  mandatory
            DESCRIPTION
            "A user-definable severity, indicating the importance of the
             trap."
            ::= { sxtrapSeverityControl 1 }

    sxtrapSeverityEnable OBJECT-TYPE
            SYNTAX  INTEGER { enabled(1), disabled(2) }
            ACCESS  read-write
            STATUS  mandatory
            DESCRIPTION
            "Enable or disable all traps of a given severity level."
            ::= { sxtrapSeverityControl 2 }

    sxtrapIncludeText OBJECT-TYPE
            SYNTAX  INTEGER { true(1), false(2) }
            ACCESS  read-write
            STATUS  mandatory
            DESCRIPTION
            "Whether or not a formatted text string is included in the trap
             PDU."
            ::= { sxtrapMgt 3 }

    sxtrapTime OBJECT-TYPE
            SYNTAX  TimeTicks
            ACCESS  read-write
            STATUS  mandatory
            DESCRIPTION
            "The time, in centiseconds, which should expire between the sending
             of traps."
            -- DEFVAL { 100 }
            ::= { sxtrapMgt 4 }

    sxtrapRetry OBJECT-TYPE
            SYNTAX  INTEGER
            ACCESS  read-write
            STATUS  mandatory
            DESCRIPTION
            "The number of times any enterprise-specific trap is to be sent for
             a given event.  PDUs are retried using a truncated exponential backoff:
             2 seconds, 4 seoncs, 8 seconds, 16 seconds, and then 32 seconds for
             all succeeding intervals."
            -- DEFVAL { 1 }
            ::= { sxtrapMgt 5 }

    sxtrapEntryNumber OBJECT-TYPE
            SYNTAX  INTEGER
            ACCESS  read-only
            STATUS  mandatory
            DESCRIPTION
            "The number of traps that are in the sxtrapTable."
            ::= { sxtrapMgt 6 }

    sxtrapTable OBJECT-TYPE
            SYNTAX  SEQUENCE OF SxtrapEntry
            ACCESS  not-accessible
            STATUS  mandatory
            DESCRIPTION
            "This table contains the latest traps that have been generated."
            ::= { sxtrapMgt 7 }

    sxtrapEntry OBJECT-TYPE
            SYNTAX  SxtrapEntry
            ACCESS  not-accessible
            STATUS  mandatory
DESCRIPTION ""
    INDEX   { sxtrapEntryIndex }
            ::= { sxtrapTable 1 }

        SxtrapEntry ::=
            SEQUENCE {
                sxtrapEntryIndex      INTEGER,
                sxtrapEntryTimeStamp  TimeTicks,
                sxtrapEntryText       DisplayString,
                sxtrapNumber          INTEGER,
                sxtrapEntrySeverity        INTEGER
                }

    sxtrapEntryIndex OBJECT-TYPE
            SYNTAX  INTEGER
            ACCESS  read-only
            STATUS  mandatory
            DESCRIPTION
            "A number representing the order in which the trap occurred
             in time.  This 32 bit number can wrap."
            ::= { sxtrapEntry 1 }

    sxtrapEntryTimeStamp OBJECT-TYPE
            SYNTAX  TimeTicks
            ACCESS  read-only
            STATUS  mandatory
            DESCRIPTION
            "The time at which the trap occurred."
            ::= { sxtrapEntry 2 }

    sxtrapEntryText OBJECT-TYPE
            SYNTAX  DisplayString
            ACCESS  read-only
            STATUS  mandatory
            DESCRIPTION
            "A description of the trap."
            ::= { sxtrapEntry 3 }

    sxtrapNumber OBJECT-TYPE
            SYNTAX  INTEGER
            ACCESS  read-only
            STATUS  mandatory
            DESCRIPTION
            "The specific trap number, as specified in the TRAP PDU."
            ::= { sxtrapEntry 4 }

    sxtrapEntrySeverity OBJECT-TYPE
            SYNTAX  INTEGER
                    {
                    informational(1),
                    warning(2),
                    minor(3),
                    major(4),
                    critical(5)
                    }
            ACCESS  read-only
            STATUS  mandatory
            DESCRIPTION
            "A user-definable severity, indicating the importance of the
             trap."
            ::= { sxtrapEntry 5 }

-- Enterprise Specific Traps

sxTempOKTrap TRAP-TYPE
    ENTERPRISE  sigma
    VARIABLES   {
        sxtrapSeverity,
        sxadminTempOK,
        sxhwManufData
    }
     DESCRIPTION
        "Sent whenever the module's temperature transitions from
         too hot to okay, and vice versa."
    ::= 1

sxWriteStatusTrap TRAP-TYPE
    ENTERPRISE  sigma
    VARIABLES   {
        sxtrapSeverity,
        sxswdisWriteStatus,
        sxswdisDesc
    }
    DESCRIPTION
        "Sent when a bank of Flash EPROM has been erased.  If
         sxswdisWriteStatus indicates success, then the unit is ready
         to be downloaded with the new software."
    ::= 2

sxPortFunctionsTrap TRAP-TYPE
    ENTERPRISE  sigma
    VARIABLES   {
        sxtrapSeverity,
        sxifFunction
    }
    DESCRIPTION
        "Sent whenever the current functional state (active
         protocols) of the port has changed."
    ::= 3

sxRxQueuesTrap TRAP-TYPE
    ENTERPRISE  sigma
    VARIABLES   {
        sxtrapSeverity,
        sxifRxQueues
    }
    DESCRIPTION
        "Sent whenever the number of times that the port's receiver
         has stopped receiving packets due to buffer space shortages
         has exceeded the port's limit."
    ::= 4

sxTxStormFlagTrap TRAP-TYPE
    ENTERPRISE  sigma
    VARIABLES   {
        sxtrapSeverity,
        sxifTxStorms
    }
    DESCRIPTION
        "Sent whenever multicast storm protection has been invoked
         for the port."
    ::= 5

sxTxCongestsTrap TRAP-TYPE
    ENTERPRISE  sigma
    VARIABLES   {
        sxtrapSeverity,
        sxadminNAMReceiveCongests
    }
    DESCRIPTION
        "Sent whenever packets destined for the unit itself were
         discarded due to lack of buffer space."
    ::= 6

sxFilterThreshTrap TRAP-TYPE
    ENTERPRISE  sigma
    VARIABLES   {
        sxtrapSeverity,
        sxfilterLastSrc,
        sxfilterPortNo
    }
    DESCRIPTION
        "Sent whenever usage of a port's combination filter has
         exceeded the filter's limits."
    ::= 7

sxDebugStringIdTrap TRAP-TYPE
    ENTERPRISE  sigma
    VARIABLES   {
        sxtrapSeverity,
        sxdebugStringID,
        sxdebugString
    }
    DESCRIPTION
        "Send whenever the unit has a debug text string to be
         displayed. The text strings are sent in a stream-like
         fashion."
    ::= 8

sxLpbkOperationTrap TRAP-TYPE
    ENTERPRISE  sigma
    VARIABLES   {
        sxtrapSeverity,
        sxlpbkOperation,
        sxlpbkErrorNoReceives,
        sxlpbkErrorBadReceives
    }
    DESCRIPTION
        "Send whenever the unit has finished a loop back test, or
         a loop back error has been detected."
    ::= 9

sxTrunkStateTrap TRAP-TYPE
    ENTERPRISE sigma
    VARIABLES {
        sxtrapSeverity,
        sxtrunkState
    }
    DESCRIPTION
        "A trunking state change transition has occurred. The possible
         transitions are:
            CLOSED-ONEWAY
            ONEWAY-PERTURBED
            PERTURBED-JOINED
            JOINED-HELDDOWN
            CLOSED-HELDDOWN
            ONEWAY-HELDDOWN
            PERTURBED-HELDDOWN"
    ::= 10

sxTrunkBridgeAddrTrap TRAP-TYPE
    ENTERPRISE sigma
    VARIABLES {
        sxtrapSeverity,
        sxtrunkRemoteBridgeAddr
    }
    DESCRIPTION
        "The associated trunking MAC address of the bridge ID of the remote
         bridge has changed."
    ::= 11

sxTrunkIPAddrTrap TRAP-TYPE
    ENTERPRISE sigma
    VARIABLES {
        sxtrapSeverity,
        sxtrunkRemoteIp
    }
    DESCRIPTION
        "The associated trunking IP address of the remote bridge has changed."
    ::= 12

sxTrunkErrorTrap TRAP-TYPE
    ENTERPRISE sigma
    VARIABLES {
        sxtrapSeverity,
        sxtrunkLastError
    }
    DESCRIPTION
        "An error has occurred in trunking."
    ::= 13

sxTrunkLinkOrdinalTrap TRAP-TYPE
    ENTERPRISE sigma
    VARIABLES {
        sxtrapSeverity,
        sxtrunkLinkOrdinal
    }
    DESCRIPTION
        "The port's index in the trunking group has changed."
    ::= 14

sxTrunkLinkCountTrap TRAP-TYPE
    ENTERPRISE sigma
    VARIABLES {
    sxtrapSeverity,
    sxtrunkLinkCount
    }
    DESCRIPTION
        "The number of ports in the trunking group has changed."
    ::= 15

sxDiagUnitBootedTrap TRAP-TYPE
    ENTERPRISE  sigma
    VARIABLES   {
        sxtrapSeverity,
        sxadminFatalErr
    }
    DESCRIPTION
        "The unit has booted. sxadminFatalErr contains information about
         why the unit rebooted."
    ::= 16

sxStorageFailureTrap TRAP-TYPE
    ENTERPRISE  sigma
    VARIABLES   {
        sxtrapSeverity
    }
    DESCRIPTION
        "Sent if the unit's Configuration EEPROM has failed. The unit
         will not be able to reboot, and must be returned to the
         factory."
::= 17

sxPortCongestedTrap TRAP-TYPE
    ENTERPRISE  sigma
    VARIABLES   {
        sxtrapSeverity,
        ifOutDiscards
    }
    DESCRIPTION
        "Sent whenever outbound congestion control has been invoked
         for the port."
    ::= 18

sxTopChangeBegunTrap TRAP-TYPE
    ENTERPRISE sigma
    VARIABLES {
        sxtrapSeverity
    }
    DESCRIPTION
        "The spanning tree topology has begun to change."
    ::= 19

sxTopChangeEndTrap TRAP-TYPE
    ENTERPRISE sigma
    VARIABLES {
        sxtrapSeverity
    }
    DESCRIPTION
        "The spanning tree topology has stopped changing."
::= 20

sxIfErrorsTrap TRAP-TYPE
    ENTERPRISE  sigma
    VARIABLES   {
        sxtrapSeverity,
        ifInErrors,
        ifOutErrors
    }
    DESCRIPTION
        "Sent whenever the number of hardware errors in received and
         transmitted packets has exceeded the port's limit."
    ::= 21

sxStRootIDTrap TRAP-TYPE
    ENTERPRISE sigma
    VARIABLES {
        sxtrapSeverity,
        dot1dStpDesignatedRoot
    }
    DESCRIPTION
        "The spanning tree root bridge ID for the unit has changed."
    ::= 22

sxStRootCostTrap TRAP-TYPE
    ENTERPRISE sigma
    VARIABLES {
        sxtrapSeverity,
        dot1dStpRootCost
    }
    DESCRIPTION
        "The unit's spanning tree cost to the root bridge has changed."
    ::= 23

sxStRootPortTrap TRAP-TYPE
    ENTERPRISE sigma
    VARIABLES {
        sxtrapSeverity,
        dot1dStpRootPort
    }
    DESCRIPTION
        "The unit's spanning tree root port has changed."
    ::= 24

sxStMaxAgeTrap TRAP-TYPE
    ENTERPRISE sigma
    VARIABLES {
        sxtrapSeverity,
        dot1dStpMaxAge
    }
    DESCRIPTION
        "The unit's spanning tree maximum age has changed."
    ::= 25

sxStHelloTimeTrap TRAP-TYPE
    ENTERPRISE sigma
    VARIABLES {
        sxtrapSeverity,
        dot1dStpHelloTime
    }
    DESCRIPTION
        "The unit's spanning tree hello time has changed."
    ::= 26

sxStForwardDelayTrap TRAP-TYPE
    ENTERPRISE sigma
    VARIABLES {
        sxtrapSeverity,
        dot1dStpForwardDelay
    }
    DESCRIPTION
        "The unit's spanning tree forward delay time has changed."
    ::= 27

sxStDesigRootTrap TRAP-TYPE
    ENTERPRISE sigma
    VARIABLES {
        sxtrapSeverity,
        dot1dStpPortDesignatedRoot
    }
    DESCRIPTION
        "The Root Bridge ID in received Spanning Tree Configuration BPDUs
         from the port has changed."
    ::= 28

sxStPortDesigBridgeTrap TRAP-TYPE
    ENTERPRISE sigma
    VARIABLES {
        sxtrapSeverity,
        dot1dStpPortDesignatedBridge
    }
    DESCRIPTION
        "The bridge ID of the spanning tree designated bridge of the LAN/WAN
         to which the port is attached has changed."
    ::= 29

sxStPortDesigCostTrap TRAP-TYPE
    ENTERPRISE sigma
    VARIABLES {
        sxtrapSeverity,
        dot1dStpPortDesignatedCost
    }
    DESCRIPTION
        "The cost to the spanning tree root bridge from the designated port of
         the LAN/WAN to which the port is attached has changed."
    ::= 30

sxStPortDesigPortTrap TRAP-TYPE
    ENTERPRISE sigma
    VARIABLES {
        sxtrapSeverity,
        dot1dStpPortDesignatedPort
    }
    DESCRIPTION
        "The port ID of the spanning tree designated port of the LAN/WAN
         to which the port is attached has changed."
    ::= 31

sxStPortStateTrap TRAP-TYPE
    ENTERPRISE sigma
    VARIABLES {
        sxtrapSeverity,
        dot1dStpPortState
    }
    DESCRIPTION
        "The spanning tree state of the port has changed."
    ::= 32

sxhwDiagTrap TRAP-TYPE
    ENTERPRISE  sigma
    VARIABLES   {
        sxtrapSeverity,
        sxhwDiagCode
    }
    DESCRIPTION
        "Sent whenever the unit's diagnostics have indicated an error."
    ::= 100

  		END
