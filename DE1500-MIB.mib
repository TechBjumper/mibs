DE1500-MIB DEFINITIONS ::= BEGIN

    IMPORTS
		DisplayString FROM SNMPv2-TC
        mgmt, OBJECT-TYPE, NetworkAddress, IpAddress,
        Counter, Gauge, TimeTicks, internet
                FROM RFC1155-SMI;

        mib        OBJECT IDENTIFIER ::= { mgmt 1 }
        directory  OBJECT IDENTIFIER ::= { internet 1 }
        experimental   OBJECT IDENTIFIER ::= { internet 3 }
        private    OBJECT IDENTIFIER ::= { internet 4 }
        enterprises OBJECT IDENTIFIER ::= { private 1 }

        system     OBJECT IDENTIFIER ::= { mib 1 }
        interfaces OBJECT IDENTIFIER ::= { mib 2 }
        ip         OBJECT IDENTIFIER ::= { mib 4 }
        icmp       OBJECT IDENTIFIER ::= { mib 5 }
        udp        OBJECT IDENTIFIER ::= { mib 7 }
        snmp       OBJECT IDENTIFIER ::= { mib 11}


        -- object types

        -- the System group

        sysDescr OBJECT-TYPE
                SYNTAX  DisplayString (SIZE(0..255))
                ACCESS  read-only
                STATUS  mandatory
	DESCRIPTION ""
                ::= { system 1 }

        sysObjectID OBJECT-TYPE
                SYNTAX  OBJECT IDENTIFIER
                ACCESS  read-only
                STATUS  mandatory
	DESCRIPTION ""
                ::= { system 2 }

        sysUpTime OBJECT-TYPE
                SYNTAX  TimeTicks
                ACCESS  read-only
                STATUS  mandatory
	DESCRIPTION ""
                ::= { system 3 }

        sysContact OBJECT-TYPE
                SYNTAX  DisplayString (SIZE(0..255))
                ACCESS  read-write
                STATUS  mandatory
	DESCRIPTION ""
                ::= { system 4 }

        sysName OBJECT-TYPE
                SYNTAX  DisplayString (SIZE(0..255))
                ACCESS  read-write
                STATUS  mandatory
	DESCRIPTION ""
                ::= { system 5 }

        sysLocation OBJECT-TYPE
                SYNTAX  DisplayString (SIZE(0..255))
                ACCESS  read-only
                STATUS  mandatory
	DESCRIPTION ""
                ::= { system 6 }

        sysServices OBJECT-TYPE
                SYNTAX  INTEGER (0..127)
                ACCESS  read-only
                STATUS  mandatory
	DESCRIPTION ""
                ::= { system 7 }


        -- the Interfaces group

        ifNumber OBJECT-TYPE
                SYNTAX  INTEGER
                ACCESS  read-only
                STATUS  mandatory
	DESCRIPTION ""
                ::= { interfaces 1 }

        -- the Interfaces table

        ifTable OBJECT-TYPE
                SYNTAX  SEQUENCE OF IfEntry
                ACCESS  read-only
                STATUS  mandatory
	DESCRIPTION ""
                ::= { interfaces 2 }

        ifEntry OBJECT-TYPE
                SYNTAX  IfEntry
                ACCESS  read-only
                STATUS  mandatory
	DESCRIPTION ""
                ::= { ifTable 1 }

        IfEntry ::= SEQUENCE {
                ifIndex
                    INTEGER,
                ifDescr
                    DisplayString,
                ifType
                    INTEGER,
                ifMtu
                    INTEGER,
                ifSpeed
                    Gauge,
                ifPhysAddress
                    OCTET STRING,
                ifAdminStatus
                    INTEGER,
                ifOperStatus
                    INTEGER,
                ifLastChange
                    TimeTicks,
                ifInOctets
                    Counter,
                ifInUcastPkts
                    Counter,
                ifInNUcastPkts
                    Counter,
                ifInDiscards
                    Counter,
                ifInErrors
                    Counter,
                ifInUnknownProtos
                    Counter,
                ifOutOctets
                    Counter,
                ifOutUcastPkts
                    Counter,
                ifOutNUcastPkts
                    Counter,
                ifOutDiscards
                    Counter,
                ifOutErrors
                    Counter,
                ifOutQLen
                    Gauge,
                ifSpecific
                    OBJECT IDENTIFIER
        }

        ifIndex OBJECT-TYPE
                SYNTAX  INTEGER
                ACCESS  read-only
                STATUS  mandatory
	DESCRIPTION ""
                ::= { ifEntry 1 }

        ifDescr OBJECT-TYPE
                SYNTAX  DisplayString (SIZE(0..255))
                ACCESS  read-only
                STATUS  mandatory
	DESCRIPTION ""
                ::= { ifEntry 2 }

        ifType OBJECT-TYPE
                SYNTAX  INTEGER {
                                other(1),       -- none of the following
                                regular1822(2),
                                hdh1822(3),
                                ddn-x25(4),
                                rfc877-x25(5),
                                ethernet-csmacd(6),
                                iso88023-csmacd(7),
                                iso88024-tokenBus(8),
                                iso88025-tokenRing(9),
                                iso88026-man(10),
                                starLan(11),
                                proteon-10Mbit(12),
                                proteon-80Mbit(13),
                                hyperchannel(14),
                                fddi(15),
                                lapb(16),
                                sdlc(17),
                                t1-carrier(18),
                                cept(19),       -- european
                                                -- equivalent of T-1
                                basicISDN(20),
                                primaryISDN(21),        -- proprietary
                                                        -- serial
                                propPointToPointSerial(22),
                                ppp(23),
                                softwareLoopback(24),
                                eon(25),                -- CLNP over IP
                                ethernet-3Mbit(26),
                                nsip(27),               -- XNS over IP
                                slip(28)                -- generic SLIP
                        }
                ACCESS  read-only
                STATUS  mandatory
	DESCRIPTION ""
                ::= { ifEntry 3 }

        ifMtu OBJECT-TYPE
                SYNTAX  INTEGER
                ACCESS  read-only
                STATUS  mandatory
	DESCRIPTION ""
                ::= { ifEntry 4 }

        ifSpeed OBJECT-TYPE
                SYNTAX  Gauge
                ACCESS  read-only
                STATUS  mandatory
	DESCRIPTION ""
                ::= { ifEntry 5 }

        ifPhyAddress OBJECT-TYPE
                SYNTAX  OCTET STRING
                ACCESS  read-only
                STATUS  mandatory
	DESCRIPTION ""
                ::= { ifEntry 6 }

        ifAdminStatus OBJECT-TYPE
                SYNTAX  INTEGER {
                                up(1),          -- ready to pass packets
                                down(2),
                                testing(3)      -- in some test mode
                        }
                ACCESS  read-write
                STATUS  mandatory
	DESCRIPTION ""
                ::= { ifEntry 7 }

        ifOperStatus OBJECT-TYPE
                SYNTAX  INTEGER {
                                up(1),          -- ready to pass packets
                                down(2),
                                testing(3)      -- in some test mode
                        }
                ACCESS  read-only
                STATUS  mandatory
	DESCRIPTION ""
                ::= { ifEntry 8 }

        ifLastChange OBJECT-TYPE
                SYNTAX  TimeTicks
                ACCESS  read-only
                STATUS  mandatory
	DESCRIPTION ""
                ::= { ifEntry 9 }

        ifInOctets OBJECT-TYPE
                SYNTAX  Counter
                ACCESS  read-only
                STATUS  mandatory
	DESCRIPTION ""
                ::= { ifEntry 10 }

        ifInUcastPkts OBJECT-TYPE
                SYNTAX  Counter
                ACCESS  read-only
                STATUS  mandatory
	DESCRIPTION ""
                ::= { ifEntry 11 }

        ifInNUcastPkts OBJECT-TYPE
                SYNTAX  Counter
                ACCESS  read-only
                STATUS  mandatory
	DESCRIPTION ""
                ::= { ifEntry 12 }

        ifInDiscards OBJECT-TYPE
                SYNTAX  Counter
                ACCESS  read-only
                STATUS  mandatory
	DESCRIPTION ""
                ::= { ifEntry 13 }

        ifInErrors OBJECT-TYPE
                SYNTAX  Counter
                ACCESS  read-only
                STATUS  mandatory
	DESCRIPTION ""
                ::= { ifEntry 14 }

        ifInUnknownProtos OBJECT-TYPE
                SYNTAX  Counter
                ACCESS  read-only
                STATUS  mandatory
	DESCRIPTION ""
                ::= { ifEntry 15 }

        ifOutOctets OBJECT-TYPE
                SYNTAX  Counter
                ACCESS  read-only
                STATUS  mandatory
	DESCRIPTION ""
                ::= { ifEntry 16 }

        ifOutUcastPkts OBJECT-TYPE
                SYNTAX  Counter
                ACCESS  read-only
                STATUS  mandatory
	DESCRIPTION ""
                ::= { ifEntry 17 }

        ifOutNUcastPkts OBJECT-TYPE
                SYNTAX  Counter
                ACCESS  read-only
                STATUS  mandatory
	DESCRIPTION ""
                ::= { ifEntry 18 }

        ifOutDiscards OBJECT-TYPE
                SYNTAX  Counter
                ACCESS  read-only
                STATUS  mandatory
	DESCRIPTION ""
                ::= { ifEntry 19 }

        ifOutErrors OBJECT-TYPE
                SYNTAX  Counter
                ACCESS  read-only
                STATUS  mandatory
	DESCRIPTION ""
                ::= { ifEntry 20 }

        ifOutQLen OBJECT-TYPE
                SYNTAX  Gauge
                ACCESS  read-only
                STATUS  mandatory
	DESCRIPTION ""
                ::= { ifEntry 21 }

        ifSpecific OBJECT-TYPE
                SYNTAX  OBJECT IDENTIFIER
                ACCESS  read-only
                STATUS  mandatory
	DESCRIPTION ""
                ::= { ifEntry 22 }

        -- the IP group

        ipForwarding OBJECT-TYPE
                SYNTAX  INTEGER {
                        gateway(1), -- entity forwards datagrams
                        host(2)     -- entity does NOT forward datagrams
                        }
                ACCESS  read-only
                STATUS  mandatory
	DESCRIPTION ""
                ::= { ip 1 }

        ipDefaultTTL OBJECT-TYPE
                SYNTAX  INTEGER
                ACCESS  read-write
                STATUS  mandatory
	DESCRIPTION ""
                ::= { ip 2 }

        ipInReceives OBJECT-TYPE
                SYNTAX  Counter
                ACCESS  read-only
                STATUS  mandatory
	DESCRIPTION ""
                ::= { ip 3 }

        ipInHdrErrors OBJECT-TYPE
                SYNTAX  Counter
                ACCESS  read-only
                STATUS  mandatory
	DESCRIPTION ""
                ::= { ip 4 }

        ipInAddrErrors OBJECT-TYPE
                SYNTAX  Counter
                ACCESS  read-only
                STATUS  mandatory
	DESCRIPTION ""
                ::= { ip 5 }

        ipForwDatagrams OBJECT-TYPE
                SYNTAX  Counter
                ACCESS  read-only
                STATUS  mandatory
	DESCRIPTION ""
                ::= { ip 6 }

        ipInUnknownProtos OBJECT-TYPE
                SYNTAX  Counter
                ACCESS  read-only
                STATUS  mandatory
	DESCRIPTION ""
                ::= { ip 7 }

        ipInDiscards OBJECT-TYPE
                SYNTAX  Counter
                ACCESS  read-only
                STATUS  mandatory
	DESCRIPTION ""
                ::= { ip 8 }

        ipInDelivers OBJECT-TYPE
                SYNTAX  Counter
                ACCESS  read-only
                STATUS  mandatory
	DESCRIPTION ""
                ::= { ip 9 }

        ipOutRequests OBJECT-TYPE
                SYNTAX  Counter
                ACCESS  read-only
                STATUS  mandatory
	DESCRIPTION ""
                ::= { ip 10 }

        ipOutDiscards OBJECT-TYPE
                SYNTAX  Counter
                ACCESS  read-only
                STATUS  mandatory
	DESCRIPTION ""
                ::= { ip 11 }

        ipOutNoRoutes OBJECT-TYPE
                SYNTAX  Counter
                ACCESS  read-only
                STATUS  mandatory
	DESCRIPTION ""
                ::= { ip 12 }

        ipReasmTimeout OBJECT-TYPE
                SYNTAX  INTEGER
                ACCESS  read-only
                STATUS  mandatory
	DESCRIPTION ""
                ::= { ip 13 }

        ipReasmReqds OBJECT-TYPE
                SYNTAX  Counter
                ACCESS  read-only
                STATUS  mandatory
	DESCRIPTION ""
                ::= { ip 14 }

        ipReasmOKs OBJECT-TYPE
                SYNTAX  Counter
                ACCESS  read-only
                STATUS  mandatory
	DESCRIPTION ""
                ::= { ip 15 }

        ipReasmFails OBJECT-TYPE
                SYNTAX  Counter
                ACCESS  read-only
                STATUS  mandatory
	DESCRIPTION ""
                ::= { ip 16 }

        ipFragOKs OBJECT-TYPE
                SYNTAX  Counter
                ACCESS  read-only
                STATUS  mandatory
	DESCRIPTION ""
                ::= { ip 17 }

        ipFragFails OBJECT-TYPE
                SYNTAX  Counter
                ACCESS  read-only
                STATUS  mandatory
	DESCRIPTION ""
                ::= { ip 18 }

        ipFragCreates OBJECT-TYPE
                SYNTAX  Counter
                ACCESS  read-only
                STATUS  mandatory
	DESCRIPTION ""
                ::= { ip 19 }

        -- the ICMP group

        icmpInMsgs OBJECT-TYPE
                SYNTAX  Counter
                ACCESS  read-only
                STATUS  mandatory
	DESCRIPTION ""
                ::= { icmp 1 }

        icmpInErrors OBJECT-TYPE
                SYNTAX  Counter
                ACCESS  read-only
                STATUS  mandatory
	DESCRIPTION ""
                ::= { icmp 2 }

        icmpInDestUnreachs OBJECT-TYPE
                SYNTAX  Counter
                ACCESS  read-only
                STATUS  mandatory
	DESCRIPTION ""
                ::= { icmp 3 }

        icmpInTimeExcds OBJECT-TYPE
                SYNTAX  Counter
                ACCESS  read-only
                STATUS  mandatory
	DESCRIPTION ""
                ::= { icmp 4 }

        icmpInParmProbs OBJECT-TYPE
                SYNTAX  Counter
                ACCESS  read-only
                STATUS  mandatory
	DESCRIPTION ""
                ::= { icmp 5 }

        icmpInSrcQuenchs OBJECT-TYPE
                SYNTAX  Counter
                ACCESS  read-only
                STATUS  mandatory
	DESCRIPTION ""
                ::= { icmp 6 }

        icmpInRedirects OBJECT-TYPE
                SYNTAX  Counter
                ACCESS  read-only
                STATUS  mandatory
	DESCRIPTION ""
                ::= { icmp 7 }

        icmpInEchos OBJECT-TYPE
                SYNTAX  Counter
                ACCESS  read-only
                STATUS  mandatory
	DESCRIPTION ""
                ::= { icmp 8 }

        icmpInEchoReps OBJECT-TYPE
                SYNTAX  Counter
                ACCESS  read-only
                STATUS  mandatory
	DESCRIPTION ""
                ::= { icmp 9 }

        icmpInTimestamps OBJECT-TYPE
                SYNTAX  Counter
                ACCESS  read-only
                STATUS  mandatory
	DESCRIPTION ""
                ::= { icmp 10 }

        icmpInTimestampReps OBJECT-TYPE
                SYNTAX  Counter
                ACCESS  read-only
                STATUS  mandatory
	DESCRIPTION ""
                ::= { icmp 11 }

        icmpInAddrMasks OBJECT-TYPE
                SYNTAX  Counter
                ACCESS  read-only
                STATUS  mandatory
	DESCRIPTION ""
                ::= { icmp 12 }

        icmpInAddrMaskReps OBJECT-TYPE
                SYNTAX  Counter
                ACCESS  read-only
                STATUS  mandatory
	DESCRIPTION ""
                ::= { icmp 13 }

        icmpOutMsgs OBJECT-TYPE
                SYNTAX  Counter
                ACCESS  read-only
                STATUS  mandatory
	DESCRIPTION ""
                ::= { icmp 14 }

        icmpOutErrors OBJECT-TYPE
                SYNTAX  Counter
                ACCESS  read-only
                STATUS  mandatory
	DESCRIPTION ""
                ::= { icmp 15 }

        icmpOutDestUnreachs OBJECT-TYPE
                SYNTAX  Counter
                ACCESS  read-only
                STATUS  mandatory
	DESCRIPTION ""
                ::= { icmp 16 }

        icmpOutTimeExcds OBJECT-TYPE
                SYNTAX  Counter
                ACCESS  read-only
                STATUS  mandatory
	DESCRIPTION ""
                ::= { icmp 17 }

        icmpOutParmProbs OBJECT-TYPE
                SYNTAX  Counter
                ACCESS  read-only
                STATUS  mandatory
	DESCRIPTION ""
                ::= { icmp 18 }

        icmpOutSrcQuenchs OBJECT-TYPE
                SYNTAX  Counter
                ACCESS  read-only
                STATUS  mandatory
	DESCRIPTION ""
                ::= { icmp 19 }

        icmpOutRedirects OBJECT-TYPE
                SYNTAX  Counter
                ACCESS  read-only
                STATUS  mandatory
	DESCRIPTION ""
                ::= { icmp 20 }

        icmpOutEchos OBJECT-TYPE
                SYNTAX  Counter
                ACCESS  read-only
                STATUS  mandatory
	DESCRIPTION ""
                ::= { icmp 21 }

        icmpOutEchoReps OBJECT-TYPE
                SYNTAX  Counter
                ACCESS  read-only
                STATUS  mandatory
	DESCRIPTION ""
                ::= { icmp 22 }

        icmpOutTimestamps OBJECT-TYPE
                SYNTAX  Counter
                ACCESS  read-only
                STATUS  mandatory
	DESCRIPTION ""
                ::= { icmp 23 }

        icmpOutTimestampReps OBJECT-TYPE
                SYNTAX  Counter
                ACCESS  read-only
                STATUS  mandatory
	DESCRIPTION ""
                ::= { icmp 24 }

        icmpOutAddrMasks OBJECT-TYPE
                SYNTAX  Counter
                ACCESS  read-only
                STATUS  mandatory
	DESCRIPTION ""
                ::= { icmp 25 }

        icmpOutAddrMaskReps OBJECT-TYPE
                SYNTAX  Counter
                ACCESS  read-only
                STATUS  mandatory
	DESCRIPTION ""
                ::= { icmp 26 }

        -- the UDP group

        udpInDatagrams OBJECT-TYPE
                SYNTAX  Counter
                ACCESS  read-only
                STATUS  mandatory
	DESCRIPTION ""
                ::= { udp 1 }

        udpNoPorts OBJECT-TYPE
                SYNTAX  Counter
                ACCESS  read-only
                STATUS  mandatory
	DESCRIPTION ""
                ::= { udp 2 }

        udpInErrors OBJECT-TYPE
                SYNTAX  Counter
                ACCESS  read-only
                STATUS  mandatory
	DESCRIPTION ""
                ::= { udp 3 }

        udpOutDatagrams OBJECT-TYPE
                SYNTAX  Counter
                ACCESS  read-only
                STATUS  mandatory
	DESCRIPTION ""
                ::= { udp 4 }

        -- the UDP listerner table

        udpTable OBJECT-TYPE
                SYNTAX SEQUENCE OF UdpEntry
                ACCESS read-only
                STATUS mandatory
	DESCRIPTION ""
                ::= { udp 5 }

        udpEntry OBJECT-TYPE
                SYNTAX UdpEntry
                ACCESS read-only
                STATUS mandatory
	DESCRIPTION ""
                ::= { udpTable 1 }

        UdpEntry ::= SEQUENCE {
                udpLocalAddress
                        IpAddress,
                udpLocalPort
                        INTEGER (0..65535)
        }

        udpLocalAddress OBJECT-TYPE
                SYNTAX IpAddress
                ACCESS read-only
                STATUS mandatory
	DESCRIPTION ""
                ::= { udpEntry 1 }

        udpLocalPort OBJECT-TYPE
                SYNTAX INTEGER (0..65535)
                ACCESS read-only
                STATUS mandatory
	DESCRIPTION ""
                ::= { udpEntry 2 }

        -- the SNMP group

        snmpInPkts OBJECT-TYPE
                SYNTAX  Counter
                ACCESS  read-only
                STATUS  mandatory
	DESCRIPTION ""
                ::= { snmp 1 }

        snmpOutPkts OBJECT-TYPE
                SYNTAX  Counter
                ACCESS  read-only
                STATUS  mandatory
	DESCRIPTION ""
                ::= { snmp 2 }

        snmpInBadVersions OBJECT-TYPE
                SYNTAX  Counter
                ACCESS  read-only
                STATUS  mandatory
	DESCRIPTION ""
                ::= { snmp 3 }

        snmpInBadCommunityNames OBJECT-TYPE
                SYNTAX  Counter
                ACCESS  read-only
                STATUS  mandatory
	DESCRIPTION ""
                ::= { snmp 4 }

        snmpInBadCommunityUses OBJECT-TYPE
                SYNTAX  Counter
                ACCESS  read-only
                STATUS  mandatory
	DESCRIPTION ""
                ::= { snmp 5 }

        snmpInASNParseErrs OBJECT-TYPE
                SYNTAX  Counter
                ACCESS  read-only
                STATUS  mandatory
	DESCRIPTION ""
                ::= { snmp 6 }

        snmpInBadTypes OBJECT-TYPE
                SYNTAX  Counter
                ACCESS  read-only
                STATUS  mandatory
	DESCRIPTION ""
                ::= { snmp 7 }

        snmpInTooBigs OBJECT-TYPE
                SYNTAX  Counter
                ACCESS  read-only
                STATUS  mandatory
	DESCRIPTION ""
                ::= { snmp 8 }

        snmpInNoSuchNames OBJECT-TYPE
                SYNTAX  Counter
                ACCESS  read-only
                STATUS  mandatory
	DESCRIPTION ""
                ::= { snmp 9 }

        snmpInBadValues OBJECT-TYPE
                SYNTAX  Counter
                ACCESS  read-only
                STATUS  mandatory
	DESCRIPTION ""
                ::= { snmp 10 }

        snmpInReadOnlys OBJECT-TYPE
                SYNTAX  Counter
                ACCESS  read-only
                STATUS  mandatory
	DESCRIPTION ""
                ::= { snmp 11 }

        snmpInGenErrs OBJECT-TYPE
                SYNTAX  Counter
                ACCESS  read-only
                STATUS  mandatory
	DESCRIPTION ""
                ::= { snmp 12 }

        snmpInTotalReqVars OBJECT-TYPE
                SYNTAX  Counter
                ACCESS  read-only
                STATUS  mandatory
	DESCRIPTION ""
                ::= { snmp 13 }

        snmpInTotalSetVars OBJECT-TYPE
                SYNTAX  Counter
                ACCESS  read-only
                STATUS  mandatory
	DESCRIPTION ""
                ::= { snmp 14 }

        snmpInGetRequests OBJECT-TYPE
                SYNTAX  Counter
                ACCESS  read-only
                STATUS  mandatory
	DESCRIPTION ""
                ::= { snmp 15 }

        snmpInGetNexts OBJECT-TYPE
                SYNTAX  Counter
                ACCESS  read-only
                STATUS  mandatory
	DESCRIPTION ""
                ::= { snmp 16 }

        snmpInSetRequests OBJECT-TYPE
                SYNTAX  Counter
                ACCESS  read-only
                STATUS  mandatory
	DESCRIPTION ""
                ::= { snmp 17 }

        snmpInGetResponses OBJECT-TYPE
                SYNTAX  Counter
                ACCESS  read-only
                STATUS  mandatory
	DESCRIPTION ""
                ::= { snmp 18 }

        snmpInTraps OBJECT-TYPE
                SYNTAX  Counter
                ACCESS  read-only
                STATUS  mandatory
	DESCRIPTION ""
                ::= { snmp 19 }

        snmpOutTooBigs OBJECT-TYPE
                SYNTAX  Counter
                ACCESS  read-only
                STATUS  mandatory
	DESCRIPTION ""
                ::= { snmp 20 }

        snmpOutNoSuchNames OBJECT-TYPE
                SYNTAX  Counter
                ACCESS  read-only
                STATUS  mandatory
	DESCRIPTION ""
                ::= { snmp 21 }

        snmpOutBadValues OBJECT-TYPE
                SYNTAX  Counter
                ACCESS  read-only
                STATUS  mandatory
	DESCRIPTION ""
                ::= { snmp 22 }

        snmpOutReadOnlys OBJECT-TYPE
                SYNTAX  Counter
                ACCESS  read-only
                STATUS  mandatory
	DESCRIPTION ""
                ::= { snmp 23 }

        snmpOutGenErrs OBJECT-TYPE
                SYNTAX  Counter
                ACCESS  read-only
                STATUS  mandatory
	DESCRIPTION ""
                ::= { snmp 24 }

        snmpOutGetRequests OBJECT-TYPE
                SYNTAX  Counter
                ACCESS  read-only
                STATUS  mandatory
	DESCRIPTION ""
                ::= { snmp 25 }

        snmpOutGetNexts OBJECT-TYPE
                SYNTAX  Counter
                ACCESS  read-only
                STATUS  mandatory
	DESCRIPTION ""
                ::= { snmp 26 }

        snmpOutSetRequests OBJECT-TYPE
                SYNTAX  Counter
                ACCESS  read-only
                STATUS  mandatory
	DESCRIPTION ""
                ::= { snmp 27 }

        snmpOutGetResponses OBJECT-TYPE
                SYNTAX  Counter
                ACCESS  read-only
                STATUS  mandatory
	DESCRIPTION ""
                ::= { snmp 28 }

        snmpOutTraps OBJECT-TYPE
                SYNTAX  Counter
                ACCESS  read-only
                STATUS  mandatory
	DESCRIPTION ""
                ::= { snmp 29 }

        snmpEnableAuthTraps OBJECT-TYPE
                SYNTAX  INTEGER {
                                enabled(1),
                                disabled(2)
                        }
                ACCESS  read-write
                STATUS  mandatory
	DESCRIPTION ""
                ::= { snmp 30 }

        d-link     OBJECT IDENTIFIER ::= { enterprises 171}
        hubmib             OBJECT IDENTIFIER ::= {d-link 2}
        basicGroup         OBJECT IDENTIFIER ::= {hubmib 1}
        monitorGroup       OBJECT IDENTIFIER ::= {hubmib 2}
        addrTrackGroup     OBJECT IDENTIFIER ::= {hubmib 3}

        -- The D-Link Hub Basic Group 1.3.6.1.4.1.171.2.1
        -- 1.3.6.1.4.1.171.2.1.1.0
        basicHubMIBVersion OBJECT-TYPE
                SYNTAX  DisplayString
                ACCESS  read-only
                STATUS  mandatory
	DESCRIPTION ""
                ::= { basicGroup 1 }

        -- 1.3.6.1.4.1.171.2.1.2.0
        basicHubVender OBJECT-TYPE
                SYNTAX  OCTET STRING
                ACCESS  read-only
                STATUS  mandatory
	DESCRIPTION ""
                ::= { basicGroup 2 }

        -- 1.3.6.1.4.1.171.2.1.3.0
        basicHubProduct OBJECT-TYPE
                SYNTAX  OCTET STRING
                ACCESS  read-only
                STATUS  mandatory
	DESCRIPTION ""
                ::= { basicGroup 3 }

        -- 1.3.6.1.4.1.171.2.1.4.0
        basicHubVersion OBJECT-TYPE
                SYNTAX  OCTET STRING
                ACCESS  read-only
                STATUS  mandatory
	DESCRIPTION ""
                ::= { basicGroup 4 }

        -- 1.3.6.1.4.1.171.2.1.5.0
        basicHubHealthState OBJECT-TYPE
                SYNTAX  INTEGER {
                                other(1),         -- undefined or unknown
                                ok(2),            -- no known failures
                                hubFailure(3),    -- hub-related failure
                                groupFailure(4),  -- group-related failure
                                portFailure(5),   -- port_related failure
                                generalFailure(6) -- failure, unspecified type
                        }
                ACCESS  read-only
                STATUS  mandatory
	DESCRIPTION ""
                ::= { basicGroup 5 }

        -- 1.3.6.1.4.1.171.2.1.6.0
        basicHubHealthText OBJECT-TYPE
                SYNTAX  DisplayString
                ACCESS  read-only
                STATUS  mandatory
	DESCRIPTION ""
                ::= { basicGroup 6 }

        -- 1.3.6.1.4.1.171.2.1.7.0
        basicHubHealthData OBJECT-TYPE
                SYNTAX  OCTET STRING
                ACCESS  read-only
                STATUS  mandatory
	DESCRIPTION ""
                ::= { basicGroup 7 }

        -- 1.3.6.1.4.1.171.2.1.8.0
        basicHubReset OBJECT-TYPE
                SYNTAX  INTEGER {
                                noReset(1),     -- do nothing
                                reset(2)        -- reset the hub
                        }
                ACCESS  read-write
                STATUS  mandatory
	DESCRIPTION ""
                ::= { basicGroup 8 }

        -- 1.3.6.1.4.1.171.2.1.9.0
        basicHubSelfTest1 OBJECT-TYPE
                SYNTAX  INTEGER {
                                noSelfTest1(1),
				selfTest1(2)
                        }
                ACCESS  read-write
                STATUS  mandatory
	DESCRIPTION ""
                ::= { basicGroup  9 }

        -- 1.3.6.1.4.1.171.2.1.10.0
        basicHubSelfTest2 OBJECT-TYPE
                SYNTAX  INTEGER {
                                noSelfTest2(1),
				selfTest2(2)
                        }
                ACCESS  read-write
                STATUS  mandatory
	DESCRIPTION ""
                ::= {basicGroup  10 }

        -- 1.3.6.1.4.1.171.2.1.11.0
        basucHubIntrusion OBJECT-TYPE
                SYNTAX  INTEGER {
                                noIntrusion(1),
				intrusion(2)
                        }
                ACCESS  read-write
                STATUS  mandatory
	DESCRIPTION ""
                ::= { basicGroup 11 }

        -- 1.3.6.1.4.1.171.2.1.12.0
        basicHubClearStats OBJECT-TYPE
                SYNTAX  INTEGER {
                                other(1),
                                clearstatsistics(2)
                        }
                ACCESS  read-write
                STATUS  mandatory
	DESCRIPTION ""
                ::= { basicGroup 12 }

        -- 1.3.6.1.4.1.171.2.1.13.0
        basicHubLed OBJECT-TYPE
                SYNTAX  OCTET STRING
                ACCESS  read-only
                STATUS  mandatory
	DESCRIPTION ""
                ::= { basicGroup 13 }

        -- 1.3.6.1.4.1.171.2.1.14.0
        basicHubNumofPorts OBJECT-TYPE
                SYNTAX  INTEGER
                ACCESS  read-only
                STATUS  mandatory
	DESCRIPTION ""
                ::= { basicGroup 14 }

        -- The D-Link Hub Basic Port Table 1.3.6.1.4.1.171.2.1.15

        basicPortTable OBJECT-TYPE
                SYNTAX  SEQUENCE OF BasicPortEntry
                ACCESS  read-only
                STATUS  mandatory
	DESCRIPTION ""
                ::= { basicGroup 15 }

        basicPortEntry OBJECT-TYPE
                SYNTAX  BasicPortEntry
                ACCESS  read-only
                STATUS  mandatory
	DESCRIPTION ""
                ::= { basicPortTable 1 }

        BasicPortEntry ::= SEQUENCE {
                basicPortID
                        INTEGER,
                basicPortAdminState
                        INTEGER,
                basicPortAutoPartState
                        INTEGER,
                basicPortName
                        DisplayString,
                basicPortType
                        INTEGER,
                basicPortLink
                        INTEGER,
                basicPortClearStats
                        INTEGER
        }

        -- 1.3.6.1.4.1.171.2.1.15.1.0xFF
        basicPortID OBJECT-TYPE
                SYNTAX  INTEGER
                ACCESS  read-only
                STATUS  mandatory
	DESCRIPTION ""
                ::= { basicPortEntry 1 }

        -- 1.3.6.1.4.1.171.2.1.15.2.0xFF
        basicPortAdminState OBJECT-TYPE
                SYNTAX  INTEGER {
                                disabled(1),
                                enabled(2)
                        }
                ACCESS  read-write
                STATUS  mandatory
	DESCRIPTION ""
                ::= { basicPortEntry 2 }

        -- 1.3.6.1.4.1.171.2.1.15.3.0xFF
        basicPortAutoPartState OBJECT-TYPE
                SYNTAX  INTEGER {
                                autoPartitioned(1),
                                notAutoPartitioned(2)
                        }
                ACCESS  read-only
                STATUS  mandatory
	DESCRIPTION ""
                ::= { basicPortEntry 3 }

        -- 1.3.6.1.4.1.171.2.1.15.4.0xFF
        basicPortName OBJECT-TYPE
                SYNTAX  DisplayString
                ACCESS  read-write
                STATUS  mandatory
	DESCRIPTION ""
                ::= { basicPortEntry 4 }

        -- 1.3.6.1.4.1.171.2.1.15.5.0xFF
        basicPortType OBJECT-TYPE
                SYNTAX  INTEGER {
                                other(1),
                                tenBASET(2),
                                tenBASE2(3),
                                tenBASE5(4)
                        }
                ACCESS  read-only
                STATUS  mandatory
	DESCRIPTION ""
                ::= { basicPortEntry 5 }

        -- 1.3.6.1.4.1.171.2.1.15.6.0xFF
        basicPortLink OBJECT-TYPE
                SYNTAX  INTEGER {
                                other(1),
                                down(2),
                                up(3)
                        }
                ACCESS  read-only
                STATUS  mandatory
	DESCRIPTION ""
                ::= { basicPortEntry 6 }

        -- 1.3.6.1.4.1.171.2.1.15.7.0xFF
        basicPortClearStats OBJECT-TYPE
                SYNTAX  INTEGER {
                                other(1),
                                clearportstats(2)
                        }
                ACCESS  read-write
                STATUS  mandatory
	DESCRIPTION ""
                ::= { basicPortEntry 7 }

        -- The D-Link Monitor Group  1.3.6.1.4.1.171.2.2

        -- The D-Link Hub Monitor Table

        -- 1.3.6.1.4.1.171.2.2.1.0
        monHubCollisions OBJECT-TYPE
                SYNTAX  Counter
                ACCESS  read-only
                STATUS  mandatory
	DESCRIPTION ""
                ::= { monitorGroup 1 }

        -- 1.3.6.1.4.1.171.2.2.2.0
        monHubBadFrames OBJECT-TYPE
                SYNTAX  Counter
                ACCESS  read-only
                STATUS  mandatory
	DESCRIPTION ""
                ::= { monitorGroup 2 }

        -- 1.3.6.1.4.1.171.2.2.3.0
        monHubReadableOctets OBJECT-TYPE
                SYNTAX  Counter
                ACCESS  read-only
                STATUS  mandatory
	DESCRIPTION ""
                ::= { monitorGroup 3 }

        -- 1.3.6.1.4.1.171.2.2.4.0
        monHubReadableFrames OBJECT-TYPE
                SYNTAX  Counter
                ACCESS  read-only
                STATUS  mandatory
	DESCRIPTION ""
                ::= { monitorGroup 4 }

        -- 1.3.6.1.4.1.171.2.2.5.0
        monHubLedFlag  OBJECT-TYPE
                SYNTAX  INTEGER
                ACCESS  read-write
                STATUS  mandatory
	DESCRIPTION ""
                ::= { monitorGroup 5 }

        -- 1.3.6.1.4.1.171.2.2.6.0
        monHubUtilization OBJECT-TYPE
                SYNTAX  INTEGER {
                                onePercentage(1),
                                twoPercentage(2),
                                fivePercentage(3),
                                tenPercentage(4),
                                fifteenPercentage(5),
                                twentyPercentage(6),
                                twenty-fivePercentage(7),
                                thirtyPercentage(8),
                                thirty-fivePercentage(9),
                                fortyPercentage(10),
                                fifty-fivePercentage(11),
                                finety-ninePercentage(12)
                }
                ACCESS  read-only
                STATUS  mandatory
	DESCRIPTION ""
                ::= { monitorGroup 6 }


        -- The D-Link Port Monitor Table 1.3.6.1.4.1.171.2.2.7

        monPortTable OBJECT-TYPE
                SYNTAX  SEQUENCE OF MonPortEntry
                ACCESS  read-only
                STATUS  mandatory
	DESCRIPTION ""
                ::= { monitorGroup 7 }

        monPortEntry OBJECT-TYPE
                SYNTAX  MonPortEntry
                ACCESS  read-only
                STATUS  mandatory
	DESCRIPTION ""
                ::= { monPortTable 1 }

        MonPortEntry ::= SEQUENCE {
                monPortID
                        INTEGER,
                monPortReadableFrames
                        Counter,
                monPortReadableOctets
                        Counter,
                monPortFcsErrors
                        Counter,
                monPortAlignmentErrors
                        Counter,
                monPortFrameTooLongs
                        Counter,
                monPortFrameTooShorts
                        Counter,
                monPortRunts
                        Counter,
                monPortCollisions
                        Counter,
                monPortLateCollisions
                        Counter,
                monPortDataRateMismatchs
                        Counter,
                monPortAutoPartitions
                        Counter,
                monPortBadFrames
                        Counter
        }

        -- 1.3.6.1.4.1.171.2.2.7.1.0xFF
        monPortID OBJECT-TYPE
                SYNTAX  INTEGER
                ACCESS  read-only
                STATUS  mandatory
	DESCRIPTION ""
                ::= { monPortEntry 1 }

        -- 1.3.6.1.4.1.171.2.2.7.2.0xFF
        monPortReadableFrames OBJECT-TYPE
                SYNTAX  Counter
                ACCESS  read-only
                STATUS  mandatory
	DESCRIPTION ""
                ::= { monPortEntry 2 }

        -- 1.3.6.1.4.1.171.2.2.7.3.0xFF
        monPortReadableOctets OBJECT-TYPE
                SYNTAX  Counter
                ACCESS  read-only
                STATUS  mandatory
	DESCRIPTION ""
                ::= { monPortEntry 3 }

        -- 1.3.6.1.4.1.171.2.2.7.4.0xFF
        monPortFcsErrors OBJECT-TYPE
                SYNTAX  Counter
                ACCESS  read-only
                STATUS  mandatory
	DESCRIPTION ""
                ::= { monPortEntry 4 }

        -- 1.3.6.1.4.1.171.2.2.7.5.0xFF
        monPortAlignmentErrors OBJECT-TYPE
                SYNTAX  Counter
                ACCESS  read-only
                STATUS  mandatory
	DESCRIPTION ""
                ::= { monPortEntry 5 }

        -- 1.3.6.1.4.1.171.2.2.7.6.0xFF
        monPortFrameTooLongs OBJECT-TYPE
                SYNTAX  Counter
                ACCESS  read-only
                STATUS  mandatory
	DESCRIPTION ""
                ::= { monPortEntry 6 }

        -- 1.3.6.1.4.1.171.2.2.7.7.0xFF
        monPortFrameTooShorts OBJECT-TYPE
                SYNTAX  Counter
                ACCESS  read-only
                STATUS  mandatory
	DESCRIPTION ""
                ::= { monPortEntry 7 }

        -- 1.3.6.1.4.1.171.2.2.7.8.0xFF
        monPortRunts OBJECT-TYPE
                SYNTAX  Counter
                ACCESS  read-only
                STATUS  mandatory
	DESCRIPTION ""
                ::= { monPortEntry 8 }

        -- 1.3.6.1.4.1.171.2.2.7.9.0xFF
        monPortCollisions OBJECT-TYPE
                SYNTAX  Counter
                ACCESS  read-only
                STATUS  mandatory
	DESCRIPTION ""
                ::= { monPortEntry 9 }

        -- 1.3.6.1.4.1.171.2.2.7.10.0xFF
        monPortLateCollisions OBJECT-TYPE
                SYNTAX  Counter
                ACCESS  read-only
                STATUS  mandatory
	DESCRIPTION ""
                ::= { monPortEntry 10 }

        -- 1.3.6.1.4.1.171.2.2.7.11.0xFF
        monPortDataRateMismatchs OBJECT-TYPE
                SYNTAX  Counter
                ACCESS  read-only
                STATUS  mandatory
	DESCRIPTION ""
                ::= { monPortEntry 11 }

        -- 1.3.6.1.4.1.171.2.2.7.12.0xFF
        monPortAutoPartitions OBJECT-TYPE
                SYNTAX  Counter
                ACCESS  read-only
                STATUS  mandatory
	DESCRIPTION ""
                ::= { monPortEntry 12}

        -- 1.3.6.1.4.1.171.2.2.7.13.0xFF
        monPortBadFrames OBJECT-TYPE
                SYNTAX  Counter
                ACCESS  read-only
                STATUS  mandatory
	DESCRIPTION ""
                ::= { monPortEntry 13 }

        -- The D-Link Port Address Tracking Table 1.3.6.1.4.1.171.2.3

        addPortTable OBJECT-TYPE
                SYNTAX  SEQUENCE OF AddPortEntry
                ACCESS  read-only
                STATUS  mandatory
	DESCRIPTION ""
                ::= { addrTrackGroup 1 }

        addPortEntry OBJECT-TYPE
                SYNTAX  AddPortEntry
                ACCESS  read-only
                STATUS  mandatory
	DESCRIPTION ""
                ::= { addPortTable 1 }

        AddPortEntry ::= SEQUENCE {
                addPortID
                        INTEGER,
                addPortLastSourceAddress
                        OCTET STRING,
                addPortSourceAddrChanges
                        Counter,
                addPortAuthorized
                        INTEGER
        }

        -- 1.3.6.1.4.1.171.2.3.1.0xFF
        addPortID OBJECT-TYPE
                SYNTAX  INTEGER
                ACCESS  read-only
                STATUS  mandatory
	DESCRIPTION ""
                ::= { addPortEntry 1 }

        -- 1.3.6.1.4.1.171.2.3.2.0xFF
        addPortLastSourceAddress OBJECT-TYPE
                SYNTAX  OCTET STRING (SIZE(6))
                ACCESS  read-write
                STATUS  mandatory
	DESCRIPTION ""
                ::= { addPortEntry 2 }

        -- 1.3.6.1.4.1.171.2.3.3.0xFF
        addPortSourceAddrChanges OBJECT-TYPE
                SYNTAX  Counter
                ACCESS  read-only
                STATUS  mandatory
	DESCRIPTION ""
                ::= { addPortEntry 3 }

        -- 1.3.6.1.4.1.171.2.3.4.0xFF
        addPortAuthorized OBJECT-TYPE
                SYNTAX  INTEGER {
                                unauthorized(1),
                                authorized(2)
                }
                ACCESS  read-write
                STATUS  mandatory
	DESCRIPTION ""
                ::= { addPortEntry 4 }
    END
