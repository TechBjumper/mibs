NETFINITYMANAGER-MIB DEFINITIONS ::= BEGIN


 -- Manager package for NetFinity

IMPORTS
    OBJECT-TYPE FROM RFC-1212
    enterprises FROM RFC1155-SMI
    DisplayString FROM RFC1213-MIB
	 dmiMibs FROM NETFINITYSERVICES-MIB
	 DisplayString FROM SNMPv2-TC;

DmiInteger                      ::= INTEGER
DmiOctetstring          ::= OCTET STRING
DmiDisplaystring        ::= DisplayString
DmiDate                         ::= OCTET STRING (SIZE (28))
DmiComponentIndex       ::= INTEGER

netFinityManagerMIB     OBJECT IDENTIFIER ::= { dmiMibs 3 }
dmtfGroups2             OBJECT IDENTIFIER ::= {netFinityManagerMIB  1}

SComponentid ::= SEQUENCE {
        a1Manufacturer                                  DmiDisplaystring,
        a1Product                                       DmiDisplaystring,
        a1Version                                       DmiDisplaystring,
        a1SerialNumber                                  DmiDisplaystring
}

tComponentid2 OBJECT-TYPE
        SYNTAX          SEQUENCE OF SComponentid
        ACCESS          not-accessible
        STATUS          mandatory
        DESCRIPTION     "This group defines attributes common to all components.This
group is required."
        ::= {dmtfGroups2 1}

eComponentid2 OBJECT-TYPE
        SYNTAX          SComponentid
        ACCESS          not-accessible
        STATUS          mandatory
        DESCRIPTION     ""
        --INDEX           {DmiComponentIndex}
        ::= {tComponentid2 1}

a1Manufacturer OBJECT-TYPE
        SYNTAX          DmiDisplaystring
        ACCESS          read-only
        STATUS          mandatory
        DESCRIPTION     "The name of the manufacturer that produces this component."
        ::= {eComponentid2 1}

a1Product OBJECT-TYPE
        SYNTAX          DmiDisplaystring
        ACCESS          read-only
        STATUS          mandatory
        DESCRIPTION     "The name of the component."
        ::= {eComponentid2 2}

a1Version OBJECT-TYPE
        SYNTAX          DmiDisplaystring
        ACCESS          read-only
        STATUS          mandatory
        DESCRIPTION     "The version for the component."
        ::= {eComponentid2 3}

a1SerialNumber OBJECT-TYPE
        SYNTAX          DmiDisplaystring
        ACCESS          read-only
        STATUS          mandatory
        DESCRIPTION     "The serial number for this instance of this component."
        ::= {eComponentid2 4}

SRemoteSystems ::= SEQUENCE {
        a11SystemTag                                    DmiInteger,
        a11SystemName                                   DmiDisplaystring,
        a11ProtocolName                                 DmiDisplaystring,
        a11NetworkAddress                               DmiDisplaystring,
        a11SystemState                                  DmiInteger,
        a11Server                                       DmiInteger,
        a11Manager                                      DmiInteger,
        a11OperatingSystemType                          DmiInteger,
        a11OsMajorVersion                               DmiInteger,
        a11OsMinorVersion                               DmiInteger,
        a11SystemModelId                                DmiOctetstring,
        a11SystemModelName                              DmiDisplaystring,
        a11SystemOn-lineNotify                          DmiInteger,
        a11SystemOff-lineNotify                         DmiInteger,
        a11PresenceCheckInterval                        DmiInteger,
        a11MacAddress                                   DmiOctetstring
}

tRemoteSystems OBJECT-TYPE
        SYNTAX          SEQUENCE OF SRemoteSystems
        ACCESS          not-accessible
        STATUS          mandatory
        DESCRIPTION     "Table of remote systems defined for managing under the Remote
System Manager service."
        ::= {dmtfGroups2 11}

eRemoteSystems OBJECT-TYPE
        SYNTAX          SRemoteSystems
        ACCESS          not-accessible
        STATUS          mandatory
        DESCRIPTION     ""
        --INDEX           {DmiComponentIndex, a11SystemTag}
        ::= {tRemoteSystems 1}

a11SystemTag OBJECT-TYPE
        SYNTAX          DmiInteger
        ACCESS          read-only
        STATUS          mandatory
        DESCRIPTION     "Unique ID number of this remote system in Remote System Manager."
        ::= {eRemoteSystems 1}

a11SystemName OBJECT-TYPE
        SYNTAX          DmiDisplaystring
        ACCESS          read-only
        STATUS          mandatory
        DESCRIPTION     "Displayable name of the given system."
        ::= {eRemoteSystems 2}

a11ProtocolName OBJECT-TYPE
        SYNTAX          DmiDisplaystring
        ACCESS          read-only
        STATUS          mandatory
        DESCRIPTION     "This is the type of network protocol used for communication
with the given system."
        ::= {eRemoteSystems 3}

a11NetworkAddress OBJECT-TYPE
        SYNTAX          DmiDisplaystring
        ACCESS          read-only
        STATUS          mandatory
        DESCRIPTION     "This is the network address of the given system."
        ::= {eRemoteSystems 4}

a11SystemState OBJECT-TYPE
        SYNTAX          INTEGER {
                vOff-line                                       (0),
                vOn-line                                        (1),
                vOff-lineWithErrorCondition                     (2),
                vOn-lineWithErrorCondition                      (3)
        }
        ACCESS          read-only
        STATUS          mandatory
        DESCRIPTION     "This reflects the on-line/off-line state of the given system."
        ::= {eRemoteSystems 5}

a11Server OBJECT-TYPE
        SYNTAX          INTEGER {
                vFalse                                          (0),
                vTrue                                           (1)
        }
        ACCESS          read-only
        STATUS          mandatory
        DESCRIPTION     "This indicates if the system is some sort of server system."
        ::= {eRemoteSystems 6}

a11Manager OBJECT-TYPE
        SYNTAX          INTEGER {
                vFalse                                          (0),
                vTrue                                           (1)
        }
        ACCESS          read-only
        STATUS          mandatory
        DESCRIPTION     "This indicates if the system is a NetFinity Manager system."
        ::= {eRemoteSystems 7}

a11OperatingSystemType OBJECT-TYPE
        SYNTAX          INTEGER {
                vUnknown                                        (0),
                vIbmOs2                                         (1),
                vMicrosoftWindows                               (2),
                vNovellNetware                                  (3),
                vMicrosoftWindowsNt                             (4),
                vIbmAix                                         (5),
                vBanyanVines                                    (6),
                vIbmPc-dos                                      (7),
                vScoXenix                                       (8),
                vUnixSystemV                                    (9),
                vMicrosoftWindows95                             (11)
        }
        ACCESS          read-only
        STATUS          mandatory
        DESCRIPTION     "The primary operating system running on the given system."
        ::= {eRemoteSystems 8}

a11OsMajorVersion OBJECT-TYPE
        SYNTAX          DmiInteger
        ACCESS          read-only
        STATUS          mandatory
        DESCRIPTION     "The major version of primary operating system running on
the given system."
        ::= {eRemoteSystems 9}

a11OsMinorVersion OBJECT-TYPE
        SYNTAX          DmiInteger
        ACCESS          read-only
        STATUS          mandatory
        DESCRIPTION     "The minor version of primary operating system running on
the given system."
        ::= {eRemoteSystems 10}

a11SystemModelId OBJECT-TYPE
        SYNTAX          DmiOctetstring
        ACCESS          read-only
        STATUS          mandatory
        DESCRIPTION     "These are the model identifier values for the given system.
 Systems which are the same non-zero model identifier are the same type of
system."
        ::= {eRemoteSystems 11}

a11SystemModelName OBJECT-TYPE
        SYNTAX          DmiDisplaystring
        ACCESS          read-only
        STATUS          mandatory
        DESCRIPTION     "This is the model name for the given system, if known."
        ::= {eRemoteSystems 12}

a11SystemOn-lineNotify OBJECT-TYPE
        SYNTAX          INTEGER {
                vSev0                                           (0),
                vSev1                                           (1),
                vSev2                                           (2),
                vSev3                                           (3),
                vSev4                                           (4),
                vSev5                                           (5),
                vSev6                                           (6),
                vSev7                                           (7),
                vNoDefault                                      (254),
                vDisabled                                       (255)
        }
        ACCESS          read-only
        STATUS          mandatory
        DESCRIPTION     "Severity of alert generated when system becomes on-line,
if enabled."
        ::= {eRemoteSystems 13}

a11SystemOff-lineNotify OBJECT-TYPE
        SYNTAX          INTEGER {
                vSev0                                           (0),
                vSev1                                           (1),
                vSev2                                           (2),
                vSev3                                           (3),
                vSev4                                           (4),
                vSev5                                           (5),
                vSev6                                           (6),
                vSev7                                           (7),
                vNoDefault                                      (254),
                vDisabled                                       (255)
        }
        ACCESS          read-only
        STATUS          mandatory
        DESCRIPTION     "Severity of alert generated when system becomes off-line,
if enabled."
        ::= {eRemoteSystems 14}

a11PresenceCheckInterval OBJECT-TYPE
        SYNTAX          DmiInteger
        ACCESS          read-only
        STATUS          mandatory
        DESCRIPTION     "This is the time between attempts by Remote System Manager
to verify the presence of the remote system, in seconds."
        ::= {eRemoteSystems 15}

a11MacAddress OBJECT-TYPE
        SYNTAX          DmiOctetstring
        ACCESS          read-only
        STATUS          mandatory
        DESCRIPTION     "Media Access Control (MAC) address of remote system, if known."
        ::= {eRemoteSystems 16}

SRemoteSystemGroups ::= SEQUENCE {
        a12GroupTag                                     DmiInteger,
        a12GroupName                                    DmiDisplaystring,
        a12RequiredKeywordsCombination                  DmiInteger,
        a12Keywords                                     DmiDisplaystring,
        a12SystemOn-lineNotifyDefault                   DmiInteger,
        a12SystemOff-lineNotifyDefault                  DmiInteger,
        a12DefaultPresenceCheckInterval                 DmiInteger,
        a12DiscoveryStartFlag                           DmiInteger
}

tRemoteSystemGroups OBJECT-TYPE
        SYNTAX          SEQUENCE OF SRemoteSystemGroups
        ACCESS          not-accessible
        STATUS          mandatory
        DESCRIPTION     "Table of remote system groups defined for managing under
the Remote System Manager service."
        ::= {dmtfGroups2 12}

eRemoteSystemGroups OBJECT-TYPE
        SYNTAX          SRemoteSystemGroups
        ACCESS          not-accessible
        STATUS          mandatory
        DESCRIPTION     ""
        --INDEX           {DmiComponentIndex, a12GroupTag}
        ::= {tRemoteSystemGroups 1}

a12GroupTag OBJECT-TYPE
        SYNTAX          DmiInteger
        ACCESS          read-only
        STATUS          mandatory
        DESCRIPTION     "Unique ID number of this system group in Remote System Manager."
        ::= {eRemoteSystemGroups 1}

a12GroupName OBJECT-TYPE
        SYNTAX          DmiDisplaystring
        ACCESS          read-only
        STATUS          mandatory
        DESCRIPTION     "Displayable name of the given group."
        ::= {eRemoteSystemGroups 2}

a12RequiredKeywordsCombination OBJECT-TYPE
        SYNTAX          INTEGER {
                vAllKeywordsMustMatch                           (0),
                vAnyOfTheKeywordsMayMatch                       (1),
                vExactlyOneOfTheKeywordsMustMatch               (2)
        }
        ACCESS          read-only
        STATUS          mandatory
        DESCRIPTION     "This reflects whether all, any, or one of the keywords for
the group must be matched during a discovery request in order for a remote
system to be discovered."
        ::= {eRemoteSystemGroups 3}

a12Keywords OBJECT-TYPE
        SYNTAX          DmiDisplaystring
        ACCESS          read-only
        STATUS          mandatory
        DESCRIPTION     "List of keywords which are used for finding remote systems
during a discovery request."
        ::= {eRemoteSystemGroups 4}

a12SystemOn-lineNotifyDefault OBJECT-TYPE
        SYNTAX          INTEGER {
                vSev0                                           (0),
                vSev1                                           (1),
                vSev2                                           (2),
                vSev3                                           (3),
                vSev4                                           (4),
                vSev5                                           (5),
                vSev6                                           (6),
                vSev7                                           (7),
                vNoDefault                                      (254),
                vDisabled                                       (255)
        }
        ACCESS          read-only
        STATUS          mandatory
        DESCRIPTION     "On-line notification default for systems in this group, if
enabled."
        ::= {eRemoteSystemGroups 5}

a12SystemOff-lineNotifyDefault OBJECT-TYPE
        SYNTAX          INTEGER {
                vSev0                                           (0),
                vSev1                                           (1),
                vSev2                                           (2),
                vSev3                                           (3),
                vSev4                                           (4),
                vSev5                                           (5),
                vSev6                                           (6),
                vSev7                                           (7),
                vNoDefault                                      (254),
                vDisabled                                       (255)
        }
        ACCESS          read-only
        STATUS          mandatory
        DESCRIPTION     "Off-line notification default for systems in this group,
if enabled."
        ::= {eRemoteSystemGroups 6}

a12DefaultPresenceCheckInterval OBJECT-TYPE
        SYNTAX          DmiInteger
        ACCESS          read-only
        STATUS          mandatory
        DESCRIPTION     "This is the default time between attempts by Remote System
Manager to verify the presence of the system in this group, in seconds.
0 = No group-specific default."
        ::= {eRemoteSystemGroups 7}

a12DiscoveryStartFlag OBJECT-TYPE
        SYNTAX          DmiInteger
        ACCESS          read-write
        STATUS          mandatory
        DESCRIPTION     "The value of this flag is not significant.  To start a discovery
request on the given System Group, write any value to this field."
        ::= {eRemoteSystemGroups 8}

SRemoteSystemGroupMap ::= SEQUENCE {
        a13SystemTag                                    DmiInteger,
        a13GroupTag                                     DmiInteger
}

tRemoteSystemGroupMap OBJECT-TYPE
        SYNTAX          SEQUENCE OF SRemoteSystemGroupMap
        ACCESS          not-accessible
        STATUS          mandatory
        DESCRIPTION     "Table mapping the membership of remote system in groups in
the Remote System Manager service."
        ::= {dmtfGroups2 13}

eRemoteSystemGroupMap OBJECT-TYPE
        SYNTAX          SRemoteSystemGroupMap
        ACCESS          not-accessible
        STATUS          mandatory
        DESCRIPTION     ""
        --INDEX           {DmiComponentIndex, a13SystemTag, a13GroupTag}
        ::= {tRemoteSystemGroupMap 1}

a13SystemTag OBJECT-TYPE
        SYNTAX          DmiInteger
        ACCESS          read-only
        STATUS          mandatory
        DESCRIPTION     "Unique ID number of remote system."
        ::= {eRemoteSystemGroupMap 1}

a13GroupTag OBJECT-TYPE
        SYNTAX          DmiInteger
        ACCESS          read-only
        STATUS          mandatory
        DESCRIPTION     "Unique ID number of group containing the remote system."
        ::= {eRemoteSystemGroupMap 2}

END
