--*****************************************************************
-- ZXR10-Qos-DS-MIB
-- OAM
-- 2013-7-5 11:28  wangfenghua
-- Copyright (c) 1985-2013 by ZTE Corp.
-- All rights reserved. 
--*****************************************************************


ZXR10-QOS-DS-MIB DEFINITIONS ::= BEGIN

IMPORTS
    MODULE-IDENTITY, OBJECT-TYPE, NOTIFICATION-TYPE,
    Unsigned32, Counter32,enterprises,IpAddress 
        FROM SNMPv2-SMI
    MODULE-COMPLIANCE, OBJECT-GROUP, NOTIFICATION-GROUP
        FROM SNMPv2-CONF
    DisplayString, MacAddress, TEXTUAL-CONVENTION, RowStatus
        FROM SNMPv2-TC
    zxr10,zxr10RosngMIB        
        FROM ZXR10-SMI; 
    
zxr10QosDsMIB MODULE-IDENTITY
        LAST-UPDATED "201309131500Z"
        ORGANIZATION "ZTE Corporation"
        CONTACT-INFO
            "       Hu Jun
            Tel:    +86-25-52870000
            E-Mail: hu.jun11@zte.com.cn "
        DESCRIPTION
            "The MIB module to describe the QOS diffserv protocol."
              
        REVISION "201309131500Z"
        DESCRIPTION
            "The leaf of zxr10QosDsPHBCosType adds ipv6_dscp,
             and modify zxr10QosDSPHBCosValue" 
             
        REVISION "201307051000Z"
        DESCRIPTION 
            "Add zxr10QosDsMIB and 
             Initial version of this MIB module.
             "
        ::= { zxr10QosMIBObjects 4 }
        
             
zxr10QosMIBObjects             OBJECT IDENTIFIER ::= { zxr10RosngMIB 30}

--******************************************************
--    Following objects are defined.   
--******************************************************   

zxr10QosDsGlobalObjects   OBJECT IDENTIFIER ::= { zxr10QosDsMIB 1}
zxr10QosDsObjects         OBJECT IDENTIFIER ::= { zxr10QosDsMIB 2}  
zxr10QosDsNotifications   OBJECT IDENTIFIER ::= { zxr10QosDsMIB 3}
zxr10QosDsConformance     OBJECT IDENTIFIER ::= { zxr10QosDsMIB 4}
  
zxr10QosDsDmObjects       OBJECT IDENTIFIER ::= { zxr10QosDsObjects 1 } 
zxr10QosDsIfBindObjects   OBJECT IDENTIFIER ::= { zxr10QosDsObjects 2 }
zxr10QosDsIfTrustObjects  OBJECT IDENTIFIER ::= { zxr10QosDsObjects 3 }
zxr10QosDsSchePwObjects   OBJECT IDENTIFIER ::= { zxr10QosDsObjects 4 }
zxr10QosDsScheTeObjects   OBJECT IDENTIFIER ::= { zxr10QosDsObjects 5 }

zxr10QosDsMapObjects      OBJECT IDENTIFIER ::= { zxr10QosDsDmObjects 2 }



--******************************************************
--    he follow part defined some data types which will 
--    be used in this mib file later  
--******************************************************   
QosDsSrvClass ::= TEXTUAL-CONVENTION
    STATUS       current
    DESCRIPTION
            "server class of PHB info ,see below:
             be  Best effort
             af1 Assured forwarding class 1
             af2 Assured forwarding class 2
             af3 Assured forwarding class 3
             af4 Assured forwarding class 4
             ef  Expedited forward
             cs6 Internetwork control service class
             cs7 Network control service class"
    SYNTAX   INTEGER {be(1),af1(2),af2(3),af3(4),
                      af4(5),ef(6),cs6(7),cs7(8)} 
    
QosDsColor ::= TEXTUAL-CONVENTION
    STATUS       current
    DESCRIPTION
            "Color of PHB info, see below:
             green   Green packets
             yellow  Yellow packets
             red     Red packets"
    SYNTAX   INTEGER {green(1),yellow(2),red(3)}   
    
    
--******************************************************
--    zxr10QosDsDmTable   
--****************************************************** 
zxr10QosDsDmTable OBJECT-TYPE
        SYNTAX  SEQUENCE OF Zxr10QosDsDmEntry
        MAX-ACCESS  not-accessible
        STATUS  current
        DESCRIPTION
                "Diffserv Domain Table"
        ::= { zxr10QosDsDmObjects 1  }

zxr10QosDsDmEntry OBJECT-TYPE
        SYNTAX   Zxr10QosDsDmEntry
        MAX-ACCESS  not-accessible
        STATUS  current
        DESCRIPTION
                "Template of diffserv domain:
                 the max number of template is 8,
                 and every template has a special
                 id(from 1 to 8),which is automatically 
                 generated by MIM"
        INDEX {zxr10QosDsDmName }
        ::= { zxr10QosDsDmTable 1 }

Zxr10QosDsDmEntry ::= 
        SEQUENCE {
           zxr10QosDsDmName   
              DisplayString,
           zxr10QosDsDmId
              Unsigned32                
        }

zxr10QosDsDmName OBJECT-TYPE
        SYNTAX   DisplayString(SIZE(0..31))
        MAX-ACCESS  not-accessible
        STATUS  current
        DESCRIPTION
                "WORD 
                 Name of the diffserv domain(1-31 characters)"
        ::= { zxr10QosDsDmEntry  1  }

zxr10QosDsDmId OBJECT-TYPE
        SYNTAX   Unsigned32(1..8)
        MAX-ACCESS  read-only
        STATUS  current
        DESCRIPTION
                "ID of the diffserv domain,from 1 to 8"
        ::= { zxr10QosDsDmEntry  2  }   
        
--******************************************************
--  zxr10QosDs8021pTable  
--****************************************************** 
zxr10QosDs8021pTable OBJECT-TYPE
        SYNTAX  SEQUENCE OF Zxr10QosDs8021pEntry
        MAX-ACCESS  not-accessible
        STATUS  current
        DESCRIPTION
                "8021p Table"
        ::= { zxr10QosDsMapObjects 1  }
        
zxr10QosDs8021pEntry OBJECT-TYPE
        SYNTAX   Zxr10QosDs8021pEntry
        MAX-ACCESS  not-accessible
        STATUS  current
        DESCRIPTION
                "Map 802.1p to PHB.
                 PHB include server class and color."
        INDEX {zxr10QosDs8021pDmName,
               zxr10QosDs8021pValue}
        ::= { zxr10QosDs8021pTable 1 }

Zxr10QosDs8021pEntry ::=
        SEQUENCE {
                zxr10QosDs8021pDmName       
                    DisplayString,
                zxr10QosDs8021pValue        
                    Unsigned32,
                zxr10QosDs8021pClass        
                    QosDsSrvClass,
                zxr10QosDs8021pColor        
                    QosDsColor                
        } 
        
zxr10QosDs8021pDmName OBJECT-TYPE
        SYNTAX   DisplayString(SIZE(0..31))
        MAX-ACCESS  not-accessible
        STATUS  current
        DESCRIPTION
                "WORD 
                 Name of the diffserv domain(1-31 characters)"
        ::= { zxr10QosDs8021pEntry  1  }    
        
zxr10QosDs8021pValue OBJECT-TYPE
        SYNTAX   Unsigned32(0..7)
        MAX-ACCESS  not-accessible
        STATUS  current
        DESCRIPTION
                "<0-7> 8021p value."
        ::= { zxr10QosDs8021pEntry  2  }    
        
zxr10QosDs8021pClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDs8021pEntry  3  } 
        
zxr10QosDs8021pColor OBJECT-TYPE
        SYNTAX   QosDsColor
        MAX-ACCESS  read-only
        STATUS  current
        DESCRIPTION
                "Color:
                 green   Green packets
                 yellow  Yellow packets
                 red     Red packets"
        ::= { zxr10QosDs8021pEntry  4  }   



--  ******************************************************
--                zxr10QosDsDscpTable
--  ******************************************************
zxr10QosDsDscpTable OBJECT-TYPE
        SYNTAX  SEQUENCE OF Zxr10QosDsDscpEntry
        MAX-ACCESS  not-accessible
        STATUS  current
        DESCRIPTION
                "IPv4 DSCP Table"
        ::= { zxr10QosDsMapObjects 2  }
        
zxr10QosDsDscpEntry OBJECT-TYPE
        SYNTAX   Zxr10QosDsDscpEntry
        MAX-ACCESS  not-accessible
        STATUS  current
        DESCRIPTION
                "Map IPv4 DSCP to PHB"
        INDEX {zxr10QosDsDscpDmName, 
               zxr10QosDsDscpValue}
        ::= { zxr10QosDsDscpTable 1 }

Zxr10QosDsDscpEntry ::=
        SEQUENCE {
                    zxr10QosDsDscpDmName       DisplayString,
                    zxr10QosDsDscpValue        Unsigned32,
                    zxr10QosDsDscpClass        QosDsSrvClass,
                    zxr10QosDsDscpColor        QosDsColor                
        } 
        
zxr10QosDsDscpDmName OBJECT-TYPE
        SYNTAX   DisplayString(SIZE(0..31))
        MAX-ACCESS  not-accessible
        STATUS  current
        DESCRIPTION
                "WORD 
                 Name of the diffserv domain(1-31 characters)"
        ::= { zxr10QosDsDscpEntry  1  }    
        
zxr10QosDsDscpValue OBJECT-TYPE
        SYNTAX   Unsigned32(0..63)
        MAX-ACCESS  not-accessible
        STATUS  current
        DESCRIPTION
                "<0-63> DSCP value"
        ::= { zxr10QosDsDscpEntry  2  }

zxr10QosDsDscpClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsDscpEntry  3  } 
        
zxr10QosDsDscpColor OBJECT-TYPE
        SYNTAX   QosDsColor
        MAX-ACCESS  read-only
        STATUS  current
        DESCRIPTION
                "Color:
                 green   Green packets
                 yellow  Yellow packets
                 red     Red packets"
        ::= { zxr10QosDsDscpEntry  4  }   
        

--  ******************************************************
--                zxr10QosDsV6DscpTable
--  ******************************************************
zxr10QosDsV6DscpTable OBJECT-TYPE
        SYNTAX  SEQUENCE OF Zxr10QosDsV6DscpEntry
        MAX-ACCESS  not-accessible
        STATUS  current
        DESCRIPTION
                "IPv6 DSCP Table"
        ::= { zxr10QosDsMapObjects 3  }
        
zxr10QosDsV6DscpEntry OBJECT-TYPE
        SYNTAX   Zxr10QosDsV6DscpEntry
        MAX-ACCESS  not-accessible
        STATUS  current
        DESCRIPTION
                "Map IPv6 DSCP to PHB"
        INDEX {zxr10QosDsV6DscpDmName, 
               zxr10QosDsV6DscpValue}
        ::= { zxr10QosDsV6DscpTable 1 }

Zxr10QosDsV6DscpEntry ::=
        SEQUENCE {
                 zxr10QosDsV6DscpDmName         
                     DisplayString,
                 zxr10QosDsV6DscpValue          
                     Unsigned32,
                 zxr10QosDsV6DscpClass         
                     QosDsSrvClass,
                 zxr10QosDsV6DscpColor          
                     QosDsColor                
        } 
        
zxr10QosDsV6DscpDmName OBJECT-TYPE
        SYNTAX   DisplayString(SIZE(0..31))
        MAX-ACCESS  not-accessible
        STATUS  current
        DESCRIPTION
                "WORD 
                 Name of the diffserv domain(1-31 characters)"
        ::= { zxr10QosDsV6DscpEntry  1  }    
        
zxr10QosDsV6DscpValue OBJECT-TYPE
        SYNTAX   Unsigned32(0..63)
        MAX-ACCESS  not-accessible
        STATUS  current
        DESCRIPTION
                "<0-63> IPv6 DSCP value"
        ::= { zxr10QosDsV6DscpEntry  2  }

zxr10QosDsV6DscpClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsV6DscpEntry  3  } 
        
zxr10QosDsV6DscpColor OBJECT-TYPE
        SYNTAX   QosDsColor
        MAX-ACCESS  read-only
        STATUS  current
        DESCRIPTION
                "Color:
                 green   Green packets
                 yellow  Yellow packets
                 red     Red packets"
        ::= { zxr10QosDsV6DscpEntry  4  }          

 
--  ******************************************************
--                zxr10QosDsMplsExpTable
--  ******************************************************
zxr10QosDsMplsExpTable OBJECT-TYPE
        SYNTAX  SEQUENCE OF Zxr10QosDsMplsExpEntry
        MAX-ACCESS  not-accessible
        STATUS  current
        DESCRIPTION
                "MPLSEXP Table"
        ::= { zxr10QosDsMapObjects 4  }
        
zxr10QosDsMplsExpEntry OBJECT-TYPE
        SYNTAX   Zxr10QosDsMplsExpEntry
        MAX-ACCESS  not-accessible
        STATUS  current
        DESCRIPTION
                "Map MPLSEXP to PHB"
        INDEX {zxr10QosDsMplsExpDmName, 
               zxr10QosDsMplsExpValue}
        ::= { zxr10QosDsMplsExpTable 1 }

Zxr10QosDsMplsExpEntry ::=
        SEQUENCE {
            zxr10QosDsMplsExpDmName        
                DisplayString,
            zxr10QosDsMplsExpValue         
                Unsigned32,
            zxr10QosDsMplsExpClass         
                QosDsSrvClass,
            zxr10QosDsMplsExpColor         
                QosDsColor                
        } 
        
zxr10QosDsMplsExpDmName OBJECT-TYPE
        SYNTAX   DisplayString(SIZE(0..31))
        MAX-ACCESS  not-accessible
        STATUS  current
        DESCRIPTION
                "WORD 
                 Name of the diffserv domain(1-31 characters)"
        ::= { zxr10QosDsMplsExpEntry  1  }    
        
zxr10QosDsMplsExpValue OBJECT-TYPE
        SYNTAX   Unsigned32(0..7)
        MAX-ACCESS  not-accessible
        STATUS  current
        DESCRIPTION
                "<0-7> MPLSEXP valu"
        ::= { zxr10QosDsMplsExpEntry  2  }

zxr10QosDsMplsExpClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsMplsExpEntry  3  } 
        
zxr10QosDsMplsExpColor OBJECT-TYPE
        SYNTAX   QosDsColor
        MAX-ACCESS  read-only
        STATUS  current
        DESCRIPTION
                "Color:
                 green   Green packets
                 yellow  Yellow packets
                 red     Red packets"
        ::= { zxr10QosDsMplsExpEntry  4  } 
                                             

--  ******************************************************
--                zxr10QosDsAclTable
--  ******************************************************
zxr10QosDsAclTable OBJECT-TYPE
        SYNTAX  SEQUENCE OF Zxr10QosDsAclEntry
        MAX-ACCESS  not-accessible
        STATUS  current
        DESCRIPTION
                "IPv4 ACL Table"
        ::= { zxr10QosDsMapObjects 5  }
        
zxr10QosDsAclEntry OBJECT-TYPE
        SYNTAX   Zxr10QosDsAclEntry
        MAX-ACCESS  not-accessible
        STATUS  current
        DESCRIPTION
                "Map IPv4 ACL to PHB"
        INDEX {zxr10QosDsAclDmName, 
               zxr10QosDsAclName}
        ::= { zxr10QosDsAclTable 1 }

Zxr10QosDsAclEntry ::=
        SEQUENCE {
                 zxr10QosDsAclDmName        
                     DisplayString,
                 zxr10QosDsAclName          
                     DisplayString,
                 zxr10QosDsAclClass         
                     QosDsSrvClass,
                 zxr10QosDsAclColor         
                     QosDsColor                
        } 
        
zxr10QosDsAclDmName OBJECT-TYPE
        SYNTAX   DisplayString(SIZE(0..31))
        MAX-ACCESS  not-accessible
        STATUS  current
        DESCRIPTION
                "WORD 
                 Name of the diffserv domain(1-31 characters)"
        ::= { zxr10QosDsAclEntry  1  }    
        
zxr10QosDsAclName OBJECT-TYPE
        SYNTAX   DisplayString(SIZE(0..31))
        MAX-ACCESS  not-accessible
        STATUS  current
        DESCRIPTION
                "WORD
                IPv4 ACL name(1-31 characters)"
        ::= { zxr10QosDsAclEntry  2  }

zxr10QosDsAclClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsAclEntry  3  } 
        
zxr10QosDsAclColor OBJECT-TYPE
        SYNTAX   QosDsColor
        MAX-ACCESS  read-only
        STATUS  current
        DESCRIPTION
                "Color:
                 green   Green packets
                 yellow  Yellow packets
                 red     Red packets"
        ::= { zxr10QosDsAclEntry  4  } 



--  ******************************************************
--                zxr10QosDsv6AclTable
--  ******************************************************

zxr10QosDsv6AclTable OBJECT-TYPE
        SYNTAX  SEQUENCE OF Zxr10QosDsv6AclEntry
        MAX-ACCESS  not-accessible
        STATUS  current
        DESCRIPTION
                "IPv6 ACL Table"
        ::= { zxr10QosDsMapObjects 6  }
        
zxr10QosDsv6AclEntry OBJECT-TYPE
        SYNTAX   Zxr10QosDsv6AclEntry
        MAX-ACCESS  not-accessible
        STATUS  current
        DESCRIPTION
                "Map IPv6 ACL to PHB"
        INDEX {zxr10QosDsv6AclDmName, 
               zxr10QosDsv6AclName}
        ::= { zxr10QosDsv6AclTable 1 }

Zxr10QosDsv6AclEntry ::=
        SEQUENCE {
                 zxr10QosDsv6AclDmName       
                     DisplayString,
                 zxr10QosDsv6AclName         
                     DisplayString,
                 zxr10QosDsv6AclClass        
                     QosDsSrvClass,
                 zxr10QosDsv6AclColor        
                     QosDsColor                
        } 
        
zxr10QosDsv6AclDmName OBJECT-TYPE
        SYNTAX   DisplayString(SIZE(0..31))
        MAX-ACCESS  not-accessible
        STATUS  current
        DESCRIPTION
                "WORD 
                 Name of the diffserv domain(1-31 characters)"
        ::= { zxr10QosDsv6AclEntry  1  }    
        
zxr10QosDsv6AclName OBJECT-TYPE
        SYNTAX   DisplayString(SIZE(0..31))
        MAX-ACCESS  not-accessible
        STATUS  current
        DESCRIPTION
                "WORD
                 IPv6 ACL name(1-31 characters)"
        ::= { zxr10QosDsv6AclEntry  2  }

zxr10QosDsv6AclClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsv6AclEntry  3  } 
        
zxr10QosDsv6AclColor OBJECT-TYPE
        SYNTAX   QosDsColor
        MAX-ACCESS  read-only
        STATUS  current
        DESCRIPTION
                "Color:
                 green   Green packets
                 yellow  Yellow packets
                 red     Red packets"
        ::= { zxr10QosDsv6AclEntry  4  } 


--  ******************************************************
--                zxr10QosDsLinkAclTable
--  ******************************************************
zxr10QosDsLinkAclTable OBJECT-TYPE
        SYNTAX  SEQUENCE OF Zxr10QosDsLinkAclEntry
        MAX-ACCESS  not-accessible
        STATUS  current
        DESCRIPTION
                "Link ACL Table"
        ::= { zxr10QosDsMapObjects 7  }
        
zxr10QosDsLinkAclEntry OBJECT-TYPE
        SYNTAX   Zxr10QosDsLinkAclEntry
        MAX-ACCESS  not-accessible
        STATUS  current
        DESCRIPTION
                "Map Link ACL to PHB."
        INDEX {zxr10QosDsLinkAclDmName, 
               zxr10QosDsLinkAclName}
        ::= { zxr10QosDsLinkAclTable 1 }

Zxr10QosDsLinkAclEntry ::=
        SEQUENCE {
                 zxr10QosDsLinkAclDmName     
                     DisplayString,
                 zxr10QosDsLinkAclName
                     DisplayString,
                 zxr10QosDsLinkAclClass
                     QosDsSrvClass,
                 zxr10QosDsLinkAclColor
                     QosDsColor                
        } 
        
zxr10QosDsLinkAclDmName OBJECT-TYPE
        SYNTAX   DisplayString(SIZE(0..31))
        MAX-ACCESS  not-accessible
        STATUS  current
        DESCRIPTION
                "WORD 
                 Name of the diffserv domain(1-31 characters)"
        ::= { zxr10QosDsLinkAclEntry  1  }    
        
zxr10QosDsLinkAclName OBJECT-TYPE
        SYNTAX   DisplayString(SIZE(0..31))
        MAX-ACCESS  not-accessible
        STATUS  current
        DESCRIPTION
                "WORD
                Link ACL name(1-31 characters)"
        ::= { zxr10QosDsLinkAclEntry  2  }

zxr10QosDsLinkAclClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsLinkAclEntry  3  } 
        
zxr10QosDsLinkAclColor OBJECT-TYPE
        SYNTAX   QosDsColor
        MAX-ACCESS  read-only
        STATUS  current
        DESCRIPTION
                "Color:
                 green   Green packets
                 yellow  Yellow packets
                 red     Red packets"
        ::= { zxr10QosDsLinkAclEntry  4  }
                                                                
                                                                
--  ******************************************************
--                zxr10QosDsv4MixAclTable
--  ******************************************************
zxr10QosDsv4MixAclTable OBJECT-TYPE
        SYNTAX  SEQUENCE OF Zxr10QosDsv4MixAclEntry
        MAX-ACCESS  not-accessible
        STATUS  current
        DESCRIPTION
                "IPv4 mixed ACL Table"
        ::= { zxr10QosDsMapObjects 8  }
        
zxr10QosDsv4MixAclEntry OBJECT-TYPE
        SYNTAX   Zxr10QosDsv4MixAclEntry
        MAX-ACCESS  not-accessible
        STATUS  current
        DESCRIPTION
                "Map IPv4 mixed ACL to PHB"
        INDEX {zxr10QosDsv4MixAclDmName,
               zxr10QosDsv4MixAclName}
        ::= { zxr10QosDsv4MixAclTable 1 }

Zxr10QosDsv4MixAclEntry ::=
        SEQUENCE {
                 zxr10QosDsv4MixAclDmName     
                     DisplayString,
                 zxr10QosDsv4MixAclName       
                     DisplayString,
                 zxr10QosDsv4MixAclClass      
                     QosDsSrvClass,
                 zxr10QosDsv4MixAclColor      
                     QosDsColor                
        } 
        
zxr10QosDsv4MixAclDmName OBJECT-TYPE
        SYNTAX   DisplayString(SIZE(0..31))
        MAX-ACCESS  not-accessible
        STATUS  current
        DESCRIPTION
                "WORD 
                 Name of the diffserv domain(1-31 characters)"
        ::= { zxr10QosDsv4MixAclEntry  1  }    
        
zxr10QosDsv4MixAclName OBJECT-TYPE
        SYNTAX   DisplayString(SIZE(0..31))
        MAX-ACCESS  not-accessible
        STATUS  current
        DESCRIPTION
                "WORD
                IPv4 mixed ACL name(1-31 characters)"
        ::= { zxr10QosDsv4MixAclEntry  2  }

zxr10QosDsv4MixAclClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsv4MixAclEntry  3  } 
        
zxr10QosDsv4MixAclColor OBJECT-TYPE
        SYNTAX   QosDsColor
        MAX-ACCESS  read-only
        STATUS  current
        DESCRIPTION
                "Color:
                 green   Green packets
                 yellow  Yellow packets
                 red     Red packets"
        ::= { zxr10QosDsv4MixAclEntry  4  }
                                                               
                                                               
--  ******************************************************
--                zxr10QosDsv6MixAclTable
--  ******************************************************
zxr10QosDsv6MixAclTable OBJECT-TYPE
        SYNTAX  SEQUENCE OF Zxr10QosDsv6MixAclEntry
        MAX-ACCESS  not-accessible
        STATUS  current
        DESCRIPTION
                "IPv6 mixed ACL Table"
        ::= { zxr10QosDsMapObjects 9  }
        
zxr10QosDsv6MixAclEntry OBJECT-TYPE
        SYNTAX   Zxr10QosDsv6MixAclEntry
        MAX-ACCESS  not-accessible
        STATUS  current
        DESCRIPTION
                "Map IPv6 mixed ACL to PHB"
        INDEX {zxr10QosDsv6MixAclDmName,
               zxr10QosDsv6MixAclName}
        ::= { zxr10QosDsv6MixAclTable 1 }

Zxr10QosDsv6MixAclEntry ::=
        SEQUENCE {
                 zxr10QosDsv6MixAclDmName
                     DisplayString,
                 zxr10QosDsv6MixAclName
                     DisplayString,
                 zxr10QosDsv6MixAclClass
                     QosDsSrvClass,
                 zxr10QosDsv6MixAclColor
                     QosDsColor                
        } 
        
zxr10QosDsv6MixAclDmName OBJECT-TYPE
        SYNTAX   DisplayString(SIZE(0..31))
        MAX-ACCESS  not-accessible
        STATUS  current
        DESCRIPTION
                "WORD 
                 Name of the diffserv domain(1-31 characters)"
        ::= { zxr10QosDsv6MixAclEntry  1  }    
        
zxr10QosDsv6MixAclName OBJECT-TYPE
        SYNTAX   DisplayString(SIZE(0..31))
        MAX-ACCESS  not-accessible
        STATUS  current
        DESCRIPTION
                "WORD
                Name of IPv6 mixed ACL(1-31 characters)"
        ::= { zxr10QosDsv6MixAclEntry  2  }

zxr10QosDsv6MixAclClass OBJECT-TYPE
        SYNTAX   QosDsSrvClass
        MAX-ACCESS  read-only
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsv6MixAclEntry  3  } 
        
zxr10QosDsv6MixAclColor OBJECT-TYPE
        SYNTAX   QosDsColor
        MAX-ACCESS  read-only
        STATUS  current
        DESCRIPTION
                "Color:
                 green   Green packets
                 yellow  Yellow packets
                 red     Red packets"
        ::= { zxr10QosDsv6MixAclEntry  4  }


--  ******************************************************
--                zxr10QosDsPhbTable
--  ******************************************************
zxr10QosDsPHBTable OBJECT-TYPE
        SYNTAX  SEQUENCE OF Zxr10QosDsPHBEntry
        MAX-ACCESS  not-accessible
        STATUS  current
        DESCRIPTION
                "PHB Table"
        ::= { zxr10QosDsMapObjects 10  }
        
zxr10QosDsPHBEntry OBJECT-TYPE
        SYNTAX   Zxr10QosDsPHBEntry
        MAX-ACCESS  not-accessible
        STATUS  current
        DESCRIPTION
                "Map PHB info to 8021p/IP DSCP/MPLSEXP."
        INDEX {zxr10QosDsPHBDmName,
               zxr10QosDsPHBClass,
               zxr10QosDsPHBColor,
               zxr10QosDsPHBCosType}
        ::= { zxr10QosDsPHBTable 1 }

Zxr10QosDsPHBEntry ::=
        SEQUENCE {
                 zxr10QosDsPHBDmName        
                     DisplayString,
                 zxr10QosDsPHBClass         
                     QosDsSrvClass,
                 zxr10QosDsPHBColor         
                     QosDsColor,
                 zxr10QosDsPHBCosType       
                     INTEGER,
                 zxr10QosDsPHBCosValue      
                     Unsigned32                
        }     
        
zxr10QosDsPHBDmName OBJECT-TYPE
        SYNTAX   DisplayString(SIZE(0..31))
        MAX-ACCESS  not-accessible
        STATUS  current
        DESCRIPTION
                "WORD
                Name of the diffserv domain(1-31 characters)"
        ::= { zxr10QosDsPHBEntry  1  } 
        
zxr10QosDsPHBClass OBJECT-TYPE
        SYNTAX   QosDsSrvClass
        MAX-ACCESS  not-accessible
        STATUS  current
        DESCRIPTION
                "Server class:
                be  Best effort
                af1 Assured forwarding class 1
                af2 Assured forwarding class 2
                af3 Assured forwarding class 3
                af4 Assured forwarding class 4
                ef  Expedited forward
                cs6 Internetwork control service class
                cs7 Network control service class"
        ::= { zxr10QosDsPHBEntry  2  } 
        
zxr10QosDsPHBColor OBJECT-TYPE
        SYNTAX   QosDsColor
        MAX-ACCESS  not-accessible
        STATUS  current
        DESCRIPTION
                "Color:
                 green   Green packets
                 yellow  Yellow packets
                 red     Red packets"
        ::= { zxr10QosDsPHBEntry  3  }    
        
zxr10QosDsPHBCosType OBJECT-TYPE
        SYNTAX   INTEGER {dot1p(1),ipv4-dscp(2),mplsexp(3),ipv6-dscp(4)}
        MAX-ACCESS  not-accessible
        STATUS  current
        DESCRIPTION
                "Cos type:802.1p,DSCP,MPLSEXP"
        ::= { zxr10QosDsPHBEntry  4  } 
        
zxr10QosDsPHBCosValue OBJECT-TYPE
        SYNTAX   Unsigned32(0..63)
        MAX-ACCESS  read-only
        STATUS  current
        DESCRIPTION
                "The value of 8021p/DSCP/MPLSEXP:
                <0-7>  8021p value
                <0-63> IPv4/IPv6 DSCP value
                <0-7>  MPLSEXP value
                "
        ::= { zxr10QosDsPHBEntry  5  }         
                                          
                                          
--  ******************************************************
--                zxr10QosDsIfBindTable
--  ******************************************************
zxr10QosDsIfBindTable OBJECT-TYPE
        SYNTAX  SEQUENCE OF Zxr10QosDsIfBindEntry
        MAX-ACCESS  not-accessible
        STATUS  current
        DESCRIPTION
                "IfBind Table"
        ::= { zxr10QosDsIfBindObjects 1  }

zxr10QosDsIfBindEntry OBJECT-TYPE
        SYNTAX   Zxr10QosDsIfBindEntry
        MAX-ACCESS  not-accessible
        STATUS  current
        DESCRIPTION
                "The used diffserv domain template"
        INDEX {zxr10QosDsIfBindIfName }
        ::= { zxr10QosDsIfBindTable 1 }

Zxr10QosDsIfBindEntry ::=
        SEQUENCE {
                zxr10QosDsIfBindIfName    
                    DisplayString,
                zxr10QosDsIfBindDmName    
                    DisplayString                
        }  
        
zxr10QosDsIfBindIfName OBJECT-TYPE
        SYNTAX   DisplayString(SIZE(0..31))
        MAX-ACCESS  not-accessible
        STATUS  current
        DESCRIPTION
                "WORD
                Name of the interface(1-31 characters)"
        ::= { zxr10QosDsIfBindEntry  1  } 
        
zxr10QosDsIfBindDmName OBJECT-TYPE
        SYNTAX   DisplayString(SIZE(0..31))
        MAX-ACCESS  read-only
        STATUS  current
        DESCRIPTION
                "WORD
                Name of the diffserv domain(1-31 characters)"
        ::= { zxr10QosDsIfBindEntry  2  }    
        
        
--  ******************************************************
--                zxr10QosDsIfTrustTable
--  ****************************************************** 
zxr10QosDsIfTrustTable OBJECT-TYPE
        SYNTAX  SEQUENCE OF Zxr10QosDsIfTrustEntry
        MAX-ACCESS  not-accessible
        STATUS  current
        DESCRIPTION
                "If Trust Table"
        ::= { zxr10QosDsIfTrustObjects 1  }

zxr10QosDsIfTrustEntry OBJECT-TYPE
        SYNTAX   Zxr10QosDsIfTrustEntry
        MAX-ACCESS  not-accessible
        STATUS  current
        DESCRIPTION
                "The type of priority trusted by QoS"
        INDEX {zxr10QosDsIfTrustIfName }
        ::= { zxr10QosDsIfTrustTable 1 }

Zxr10QosDsIfTrustEntry ::=
        SEQUENCE {
                zxr10QosDsIfTrustIfName      
                    DisplayString,
                zxr10QosDsIfTrustType        
                    INTEGER                
        }  
        
zxr10QosDsIfTrustIfName OBJECT-TYPE
        SYNTAX   DisplayString(SIZE(0..31))
        MAX-ACCESS  not-accessible
        STATUS  current
        DESCRIPTION
                "WORD
                Name of the interface(1-31 characters)"
        ::= { zxr10QosDsIfTrustEntry  1  } 
        
zxr10QosDsIfTrustType OBJECT-TYPE
        SYNTAX   INTEGER {dot1p(1),dscp(2),mplsexp(3)}
        MAX-ACCESS  read-only
        STATUS  current
        DESCRIPTION
                "Trust type : 
                 8021p     Based on 802.1p
                 DSCP      Based on IP DSCP
                 MPLSEXP   Based on MPLSEXP"
        ::= { zxr10QosDsIfTrustEntry  2  } 
        
--  ******************************************************
--                zxr10QosDsSchePwTable
--  ******************************************************         
zxr10QosDsSchePwTable OBJECT-TYPE
        SYNTAX  SEQUENCE OF Zxr10QosDsSchePwEntry
        MAX-ACCESS  not-accessible
        STATUS  current
        DESCRIPTION
                "Schedule Pw Table"
        ::= { zxr10QosDsSchePwObjects 1  }

zxr10QosDsSchePwEntry OBJECT-TYPE
        SYNTAX   Zxr10QosDsSchePwEntry
        MAX-ACCESS  not-accessible
        STATUS  current
        DESCRIPTION
                "Set scheduling policy for a certain PW.
                
                1.These leaf nodes conflict with each other:
                    zxr10QosDsSchePwWeight,
                    zxr10QosDsSchePwPQ.   
                "
        INDEX {zxr10QosDsSchePwName }
        ::= { zxr10QosDsSchePwTable 1 }

Zxr10QosDsSchePwEntry ::=
        SEQUENCE {
                zxr10QosDsSchePwName      
                    DisplayString,
                zxr10QosDsSchePwWeight
                    Unsigned32,
                zxr10QosDsSchePwPQ
                    Unsigned32,
                zxr10QosDsSchePwPolicy
                    DisplayString,
                zxr10QosDsSchePwFlag
                    INTEGER,
                zxr10QosDsSchePwId
                    Unsigned32                    
        }  
        
zxr10QosDsSchePwName OBJECT-TYPE
        SYNTAX   DisplayString(SIZE(0..31))
        MAX-ACCESS  not-accessible
        STATUS  current
        DESCRIPTION
                "WORD
                 Name of the PW(1-31 characters)"
        ::= { zxr10QosDsSchePwEntry  1  } 
        
zxr10QosDsSchePwWeight OBJECT-TYPE
        SYNTAX   Unsigned32(1..100)
        MAX-ACCESS  read-only
        STATUS  current
        DESCRIPTION
                "0       default
                 <1-100> weight value"
        ::= { zxr10QosDsSchePwEntry  2  }  
        
zxr10QosDsSchePwPQ OBJECT-TYPE
        SYNTAX   Unsigned32(1..4)
        MAX-ACCESS  read-only
        STATUS  current
        DESCRIPTION
                "0     default value
                 <1-4> the level of priority"
        ::= { zxr10QosDsSchePwEntry  3  } 
        
zxr10QosDsSchePwPolicy OBJECT-TYPE
        SYNTAX   DisplayString(SIZE(0..31))
        MAX-ACCESS  read-only
        STATUS  current
        DESCRIPTION
                "WORD
                 Name of policy-map(1-31 characters)"
        ::= { zxr10QosDsSchePwEntry  4  } 
        
zxr10QosDsSchePwFlag OBJECT-TYPE
        SYNTAX   INTEGER{wfq(1),pq(2)}
        MAX-ACCESS  read-only
        STATUS  current
        DESCRIPTION
                "1   wfq
                 2   pq"
        ::= { zxr10QosDsSchePwEntry  5  }  
        
zxr10QosDsSchePwId OBJECT-TYPE
        SYNTAX   Unsigned32(1..65535)
        MAX-ACCESS  read-only
        STATUS  current
        DESCRIPTION
                "<1-65535> pw ID"
        ::= { zxr10QosDsSchePwEntry  6  } 


--  ******************************************************
--                zxr10QosDsScheTeTable
--  ******************************************************         
zxr10QosDsScheTeTable OBJECT-TYPE
        SYNTAX  SEQUENCE OF Zxr10QosDsScheTeEntry
        MAX-ACCESS  not-accessible
        STATUS  current
        DESCRIPTION
                "Schedule Te Table"
        ::= { zxr10QosDsScheTeObjects 1  }

zxr10QosDsScheTeEntry OBJECT-TYPE
        SYNTAX   Zxr10QosDsScheTeEntry
        MAX-ACCESS  not-accessible
        STATUS  current
        DESCRIPTION
                "Set scheduling policy for a certain tunnel.
                
                1.These leaf nodes conflict with each other:
                    zxr10QosDsScheTeWeight,
                    zxr10QosDsScheTePQ.   
                "
        INDEX {zxr10QosDsScheTeName }
        ::= { zxr10QosDsScheTeTable 1 }

Zxr10QosDsScheTeEntry ::=
        SEQUENCE {
                zxr10QosDsScheTeName      
                    DisplayString,
                zxr10QosDsScheTeWeight
                    Unsigned32,
                zxr10QosDsScheTePQ
                    Unsigned32,
                zxr10QosDsScheTePolicy
                    DisplayString,
                zxr10QosDsScheTeFlag
                    INTEGER                    
        }  
        
zxr10QosDsScheTeName OBJECT-TYPE
        SYNTAX   DisplayString(SIZE(0..31))
        MAX-ACCESS  not-accessible
        STATUS  current
        DESCRIPTION
                "WORD
                 Name of the attaching tunnel(1-31 characters)"
        ::= { zxr10QosDsScheTeEntry  1  } 
        
zxr10QosDsScheTeWeight OBJECT-TYPE
        SYNTAX   Unsigned32(1..100)
        MAX-ACCESS  read-only
        STATUS  current
        DESCRIPTION
                "0       default
                 <1-100> weight value"
        ::= { zxr10QosDsScheTeEntry  2  }  
        
zxr10QosDsScheTePQ OBJECT-TYPE
        SYNTAX   Unsigned32(1..4)
        MAX-ACCESS  read-only
        STATUS  current
        DESCRIPTION
                "0     default value
                 <1-4> the level of priority"
        ::= { zxr10QosDsScheTeEntry  3  } 
        
zxr10QosDsScheTePolicy OBJECT-TYPE
        SYNTAX   DisplayString(SIZE(0..31))
        MAX-ACCESS  read-only
        STATUS  current
        DESCRIPTION
                "WORD
                 Name of policy-map(1-31 characters)"
        ::= { zxr10QosDsScheTeEntry  4  } 
        
zxr10QosDsScheTeFlag OBJECT-TYPE
        SYNTAX   INTEGER{wfq(1),pq(2)}
        MAX-ACCESS  read-only
        STATUS  current
        DESCRIPTION
                "1   wfq
                 2   pq"
        ::= { zxr10QosDsScheTeEntry  5  }
                                                                                                                
END
