--  ******************************************************
--  $Id: ZXR10-ACL-NEW-MIB.mib  
--  
--  ZXR10-ACL-NEW-MIB
--  
--  Mar. 2013, Qian Yi 
--  
--  Copyright(c) 2010 by ZTE Corporaton
--  All rights reservered
--  ******************************************************

ZXR10-ACL-NEW-MIB DEFINITIONS ::= BEGIN

IMPORTS
    MODULE-IDENTITY, OBJECT-TYPE, NOTIFICATION-TYPE,
    Integer32, Unsigned32, Counter32,enterprises, IpAddress 
        FROM SNMPv2-SMI
    MODULE-COMPLIANCE, OBJECT-GROUP, NOTIFICATION-GROUP
        FROM SNMPv2-CONF
    DisplayString, MacAddress, TEXTUAL-CONVENTION, RowStatus
        FROM SNMPv2-TC
    Ipv6Address FROM IPV6-TC
    zxr10,zxr10RosngMIB
        FROM ZXR10-SMI;

zxr10AclNewMIB MODULE-IDENTITY
    LAST-UPDATED "201707111500Z"
    ORGANIZATION "ZTE Corporation"
    CONTACT-INFO
        "       Hu Jun
        Tel:    +86-25-52870000
        E-Mail: hu.jun11@zte.com.cn "  
    DESCRIPTION
        "The MIB module to describe the ACL protocol." 
    REVISION "201707111500Z" 
    DESCRIPTION
        "add: zxr10ACLLinkRuleDsap,
              zxr10ACLLinkRuleSsap,
              zxr10ACLv4MixRuleDsap,
              zxr10ACLv4MixRuleSsap,
              zxr10ACLv6MixRuleDsap,
              zxr10ACLv6MixRuleSsap."
    REVISION "201707071000Z" 
    DESCRIPTION
        "add: zxr10ACLv4RulePrecRange,
              zxr10ACLv4RuleDscpRange,
              zxr10ACLLinkRuleInCosRange,
              zxr10ACLLinkRuleOutCosRange."
    REVISION "201706021000Z" 
    DESCRIPTION
        "add: zxr10ACLLinkRuleLinkProtocolMask."
    REVISION "201608221000Z" 
    DESCRIPTION
        "add: zxr10ACLv4RuleDescription
              zxr10ACLv6RuleDescription
              zxr10ACLLinkRuleDescription."
    REVISION "201608191000Z" 
    DESCRIPTION
        "modify syntax of which, such as zxr10ACLv4RuleIpProtocol, 
         zxr10ACLv6RuleIpProtocol,
         zxr10ACLv4MixRuleIpProtocol,
         zxr10ACLv6MixRuleIpProtocol to add INTEGER{sctp(132)}"
    REVISION "201607201000Z" 
    DESCRIPTION
        "add: zxr10ACLv6RuleSrcAddrMaskFlag
              zxr10ACLv6RuleSrcWildcardBits
              zxr10ACLv6RuleDestAddrMaskFlag
              zxr10ACLv6RuleDestWildcardBits.
         add: zxr10ACLv6MixRuleSrcAddrMaskFlag
              zxr10ACLv6MixRuleSrcWildcardBits
              zxr10ACLv6MixRuleDstAddrMaskFlag
              zxr10ACLv6MixRuleDstWildcardBits."
    REVISION "201601221000Z" 
    DESCRIPTION 
        "add: zxr10ACLv4VxlanObjects."  
    REVISION "201512211000Z"
    DESCRIPTION 
        "add: zxr10ACLUsrDefObjects."         
    REVISION "201512171000Z"
    DESCRIPTION 
        "add: zxr10ACLUsrProtocolRuleDestMACWildcard and
              zxr10ACLUsrProtocolRuleAnyEtherType."   
    REVISION "201504271500Z"
    DESCRIPTION 
        "modify: syntax of zxr10ACLLinkRuleLinkProtocol.
        modify: syntax and status of zxr10ACLv4MixRuleLinkProtocolEx.
        modify: syntax and status of zxr10ACLv6MixRuleLinkProtocolEx."  
    REVISION "201501121500Z"
    DESCRIPTION 
        "add: zxr10ACLUsrProtocolObjects."   
    REVISION "201409011500Z"
    DESCRIPTION 
        "add: zxr10ACLv4MixRuleLinkProtocolEx.
         add: zxr10ACLv6MixRuleLinkProtocolEx"        
    REVISION "201405211700Z"
    DESCRIPTION 
        "modify: MAX-ACCESS of URL."
    REVISION "201404161000Z"
    DESCRIPTION 
        "add: source and destination URL."
    REVISION "201402271400Z"
    DESCRIPTION
        "obsolete: zxr10ACLv4MixRuleLinkProtocol.
         obsolete: zxr10ACLv6MixRuleLinkProtocol."   
    REVISION "201401201500Z"
    DESCRIPTION 
        "modify: index with DisplayString syntax."
    REVISION "201312161000Z"
    DESCRIPTION 
        "add: definitions about MAC address range."
    REVISION "201308051500Z"
    DESCRIPTION 
        "modify: syntax of portValue."
    REVISION "201305071400Z"
    DESCRIPTION 
        "modify: default and invalid valut about AclTcpFlagType."
    REVISION "201304101400Z"
    DESCRIPTION 
        "add:   zxr10ACLMIB
        Initial version of this MIB module."
    ::= { zxr10RosngMIB 602 }

---------------------------------------------------------------------------
---------------------------------------------------------------------------
-- Groups in the ZXR10-URPF-MIB MIB Module
---------------------------------------------------------------------------
-- Following objects are defined.

zxr10ACLGlobalObjects  OBJECT IDENTIFIER ::= { zxr10AclNewMIB 1}
zxr10ACLObjects        OBJECT IDENTIFIER ::= { zxr10AclNewMIB 2}
zxr10ACLNotifications  OBJECT IDENTIFIER ::= { zxr10AclNewMIB 3}
zxr10ACLConformance    OBJECT IDENTIFIER ::= { zxr10AclNewMIB 4}

zxr10ACLv4Objects  OBJECT IDENTIFIER ::= { zxr10ACLObjects 1}
zxr10ACLv6Objects  OBJECT IDENTIFIER ::= { zxr10ACLObjects 2}
zxr10ACLLinkObjects  OBJECT IDENTIFIER ::= { zxr10ACLObjects 3}
zxr10ACLv4MixObjects  OBJECT IDENTIFIER ::= { zxr10ACLObjects 4}
zxr10ACLv6MixObjects  OBJECT IDENTIFIER ::= { zxr10ACLObjects 5}
zxr10ACLUsrProtocolObjects   OBJECT IDENTIFIER ::= { zxr10ACLObjects 6}
zxr10ACLUsrDefObjects    OBJECT IDENTIFIER ::= { zxr10ACLObjects 7}
zxr10ACLv4VxlanObjects   OBJECT IDENTIFIER ::= { zxr10ACLObjects 8}

zxr10ACLGroups     OBJECT IDENTIFIER ::= { zxr10ACLConformance 1 }

--------------------------------------------------------------
--------------------------------------------------------------
-- Textual conventions
--------------------------------------------------------------
--The follow part defined some data types which will be used in this 
--mib file later
--

AclPermitDeny ::= TEXTUAL-CONVENTION
    STATUS       current
    DESCRIPTION
            "permit = 1,deny = 2."
    SYNTAX       INTEGER{permit(1),deny(2)}

AclValidOrNot ::= TEXTUAL-CONVENTION
    STATUS       current
    DESCRIPTION
            "valid = 1,invalid = 2."
    SYNTAX       INTEGER{valid(1),invalid(2)}

AclTcpFlagType ::= TEXTUAL-CONVENTION
    STATUS       current
    DESCRIPTION
            "plus(+) = 1,minus(-) = 2,unset = 65535."
    SYNTAX       INTEGER{plus(1),minus(2),unset(65535)}


--------------------------------------------------------------
--------------------------------------------------------------
--Table Define
-- 

--------------------------------------------------------------
--------------------------------------------------------------
--zxr10ACLv4Objects
--------------------------------------------------------------
--1  zxr10ACLv4ListTable
--2  zxr10ACLv4RuleTable

--------------------------------------------------------------
--------------------------------------------------------------
--zxr10ACLv4ListTable
--------------------------------------------------------------
zxr10ACLv4ListTable  OBJECT-TYPE
    SYNTAX  SEQUENCE OF Zxr10ACLv4ListEntry
    MAX-ACCESS  not-accessible
    STATUS  current
    DESCRIPTION
        "IPv4 ACL Table"
    ::= { zxr10ACLv4Objects 1 }

zxr10ACLv4ListEntry  OBJECT-TYPE
    SYNTAX  Zxr10ACLv4ListEntry
    MAX-ACCESS  not-accessible
    STATUS  current
    DESCRIPTION
        "IPv4 ACL"
    INDEX  { zxr10ACLv4ListName }
    ::= { zxr10ACLv4ListTable 1 }

Zxr10ACLv4ListEntry ::=SEQUENCE {
        zxr10ACLv4ListName                  DisplayString
    }

zxr10ACLv4ListName  OBJECT-TYPE
    SYNTAX   DisplayString(SIZE(1..31))
    MAX-ACCESS  read-only
    STATUS  current
    DESCRIPTION
        "Name of an IPv4 access-list (1-31 characters)"
    ::= { zxr10ACLv4ListEntry 1 } 


--------------------------------------------------------------
--------------------------------------------------------------
--zxr10ACLv4RuleTable
--------------------------------------------------------------
zxr10ACLv4RuleTable  OBJECT-TYPE
    SYNTAX  SEQUENCE OF Zxr10ACLv4RuleEntry
    MAX-ACCESS  not-accessible
    STATUS  current
    DESCRIPTION
        "IPv4 ACL Rule Table"
    ::= { zxr10ACLv4Objects 2 }

zxr10ACLv4RuleEntry  OBJECT-TYPE
    SYNTAX  Zxr10ACLv4RuleEntry
    MAX-ACCESS  not-accessible
    STATUS  current
    DESCRIPTION          
       "IPv4 ACL 
        effective leaf nodes: 
        A leaf node which is effective or not depends on the type of rule.
        Rule types include standard type,ip type,tcp type,udp type,icmp type,
        represented by zxr10ACLv4RuleIpProtocol in this table. 
        According to the rule type (zxr10ACLv4RuleIpProtocol), the following
        leaf nodes are effective. 
        1. rule type : std type
           effective leaf nodes: zxr10ACLv4RuleAclName ,
                                 zxr10ACLv4RuleRuleID, 
                                 zxr10ACLv4RulePermitDeny,
                                 zxr10ACLv4RuleSrcAddr,
                                 zxr10ACLv4RuleSrcWildcard,
                                 zxr10ACLv4RuleTimerangeName,
                                 zxr10ACLv4RuleSrcUrl,
                                 zxr10ACLv4RuleDescription
        2. rule type : ip type
           effective leaf nodes: zxr10ACLv4RuleAclName ,
                                 zxr10ACLv4RuleRuleID, 
                                 zxr10ACLv4RulePermitDeny,
                                 zxr10ACLv4RuleSrcAddr,
                                 zxr10ACLv4RuleSrcWildcard,
                                 zxr10ACLv4RuleDestAddr,
                                 zxr10ACLv4RuleDestWildcard,
                                 zxr10ACLv4RuleIpProtocol,
                                 zxr10ACLv4RulePrecedence,
                                 zxr10ACLv4RuleTOS,
                                 zxr10ACLv4RuleDSCP, 
                                 zxr10ACLv4RuleFragment,
                                 zxr10ACLv4RuleTtlOpr,
                                 zxr10ACLv4RuleTtlValue,
                                 zxr10ACLv4RuleTtlRange,
                                 zxr10ACLv4RuleTimerangeName,
                                 zxr10ACLv4RuleSrcUrl,
                                 zxr10ACLv4RuleDestUrl,
                                 zxr10ACLv4RuleDescription,
                                 zxr10ACLv4RulePrecRange,
                                 zxr10ACLv4RuleDscpRange
         3. rule type : tcp type
           effective leaf nodes: zxr10ACLv4RuleAclName,
                                 zxr10ACLv4RuleRuleID,
                                 zxr10ACLv4RulePermitDeny,
                                 zxr10ACLv4RuleSrcAddr,
                                 zxr10ACLv4RuleSrcWildcard,
                                 zxr10ACLv4RuleDestAddr,
                                 zxr10ACLv4RuleDestWildcard,
                                 zxr10ACLv4RuleIpProtocol,
                                 zxr10ACLv4RuleSrcPortOpr,
                                 zxr10ACLv4RuleSrcPortValue,
                                 zxr10ACLv4RuleSrcPortRange,
                                 zxr10ACLv4RuleDestPortOpr,
                                 zxr10ACLv4RuleDestPortValue,
                                 zxr10ACLv4RuleDestPortRange,
                                 zxr10ACLv4RuleTCPEstablish,
                                 zxr10ACLv4RulePrecedence,
                                 zxr10ACLv4RuleTOS,
                                 zxr10ACLv4RuleDSCP,
                                 zxr10ACLv4RuleFragment,
                                 zxr10ACLv4RuleRstFlag,
                                 zxr10ACLv4RuleAckFlag,
                                 zxr10ACLv4RuleFinFlag,
                                 zxr10ACLv4RuleSynFlag,
                                 zxr10ACLv4RulePshFlag,
                                 zxr10ACLv4RuleUrgFlag,
                                 zxr10ACLv4RuleTtlOpr,
                                 zxr10ACLv4RuleTtlValue,
                                 zxr10ACLv4RuleTtlRange,
                                 zxr10ACLv4RuleTimerangeName,
                                 zxr10ACLv4RuleSrcUrl,
                                 zxr10ACLv4RuleDestUrl,
                                 zxr10ACLv4RuleDescription,
                                 zxr10ACLv4RulePrecRange,
                                 zxr10ACLv4RuleDscpRange
          4. rule type : udp type
           effective leaf nodes: zxr10ACLv4RuleAclName,
                                 zxr10ACLv4RuleRuleID,
                                 zxr10ACLv4RulePermitDeny,
                                 zxr10ACLv4RuleSrcAddr,
                                 zxr10ACLv4RuleSrcWildcard,
                                 zxr10ACLv4RuleDestAddr,
                                 zxr10ACLv4RuleDestWildcard,
                                 zxr10ACLv4RuleIpProtocol,
                                 zxr10ACLv4RuleSrcPortOpr,
                                 zxr10ACLv4RuleSrcPortValue,
                                 zxr10ACLv4RuleSrcPortRange,
                                 zxr10ACLv4RuleDestPortOpr,
                                 zxr10ACLv4RuleDestPortValue,
                                 zxr10ACLv4RuleDestPortRange,
                                 zxr10ACLv4RulePrecedence,
                                 zxr10ACLv4RuleTOS,
                                 zxr10ACLv4RuleDSCP, 
                                 zxr10ACLv4RuleFragment,
                                 zxr10ACLv4RuleTtlOpr,
                                 zxr10ACLv4RuleTtlValue,
                                 zxr10ACLv4RuleTtlRange,
                                 zxr10ACLv4RuleTimerangeName,
                                 zxr10ACLv4RuleSrcUrl,
                                 zxr10ACLv4RuleDestUrl,
                                 zxr10ACLv4RuleDescription,
                                 zxr10ACLv4RulePrecRange,
                                 zxr10ACLv4RuleDscpRange
         5. rule type : icmp type
           effective leaf nodes: zxr10ACLv4RuleAclName,
                                 zxr10ACLv4RuleRuleID,
                                 zxr10ACLv4RulePermitDeny,
                                 zxr10ACLv4RuleSrcAddr,
                                 zxr10ACLv4RuleSrcWildcard,
                                 zxr10ACLv4RuleDestAddr,
                                 zxr10ACLv4RuleDestWildcard,
                                 zxr10ACLv4RuleIpProtocol,
                                 zxr10ACLv4RuleICMPType,
                                 zxr10ACLv4RuleICMPCode,
                                 zxr10ACLv4RulePrecedence,
                                 zxr10ACLv4RuleTOS,
                                 zxr10ACLv4RuleDSCP,
                                 zxr10ACLv4RuleFragment,
                                 zxr10ACLv4RuleTtlOpr,
                                 zxr10ACLv4RuleTtlValue,
                                 zxr10ACLv4RuleTtlRange,
                                 zxr10ACLv4RuleTimerangeName, 
                                 zxr10ACLv4RuleSrcUrl,
                                 zxr10ACLv4RuleDestUrl,
                                 zxr10ACLv4RuleDescription,
                                 zxr10ACLv4RulePrecRange,
                                 zxr10ACLv4RuleDscpRange
        
        conflict leaf nodes:
        1. zxr10ACLv4RuleFragment conflicts with 
                                 zxr10ACLv4RuleSrcPortOpr,
                                 zxr10ACLv4RuleSrcPortValue,
                                 zxr10ACLv4RuleSrcPortRange,
                                 zxr10ACLv4RuleDestPortOpr,
                                 zxr10ACLv4RuleDestPortValue,
                                 zxr10ACLv4RuleDestPortRange,
                                 zxr10ACLv4RuleTCPEstablish,
                                 zxr10ACLv4RuleICMPType,
                                 zxr10ACLv4RuleICMPCode,
                                 zxr10ACLv4RuleRstFlag,
                                 zxr10ACLv4RuleAckFlag,
                                 zxr10ACLv4RuleFinFlag,
                                 zxr10ACLv4RuleSynFlag,
                                 zxr10ACLv4RulePshFlag,
                                 zxr10ACLv4RuleUrgFlag,
        
        2.These leaf nodes conflict with each other: 
                                 zxr10ACLv4RulePrecedence,
                                 zxr10ACLv4RuleTOS,
                                 zxr10ACLv4RuleDSCP,
                                 zxr10ACLv4RulePrecRange,
                                 zxr10ACLv4RuleDscpRange
        
        3.zxr10ACLv4RuleTCPEstablish conflicts with 
                                 zxr10ACLv4RuleRstFlag,
                                 zxr10ACLv4RuleAckFlag,
        "
    INDEX  { zxr10ACLv4RuleAclName,
             zxr10ACLv4RuleRuleID }
    ::= { zxr10ACLv4RuleTable 1 }
    
Zxr10ACLv4RuleEntry ::=SEQUENCE {
        zxr10ACLv4RuleAclName               DisplayString,
        zxr10ACLv4RuleRuleID                Integer32,
        zxr10ACLv4RulePermitDeny            AclPermitDeny,
        zxr10ACLv4RuleSrcAddr               IpAddress,
        zxr10ACLv4RuleSrcWildcard           IpAddress,
        zxr10ACLv4RuleDestAddr              IpAddress,
        zxr10ACLv4RuleDestWildcard          IpAddress,
        zxr10ACLv4RuleIpProtocol            INTEGER,
        zxr10ACLv4RuleSrcPortOpr            INTEGER,
        zxr10ACLv4RuleSrcPortValue          INTEGER,
        zxr10ACLv4RuleSrcPortRange          DisplayString,
        zxr10ACLv4RuleDestPortOpr           INTEGER,
        zxr10ACLv4RuleDestPortValue         INTEGER,
        zxr10ACLv4RuleDestPortRange         DisplayString,
        zxr10ACLv4RuleTCPEstablish          AclValidOrNot,
        zxr10ACLv4RuleICMPType              INTEGER,
        zxr10ACLv4RuleICMPCode              INTEGER,
        zxr10ACLv4RulePrecedence            Integer32,
        zxr10ACLv4RuleTOS                   Integer32,
        zxr10ACLv4RuleDSCP                  Integer32,
        zxr10ACLv4RuleFragment              AclValidOrNot,
        zxr10ACLv4RuleRstFlag               AclTcpFlagType,
        zxr10ACLv4RuleAckFlag               AclTcpFlagType,
        zxr10ACLv4RuleFinFlag               AclTcpFlagType,
        zxr10ACLv4RuleSynFlag               AclTcpFlagType,
        zxr10ACLv4RulePshFlag               AclTcpFlagType,
        zxr10ACLv4RuleUrgFlag               AclTcpFlagType,
        zxr10ACLv4RuleTtlOpr                INTEGER,
        zxr10ACLv4RuleTtlValue              Integer32,
        zxr10ACLv4RuleTtlRange              DisplayString,
        zxr10ACLv4RuleTimerangeName         DisplayString,
        zxr10ACLv4RuleSrcUrl                DisplayString,
        zxr10ACLv4RuleDestUrl               DisplayString,
        zxr10ACLv4RuleDescription           DisplayString,
        zxr10ACLv4RulePrecRange             DisplayString,
        zxr10ACLv4RuleDscpRange             DisplayString
    }

zxr10ACLv4RuleAclName  OBJECT-TYPE
    SYNTAX   DisplayString(SIZE(1..31))
    MAX-ACCESS  not-accessible
    STATUS  current
    DESCRIPTION
        "Name of an IPv4 access-list (1-31 characters)"
    ::= { zxr10ACLv4RuleEntry 1 } 
        
zxr10ACLv4RuleRuleID  OBJECT-TYPE
    SYNTAX   Integer32(1..2147483644)
    MAX-ACCESS  not-accessible
    STATUS  current
    DESCRIPTION
        "ID of this rule" 
    ::= { zxr10ACLv4RuleEntry 2 }    

zxr10ACLv4RulePermitDeny  OBJECT-TYPE
    SYNTAX   AclPermitDeny
    MAX-ACCESS  read-only
    STATUS  current
    DESCRIPTION
        "deny  :  Specify packets to reject
         permit:  Specify packets to forward"
    ::= { zxr10ACLv4RuleEntry 3 }    

zxr10ACLv4RuleSrcAddr  OBJECT-TYPE
    SYNTAX   IpAddress
    MAX-ACCESS  read-only
    STATUS  current
    DESCRIPTION
        "A.B.C.D  Source address"
    ::= { zxr10ACLv4RuleEntry 4 }    

zxr10ACLv4RuleSrcWildcard  OBJECT-TYPE
    SYNTAX   IpAddress
    MAX-ACCESS  read-only
    STATUS  current
    DESCRIPTION
        "A.B.C.D  Wildcard bits"
    ::= { zxr10ACLv4RuleEntry 5 } 
 
zxr10ACLv4RuleDestAddr  OBJECT-TYPE
    SYNTAX   IpAddress
    MAX-ACCESS  read-only
    STATUS  current
    DESCRIPTION
        "A.B.C.D  Destination address"
    ::= { zxr10ACLv4RuleEntry 6 } 
       
zxr10ACLv4RuleDestWildcard  OBJECT-TYPE
    SYNTAX   IpAddress
    MAX-ACCESS  read-only
    STATUS  current
    DESCRIPTION
        "A.B.C.D  Destination wildcard bits"
    ::= { zxr10ACLv4RuleEntry 7 } 

zxr10ACLv4RuleIpProtocol  OBJECT-TYPE
    SYNTAX   INTEGER{icmp(1),igmp(2),tcp(6),udp(17),gre(47),ospf(89),
                     pim(103),vrrp(112),sctp(132),std(65534),ip(65535)}
    MAX-ACCESS  read-only
    STATUS  current
    DESCRIPTION
        " <0-255>   An IP protocol number  
          std      standard rule type (65534)
          gre      Generic Routing Encapsulation (47)
          icmp     Internet Control Message Protocol (1)
          igmp     Internet Group Management Protocol (2)
          ip       Any internet protocol (65535)
          ospf     Open Shortest Path First Protocol (89)
          pim      Protocol Independent Multicast (103)
          tcp      Transmission Control Protocol (6)
          udp      User Datagram Protocol (17)
          sctp     Stream Control Transmission Protocol (132)
          vrrp     Virtual Router Redundancy Protocol (112)"
    ::= { zxr10ACLv4RuleEntry 8 }
       
zxr10ACLv4RuleSrcPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number
         le       Match only packets with a no greater port number
         range    Match only packet on a given port range
         65535    invalid value
         
        Needn't care for zxr10ACLv4RuleSrcPortValue and 
        zxr10ACLv4RuleSrcPortRange When the value of 
        zxr10ACLv4RuleSrcPortOpr is invalid(65535).
        Check zxr10ACLv4RuleSrcPortValue when the value 
        zxr10ACLv4RuleSrcPortOpr is eq(1),ge(2) or le(3).
        Check zxr10ACLv4RuleSrcPortRange only when the value of 
        zxr10ACLv4RuleSrcPortOpr is range(7)."
    ::= { zxr10ACLv4RuleEntry 9 }
    
zxr10ACLv4RuleSrcPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv4RuleSrcPortOpr is 
        eq(1),ge(2) or le(3)."
    ::= { zxr10ACLv4RuleEntry 10 }
    
zxr10ACLv4RuleSrcPortRange  OBJECT-TYPE
    SYNTAX   DisplayString
    MAX-ACCESS  read-only
    STATUS  current
    DESCRIPTION
        "Port range:  <0-65535>-<0-65535>
        Check zxr10ACLv4RuleSrcPortRange only when the value of 
        zxr10ACLv4RuleSrcPortOpr is range(7)."
    ::= { zxr10ACLv4RuleEntry 11 }
    
zxr10ACLv4RuleDestPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number
         le       Match only packets with a no greater port number
         range    Match only packet on a given port range
         65535    invalid value
         
        Needn't care for zxr10ACLv4RuleDestPortValue and 
        zxr10ACLv4RuleDestPortRange When the value of 
        zxr10ACLv4RuleDestPortOpr is invalid(65535).
        Check zxr10ACLv4RuleDestPortValue when the value 
        zxr10ACLv4RuleDestPortOpr is eq(1),ge(2) or le(3).
        Check zxr10ACLv4RuleDestPortRange only when the value of 
        zxr10ACLv4RuleDestPortOpr is range(7)."
    ::= { zxr10ACLv4RuleEntry 12 }    
    
zxr10ACLv4RuleDestPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv4RuleDestPortOpr is 
        eq(1),ge(2) or le(3)."
    ::= { zxr10ACLv4RuleEntry 13 }
    
zxr10ACLv4RuleDestPortRange  OBJECT-TYPE
    SYNTAX   DisplayString
    MAX-ACCESS  read-only
    STATUS  current
    DESCRIPTION
        "Port range:  <0-65535>-<0-65535>
        Check zxr10ACLv4RuleDestPortRange only when the value of 
        zxr10ACLv4RuleDestPortOpr is range(7)."
    ::= { zxr10ACLv4RuleEntry 14 }   
     
zxr10ACLv4RuleTCPEstablish  OBJECT-TYPE
    SYNTAX    AclValidOrNot
    MAX-ACCESS  read-only
    STATUS  current
    DESCRIPTION
        "Match established connections.
         This is an optional node. 
         This node is conflict with zxr10ACLv4RuleAckFlag and 
         zxr10ACLv4RuleRstFlag."
    DEFVAL    {2} 
    ::= { zxr10ACLv4RuleEntry 15 }  

zxr10ACLv4RuleICMPType  OBJECT-TYPE
    SYNTAX   INTEGER(0..255|65535)
    MAX-ACCESS  read-only
    STATUS  current
    DESCRIPTION
        "ICMP type:
         <0-255>               valid value
         65535                 invalid value
         specific value:
         alternate-address     Alternate address (6)
         echo                  Echo (ping, 8)
         echo-reply            Echo reply (0)
         information-request   Information requests (15)
         parameter-problem     All parameter problems (12)
         redirect              All redirects (5)
         router-advertisement  Router discovery advertisements (9)
         router-solicitation   Router discovery solicitations (10)
         source-quench         Source quenches (4)
         time-exceeded         All time exceededs (11)
         timestamp-reply       Timestamp replies (14)
         timestamp-request     Timestamp requests (13)
         unreachable           All unreachables (3)

        This is an optional node."
    ::= { zxr10ACLv4RuleEntry 16 }    
    
zxr10ACLv4RuleICMPCode  OBJECT-TYPE
    SYNTAX   INTEGER(0..255|65535)
    MAX-ACCESS  read-only
    STATUS  current
    DESCRIPTION
        "ICMP code:
         <0-255>      valid value
         65535        invalid value
         This is an optional node."
    ::= { zxr10ACLv4RuleEntry 17 }  
    
zxr10ACLv4RulePrecedence  OBJECT-TYPE
    SYNTAX   Integer32(0..7|255)
    MAX-ACCESS  read-only
    STATUS  current
    DESCRIPTION
        "Precedence level:
         <0-7>   valid value
         255     invalid value
         This is an optional node."
    ::= { zxr10ACLv4RuleEntry 18 }    
    
zxr10ACLv4RuleTOS  OBJECT-TYPE
    SYNTAX   Integer32(0..15|255)
    MAX-ACCESS  read-only
    STATUS  current
    DESCRIPTION
        "Type of service(ToS):
         <0-15>  valid value
         255     invalid value
         This is an optional node."
    ::= { zxr10ACLv4RuleEntry 19 }  
      
zxr10ACLv4RuleDSCP  OBJECT-TYPE
    SYNTAX   Integer32(0..63|255)
    MAX-ACCESS  read-only
    STATUS  current
    DESCRIPTION
        "DSCP value:
         <0-63>  valid value
         255     invalid value
         This is an optional node."
    ::= { zxr10ACLv4RuleEntry 20 } 
   
zxr10ACLv4RuleFragment  OBJECT-TYPE
    SYNTAX     AclValidOrNot
    MAX-ACCESS  read-only        
    STATUS  current
    DESCRIPTION
        "Fragment enable or disable flag.
         This is an optional node."
    DEFVAL    {2} 
    ::= { zxr10ACLv4RuleEntry 21 }

zxr10ACLv4RuleRstFlag  OBJECT-TYPE
    SYNTAX   AclTcpFlagType
    MAX-ACCESS  read-only
    STATUS  current
    DESCRIPTION
        "Match when the RST flag set or not.
         This is an optional node.
         invalid value:     (65535)"
    ::= { zxr10ACLv4RuleEntry 22 }
    
zxr10ACLv4RuleAckFlag  OBJECT-TYPE
    SYNTAX   AclTcpFlagType
    MAX-ACCESS  read-only
    STATUS  current
    DESCRIPTION
        "Match when the ACK flag set or not.
         This is an optional node.
         invalid value:     (65535)"
    ::= { zxr10ACLv4RuleEntry 23 }

zxr10ACLv4RuleFinFlag  OBJECT-TYPE
    SYNTAX   AclTcpFlagType
    MAX-ACCESS  read-only
    STATUS  current
    DESCRIPTION
        "Match when the FIN flag set or not.
         This is an optional node.
         invalid value:     (65535)"
    ::= { zxr10ACLv4RuleEntry 24 }

zxr10ACLv4RuleSynFlag  OBJECT-TYPE
    SYNTAX   AclTcpFlagType
    MAX-ACCESS  read-only
    STATUS  current
    DESCRIPTION
        "Match when the SYN flag set or not.
         This is an optional node.
         invalid value:     (65535)"
    ::= { zxr10ACLv4RuleEntry 25 }
    
zxr10ACLv4RulePshFlag  OBJECT-TYPE
    SYNTAX   AclTcpFlagType
    MAX-ACCESS  read-only
    STATUS  current
    DESCRIPTION
        "Match when the PSH flag set or not.
         This is an optional node.
         invalid value:     (65535)"
    ::= { zxr10ACLv4RuleEntry 26 }

zxr10ACLv4RuleUrgFlag  OBJECT-TYPE
    SYNTAX   AclTcpFlagType
    MAX-ACCESS  read-only
    STATUS  current
    DESCRIPTION
        "Match when the URG flag set or not.
         This is an optional node.
         invalid value:     (65535)"
    ::= { zxr10ACLv4RuleEntry 27 }

zxr10ACLv4RuleTtlOpr  OBJECT-TYPE
    SYNTAX   INTEGER{invalid(65535),eq(1),ge(2),le(3),neq(6),range(7)}
    MAX-ACCESS  read-only
    STATUS  current
    DESCRIPTION
        "This is an optional node.
         eq       Match only packets on a given ttl value
         ge       Match only packets with a no lower ttl value
         le       Match only packets with a no greater ttl value
         neq      Match only packets with a no equeal ttl value
         range    Match only packet on a given ttl value range 
         65535    invalid value
 
        Needn't care for zxr10ACLv4RuleTtlValue and zxr10ACLv4RuleTtlRange 
        When the value of zxr10ACLv4RuleTtlOpr is invalid(65535).
        Check zxr10ACLv4RuleTtlValue when the value zxr10ACLv4RuleTtlOpr is 
        eq(1),ge(2),le(3) or neq(6).
        Check zxr10ACLv4RuleTtlRange only when the value of 
        zxr10ACLv4RuleTtlOpr is range(7). "
    ::= { zxr10ACLv4RuleEntry 28 }
    
zxr10ACLv4RuleTtlValue  OBJECT-TYPE
    SYNTAX   Integer32(0|1..255)
    MAX-ACCESS  read-only
    STATUS  current
    DESCRIPTION
        "The TTL value:  
         <1-255>  valid value
         0        invalid value
        Check this node when the value of zxr10ACLv4RuleTtlOpr is eq(1),
        ge(2),le(3) or neq(6)."
    DEFVAL    {0} 
    ::= { zxr10ACLv4RuleEntry 29 }

 zxr10ACLv4RuleTtlRange  OBJECT-TYPE
    SYNTAX   DisplayString
    MAX-ACCESS  read-only
    STATUS  current
    DESCRIPTION
        "The TTL value Range: 
         <1-255>-<1-255>    valid value
         0                  invalid value
        Check this node when the value of zxr10ACLv4RuleTtlOpr is range(7)."
    ::= { zxr10ACLv4RuleEntry 30 }              
        
zxr10ACLv4RuleTimerangeName  OBJECT-TYPE
    SYNTAX   DisplayString(SIZE(0..31))
    MAX-ACCESS  read-only
    STATUS  current
    DESCRIPTION
        "Time range name (1-31 characters).
         This is an optional node."
    ::= { zxr10ACLv4RuleEntry 31 } 

zxr10ACLv4RuleSrcUrl  OBJECT-TYPE
    SYNTAX   DisplayString(SIZE(0..95))
    MAX-ACCESS  read-only
    STATUS  current
    DESCRIPTION
        "Source URL (1-95 characters)
        If source Url is configured, zxr10ACLv4RuleSrcAddr and 
        zxr10ACLv4RuleSrcWildcard are invalid."
    ::= { zxr10ACLv4RuleEntry 32 } 

zxr10ACLv4RuleDestUrl  OBJECT-TYPE
    SYNTAX   DisplayString(SIZE(0..95))
    MAX-ACCESS  read-only
    STATUS  current
    DESCRIPTION
        "Destination URL (1-95 characters)
        If Destination Url is configured, zxr10ACLv4RuleDestAddr and 
        zxr10ACLv4RuleDestWildcard are invalid."
    ::= { zxr10ACLv4RuleEntry 33 }
    
zxr10ACLv4RuleDescription  OBJECT-TYPE
    SYNTAX   DisplayString(SIZE(0..70))
    MAX-ACCESS  read-only
    STATUS  current
    DESCRIPTION
        "Description for use (1-70 characters)."
    ::= { zxr10ACLv4RuleEntry 34 }

zxr10ACLv4RulePrecRange  OBJECT-TYPE
    SYNTAX   DisplayString
    MAX-ACCESS  read-only
    STATUS  current
    DESCRIPTION
        "Precedence range:    <0-7>-<0-7>
        Invalid value:        65535."
    ::= { zxr10ACLv4RuleEntry 35 }
    
zxr10ACLv4RuleDscpRange  OBJECT-TYPE
    SYNTAX   DisplayString
    MAX-ACCESS  read-only
    STATUS  current
    DESCRIPTION
        "DSCP range:    <0-63>-<0-63>
        Invalid value:  65535."
    ::= { zxr10ACLv4RuleEntry 36 }

--------------------------------------------------------------
--------------------------------------------------------------
--zxr10ACLv6Objects
--------------------------------------------------------------
--1  zxr10ACLv6ListTable
--2  zxr10ACLv6RuleTable

--------------------------------------------------------------
--------------------------------------------------------------
--zxr10ACLv6ListTable
--------------------------------------------------------------
zxr10ACLv6ListTable  OBJECT-TYPE
    SYNTAX  SEQUENCE OF Zxr10ACLv6ListEntry
    MAX-ACCESS  not-accessible
    STATUS  current
    DESCRIPTION
        "IPv6 ACL Table"
    ::= { zxr10ACLv6Objects 1 }

zxr10ACLv6ListEntry  OBJECT-TYPE
    SYNTAX  Zxr10ACLv6ListEntry
    MAX-ACCESS  not-accessible
    STATUS  current
    DESCRIPTION
        "IPv6 ACL"
    INDEX  { zxr10ACLv6ListName }
    ::= { zxr10ACLv6ListTable 1 }
    
Zxr10ACLv6ListEntry ::= SEQUENCE {
        zxr10ACLv6ListName                 DisplayString
    }
       
zxr10ACLv6ListName  OBJECT-TYPE
    SYNTAX   DisplayString(SIZE(1..31))
    MAX-ACCESS  read-only
    STATUS  current
    DESCRIPTION
        "Name of an IPv6 access-list (1-31 characters)"
    ::= { zxr10ACLv6ListEntry 1 } 

--------------------------------------------------------------
--------------------------------------------------------------
--zxr10ACLv6RuleTable
--------------------------------------------------------------
zxr10ACLv6RuleTable  OBJECT-TYPE
    SYNTAX  SEQUENCE OF Zxr10ACLv6RuleEntry
    MAX-ACCESS  not-accessible
    STATUS  current
    DESCRIPTION
        "IPv6 ACL Rule Table"
    ::= { zxr10ACLv6Objects 2 }

zxr10ACLv6RuleEntry  OBJECT-TYPE
    SYNTAX  Zxr10ACLv6RuleEntry
    MAX-ACCESS  not-accessible
    STATUS  current
    DESCRIPTION
        "IPv6 ACL  
        effective leaf nodes: 
        A leaf node which is effective or not depends on the type of rule. 
        Rule types include ip type,tcp type,udp type,icmp type, represented 
        by zxr10ACLv6RuleIpProtocol in this table. 
        According to the rule type (zxr10ACLv6RuleIpProtocol), the following 
        leaf nodes are effective. 
 
        1.rule type :  ip type
        effective leaf nodes: zxr10ACLv6RuleAclName,
                              zxr10ACLv6RuleRuleID,
                              zxr10ACLv6RulePermitDeny, 
                              zxr10ACLv6Ruleflowlabel,
                              zxr10ACLv6RuleSrcAddr,
                              zxr10ACLv6RuleSrcWildcard,
                              zxr10ACLv6RuleDestAddr,
                              zxr10ACLv6RuleDestWildcard,
                              zxr10ACLv6RuleIpProtocol,
                              zxr10ACLv6RuleRouting,
                              zxr10ACLv6RuleAuthen,
                              zxr10ACLv6RuleDestops,
                              zxr10ACLv6RuleFragments,
                              zxr10ACLv6RuleHopByHop,
                              zxr10ACLv6RuleEsp,
                              zxr10ACLv6RuleDSCP,   
                              zxr10ACLv6RuleTc,
                              zxr10ACLv6RuleTimerangeName,
                              zxr10ACLv6RuleSrcAddrMaskFlag,
                              zxr10ACLv6RuleSrcWildcardBits,
                              zxr10ACLv6RuleDestAddrMaskFlag,
                              zxr10ACLv6RuleDestWildcardBits,
                              zxr10ACLv6RuleDescription
       2. rule type :  tcp type
        effective leaf nodes: zxr10ACLv6RuleAclName,
                              zxr10ACLv6RuleRuleID,
                              zxr10ACLv6RulePermitDeny, 
                              zxr10ACLv6Ruleflowlabel,
                              zxr10ACLv6RuleSrcAddr,
                              zxr10ACLv6RuleSrcWildcard,
                              zxr10ACLv6RuleDestAddr,
                              zxr10ACLv6RuleDestWildcard,
                              zxr10ACLv6RuleIpProtocol,
                              zxr10ACLv6RuleSrcPortOpr,
                              zxr10ACLv6RuleSrcPortValue,
                              zxr10ACLv6RuleSrcPortRange,
                              zxr10ACLv6RuleDestPortOpr,
                              zxr10ACLv6RuleDestPortValue,
                              zxr10ACLv6RuleDestPortRange,  
                              zxr10ACLv6RuleTCPEstablish, 
                              zxr10ACLv6RuleRstFlag, 
                              zxr10ACLv6RuleAckFlag,
                              zxr10ACLv6RuleFinFlag,
                              zxr10ACLv6RuleSynFlag,
                              zxr10ACLv6RulePshFlag,
                              zxr10ACLv6RuleUrgFlag,
                              zxr10ACLv6RuleRouting,
                              zxr10ACLv6RuleAuthen,
                              zxr10ACLv6RuleDestops,
                              zxr10ACLv6RuleFragments,
                              zxr10ACLv6RuleHopByHop,
                              zxr10ACLv6RuleEsp,
                              zxr10ACLv6RuleDSCP,
                              zxr10ACLv6RuleTc,
                              zxr10ACLv6RuleTimerangeName,
                              zxr10ACLv6RuleSrcUrl,
                              zxr10ACLv6RuleDestUrl,
                              zxr10ACLv6RuleSrcAddrMaskFlag,
                              zxr10ACLv6RuleSrcWildcardBits,
                              zxr10ACLv6RuleDestAddrMaskFlag,
                              zxr10ACLv6RuleDestWildcardBits,
                              zxr10ACLv6RuleDescription
        3.rule type :   udp type
        effective leaf nodes: zxr10ACLv6RuleAclName,
                              zxr10ACLv6RuleRuleID,
                              zxr10ACLv6RulePermitDeny, 
                              zxr10ACLv6Ruleflowlabel,
                              zxr10ACLv6RuleSrcAddr,
                              zxr10ACLv6RuleSrcWildcard,
                              zxr10ACLv6RuleDestAddr,
                              zxr10ACLv6RuleDestWildcard,
                              zxr10ACLv6RuleIpProtocol,
                              zxr10ACLv6RuleSrcPortOpr,
                              zxr10ACLv6RuleSrcPortValue,
                              zxr10ACLv6RuleSrcPortRange,
                              zxr10ACLv6RuleDestPortOpr,
                              zxr10ACLv6RuleDestPortValue,
                              zxr10ACLv6RuleDestPortRange,
                              zxr10ACLv6RuleRouting,
                              zxr10ACLv6RuleAuthen,
                              zxr10ACLv6RuleDestops,
                              zxr10ACLv6RuleFragments,
                              zxr10ACLv6RuleHopByHop,
                              zxr10ACLv6RuleEsp,
                              zxr10ACLv6RuleDSCP,
                              zxr10ACLv6RuleTc,
                              zxr10ACLv6RuleTimerangeName,
                              zxr10ACLv6RuleSrcUrl,
                              zxr10ACLv6RuleDestUrl,
                              zxr10ACLv6RuleSrcAddrMaskFlag,
                              zxr10ACLv6RuleSrcWildcardBits,
                              zxr10ACLv6RuleDestAddrMaskFlag,
                              zxr10ACLv6RuleDestWildcardBits,
                              zxr10ACLv6RuleDescription
        4.rule type :   icmp type
        effective leaf nodes: zxr10ACLv6RuleAclName,
                              zxr10ACLv6RuleRuleID,
                              zxr10ACLv6RulePermitDeny, 
                              zxr10ACLv6Ruleflowlabel,
                              zxr10ACLv6RuleSrcAddr,
                              zxr10ACLv6RuleSrcWildcard,
                              zxr10ACLv6RuleDestAddr,
                              zxr10ACLv6RuleDestWildcard,
                              zxr10ACLv6RuleIpProtocol,
                              zxr10ACLv6RuleICMPType,
                              zxr10ACLv6RuleICMPCode,
                              zxr10ACLv6RuleRouting,
                              zxr10ACLv6RuleAuthen,
                              zxr10ACLv6RuleDestops,
                              zxr10ACLv6RuleFragments,
                              zxr10ACLv6RuleHopByHop,
                              zxr10ACLv6RuleEsp,
                              zxr10ACLv6RuleDSCP,
                              zxr10ACLv6RuleTc,
                              zxr10ACLv6RuleTimerangeName,
                              zxr10ACLv6RuleSrcUrl,
                              zxr10ACLv6RuleDestUrl,
                              zxr10ACLv6RuleSrcAddrMaskFlag,
                              zxr10ACLv6RuleSrcWildcardBits,
                              zxr10ACLv6RuleDestAddrMaskFlag,
                              zxr10ACLv6RuleDestWildcardBits,
                              zxr10ACLv6RuleDescription
        conflict leaf nodes:
        1. zxr10ACLv6RuleFragments conflicts with
                              zxr10ACLv6RuleSrcPortOpr,
                              zxr10ACLv6RuleSrcPortValue,
                              zxr10ACLv6RuleSrcPortRange,
                              zxr10ACLv6RuleDestPortOpr,
                              zxr10ACLv6RuleDestPortValue,
                              zxr10ACLv6RuleDestPortRange,
                              zxr10ACLv6RuleICMPType,
                              zxr10ACLv6RuleICMPCode,
                              zxr10ACLv6RuleTCPEstablish, 
                              zxr10ACLv6RuleRstFlag, 
                              zxr10ACLv6RuleAckFlag,
                              zxr10ACLv6RuleFinFlag,
                              zxr10ACLv6RuleSynFlag,
                              zxr10ACLv6RulePshFlag,
                              zxr10ACLv6RuleUrgFlag,
         2. zxr10ACLv6RuleDSCP conflicts with
                              zxr10ACLv6RuleTC

         3. zxr10ACLv6RuleTCPEstablish conflicts with
                              zxr10ACLv6RuleRstFlag, 
                              zxr10ACLv6RuleAckFlag
"
    INDEX  { zxr10ACLv6RuleAclName,
             zxr10ACLv6RuleRuleID }
    ::= { zxr10ACLv6RuleTable 1 }
    
Zxr10ACLv6RuleEntry ::= SEQUENCE {
        zxr10ACLv6RuleAclName              DisplayString,
        zxr10ACLv6RuleRuleID               Integer32,
        zxr10ACLv6RulePermitDeny           AclPermitDeny, 
        zxr10ACLv6RuleFlowlabel            Integer32,
        zxr10ACLv6RuleSrcAddr              DisplayString,
        zxr10ACLv6RuleSrcWildcard          INTEGER,
        zxr10ACLv6RuleDestAddr             DisplayString,
        zxr10ACLv6RuleDestWildcard         INTEGER,
        zxr10ACLv6RuleIpProtocol           INTEGER,
        zxr10ACLv6RuleSrcPortOpr           INTEGER,
        zxr10ACLv6RuleSrcPortValue         INTEGER,
        zxr10ACLv6RuleSrcPortRange         DisplayString,
        zxr10ACLv6RuleDestPortOpr          INTEGER,
        zxr10ACLv6RuleDestPortValue        INTEGER,
        zxr10ACLv6RuleDestPortRange        DisplayString,
        zxr10ACLv6RuleTCPEstablish         AclValidOrNot, 
        zxr10ACLv6RuleRstFlag              AclTcpFlagType, 
        zxr10ACLv6RuleAckFlag              AclTcpFlagType,
        zxr10ACLv6RuleFinFlag              AclTcpFlagType,
        zxr10ACLv6RuleSynFlag              AclTcpFlagType,
        zxr10ACLv6RulePshFlag              AclTcpFlagType,
        zxr10ACLv6RuleUrgFlag              AclTcpFlagType,
        zxr10ACLv6RuleICMPType             INTEGER,
        zxr10ACLv6RuleICMPCode             INTEGER,
        zxr10ACLv6RuleRouting              AclValidOrNot,
        zxr10ACLv6RuleAuthen               AclValidOrNot,
        zxr10ACLv6RuleDestops              AclValidOrNot,
        zxr10ACLv6RuleFragments            AclValidOrNot,
        zxr10ACLv6RuleHopByHop             AclValidOrNot,
        zxr10ACLv6RuleEsp                  AclValidOrNot,
        zxr10ACLv6RuleDSCP                 Integer32,
        zxr10ACLv6RuleTc                   Integer32,
        zxr10ACLv6RuleTimerangeName        DisplayString,
        zxr10ACLv6RuleSrcUrl               DisplayString,
        zxr10ACLv6RuleDestUrl              DisplayString,
        zxr10ACLv6RuleSrcAddrMaskFlag      AclValidOrNot,
        zxr10ACLv6RuleSrcWildcardBits      Ipv6Address,
        zxr10ACLv6RuleDestAddrMaskFlag     AclValidOrNot,
        zxr10ACLv6RuleDestWildcardBits     Ipv6Address,
        zxr10ACLv6RuleDescription          DisplayString
}

zxr10ACLv6RuleAclName  OBJECT-TYPE
    SYNTAX   DisplayString(SIZE(1..31))
    MAX-ACCESS  not-accessible
    STATUS  current
    DESCRIPTION
        "Name of an IPv6 access-list (1-31 characters)"
    ::= { zxr10ACLv6RuleEntry 1 } 
        
zxr10ACLv6RuleRuleID  OBJECT-TYPE
    SYNTAX   Integer32(1..2147483644)
    MAX-ACCESS  not-accessible
    STATUS  current
    DESCRIPTION
        "ID of this rule"
    ::= { zxr10ACLv6RuleEntry 2 }    

zxr10ACLv6RulePermitDeny  OBJECT-TYPE
    SYNTAX   AclPermitDeny
    MAX-ACCESS  read-only
    STATUS  current
    DESCRIPTION
        "deny  :  Specify packets to reject
         permit:  Specify packets to forward"
    ::= { zxr10ACLv6RuleEntry 3 }  
    
zxr10ACLv6RuleFlowlabel  OBJECT-TYPE
    SYNTAX   Integer32(0..1048575|2147483647)
    MAX-ACCESS  read-only
    STATUS  current
    DESCRIPTION
        "Flowlabel value:
         <0-1048575>  valid value
         2147483647   invalid value
         This is an optional node."
    ::= { zxr10ACLv6RuleEntry 4 }   

zxr10ACLv6RuleSrcAddr  OBJECT-TYPE
    SYNTAX   DisplayString
    MAX-ACCESS  read-only
    STATUS  current
    DESCRIPTION
        "<X:X::X:X>  Source address"
    ::= { zxr10ACLv6RuleEntry 5 } 

zxr10ACLv6RuleSrcWildcard  OBJECT-TYPE
    SYNTAX   INTEGER(0..128)
    MAX-ACCESS  read-only
    STATUS  current
    DESCRIPTION
        "<0-128>  Source Wildcard"
    ::= { zxr10ACLv6RuleEntry 6 }    
    
zxr10ACLv6RuleDestAddr  OBJECT-TYPE
    SYNTAX   DisplayString
    MAX-ACCESS  read-only
    STATUS  current
    DESCRIPTION
        "<X:X::X:X>  Destination address"
    ::= { zxr10ACLv6RuleEntry 7 } 
    
zxr10ACLv6RuleDestWildcard  OBJECT-TYPE
    SYNTAX   INTEGER(0..128)
    MAX-ACCESS  read-only
    STATUS  current
    DESCRIPTION
        "<0-128>  Destination Wildcard"
    ::= { zxr10ACLv6RuleEntry 8 }

zxr10ACLv6RuleIpProtocol  OBJECT-TYPE
    SYNTAX   INTEGER{igmp(2),tcp(6),udp(17),gre(47),icmp(58),ospf(89),
                     pim(103),vrrp(112),sctp(132),ip(65535)}
    MAX-ACCESS  read-only
    STATUS  current
    DESCRIPTION
        " <0-255>  An IP protocol number
          gre      Generic Routing Encapsulation (47)
          icmp     Internet Control Message Protocol (58)
          igmp     Internet Group Management Protocol (2)
          ip       Any internet protocol (65535)
          ospf     Open Shortest Path First Protocol (89)
          pim      Protocol Independent Multicast (103)
          tcp      Transmission Control Protocol (6)
          udp      User Datagram Protocol (17)
          sctp     Stream Control Transmission Protocol (132)
          vrrp     Virtual Router Redundancy Protocol (112)"
    ::= { zxr10ACLv6RuleEntry 9 }
        
zxr10ACLv6RuleSrcPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number
         le       Match only packets with a no greater port number
         range    Match only packet on a given port range
         65535    invalid value
 
        Needn't care for zxr10ACLv6RuleSrcPortValue and 
        zxr10ACLv6RuleSrcPortRange When the value of 
        zxr10ACLv6RuleSrcPortOpr is invalid(65535).
        Check zxr10ACLv6RuleSrcPortValue when the value 
        zxr10ACLv6RuleSrcPortOpr is eq(1),ge(2) or le(3).
        Check zxr10ACLv6RuleSrcPortRange only when the value of 
        zxr10ACLv6RuleSrcPortOpr is range(7)."
    ::= { zxr10ACLv6RuleEntry 10 }    
    
zxr10ACLv6RuleSrcPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv6RuleSrcPortOpr is eq(1),
        ge(2) or le(3)."
    ::= { zxr10ACLv6RuleEntry 11 }    
    
zxr10ACLv6RuleSrcPortRange  OBJECT-TYPE
    SYNTAX   DisplayString
    MAX-ACCESS  read-only
    STATUS  current
    DESCRIPTION
        "Port range:  <0-65535>-<0-65535>
        Check zxr10ACLv6RuleSrcPortRange only when the value of 
        zxr10ACLv6RuleSrcPortOpr is range(7)."
    ::= { zxr10ACLv6RuleEntry 12 }    
    
zxr10ACLv6RuleDestPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number
         le       Match only packets with a no greater port number
         range    Match only packet on a given port range
         65535    invalid value
 
        Needn't care for zxr10ACLv6RuleDestPortValue and 
        zxr10ACLv6RuleDestPortRange When the value of 
        zxr10ACLv6RuleDestPortOpr is invalid(65535).
        Check zxr10ACLv6RuleDestPortValue when the value 
        zxr10ACLv6RuleDestPortOpr is eq(1),ge(2) or le(3).
        Check zxr10ACLv6RuleDestPortRange only when the value of 
        zxr10ACLv6RuleDestPortOpr is range(7)." 
    ::= { zxr10ACLv6RuleEntry 13 }    
    
zxr10ACLv6RuleDestPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv6RuleDestPortOpr is eq(1),
        ge(2) or le(3)."
    ::= { zxr10ACLv6RuleEntry 14 }    
    
zxr10ACLv6RuleDestPortRange  OBJECT-TYPE
    SYNTAX   DisplayString
    MAX-ACCESS  read-only
    STATUS  current
    DESCRIPTION
        "Port range:  <0-65535>-<0-65535>
        Check zxr10ACLv6RuleDestPortRange only when the value of 
        zxr10ACLv6RuleDestPortOpr is range(7)." 
    ::= { zxr10ACLv6RuleEntry 15 }   
     
zxr10ACLv6RuleTCPEstablish  OBJECT-TYPE
    SYNTAX    AclValidOrNot
    MAX-ACCESS  read-only
    STATUS  current
    DESCRIPTION
        "Match established connections.
         This is an optional node."
    DEFVAL    {2}  
    ::= { zxr10ACLv6RuleEntry 16 } 
     
zxr10ACLv6RuleRstFlag  OBJECT-TYPE
    SYNTAX   AclTcpFlagType
    MAX-ACCESS  read-only
    STATUS  current
    DESCRIPTION
        "Match when the RST flag set or not.
         This is an optional node.
         invalid value:     (65535)"
    ::= { zxr10ACLv6RuleEntry 17 }
    
zxr10ACLv6RuleAckFlag  OBJECT-TYPE
    SYNTAX   AclTcpFlagType
    MAX-ACCESS  read-only
    STATUS  current
    DESCRIPTION
        "Match when the ACK flag set or not.
         This is an optional node.
         invalid value:     (65535)"
    ::= { zxr10ACLv6RuleEntry 18 }

zxr10ACLv6RuleFinFlag  OBJECT-TYPE
    SYNTAX   AclTcpFlagType
    MAX-ACCESS  read-only
    STATUS  current
    DESCRIPTION
        "Match when the FIN flag set or not.
         This is an optional node.
         invalid value:     (65535)"
    ::= { zxr10ACLv6RuleEntry 19 }

zxr10ACLv6RuleSynFlag  OBJECT-TYPE
    SYNTAX   AclTcpFlagType
    MAX-ACCESS  read-only
    STATUS  current
    DESCRIPTION
        "Match when the SYN flag set or not.
         This is an optional node.
         invalid value:     (65535)"
    ::= { zxr10ACLv6RuleEntry 20 }     
    
zxr10ACLv6RulePshFlag  OBJECT-TYPE
    SYNTAX   AclTcpFlagType
    MAX-ACCESS  read-only
    STATUS  current
    DESCRIPTION
        "Match when the PSH flag set or not.
         This is an optional node.
         invalid value:     (65535)"
    ::= { zxr10ACLv6RuleEntry 21 }

zxr10ACLv6RuleUrgFlag  OBJECT-TYPE
    SYNTAX   AclTcpFlagType
    MAX-ACCESS  read-only
    STATUS  current
    DESCRIPTION
        "Match when the URG flag set or not.
         This is an optional node.
         invalid value:     (65535)"
    ::= { zxr10ACLv6RuleEntry 22 } 
    
zxr10ACLv6RuleICMPType  OBJECT-TYPE
    SYNTAX   INTEGER{destination-unreachable(1),packet-too-big(2),
             time-exceeded(3),parameter-problem(4),echo-request(128),
             echo-reply(129),mld-query(130),mld-report(131),
             router-solicitation(133),router-advertisment(134),nd-ns(135),
             nd-na(136),redirect(137),router-renumbering(138),invalid(65535)}
    MAX-ACCESS  read-only
    STATUS  current
    DESCRIPTION
        "ICMP type:
        <0-255>               valid value
        65535                 invalid value
        specific value:
        destination-unreachable  Destination unreachable (1)
        echo-reply               Echo reply (129)
        echo-request             Echo request (ping, 128)
        mld-query                Multicast Listener Discovery Query (130)
        mld-reduction            Multicast Listener Discovery Reduction (132)
        mld-report               Multicast Listener Discovery Report (131)
        nd-na                    Neighbor discovery neighbor advertisments(136)
        nd-ns                    Neighbor discovery neighbor solicitations(135)
        packet-too-big           Packet too big (2)
        parameter-problem        All parameter problems (4)
        redirect                 Neighbor redirect (137)
        router-advertisment      Neighbor discovery router advertisments(134)
        router-renumbering       All router renumbering (138)
        router-solicitation      Neighbor discovery router solicitations(133)
        time-exceeded            Time exceeded (3)

        This is an optional node."
    ::= { zxr10ACLv6RuleEntry 23 }    
    
zxr10ACLv6RuleICMPCode  OBJECT-TYPE
    SYNTAX   INTEGER(0..255|65535)
    MAX-ACCESS  read-only
    STATUS  current
    DESCRIPTION
        "ICMP code:
         <0-255>      valid value
         65535        invalid value
         This is an optional node."
    ::= { zxr10ACLv6RuleEntry 24 }  
     
zxr10ACLv6RuleRouting  OBJECT-TYPE
    SYNTAX   AclValidOrNot
    MAX-ACCESS  read-only
    STATUS  current
    DESCRIPTION
        "Match if the specify IPv6 header is present.
         This is an optional node."
    DEFVAL    {2} 
    ::= { zxr10ACLv6RuleEntry 25 }

zxr10ACLv6RuleAuthen  OBJECT-TYPE
    SYNTAX   AclValidOrNot
    MAX-ACCESS  read-only
    STATUS  current
    DESCRIPTION
        "Match if the specify IPv6 header is present.
         This is an optional node."
    DEFVAL    {2} 
    ::= { zxr10ACLv6RuleEntry 26 }
 
zxr10ACLv6RuleDestops  OBJECT-TYPE
    SYNTAX   AclValidOrNot
    MAX-ACCESS  read-only
    STATUS  current
    DESCRIPTION
        "Match if the specify IPv6 header is present.
         This is an optional node."
    DEFVAL    {2} 
    ::= { zxr10ACLv6RuleEntry 27 }
     
zxr10ACLv6RuleFragments  OBJECT-TYPE
    SYNTAX   AclValidOrNot
    MAX-ACCESS  read-only
    STATUS  current
    DESCRIPTION
        "Match if the specify IPv6 header is present.
         This is an optional node."
    DEFVAL    {2} 
    ::= { zxr10ACLv6RuleEntry 28 }
    
zxr10ACLv6RuleHopByHop  OBJECT-TYPE
    SYNTAX   AclValidOrNot
    MAX-ACCESS  read-only
    STATUS  current
    DESCRIPTION
        "Match if the specify IPv6 header is present.
         This is an optional node."
    DEFVAL    {2} 
    ::= { zxr10ACLv6RuleEntry 29 }
    
zxr10ACLv6RuleEsp  OBJECT-TYPE
    SYNTAX   AclValidOrNot
    MAX-ACCESS  read-only
    STATUS  current
    DESCRIPTION
        "Match if the specify IPv6 header is present.
         This is an optional node."
    DEFVAL    {2} 
    ::= { zxr10ACLv6RuleEntry 30 }
             
zxr10ACLv6RuleDSCP  OBJECT-TYPE
    SYNTAX   Integer32(0..63|255)
    MAX-ACCESS  read-only
    STATUS  current
    DESCRIPTION
        "DSCP value:
         <0-63>  valid value
         255     invalid value
         This is an optional node."
    ::= { zxr10ACLv6RuleEntry 31 }

zxr10ACLv6RuleTc  OBJECT-TYPE    
    SYNTAX   Integer32(0..255|65535)
    MAX-ACCESS  read-only
    STATUS  current
    DESCRIPTION
        "Traffic Class value:
         <0-255>  valid value
         65535    invalid value
         This is an optional node."
    ::= { zxr10ACLv6RuleEntry 32 }
         
zxr10ACLv6RuleTimerangeName  OBJECT-TYPE
    SYNTAX   DisplayString(SIZE(0..31))
    MAX-ACCESS  read-only
    STATUS  current
    DESCRIPTION
        "Time range name (1-31 characters).
         This is an optional node."
    ::= { zxr10ACLv6RuleEntry 33 }     

zxr10ACLv6RuleSrcUrl  OBJECT-TYPE
    SYNTAX   DisplayString(SIZE(0..95))
    MAX-ACCESS  read-only
    STATUS  current
    DESCRIPTION
        "Source URL (1-95 characters)
        If source Url is configured, zxr10ACLv6RuleSrcAddr and 
        zxr10ACLv6RuleSrcWildcard are invalid."
    ::= { zxr10ACLv6RuleEntry 34 } 

zxr10ACLv6RuleDestUrl  OBJECT-TYPE
    SYNTAX   DisplayString(SIZE(0..95))
    MAX-ACCESS  read-only
    STATUS  current
    DESCRIPTION
        "Destination URL (1-95 characters)
        If Destination Url is configured, zxr10ACLv6RuleDestAddr and 
        zxr10ACLv6RuleDestWildcard are invalid."
    ::= { zxr10ACLv6RuleEntry 35 } 
    
zxr10ACLv6RuleSrcAddrMaskFlag  OBJECT-TYPE
    SYNTAX    AclValidOrNot
    MAX-ACCESS  read-only
    STATUS  current
    DESCRIPTION
        "This flag indicates the way of configuring IPv6 source address mask,
        such as zxr10ACLv6RuleSrcWildcard, zxr10ACLv6RuleSrcWildcardBits.
        If this flag is valid, IPv6 source address mask is configured by 
        wildcard bits,(e.g. X:X::X:X) and zxr10ACLv6RuleSrcWildcardBits 
        is valid;
        if not, IPv6 source address mask is configured by prefix length,
        (e.g. X:X::X:X/0-128) and zxr10ACLv6RuleSrcWildcard is valid."
    DEFVAL    {2}  
    ::= { zxr10ACLv6RuleEntry 36 }
    
zxr10ACLv6RuleSrcWildcardBits  OBJECT-TYPE
    SYNTAX   Ipv6Address
    MAX-ACCESS  read-only
    STATUS  current
    DESCRIPTION
        "<X:X::X:X>   Source address wildcard bits"
    ::= { zxr10ACLv6RuleEntry 37 } 
    
zxr10ACLv6RuleDestAddrMaskFlag  OBJECT-TYPE
    SYNTAX    AclValidOrNot
    MAX-ACCESS  read-only
    STATUS  current
    DESCRIPTION
        "This flag indicates the way of configuring IPv6 destination address 
        mask,such as zxr10ACLv6RuleDestWildcard,zxr10ACLv6RuleDestWildcardBits.
        If this flag is valid, IPv6 destination address mask is configured by 
        wildcard bits, (e.g. X:X::X:X) and zxr10ACLv6RuleDestWildcardBits 
        is valid; 
        if not, IPv6 destination address mask is configured by prefix length,
        (e.g. X:X::X:X/0-128) and zxr10ACLv6RuleDestWildcard is valid."
    DEFVAL    {2}  
    ::= { zxr10ACLv6RuleEntry 38 }
    
zxr10ACLv6RuleDestWildcardBits  OBJECT-TYPE
    SYNTAX   Ipv6Address
    MAX-ACCESS  read-only
    STATUS  current
    DESCRIPTION
        "<X:X::X:X>   Destination address wildcard bits"
    ::= { zxr10ACLv6RuleEntry 39 }
    
zxr10ACLv6RuleDescription  OBJECT-TYPE
    SYNTAX   DisplayString(SIZE(0..70))
    MAX-ACCESS  read-only
    STATUS  current
    DESCRIPTION
        "Description for use (1-70 characters)."
    ::= { zxr10ACLv6RuleEntry 40 }


--------------------------------------------------------------
--------------------------------------------------------------
--zxr10ACLLinkObjects
--------------------------------------------------------------
--1  zxr10ACLLinkListTable
--2  zxr10ACLLinkRuleTable

--------------------------------------------------------------
--------------------------------------------------------------
--zxr10ACLLinkListTable
--------------------------------------------------------------
zxr10ACLLinkListTable  OBJECT-TYPE
    SYNTAX  SEQUENCE OF Zxr10ACLLinkListEntry
    MAX-ACCESS  not-accessible
    STATUS  current
    DESCRIPTION
        "Link ACL"
    ::= { zxr10ACLLinkObjects 1 }

zxr10ACLLinkListEntry  OBJECT-TYPE
    SYNTAX  Zxr10ACLLinkListEntry
    MAX-ACCESS  not-accessible
    STATUS  current
    DESCRIPTION
        "Link ACL"
    INDEX  { zxr10ACLLinkListName }
    ::= { zxr10ACLLinkListTable 1 }
    
Zxr10ACLLinkListEntry ::=SEQUENCE {
        zxr10ACLLinkListName                    DisplayString
   }
    
zxr10ACLLinkListName  OBJECT-TYPE
    SYNTAX   DisplayString(SIZE(1..31))
    MAX-ACCESS  read-only
    STATUS  current
    DESCRIPTION
        "Name of a link access-list (1-31 characters)"
    ::= { zxr10ACLLinkListEntry 1 } 


--------------------------------------------------------------
--------------------------------------------------------------
--zxr10ACLLinkRuleTable
--------------------------------------------------------------
zxr10ACLLinkRuleTable  OBJECT-TYPE
    SYNTAX  SEQUENCE OF Zxr10ACLLinkRuleEntry
    MAX-ACCESS  not-accessible
    STATUS  current
    DESCRIPTION
        "Link ACL Rule Table"
    ::= { zxr10ACLLinkObjects 2 }

zxr10ACLLinkRuleEntry  OBJECT-TYPE
    SYNTAX  Zxr10ACLLinkRuleEntry
    MAX-ACCESS  not-accessible
    STATUS  current
    DESCRIPTION
        "Link ACL
        effective leaf nodes: 
          All of the leaf nodes are effective:
                              zxr10ACLLinkRuleAclName,
                              zxr10ACLLinkRuleRuleID,
                              zxr10ACLLinkRulePermitDeny,
                              zxr10ACLLinkRuleLinkProtocol,
                              zxr10ACLLinkRuleSrcMAC, 
                              zxr10ACLLinkRuleSrcMACWildcard,
                              zxr10ACLLinkRuleDestMAC,
                              zxr10ACLLinkRuleDestMACWildcard,
                              zxr10ACLLinkRuleIncos,
                              zxr10ACLLinkRuleOutCos,
                              zxr10ACLLinkRuleInVlanID,
                              zxr10ACLLinkRuleOutVlanID,
                              zxr10ACLLinkRuleInVlanRange,
                              zxr10ACLLinkRuleOutVlanRange,
                              zxr10ACLLinkRuleTimerangeName,  
                              zxr10ACLLinkRuleBSrcMACRange1,
                              zxr10ACLLinkRuleSrcMACRg1Min,
                              zxr10ACLLinkRuleSrcMACRg1Max,  
                              zxr10ACLLinkRuleBSrcMACRange2,
                              zxr10ACLLinkRuleSrcMACRg2Min,
                              zxr10ACLLinkRuleSrcMACRg2Max,  
                              zxr10ACLLinkRuleBDestMACRange1,
                              zxr10ACLLinkRuleDestMACRg1Min,
                              zxr10ACLLinkRuleDestMACRg1Max,  
                              zxr10ACLLinkRuleBDestMACRange2,
                              zxr10ACLLinkRuleDestMACRg2Min,
                              zxr10ACLLinkRuleDestMACRg2Max,
                              zxr10ACLLinkRuleDescription,
                              zxr10ACLLinkRuleLinkProtocolMask,
                              zxr10ACLLinkRuleInCosRange,
                              zxr10ACLLinkRuleOutCosRange,
                              zxr10ACLLinkRuleDsap,
                              zxr10ACLLinkRuleSsap
                               
        conflict leaf nodes:  
        1. zxr10ACLLinkRuleLinkProtocol conflicts with
                              zxr10ACLLinkRuleDsap,
                              zxr10ACLLinkRuleSsap
                              "
    INDEX  { zxr10ACLLinkRuleAclName,
             zxr10ACLLinkRuleRuleID }
    ::= { zxr10ACLLinkRuleTable 1 }
    
Zxr10ACLLinkRuleEntry ::=SEQUENCE {
        zxr10ACLLinkRuleAclName                 DisplayString,
        zxr10ACLLinkRuleRuleID                  Integer32,
        zxr10ACLLinkRulePermitDeny              AclPermitDeny,
        zxr10ACLLinkRuleLinkProtocol            Integer32,
        zxr10ACLLinkRuleSrcMAC                  MacAddress,
        zxr10ACLLinkRuleSrcMACWildcard          MacAddress,
        zxr10ACLLinkRuleDestMAC                 MacAddress,
        zxr10ACLLinkRuleDestMACWildcard         MacAddress,
        zxr10ACLLinkRuleIncos                   Integer32, 
        zxr10ACLLinkRuleOutCos                  Integer32, 
        zxr10ACLLinkRuleInVlanID                Integer32,
        zxr10ACLLinkRuleOutVlanID               Integer32,
        zxr10ACLLinkRuleInVlanRange             DisplayString,
        zxr10ACLLinkRuleOutVlanRange            DisplayString,
        zxr10ACLLinkRuleTimerangeName           DisplayString,
        zxr10ACLLinkRuleBSrcMACRange1           AclValidOrNot,
        zxr10ACLLinkRuleSrcMACRg1Min            MacAddress,
        zxr10ACLLinkRuleSrcMACRg1Max            MacAddress,  
        zxr10ACLLinkRuleBSrcMACRange2           AclValidOrNot,
        zxr10ACLLinkRuleSrcMACRg2Min            MacAddress,
        zxr10ACLLinkRuleSrcMACRg2Max            MacAddress,  
        zxr10ACLLinkRuleBDestMACRange1          AclValidOrNot,
        zxr10ACLLinkRuleDestMACRg1Min           MacAddress,
        zxr10ACLLinkRuleDestMACRg1Max           MacAddress,  
        zxr10ACLLinkRuleBDestMACRange2          AclValidOrNot,
        zxr10ACLLinkRuleDestMACRg2Min           MacAddress,
        zxr10ACLLinkRuleDestMACRg2Max           MacAddress,
        zxr10ACLLinkRuleDescription             DisplayString,
        zxr10ACLLinkRuleLinkProtocolMask        Unsigned32,
        zxr10ACLLinkRuleInCosRange              DisplayString,
        zxr10ACLLinkRuleOutCosRange             DisplayString,
        zxr10ACLLinkRuleDsap                    Integer32,
        zxr10ACLLinkRuleSsap                    Integer32    
   }
    
zxr10ACLLinkRuleAclName  OBJECT-TYPE
    SYNTAX   DisplayString(SIZE(1..31))
    MAX-ACCESS  not-accessible
    STATUS  current
    DESCRIPTION
        "Name of a link access-list (1-31 characters)"
    ::= { zxr10ACLLinkRuleEntry 1 } 
        
zxr10ACLLinkRuleRuleID  OBJECT-TYPE
    SYNTAX   Integer32(1..2147483644)
    MAX-ACCESS  not-accessible
    STATUS  current
    DESCRIPTION
        "ID of this rule"
    ::= { zxr10ACLLinkRuleEntry 2 }    

zxr10ACLLinkRulePermitDeny  OBJECT-TYPE
    SYNTAX   AclPermitDeny
    MAX-ACCESS  read-only
    STATUS  current
    DESCRIPTION
        "deny  :  Specify packets to reject
         permit:  Specify packets to forward"
    ::= { zxr10ACLLinkRuleEntry 3 }    

zxr10ACLLinkRuleLinkProtocol  OBJECT-TYPE
    SYNTAX   Integer32(1536..65536)   
    MAX-ACCESS  read-only
    STATUS  current
    DESCRIPTION
        "Link protocal:
         <1536-65535>  valid value
         65536         invalid value
         This is an optional node."
    ::= { zxr10ACLLinkRuleEntry 4 } 

zxr10ACLLinkRuleSrcMAC  OBJECT-TYPE
    SYNTAX   MacAddress
    MAX-ACCESS  read-only
    STATUS  current
    DESCRIPTION
        "<xxxx.xxxx.xxxx>  Source MAC address"
    ::= { zxr10ACLLinkRuleEntry 5 }

zxr10ACLLinkRuleSrcMACWildcard  OBJECT-TYPE
    SYNTAX   MacAddress
    MAX-ACCESS  read-only
    STATUS  current
    DESCRIPTION
        "<xxxx.xxxx.xxxx>  Source MAC wildcard"
    ::= { zxr10ACLLinkRuleEntry 6 } 

zxr10ACLLinkRuleDestMAC  OBJECT-TYPE
    SYNTAX   MacAddress
    MAX-ACCESS  read-only
    STATUS  current
    DESCRIPTION
        "<xxxx.xxxx.xxxx>  Destination MAC address"
    ::= { zxr10ACLLinkRuleEntry 7 } 
    
zxr10ACLLinkRuleDestMACWildcard  OBJECT-TYPE
    SYNTAX   MacAddress
    MAX-ACCESS  read-only
    STATUS  current
    DESCRIPTION
        "<xxxx.xxxx.xxxx>  Destination MAC wildcard"
    ::= { zxr10ACLLinkRuleEntry 8 } 
 
zxr10ACLLinkRuleIncos     OBJECT-TYPE
    SYNTAX   Integer32(0..7|255)
    MAX-ACCESS  read-only
    STATUS  current
    DESCRIPTION
        "Value of inner cos:
         <0-7>  valid value
         255    invalid value
         This is an optional node."
    ::= { zxr10ACLLinkRuleEntry 9 }     
    
zxr10ACLLinkRuleOutCos   OBJECT-TYPE
    SYNTAX   Integer32(0..7|255)
    MAX-ACCESS  read-only
    STATUS  current
    DESCRIPTION
        "Value of outer cos:
         <0-7>  valid value
         255    invalid value
         This is an optional node."
    ::= { zxr10ACLLinkRuleEntry 10 }
    
zxr10ACLLinkRuleInVlanID  OBJECT-TYPE
    SYNTAX   Integer32(1..4094|65535)
    MAX-ACCESS  read-only
    STATUS  current
    DESCRIPTION
        "Value of inner vlan
         <1-4094>   valid value
         65535      invalid value
         This is an optional node."
    ::= { zxr10ACLLinkRuleEntry 11 }
    
zxr10ACLLinkRuleOutVlanID  OBJECT-TYPE
    SYNTAX   Integer32(1..4094|65535)
    MAX-ACCESS  read-only
    STATUS  current
    DESCRIPTION
        "Value of outer vlan
         <1-4094>   valid value
         65535      invalid value
         This is an optional node."
    ::= { zxr10ACLLinkRuleEntry 12 }
 
zxr10ACLLinkRuleInVlanRange  OBJECT-TYPE
    SYNTAX   DisplayString
    MAX-ACCESS  read-only
    STATUS  current
    DESCRIPTION
        "Range of inner vlan
         <1-4094>-<1-4094>    valid value
         0                    invalid value
         This is an optional node."
    ::= { zxr10ACLLinkRuleEntry 13 } 
    
zxr10ACLLinkRuleOutVlanRange   OBJECT-TYPE
    SYNTAX   DisplayString
    MAX-ACCESS  read-only
    STATUS  current
    DESCRIPTION
        "Range of outer vlan
         <1-4094>-<1-4094>    valid value
         0                    invalid value
         This is an optional node."
    ::= { zxr10ACLLinkRuleEntry 14 } 
    
zxr10ACLLinkRuleTimerangeName  OBJECT-TYPE
    SYNTAX   DisplayString(SIZE(0..31))
    MAX-ACCESS  read-only
    STATUS  current
    DESCRIPTION
        "Time range name (1-31 characters).
         This is an optional node."
    ::= { zxr10ACLLinkRuleEntry 15 }

zxr10ACLLinkRuleBSrcMACRange1  OBJECT-TYPE
    SYNTAX   AclValidOrNot   
    MAX-ACCESS  read-only
    STATUS  current
    DESCRIPTION
        "Match if source MAC address range is configured.
        When this is valid, zxr10ACLLinkRuleSrcMAC and 
        zxr10ACLLinkRuleSrcMACWildcard are invalid,
        zxr10ACLLinkRuleSrcMACRg1Min and 
        zxr10ACLLinkRuleSrcMACRg1Max are valid."
    DEFVAL    {2} 
    ::= { zxr10ACLLinkRuleEntry 16 } 

zxr10ACLLinkRuleSrcMACRg1Min  OBJECT-TYPE
    SYNTAX   MacAddress
    MAX-ACCESS  read-only
    STATUS  current
    DESCRIPTION
        "<xxxx.xxxx.xxxx>  
        Lower limit of first source MAC address range"
    ::= { zxr10ACLLinkRuleEntry 17 }

zxr10ACLLinkRuleSrcMACRg1Max  OBJECT-TYPE
    SYNTAX   MacAddress
    MAX-ACCESS  read-only
    STATUS  current
    DESCRIPTION
        "<xxxx.xxxx.xxxx>  
        Upper limit of first source MAC address range"
    ::= { zxr10ACLLinkRuleEntry 18 } 

zxr10ACLLinkRuleBSrcMACRange2  OBJECT-TYPE
    SYNTAX   AclValidOrNot   
    MAX-ACCESS  read-only
    STATUS  current
    DESCRIPTION
        "Match if second source MAC address range is configured.
        When this is valid, zxr10ACLLinkRuleSrcMAC and 
        zxr10ACLLinkRuleSrcMACWildcard are invalid,
        zxr10ACLLinkRuleSrcMACRg2Min and 
        zxr10ACLLinkRuleSrcMACRg2Max are valid."
    DEFVAL    {2} 
    ::= { zxr10ACLLinkRuleEntry 19 } 

zxr10ACLLinkRuleSrcMACRg2Min  OBJECT-TYPE
    SYNTAX   MacAddress
    MAX-ACCESS  read-only
    STATUS  current
    DESCRIPTION
        "<xxxx.xxxx.xxxx>
        Lower limit of second source MAC address range"
    ::= { zxr10ACLLinkRuleEntry 20 }

zxr10ACLLinkRuleSrcMACRg2Max  OBJECT-TYPE
    SYNTAX   MacAddress
    MAX-ACCESS  read-only
    STATUS  current
    DESCRIPTION
        "<xxxx.xxxx.xxxx>  
        Upper limit of second source MAC address range"
    ::= { zxr10ACLLinkRuleEntry 21 } 

zxr10ACLLinkRuleBDestMACRange1  OBJECT-TYPE
    SYNTAX   AclValidOrNot   
    MAX-ACCESS  read-only
    STATUS  current
    DESCRIPTION
        "Match if destination MAC address range is configured.
        When this is valid, zxr10ACLLinkRuleDestMAC and 
        zxr10ACLLinkRuleDestMACWildcard are invalid,
        zxr10ACLLinkRuleDestMACRg1Min and 
        zxr10ACLLinkRuleDestMACRg1Max are valid."
    DEFVAL    {2} 
    ::= { zxr10ACLLinkRuleEntry 22 } 

zxr10ACLLinkRuleDestMACRg1Min  OBJECT-TYPE
    SYNTAX   MacAddress
    MAX-ACCESS  read-only
    STATUS  current
    DESCRIPTION
        "<xxxx.xxxx.xxxx>  
        Lower limit of first destination MAC address range"
    ::= { zxr10ACLLinkRuleEntry 23 }

zxr10ACLLinkRuleDestMACRg1Max  OBJECT-TYPE
    SYNTAX   MacAddress
    MAX-ACCESS  read-only
    STATUS  current
    DESCRIPTION
        "<xxxx.xxxx.xxxx>  
        Upper limit of first destination MAC address range"
    ::= { zxr10ACLLinkRuleEntry 24 } 

zxr10ACLLinkRuleBDestMACRange2  OBJECT-TYPE
    SYNTAX   AclValidOrNot   
    MAX-ACCESS  read-only
    STATUS  current
    DESCRIPTION
        "Match if second destination MAC address range is configured.
        When this is valid, zxr10ACLLinkRuleDestMAC and 
        zxr10ACLLinkRuleDestMACWildcard are invalid,
        zxr10ACLLinkRuleDestMACRg2Min and 
        zxr10ACLLinkRuleDestMACRg2Max are valid."
    DEFVAL    {2} 
    ::= { zxr10ACLLinkRuleEntry 25 } 

zxr10ACLLinkRuleDestMACRg2Min  OBJECT-TYPE
    SYNTAX   MacAddress
    MAX-ACCESS  read-only
    STATUS  current
    DESCRIPTION
        "<xxxx.xxxx.xxxx>
        Lower limit of second destination MAC address range"
    ::= { zxr10ACLLinkRuleEntry 26 }

zxr10ACLLinkRuleDestMACRg2Max  OBJECT-TYPE
    SYNTAX   MacAddress
    MAX-ACCESS  read-only
    STATUS  current
    DESCRIPTION
        "<xxxx.xxxx.xxxx>  
        Upper limit of second destination MAC address range"
    ::= { zxr10ACLLinkRuleEntry 27 }
    
zxr10ACLLinkRuleDescription  OBJECT-TYPE
    SYNTAX   DisplayString(SIZE(0..70))
    MAX-ACCESS  read-only
    STATUS  current
    DESCRIPTION
        "Description for use (1-70 characters)."
    ::= { zxr10ACLLinkRuleEntry 28 }

zxr10ACLLinkRuleLinkProtocolMask  OBJECT-TYPE
    SYNTAX   Unsigned32(0..65536)   
    MAX-ACCESS  read-only
    STATUS  current
    DESCRIPTION
        "Link protocal mask:
         <0-65535>     valid value
         65536         invalid value
         This is an optional node."
    ::= { zxr10ACLLinkRuleEntry 29 } 

zxr10ACLLinkRuleInCosRange  OBJECT-TYPE
    SYNTAX   DisplayString
    MAX-ACCESS  read-only
    STATUS  current
    DESCRIPTION
        "Range of inner CoS:
         <0-7>-<0-7>    valid value
         65535          invalid value
         This is an optional node."
    ::= { zxr10ACLLinkRuleEntry 30 } 
    
zxr10ACLLinkRuleOutCosRange   OBJECT-TYPE
    SYNTAX   DisplayString
    MAX-ACCESS  read-only
    STATUS  current
    DESCRIPTION
        "Range of outer CoS:
         <0-7>-<0-7>    valid value
         65535          invalid value
         This is an optional node."
    ::= { zxr10ACLLinkRuleEntry 31 } 

zxr10ACLLinkRuleDsap  OBJECT-TYPE
    SYNTAX   Integer32(0..255|65535)   
    MAX-ACCESS  read-only
    STATUS  current
    DESCRIPTION
        "Destination service access point:
         <0-255>       valid value
         65535         invalid value
         This is an optional node."
    ::= { zxr10ACLLinkRuleEntry 32 } 

zxr10ACLLinkRuleSsap  OBJECT-TYPE
    SYNTAX   Integer32(0..255|65535)   
    MAX-ACCESS  read-only
    STATUS  current
    DESCRIPTION
        "Source service access point:
         <0-255>       valid value
         65535         invalid value
         This is an optional node."
    ::= { zxr10ACLLinkRuleEntry 33 } 


--------------------------------------------------------------
--------------------------------------------------------------
--zxr10ACLv4MixObjects
--------------------------------------------------------------
--1  zxr10ACLv4MixListTable
--2  zxr10ACLv4MixRuleTable

--------------------------------------------------------------
--------------------------------------------------------------
--zxr10ACLv4MixTable
--------------------------------------------------------------
zxr10ACLv4MixListTable  OBJECT-TYPE
    SYNTAX  SEQUENCE OF Zxr10ACLv4MixListEntry
    MAX-ACCESS  not-accessible
    STATUS  current
    DESCRIPTION
        "IPv4 Mixed ACL Table"
    ::= { zxr10ACLv4MixObjects 1 }

zxr10ACLv4MixListEntry  OBJECT-TYPE
    SYNTAX  Zxr10ACLv4MixListEntry
    MAX-ACCESS  not-accessible
    STATUS  current
    DESCRIPTION
        "IPv4Mix ACL"
    INDEX  { zxr10ACLv4MixListName }
    ::= { zxr10ACLv4MixListTable 1 }
    
Zxr10ACLv4MixListEntry ::=SEQUENCE {
        zxr10ACLv4MixListName                DisplayString
}
       
zxr10ACLv4MixListName  OBJECT-TYPE
    SYNTAX   DisplayString(SIZE(1..31))
    MAX-ACCESS  read-only
    STATUS  current
    DESCRIPTION
        "Name of an IPv4 mixed access-list (1-31 characters)"
    ::= { zxr10ACLv4MixListEntry 1 }


--------------------------------------------------------------
--------------------------------------------------------------
--zxr10ACLv4MixRuleTable
--------------------------------------------------------------
zxr10ACLv4MixRuleTable  OBJECT-TYPE
    SYNTAX  SEQUENCE OF Zxr10ACLv4MixRuleEntry
    MAX-ACCESS  not-accessible
    STATUS  current
    DESCRIPTION
        "IPv4 Mixed ACL Rule Table"
    ::= { zxr10ACLv4MixObjects 2 }

zxr10ACLv4MixRuleEntry  OBJECT-TYPE
    SYNTAX  Zxr10ACLv4MixRuleEntry
    MAX-ACCESS  not-accessible
    STATUS  current
    DESCRIPTION
        "IPv4Mix ACL
        effective leaf nodes: 
        A leaf node which is effective or not depends on the type of rule. 
        Rule types include standard type, ip type, tcp type, udp type ,icmp 
        type , represented by  zxr10ACLv4RuleIpProtocol in this table. 
        According to the rule type (zxr10ACLv4MixRuleIpProtocol) , 
        the following leaf nodes are effective. 

        1. rule type : std type
           effective leaf nodes: zxr10ACLv4MixRuleAclName,
                                 zxr10ACLv4MixRuleRuleID,
                                 zxr10ACLv4MixRulePermitDeny,
                                 zxr10ACLv4MixRuleLinkProtocol,
                                 zxr10ACLv4MixRuleSrcMAC, 
                                 zxr10ACLv4MixRuleSrcMACWildcard,
                                 zxr10ACLv4MixRuleDestMAC,
                                 zxr10ACLv4MixRuleDestMACWildcard,
                                 zxr10ACLv4MixRuleIncos, 
                                 zxr10ACLv4MixRuleOutCos,
                                 zxr10ACLv4MixRuleInVlanID,
                                 zxr10ACLv4MixRuleOutVlanID,
                                 zxr10ACLv4MixRuleInVlanRange,
                                 zxr10ACLv4MixRuleOutVlanRange,
                                 zxr10ACLv4MixRuleSrcAddr,
                                 zxr10ACLv4MixRuleSrcWildcard,
                                 zxr10ACLv4MixRuleTimerangeName,
                                 zxr10ACLv4MixRuleBSrcMACRange1,
                                 zxr10ACLv4MixRuleSrcMACRg1Min,
                                 zxr10ACLv4MixRuleSrcMACRg1Max,  
                                 zxr10ACLv4MixRuleBSrcMACRange2,
                                 zxr10ACLv4MixRuleSrcMACRg2Min,
                                 zxr10ACLv4MixRuleSrcMACRg2Max,  
                                 zxr10ACLv4MixRuleBDestMACRange1,
                                 zxr10ACLv4MixRuleDestMACRg1Min,
                                 zxr10ACLv4MixRuleDestMACRg1Max,  
                                 zxr10ACLv4MixRuleBDestMACRange2,
                                 zxr10ACLv4MixRuleDestMACRg2Min,
                                 zxr10ACLv4MixRuleDestMACRg2Max,
                                 zxr10ACLv4MixRuleLinkProtocolEx
                                 zxr10ACLv4MixRuleDsap,
                                 zxr10ACLv4MixRuleSsap
        2. rule type : ip type
           effective leaf nodes: zxr10ACLv4MixRuleAclName, 
                                 zxr10ACLv4MixRuleRuleID,
                                 zxr10ACLv4MixRulePermitDeny,
                                 zxr10ACLv4MixRuleLinkProtocol,
                                 zxr10ACLv4MixRuleSrcMAC, 
                                 zxr10ACLv4MixRuleSrcMACWildcard,
                                 zxr10ACLv4MixRuleDestMAC,
                                 zxr10ACLv4MixRuleDestMACWildcard,
                                 zxr10ACLv4MixRuleIncos, 
                                 zxr10ACLv4MixRuleOutCos,
                                 zxr10ACLv4MixRuleInVlanID,
                                 zxr10ACLv4MixRuleOutVlanID,
                                 zxr10ACLv4MixRuleInVlanRange,
                                 zxr10ACLv4MixRuleOutVlanRange,
                                 zxr10ACLv4MixRuleSrcAddr,
                                 zxr10ACLv4MixRuleSrcWildcard,
                                 zxr10ACLv4MixRuleDestAddr,
                                 zxr10ACLv4MixRuleDestWildcard,
                                 zxr10ACLv4MixRuleIpProtocol, 
                                 zxr10ACLv4MixRulePrecedence,
                                 zxr10ACLv4MixRuleTOS,
                                 zxr10ACLv4MixRuleDSCP,
                                 zxr10ACLv4MixRuleFragment,
                                 zxr10ACLv4MixRuleTimerangeName,
                                 zxr10ACLv4MixRuleBSrcMACRange1,
                                 zxr10ACLv4MixRuleSrcMACRg1Min,
                                 zxr10ACLv4MixRuleSrcMACRg1Max,  
                                 zxr10ACLv4MixRuleBSrcMACRange2,
                                 zxr10ACLv4MixRuleSrcMACRg2Min,
                                 zxr10ACLv4MixRuleSrcMACRg2Max,  
                                 zxr10ACLv4MixRuleBDestMACRange1,
                                 zxr10ACLv4MixRuleDestMACRg1Min,
                                 zxr10ACLv4MixRuleDestMACRg1Max,  
                                 zxr10ACLv4MixRuleBDestMACRange2,
                                 zxr10ACLv4MixRuleDestMACRg2Min,
                                 zxr10ACLv4MixRuleDestMACRg2Max,
                                 zxr10ACLv4MixRuleLinkProtocolEx                                
                                 zxr10ACLv4MixRuleDsap,
                                 zxr10ACLv4MixRuleSsap
        3. rule type : tcp type
           effective leaf nodes: zxr10ACLv4MixRuleAclName,
                                 zxr10ACLv4MixRuleRuleID,
                                 zxr10ACLv4MixRulePermitDeny,
                                 zxr10ACLv4MixRuleLinkProtocol,
                                 zxr10ACLv4MixRuleSrcMAC, 
                                 zxr10ACLv4MixRuleSrcMACWildcard,
                                 zxr10ACLv4MixRuleDestMAC,
                                 zxr10ACLv4MixRuleDestMACWildcard,
                                 zxr10ACLv4MixRuleIncos, 
                                 zxr10ACLv4MixRuleOutCos,
                                 zxr10ACLv4MixRuleInVlanID,
                                 zxr10ACLv4MixRuleOutVlanID, 
                                 zxr10ACLv4MixRuleInVlanRange,
                                 zxr10ACLv4MixRuleOutVlanRange, 
                                 zxr10ACLv4MixRuleSrcAddr,
                                 zxr10ACLv4MixRuleSrcWildcard,
                                 zxr10ACLv4MixRuleDestAddr,
                                 zxr10ACLv4MixRuleDestWildcard,
                                 zxr10ACLv4MixRuleIpProtocol,
                                 zxr10ACLv4MixRuleSrcPortOpr,
                                 zxr10ACLv4MixRuleSrcPortValue,
                                 zxr10ACLv4MixRuleSrcPortRange,
                                 zxr10ACLv4MixRuleDestPortOpr,
                                 zxr10ACLv4MixRuleDestPortValue,
                                 zxr10ACLv4MixRuleDestPortRange,
                                 zxr10ACLv4MixRuleTCPEstablish,
                                 zxr10ACLv4MixRulePrecedence,
                                 zxr10ACLv4MixRuleTOS,
                                 zxr10ACLv4MixRuleDSCP,
                                 zxr10ACLv4MixRuleFragment,
                                 zxr10ACLv4MixRuleRstFlag,
                                 zxr10ACLv4MixRuleAckFlag,
                                 zxr10ACLv4MixRuleFinFlag,
                                 zxr10ACLv4MixRuleSynFlag,
                                 zxr10ACLv4MixRulePshFlag,
                                 zxr10ACLv4MixRuleUrgFlag,
                                 zxr10ACLv4MixRuleTimerangeName,
                                 zxr10ACLv4MixRuleBSrcMACRange1,
                                 zxr10ACLv4MixRuleSrcMACRg1Min,
                                 zxr10ACLv4MixRuleSrcMACRg1Max,  
                                 zxr10ACLv4MixRuleBSrcMACRange2,
                                 zxr10ACLv4MixRuleSrcMACRg2Min,
                                 zxr10ACLv4MixRuleSrcMACRg2Max,  
                                 zxr10ACLv4MixRuleBDestMACRange1,
                                 zxr10ACLv4MixRuleDestMACRg1Min,
                                 zxr10ACLv4MixRuleDestMACRg1Max,  
                                 zxr10ACLv4MixRuleBDestMACRange2,
                                 zxr10ACLv4MixRuleDestMACRg2Min,
                                 zxr10ACLv4MixRuleDestMACRg2Max,
                                 zxr10ACLv4MixRuleLinkProtocolEx                               
                                 zxr10ACLv4MixRuleDsap,
                                 zxr10ACLv4MixRuleSsap
        4. rule type : ucp type
           effective leaf nodes: zxr10ACLv4MixRuleAclName,
                                 zxr10ACLv4MixRuleRuleID,
                                 zxr10ACLv4MixRulePermitDeny,
                                 zxr10ACLv4MixRuleLinkProtocol,
                                 zxr10ACLv4MixRuleSrcMAC, 
                                 zxr10ACLv4MixRuleSrcMACWildcard,
                                 zxr10ACLv4MixRuleDestMAC,
                                 zxr10ACLv4MixRuleDestMACWildcard,
                                 zxr10ACLv4MixRuleIncos, 
                                 zxr10ACLv4MixRuleOutCos,
                                 zxr10ACLv4MixRuleInVlanID,
                                 zxr10ACLv4MixRuleOutVlanID,
                                 zxr10ACLv4MixRuleInVlanRange,
                                 zxr10ACLv4MixRuleOutVlanRange,
                                 zxr10ACLv4MixRuleSrcAddr,
                                 zxr10ACLv4MixRuleSrcWildcard,
                                 zxr10ACLv4MixRuleDestAddr,
                                 zxr10ACLv4MixRuleDestWildcard,
                                 zxr10ACLv4MixRuleIpProtocol,
                                 zxr10ACLv4MixRuleSrcPortOpr,
                                 zxr10ACLv4MixRuleSrcPortValue,
                                 zxr10ACLv4MixRuleSrcPortRange,
                                 zxr10ACLv4MixRuleDestPortOpr,
                                 zxr10ACLv4MixRuleDestPortValue,
                                 zxr10ACLv4MixRuleDestPortRange,
                                 zxr10ACLv4MixRulePrecedence,
                                 zxr10ACLv4MixRuleTOS,
                                 zxr10ACLv4MixRuleDSCP,
                                 zxr10ACLv4MixRuleFragment,
                                 zxr10ACLv4MixRuleTimerangeName,
                                 zxr10ACLv4MixRuleBSrcMACRange1,
                                 zxr10ACLv4MixRuleSrcMACRg1Min,
                                 zxr10ACLv4MixRuleSrcMACRg1Max,  
                                 zxr10ACLv4MixRuleBSrcMACRange2,
                                 zxr10ACLv4MixRuleSrcMACRg2Min,
                                 zxr10ACLv4MixRuleSrcMACRg2Max,  
                                 zxr10ACLv4MixRuleBDestMACRange1,
                                 zxr10ACLv4MixRuleDestMACRg1Min,
                                 zxr10ACLv4MixRuleDestMACRg1Max,  
                                 zxr10ACLv4MixRuleBDestMACRange2,
                                 zxr10ACLv4MixRuleDestMACRg2Min,
                                 zxr10ACLv4MixRuleDestMACRg2Max,
                                 zxr10ACLv4MixRuleLinkProtocolEx                              
                                 zxr10ACLv4MixRuleDsap,
                                 zxr10ACLv4MixRuleSsap
        5. rule type : icmp type
           effective leaf nodes: zxr10ACLv4MixRuleAclName,
                                 zxr10ACLv4MixRuleRuleID,
                                 zxr10ACLv4MixRulePermitDeny,
                                 zxr10ACLv4MixRuleLinkProtocol,
                                 zxr10ACLv4MixRuleSrcMAC, 
                                 zxr10ACLv4MixRuleSrcMACWildcard,
                                 zxr10ACLv4MixRuleDestMAC,
                                 zxr10ACLv4MixRuleDestMACWildcard,
                                 zxr10ACLv4MixRuleIncos, 
                                 zxr10ACLv4MixRuleOutCos,
                                 zxr10ACLv4MixRuleInVlanID,
                                 zxr10ACLv4MixRuleOutVlanID,
                                 zxr10ACLv4MixRuleInVlanRange,
                                 zxr10ACLv4MixRuleOutVlanRange,
                                 zxr10ACLv4MixRuleSrcAddr,
                                 zxr10ACLv4MixRuleSrcWildcard,
                                 zxr10ACLv4MixRuleDestAddr,
                                 zxr10ACLv4MixRuleDestWildcard,
                                 zxr10ACLv4MixRuleIpProtocol,
                                 zxr10ACLv4MixRuleICMPType,
                                 zxr10ACLv4MixRuleICMPCode,
                                 zxr10ACLv4MixRulePrecedence,
                                 zxr10ACLv4MixRuleTOS,
                                 zxr10ACLv4MixRuleDSCP,
                                 zxr10ACLv4MixRuleFragment,
                                 zxr10ACLv4MixRuleTimerangeName,
                                 zxr10ACLv4MixRuleBSrcMACRange1,
                                 zxr10ACLv4MixRuleSrcMACRg1Min,
                                 zxr10ACLv4MixRuleSrcMACRg1Max,  
                                 zxr10ACLv4MixRuleBSrcMACRange2,
                                 zxr10ACLv4MixRuleSrcMACRg2Min,
                                 zxr10ACLv4MixRuleSrcMACRg2Max,  
                                 zxr10ACLv4MixRuleBDestMACRange1,
                                 zxr10ACLv4MixRuleDestMACRg1Min,
                                 zxr10ACLv4MixRuleDestMACRg1Max,  
                                 zxr10ACLv4MixRuleBDestMACRange2,
                                 zxr10ACLv4MixRuleDestMACRg2Min,
                                 zxr10ACLv4MixRuleDestMACRg2Max,
                                 zxr10ACLv4MixRuleLinkProtocolEx,
                                 zxr10ACLv4MixRuleDsap,
                                 zxr10ACLv4MixRuleSsap                              
        conflict leaf nodes:
        1. zxr10ACLv4MixRuleFragment conflicts with 
                                 zxr10ACLv4MixRuleSrcPortOpr,
                                 zxr10ACLv4MixRuleSrcPortValue,
                                 zxr10ACLv4MixRuleSrcPortRange,
                                 zxr10ACLv4MixRuleDestPortOpr,
                                 zxr10ACLv4MixRuleDestPortValue,
                                 zxr10ACLv4MixRuleDestPortRange,
                                 zxr10ACLv4MixRuleTCPEstablish,
                                 zxr10ACLv4MixRuleICMPType,
                                 zxr10ACLv4MixRuleICMPCode,
                                 zxr10ACLv4MixRuleRstFlag,
                                 zxr10ACLv4MixRuleAckFlag,
                                 zxr10ACLv4MixRuleFinFlag,
                                 zxr10ACLv4MixRuleSynFlag,
                                 zxr10ACLv4MixRulePshFlag,
                                 zxr10ACLv4MixRuleUrgFlag 
        2. These leaf nodes conflict with each other:
                                 zxr10ACLv4MixRulePrecedence,
                                 zxr10ACLv4MixRuleTOS,
                                 zxr10ACLv4MixRuleDSCP
        3. zxr10ACLv4MixRuleTCPEstablish conflicts with 
                                 zxr10ACLv4MixRuleRstFlag,
                                 zxr10ACLv4MixRuleAckFlag 
        4. zxr10ACLv4MixRuleLinkProtocolEx conflicts with
                                 zxr10ACLv4MixRuleDsap,
                                 zxr10ACLv4MixRuleSsap
                                 "
    INDEX  { zxr10ACLv4MixRuleAclName,
             zxr10ACLv4MixRuleRuleID }
    ::= { zxr10ACLv4MixRuleTable 1 }
    
Zxr10ACLv4MixRuleEntry ::=SEQUENCE {
        zxr10ACLv4MixRuleAclName             DisplayString,
        zxr10ACLv4MixRuleRuleID              Integer32,
        zxr10ACLv4MixRulePermitDeny          AclPermitDeny,
        zxr10ACLv4MixRuleLinkProtocol        Integer32,
        zxr10ACLv4MixRuleSrcMAC              MacAddress,
        zxr10ACLv4MixRuleSrcMACWildcard      MacAddress,
        zxr10ACLv4MixRuleDestMAC             MacAddress,
        zxr10ACLv4MixRuleDestMACWildcard     MacAddress,
        zxr10ACLv4MixRuleIncos               Integer32, 
        zxr10ACLv4MixRuleOutCos              Integer32,
        zxr10ACLv4MixRuleInVlanID            Integer32,
        zxr10ACLv4MixRuleOutVlanID           Integer32,
        zxr10ACLv4MixRuleInVlanRange         DisplayString,
        zxr10ACLv4MixRuleOutVlanRange        DisplayString,
        zxr10ACLv4MixRuleSrcAddr             IpAddress,
        zxr10ACLv4MixRuleSrcWildcard         IpAddress,
        zxr10ACLv4MixRuleDestAddr            IpAddress,
        zxr10ACLv4MixRuleDestWildcard        IpAddress,
        zxr10ACLv4MixRuleIpProtocol          INTEGER,
        zxr10ACLv4MixRuleSrcPortOpr          INTEGER,
        zxr10ACLv4MixRuleSrcPortValue        INTEGER,
        zxr10ACLv4MixRuleSrcPortRange        DisplayString,
        zxr10ACLv4MixRuleDestPortOpr         INTEGER,
        zxr10ACLv4MixRuleDestPortValue       INTEGER,
        zxr10ACLv4MixRuleDestPortRange       DisplayString,
        zxr10ACLv4MixRuleTCPEstablish        AclValidOrNot, 
        zxr10ACLv4MixRuleICMPType            INTEGER,
        zxr10ACLv4MixRuleICMPCode            INTEGER,
        zxr10ACLv4MixRulePrecedence          Integer32,
        zxr10ACLv4MixRuleTOS                 Integer32,
        zxr10ACLv4MixRuleDSCP                Integer32,
        zxr10ACLv4MixRuleFragment            AclValidOrNot,
        zxr10ACLv4MixRuleRstFlag             AclTcpFlagType,
        zxr10ACLv4MixRuleAckFlag             AclTcpFlagType,
        zxr10ACLv4MixRuleFinFlag             AclTcpFlagType,
        zxr10ACLv4MixRuleSynFlag             AclTcpFlagType,
        zxr10ACLv4MixRulePshFlag             AclTcpFlagType,
        zxr10ACLv4MixRuleUrgFlag             AclTcpFlagType,
        zxr10ACLv4MixRuleTimerangeName       DisplayString,
        zxr10ACLv4MixRuleBSrcMACRange1       AclValidOrNot,
        zxr10ACLv4MixRuleSrcMACRg1Min        MacAddress,
        zxr10ACLv4MixRuleSrcMACRg1Max        MacAddress,  
        zxr10ACLv4MixRuleBSrcMACRange2       AclValidOrNot,
        zxr10ACLv4MixRuleSrcMACRg2Min        MacAddress,
        zxr10ACLv4MixRuleSrcMACRg2Max        MacAddress,  
        zxr10ACLv4MixRuleBDestMACRange1      AclValidOrNot,
        zxr10ACLv4MixRuleDestMACRg1Min       MacAddress,
        zxr10ACLv4MixRuleDestMACRg1Max       MacAddress,  
        zxr10ACLv4MixRuleBDestMACRange2      AclValidOrNot,
        zxr10ACLv4MixRuleDestMACRg2Min       MacAddress,
        zxr10ACLv4MixRuleDestMACRg2Max       MacAddress,
        zxr10ACLv4MixRuleLinkProtocolEx      Integer32,
        zxr10ACLv4MixRuleDsap                Integer32,
        zxr10ACLv4MixRuleSsap                Integer32
}
       
zxr10ACLv4MixRuleAclName  OBJECT-TYPE
    SYNTAX   DisplayString(SIZE(1..31))
    MAX-ACCESS  not-accessible
    STATUS  current
    DESCRIPTION
        "Name of an IPv4 mixed access-list (1-31 characters)"
    ::= { zxr10ACLv4MixRuleEntry 1 } 
        
zxr10ACLv4MixRuleRuleID  OBJECT-TYPE
    SYNTAX   Integer32(1..2147483644)
    MAX-ACCESS  not-accessible
    STATUS  current
    DESCRIPTION
        "ID of this rule"
    ::= { zxr10ACLv4MixRuleEntry 2 }    

zxr10ACLv4MixRulePermitDeny  OBJECT-TYPE
    SYNTAX   AclPermitDeny
    MAX-ACCESS  read-only
    STATUS  current
    DESCRIPTION
        "deny  :  Specify packets to reject
         permit:  Specify packets to forward"
    ::= { zxr10ACLv4MixRuleEntry 3 } 

zxr10ACLv4MixRuleLinkProtocol  OBJECT-TYPE
    SYNTAX   Integer32(0..65536)   
    MAX-ACCESS  read-only
    STATUS  obsolete
    DESCRIPTION
        "Link protocal:
         <0-65535>  valid value
         65536      invalid value
         This is an optional node."
    ::= { zxr10ACLv4MixRuleEntry 4 } 

zxr10ACLv4MixRuleSrcMAC  OBJECT-TYPE
    SYNTAX   MacAddress
    MAX-ACCESS  read-only
    STATUS  current
    DESCRIPTION
        "<xxxx.xxxx.xxxx>  Source MAC address"
    ::= { zxr10ACLv4MixRuleEntry 5 }

zxr10ACLv4MixRuleSrcMACWildcard  OBJECT-TYPE
    SYNTAX   MacAddress
    MAX-ACCESS  read-only
    STATUS  current
    DESCRIPTION
        "<xxxx.xxxx.xxxx>  Source MAC wildcard"
    ::= { zxr10ACLv4MixRuleEntry 6 } 

zxr10ACLv4MixRuleDestMAC  OBJECT-TYPE
    SYNTAX   MacAddress
    MAX-ACCESS  read-only
    STATUS  current
    DESCRIPTION
        "<xxxx.xxxx.xxxx>  Destination MAC address"
    ::= { zxr10ACLv4MixRuleEntry 7 } 
    
zxr10ACLv4MixRuleDestMACWildcard  OBJECT-TYPE
    SYNTAX   MacAddress
    MAX-ACCESS  read-only
    STATUS  current
    DESCRIPTION
        "<xxxx.xxxx.xxxx>  Destination MAC wildcard"
    ::= { zxr10ACLv4MixRuleEntry 8 } 
 
zxr10ACLv4MixRuleIncos     OBJECT-TYPE
    SYNTAX   Integer32(0..7|255)
    MAX-ACCESS  read-only
    STATUS  current
    DESCRIPTION
        "Value of inner cos:
         <0-7>  valid value
         255    invalid value
         This is an optional node."
    ::= { zxr10ACLv4MixRuleEntry 9 }     
    
zxr10ACLv4MixRuleOutCos   OBJECT-TYPE
    SYNTAX   Integer32(0..7|255)
    MAX-ACCESS  read-only
    STATUS  current
    DESCRIPTION
        "Value of outer cos:
         <0-7>  valid value
         255    invalid value
         This is an optional node."
    ::= { zxr10ACLv4MixRuleEntry 10 }

zxr10ACLv4MixRuleInVlanID  OBJECT-TYPE
    SYNTAX   Integer32(1..4094|65535)
    MAX-ACCESS  read-only
    STATUS  current
    DESCRIPTION
        "Value of inner vlan
         <1-4094>   valid value
         65535      invalid value
         This is an optional node."
    ::= { zxr10ACLv4MixRuleEntry 11 }
    
zxr10ACLv4MixRuleOutVlanID  OBJECT-TYPE
    SYNTAX   Integer32(1..4094|65535)
    MAX-ACCESS  read-only
    STATUS  current
    DESCRIPTION
        "Value of outer vlan
         <1-4094>   valid value
         65535      invalid value
         This is an optional node."
    ::= { zxr10ACLv4MixRuleEntry 12 }
    
zxr10ACLv4MixRuleInVlanRange  OBJECT-TYPE
    SYNTAX   DisplayString
    MAX-ACCESS  read-only
    STATUS  current
    DESCRIPTION
        "Range of inner vlan
         <1-4094>-<1-4094>    valid value
         0                    invalid value
         This is an optional node."
    ::= { zxr10ACLv4MixRuleEntry 13 } 
    
zxr10ACLv4MixRuleOutVlanRange   OBJECT-TYPE
    SYNTAX   DisplayString
    MAX-ACCESS  read-only
    STATUS  current
    DESCRIPTION
        "Range of outer vlan
         <1-4094>-<1-4094>    valid value
         0                    invalid value
         This is an optional node."
    ::= { zxr10ACLv4MixRuleEntry 14 }

zxr10ACLv4MixRuleSrcAddr  OBJECT-TYPE
    SYNTAX   IpAddress
    MAX-ACCESS  read-only
    STATUS  current
    DESCRIPTION
        "A.B.C.D  Source address"
    ::= { zxr10ACLv4MixRuleEntry 15 }    

zxr10ACLv4MixRuleSrcWildcard  OBJECT-TYPE
    SYNTAX   IpAddress
    MAX-ACCESS  read-only
    STATUS  current
    DESCRIPTION
        "A.B.C.D  Wildcard bits"
    ::= { zxr10ACLv4MixRuleEntry 16 } 
    
zxr10ACLv4MixRuleDestAddr  OBJECT-TYPE
    SYNTAX   IpAddress
    MAX-ACCESS  read-only
    STATUS  current
    DESCRIPTION
        "A.B.C.D  Destination address"
    ::= { zxr10ACLv4MixRuleEntry 17 } 
       
zxr10ACLv4MixRuleDestWildcard  OBJECT-TYPE
    SYNTAX   IpAddress
    MAX-ACCESS  read-only
    STATUS  current
    DESCRIPTION
        "A.B.C.D  Destination wildcard bits"
    ::= { zxr10ACLv4MixRuleEntry 18 } 

zxr10ACLv4MixRuleIpProtocol  OBJECT-TYPE
    SYNTAX   INTEGER{icmp(1),igmp(2),tcp(6),udp(17),gre(47),ospf(89),
             pim(103),vrrp(112),sctp(132),std(65534),ip(65535)}
    MAX-ACCESS  read-only
    STATUS  current
    DESCRIPTION
        "<0-255>  An IP protocol number   
          std      Standard rule type (65534)
          gre      Generic Routing Encapsulation (47)
          icmp     Internet Control Message Protocol (1)
          igmp     Internet Group Management Protocol (2)
          ip       Any internet protocol (65535)
          ospf     Open Shortest Path First Protocol (89)
          pim      Protocol Independent Multicast (103)
          tcp      Transmission Control Protocol (6)
          udp      User Datagram Protocol (17)
          sctp     Stream Control Transmission Protocol (132)
          vrrp     Virtual Router Redundancy Protocol (112)"
    ::= { zxr10ACLv4MixRuleEntry 19 }
        
zxr10ACLv4MixRuleSrcPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number
         le       Match only packets with a no greater port number
         range    Match only packet on a given port range
         65535    invalid value
 
        Needn't care for zxr10ACLv4MixRuleSrcPortValue and 
        zxr10ACLv4MixRuleSrcPortRange When the value of 
        zxr10ACLv4MixRuleSrcPortOpr is invalid(65535).
        Check zxr10ACLv4MixRuleSrcPortValue when the value 
        zxr10ACLv4MixRuleSrcPortOpr is eq(1),ge(2) or le(3).
        Check zxr10ACLv4MixRuleSrcPortRange only when the value of 
        zxr10ACLv4MixRuleSrcPortOpr is range(7)."
    ::= { zxr10ACLv4MixRuleEntry 20 }    
    
zxr10ACLv4MixRuleSrcPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv4MixRuleSrcPortOpr is 
        eq(1), ge(2) or le(3)."
    ::= { zxr10ACLv4MixRuleEntry 21 }    
    
zxr10ACLv4MixRuleSrcPortRange  OBJECT-TYPE
    SYNTAX   DisplayString
    MAX-ACCESS  read-only
    STATUS  current
    DESCRIPTION
        "Port range:  <0-65535>-<0-65535>
        Check zxr10ACLv4MixRuleSrcPortRange only when the value of 
        zxr10ACLv4MixRuleSrcPortOpr is range(7)."
    ::= { zxr10ACLv4MixRuleEntry 22 }    
    
zxr10ACLv4MixRuleDestPortOpr  OBJECT-TYPE
    SYNTAX   INTEGER{oprTypeInvalid(65535),eq(1),ge(2),le(3),range(7)}
    MAX-ACCESS  read-only
    STATUS  current
    DESCRIPTION
        "This is an optional node.
         eq       Match only packets on a given port number 
         ge       Match only packets with a no lower port number
         le       Match only packets with a no greater port number 
         range    Match only packet on a given port range
         65535    invalid value
 
        Needn't care for zxr10ACLv4MixRuleDestPortValue and 
        zxr10ACLv4MixRuleDestPortRange When the value of 
        zxr10ACLv4MixRuleDestPortOpr is invalid(65535).
        Check zxr10ACLv4MixRuleDestPortValue when the value 
        zxr10ACLv4MixRuleDestPortOpr is eq(1),ge(2) or le(3).
        Check zxr10ACLv4MixRuleDestPortRange only when the value of 
        zxr10ACLv4MixRuleDestPortOpr is range(7)."
    ::= { zxr10ACLv4MixRuleEntry 23 }    
    
zxr10ACLv4MixRuleDestPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number 
        bootpc       Bootstrap protocol (BOOTP) client (68)
        bootps       Bootstrap protocol (BOOTP) server (67) 
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv4MixRuleDestPortOpr is 
        eq(1),ge(2) or le(3)."
    ::= { zxr10ACLv4MixRuleEntry 24 }    
    
zxr10ACLv4MixRuleDestPortRange  OBJECT-TYPE
    SYNTAX   DisplayString
    MAX-ACCESS  read-only
    STATUS  current
    DESCRIPTION
        "Port range:  <0-65535>-<0-65535>
        Check zxr10ACLv4MixRuleDestPortRange only when the value of 
        zxr10ACLv4MixRuleDestPortOpr is range(7)."
    ::= { zxr10ACLv4MixRuleEntry 25 }   
     
zxr10ACLv4MixRuleTCPEstablish  OBJECT-TYPE
    SYNTAX    AclValidOrNot
    MAX-ACCESS  read-only
    STATUS  current
    DESCRIPTION
        "Match established connections.
         This is an optional node."
    DEFVAL    {2} 
    ::= { zxr10ACLv4MixRuleEntry 26 }  

zxr10ACLv4MixRuleICMPType  OBJECT-TYPE
    SYNTAX   INTEGER(0..255|65535)
    MAX-ACCESS  read-only
    STATUS  current
    DESCRIPTION
        "ICMP type:
         <0-255>               valid value
         65535                 invalid value
         specific value:
         alternate-address     Alternate address (6)
         echo                  Echo (ping, 8)
         echo-reply            Echo reply (0)
         information-request   Information requests (15)
         parameter-problem     All parameter problems (12)
         redirect              All redirects (5)
         router-advertisement  Router discovery advertisements (9)
         router-solicitation   Router discovery solicitations (10)
         source-quench         Source quenches (4)
         time-exceeded         All time exceededs (11)
         timestamp-reply       Timestamp replies (14)
         timestamp-request     Timestamp requests (13)
         unreachable           All unreachables (3)

        This is an optional node."
    ::= { zxr10ACLv4MixRuleEntry 27 }    
    
zxr10ACLv4MixRuleICMPCode  OBJECT-TYPE
    SYNTAX   INTEGER(0..255|65535)
    MAX-ACCESS  read-only
    STATUS  current
    DESCRIPTION
        "ICMP code:
         <0-255>      valid value
         65535        invalid value
         This is an optional node."
    ::= { zxr10ACLv4MixRuleEntry 28 }  
        
zxr10ACLv4MixRulePrecedence  OBJECT-TYPE
    SYNTAX   Integer32(0..7|255)
    MAX-ACCESS  read-only
    STATUS  current
    DESCRIPTION
        "Precedence level:
         <0-7>   valid value
         255     invalid value
         This is an optional node."
    ::= { zxr10ACLv4MixRuleEntry 29 }    
    
zxr10ACLv4MixRuleTOS  OBJECT-TYPE
    SYNTAX   Integer32(0..15|255)
    MAX-ACCESS  read-only
    STATUS  current
    DESCRIPTION
        "Type of service(ToS):
         <0-15>  valid value
         255     invalid value
         This is an optional node."
    ::= { zxr10ACLv4MixRuleEntry 30 }  
      
zxr10ACLv4MixRuleDSCP  OBJECT-TYPE
    SYNTAX   Integer32(0..63|255)
    MAX-ACCESS  read-only
    STATUS  current
    DESCRIPTION
        "DSCP value:
         <0-63>  valid value
         255     invalid value
         This is an optional node."
    ::= { zxr10ACLv4MixRuleEntry 31 }
    
zxr10ACLv4MixRuleFragment  OBJECT-TYPE
    SYNTAX     AclValidOrNot
    MAX-ACCESS  read-only        
    STATUS  current
    DESCRIPTION
        "Fragment enable or disable flag.
         This is an optional node."
    DEFVAL    {2}
    ::= { zxr10ACLv4MixRuleEntry 32 }     

zxr10ACLv4MixRuleRstFlag  OBJECT-TYPE
    SYNTAX   AclTcpFlagType
    MAX-ACCESS  read-only
    STATUS  current
    DESCRIPTION
        "Match when the RST flag set or not.
         This is an optional node.
         invalid value:     (65535)"
    ::= { zxr10ACLv4MixRuleEntry 33 }
    
zxr10ACLv4MixRuleAckFlag  OBJECT-TYPE
    SYNTAX   AclTcpFlagType
    MAX-ACCESS  read-only
    STATUS  current
    DESCRIPTION
        "Match when the ACK flag set or not.
         This is an optional node.
         invalid value:     (65535)"
    ::= { zxr10ACLv4MixRuleEntry 34 }

zxr10ACLv4MixRuleFinFlag  OBJECT-TYPE
    SYNTAX   AclTcpFlagType
    MAX-ACCESS  read-only
    STATUS  current
    DESCRIPTION
        "Match when the FIN flag set or not.
         This is an optional node.
         invalid value:     (65535)"
    ::= { zxr10ACLv4MixRuleEntry 35 }

zxr10ACLv4MixRuleSynFlag  OBJECT-TYPE
    SYNTAX   AclTcpFlagType
    MAX-ACCESS  read-only
    STATUS  current
    DESCRIPTION
        "Match when the SYN flag set or not.
         This is an optional node.
         invalid value:     (65535)"
    ::= { zxr10ACLv4MixRuleEntry 36 }     
    
zxr10ACLv4MixRulePshFlag  OBJECT-TYPE
    SYNTAX   AclTcpFlagType
    MAX-ACCESS  read-only
    STATUS  current
    DESCRIPTION
        "Match when the PSH flag set or not.
         This is an optional node.
         invalid value:     (65535)"
    ::= { zxr10ACLv4MixRuleEntry 37 }

zxr10ACLv4MixRuleUrgFlag  OBJECT-TYPE
    SYNTAX   AclTcpFlagType
    MAX-ACCESS  read-only
    STATUS  current
    DESCRIPTION
        "Match when the URG flag set or not.
         This is an optional node.
         invalid value:     (65535)"
    ::= { zxr10ACLv4MixRuleEntry 38 }
        
zxr10ACLv4MixRuleTimerangeName  OBJECT-TYPE
    SYNTAX   DisplayString(SIZE(0..31))
    MAX-ACCESS  read-only
    STATUS  current
    DESCRIPTION
        "Time range name (1-31 characters).
         This is an optional node."
    ::= { zxr10ACLv4MixRuleEntry 39 }  

zxr10ACLv4MixRuleBSrcMACRange1  OBJECT-TYPE
    SYNTAX   AclValidOrNot   
    MAX-ACCESS  read-only
    STATUS  current
    DESCRIPTION
        "Match if source MAC address range is configured.
        When this is valid, zxr10ACLv4MixRuleSrcMAC and 
        zxr10ACLv4MixRuleSrcMACWildcard are invalid,
        zxr10ACLv4MixRuleSrcMACRg1Min and 
        zxr10ACLv4MixRuleSrcMACRg1Max are valid."
    DEFVAL    {2} 
    ::= { zxr10ACLv4MixRuleEntry 40 } 

zxr10ACLv4MixRuleSrcMACRg1Min  OBJECT-TYPE
    SYNTAX   MacAddress
    MAX-ACCESS  read-only
    STATUS  current
    DESCRIPTION
        "<xxxx.xxxx.xxxx>  
        Lower limit of first source MAC address range"
    ::= { zxr10ACLv4MixRuleEntry 41 }

zxr10ACLv4MixRuleSrcMACRg1Max  OBJECT-TYPE
    SYNTAX   MacAddress
    MAX-ACCESS  read-only
    STATUS  current
    DESCRIPTION
        "<xxxx.xxxx.xxxx>  
        Upper limit of first source MAC address range"
    ::= { zxr10ACLv4MixRuleEntry 42 } 

zxr10ACLv4MixRuleBSrcMACRange2  OBJECT-TYPE
    SYNTAX   AclValidOrNot   
    MAX-ACCESS  read-only
    STATUS  current
    DESCRIPTION
        "Match if second source MAC address range is configured.
        When this is valid, zxr10ACLv4MixRuleSrcMAC and 
        zxr10ACLv4MixRuleSrcMACWildcard are invalid,
        zxr10ACLv4MixRuleSrcMACRg2Min and 
        zxr10ACLv4MixRuleSrcMACRg2Max are valid."
    DEFVAL    {2} 
    ::= { zxr10ACLv4MixRuleEntry 43 } 

zxr10ACLv4MixRuleSrcMACRg2Min  OBJECT-TYPE
    SYNTAX   MacAddress
    MAX-ACCESS  read-only
    STATUS  current
    DESCRIPTION
        "<xxxx.xxxx.xxxx>
        Lower limit of second source MAC address range"
    ::= { zxr10ACLv4MixRuleEntry 44 }

zxr10ACLv4MixRuleSrcMACRg2Max  OBJECT-TYPE
    SYNTAX   MacAddress
    MAX-ACCESS  read-only
    STATUS  current
    DESCRIPTION
        "<xxxx.xxxx.xxxx>  
        Upper limit of second source MAC address range"
    ::= { zxr10ACLv4MixRuleEntry 45 } 

zxr10ACLv4MixRuleBDestMACRange1  OBJECT-TYPE
    SYNTAX   AclValidOrNot   
    MAX-ACCESS  read-only
    STATUS  current
    DESCRIPTION
        "Match if destination MAC address range is configured.
        When this is valid, zxr10ACLv4MixRuleDestMAC and 
        zxr10ACLv4MixRuleDestMACWildcard are invalid,
        zxr10ACLv4MixRuleDestMACRg1Min and  
        zxr10ACLv4MixRuleDestMACRg1Max are valid."
    DEFVAL    {2} 
    ::= { zxr10ACLv4MixRuleEntry 46 } 

zxr10ACLv4MixRuleDestMACRg1Min  OBJECT-TYPE
    SYNTAX   MacAddress
    MAX-ACCESS  read-only
    STATUS  current
    DESCRIPTION
        "<xxxx.xxxx.xxxx>  
        Lower limit of first destination MAC address range"
    ::= { zxr10ACLv4MixRuleEntry 47 }

zxr10ACLv4MixRuleDestMACRg1Max  OBJECT-TYPE
    SYNTAX   MacAddress
    MAX-ACCESS  read-only
    STATUS  current
    DESCRIPTION
        "<xxxx.xxxx.xxxx>  
        Upper limit of first destination MAC address range"
    ::= { zxr10ACLv4MixRuleEntry 48 } 

zxr10ACLv4MixRuleBDestMACRange2  OBJECT-TYPE
    SYNTAX   AclValidOrNot   
    MAX-ACCESS  read-only
    STATUS  current
    DESCRIPTION
        "Match if second destination MAC address range is configured.
        When this is valid, zxr10ACLv4MixRuleDestMAC and 
        zxr10ACLv4MixRuleDestMACWildcard are invalid,
        zxr10ACLv4MixRuleDestMACRg2Min and 
        zxr10ACLv4MixRuleDestMACRg2Max are valid."
    DEFVAL    {2} 
    ::= { zxr10ACLv4MixRuleEntry 49 } 

zxr10ACLv4MixRuleDestMACRg2Min  OBJECT-TYPE
    SYNTAX   MacAddress
    MAX-ACCESS  read-only
    STATUS  current
    DESCRIPTION
        "<xxxx.xxxx.xxxx>
        Lower limit of second destination MAC address range"
    ::= { zxr10ACLv4MixRuleEntry 50 }

zxr10ACLv4MixRuleDestMACRg2Max  OBJECT-TYPE
    SYNTAX   MacAddress
    MAX-ACCESS  read-only
    STATUS  current
    DESCRIPTION
        "<xxxx.xxxx.xxxx>  
        Upper limit of second destination MAC address range"
    ::= { zxr10ACLv4MixRuleEntry 51 } 


zxr10ACLv4MixRuleLinkProtocolEx  OBJECT-TYPE
    SYNTAX   Integer32(1536..65536)   
    MAX-ACCESS  read-only
    STATUS  current
    DESCRIPTION
        "Link protocal:
         <1536-65535>  valid value
         65536         invalid value
         This is an optional node."
    ::= { zxr10ACLv4MixRuleEntry 52 } 

zxr10ACLv4MixRuleDsap  OBJECT-TYPE
    SYNTAX   Integer32(0..255|65535)   
    MAX-ACCESS  read-only
    STATUS  current
    DESCRIPTION
        "Destination service access point:
         <0-255>       valid value
         65535         invalid value
         This is an optional node."
    ::= { zxr10ACLv4MixRuleEntry 53 } 

zxr10ACLv4MixRuleSsap  OBJECT-TYPE
    SYNTAX   Integer32(0..255|65535)   
    MAX-ACCESS  read-only
    STATUS  current
    DESCRIPTION
        "Source service access point:
         <0-255>       valid value
         65535         invalid value
         This is an optional node."
    ::= { zxr10ACLv4MixRuleEntry 54 }

--------------------------------------------------------------
--------------------------------------------------------------
--zxr10ACLv6MixObjects
--------------------------------------------------------------
--1  zxr10ACLv6MixListTable
--2  zxr10ACLv6MixRuleTable

--------------------------------------------------------------
--------------------------------------------------------------
--zxr10ACLv6MixListTable
--------------------------------------------------------------
zxr10ACLv6MixListTable  OBJECT-TYPE
    SYNTAX  SEQUENCE OF Zxr10ACLv6MixListEntry
    MAX-ACCESS  not-accessible
    STATUS  current
    DESCRIPTION
        "IPv6 Mixed ACL Table"
    ::= { zxr10ACLv6MixObjects 1 }

zxr10ACLv6MixListEntry  OBJECT-TYPE
    SYNTAX  Zxr10ACLv6MixListEntry
    MAX-ACCESS  not-accessible
    STATUS  current
    DESCRIPTION
        "IPv6 Mixed ACL"
    INDEX  { zxr10ACLv6MixListName }
    ::= { zxr10ACLv6MixListTable 1 }
    
Zxr10ACLv6MixListEntry ::=SEQUENCE {
        zxr10ACLv6MixListName                  DisplayString
     } 

zxr10ACLv6MixListName  OBJECT-TYPE
    SYNTAX   DisplayString(SIZE(1..31))
    MAX-ACCESS  read-only
    STATUS  current
    DESCRIPTION
        "Name of an IPv6 Mixed access-list (1-31 characters)"
    ::= { zxr10ACLv6MixListEntry 1 } 
        
--------------------------------------------------------------
--------------------------------------------------------------
--zxr10ACLv6MixRuleTable
--------------------------------------------------------------
zxr10ACLv6MixRuleTable  OBJECT-TYPE
    SYNTAX  SEQUENCE OF Zxr10ACLv6MixRuleEntry
    MAX-ACCESS  not-accessible
    STATUS  current
    DESCRIPTION
        "IPv6 Mixed ACL Rule Table"
    ::= { zxr10ACLv6MixObjects 2 }

zxr10ACLv6MixRuleEntry  OBJECT-TYPE
    SYNTAX  Zxr10ACLv6MixRuleEntry
    MAX-ACCESS  not-accessible
    STATUS  current
    DESCRIPTION
        "IPv6 Mixed ACL 
        effective leaf nodes: 
        A leaf node which is effective or not depends on the type of rule.
        Rule types include standard type, ip type, tcp type, udp type ,icmp 
        type , represented by  zxr10ACLv4RuleIpProtocol in this table.
        According to the rule type (zxr10ACLv6MixRuleIpProtocol), the 
        following leaf nodes are effective. 
        1. rule type : ip type
           effective leaf nodes:zxr10ACLv6MixRuleAclName,
                                zxr10ACLv6MixRuleRuleID,
                                zxr10ACLv6MixRulePermitDeny,
                                zxr10ACLv6MixRuleLinkProtocol,
                                zxr10ACLv6MixRuleSrcMAC, 
                                zxr10ACLv6MixRuleSrcMACWildcard,
                                zxr10ACLv6MixRuleDestMAC,
                                zxr10ACLv6MixRuleDestMACWildcard,
                                zxr10ACLv6MixRuleIncos,
                                zxr10ACLv6MixRuleOutCos,
                                zxr10ACLv6MixRuleInVlanID,
                                zxr10ACLv6MixRuleOutVlanID,
                                zxr10ACLv6MixRuleInVlanRange,
                                zxr10ACLv6MixRuleOutVlanRange,
                                zxr10ACLv6MixRuleFlowlabel,  
                                zxr10ACLv6MixRuleSrcAddr, 
                                zxr10ACLv6MixRuleSrcWildcard,
                                zxr10ACLv6MixRuleDestAddr,
                                zxr10ACLv6MixRuleDestWildcard,
                                zxr10ACLv6MixRuleIpProtocol,
                                zxr10ACLv6MixRuleRouting,
                                zxr10ACLv6MixRuleAuthen,
                                zxr10ACLv6MixRuleDestops,
                                zxr10ACLv6MixRuleFragments,
                                zxr10ACLv6MixRuleHopByHop,
                                zxr10ACLv6MixRuleEsp,
                                zxr10ACLv6MixRuleDSCP, 
                                zxr10ACLv6MixRuleTc,
                                zxr10ACLv6MixRuleTimerangeName,
                                zxr10ACLv6MixRuleBSrcMACRange1,
                                zxr10ACLv6MixRuleSrcMACRg1Min,
                                zxr10ACLv6MixRuleSrcMACRg1Max,  
                                zxr10ACLv6MixRuleBSrcMACRange2,
                                zxr10ACLv6MixRuleSrcMACRg2Min,
                                zxr10ACLv6MixRuleSrcMACRg2Max,  
                                zxr10ACLv6MixRuleBDestMACRange1,
                                zxr10ACLv6MixRuleDestMACRg1Min,
                                zxr10ACLv6MixRuleDestMACRg1Max,  
                                zxr10ACLv6MixRuleBDestMACRange2,
                                zxr10ACLv6MixRuleDestMACRg2Min,
                                zxr10ACLv6MixRuleDestMACRg2Max,
                                zxr10ACLv6MixRuleLinkProtocolEx,
                                zxr10ACLv6MixRuleSrcAddrMaskFlag,
                                zxr10ACLv6MixRuleSrcWildcardBits,
                                zxr10ACLv6MixRuleDstAddrMaskFlag,
                                zxr10ACLv6MixRuleDstWildcardBits,
                                zxr10ACLv6MixRuleDsap,
                                zxr10ACLv6MixRuleSsap
        2. rule type : tcp type
            effective leaf nodes:zxr10ACLv6MixRuleAclName,
                                zxr10ACLv6MixRuleRuleID,
                                zxr10ACLv6MixRulePermitDeny,
                                zxr10ACLv6MixRuleLinkProtocol,
                                zxr10ACLv6MixRuleSrcMAC, 
                                zxr10ACLv6MixRuleSrcMACWildcard,
                                zxr10ACLv6MixRuleDestMAC,
                                zxr10ACLv6MixRuleDestMACWildcard,
                                zxr10ACLv6MixRuleIncos,
                                zxr10ACLv6MixRuleOutCos,
                                zxr10ACLv6MixRuleInVlanID,
                                zxr10ACLv6MixRuleOutVlanID,
                                zxr10ACLv6MixRuleInVlanRange,
                                zxr10ACLv6MixRuleOutVlanRange,
                                zxr10ACLv6MixRuleFlowlabel,  
                                zxr10ACLv6MixRuleSrcAddr, 
                                zxr10ACLv6MixRuleSrcWildcard,
                                zxr10ACLv6MixRuleDestAddr,
                                zxr10ACLv6MixRuleDestWildcard,
                                zxr10ACLv6MixRuleIpProtocol,
                                zxr10ACLv6MixRuleSrcPortOpr,
                                zxr10ACLv6MixRuleSrcPortValue,
                                zxr10ACLv6MixRuleSrcPortRange,
                                zxr10ACLv6MixRuleDestPortOpr,
                                zxr10ACLv6MixRuleDestPortValue,
                                zxr10ACLv6MixRuleDestPortRange,
                                zxr10ACLv6MixRuleTCPEstablish,
                                zxr10ACLv6MixRuleRstFlag,
                                zxr10ACLv6MixRuleAckFlag,
                                zxr10ACLv6MixRuleFinFlag,
                                zxr10ACLv6MixRuleSynFlag,
                                zxr10ACLv6MixRulePshFlag,
                                zxr10ACLv6MixRuleUrgFlag,
                                zxr10ACLv6MixRuleRouting,
                                zxr10ACLv6MixRuleAuthen,
                                zxr10ACLv6MixRuleDestops,
                                zxr10ACLv6MixRuleFragments,
                                zxr10ACLv6MixRuleHopByHop,
                                zxr10ACLv6MixRuleEsp,
                                zxr10ACLv6MixRuleDSCP, 
                                zxr10ACLv6MixRuleTc,
                                zxr10ACLv6MixRuleTimerangeName,
                                zxr10ACLv6MixRuleBSrcMACRange1,
                                zxr10ACLv6MixRuleSrcMACRg1Min,
                                zxr10ACLv6MixRuleSrcMACRg1Max,  
                                zxr10ACLv6MixRuleBSrcMACRange2,
                                zxr10ACLv6MixRuleSrcMACRg2Min,
                                zxr10ACLv6MixRuleSrcMACRg2Max,  
                                zxr10ACLv6MixRuleBDestMACRange1,
                                zxr10ACLv6MixRuleDestMACRg1Min,
                                zxr10ACLv6MixRuleDestMACRg1Max,  
                                zxr10ACLv6MixRuleBDestMACRange2,
                                zxr10ACLv6MixRuleDestMACRg2Min,
                                zxr10ACLv6MixRuleDestMACRg2Max,
                                zxr10ACLv6MixRuleSrcAddrMaskFlag,
                                zxr10ACLv6MixRuleSrcWildcardBits,
                                zxr10ACLv6MixRuleDstAddrMaskFlag,
                                zxr10ACLv6MixRuleDstWildcardBits
                                zxr10ACLv6MixRuleDsap,
                                zxr10ACLv6MixRuleSsap
        3. rule type : udp type
            effective leaf nodes:zxr10ACLv6MixRuleAclName,
                                zxr10ACLv6MixRuleRuleID,
                                zxr10ACLv6MixRulePermitDeny,
                                zxr10ACLv6MixRuleLinkProtocol,
                                zxr10ACLv6MixRuleSrcMAC, 
                                zxr10ACLv6MixRuleSrcMACWildcard,
                                zxr10ACLv6MixRuleDestMAC,
                                zxr10ACLv6MixRuleDestMACWildcard,
                                zxr10ACLv6MixRuleIncos,
                                zxr10ACLv6MixRuleOutCos,
                                zxr10ACLv6MixRuleInVlanID,
                                zxr10ACLv6MixRuleOutVlanID,
                                zxr10ACLv6MixRuleInVlanRange,
                                zxr10ACLv6MixRuleOutVlanRange,
                                zxr10ACLv6MixRuleFlowlabel,  
                                zxr10ACLv6MixRuleSrcAddr, 
                                zxr10ACLv6MixRuleSrcWildcard,
                                zxr10ACLv6MixRuleDestAddr,
                                zxr10ACLv6MixRuleDestWildcard,
                                zxr10ACLv6MixRuleIpProtocol,
                                zxr10ACLv6MixRuleSrcPortOpr,
                                zxr10ACLv6MixRuleSrcPortValue,
                                zxr10ACLv6MixRuleSrcPortRange,
                                zxr10ACLv6MixRuleDestPortOpr,
                                zxr10ACLv6MixRuleDestPortValue,
                                zxr10ACLv6MixRuleDestPortRange,
                                zxr10ACLv6MixRuleRouting,
                                zxr10ACLv6MixRuleAuthen,
                                zxr10ACLv6MixRuleDestops,
                                zxr10ACLv6MixRuleFragments,
                                zxr10ACLv6MixRuleHopByHop,
                                zxr10ACLv6MixRuleEsp,
                                zxr10ACLv6MixRuleDSCP,
                                zxr10ACLv6MixRuleTc,
                                zxr10ACLv6MixRuleTimerangeName,
                                zxr10ACLv6MixRuleBSrcMACRange1,
                                zxr10ACLv6MixRuleSrcMACRg1Min,
                                zxr10ACLv6MixRuleSrcMACRg1Max,  
                                zxr10ACLv6MixRuleBSrcMACRange2,
                                zxr10ACLv6MixRuleSrcMACRg2Min,
                                zxr10ACLv6MixRuleSrcMACRg2Max,  
                                zxr10ACLv6MixRuleBDestMACRange1,
                                zxr10ACLv6MixRuleDestMACRg1Min,
                                zxr10ACLv6MixRuleDestMACRg1Max,  
                                zxr10ACLv6MixRuleBDestMACRange2,
                                zxr10ACLv6MixRuleDestMACRg2Min,
                                zxr10ACLv6MixRuleDestMACRg2Max,
                                zxr10ACLv6MixRuleLinkProtocolEx,
                                zxr10ACLv6MixRuleSrcAddrMaskFlag,
                                zxr10ACLv6MixRuleSrcWildcardBits,
                                zxr10ACLv6MixRuleDstAddrMaskFlag,
                                zxr10ACLv6MixRuleDstWildcardBits
                                zxr10ACLv6MixRuleDsap,
                                zxr10ACLv6MixRuleSsap
        4. rule type : icmp type
            effective leaf nodes:zxr10ACLv6MixRuleAclName,
                                zxr10ACLv6MixRuleRuleID,
                                zxr10ACLv6MixRulePermitDeny,
                                zxr10ACLv6MixRuleLinkProtocol,
                                zxr10ACLv6MixRuleSrcMAC, 
                                zxr10ACLv6MixRuleSrcMACWildcard,
                                zxr10ACLv6MixRuleDestMAC,
                                zxr10ACLv6MixRuleDestMACWildcard,
                                zxr10ACLv6MixRuleIncos,
                                zxr10ACLv6MixRuleOutCos,
                                zxr10ACLv6MixRuleInVlanID,
                                zxr10ACLv6MixRuleOutVlanID,
                                zxr10ACLv6MixRuleInVlanRange,
                                zxr10ACLv6MixRuleOutVlanRange,
                                zxr10ACLv6MixRuleFlowlabel,
                                zxr10ACLv6MixRuleSrcAddr,
                                zxr10ACLv6MixRuleSrcWildcard,
                                zxr10ACLv6MixRuleDestAddr,
                                zxr10ACLv6MixRuleDestWildcard,
                                zxr10ACLv6MixRuleIpProtocol,
                                zxr10ACLv6MixRuleICMPType,
                                zxr10ACLv6MixRuleICMPCode,
                                zxr10ACLv6MixRuleRouting,
                                zxr10ACLv6MixRuleAuthen,
                                zxr10ACLv6MixRuleDestops,
                                zxr10ACLv6MixRuleFragments,
                                zxr10ACLv6MixRuleHopByHop,
                                zxr10ACLv6MixRuleEsp,
                                zxr10ACLv6MixRuleDSCP, 
                                zxr10ACLv6MixRuleTc,
                                zxr10ACLv6MixRuleTimerangeName,
                                zxr10ACLv6MixRuleBSrcMACRange1,
                                zxr10ACLv6MixRuleSrcMACRg1Min,
                                zxr10ACLv6MixRuleSrcMACRg1Max,  
                                zxr10ACLv6MixRuleBSrcMACRange2,
                                zxr10ACLv6MixRuleSrcMACRg2Min,
                                zxr10ACLv6MixRuleSrcMACRg2Max,  
                                zxr10ACLv6MixRuleBDestMACRange1,
                                zxr10ACLv6MixRuleDestMACRg1Min,
                                zxr10ACLv6MixRuleDestMACRg1Max,  
                                zxr10ACLv6MixRuleBDestMACRange2,
                                zxr10ACLv6MixRuleDestMACRg2Min,
                                zxr10ACLv6MixRuleDestMACRg2Max,
                                zxr10ACLv6MixRuleLinkProtocolEx,
                                zxr10ACLv6MixRuleSrcAddrMaskFlag,
                                zxr10ACLv6MixRuleSrcWildcardBits,
                                zxr10ACLv6MixRuleDstAddrMaskFlag,
                                zxr10ACLv6MixRuleDstWildcardBits
                                zxr10ACLv6MixRuleDsap,
                                zxr10ACLv6MixRuleSsap
        conflict leaf nodes:
        1. zxr10ACLv6MixRuleFragments conflicts with 
                                zxr10ACLv6MixRuleSrcPortOpr,
                                zxr10ACLv6MixRuleSrcPortValue,
                                zxr10ACLv6MixRuleSrcPortRange,
                                zxr10ACLv6MixRuleDestPortOpr,
                                zxr10ACLv6MixRuleDestPortValue,
                                zxr10ACLv6MixRuleDestPortRange,
                                zxr10ACLv6MixRuleTCPEstablish,
                                zxr10ACLv6MixRuleICMPType,
                                zxr10ACLv6MixRuleICMPCode,
                                zxr10ACLv6MixRuleRstFlag,
                                zxr10ACLv6MixRuleAckFlag,
                                zxr10ACLv6MixRuleFinFlag,
                                zxr10ACLv6MixRuleSynFlag,
                                zxr10ACLv6MixRulePshFlag,
                                zxr10ACLv6MixRuleUrgFlag 
         2. zxr10ACLv6MixRuleDSCP conflicts with 
                                zxr10ACLv6MixRuleTc
         3. zxr10ACLv6MixRuleTCPEstablish conflicts with
                                zxr10ACLv6MixRuleRstFlag, 
                                zxr10ACLv6MixRuleAckFlag
         3. zxr10ACLv6MixRuleLinkProtocolEx conflicts with
                                zxr10ACLv6MixRuleDsap,
                                zxr10ACLv6MixRuleSsap
                                "
    INDEX  { zxr10ACLv6MixRuleAclName,
             zxr10ACLv6MixRuleRuleID }
    ::= { zxr10ACLv6MixRuleTable 1 }
    
Zxr10ACLv6MixRuleEntry ::=SEQUENCE {
        zxr10ACLv6MixRuleAclName               DisplayString,
        zxr10ACLv6MixRuleRuleID                Integer32,
        zxr10ACLv6MixRulePermitDeny            AclPermitDeny,
        zxr10ACLv6MixRuleLinkProtocol          Integer32,
        zxr10ACLv6MixRuleSrcMAC                MacAddress,
        zxr10ACLv6MixRuleSrcMACWildcard        MacAddress,
        zxr10ACLv6MixRuleDestMAC               MacAddress,
        zxr10ACLv6MixRuleDestMACWildcard       MacAddress,
        zxr10ACLv6MixRuleIncos                 Integer32,
        zxr10ACLv6MixRuleOutCos                Integer32,
        zxr10ACLv6MixRuleInVlanID              Integer32,
        zxr10ACLv6MixRuleOutVlanID             Integer32,
        zxr10ACLv6MixRuleInVlanRange           DisplayString,
        zxr10ACLv6MixRuleOutVlanRange          DisplayString,
        zxr10ACLv6MixRuleFlowlabel             Integer32,
        zxr10ACLv6MixRuleSrcAddr               DisplayString,
        zxr10ACLv6MixRuleSrcWildcard           INTEGER,
        zxr10ACLv6MixRuleDestAddr              DisplayString,
        zxr10ACLv6MixRuleDestWildcard          INTEGER,
        zxr10ACLv6MixRuleIpProtocol            INTEGER,
        zxr10ACLv6MixRuleSrcPortOpr            INTEGER,
        zxr10ACLv6MixRuleSrcPortValue          INTEGER,
        zxr10ACLv6MixRuleSrcPortRange          DisplayString,
        zxr10ACLv6MixRuleDestPortOpr           INTEGER,
        zxr10ACLv6MixRuleDestPortValue         INTEGER,
        zxr10ACLv6MixRuleDestPortRange         DisplayString,
        zxr10ACLv6MixRuleTCPEstablish          AclValidOrNot,
        zxr10ACLv6MixRuleRstFlag               AclTcpFlagType,
        zxr10ACLv6MixRuleAckFlag               AclTcpFlagType,
        zxr10ACLv6MixRuleFinFlag               AclTcpFlagType,
        zxr10ACLv6MixRuleSynFlag               AclTcpFlagType,
        zxr10ACLv6MixRulePshFlag               AclTcpFlagType,
        zxr10ACLv6MixRuleUrgFlag               AclTcpFlagType,
        zxr10ACLv6MixRuleICMPType              INTEGER,
        zxr10ACLv6MixRuleICMPCode              INTEGER,
        zxr10ACLv6MixRuleRouting               AclValidOrNot,
        zxr10ACLv6MixRuleAuthen                AclValidOrNot,
        zxr10ACLv6MixRuleDestops               AclValidOrNot,
        zxr10ACLv6MixRuleFragments             AclValidOrNot,
        zxr10ACLv6MixRuleHopByHop              AclValidOrNot,
        zxr10ACLv6MixRuleEsp                   AclValidOrNot,
        zxr10ACLv6MixRuleDSCP                  Integer32,
        zxr10ACLv6MixRuleTc                    Integer32,
        zxr10ACLv6MixRuleTimerangeName         DisplayString,
        zxr10ACLv6MixRuleBSrcMACRange1         AclValidOrNot,
        zxr10ACLv6MixRuleSrcMACRg1Min          MacAddress,
        zxr10ACLv6MixRuleSrcMACRg1Max          MacAddress,  
        zxr10ACLv6MixRuleBSrcMACRange2         AclValidOrNot,
        zxr10ACLv6MixRuleSrcMACRg2Min          MacAddress,
        zxr10ACLv6MixRuleSrcMACRg2Max          MacAddress,  
        zxr10ACLv6MixRuleBDestMACRange1        AclValidOrNot,
        zxr10ACLv6MixRuleDestMACRg1Min         MacAddress,
        zxr10ACLv6MixRuleDestMACRg1Max         MacAddress,  
        zxr10ACLv6MixRuleBDestMACRange2        AclValidOrNot,
        zxr10ACLv6MixRuleDestMACRg2Min         MacAddress,
        zxr10ACLv6MixRuleDestMACRg2Max         MacAddress,
        zxr10ACLv6MixRuleLinkProtocolEx        Integer32,
        zxr10ACLv6MixRuleSrcAddrMaskFlag       AclValidOrNot,
        zxr10ACLv6MixRuleSrcWildcardBits       Ipv6Address,
        zxr10ACLv6MixRuleDstAddrMaskFlag       AclValidOrNot,
        zxr10ACLv6MixRuleDstWildcardBits       Ipv6Address,
        zxr10ACLv6MixRuleDsap                  Integer32,
        zxr10ACLv6MixRuleSsap                  Integer32
     } 

zxr10ACLv6MixRuleAclName  OBJECT-TYPE
    SYNTAX   DisplayString(SIZE(1..31))
    MAX-ACCESS  not-accessible
    STATUS  current
    DESCRIPTION
        "Name of an IPv6 Mixed access-list (1-31 characters)"
    ::= { zxr10ACLv6MixRuleEntry 1 } 
        
zxr10ACLv6MixRuleRuleID  OBJECT-TYPE
    SYNTAX   Integer32(1..2147483644)
    MAX-ACCESS  not-accessible
    STATUS  current
    DESCRIPTION
        "ID of this rule"
    ::= { zxr10ACLv6MixRuleEntry 2 }

zxr10ACLv6MixRulePermitDeny  OBJECT-TYPE
    SYNTAX   AclPermitDeny
    MAX-ACCESS  read-only
    STATUS  current
    DESCRIPTION
        "deny  :  Specify packets to reject
         permit:  Specify packets to forward"
    ::= { zxr10ACLv6MixRuleEntry 3 }

zxr10ACLv6MixRuleLinkProtocol  OBJECT-TYPE
    SYNTAX   Integer32(0..65536)   
    MAX-ACCESS  read-only
    STATUS  obsolete
    DESCRIPTION
        "Link protocal:
         <0-65535>  valid value
         65536      invalid value
         This is an optional node."
    ::= { zxr10ACLv6MixRuleEntry 4 } 

zxr10ACLv6MixRuleSrcMAC  OBJECT-TYPE
    SYNTAX   MacAddress
    MAX-ACCESS  read-only
    STATUS  current
    DESCRIPTION
        "<xxxx.xxxx.xxxx>  Source MAC address"
    ::= { zxr10ACLv6MixRuleEntry 5 }

zxr10ACLv6MixRuleSrcMACWildcard  OBJECT-TYPE
    SYNTAX   MacAddress
    MAX-ACCESS  read-only
    STATUS  current
    DESCRIPTION
        "<xxxx.xxxx.xxxx>  Source MAC wildcard"
    ::= { zxr10ACLv6MixRuleEntry 6 } 

zxr10ACLv6MixRuleDestMAC  OBJECT-TYPE
    SYNTAX   MacAddress
    MAX-ACCESS  read-only
    STATUS  current
    DESCRIPTION
        "<xxxx.xxxx.xxxx>  Destination MAC address"
    ::= { zxr10ACLv6MixRuleEntry 7 } 
    
zxr10ACLv6MixRuleDestMACWildcard  OBJECT-TYPE
    SYNTAX   MacAddress
    MAX-ACCESS  read-only
    STATUS  current
    DESCRIPTION
        "<xxxx.xxxx.xxxx>  Destination MAC wildcard"
    ::= { zxr10ACLv6MixRuleEntry 8 } 
 
zxr10ACLv6MixRuleIncos     OBJECT-TYPE
    SYNTAX   Integer32(0..7|255)
    MAX-ACCESS  read-only
    STATUS  current
    DESCRIPTION
        "Value of inner cos:
         <0-7>  valid value
         255    invalid value
         This is an optional node."
    ::= { zxr10ACLv6MixRuleEntry 9 }     
    
zxr10ACLv6MixRuleOutCos   OBJECT-TYPE
    SYNTAX   Integer32(0..7|255)
    MAX-ACCESS  read-only
    STATUS  current
    DESCRIPTION
        "Value of outer cos:
         <0-7>  valid value
         255    invalid value
         This is an optional node."
    ::= { zxr10ACLv6MixRuleEntry 10 }

zxr10ACLv6MixRuleInVlanID  OBJECT-TYPE
    SYNTAX   Integer32(1..4094|65535)
    MAX-ACCESS  read-only
    STATUS  current
    DESCRIPTION
        "Value of inner vlan
         <1-4094>   valid value
         65535      invalid value
         This is an optional node."
    ::= { zxr10ACLv6MixRuleEntry 11 }
    
zxr10ACLv6MixRuleOutVlanID  OBJECT-TYPE
    SYNTAX   Integer32(1..4094|65535)
    MAX-ACCESS  read-only
    STATUS  current
    DESCRIPTION
        "Value of outer vlan
         <1-4094>   valid value
         65535      invalid value
         This is an optional node."
    ::= { zxr10ACLv6MixRuleEntry 12 }
    
zxr10ACLv6MixRuleInVlanRange  OBJECT-TYPE
    SYNTAX   DisplayString
    MAX-ACCESS  read-only
    STATUS  current
    DESCRIPTION
        "Range of inner vlan
         <1-4094>-<1-4094>    valid value
         0                    invalid value
         This is an optional node."
    ::= { zxr10ACLv6MixRuleEntry 13 } 
    
zxr10ACLv6MixRuleOutVlanRange   OBJECT-TYPE
    SYNTAX   DisplayString
    MAX-ACCESS  read-only
    STATUS  current
    DESCRIPTION
        "Range of outer vlan
         <1-4094>-<1-4094>    valid value
         0                    invalid value
         This is an optional node."
    ::= { zxr10ACLv6MixRuleEntry 14 }

zxr10ACLv6MixRuleFlowlabel  OBJECT-TYPE
    SYNTAX   Integer32(0..1048575|2147483647)
    MAX-ACCESS  read-only
    STATUS  current
    DESCRIPTION
        "Flowlabel value:
         <0-1048575>  valid value
         2147483647   invalid value
         This is an optional node."
    ::= { zxr10ACLv6MixRuleEntry 15 }   

zxr10ACLv6MixRuleSrcAddr  OBJECT-TYPE
    SYNTAX   DisplayString
    MAX-ACCESS  read-only
    STATUS  current
    DESCRIPTION
        "X:X::X:X  Source address"
    ::= { zxr10ACLv6MixRuleEntry 16 } 

zxr10ACLv6MixRuleSrcWildcard  OBJECT-TYPE
    SYNTAX   INTEGER(0..128)
    MAX-ACCESS  read-only
    STATUS  current
    DESCRIPTION
        "<0-128>  Source Wildcard"
    ::= { zxr10ACLv6MixRuleEntry 17 }    
    
zxr10ACLv6MixRuleDestAddr  OBJECT-TYPE
    SYNTAX   DisplayString
    MAX-ACCESS  read-only
    STATUS  current
    DESCRIPTION
        "X:X::X:X  Destination address"
    ::= { zxr10ACLv6MixRuleEntry 18 } 
    
zxr10ACLv6MixRuleDestWildcard  OBJECT-TYPE
    SYNTAX   INTEGER(0..128)
    MAX-ACCESS  read-only
    STATUS  current
    DESCRIPTION
        "<0-128>  Destination Wildcard"
    ::= { zxr10ACLv6MixRuleEntry 19 }

zxr10ACLv6MixRuleIpProtocol  OBJECT-TYPE
    SYNTAX   INTEGER{igmp(2),tcp(6),udp(17),gre(47),icmp(58),ospf(89),
             pim(103),vrrp(112),sctp(132),ip(65535)}
    MAX-ACCESS  read-only
    STATUS  current
    DESCRIPTION
        " <0-255>  An IP protocol number
          gre      Generic Routing Encapsulation (47)
          icmp     Internet Control Message Protocol (58)
          igmp     Internet Group Management Protocol (2)
          ip       Any internet protocol (65535) 
          ospf     Open Shortest Path First Protocol (89)
          pim      Protocol Independent Multicast (103)
          tcp      Transmission Control Protocol (6)
          udp      User Datagram Protocol (17)
          sctp     Stream Control Transmission Protocol (132)
          vrrp     Virtual Router Redundancy Protocol (112)"
    ::= { zxr10ACLv6MixRuleEntry 20 }
                 
zxr10ACLv6MixRuleSrcPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number
         le       Match only packets with a no greater port number
         range    Match only packet on a given port range
         65535    invalid value
 
        Needn't care for zxr10ACLv6MixRuleSrcPortValue and 
        zxr10ACLv6MixRuleSrcPortRange When the value of 
        zxr10ACLv6MixRuleSrcPortOpr is invalid(65535).
        Check zxr10ACLv6MixRuleSrcPortValue when the value 
        zxr10ACLv6MixRuleSrcPortOpr is eq(1),ge(2) or le(3).
        Check zxr10ACLv6MixRuleSrcPortRange only when the value 
        of zxr10ACLv6MixRuleSrcPortOpr is range(7)."
    ::= { zxr10ACLv6MixRuleEntry 21 }    
    
zxr10ACLv6MixRuleSrcPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number 
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv6MixRuleSrcPortOpr is 
        eq(1),ge(2) or le(3)."
    ::= { zxr10ACLv6MixRuleEntry 22 }    
    
zxr10ACLv6MixRuleSrcPortRange  OBJECT-TYPE
    SYNTAX   DisplayString
    MAX-ACCESS  read-only
    STATUS  current
    DESCRIPTION
        "Port range:  <0-65535>-<0-65535>
        Check zxr10ACLv6MixRuleSrcPortRange only when the value of 
        zxr10ACLv6MixRuleSrcPortOpr is range(7)."
    ::= { zxr10ACLv6MixRuleEntry 23 }    
    
zxr10ACLv6MixRuleDestPortOpr  OBJECT-TYPE
    SYNTAX   INTEGER{oprTypeInvalid(65535),eq(1),ge(2),le(3),range(7)}
    MAX-ACCESS  read-only
    STATUS  current
    DESCRIPTION
        "This is an optional node.
         eq       Match only packets on a given port number
         ge       Match only packets with a no lower port number 
         le       Match only packets with a no greater port number
         range    Match only packet on a given port range
         65535    invalid value
 
        Needn't care for zxr10ACLv6MixRuleDestPortValue and 
        zxr10ACLv6MixRuleDestPortRange When the value of 
        zxr10ACLv6MixRuleDestPortOpr is invalid(65535).
        Check zxr10ACLv6MixRuleDestPortValue when the value 
        zxr10ACLv6MixRuleDestPortOpr is eq(1),ge(2) or le(3).
        Check zxr10ACLv6MixRuleDestPortRange only when the value of 
        zxr10ACLv6MixRuleDestPortOpr is range(7)."
    ::= { zxr10ACLv6MixRuleEntry 24 }
    
zxr10ACLv6MixRuleDestPortValue  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-only
    STATUS  current
    DESCRIPTION
        "<0-65535>   Port number 
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)

        Check this node when the value of zxr10ACLv6MixRuleDestPortOpr is 
        eq(1),ge(2) or le(3)."
    ::= { zxr10ACLv6MixRuleEntry 25 }    
    
zxr10ACLv6MixRuleDestPortRange  OBJECT-TYPE
    SYNTAX   DisplayString
    MAX-ACCESS  read-only
    STATUS  current
    DESCRIPTION
        "Port range:  <0-65535>-<0-65535>
        Check zxr10ACLv6MixRuleDestPortRange only when the value of 
        zxr10ACLv6MixRuleDestPortOpr is range(7)."
    ::= { zxr10ACLv6MixRuleEntry 26 }   
     
zxr10ACLv6MixRuleTCPEstablish  OBJECT-TYPE
    SYNTAX    AclValidOrNot
    MAX-ACCESS  read-only
    STATUS  current
    DESCRIPTION
        "Match established connections.
         This is an optional node."
    DEFVAL    {2} 
    ::= { zxr10ACLv6MixRuleEntry 27 }  
    
zxr10ACLv6MixRuleRstFlag  OBJECT-TYPE
    SYNTAX   AclTcpFlagType
    MAX-ACCESS  read-only
    STATUS  current
    DESCRIPTION
        "Match when the RST flag set or not.
         This is an optional node.
         invalid value:     (65535)"
    ::= { zxr10ACLv6MixRuleEntry 28 }
    
zxr10ACLv6MixRuleAckFlag  OBJECT-TYPE
    SYNTAX   AclTcpFlagType
    MAX-ACCESS  read-only
    STATUS  current
    DESCRIPTION
        "Match when the ACK flag set or not.
         This is an optional node.
         invalid value:     (65535)"
    ::= { zxr10ACLv6MixRuleEntry 29 }

zxr10ACLv6MixRuleFinFlag  OBJECT-TYPE
    SYNTAX   AclTcpFlagType
    MAX-ACCESS  read-only
    STATUS  current
    DESCRIPTION
        "Match when the FIN flag set or not.
         This is an optional node.
         invalid value:     (65535)"
    ::= { zxr10ACLv6MixRuleEntry 30 }

zxr10ACLv6MixRuleSynFlag  OBJECT-TYPE
    SYNTAX   AclTcpFlagType
    MAX-ACCESS  read-only
    STATUS  current
    DESCRIPTION
        "Match when the SYN flag set or not.
         This is an optional node.
         invalid value:     (65535)"
    ::= { zxr10ACLv6MixRuleEntry 31 }     
    
zxr10ACLv6MixRulePshFlag  OBJECT-TYPE
    SYNTAX   AclTcpFlagType
    MAX-ACCESS  read-only
    STATUS  current
    DESCRIPTION
        "Match when the PSH flag set or not.
         This is an optional node.
         invalid value:     (65535)"
    ::= { zxr10ACLv6MixRuleEntry 32 }

zxr10ACLv6MixRuleUrgFlag  OBJECT-TYPE
    SYNTAX   AclTcpFlagType
    MAX-ACCESS  read-only
    STATUS  current
    DESCRIPTION
        "Match when the URG flag set or not.
         This is an optional node.
         invalid value:     (65535)"
    ::= { zxr10ACLv6MixRuleEntry 33 }    
    
zxr10ACLv6MixRuleICMPType  OBJECT-TYPE
    SYNTAX   INTEGER{destination-unreachable(1),packet-too-big(2),
             time-exceeded(3),parameter-problem(4),echo-request(128),
             echo-reply(129),mld-query(130),mld-report(131),
             router-solicitation(133),router-advertisment(134),nd-ns(135),
             nd-na(136),redirect(137),router-renumbering(138),invalid(65535)}
    MAX-ACCESS  read-only
    STATUS  current
    DESCRIPTION
        "ICMP type:
        <0-255>               valid value
        65535                 invalid value
        specific value:
        destination-unreachable  Destination unreachable (1)
        echo-reply               Echo reply (129)
        echo-request             Echo request (ping, 128)
        mld-query                Multicast Listener Discovery Query (130)
        mld-reduction            Multicast Listener Discovery Reduction(132)
        mld-report               Multicast Listener Discovery Report(131)
        nd-na                    Neighbor discovery neighbor advertisments(136)
        nd-ns                    Neighbor discovery neighbor solicitations(135)
        packet-too-big           Packet too big (2)
        parameter-problem        All parameter problems (4)
        redirect                 Neighbor redirect (137)
        router-advertisment      Neighbor discovery router advertisments(134)
        router-renumbering       All router renumbering (138)
        router-solicitation      Neighbor discovery router solicitations(133)
        time-exceeded            Time exceeded (3)

        This is an optional node." 
    ::= { zxr10ACLv6MixRuleEntry 34 }    
    
zxr10ACLv6MixRuleICMPCode  OBJECT-TYPE
    SYNTAX   INTEGER(0..255|65535)
    MAX-ACCESS  read-only
    STATUS  current
    DESCRIPTION
        "ICMP code:
         <0-255>      valid value
         65535        invalid value
         This is an optional node."
    ::= { zxr10ACLv6MixRuleEntry 35 } 
          
zxr10ACLv6MixRuleRouting  OBJECT-TYPE
    SYNTAX   AclValidOrNot
    MAX-ACCESS  read-only
    STATUS  current
    DESCRIPTION
        "Match if the specify IPv6 header is present.
         This is an optional node."
    DEFVAL    {2} 
    ::= { zxr10ACLv6MixRuleEntry 36 }

zxr10ACLv6MixRuleAuthen  OBJECT-TYPE
    SYNTAX   AclValidOrNot
    MAX-ACCESS  read-only
    STATUS  current
    DESCRIPTION
        "Match if the specify IPv6 header is present.
         This is an optional node."
    DEFVAL    {2} 
    ::= { zxr10ACLv6MixRuleEntry 37 }
 
zxr10ACLv6MixRuleDestops  OBJECT-TYPE
    SYNTAX   AclValidOrNot
    MAX-ACCESS  read-only
    STATUS  current
    DESCRIPTION
        "Match if the specify IPv6 header is present.
         This is an optional node."
    DEFVAL    {2} 
    ::= { zxr10ACLv6MixRuleEntry 38 }
     
zxr10ACLv6MixRuleFragments  OBJECT-TYPE
    SYNTAX   AclValidOrNot
    MAX-ACCESS  read-only
    STATUS  current
    DESCRIPTION
        "Match if the specify IPv6 header is present.
         This is an optional node."
    DEFVAL    {2} 
    ::= { zxr10ACLv6MixRuleEntry 39 }
    
zxr10ACLv6MixRuleHopByHop  OBJECT-TYPE
    SYNTAX   AclValidOrNot
    MAX-ACCESS  read-only
    STATUS  current
    DESCRIPTION
        "Match if the specify IPv6 header is present.
         This is an optional node."
    DEFVAL    {2} 
    ::= { zxr10ACLv6MixRuleEntry 40 }
    
zxr10ACLv6MixRuleEsp  OBJECT-TYPE
    SYNTAX   AclValidOrNot
    MAX-ACCESS  read-only
    STATUS  current
    DESCRIPTION
        "Match if the specify IPv6 header is present.
         This is an optional node."
    DEFVAL    {2} 
    ::= { zxr10ACLv6MixRuleEntry 41 }
         
zxr10ACLv6MixRuleDSCP  OBJECT-TYPE
    SYNTAX   Integer32(0..63|255)
    MAX-ACCESS  read-only
    STATUS  current
    DESCRIPTION
        "DSCP value:
         <0-63>  valid value
         255     invalid value
         This is an optional node."
    ::= { zxr10ACLv6MixRuleEntry 42 }

zxr10ACLv6MixRuleTc  OBJECT-TYPE    
    SYNTAX   Integer32(0..255|65535)
    MAX-ACCESS  read-only
    STATUS  current
    DESCRIPTION
        "Traffic Class value:
         <0-255>  valid value
         65535    invalid value
         This is an optional node."
    ::= { zxr10ACLv6MixRuleEntry 43 }
        
zxr10ACLv6MixRuleTimerangeName  OBJECT-TYPE
    SYNTAX   DisplayString(SIZE(0..31))
    MAX-ACCESS  read-only
    STATUS  current
    DESCRIPTION
        "Time range name (1-31 characters).
         This is an optional node."
    ::= { zxr10ACLv6MixRuleEntry 44 }  

zxr10ACLv6MixRuleBSrcMACRange1  OBJECT-TYPE
    SYNTAX   AclValidOrNot   
    MAX-ACCESS  read-only
    STATUS  current
    DESCRIPTION
        "Match if source MAC address range is configured.
        When this is valid, zxr10ACLv6MixRuleSrcMAC and 
        zxr10ACLv6MixRuleSrcMACWildcard are invalid,
        zxr10ACLv6MixRuleSrcMACRg1Min and 
        zxr10ACLv6MixRuleSrcMACRg1Max are valid."
    DEFVAL    {2} 
    ::= { zxr10ACLv6MixRuleEntry 45 } 

zxr10ACLv6MixRuleSrcMACRg1Min  OBJECT-TYPE
    SYNTAX   MacAddress
    MAX-ACCESS  read-only
    STATUS  current
    DESCRIPTION
        "<xxxx.xxxx.xxxx>  
        Lower limit of first source MAC address range"
    ::= { zxr10ACLv6MixRuleEntry 46 }

zxr10ACLv6MixRuleSrcMACRg1Max  OBJECT-TYPE
    SYNTAX   MacAddress
    MAX-ACCESS  read-only
    STATUS  current
    DESCRIPTION
        "<xxxx.xxxx.xxxx>  
        Upper limit of first source MAC address range"
    ::= { zxr10ACLv6MixRuleEntry 47 } 

zxr10ACLv6MixRuleBSrcMACRange2  OBJECT-TYPE
    SYNTAX   AclValidOrNot   
    MAX-ACCESS  read-only
    STATUS  current
    DESCRIPTION
        "Match if second source MAC address range is configured.
        When this is valid, zxr10ACLv6MixRuleSrcMAC and 
        zxr10ACLv6MixRuleSrcMACWildcard are invalid,
        zxr10ACLv6MixRuleSrcMACRg2Min and 
        zxr10ACLv6MixRuleSrcMACRg2Max are valid."
    DEFVAL    {2} 
    ::= { zxr10ACLv6MixRuleEntry 48 } 

zxr10ACLv6MixRuleSrcMACRg2Min  OBJECT-TYPE
    SYNTAX   MacAddress
    MAX-ACCESS  read-only
    STATUS  current
    DESCRIPTION
        "<xxxx.xxxx.xxxx>
        Lower limit of second source MAC address range"
    ::= { zxr10ACLv6MixRuleEntry 49 }

zxr10ACLv6MixRuleSrcMACRg2Max  OBJECT-TYPE
    SYNTAX   MacAddress
    MAX-ACCESS  read-only
    STATUS  current
    DESCRIPTION
        "<xxxx.xxxx.xxxx>  
        Upper limit of second source MAC address range"
    ::= { zxr10ACLv6MixRuleEntry 50 } 

zxr10ACLv6MixRuleBDestMACRange1  OBJECT-TYPE
    SYNTAX   AclValidOrNot   
    MAX-ACCESS  read-only
    STATUS  current
    DESCRIPTION
        "Match if destination MAC address range is configured.
        When this is valid, zxr10ACLv6MixRuleDestMAC and 
        zxr10ACLv6MixRuleDestMACWildcard are invalid,
        zxr10ACLv6MixRuleDestMACRg1Min and
        zxr10ACLv6MixRuleDestMACRg1Max are valid."
    DEFVAL    {2} 
    ::= { zxr10ACLv6MixRuleEntry 51 } 

zxr10ACLv6MixRuleDestMACRg1Min  OBJECT-TYPE
    SYNTAX   MacAddress
    MAX-ACCESS  read-only
    STATUS  current
    DESCRIPTION
        "<xxxx.xxxx.xxxx>  
        Lower limit of first destination MAC address range"
    ::= { zxr10ACLv6MixRuleEntry 52 }

zxr10ACLv6MixRuleDestMACRg1Max  OBJECT-TYPE
    SYNTAX   MacAddress
    MAX-ACCESS  read-only
    STATUS  current
    DESCRIPTION
        "<xxxx.xxxx.xxxx>  
        Upper limit of first destination MAC address range"
    ::= { zxr10ACLv6MixRuleEntry 53 } 

zxr10ACLv6MixRuleBDestMACRange2  OBJECT-TYPE
    SYNTAX   AclValidOrNot   
    MAX-ACCESS  read-only
    STATUS  current
    DESCRIPTION
        "Match if second destination MAC address range is configured.
        When this is valid, zxr10ACLv6MixRuleDestMAC and 
        zxr10ACLv6MixRuleDestMACWildcard are invalid,
        zxr10ACLv6MixRuleDestMACRg2Min and 
        zxr10ACLv6MixRuleDestMACRg2Max are valid."
    DEFVAL    {2} 
    ::= { zxr10ACLv6MixRuleEntry 54 } 

zxr10ACLv6MixRuleDestMACRg2Min  OBJECT-TYPE
    SYNTAX   MacAddress
    MAX-ACCESS  read-only
    STATUS  current
    DESCRIPTION
        "<xxxx.xxxx.xxxx>
        Lower limit of second destination MAC address range"
    ::= { zxr10ACLv6MixRuleEntry 55 }

zxr10ACLv6MixRuleDestMACRg2Max  OBJECT-TYPE
    SYNTAX   MacAddress
    MAX-ACCESS  read-only
    STATUS  current
    DESCRIPTION
        "<xxxx.xxxx.xxxx>  
        Upper limit of second destination MAC address range"
    ::= { zxr10ACLv6MixRuleEntry 56 } 

zxr10ACLv6MixRuleLinkProtocolEx  OBJECT-TYPE
    SYNTAX   Integer32(1536..65536)   
    MAX-ACCESS  read-only
    STATUS  current
    DESCRIPTION
        "Link protocal:
         <1536-65535>  valid value
         65536         invalid value
         This is an optional node."
    ::= { zxr10ACLv6MixRuleEntry 57 }
    
zxr10ACLv6MixRuleSrcAddrMaskFlag  OBJECT-TYPE
    SYNTAX    AclValidOrNot
    MAX-ACCESS  read-only
    STATUS  current
    DESCRIPTION
        "This flag indicates the way of configuring IPv6 source address mask,
        such as zxr10ACLv6MixRuleSrcWildcard, zxr10ACLv6MixRuleSrcWildcardBits.
        If this flag is valid, IPv6 source address mask is configured by 
        wildcard bits, (e.g. X:X::X:X) and zxr10ACLv6MixRuleSrcWildcardBits 
        is valid;
        if not, IPv6 source address mask is configured by prefix length,
        (e.g. X:X::X:X/0-128) and zxr10ACLv6MixRuleSrcWildcard is valid."
    DEFVAL    {2}  
    ::= { zxr10ACLv6MixRuleEntry 58 }
    
zxr10ACLv6MixRuleSrcWildcardBits  OBJECT-TYPE
    SYNTAX   Ipv6Address
    MAX-ACCESS  read-only
    STATUS  current
    DESCRIPTION
        "<X:X::X:X>   Source address wildcard bits"
    ::= { zxr10ACLv6MixRuleEntry 59 } 
    
zxr10ACLv6MixRuleDstAddrMaskFlag  OBJECT-TYPE
    SYNTAX    AclValidOrNot
    MAX-ACCESS  read-only
    STATUS  current
    DESCRIPTION
        "This flag indicates the way of configuring IPv6 destination address 
        mask, such as zxr10ACLv6MixRuleDestWildcard, 
        zxr10ACLv6MixRuleDstWildcardBits.
        If this flag is valid, IPv6 destination address mask is configured by 
        wildcard bits, (e.g. X:X::X:X) and zxr10ACLv6MixRuleDstWildcardBits 
        is valid; 
        if not, IPv6 destination address mask is configured by prefix length,
        (e.g. X:X::X:X/0-128) and zxr10ACLv6MixRuleDestWildcard is valid."
    DEFVAL    {2}  
    ::= { zxr10ACLv6MixRuleEntry 60 }
    
zxr10ACLv6MixRuleDstWildcardBits  OBJECT-TYPE
    SYNTAX   Ipv6Address
    MAX-ACCESS  read-only
    STATUS  current
    DESCRIPTION
        "<X:X::X:X>   Destination address wildcard bits"
    ::= { zxr10ACLv6MixRuleEntry 61 }

zxr10ACLv6MixRuleDsap  OBJECT-TYPE
    SYNTAX   Integer32(0..255|65535)   
    MAX-ACCESS  read-only
    STATUS  current
    DESCRIPTION
        "Destination service access point:
         <0-255>       valid value
         65535         invalid value
         This is an optional node."
    ::= { zxr10ACLv6MixRuleEntry 62 } 

zxr10ACLv6MixRuleSsap  OBJECT-TYPE
    SYNTAX   Integer32(0..255|65535)   
    MAX-ACCESS  read-only
    STATUS  current
    DESCRIPTION
        "Source service access point:
         <0-255>       valid value
         65535         invalid value
         This is an optional node."
    ::= { zxr10ACLv6MixRuleEntry 63 }


--------------------------------------------------------------
--------------------------------------------------------------
--zxr10ACLUsrProtocolObjects
--------------------------------------------------------------
--1  zxr10ACLUsrProtocolListTable
--2  zxr10ACLUsrProtocolRuleTable

--------------------------------------------------------------
--------------------------------------------------------------
--zxr10ACLUsrProtocolListTable
--------------------------------------------------------------
zxr10ACLUsrProtocolListTable  OBJECT-TYPE
    SYNTAX  SEQUENCE OF Zxr10ACLUsrProtocolListEntry
    MAX-ACCESS  not-accessible
    STATUS  current
    DESCRIPTION
        "User Protocol ACL"
    ::= { zxr10ACLUsrProtocolObjects 1 }

zxr10ACLUsrProtocolListEntry  OBJECT-TYPE
    SYNTAX  Zxr10ACLUsrProtocolListEntry
    MAX-ACCESS  not-accessible
    STATUS  current
    DESCRIPTION
        "User Protocol ACL"
    INDEX  { zxr10ACLUsrProtocolListName }
    ::= { zxr10ACLUsrProtocolListTable 1 }
    
Zxr10ACLUsrProtocolListEntry ::=SEQUENCE {
        zxr10ACLUsrProtocolListName                    DisplayString
   }
    
zxr10ACLUsrProtocolListName  OBJECT-TYPE
    SYNTAX   DisplayString(SIZE(1..31))
    MAX-ACCESS  read-only
    STATUS  current
    DESCRIPTION
        "Name of a User Protocol access-list (1-31 characters)"
    ::= { zxr10ACLUsrProtocolListEntry 1 } 


--------------------------------------------------------------
--------------------------------------------------------------
--zxr10ACLUTable
--------------------------------------------------------------
zxr10ACLUsrProtocolRuleTable  OBJECT-TYPE
    SYNTAX  SEQUENCE OF Zxr10ACLUsrProtocolRuleEntry
    MAX-ACCESS  not-accessible
    STATUS  current
    DESCRIPTION
        "User Protocol Rule Table"
    ::= { zxr10ACLUsrProtocolObjects 2 }

zxr10ACLUsrProtocolRuleEntry  OBJECT-TYPE
    SYNTAX  Zxr10ACLUsrProtocolRuleEntry
    MAX-ACCESS  not-accessible
    STATUS  current
    DESCRIPTION
        "User Protocol ACL
        effective leaf nodes: 
          All of the leaf nodes are effective:
                              zxr10ACLUsrProtocolRuleAclName,
                              zxr10ACLUsrProtocolRuleRuleID,
                              zxr10ACLUsrProtocolRuleEtherType,
                              zxr10ACLUsrProtocolRuleDestMAC,
                              zxr10ACLUsrProtocolRuleDMACMask,
                              zxr10ACLUsrProtocolRuleAnyEther,
        conflict leaf nodes:
       "
    INDEX  { zxr10ACLUsrProtocolRuleAclName,
             zxr10ACLUsrProtocolRuleRuleID }
    ::= { zxr10ACLUsrProtocolRuleTable 1 }
    
Zxr10ACLUsrProtocolRuleEntry ::=SEQUENCE {
        zxr10ACLUsrProtocolRuleAclName                 DisplayString,
        zxr10ACLUsrProtocolRuleRuleID                  Integer32,
        zxr10ACLUsrProtocolRuleEtherType               Integer32,
        zxr10ACLUsrProtocolRuleDestMAC                 MacAddress,
        zxr10ACLUsrProtocolRuleDMACMask                MacAddress,
        zxr10ACLUsrProtocolRuleAnyEther                AclValidOrNot
   }
    
zxr10ACLUsrProtocolRuleAclName  OBJECT-TYPE
    SYNTAX   DisplayString(SIZE(1..31))
    MAX-ACCESS  not-accessible
    STATUS  current
    DESCRIPTION
        "Name of a User Protocol access-list (1-31 characters)"
    ::= { zxr10ACLUsrProtocolRuleEntry 1 } 
        
zxr10ACLUsrProtocolRuleRuleID  OBJECT-TYPE
    SYNTAX   Integer32(1..2147483644)
    MAX-ACCESS  not-accessible
    STATUS  current
    DESCRIPTION
        "ID of this rule"
    ::= { zxr10ACLUsrProtocolRuleEntry 2 }    

zxr10ACLUsrProtocolRuleEtherType  OBJECT-TYPE
    SYNTAX   Integer32(0..65536)   
    MAX-ACCESS  read-only
    STATUS  current
    DESCRIPTION
        "Ether type of User Protocol:
         <0-65535>  valid value
         65536      invalid value"
    ::= { zxr10ACLUsrProtocolRuleEntry 3 } 

zxr10ACLUsrProtocolRuleDestMAC  OBJECT-TYPE
    SYNTAX   MacAddress
    MAX-ACCESS  read-only
    STATUS  current
    DESCRIPTION
        "<xxxx.xxxx.xxxx>  Destination MAC address"
    ::= { zxr10ACLUsrProtocolRuleEntry 4 } 
    
zxr10ACLUsrProtocolRuleDMACMask  OBJECT-TYPE
    SYNTAX   MacAddress
    MAX-ACCESS  read-only
    STATUS  current
    DESCRIPTION
        "<xxxx.xxxx.xxxx>  Destination MAC address wildcard
        This is an optional node."
    ::= { zxr10ACLUsrProtocolRuleEntry 5 } 

zxr10ACLUsrProtocolRuleAnyEther  OBJECT-TYPE
    SYNTAX   AclValidOrNot   
    MAX-ACCESS  read-only
    STATUS  current
    DESCRIPTION
        "Match any ethernet type if the value is valid."
    ::= { zxr10ACLUsrProtocolRuleEntry 6 } 

--------------------------------------------------------------
--------------------------------------------------------------
--zxr10ACLUsrDefObjects
--------------------------------------------------------------
--1  zxr10ACLUsrDefListTable
--2  zxr10ACLUsrDefRuleTable

--------------------------------------------------------------
--------------------------------------------------------------
--zxr10ACLUsrDefListTable
--------------------------------------------------------------
zxr10ACLUsrDefListTable  OBJECT-TYPE
    SYNTAX  SEQUENCE OF Zxr10ACLUsrDefListEntry
    MAX-ACCESS  not-accessible
    STATUS  current
    DESCRIPTION
        "User defined ACL"
    ::= { zxr10ACLUsrDefObjects 1 }

zxr10ACLUsrDefListEntry  OBJECT-TYPE
    SYNTAX  Zxr10ACLUsrDefListEntry
    MAX-ACCESS  not-accessible
    STATUS  current
    DESCRIPTION
        "User defined ACL"
    INDEX  { zxr10ACLUsrDefListName }
    ::= { zxr10ACLUsrDefListTable 1 }
    
Zxr10ACLUsrDefListEntry ::=SEQUENCE {
        zxr10ACLUsrDefListName                    DisplayString
   }
    
zxr10ACLUsrDefListName  OBJECT-TYPE
    SYNTAX   DisplayString(SIZE(1..31))
    MAX-ACCESS  read-only
    STATUS  current
    DESCRIPTION
        "Name of a User defined access-list (1-31 characters)"
    ::= { zxr10ACLUsrDefListEntry 1 } 


--------------------------------------------------------------
--------------------------------------------------------------
--zxr10ACLUTable
--------------------------------------------------------------
zxr10ACLUsrDefRuleTable  OBJECT-TYPE
    SYNTAX  SEQUENCE OF Zxr10ACLUsrDefRuleEntry
    MAX-ACCESS  not-accessible
    STATUS  current
    DESCRIPTION
        "User defined Rule Table"
    ::= { zxr10ACLUsrDefObjects 2 }

zxr10ACLUsrDefRuleEntry  OBJECT-TYPE
    SYNTAX  Zxr10ACLUsrDefRuleEntry
    MAX-ACCESS  not-accessible
    STATUS  current
    DESCRIPTION
        "User defined ACL
        effective leaf nodes: 
          All of the leaf nodes are effective:
                              zxr10ACLUsrDefRuleAclName,
                              zxr10ACLUsrDefRuleRuleID,
                              zxr10ACLUsrDefRulePermitDeny,
                              zxr10ACLUsrDefRuleFrameType,
                              zxr10ACLUsrDefRuleTagStatus,
                              zxr10ACLUsrDefRuleIpFlag,
                              zxr10ACLUsrDefRuleAnySegment,
                              zxr10ACLUsrDefRuleOffSet1,
                              zxr10ACLUsrDefRuleRuleString1,
                              zxr10ACLUsrDefRuleRuleMask1,
                              zxr10ACLUsrDefRuleOffSet2,
                              zxr10ACLUsrDefRuleRuleString2,
                              zxr10ACLUsrDefRuleRuleMask2,
                              zxr10ACLUsrDefRuleOffSet3,
                              zxr10ACLUsrDefRuleRuleString3,
                              zxr10ACLUsrDefRuleRuleMask3,
                              zxr10ACLUsrDefRuleOffSet4,
                              zxr10ACLUsrDefRuleRuleString4,
                              zxr10ACLUsrDefRuleRuleMask4,
                              zxr10ACLUsrDefRuleTimerangeName,
                              
        conflict leaf nodes:
       "
    INDEX  { zxr10ACLUsrDefRuleAclName,
             zxr10ACLUsrDefRuleRuleID }
    ::= { zxr10ACLUsrDefRuleTable 1 }
    
Zxr10ACLUsrDefRuleEntry ::=SEQUENCE {
        zxr10ACLUsrDefRuleAclName               DisplayString,
        zxr10ACLUsrDefRuleRuleID                Integer32,
        zxr10ACLUsrDefRulePermitDeny            AclPermitDeny,
        zxr10ACLUsrDefRuleFrameType             INTEGER,
        zxr10ACLUsrDefRuleTagStatus             INTEGER,
        zxr10ACLUsrDefRuleIpFlag                INTEGER,
        zxr10ACLUsrDefRuleAnySegment            AclValidOrNot,
        zxr10ACLUsrDefRuleOffSet1               Integer32,
        zxr10ACLUsrDefRuleRuleString1           DisplayString,
        zxr10ACLUsrDefRuleRuleMask1             DisplayString,
        zxr10ACLUsrDefRuleOffSet2               Integer32,
        zxr10ACLUsrDefRuleRuleString2           DisplayString,
        zxr10ACLUsrDefRuleRuleMask2             DisplayString,
        zxr10ACLUsrDefRuleOffSet3               Integer32,
        zxr10ACLUsrDefRuleRuleString3           DisplayString,
        zxr10ACLUsrDefRuleRuleMask3             DisplayString,
        zxr10ACLUsrDefRuleOffSet4               Integer32,
        zxr10ACLUsrDefRuleRuleString4           DisplayString,
        zxr10ACLUsrDefRuleRuleMask4             DisplayString,
        zxr10ACLUsrDefRuleTimerangeName         DisplayString
   }
    
zxr10ACLUsrDefRuleAclName  OBJECT-TYPE
    SYNTAX   DisplayString(SIZE(1..31))
    MAX-ACCESS  not-accessible
    STATUS  current
    DESCRIPTION
        "Name of a User defined access-list (1-31 characters)"
    ::= { zxr10ACLUsrDefRuleEntry 1 } 
        
zxr10ACLUsrDefRuleRuleID  OBJECT-TYPE
    SYNTAX   Integer32(1..2147483644)
    MAX-ACCESS  not-accessible
    STATUS  current
    DESCRIPTION
        "ID of this rule"
    ::= { zxr10ACLUsrDefRuleEntry 2 }  
    
zxr10ACLUsrDefRulePermitDeny  OBJECT-TYPE
    SYNTAX   AclPermitDeny
    MAX-ACCESS  read-only
    STATUS  current
    DESCRIPTION
        "deny  :  Specify packets to reject
         permit:  Specify packets to forward"
    ::= { zxr10ACLUsrDefRuleEntry 3 }    

zxr10ACLUsrDefRuleFrameType  OBJECT-TYPE
    SYNTAX   INTEGER{ethernet2(1),llc-snap(2),sap(3),any(4)}
    MAX-ACCESS  read-only
    STATUS  current
    DESCRIPTION
        " ethernet2   Ethernet version II frame  
          llc-snap    LLC/SNAP frame in IEEE802.3
          sap         SAP frame in IEEE802.3
          any         Any frame"
    ::= { zxr10ACLUsrDefRuleEntry 4 }
       
zxr10ACLUsrDefRuleTagStatus  OBJECT-TYPE
    SYNTAX   INTEGER{untag(1),single-tag(2),double-tag(3),any(4)}
    MAX-ACCESS  read-only
    STATUS  current
    DESCRIPTION
        "untag         Status with no VLAN tag
         single-tag    Status with VLAN tag
         double-tag    Status with outer and inner VLAN tag
         any           Any status with VLAN tag"
    ::= { zxr10ACLUsrDefRuleEntry 5 }
    
zxr10ACLUsrDefRuleIpFlag  OBJECT-TYPE
    SYNTAX   INTEGER{ip4-hdr-only(1),ip6-hdr-only(2),ip6-fragment(3),
             ip4-over-ip4(4),ip6-over-ip4(5),ip6-fragment-over-ip4(6),
             ip4-over-ip6(7),ip6-over-ip6(8),gre-ip4-over-ip4(9),
             gre-ip6-over-ip4(10),gre-ip4-over-ip6(11),gre-ip6-over-ip6(12),
             ip-unused(13),one-mpls-label(14),two-mpls-labels(15),
             any-mpls-labels(16),any(17)}
    MAX-ACCESS  read-only
    STATUS  current
    DESCRIPTION
        "ip4-hdr-only             Segment of only IPv4 header
         ip6-hdr-only             Segment of only IPv6 header
         ip6-fragment             Segment of IPv6 fragment
         ip4-over-ip4             Segment of IPv4 datagram over IPv4
         ip6-over-ip4             Segment of IPv6 datagram over IPv4
         ip6-fragment-over-ip4    Segment of IPv6 fragment datagram over IPv4
         ip4-over-ip6             Segment of IPv4 datagram over IPv6
         ip6-over-ip6             Segment of IPv6 datagram over IPv6
         gre-ip4-over-ip4         Segment of IPv4 datagram over IPv4 by GRE
         gre-ip6-over-ip4         Segment of IPv6 datagram over IPv4 by GRE
         gre-ip4-over-ip6         Segment of IPv4 datagram over IPv6 by GRE
         gre-ip6-over-ip6         Segment of IPv6 datagram over IPv6 by GRE
         ip-unused                None IP format datagram
         one-mpls-label           Segment of the first label out of tunnel
         two-mpls-labels          Segment of the second label in tunnel
         any-mpls-labels          Segment of any or multiple MPLS label
         any                      Any segment"
    ::= { zxr10ACLUsrDefRuleEntry 6 }
    
zxr10ACLUsrDefRuleAnySegment  OBJECT-TYPE
    SYNTAX   AclValidOrNot   
    MAX-ACCESS  read-only
    STATUS  current
    DESCRIPTION
        " Any rule segment."
    ::= { zxr10ACLUsrDefRuleEntry 7 } 
        
zxr10ACLUsrDefRuleOffSet1  OBJECT-TYPE
    SYNTAX   Integer32(2..126|65535)
    MAX-ACCESS  read-only
    STATUS  current
    DESCRIPTION
        "First offset from packet head (2+4*n, n = 0, 1, 2, ...)
         2-126     valid value
         65535     invalid value."
    ::= { zxr10ACLUsrDefRuleEntry 8 } 

zxr10ACLUsrDefRuleRuleString1  OBJECT-TYPE
    SYNTAX   DisplayString(SIZE(0|10))
    MAX-ACCESS  read-only
    STATUS  current
    DESCRIPTION
        "First user defined hexadecimal string(must be 10 characters)"
    ::= { zxr10ACLUsrDefRuleEntry 9 } 

zxr10ACLUsrDefRuleRuleMask1  OBJECT-TYPE
    SYNTAX   DisplayString(SIZE(0|10))
    MAX-ACCESS  read-only
    STATUS  current
    DESCRIPTION
        "First user defined hexadecimal string mask(must be 10 characters)"
    ::= { zxr10ACLUsrDefRuleEntry 10 }

zxr10ACLUsrDefRuleOffSet2  OBJECT-TYPE
    SYNTAX   Integer32(2..126|65535)
    MAX-ACCESS  read-only
    STATUS  current
    DESCRIPTION
        "Second offset from packet head (2+4*n, n = 0, 1, 2, ...)
         2-126     valid value
         65535     invalid value."
    ::= { zxr10ACLUsrDefRuleEntry 11 } 

zxr10ACLUsrDefRuleRuleString2  OBJECT-TYPE
    SYNTAX   DisplayString(SIZE(0|10))
    MAX-ACCESS  read-only
    STATUS  current
    DESCRIPTION
        "Second user defined hexadecimal string(must be 10 characters)"
    ::= { zxr10ACLUsrDefRuleEntry 12 } 

zxr10ACLUsrDefRuleRuleMask2  OBJECT-TYPE
    SYNTAX   DisplayString(SIZE(0|10))
    MAX-ACCESS  read-only
    STATUS  current
    DESCRIPTION
        "Second user defined hexadecimal string mask(must be 10 characters)"
    ::= { zxr10ACLUsrDefRuleEntry 13 }

zxr10ACLUsrDefRuleOffSet3  OBJECT-TYPE
    SYNTAX   Integer32(2..126|65535)
    MAX-ACCESS  read-only
    STATUS  current
    DESCRIPTION
        "Third offset from packet head (2+4*n, n = 0, 1, 2, ...)
         2-126     valid value
         65535     invalid value."
    ::= { zxr10ACLUsrDefRuleEntry 14 } 

zxr10ACLUsrDefRuleRuleString3  OBJECT-TYPE
    SYNTAX   DisplayString(SIZE(0|10))
    MAX-ACCESS  read-only
    STATUS  current
    DESCRIPTION
        "Third user defined hexadecimal string(must be 10 characters)"
    ::= { zxr10ACLUsrDefRuleEntry 15 } 

zxr10ACLUsrDefRuleRuleMask3  OBJECT-TYPE
    SYNTAX   DisplayString(SIZE(0|10))
    MAX-ACCESS  read-only
    STATUS  current
    DESCRIPTION
        "Third user defined hexadecimal string mask(must be 10 characters)"
    ::= { zxr10ACLUsrDefRuleEntry 16 }

zxr10ACLUsrDefRuleOffSet4  OBJECT-TYPE
    SYNTAX   Integer32(2..126|65535)
    MAX-ACCESS  read-only
    STATUS  current
    DESCRIPTION
        "Fourth offset from packet head (2+4*n, n = 0, 1, 2, ...)
         2-126     valid value
         65535     invalid value."
    ::= { zxr10ACLUsrDefRuleEntry 17 } 

zxr10ACLUsrDefRuleRuleString4  OBJECT-TYPE
    SYNTAX   DisplayString(SIZE(0|10))
    MAX-ACCESS  read-only
    STATUS  current
    DESCRIPTION
        "Fourth user defined hexadecimal string(must be 10 characters)"
    ::= { zxr10ACLUsrDefRuleEntry 18 } 

zxr10ACLUsrDefRuleRuleMask4  OBJECT-TYPE
    SYNTAX   DisplayString(SIZE(0|10))
    MAX-ACCESS  read-only
    STATUS  current
    DESCRIPTION
        "Fourth user defined hexadecimal string mask(must be 10 characters)"
    ::= { zxr10ACLUsrDefRuleEntry 19 }

zxr10ACLUsrDefRuleTimerangeName  OBJECT-TYPE
    SYNTAX   DisplayString(SIZE(0..31))
    MAX-ACCESS  read-only
    STATUS  current
    DESCRIPTION
        "Time range name (1-31 characters).
         This is an optional node."
    ::= { zxr10ACLUsrDefRuleEntry 20 }  

       
--------------------------------------------------------------
--------------------------------------------------------------
--zxr10ACLv4VxlanObjects
--------------------------------------------------------------
--1  zxr10ACLv4VxlanListTable
--2  zxr10ACLv4VxlanRuleTable
--------------------------------------------------------------
--------------------------------------------------------------
--zxr10ACLv4VxlanListTable
--------------------------------------------------------------
zxr10ACLv4VxlanListTable  OBJECT-TYPE
    SYNTAX  SEQUENCE OF Zxr10ACLv4VxlanListEntry
    MAX-ACCESS  not-accessible
    STATUS  current
    DESCRIPTION
        "IPv4 VXLAN ACL"
    ::= { zxr10ACLv4VxlanObjects 1 }

zxr10ACLv4VxlanListEntry  OBJECT-TYPE
    SYNTAX  Zxr10ACLv4VxlanListEntry
    MAX-ACCESS  not-accessible
    STATUS  current
    DESCRIPTION
        "IPv4 VXLAN ACL"
    INDEX  { zxr10ACLv4VxlanListName }
    ::= { zxr10ACLv4VxlanListTable 1 }
    
Zxr10ACLv4VxlanListEntry ::=SEQUENCE {
        zxr10ACLv4VxlanListName                    DisplayString,
        zxr10ACLv4VxlanListWithoutVni              AclValidOrNot,
        zxr10ACLv4VxlanListRowStatus               RowStatus      
   }
    
zxr10ACLv4VxlanListName  OBJECT-TYPE
    SYNTAX   DisplayString(SIZE(1..31))
    MAX-ACCESS  not-accessible
    STATUS  current
    DESCRIPTION
        "Name of an IPv4 VXLAN access-list (1-31 characters)"
    ::= { zxr10ACLv4VxlanListEntry 1 } 

zxr10ACLv4VxlanListWithoutVni  OBJECT-TYPE
    SYNTAX   AclValidOrNot
    MAX-ACCESS  read-create
    STATUS  current
    DESCRIPTION
        "If the flag is setted with valid,
         this acl can not be configed with VNI.
         If the flag is setted with invalid,
         this acl can be configed with VNI."
    ::= { zxr10ACLv4VxlanListEntry 2 } 

zxr10ACLv4VxlanListRowStatus  OBJECT-TYPE
    SYNTAX   RowStatus
    MAX-ACCESS  read-create
    STATUS  current
    DESCRIPTION
        "RowStatus"
    ::= { zxr10ACLv4VxlanListEntry 100 }    
--------------------------------------------------------------
--------------------------------------------------------------
--zxr10ACLv4VxlanRuleTable
--------------------------------------------------------------
zxr10ACLv4VxlanRuleTable  OBJECT-TYPE
    SYNTAX  SEQUENCE OF Zxr10ACLv4VxlanRuleEntry
    MAX-ACCESS  not-accessible
    STATUS  current
    DESCRIPTION
        "IPv4 VXLAN ACL Rule Table"
    ::= { zxr10ACLv4VxlanObjects 2 }

zxr10ACLv4VxlanRuleEntry  OBJECT-TYPE
    SYNTAX  Zxr10ACLv4VxlanRuleEntry
    MAX-ACCESS  not-accessible
    STATUS  current
    DESCRIPTION
        "IPv4 VXLAN ACL
        effective leaf nodes: 
          All of the leaf nodes are effective:
                              
        conflict leaf nodes:
          These 3 nodes below conflict, can only config one at most:
            zxr10ACLv4VxlanRulePrecedenceIn,
            zxr10ACLv4VxlanRuleTOSIn,
            zxr10ACLv4VxlanRuleDSCPIn
          
          These 3 nodes below conflict, can only config one at mos:
            zxr10ACLv4VxlanRulePrecedenceOut,
            zxr10ACLv4VxlanRuleTOSOut,
            zxr10ACLv4VxlanRuleDSCPOut 
          
          The inner-layer information contains these nodes below:
            zxr10ACLv4VxlanRuleInnerFlag,
            zxr10ACLv4VxlanRuleIpProtocolIn,
            zxr10ACLv4VxlanRuleSrcAddrIn,
            zxr10ACLv4VxlanRuleSrcIMaskIn,
            zxr10ACLv4VxlanRuleSrcAnyIn,
            zxr10ACLv4VxlanRuleDstAddrIn,
            zxr10ACLv4VxlanRuleDstIMaskIn,
            zxr10ACLv4VxlanRuleDstAnyIn,
            zxr10ACLv4VxlanRuleSrcPortOprIn,
            zxr10ACLv4VxlanRuleSrcPortValIn,
            zxr10ACLv4VxlanRuleSrcPortRgIn,
            zxr10ACLv4VxlanRuleDstPortOprIn,
            zxr10ACLv4VxlanRuleDstPortValIn,
            zxr10ACLv4VxlanRuleDstPortRgIn,
            zxr10ACLv4VxlanRulePrecedenceIn,
            zxr10ACLv4VxlanRuleTOSIn,
            zxr10ACLv4VxlanRuleDSCPIn
          The outer-layer information contains these nodes below:
            zxr10ACLv4VxlanRuleOuterFlag,
            zxr10ACLv4VxlanRuleIpProtocolOut,
            zxr10ACLv4VxlanRuleSrcAddrOut,
            zxr10ACLv4VxlanRuleSrcIMaskOut,
            zxr10ACLv4VxlanRuleSrcAnyOut,
            zxr10ACLv4VxlanRuleDstAddrOut,
            zxr10ACLv4VxlanRuleDstIMaskOut,
            zxr10ACLv4VxlanRuleDstAnyOut,
            zxr10ACLv4VxlanRuleSrcPortOprOut,
            zxr10ACLv4VxlanRuleSrcPortValOut,
            zxr10ACLv4VxlanRuleSrcPortRgOut,
            zxr10ACLv4VxlanRuleDstPortOprOut,
            zxr10ACLv4VxlanRuleDstPortValOut,
            zxr10ACLv4VxlanRuleDstPortRgOut,
            zxr10ACLv4VxlanRulePrecedenceOut,
            zxr10ACLv4VxlanRuleTOSOut,
            zxr10ACLv4VxlanRuleDSCPOut
          
       "
    INDEX  { zxr10ACLv4VxlanRuleAclName,
             zxr10ACLv4VxlanRuleRuleID }
    ::= { zxr10ACLv4VxlanRuleTable 1 }
    
Zxr10ACLv4VxlanRuleEntry ::=SEQUENCE {
        zxr10ACLv4VxlanRuleAclName                 DisplayString,
        zxr10ACLv4VxlanRuleRuleID                  Integer32, 
        zxr10ACLv4VxlanRulePermitDeny              AclPermitDeny, 
        zxr10ACLv4VxlanRuleInnerFlag               AclValidOrNot,
        zxr10ACLv4VxlanRuleIpProtocolIn            INTEGER,
        zxr10ACLv4VxlanRuleSrcAddrIn               IpAddress,
        zxr10ACLv4VxlanRuleSrcIMaskIn              IpAddress, 
        zxr10ACLv4VxlanRuleSrcAnyIn                AclValidOrNot,
        zxr10ACLv4VxlanRuleDstAddrIn               IpAddress,
        zxr10ACLv4VxlanRuleDstIMaskIn              IpAddress,
        zxr10ACLv4VxlanRuleDstAnyIn                AclValidOrNot,
        zxr10ACLv4VxlanRuleSrcPortOprIn            INTEGER,
        zxr10ACLv4VxlanRuleSrcPortValIn            INTEGER,
        zxr10ACLv4VxlanRuleSrcPortRgIn             DisplayString,
        zxr10ACLv4VxlanRuleDstPortOprIn            INTEGER,
        zxr10ACLv4VxlanRuleDstPortValIn            INTEGER,
        zxr10ACLv4VxlanRuleDstPortRgIn             DisplayString,
        zxr10ACLv4VxlanRulePrecedenceIn            Integer32,
        zxr10ACLv4VxlanRuleTOSIn                   Integer32,
        zxr10ACLv4VxlanRuleDSCPIn                  Integer32, 
        zxr10ACLv4VxlanRuleVniID                   Integer32,
        zxr10ACLv4VxlanRuleOuterFlag               AclValidOrNot,
        zxr10ACLv4VxlanRuleIpProtocolOut           INTEGER,
        zxr10ACLv4VxlanRuleSrcAddrOut              IpAddress,
        zxr10ACLv4VxlanRuleSrcIMaskOut             IpAddress,
        zxr10ACLv4VxlanRuleSrcAnyOut               AclValidOrNot,
        zxr10ACLv4VxlanRuleDstAddrOut              IpAddress,
        zxr10ACLv4VxlanRuleDstIMaskOut             IpAddress,
        zxr10ACLv4VxlanRuleDstAnyOut               AclValidOrNot,
        zxr10ACLv4VxlanRuleSrcPortOprOut           INTEGER,
        zxr10ACLv4VxlanRuleSrcPortValOut           INTEGER,
        zxr10ACLv4VxlanRuleSrcPortRgOut            DisplayString,
        zxr10ACLv4VxlanRuleDstPortOprOut           INTEGER,
        zxr10ACLv4VxlanRuleDstPortValOut           INTEGER,
        zxr10ACLv4VxlanRuleDstPortRgOut            DisplayString,
        zxr10ACLv4VxlanRulePrecedenceOut           Integer32,
        zxr10ACLv4VxlanRuleTOSOut                  Integer32,
        zxr10ACLv4VxlanRuleDSCPOut                 Integer32, 
        zxr10ACLv4VxlanRuleRowStatus               RowStatus      
   }
    
zxr10ACLv4VxlanRuleAclName  OBJECT-TYPE
    SYNTAX   DisplayString(SIZE(1..31))
    MAX-ACCESS  not-accessible
    STATUS  current
    DESCRIPTION
        "Name of an IPv4 VXLAN access-list (1-31 characters)"
    ::= { zxr10ACLv4VxlanRuleEntry 1 } 
        
zxr10ACLv4VxlanRuleRuleID  OBJECT-TYPE
    SYNTAX   Integer32(1..2147483644)
    MAX-ACCESS  not-accessible
    STATUS  current
    DESCRIPTION
        "ID of this rule"
    ::= { zxr10ACLv4VxlanRuleEntry 2 }    

zxr10ACLv4VxlanRulePermitDeny  OBJECT-TYPE
    SYNTAX   AclPermitDeny
    MAX-ACCESS  read-create
    STATUS  current
    DESCRIPTION
        "The node has two values:
         1. deny means that packets can not be handled.
         2. permit means that packets can be handled."
    ::= { zxr10ACLv4VxlanRuleEntry 3 }
    
zxr10ACLv4VxlanRuleInnerFlag  OBJECT-TYPE
    SYNTAX   AclValidOrNot
    MAX-ACCESS  read-create
    STATUS  current
    DESCRIPTION
        "If the flag is setted with valid, 
         the inner infomation is meaningful.
         If the flag is setted with invalid,
         the inner infomation is not meaningful."
    ::= { zxr10ACLv4VxlanRuleEntry 4 }    

zxr10ACLv4VxlanRuleIpProtocolIn  OBJECT-TYPE
    SYNTAX   INTEGER{icmp(1),igmp(2),tcp(6),udp(17),gre(47),ospf(89),
                     pim(103),vrrp(112),ip(65535)}
    MAX-ACCESS  read-create
    STATUS  current
    DESCRIPTION
        " <0-255>  An IP protocol number  
          gre      Generic Routing Encapsulation (47)
          icmp     Internet Control Message Protocol(1)
          igmp     Internet Group Management Protocol (2)
          ip       Any internet protocol(65535)
          ospf     Open Shortest Path First Protocol (89)
          pim      Protocol Independent Multicast (103)
          tcp      Transmission Control Protocol(6)
          udp      User Datagram Protocol(17)
          vrrp     Virtual Router Redundancy Protocol (112)"
    ::= { zxr10ACLv4VxlanRuleEntry 5 }

zxr10ACLv4VxlanRuleSrcAddrIn  OBJECT-TYPE
    SYNTAX   IpAddress
    MAX-ACCESS  read-create
    STATUS  current
    DESCRIPTION
        "A.B.C.D  Source address"
    ::= { zxr10ACLv4VxlanRuleEntry 6 }    

zxr10ACLv4VxlanRuleSrcIMaskIn  OBJECT-TYPE
    SYNTAX   IpAddress
    MAX-ACCESS  read-create
    STATUS  current
    DESCRIPTION
        "A.B.C.D  Wildcard bits"
    ::= { zxr10ACLv4VxlanRuleEntry 7 } 

zxr10ACLv4VxlanRuleSrcAnyIn  OBJECT-TYPE
    SYNTAX   AclValidOrNot
    MAX-ACCESS  read-create
    STATUS  current
    DESCRIPTION
        "If the flag is setted with valid,
         the rule is effective to any source address."
    ::= { zxr10ACLv4VxlanRuleEntry 8 } 
      
zxr10ACLv4VxlanRuleDstAddrIn  OBJECT-TYPE
    SYNTAX   IpAddress
    MAX-ACCESS  read-create
    STATUS  current
    DESCRIPTION
        "A.B.C.D  Destination address"
    ::= { zxr10ACLv4VxlanRuleEntry 9 } 
       
zxr10ACLv4VxlanRuleDstIMaskIn  OBJECT-TYPE
    SYNTAX   IpAddress
    MAX-ACCESS  read-create
    STATUS  current
    DESCRIPTION
        "A.B.C.D  Destination wildcard bits"
    ::= { zxr10ACLv4VxlanRuleEntry 10 }  
    
zxr10ACLv4VxlanRuleDstAnyIn  OBJECT-TYPE
    SYNTAX   AclValidOrNot
    MAX-ACCESS  read-create
    STATUS  current
    DESCRIPTION
        "If the flag is setted with valid,
         the rule is effective to any destination address."
    ::= { zxr10ACLv4VxlanRuleEntry 11 }
       
zxr10ACLv4VxlanRuleSrcPortOprIn  OBJECT-TYPE
    SYNTAX   INTEGER{oprTypeInvalid(65535),eq(1),ge(2),le(3),range(7)}
    MAX-ACCESS  read-create
    STATUS  current
    DESCRIPTION
        "This is an optional node.
         eq       Match only packets on a given port number
         ge       Match only packets with a no lower port number
         le       Match only packets with a no greater port number
         range    Match only packet on a given port range
         65535    invalid value
         
        Needn't care for zxr10ACLv4VxlanRuleSrcPortValIn and 
        zxr10ACLv4VxlanRuleSrcPortRgIn When the value of 
        zxr10ACLv4VxlanRuleSrcPortOprIn is invalid(65535).
        Check zxr10ACLv4VxlanRuleSrcPortValIn when the value 
        zxr10ACLv4VxlanRuleSrcPortOprIn is eq(1),ge(2) or le(3).
        Check zxr10ACLv4VxlanRuleSrcPortRgIn only when the value
        of zxr10ACLv4VxlanRuleSrcPortOprIn is range(7)."
    ::= { zxr10ACLv4VxlanRuleEntry 12 }
    
zxr10ACLv4VxlanRuleSrcPortValIn  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-create
    STATUS  current
    DESCRIPTION
        "<0-65535>   Port number 
        UDP protocol contains known port as follows:
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)
        TCP protocol contains known port as follows:
        bgp          Border gateway protocol (179)
        domain       Domain name service (53)
        finger       Finger (79)
        ftp          File transfer protocol (21)
        login        Login (rlogin, 513)
        pop2         Post office protocol v2 (109)
        pop3         Post office protocol v3 (110)
        smtp         Simple mail transport protocol (25)
        telnet       Telnet (23)
        www          World wide web (HTTP, 80)
                 
        Check this node when the value of zxr10ACLv4VxlanRuleSrcPortOprIn
        is eq(1),ge(2) or le(3)."
    ::= { zxr10ACLv4VxlanRuleEntry 13 }
    
zxr10ACLv4VxlanRuleSrcPortRgIn  OBJECT-TYPE
    SYNTAX   DisplayString
    MAX-ACCESS  read-create
    STATUS  current
    DESCRIPTION
        "Port range:  <0-65535>-<0-65535>
        Check this node only when the value of 
        zxr10ACLv4RuleSrcPortOprIn is range(7)."
    ::= { zxr10ACLv4VxlanRuleEntry 14 }
    
zxr10ACLv4VxlanRuleDstPortOprIn  OBJECT-TYPE
    SYNTAX   INTEGER{oprTypeInvalid(65535),eq(1),ge(2),le(3),range(7)}
    MAX-ACCESS  read-create
    STATUS  current
    DESCRIPTION
        "This is an optional node.
         eq       Match only packets on a given port number
         ge       Match only packets with a no lower port number
         le       Match only packets with a no greater port number
         range    Match only packet on a given port range
         65535    invalid value
         
        Needn't care for zxr10ACLv4VxlanRuleDstPortValIn and 
        zxr10ACLv4VxlanRuleDstPortRgIn When the value of 
        zxr10ACLv4VxlanRuleDestPortOprIn is invalid(65535).
        Check zxr10ACLv4VxlanRuleDstPortValIn when the value 
        zxr10ACLv4VxlanRuleDestPortOprIn is eq(1),ge(2) or le(3).
        Check zxr10ACLv4VxlanRuleDstPortRgIn only when the value
        of zxr10ACLv4VxlanRuleDestPortOprIn is range(7)."
    ::= { zxr10ACLv4VxlanRuleEntry 15 }    
    
zxr10ACLv4VxlanRuleDstPortValIn  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-create
    STATUS  current
    DESCRIPTION
        "<0-65535>   Port number
        UDP protocol contains known port as follows:
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)
        TCP protocol contains known port as follows:
        bgp          Border gateway protocol (179)
        domain       Domain name service (53)
        finger       Finger (79)
        ftp          File transfer protocol (21)
        login        Login (rlogin, 513)
        pop2         Post office protocol v2 (109)
        pop3         Post office protocol v3 (110)
        smtp         Simple mail transport protocol (25)
        telnet       Telnet (23)
        www          World wide web (HTTP, 80)

        Check this node when the value of zxr10ACLv4VxlanRuleDestPortOprIn
        is eq(1),ge(2) or le(3)."
    ::= { zxr10ACLv4VxlanRuleEntry 16 }

zxr10ACLv4VxlanRuleDstPortRgIn  OBJECT-TYPE
    SYNTAX   DisplayString
    MAX-ACCESS  read-create
    STATUS  current
    DESCRIPTION
        "Port range:  <0-65535>-<0-65535>
        Check this node only when the value of 
        zxr10ACLv4VxlanRuleDestPortOprIn is range(7)."
    ::= { zxr10ACLv4VxlanRuleEntry 17 }   
         
zxr10ACLv4VxlanRulePrecedenceIn  OBJECT-TYPE
    SYNTAX   Integer32(0..7|255)
    MAX-ACCESS  read-create
    STATUS  current
    DESCRIPTION
        "Precedence level:
         <0-7>   valid value
         255     invalid value
         This is an optional node.
         This node conflicts with zxr10ACLv4VxlanRuleTOSIn 
         and zxr10ACLv4VxlanRuleDSCPIn."
    ::= { zxr10ACLv4VxlanRuleEntry 18 }    
    
zxr10ACLv4VxlanRuleTOSIn  OBJECT-TYPE
    SYNTAX   Integer32(0..15|255)
    MAX-ACCESS  read-create
    STATUS  current
    DESCRIPTION
        "Type of service(ToS):
         <0-15>  valid value
         255     invalid value
         This is an optional node.
         This node conflicts with zxr10ACLv4VxlanRulePrecedenceIn 
         and zxr10ACLv4VxlanRuleDSCPIn."
    ::= { zxr10ACLv4VxlanRuleEntry 19 }  
      
zxr10ACLv4VxlanRuleDSCPIn  OBJECT-TYPE
    SYNTAX   Integer32(0..63|255)
    MAX-ACCESS  read-create
    STATUS  current
    DESCRIPTION
        "DSCP value:
         <0-63>  valid value
         255     invalid value
         This is an optional node.
         This node conflicts with zxr10ACLv4VxlanRulePrecedenceIn 
         and zxr10ACLv4VxlanRuleTOSIn"
    ::= { zxr10ACLv4VxlanRuleEntry 20 } 

zxr10ACLv4VxlanRuleVniID  OBJECT-TYPE
    SYNTAX   Integer32(0..16777215)
    MAX-ACCESS  read-create
    STATUS  current
    DESCRIPTION
        "VXLAN id. 
         Range is 1 to 16777215.
         0 is invalid value."
    ::= { zxr10ACLv4VxlanRuleEntry 21 }   
    
zxr10ACLv4VxlanRuleOuterFlag  OBJECT-TYPE
    SYNTAX   AclValidOrNot
    MAX-ACCESS  read-create
    STATUS  current
    DESCRIPTION
        "If the flag is setted with valid,
         the outer infomatino is meaningful.
         If the flag is setted with invalid,
         the outer infomation is not meaningful."
    ::= { zxr10ACLv4VxlanRuleEntry 22 }    

zxr10ACLv4VxlanRuleIpProtocolOut  OBJECT-TYPE
    SYNTAX   INTEGER{udp(17),invalid(65533)}
    MAX-ACCESS  read-create
    STATUS  current
    DESCRIPTION
        " udp      User Datagram Protocol(17)
          65533    Invalid value."
    ::= { zxr10ACLv4VxlanRuleEntry 23 }

zxr10ACLv4VxlanRuleSrcAddrOut  OBJECT-TYPE
    SYNTAX   IpAddress
    MAX-ACCESS  read-create
    STATUS  current
    DESCRIPTION
        "A.B.C.D  Source address"
    ::= { zxr10ACLv4VxlanRuleEntry 24 }    

zxr10ACLv4VxlanRuleSrcIMaskOut  OBJECT-TYPE
    SYNTAX   IpAddress
    MAX-ACCESS  read-create
    STATUS  current
    DESCRIPTION
        "A.B.C.D  Wildcard bits"
    ::= { zxr10ACLv4VxlanRuleEntry 25 } 

zxr10ACLv4VxlanRuleSrcAnyOut  OBJECT-TYPE
    SYNTAX   AclValidOrNot
    MAX-ACCESS  read-create
    STATUS  current
    DESCRIPTION
        "If the flag is setted with valid,
         the rule is effective to any dest address."
    ::= { zxr10ACLv4VxlanRuleEntry 26 }
 
zxr10ACLv4VxlanRuleDstAddrOut  OBJECT-TYPE
    SYNTAX   IpAddress
    MAX-ACCESS  read-create
    STATUS  current
    DESCRIPTION
        "A.B.C.D  Destination address"
    ::= { zxr10ACLv4VxlanRuleEntry 27 } 
       
zxr10ACLv4VxlanRuleDstIMaskOut  OBJECT-TYPE
    SYNTAX   IpAddress
    MAX-ACCESS  read-create
    STATUS  current
    DESCRIPTION
        "A.B.C.D  Destination wildcard bits"
    ::= { zxr10ACLv4VxlanRuleEntry 28} 

zxr10ACLv4VxlanRuleDstAnyOut  OBJECT-TYPE
    SYNTAX   AclValidOrNot
    MAX-ACCESS  read-create
    STATUS  current
    DESCRIPTION
        "If the flag is setted with valid,
         the rule is effective to any destination address."
    ::= { zxr10ACLv4VxlanRuleEntry 29 }
           
zxr10ACLv4VxlanRuleSrcPortOprOut  OBJECT-TYPE
    SYNTAX   INTEGER{oprTypeInvalid(65535),eq(1),ge(2),le(3),range(7)}
    MAX-ACCESS  read-create
    STATUS  current
    DESCRIPTION
        "This is an optional node.
         eq       Match only packets on a given port number
         ge       Match only packets with a no lower port number
         le       Match only packets with a no greater port number
         range    Match only packet on a given port range
         65535    invalid value
         
        Needn't care for zxr10ACLv4VxlanRuleSrcPortValOut and 
        zxr10ACLv4VxlanRuleSrcPortRgOut When the value of 
        zxr10ACLv4VxlanRuleSrcPortOprOut is invalid(65535).
        Check zxr10ACLv4VxlanRuleSrcPortValOut when the value 
        zxr10ACLv4VxlanRuleSrcPortOprOut is eq(1),ge(2) or le(3).
        Check zxr10ACLv4VxlanRuleSrcPortRgOut only when the value
        of zxr10ACLv4VxlanRuleSrcPortOprOut is range(7)."
    ::= { zxr10ACLv4VxlanRuleEntry 30 }
    
zxr10ACLv4VxlanRuleSrcPortValOut  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-create
    STATUS  current
    DESCRIPTION
        "<0-65535>   Port number
        UDP protocol contains known port as follows:
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)
        TCP protocol contains known port as follows:
        bgp          Border gateway protocol (179)
        domain       Domain name service (53)
        finger       Finger (79)
        ftp          File transfer protocol (21)
        login        Login (rlogin, 513)
        pop2         Post office protocol v2 (109)
        pop3         Post office protocol v3 (110)
        smtp         Simple mail transport protocol (25)
        telnet       Telnet (23)
        www          World wide web (HTTP, 80)

        Check this node when the value of zxr10ACLv4VxlanRuleSrcPortOprOut
        is eq(1),ge(2) or le(3)."
    ::= { zxr10ACLv4VxlanRuleEntry 31 }
    
zxr10ACLv4VxlanRuleSrcPortRgOut  OBJECT-TYPE
    SYNTAX   DisplayString
    MAX-ACCESS  read-create
    STATUS  current
    DESCRIPTION
        "Port range:  <0-65535>-<0-65535>
        Check this node only when the value of 
        zxr10ACLv4RuleSrcPortOprIn is range(7)."
    ::= { zxr10ACLv4VxlanRuleEntry 32 }
    
zxr10ACLv4VxlanRuleDstPortOprOut  OBJECT-TYPE
    SYNTAX   INTEGER{oprTypeInvalid(65535),eq(1),ge(2),le(3),range(7)}
    MAX-ACCESS  read-create
    STATUS  current
    DESCRIPTION
        "This is an optional node.
         eq       Match only packets on a given port number
         ge       Match only packets with a no lower port number
         le       Match only packets with a no greater port number
         range    Match only packet on a given port range
         65535    invalid value
         
        Needn't care for zxr10ACLv4VxlanRuleDstPortValOut and 
        zxr10ACLv4VxlanRuleDstPortRgOut When the value of 
        zxr10ACLv4VxlanRuleDestPortOprOut is invalid(65535).
        Check zxr10ACLv4VxlanRuleDstPortValOut when the value 
        zxr10ACLv4VxlanRuleDestPortOprOut is eq(1),ge(2) or le(3).
        Check zxr10ACLv4VxlanRuleDstPortRgOut only when the value
        of zxr10ACLv4VxlanRuleDestPortOprOut is range(7)."
    ::= { zxr10ACLv4VxlanRuleEntry 33 }    
    
zxr10ACLv4VxlanRuleDstPortValOut  OBJECT-TYPE
    SYNTAX   INTEGER{ftp(21),telnet(23),smtp(25),domain(53),bootps(67),
             bootpc(68),tftp(69),finger(79),www(80),pop2(109),pop3(110),
             ntp(123),snmp(161),snmptrap(162),bgp(179),pim-auto-rp(496),
             login(513),rip(520)}
    MAX-ACCESS  read-create
    STATUS  current
    DESCRIPTION
        "<0-65535>   Port number
        UDP protocol contains known port as follows:
        bootpc       Bootstrap protocol (BOOTP) client (68)
        bootps       Bootstrap protocol (BOOTP) server (67)
        domain       Domain name service (DNS, 53)
        ntp          Network time protocol (123)
        pim-auto-rp  PIM auto-RP (496)
        rip          Routing information protocol (router, in.routed, 520)
        snmp         Simple network management protocol (161)
        snmptrap     SNMP traps (162)
        tftp         Trivial file transfer protocol (69)
        TCP protocol contains known port as follows:
        bgp          Border gateway protocol (179)
        domain       Domain name service (53)
        finger       Finger (79)
        ftp          File transfer protocol (21)
        login        Login (rlogin, 513)
        pop2         Post office protocol v2 (109)
        pop3         Post office protocol v3 (110)
        smtp         Simple mail transport protocol (25)
        telnet       Telnet (23)
        www          World wide web (HTTP, 80)

        Check this node when the value of zxr10ACLv4VxlanRuleDestPortOprOut
        is eq(1),ge(2) or le(3)."
    ::= { zxr10ACLv4VxlanRuleEntry 34 }
    
zxr10ACLv4VxlanRuleDstPortRgOut  OBJECT-TYPE
    SYNTAX   DisplayString
    MAX-ACCESS  read-create
    STATUS  current
    DESCRIPTION
        "Port range:  <0-65535>-<0-65535>
        Check this node only when the value of 
        zxr10ACLv4VxlanRuleDestPortOprOut is range(7)."
    ::= { zxr10ACLv4VxlanRuleEntry 35 }   
         
zxr10ACLv4VxlanRulePrecedenceOut  OBJECT-TYPE
    SYNTAX   Integer32(0..7|255)
    MAX-ACCESS  read-create
    STATUS  current
    DESCRIPTION
        "Precedence level:
         <0-7>   valid value
         255     invalid value
         This is an optional node.
         This node conflicts with zxr10ACLv4VxlanRuleTOSOut 
         and zxr10ACLv4VxlanRuleDSCPOut."
    ::= { zxr10ACLv4VxlanRuleEntry 36 }    
    
zxr10ACLv4VxlanRuleTOSOut  OBJECT-TYPE
    SYNTAX   Integer32(0..15|255)
    MAX-ACCESS  read-create
    STATUS  current
    DESCRIPTION
        "Type of service(ToS):
         <0-15>  valid value
         255     invalid value
         This is an optional node.
         This node conflicts with zxr10ACLv4VxlanRulePrecedenceOut 
         and zxr10ACLv4VxlanRuleDSCPOut."
    ::= { zxr10ACLv4VxlanRuleEntry 37 }  
      
zxr10ACLv4VxlanRuleDSCPOut  OBJECT-TYPE
    SYNTAX   Integer32(0..63|255)
    MAX-ACCESS  read-create
    STATUS  current
    DESCRIPTION
        "DSCP value:
         <0-63>  valid value
         255     invalid value
         This is an optional node.
         This node conflicts with zxr10ACLv4VxlanRulePrecedenceOut 
         and zxr10ACLv4VxlanRuleTOSOut."
    ::= { zxr10ACLv4VxlanRuleEntry 38 } 

zxr10ACLv4VxlanRuleRowStatus  OBJECT-TYPE
    SYNTAX   RowStatus
    MAX-ACCESS  read-create
    STATUS  current
    DESCRIPTION
        "RowStatus"
    ::= { zxr10ACLv4VxlanRuleEntry 100 }

--------------------------------------------------------------
--------------------------------------------------------------
--zxr10ACLGroup
--------------------------------------------------------------
zxr10ACLv4Group OBJECT-GROUP
    OBJECTS {
            zxr10ACLv4ListName,
            zxr10ACLv4RulePermitDeny,
            zxr10ACLv4RuleSrcAddr,
            zxr10ACLv4RuleSrcWildcard, 
            zxr10ACLv4RuleDestAddr,
            zxr10ACLv4RuleDestWildcard,
            zxr10ACLv4RuleIpProtocol,           
            zxr10ACLv4RuleSrcPortOpr,            
            zxr10ACLv4RuleSrcPortValue,          
            zxr10ACLv4RuleSrcPortRange,
            zxr10ACLv4RuleDestPortOpr,           
            zxr10ACLv4RuleDestPortValue,         
            zxr10ACLv4RuleDestPortRange,
            zxr10ACLv4RuleTCPEstablish,
            zxr10ACLv4RuleICMPType,     
            zxr10ACLv4RuleICMPCode,     
            zxr10ACLv4RulePrecedence,  
            zxr10ACLv4RuleTOS,          
            zxr10ACLv4RuleDSCP,         
            zxr10ACLv4RuleFragment,
            zxr10ACLv4RuleRstFlag,
            zxr10ACLv4RuleAckFlag,
            zxr10ACLv4RuleFinFlag,
            zxr10ACLv4RuleSynFlag,
            zxr10ACLv4RulePshFlag,
            zxr10ACLv4RuleUrgFlag,
            zxr10ACLv4RuleTtlOpr,       
            zxr10ACLv4RuleTtlValue,     
            zxr10ACLv4RuleTtlRange,
            zxr10ACLv4RuleTimerangeName,
            zxr10ACLv4RuleSrcUrl,
            zxr10ACLv4RuleDestUrl,
            zxr10ACLv4RuleDescription,
            zxr10ACLv4RulePrecRange,
            zxr10ACLv4RuleDscpRange
    }
    STATUS       current
    DESCRIPTION
       "IPv4 ACL group."
    ::= { zxr10ACLGroups 1 }

zxr10ACLv6Group OBJECT-GROUP
    OBJECTS {
            zxr10ACLv6ListName,
            zxr10ACLv6RulePermitDeny, 
            zxr10ACLv6RuleFlowlabel,    
            zxr10ACLv6RuleSrcAddr,
            zxr10ACLv6RuleSrcWildcard,  
            zxr10ACLv6RuleDestAddr,
            zxr10ACLv6RuleDestWildcard, 
            zxr10ACLv6RuleIpProtocol,   
            zxr10ACLv6RuleSrcPortOpr,   
            zxr10ACLv6RuleSrcPortValue, 
            zxr10ACLv6RuleSrcPortRange,
            zxr10ACLv6RuleDestPortOpr,  
            zxr10ACLv6RuleDestPortValue,
            zxr10ACLv6RuleDestPortRange,
            zxr10ACLv6RuleTCPEstablish, 
            zxr10ACLv6RuleRstFlag, 
            zxr10ACLv6RuleAckFlag,
            zxr10ACLv6RuleFinFlag,
            zxr10ACLv6RuleSynFlag,
            zxr10ACLv6RulePshFlag,
            zxr10ACLv6RuleUrgFlag,
            zxr10ACLv6RuleICMPType,       
            zxr10ACLv6RuleICMPCode,       
            zxr10ACLv6RuleRouting,
            zxr10ACLv6RuleAuthen,
            zxr10ACLv6RuleDestops,
            zxr10ACLv6RuleFragments,
            zxr10ACLv6RuleHopByHop,
            zxr10ACLv6RuleEsp,
            zxr10ACLv6RuleDSCP,          
            zxr10ACLv6RuleTc,             
            zxr10ACLv6RuleTimerangeName,
            zxr10ACLv6RuleSrcUrl,
            zxr10ACLv6RuleDestUrl,
            zxr10ACLv6RuleSrcAddrMaskFlag,
            zxr10ACLv6RuleSrcWildcardBits,
            zxr10ACLv6RuleDestAddrMaskFlag,
            zxr10ACLv6RuleDestWildcardBits,
            zxr10ACLv6RuleDescription
    }
    STATUS       current
    DESCRIPTION
       "IPv6 ACL group."
    ::= { zxr10ACLGroups 2 }

zxr10ACLLinkGroup OBJECT-GROUP
    OBJECTS {
            zxr10ACLLinkListName,       
            zxr10ACLLinkRulePermitDeny,
            zxr10ACLLinkRuleLinkProtocol,    
            zxr10ACLLinkRuleSrcMAC,
            zxr10ACLLinkRuleSrcMACWildcard,
            zxr10ACLLinkRuleDestMAC,
            zxr10ACLLinkRuleDestMACWildcard,
            zxr10ACLLinkRuleIncos,            
            zxr10ACLLinkRuleOutCos,           
            zxr10ACLLinkRuleInVlanID,        
            zxr10ACLLinkRuleOutVlanID,       
            zxr10ACLLinkRuleInVlanRange,
            zxr10ACLLinkRuleOutVlanRange,
            zxr10ACLLinkRuleTimerangeName,
            zxr10ACLLinkRuleBSrcMACRange1,
            zxr10ACLLinkRuleSrcMACRg1Min,
            zxr10ACLLinkRuleSrcMACRg1Max,  
            zxr10ACLLinkRuleBSrcMACRange2,
            zxr10ACLLinkRuleSrcMACRg2Min,
            zxr10ACLLinkRuleSrcMACRg2Max,  
            zxr10ACLLinkRuleBDestMACRange1,
            zxr10ACLLinkRuleDestMACRg1Min,
            zxr10ACLLinkRuleDestMACRg1Max,  
            zxr10ACLLinkRuleBDestMACRange2,
            zxr10ACLLinkRuleDestMACRg2Min,
            zxr10ACLLinkRuleDestMACRg2Max,
            zxr10ACLLinkRuleDescription,
            zxr10ACLLinkRuleLinkProtocolMask,
            zxr10ACLLinkRuleInCosRange,
            zxr10ACLLinkRuleOutCosRange,
            zxr10ACLLinkRuleDsap,
            zxr10ACLLinkRuleSsap
    }
    STATUS       current
    DESCRIPTION
       "Link ACL group."
    ::= { zxr10ACLGroups 3 }

zxr10ACLv4MixGroup OBJECT-GROUP
    OBJECTS {
            zxr10ACLv4MixListName,
            zxr10ACLv4MixRulePermitDeny,
            zxr10ACLv4MixRuleLinkProtocol,   
            zxr10ACLv4MixRuleSrcMAC,        
            zxr10ACLv4MixRuleSrcMACWildcard, 
            zxr10ACLv4MixRuleDestMAC,        
            zxr10ACLv4MixRuleDestMACWildcard,
            zxr10ACLv4MixRuleIncos,            
            zxr10ACLv4MixRuleOutCos,           
            zxr10ACLv4MixRuleInVlanID,         
            zxr10ACLv4MixRuleOutVlanID,        
            zxr10ACLv4MixRuleInVlanRange,
            zxr10ACLv4MixRuleOutVlanRange,
            zxr10ACLv4MixRuleSrcAddr,          
            zxr10ACLv4MixRuleSrcWildcard,      
            zxr10ACLv4MixRuleDestAddr,         
            zxr10ACLv4MixRuleDestWildcard,     
            zxr10ACLv4MixRuleIpProtocol,       
            zxr10ACLv4MixRuleSrcPortOpr,       
            zxr10ACLv4MixRuleSrcPortValue,     
            zxr10ACLv4MixRuleSrcPortRange,
            zxr10ACLv4MixRuleDestPortOpr,      
            zxr10ACLv4MixRuleDestPortValue,   
            zxr10ACLv4MixRuleDestPortRange,
            zxr10ACLv4MixRuleTCPEstablish, 
            zxr10ACLv4MixRuleICMPType,         
            zxr10ACLv4MixRuleICMPCode,         
            zxr10ACLv4MixRulePrecedence,       
            zxr10ACLv4MixRuleTOS,              
            zxr10ACLv4MixRuleDSCP,             
            zxr10ACLv4MixRuleFragment,
            zxr10ACLv4MixRuleRstFlag,
            zxr10ACLv4MixRuleAckFlag,
            zxr10ACLv4MixRuleFinFlag,
            zxr10ACLv4MixRuleSynFlag,
            zxr10ACLv4MixRulePshFlag,
            zxr10ACLv4MixRuleUrgFlag,
            zxr10ACLv4MixRuleTimerangeName,
            zxr10ACLv4MixRuleBSrcMACRange1,
            zxr10ACLv4MixRuleSrcMACRg1Min,     
            zxr10ACLv4MixRuleSrcMACRg1Max,     
            zxr10ACLv4MixRuleBSrcMACRange2,
            zxr10ACLv4MixRuleSrcMACRg2Min,     
            zxr10ACLv4MixRuleSrcMACRg2Max,     
            zxr10ACLv4MixRuleBDestMACRange1,
            zxr10ACLv4MixRuleDestMACRg1Min,    
            zxr10ACLv4MixRuleDestMACRg1Max,    
            zxr10ACLv4MixRuleBDestMACRange2,
            zxr10ACLv4MixRuleDestMACRg2Min,    
            zxr10ACLv4MixRuleDestMACRg2Max,    
            zxr10ACLv4MixRuleLinkProtocolEx,
            zxr10ACLv4MixRuleDsap,
            zxr10ACLv4MixRuleSsap   
    }
    STATUS       current
    DESCRIPTION
       "IPv4 mixed ACL group."
    ::= { zxr10ACLGroups 4 }

zxr10ACLv6MixGroup OBJECT-GROUP
    OBJECTS {
            zxr10ACLv6MixListName,
            zxr10ACLv6MixRulePermitDeny,
            zxr10ACLv6MixRuleLinkProtocol,     
            zxr10ACLv6MixRuleSrcMAC,         
            zxr10ACLv6MixRuleSrcMACWildcard,  
            zxr10ACLv6MixRuleDestMAC,         
            zxr10ACLv6MixRuleDestMACWildcard, 
            zxr10ACLv6MixRuleIncos,           
            zxr10ACLv6MixRuleOutCos,          
            zxr10ACLv6MixRuleInVlanID,        
            zxr10ACLv6MixRuleOutVlanID,       
            zxr10ACLv6MixRuleInVlanRange,     
            zxr10ACLv6MixRuleOutVlanRange,    
            zxr10ACLv6MixRuleFlowlabel,
            zxr10ACLv6MixRuleSrcAddr,
            zxr10ACLv6MixRuleSrcWildcard,
            zxr10ACLv6MixRuleDestAddr,
            zxr10ACLv6MixRuleDestWildcard,
            zxr10ACLv6MixRuleIpProtocol,
            zxr10ACLv6MixRuleSrcPortOpr,
            zxr10ACLv6MixRuleSrcPortValue,
            zxr10ACLv6MixRuleSrcPortRange,
            zxr10ACLv6MixRuleDestPortOpr,
            zxr10ACLv6MixRuleDestPortValue,
            zxr10ACLv6MixRuleDestPortRange,
            zxr10ACLv6MixRuleTCPEstablish,
            zxr10ACLv6MixRuleRstFlag,
            zxr10ACLv6MixRuleAckFlag,
            zxr10ACLv6MixRuleFinFlag,
            zxr10ACLv6MixRuleSynFlag,
            zxr10ACLv6MixRulePshFlag,
            zxr10ACLv6MixRuleUrgFlag,
            zxr10ACLv6MixRuleICMPType,
            zxr10ACLv6MixRuleICMPCode,
            zxr10ACLv6MixRuleRouting,
            zxr10ACLv6MixRuleAuthen,
            zxr10ACLv6MixRuleDestops,
            zxr10ACLv6MixRuleFragments,
            zxr10ACLv6MixRuleHopByHop,
            zxr10ACLv6MixRuleEsp,
            zxr10ACLv6MixRuleDSCP,
            zxr10ACLv6MixRuleTc,
            zxr10ACLv6MixRuleTimerangeName,
            zxr10ACLv6MixRuleBSrcMACRange1,
            zxr10ACLv6MixRuleSrcMACRg1Min,
            zxr10ACLv6MixRuleSrcMACRg1Max,
            zxr10ACLv6MixRuleBSrcMACRange2,
            zxr10ACLv6MixRuleSrcMACRg2Min,
            zxr10ACLv6MixRuleSrcMACRg2Max, 
            zxr10ACLv6MixRuleBDestMACRange1,
            zxr10ACLv6MixRuleDestMACRg1Min,
            zxr10ACLv6MixRuleDestMACRg1Max,
            zxr10ACLv6MixRuleBDestMACRange2,
            zxr10ACLv6MixRuleDestMACRg2Min,
            zxr10ACLv6MixRuleDestMACRg2Max,
            zxr10ACLv6MixRuleLinkProtocolEx,
            zxr10ACLv6MixRuleSrcAddrMaskFlag,
            zxr10ACLv6MixRuleSrcWildcardBits,
            zxr10ACLv6MixRuleDstAddrMaskFlag,
            zxr10ACLv6MixRuleDstWildcardBits,
            zxr10ACLv6MixRuleDsap,
            zxr10ACLv6MixRuleSsap 
    }
    STATUS       current
    DESCRIPTION
       "IPv6 mixed ACL group."
    ::= { zxr10ACLGroups 5 }

zxr10ACLUsrProtocolGroup OBJECT-GROUP
    OBJECTS {
            zxr10ACLUsrProtocolListName,
            zxr10ACLUsrProtocolRuleEtherType,
            zxr10ACLUsrProtocolRuleDestMAC,
            zxr10ACLUsrProtocolRuleDMACMask, 
            zxr10ACLUsrProtocolRuleAnyEther
    }
    STATUS       current
    DESCRIPTION
       "User protocol ACL group."
    ::= { zxr10ACLGroups 6 }

zxr10ACLUsrDefinedGroup OBJECT-GROUP
    OBJECTS {
            zxr10ACLUsrDefListName,
            zxr10ACLUsrDefRulePermitDeny,
            zxr10ACLUsrDefRuleFrameType,
            zxr10ACLUsrDefRuleTagStatus,
            zxr10ACLUsrDefRuleIpFlag,
            zxr10ACLUsrDefRuleAnySegment,
            zxr10ACLUsrDefRuleOffSet1,
            zxr10ACLUsrDefRuleRuleString1,
            zxr10ACLUsrDefRuleRuleMask1,
            zxr10ACLUsrDefRuleOffSet2,
            zxr10ACLUsrDefRuleRuleString2,
            zxr10ACLUsrDefRuleRuleMask2,
            zxr10ACLUsrDefRuleOffSet3,
            zxr10ACLUsrDefRuleRuleString3,
            zxr10ACLUsrDefRuleRuleMask3,
            zxr10ACLUsrDefRuleOffSet4,
            zxr10ACLUsrDefRuleRuleString4,
            zxr10ACLUsrDefRuleRuleMask4,
            zxr10ACLUsrDefRuleTimerangeName
    }
    STATUS       current
    DESCRIPTION
       "User defined ACL group."
    ::= { zxr10ACLGroups 7 }
 
zxr10ACLv4VxlanGroup OBJECT-GROUP
    OBJECTS {
            zxr10ACLv4VxlanListWithoutVni,
            zxr10ACLv4VxlanListRowStatus,
            zxr10ACLv4VxlanRulePermitDeny,
            zxr10ACLv4VxlanRuleInnerFlag,
            zxr10ACLv4VxlanRuleIpProtocolIn,
            zxr10ACLv4VxlanRuleSrcAddrIn,
            zxr10ACLv4VxlanRuleSrcIMaskIn,
            zxr10ACLv4VxlanRuleSrcAnyIn,
            zxr10ACLv4VxlanRuleDstAddrIn,
            zxr10ACLv4VxlanRuleDstIMaskIn,
            zxr10ACLv4VxlanRuleDstAnyIn,
            zxr10ACLv4VxlanRuleSrcPortOprIn,
            zxr10ACLv4VxlanRuleSrcPortValIn,
            zxr10ACLv4VxlanRuleSrcPortRgIn,
            zxr10ACLv4VxlanRuleDstPortOprIn,
            zxr10ACLv4VxlanRuleDstPortValIn,
            zxr10ACLv4VxlanRuleDstPortRgIn,
            zxr10ACLv4VxlanRulePrecedenceIn,
            zxr10ACLv4VxlanRuleTOSIn,
            zxr10ACLv4VxlanRuleDSCPIn,
            zxr10ACLv4VxlanRuleVniID,
            zxr10ACLv4VxlanRuleOuterFlag,
            zxr10ACLv4VxlanRuleIpProtocolOut,
            zxr10ACLv4VxlanRuleSrcAddrOut,
            zxr10ACLv4VxlanRuleSrcIMaskOut,
            zxr10ACLv4VxlanRuleSrcAnyOut,
            zxr10ACLv4VxlanRuleDstAddrOut,
            zxr10ACLv4VxlanRuleDstIMaskOut,
            zxr10ACLv4VxlanRuleDstAnyOut,
            zxr10ACLv4VxlanRuleSrcPortOprOut,
            zxr10ACLv4VxlanRuleSrcPortValOut,
            zxr10ACLv4VxlanRuleSrcPortRgOut,
            zxr10ACLv4VxlanRuleDstPortOprOut,
            zxr10ACLv4VxlanRuleDstPortValOut,
            zxr10ACLv4VxlanRuleDstPortRgOut,
            zxr10ACLv4VxlanRulePrecedenceOut,
            zxr10ACLv4VxlanRuleTOSOut,
            zxr10ACLv4VxlanRuleDSCPOut,
            zxr10ACLv4VxlanRuleRowStatus
    }
    STATUS       current
    DESCRIPTION
       "IPv4 VXLAN ACL group."
    ::= { zxr10ACLGroups 8 }

END
