-- Teldat, S.A.

                -- Parque Tecnolgico de Madrid

                -- 28760, Tres Cantos (Madrid)

                -- Tlf: +34-918076565

                -- Fax: +34-918076521

                -- e-mail: id@teldat.com


            -- MIB privada de Teldat

            -- Monitorizacin del interfaz GPRS


    -- Historial:
    --      07-02-14    M.A. Pastor     XH 3523. Errors with HP Openview 9.20
    -- 1.2  11-01-13    E. Amorena      XH 2610. MIBs compilation.
    -- 1.1  10-02-12    FDMB             Throughput included
    -- 1.0  17-06-09    Benjamin G.      Implementacin inicial
--------------------------------------------------------------------------------

TELDAT-MON-INTERF-GPRS-MIB DEFINITIONS ::= BEGIN

IMPORTS
    OBJECT-TYPE
        FROM RFC-1212
    DisplayString
        FROM RFC1213-MIB
    telProdNpMonInterfRouter
        FROM TELDAT-SW-STRUCTURE-MIB;


-- Monitorizacin privada del interfaz GPRS

telProdNpMonInterfGPRS OBJECT IDENTIFIER ::= { telProdNpMonInterfRouter 22 }


--  = = = = = = = = = = = = = = = = = = = = = = = = = = = = = = = = = = = = = =
--  Global GPRS monitoring variables
--  = = = = = = = = = = = = = = = = = = = = = = = = = = = = = = = = = = = = = =


--  = = = = = = = = = = = = = = = = = = = = = = = = = = = = = = = = = = = = = =
--  Global Info GPRS monitoring variables
--  = = = = = = = = = = = = = = = = = = = = = = = = = = = = = = = = = = = = = =

telGPRSInfoInterfaceTable OBJECT-TYPE
    SYNTAX  SEQUENCE OF TelGPRSInfoInterfaceEntry
    ACCESS  not-accessible
    STATUS  mandatory
    DESCRIPTION
        "Table of information available for GPRS interfaces.
        Each row represents an interface"
    ::= { telProdNpMonInterfGPRS 1 }

telGPRSInfoInterfaceEntry OBJECT-TYPE
    SYNTAX  TelGPRSInfoInterfaceEntry
    ACCESS  not-accessible
    STATUS  mandatory
    DESCRIPTION
        "A base list of objects that are information about a GPRS interface.
        The inex is the number of the interface"
    INDEX   { telGPRSInfoInterfaceIndex }
    ::= { telGPRSInfoInterfaceTable 1 }

TelGPRSInfoInterfaceEntry ::= SEQUENCE
{
    telGPRSInfoInterfaceIndex                INTEGER,
    telGPRSInfoInterfaceModuleManufacturer   DisplayString,
    telGPRSInfoInterfaceModuleModel          DisplayString,
    telGPRSInfoInterfaceModuleFirmware       DisplayString,
    telGPRSInfoInterfaceModuleIMEI           DisplayString,
    telGPRSInfoInterfaceModuleIMSI           DisplayString,
    telGPRSInfoInterfaceSIMId                DisplayString,
    telGPRSInfoInterfaceSIMIcc               DisplayString
}

telGPRSInfoInterfaceIndex OBJECT-TYPE
    SYNTAX  INTEGER(1 .. 255)
    ACCESS  read-only
    STATUS  mandatory
    DESCRIPTION
        "Interface index"
    ::= { telGPRSInfoInterfaceEntry 1 }

telGPRSInfoInterfaceModuleManufacturer OBJECT-TYPE
    SYNTAX  DisplayString
    ACCESS  read-only
    STATUS  mandatory
    DESCRIPTION
        "GPRS module manufacturer."
    ::={ telGPRSInfoInterfaceEntry 2 }

telGPRSInfoInterfaceModuleModel OBJECT-TYPE
    SYNTAX  DisplayString
    ACCESS  read-only
    STATUS  mandatory
    DESCRIPTION
        "GPRS module model."
    ::={ telGPRSInfoInterfaceEntry 3 }

telGPRSInfoInterfaceModuleFirmware OBJECT-TYPE
    SYNTAX  DisplayString
    ACCESS  read-only
    STATUS  mandatory
    DESCRIPTION
        "GPRS module firmware release."
    ::={ telGPRSInfoInterfaceEntry 4 }

telGPRSInfoInterfaceModuleIMEI OBJECT-TYPE
    SYNTAX  DisplayString
    ACCESS  read-only
    STATUS  mandatory
    DESCRIPTION
        "GPRS module IMEI."
    ::={ telGPRSInfoInterfaceEntry 5 }

telGPRSInfoInterfaceModuleIMSI OBJECT-TYPE
    SYNTAX  DisplayString
    ACCESS  read-only
    STATUS  mandatory
    DESCRIPTION
        "GPRS module IMSI."
    ::={ telGPRSInfoInterfaceEntry 6 }

telGPRSInfoInterfaceSIMId OBJECT-TYPE
    SYNTAX  DisplayString
    ACCESS  read-only
    STATUS  mandatory
    DESCRIPTION
        "GPRS active SIM ID."
    ::={ telGPRSInfoInterfaceEntry 7 }

telGPRSInfoInterfaceSIMIcc OBJECT-TYPE
    SYNTAX  DisplayString
    ACCESS  read-only
    STATUS  mandatory
    DESCRIPTION
        "GPRS active SIM ICC."
    ::={ telGPRSInfoInterfaceEntry 8 }


--  = = = = = = = = = = = = = = = = = = = = = = = = = = = = = = = = = = = = = =
--  Global Stats group GPRS monitoring variables
--  = = = = = = = = = = = = = = = = = = = = = = = = = = = = = = = = = = = = = =

telGPRSStatObject    OBJECT IDENTIFIER ::= { telProdNpMonInterfGPRS 3 }

--  - - - - - - - - - - - - - - - - - - - - - - - - - - - - - - - - - - - - - -
--   GPRS State Table, interface variables
--  - - - - - - - - - - - - - - - - - - - - - - - - - - - - - - - - - - - - - -

telGPRSStateInterfaceTable OBJECT-TYPE
    SYNTAX  SEQUENCE OF TelGPRSStateInterfaceEntry
    ACCESS  not-accessible
    STATUS  mandatory
    DESCRIPTION
        "Table of GPRS interface state information."
    ::= { telGPRSStatObject 1 }

telGPRSStateInterfaceEntry OBJECT-TYPE
    SYNTAX  TelGPRSStateInterfaceEntry
    ACCESS  not-accessible
    STATUS  mandatory
    DESCRIPTION
        "A base list of objects that are interface state information."
    INDEX   { telGPRSStateInterfaceIndex}
    ::= { telGPRSStateInterfaceTable 1 }

TelGPRSStateInterfaceEntry ::= SEQUENCE
{
    telGPRSStateInterfaceIndex           INTEGER,
    telGPRSStateInterfaceState           INTEGER,
    telGPRSStateInterfaceDropPing        INTEGER,
    telGPRSStateInterfaceDropTrace       INTEGER,
    telGPRSStateInterfaceDropTraffic     INTEGER,
    telGPRSStateInterfaceTConnTime       INTEGER,
    telGPRSStateInterfaceCConnTime       INTEGER,
    telGPRSStateInterfaceCurDial         DisplayString,
    telGPRSStateInterfaceNCall           INTEGER,
    telGPRSStateInterfaceDestination     DisplayString,
    telGPRSStateInterfaceTime2Sp         INTEGER
}

telGPRSStateInterfaceIndex OBJECT-TYPE
    SYNTAX  INTEGER(1 .. 255)
    ACCESS  read-only
    STATUS  mandatory
    DESCRIPTION
        "GPRS Interface index."
    ::={ telGPRSStateInterfaceEntry 1 }

telGPRSStateInterfaceState OBJECT-TYPE
    SYNTAX  INTEGER {
        initial(0),
        disconnect(1),
        trying-to-connect-ini(2),
        trying-to-connect-mk(3),
        trying-to-connect-cp(4),
        connect(5),
        waiting-call(6),
        hanging-up-ini(7),
        hanging-up(8),
        hanging-up-wta(9),
        hanging-up-wtar(10),
        discconnect-n-wait-call(11),
        wait-attach-wapn(12),
        wait-attach(13),
        wait-detach(14),
        wakeup-machine(15),
        command-mode(16),
        trying-to-connect-con(17),
        hanging-up-wesc(18),
        hanging-up-wt(19),
        disconnect-clcc(20),
        connect-wesc(21),
        connect-clcc(22),
        connect-ron(23),
        trying-to-connect-wgic(24),
        trying-to-connect-ucsq(25),
        trying-to-connect-unet(26),
        trying-to-connect-watc(27),
        establish-audio(28),
        gsm-incom-notify(29),
        wait-gsm-incom-notify(30),
        hanging-up-wdt(31)
        }
    ACCESS  read-only
    STATUS  mandatory
    DESCRIPTION
        "Call state."
    ::={ telGPRSStateInterfaceEntry 2 }

telGPRSStateInterfaceDropPing OBJECT-TYPE
    SYNTAX  INTEGER
    ACCESS  read-only
    STATUS  mandatory
    DESCRIPTION
        "Number of calls dropped due to ping supervision."
    ::={ telGPRSStateInterfaceEntry 3 }

telGPRSStateInterfaceDropTrace OBJECT-TYPE
    SYNTAX  INTEGER
    ACCESS  read-only
    STATUS  mandatory
    DESCRIPTION
        "Number of calls dropped due to traceroute supervision."
    ::={ telGPRSStateInterfaceEntry 4 }

telGPRSStateInterfaceDropTraffic OBJECT-TYPE
    SYNTAX  INTEGER
    ACCESS  read-only
    STATUS  mandatory
    DESCRIPTION
        "Number of calls dropped due to traffic supervision."
    ::={ telGPRSStateInterfaceEntry 5 }

telGPRSStateInterfaceTConnTime OBJECT-TYPE
    SYNTAX  INTEGER
    ACCESS  read-only
    STATUS  mandatory
    DESCRIPTION
        "Total connection time ."
    ::={ telGPRSStateInterfaceEntry 6 }

telGPRSStateInterfaceCConnTime OBJECT-TYPE
    SYNTAX  INTEGER
    ACCESS  read-only
    STATUS  mandatory
    DESCRIPTION
        "Current connection time."
    ::={ telGPRSStateInterfaceEntry 7 }

telGPRSStateInterfaceCurDial OBJECT-TYPE
    SYNTAX  DisplayString
    ACCESS  read-only
    STATUS  mandatory
    DESCRIPTION
        "Current dial-profile used."
    ::={ telGPRSStateInterfaceEntry 8 }

telGPRSStateInterfaceNCall OBJECT-TYPE
    SYNTAX  INTEGER
    ACCESS  read-only
    STATUS  mandatory
    DESCRIPTION
        "Number of processed calls."
    ::={ telGPRSStateInterfaceEntry 9 }

telGPRSStateInterfaceDestination OBJECT-TYPE
    SYNTAX  DisplayString
    ACCESS  read-only
    STATUS  mandatory
    DESCRIPTION
        "Connection destination."
    ::={ telGPRSStateInterfaceEntry 10 }

telGPRSStateInterfaceTime2Sp OBJECT-TYPE
    SYNTAX  INTEGER
    ACCESS  read-only
    STATUS  mandatory
    DESCRIPTION
        "Time to establish the call."
    ::={ telGPRSStateInterfaceEntry 11 }


--  - - - - - - - - - - - - - - - - - - - - - - - - - - - - - - - - - - - - - -
--   GPRS State Table, Mobile variables
--  - - - - - - - - - - - - - - - - - - - - - - - - - - - - - - - - - - - - - -

telGPRSStateMobileTable OBJECT-TYPE
    SYNTAX  SEQUENCE OF TelGPRSStateMobileEntry
    ACCESS  not-accessible
    STATUS  mandatory
    DESCRIPTION
        "Table of GPRS mobile state information."
    ::= { telGPRSStatObject 2 }

telGPRSStateMobileEntry OBJECT-TYPE
    SYNTAX  TelGPRSStateMobileEntry
    ACCESS  not-accessible
    STATUS  mandatory
    DESCRIPTION
        "A base list of objects that are mobile state information."
    INDEX   { telGPRSStateMobileIndex }
    ::= { telGPRSStateMobileTable 1 }

TelGPRSStateMobileEntry ::= SEQUENCE
{
    telGPRSStateMobileIndex                      INTEGER,
    telGPRSStateMobileRegistrationState          INTEGER,
    telGPRSStateMobilePublicLandMobileNtwCode    INTEGER,
    telGPRSStateMobileCellLocationAreaCode       INTEGER,
    telGPRSStateMobileCellId                     INTEGER,
    telGPRSStateMobileRadioTechnology            DisplayString,
    telGPRSStateMobileReceivedSignalStrength     INTEGER,
    telGPRSStateMobileRxPackets                  INTEGER,
    telGPRSStateMobileRxBytes                    INTEGER,
    telGPRSStateMobileTxPackets                  INTEGER,
    telGPRSStateMobileTxBytes                    INTEGER,
    telGPRSStateMobileRxBpsLast1s                INTEGER,
    telGPRSStateMobileTxBpsLast1s                INTEGER,
    telGPRSStateMobileRxBpsLast1m                INTEGER,
    telGPRSStateMobileTxBpsLast1m                INTEGER,
    telGPRSStateMobileRxBpsLast5m                INTEGER,
    telGPRSStateMobileTxBpsLast5m                INTEGER

}

telGPRSStateMobileIndex OBJECT-TYPE
    SYNTAX  INTEGER(1 .. 255)
    ACCESS  read-only
    STATUS  mandatory
    DESCRIPTION
        "GPRS mobile state index."
    ::={ telGPRSStateMobileEntry 1 }

telGPRSStateMobileRegistrationState OBJECT-TYPE
    SYNTAX  INTEGER {
        searching(0),
        home-network(1),
        attaching(2),
        denied(3),
        unknown(4),
        roaming(5)
        }
    ACCESS  read-only
    STATUS  mandatory
    DESCRIPTION
        "GPRS mobile registration state ()."
    ::={ telGPRSStateMobileEntry  2 }

telGPRSStateMobilePublicLandMobileNtwCode OBJECT-TYPE
    SYNTAX  INTEGER
    ACCESS  read-only
    STATUS  mandatory
    DESCRIPTION
        "Public land mobile network used."
    ::={ telGPRSStateMobileEntry  3 }


telGPRSStateMobileCellLocationAreaCode OBJECT-TYPE
    SYNTAX  INTEGER
    ACCESS  read-only
    STATUS  mandatory
    DESCRIPTION
        "GPRS mobile cell location area code."
    ::={ telGPRSStateMobileEntry  4 }

telGPRSStateMobileCellId OBJECT-TYPE
    SYNTAX  INTEGER
    ACCESS  read-only
    STATUS  mandatory
    DESCRIPTION
        "GPRS mobile used cell id."
    ::={ telGPRSStateMobileEntry  5 }


telGPRSStateMobileRadioTechnology OBJECT-TYPE
    SYNTAX  DisplayString
    ACCESS  read-only
    STATUS  mandatory
    DESCRIPTION
        "GSM mobile current radio access tecnology used. "
    ::={ telGPRSStateMobileEntry  6 }

telGPRSStateMobileReceivedSignalStrength OBJECT-TYPE
    SYNTAX  INTEGER
    ACCESS  read-only
    STATUS  mandatory
    DESCRIPTION
        "GPRS mobile received signal strength (RSSI). Value in -dBm."
    ::={ telGPRSStateMobileEntry  7 }

telGPRSStateMobileRxPackets OBJECT-TYPE
    SYNTAX  INTEGER
    ACCESS  read-only
    STATUS  mandatory
    DESCRIPTION
        "Number of data packtes received by the radio interface"
    ::={ telGPRSStateMobileEntry  8 }

telGPRSStateMobileRxBytes OBJECT-TYPE
    SYNTAX  INTEGER
    ACCESS  read-only
    STATUS  mandatory
    DESCRIPTION
        "Number of data bytes received by the radio interface"
    ::={ telGPRSStateMobileEntry  9 }

telGPRSStateMobileTxPackets OBJECT-TYPE
    SYNTAX  INTEGER
    ACCESS  read-only
    STATUS  mandatory
    DESCRIPTION
        "Number of data packtes sent by the radio interface"
    ::={ telGPRSStateMobileEntry  10 }

telGPRSStateMobileTxBytes OBJECT-TYPE
    SYNTAX  INTEGER
    ACCESS  read-only
    STATUS  mandatory
    DESCRIPTION
        "Number of data packtes sent by the radio interface"
    ::={ telGPRSStateMobileEntry  11 }

telGPRSStateMobileRxBpsLast1s OBJECT-TYPE
    SYNTAX  INTEGER
    ACCESS  read-only
    STATUS  mandatory
    DESCRIPTION
        "Rx througput measured in the last second in bps"
    ::={ telGPRSStateMobileEntry  12 }

telGPRSStateMobileTxBpsLast1s OBJECT-TYPE
    SYNTAX  INTEGER
    ACCESS  read-only
    STATUS  mandatory
    DESCRIPTION
        "Tx througput measured in the last second in bps"
    ::={ telGPRSStateMobileEntry  13 }

telGPRSStateMobileRxBpsLast1m OBJECT-TYPE
    SYNTAX  INTEGER
    ACCESS  read-only
    STATUS  mandatory
    DESCRIPTION
        "Rx througput measured in the last minute in bps"
    ::={ telGPRSStateMobileEntry  14 }

telGPRSStateMobileTxBpsLast1m OBJECT-TYPE
    SYNTAX  INTEGER
    ACCESS  read-only
    STATUS  mandatory
    DESCRIPTION
        "Tx througput measured in the last minute in bps"
    ::={ telGPRSStateMobileEntry  15 }

telGPRSStateMobileRxBpsLast5m OBJECT-TYPE
    SYNTAX  INTEGER
    ACCESS  read-only
    STATUS  mandatory
    DESCRIPTION
        "Rx througput measured in the last five minutes in bps"
    ::={ telGPRSStateMobileEntry  16 }

telGPRSStateMobileTxBpsLast5m OBJECT-TYPE
    SYNTAX  INTEGER
    ACCESS  read-only
    STATUS  mandatory
    DESCRIPTION
        "Tx througput measured in the last five minutes in bps"
    ::={ telGPRSStateMobileEntry  17 }

END
