--  =================================================================
-- Copyright (C) 2009 by  HUAWEI TECHNOLOGIES. All rights reserved
-- 
-- Description:
-- Reference:
-- Version: V1.0
-- History:
-- shaoyu,2009-03-12,<contents>
-- =================================================================

    HUAWEI-SECURITY-FULLCONE-MIB DEFINITIONS ::= BEGIN
 
        IMPORTS
	    enterprises			
		FROM RFC1155-SMI
            OBJECT-GROUP            
                FROM SNMPv2-CONF            
            Integer32, Counter64, OBJECT-TYPE, MODULE-IDENTITY , Gauge32  , IpAddress        
                FROM SNMPv2-SMI            
            TruthValue            
                FROM SNMPv2-TC;
    
    

--
-- Node definitions
--                       
 	-- 1.3.6.1.4.1.2011
	huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }          
        
        -- 1.3.6.1.4.1.2011.6.122.48
        hwSecFullConeMibObjects OBJECT IDENTIFIER ::= { hwSecurity 48 }
   
       	-- 1.3.6.1.4.1.2011.6.122.48.1                          
    	hwSecFullConeTrapsObjests OBJECT IDENTIFIER ::= { hwSecFullConeMibObjects 1 }    
    	
        -- 1.3.6.1.4.1.2011.6.122.48.1.1 		
       	hwSecFullConeTrapSlot OBJECT-TYPE
        	SYNTAX Gauge32 (1..16)
        	MAX-ACCESS accessible-for-notify
        	STATUS current
        	DESCRIPTION
            		"The slot number."
        	::= { hwSecFullConeTrapsObjests 1 }     
        
        -- 1.3.6.1.4.1.2011.6.122.48.1.2        
    	hwSecFullConeTrapCPU OBJECT-TYPE
        	SYNTAX Gauge32 (0..3) 
        	MAX-ACCESS accessible-for-notify
       	 	STATUS current
        	DESCRIPTION
            		"The CPU number."
        	::= { hwSecFullConeTrapsObjests 2 }  
 
         -- 1.3.6.1.4.1.2011.6.122.48.1.3        
    	hwSecFullConeTrapIpPoolIndex OBJECT-TYPE
        	SYNTAX Gauge32 (0..4095) 
        	MAX-ACCESS accessible-for-notify
       	 	STATUS current
        	DESCRIPTION
            		"The Ip Pool Index."
        	::= { hwSecFullConeTrapsObjests 3 }  
 
        -- 1.3.6.1.4.1.2011.6.122.48.1.4       
    	hwSecFullConeIpPoolPortUsageTrap OBJECT-TYPE
        	SYNTAX Gauge32 (0..100)
        	--SYNTAX OCTET STRING
        	MAX-ACCESS accessible-for-notify
        	STATUS current
        	DESCRIPTION
            		"The Usage of Ip Pool Port in the CPU."
        	::= { hwSecFullConeTrapsObjests 4 }   
        
        -- 1.3.6.1.4.1.2011.6.122.48.1.5       
    	hwSecFullConeIpPoolPortUsageThresholdTrap OBJECT-TYPE
        	SYNTAX Gauge32 (0..100)
        	--SYNTAX OCTET STRING
        	MAX-ACCESS accessible-for-notify
        	STATUS current
        	DESCRIPTION
            		"Threshold of Ip Pool Port Usage in the CPU."
        	::= { hwSecFullConeTrapsObjests 5 } 

        -- 1.3.6.1.4.1.2011.6.122.48.1.6       
    	hwSecFullConeIpAddrTrap OBJECT-TYPE
        	--SYNTAX Gauge32 (0..2000000)
        	SYNTAX IpAddress
        	MAX-ACCESS accessible-for-notify
        	STATUS current
        	DESCRIPTION
            		"Ip Address in the CPU."
        	::= { hwSecFullConeTrapsObjests 6 }   
        	
        -- 1.3.6.1.4.1.2011.6.122.48.1.7       
    	hwSecFullConeIpPortUsageTrap OBJECT-TYPE
        	SYNTAX Gauge32 (0..100)
        	--SYNTAX OCTET STRING
        	MAX-ACCESS accessible-for-notify
        	STATUS current
        	DESCRIPTION
            		"The IP Port Usage in the CPU."
        	::= { hwSecFullConeTrapsObjests 7 }   
        
        -- 1.3.6.1.4.1.2011.6.122.48.1.8       
    	hwSecFullConeIpPortUsageThresholdTrap OBJECT-TYPE
        	SYNTAX Gauge32 (0..100)
        	--SYNTAX OCTET STRING
        	MAX-ACCESS accessible-for-notify
        	STATUS current
        	DESCRIPTION
            		"Threshold of IP Port Usage in the CPU."
        	::= { hwSecFullConeTrapsObjests 8 } 
   	
        -- 1.3.6.1.4.1.2011.6.122.48.2                          
    	hwSecFullConeTraps OBJECT IDENTIFIER ::= { hwSecFullConeMibObjects 2 }   	 
                		                                
        hwSecFullConeIpPoolPortUsageOverThreshold NOTIFICATION-TYPE
		OBJECTS { 
			  hwSecFullConeTrapSlot,
			  hwSecFullConeTrapCPU,
			  hwSecFullConeTrapIpPoolIndex,  
			  hwSecFullConeIpPoolPortUsageTrap,
			  hwSecFullConeIpPoolPortUsageThresholdTrap   
		        }
		STATUS     current
		DESCRIPTION
		    "The Port Usage of the CPU exceeds threshold."
		::= { hwSecFullConeTraps 1 }
                                   
        hwSecFullConeIpPortUsageOverThreshold NOTIFICATION-TYPE
		OBJECTS { 
			  hwSecFullConeTrapSlot,
			  hwSecFullConeTrapCPU,
			  hwSecFullConeIpAddrTrap,  
			  hwSecFullConeIpPortUsageTrap,
			  hwSecFullConeIpPortUsageThresholdTrap   
		        }
		STATUS     current
		DESCRIPTION
		    "The IP Port Usage of the CPU exceeds threshold."
		::= { hwSecFullConeTraps 2 }

        hwSecFullConeIpPoolPortUsageLessThreshold NOTIFICATION-TYPE
		OBJECTS { 
			  hwSecFullConeTrapSlot,
			  hwSecFullConeTrapCPU,
			  hwSecFullConeTrapIpPoolIndex,  
			  hwSecFullConeIpPoolPortUsageTrap,
			  hwSecFullConeIpPoolPortUsageThresholdTrap   
		        }
		STATUS     current
		DESCRIPTION
		    "The Port Usage of the CPU Less threshold."
		::= { hwSecFullConeTraps 3 }
                                   
        hwSecFullConeIpPortUsageLessThreshold NOTIFICATION-TYPE
		OBJECTS { 
			  hwSecFullConeTrapSlot,
			  hwSecFullConeTrapCPU,
			  hwSecFullConeIpAddrTrap,  
			  hwSecFullConeIpPortUsageTrap,
			  hwSecFullConeIpPortUsageThresholdTrap   
		        }
		STATUS     current
		DESCRIPTION
		    "The IP Port Usage of the CPU Less threshold."
		::= { hwSecFullConeTraps 4 }

    END

--
-- HUAWEI-SECSTAT-MIB.mib
--
