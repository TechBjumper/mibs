--
-- Eltex Enterprise Specific MIB: mc240 MIB
--
-- Copyright (c) 2007, Eltex Co
-- All rights reserved.
--
-- The contents of this document are subject to change without notice.
--
-- Please, use english only in this document!
--
-- tauMegacoTrapsTable also used for SMG SBC MSR
--


ELTEX-FXS72 DEFINITIONS ::= BEGIN

IMPORTS
    MODULE-IDENTITY, OBJECT-TYPE, NOTIFICATION-TYPE,
    Integer32, Gauge32, Counter32, TimeTicks, Unsigned32
        FROM SNMPv2-SMI
    TruthValue, DisplayString, TimeStamp, TimeInterval, TEXTUAL-CONVENTION, RowStatus
        FROM SNMPv2-TC
    OBJECT-GROUP
    	FROM SNMPv2-CONF
    elHardware
        FROM ELTEX-SMI-ACTUAL;

 fxs72 MODULE-IDENTITY
    LAST-UPDATED "200910190000Z"
    ORGANIZATION "Eltex Co"
    CONTACT-INFO "  eltex@gcom.ru "
    DESCRIPTION  "fxs72 mib"
    REVISION     "200910190000Z"
    DESCRIPTION  "last revision"
    ::= { elHardware 9 }
    
SSwStatusConv ::= TEXTUAL-CONVENTION
  STATUS current
  DESCRIPTION ""
  SYNTAX INTEGER  {
  	  undefined(0),
      connected(1),
      disconnected(2)}
      
VoltageMode ::= TEXTUAL-CONVENTION
  STATUS current
  DESCRIPTION ""
  SYNTAX INTEGER  {
  	  high(1),
      normal(2),
      low(3) }
      
FXSFanState ::= TEXTUAL-CONVENTION
	STATUS current
	DESCRIPTION ""
	SYNTAX INTEGER {
		off(0),
		on(1)}
		
BoolValue ::= TEXTUAL-CONVENTION
	STATUS  current
	DESCRIPTION ""
	SYNTAX INTEGER {
			false(0),
			true(1) }
			
DevTypeString ::= TEXTUAL-CONVENTION
  STATUS current
  DESCRIPTION ""
  SYNTAX INTEGER  {
  	  fxs72(16),
      tau72(17),
      tau36(33),
      tau32m(50)}
      
FxsPortState ::= TEXTUAL-CONVENTION
  STATUS current
  DESCRIPTION ""
  SYNTAX INTEGER  {
	-- off hook state --
	hangdown(0),
	-- on hook state --
	hangup(1),
	dial(2),
	calling(3),
	ringback(4),
	ringing(5),
	talking(6),
	busy(7),
	hold(8),
	holdDial(9),
	dvo(10),
	test(11),
	blocked(12),
	preCalling(13),
    conference3way(14),
    void(15),
    fxoHangdown(16),
	fxoHangup(17),
	disabled(255) }
	
PortMegacoState ::= TEXTUAL-CONVENTION
  STATUS current
  DESCRIPTION ""
  SYNTAX INTEGER  {
	-- off hook state --
	hangdown(0),
	-- on hook state --
	hangup(1),
	dial(2),
	calling(3),
	ringback(4),
	ringing(5),
	talking(6),
	busy(7),
	hold(8),
	holdDial(9),
	holdDvo(10),
	transfer(11),
	unattended(12),
	blocked(13),
    ready(14),
    notInited(15),
    disabled(16),
	absent(17),
	noActualData(255)}

PortMegacoJitter ::= TEXTUAL-CONVENTION
  STATUS current
  DESCRIPTION ""
  SYNTAX INTEGER  {
	ok(0),
	leakageCurrent(1),
	overheating(2),
	dissipatedPower(3)
  }
	
SipConnectState ::= TEXTUAL-CONVENTION
  STATUS current
  DESCRIPTION ""
  SYNTAX INTEGER  {
	off(0),
	ok(1),
	failed(2)}

	

FxsDialPlanType ::= TEXTUAL-CONVENTION
  STATUS current
  DESCRIPTION ""
  SYNTAX INTEGER  {
	h323GateKeeper(1),
	sipProxy(2),
	h323DirectIP(3),
	sipDirectIP(4),
	siptDirectIP(5),
	pickupGroup(6) }
	
FxsAON ::= TEXTUAL-CONVENTION
	STATUS current
	DESCRIPTION ""
	SYNTAX INTEGER {
		off(0),
		aonRus(1),
		dtmf(2),
		fskBell202(3),
		fskV23(4) }
		
FxsGroupSerialType ::= TEXTUAL-CONVENTION
	STATUS current
	DESCRIPTION ""
	SYNTAX INTEGER {
		group(0),
		serial(1),
		cyclic(2) }
		
FxoGroupType ::= TEXTUAL-CONVENTION
	STATUS current
	DESCRIPTION ""
	SYNTAX INTEGER {
		fxoFirstFree(3),
		fxoAround(4) }

FxsGroupBusyType ::= TEXTUAL-CONVENTION
	STATUS current
	DESCRIPTION ""
	SYNTAX INTEGER {
		clearOnBusy(0),
		waitFirstFree(1) }

FxsGroupSerialEnableType ::= TEXTUAL-CONVENTION
	STATUS current
	DESCRIPTION ""
	SYNTAX INTEGER {
		true(1),
		false(2) }
		
FxsTaxophoneType ::= TEXTUAL-CONVENTION
	STATUS current
	DESCRIPTION "0-3 for TAU72,36; 
		0-1 for TAU32M (from v2.8)
		0-3 for TAU32M-revB (from 2.10)"
	SYNTAX INTEGER {
		off(0),
		polarity(1),
		kHz16(2),
		kHz12(3) }
		
 

FxsDialPlanNatureType ::= TEXTUAL-CONVENTION
  STATUS current
  DESCRIPTION ""
  SYNTAX INTEGER  {
	unknown(0),
	subscriber(1),
	national(2),
	international(3) }

FxsProcessFlashType ::= TEXTUAL-CONVENTION
  STATUS current
  DESCRIPTION ""
  SYNTAX INTEGER  {
	transmitFlash(0),
	attendedCT(1),
	unattendedCT(2),
	noDetectFlash(3),
	localCT(4) -- TAU-SIP 2.7
	}
	
TauDialProtocolType ::= TEXTUAL-CONVENTION
  STATUS current
  DESCRIPTION ""
  SYNTAX INTEGER  {
	sip(1),
	h323(2) }
	
ProxyMode ::= TEXTUAL-CONVENTION
  STATUS current
  DESCRIPTION ""
  SYNTAX INTEGER  {
	off(0),
	parking(1),
	homing(2) }

OptionsHomeServerTest ::= TEXTUAL-CONVENTION
  STATUS current
  DESCRIPTION ""
  SYNTAX INTEGER  {
	invite(0),
	options(1),
	register(2) }

AuthenticationType ::= TEXTUAL-CONVENTION
  STATUS current
  DESCRIPTION ""
  SYNTAX INTEGER  {
	off(0),
	global(1),
	userDefined(2) }

CwRingbackRingbackAtCallwaiting ::= TEXTUAL-CONVENTION
  STATUS current
  DESCRIPTION ""
  SYNTAX INTEGER  {
	ring180Ringing(0),
	ring182Queued(1) }

RemoteRingback ::= TEXTUAL-CONVENTION
  STATUS current
  DESCRIPTION ""
  SYNTAX INTEGER  {
	dontSendRingbackInRTP(0),
	ringbackWith180Ringing(1),
	ringbackWith183Progress(2) }

-- application/dtmf        dtmf	0
-- application/dtmf-relay  dtmfr	1
-- audio/telephone-event   audio	2
DTMFMIMEType ::= TEXTUAL-CONVENTION
  STATUS current
  DESCRIPTION ""
  SYNTAX INTEGER  {
	applicationDtmfRelay(0),
	applicationDtmf(1),
	audioTelephoneEvent(2) }

-- dtmf		asDTMF			0
-- hookf		applicationHookFlash	1
-- broadsoft	applicationBroadsoft	2
-- sscc (Huawei) applicationSscc 3
HookFlashMIMEType ::= TEXTUAL-CONVENTION
  STATUS current
  DESCRIPTION ""
  SYNTAX INTEGER  {
	asDTMF(0),
	applicationHookFlash(1),
	applicationBroadsoft(2),
	applicationSscc(3) }

TypeTransport ::= TEXTUAL-CONVENTION
  STATUS current
  DESCRIPTION ""
  SYNTAX INTEGER  {
	udpPrefferedOrTcp(0),
	tcpPrefferedOrUdp(1),
	udpOnly(2),
	tcpOnly(3) }

Type100rel ::= TEXTUAL-CONVENTION
  STATUS current
  DESCRIPTION ""
  SYNTAX INTEGER  {
	supported (0),
	required (1),
	off(2) } 
	
OutboundType ::= TEXTUAL-CONVENTION
  STATUS current
  DESCRIPTION ""
  SYNTAX INTEGER  {
	off(0),
	on(1),
	withBusyTone(2) }
	
FxoDialingType ::= TEXTUAL-CONVENTION
  STATUS current
  DESCRIPTION ""
  SYNTAX INTEGER  {
	dtmf(1),
	pulse(2) }
	
FxsToneParametrs ::= TEXTUAL-CONVENTION
	STATUS current
	DESCRIPTION " X;Z(A/B/1)
				X,Y;Z(A/B/1)
				X,Y;Z(A/B/1+2)
				X,Y;Z(A/B/2)
				X - frequency 1
				Y - frequency 2 (set X=Y to use only one frequency)
				Z - number of parcels needed for signal detection (for ringback and busy)
				A - signal duration
				B - pause duration "
	SYNTAX OCTET STRING (SIZE (0..64))
	
TauDtmfTransferType ::= TEXTUAL-CONVENTION
  STATUS current
  DESCRIPTION ""
  SYNTAX INTEGER  {
  	inband(0), 
  	rfc2833(1), 
  	info(2) }

TauFlashTransferType ::= TEXTUAL-CONVENTION
  STATUS current
  DESCRIPTION ""
  SYNTAX INTEGER  {
  	disabled(0), 
  	rfc2833(1), 
  	info(2) }

TauFaxDirectionType ::= TEXTUAL-CONVENTION
  STATUS current
  DESCRIPTION ""
  SYNTAX INTEGER  {
  	both(0), 
  	caller(1), 
  	callee(2), 
  	none(3) }

TauFaxTransferType ::= TEXTUAL-CONVENTION
  STATUS current
  DESCRIPTION ""
  SYNTAX INTEGER  {
  	g711a(0), 
  	g711u(1), 
  	t38(2) }	

TauFaxTransferSlaveType ::= TEXTUAL-CONVENTION
  STATUS current
  DESCRIPTION ""
  SYNTAX INTEGER  {
  	g711a(0), 
  	g711u(1), 
  	t38(2), 
  	none(3) }	

TauModemTransferType ::= TEXTUAL-CONVENTION
  STATUS current
  DESCRIPTION ""
  SYNTAX INTEGER  {
  	g711aVbd(0), 
  	g711uVbd(1), 
  	g711aRfc3108(2), 
  	g711uRfc3108(3), 
  	off(4), 
  	g711aNse(5), 
  	g711uNse(6) }	

TauVoiceModeType ::= TEXTUAL-CONVENTION
  STATUS current
  DESCRIPTION ""
  SYNTAX INTEGER  {
  	fixed(0), 
  	adaptive(1) }	

TauvoiceDeletionModeType ::= TEXTUAL-CONVENTION
  STATUS current
  DESCRIPTION ""
  SYNTAX INTEGER  {
  	hard(0), 
  	soft(1) }
  	
TauTrapVersion ::= TEXTUAL-CONVENTION
  STATUS current
  DESCRIPTION ""
  SYNTAX INTEGER  {
  	v1(1), 
  	v2(2) }
  	
TauMegacoTrapVersion ::= TEXTUAL-CONVENTION
  STATUS current
  DESCRIPTION ""
  SYNTAX INTEGER  {
  	inform(0),
  	trapV1(1), 
  	trapV2(2) }  
  	
TauUserViewType ::= TEXTUAL-CONVENTION
  STATUS current
  DESCRIPTION ""
  SYNTAX INTEGER  {
  	readOnly(1), 
  	readWrite(2) } 

FxoGroupBusyType ::= TEXTUAL-CONVENTION
	STATUS current
	DESCRIPTION ""
	SYNTAX INTEGER {
		clearOnBusy(0),
		waitFirstFree(1) }

FxsNetworkAutoupdateSourceType ::= TEXTUAL-CONVENTION
	STATUS		current
	DESCRIPTION	""
	SYNTAX		INTEGER {
		dhcp(0),
		dhcpVlan1(1),
		dhcpVlan2(2),
		dhcpVlan3(3),
		noDhcp(4)
	}
	
SipLogLevel ::= TEXTUAL-CONVENTION
	STATUS current
	DESCRIPTION ""
	SYNTAX INTEGER {
		none(-1),
		fatalErrors(0),
		criticalErrors(1),
		nonCriticalErrors(2),
		warnings(3),
		verbose1(4),
		signalProtocol(5),
		verbose2(6),
		mediaProtocol(7),
		verobse3(8),
		everything(9) }
		
H323LogLevel ::= TEXTUAL-CONVENTION
	STATUS current
	DESCRIPTION ""
	SYNTAX INTEGER {
		none(0),
		errors(1),
		warnings(2),
		info(3),
		debugA(4),
		debugB(5),
		debugC(6) }
		
VapiLibLogLevel ::= TEXTUAL-CONVENTION
	STATUS current
	DESCRIPTION ""
	SYNTAX INTEGER {
		none(0),
		api(1),
		apiPacket(2),
		vapiInfo(3),
		vapiGtlInfo(4),
		vapiUt(5),
		allInfo(6) }
		
VapiAppLogLevel ::= TEXTUAL-CONVENTION
	STATUS current
	DESCRIPTION ""
	SYNTAX INTEGER {
		none(5),
		warnings(4),
		packet(3),
		debug(2),
		info(1) }
		
FxsPortTestStatus ::= TEXTUAL-CONVENTION
  STATUS current
  DESCRIPTION "TAU-SIP 2.7"
  SYNTAX INTEGER  {
	idle(0),
	requested(1),
	completed(2),
	disabled(255) }
	
FxsPortTestFlag ::= TEXTUAL-CONVENTION
  STATUS current
  DESCRIPTION "TAU-SIP 2.7"
  SYNTAX INTEGER  {
	unknown(-1),
	ok(0),
	overheat(1),
	leakageCurrent(2),
	resistanceNotMeasured(3),
	capacitanceNotMeasured(4),
	testingUnavailable(5),
	testFailure(255) }
	
KeepAliveMode ::= TEXTUAL-CONVENTION
  STATUS current
  DESCRIPTION "TAU-SIP 2.7"
  SYNTAX INTEGER  {
	off(0),
	options(1),
	notify(2),
	clrf(3) }
	
ConferenceMode ::= TEXTUAL-CONVENTION
  STATUS current
  DESCRIPTION "TAU-SIP 2.8"
  SYNTAX INTEGER  {
	local(0),
	remote(1) }
	
GroupRegistrationState ::= TEXTUAL-CONVENTION
  STATUS current
  DESCRIPTION "TAU-SIP 2.7"
  SYNTAX INTEGER  {
	off(0),
	ok(1),
	failed(2) }
	
FirewallProtocol ::= TEXTUAL-CONVENTION
  STATUS current
  DESCRIPTION "TAU-SIP 2.7"
  SYNTAX INTEGER  {
			-- to config file
	any(0), -- any
	udp(1), -- UDP
	tcp(2), -- TCP
	icmp(3) -- ICMP
	}
	
TypeOfMessageICMP ::= TEXTUAL-CONVENTION
  STATUS current
  DESCRIPTION "TAU-SIP 2.7"
  SYNTAX INTEGER  {
	any(0), -- any
	echoReply(1), -- echo-reply
	destinationUnreachable(2), -- destination-unreachable
	networkUnreachable(3), -- network-unreachable
	hostUnreachable(4), -- host-unreachable
	protocolUnreachable(5), -- protocol-unreachable
	portUnreachable(6), -- port-unreachable
	fragmentationNeeded(7), -- fragmentation-needed
	sourceRouteFailed(8), -- source-route-failed
	networkUnknown(9), -- network-unknown
	hostUnknown(10), -- host-unknown
	networkProhibited(11), -- network-prohibited
	hostProhibited(12), -- host-prohibited
	tosNetworkUnreachable(13), -- TOS-network-unreachable
	tosHostUnreachable(14), -- TOS-host-unreachable
	communicationProhibited(15), -- communication-prohibited
	hostPrecedenceViolation(16), -- host-precedence-violation
	precedenceCutoff(17), -- precedence-cutoff
	sourceQuench(18), -- source-quench
	redirect(19), -- redirect
	networkRedirect(20), -- network-redirect
	hostRedirect(21), -- host-redirect
	tosNetworkRedirect(22), -- TOS-network-redirect
	tosHostRedirect(23), -- TOS-host-redirect
	echoRequest(24), -- echo-request
	routerAdvertisement(25), -- router-advertisement
	routerSolicitation(26), -- router-solicitation
	timeExceeded(27), -- time-exceeded
	ttlZeroDuringTransit(28), -- ttl-zero-during-transit
	ttlZeroDuringReassembly(29), -- ttl-zero-during-reassembly
	parameterProblem(30), -- parameter-problem
	ipHeaderBad(31), -- ip-header-bad
	requiredOptionMissing(32), -- required-option-missing
	timestampRequest(33), -- timestamp-request
	timestampReply(34), -- timestamp-reply
	addressMaskRequest(35), -- address-mask-request
	addressMaskReply(36) -- address-mask-reply
  }
  
FirewallTarget ::= TEXTUAL-CONVENTION
  STATUS current
  DESCRIPTION "TAU-SIP 2.7"
  SYNTAX INTEGER  {
			-- to config file
	drop(0), -- DROP
	accept(1), -- ACCEPT
	reject(2) -- REJECT
	}

ReversalPolarityAction ::= TEXTUAL-CONVENTION
  STATUS current
  DESCRIPTION "TAU-SIP 2.9"
  SYNTAX INTEGER  {
	ignore(0), -- Ignore polarity reversal
	release(1), -- Release after polarity reversal detection
	answer(2) -- Answer after polarity reversal detection
	}
	
CallLimitType ::= TEXTUAL-CONVENTION
  STATUS current
  DESCRIPTION "TAU-SIP 2.9"
  SYNTAX INTEGER  {
	proxyGk(0),
	host(1)
	}
	
PowerMode ::= TEXTUAL-CONVENTION
  STATUS current
  DESCRIPTION "TAU-SIP 2.9. added for TAU-32M-revB (TAU-32M_1v5)"
  SYNTAX INTEGER  {
	normal(0), -- fans off, lowLineVoltage
	extendedRange(1) -- fans enabled, normalLineVoltage
	}
	
DRSubscriberProfilesType ::= TEXTUAL-CONVENTION
  STATUS current
  DESCRIPTION "TAU-SIP 2.9
    set 01 = 00000001 to enable Profile1
    set 03 = 00000011 to enable Profile2 and Profile1
	set 80 = 10000000 to enable Profile8"
  SYNTAX OCTET STRING (SIZE(1))	

PstnActivityType ::= TEXTUAL-CONVENTION
  STATUS current
  DESCRIPTION "TAU-SIP 2.9"
  SYNTAX INTEGER  {
	off(0),
	releaseAtPstnReversalPolarityDetection(1),
	answerAtPstnReversalPolarityDetection(2),
	pstnAnswerDetection(3) }
	
IMSMode ::= TEXTUAL-CONVENTION
  STATUS current
  DESCRIPTION "IMS notify mode TAU-SIP 2.10"
  SYNTAX INTEGER  {
	off(0),
	implicit(1),
	explicit(2) }
	
AutoupdateProtocolType ::= TEXTUAL-CONVENTION
  STATUS current
  DESCRIPTION "TAU-SIP 2.12"
  SYNTAX INTEGER  {
    tftp(0),
    ftp(1),
    http(2),
    https(3) }
    
SipProfileChangeoverType ::= TEXTUAL-CONVENTION
  STATUS current
  DESCRIPTION "TAU-SIP 2.12"
  SYNTAX INTEGER  {
    changeoverOnFailureOfInviteOrRegisterRequest(0),
    changeoverOnFailureOfRegisterRequest(1) }
    
DevPowerType ::= TEXTUAL-CONVENTION
  STATUS current
  DESCRIPTION "Power type. TAU-SIP 2.13"
  SYNTAX INTEGER {
	ac(1),
	dc(2)
  }

-- main pbx properties

    fxsDevName OBJECT-TYPE
	SYNTAX		DisplayString (SIZE (0..255))
	MAX-ACCESS	read-only
	STATUS		current
	DESCRIPTION
		"PBX name 'fxs72'"
	::= { fxs72 1 }

    fxsDevType OBJECT-TYPE
	SYNTAX		DevTypeString
	MAX-ACCESS	read-only
	STATUS		current
	DESCRIPTION
		"device type"
	::= { fxs72 2 }

    fxsDevCfgBuild OBJECT-TYPE
	SYNTAX		DisplayString (SIZE (0..255))
	MAX-ACCESS	read-only
	STATUS		current
	DESCRIPTION
		"os build string: compiling data and other info"
	::= { fxs72 3 }

    fxsFreeSpace OBJECT-TYPE
	SYNTAX		DisplayString
	MAX-ACCESS	read-only
	STATUS		current
	DESCRIPTION
		"percent of free blocks on flash disk"
	::= { fxs72 4 }

    fxsFreeRam OBJECT-TYPE
	SYNTAX		DisplayString
	MAX-ACCESS	read-only
	STATUS		current
	DESCRIPTION
		"free RAM (bytes)"
	::= { fxs72 5 }
	
	fxsSSwStatus  OBJECT-TYPE
	SYNTAX		SSwStatusConv
	MAX-ACCESS	read-only
	STATUS		current
	DESCRIPTION
		"Softswitch status"
	::= { fxs72 6 }
	
	fxsSSwStatusTime  OBJECT-TYPE
	SYNTAX		TimeTicks
	MAX-ACCESS	read-only
	STATUS		current
	DESCRIPTION
		"How long in current state"
	::= { fxs72 7 }
	
	fxsCpuUsage  OBJECT-TYPE
	SYNTAX		DisplayString
	MAX-ACCESS	read-only
	STATUS		current
	DESCRIPTION
		"Total CPU usage (%)"
	::= { fxs72 8 }
	
fxsMonitoring OBJECT IDENTIFIER ::= { fxs72 10 }

    fxsMonitoringVMode OBJECT-TYPE
		SYNTAX		VoltageMode
		MAX-ACCESS	read-only
		STATUS		current
		DESCRIPTION
			" "
		::= { fxsMonitoring 1 }
	
    fxsMonitoringVBat OBJECT-TYPE
		SYNTAX		Integer32
		UNITS		"V"
		MAX-ACCESS	read-only
		STATUS		current
		DESCRIPTION
			" "
		::= { fxsMonitoring 2 }
	
	fxsMonitoringVRing1 OBJECT-TYPE
		SYNTAX		Integer32
		UNITS		"V"
		MAX-ACCESS	read-only
		STATUS		current
		DESCRIPTION
			" "
		::= { fxsMonitoring 3 }
		
	fxsMonitoringVRing2 OBJECT-TYPE
		SYNTAX		Integer32
		UNITS		"V"
		MAX-ACCESS	read-only
		STATUS		current
		DESCRIPTION
			" "
		::= { fxsMonitoring 4 }
		
	fxsMonitoringTemp1 OBJECT-TYPE
		SYNTAX		Integer32
		UNITS		"oC"
		MAX-ACCESS	read-only
		STATUS		current
		DESCRIPTION
			" "
		::= { fxsMonitoring 5 }
		
	fxsMonitoringTemp2 OBJECT-TYPE
		SYNTAX		Integer32
		UNITS		"oC"
		MAX-ACCESS	read-only
		STATUS		current
		DESCRIPTION
			" "
		::= { fxsMonitoring 6 }
		
	fxsMonitoringTemp3 OBJECT-TYPE
		SYNTAX		Integer32
		UNITS		"oC"
		MAX-ACCESS	read-only
		STATUS		current
		DESCRIPTION
			" "
		::= { fxsMonitoring 7 }
	
	fxsMonitoringTemp4 OBJECT-TYPE
		SYNTAX		Integer32
		UNITS		"oC"
		MAX-ACCESS	read-only
		STATUS		current
		DESCRIPTION
			" "
		::= { fxsMonitoring 8 }
		
	fxsMonitoringFanState OBJECT-TYPE
		SYNTAX		FXSFanState
		MAX-ACCESS	read-only
		STATUS		current
		DESCRIPTION
			" "
		::= { fxsMonitoring 9 }
		
	fxsMonitoringFan1Rotate OBJECT-TYPE
		SYNTAX		BoolValue
		MAX-ACCESS	read-only
		STATUS		current
		DESCRIPTION
			" "
		::= { fxsMonitoring 10 }
		
	fxsMonitoringFan2Rotate OBJECT-TYPE
		SYNTAX		BoolValue
		MAX-ACCESS	read-only
		STATUS		current
		DESCRIPTION
			" "
		::= { fxsMonitoring 11 }
		
	fxsMonitoringSubCooling OBJECT-TYPE
		SYNTAX		Integer32
		MAX-ACCESS	read-only
		STATUS		current
		DESCRIPTION
			" "
		::= { fxsMonitoring 12 }
		
	fxsMonitoringVinput OBJECT-TYPE
		SYNTAX		Integer32
		UNITS		"V"
		MAX-ACCESS	read-only
		STATUS		current
		DESCRIPTION
			" added for TAU-32M "
		::= { fxsMonitoring 13 }
		
	fxsMonitoringDevicePower OBJECT-TYPE
		SYNTAX     DevPowerType
		MAX-ACCESS read-only
		STATUS     current
		DESCRIPTION "Power: AC, DC"
		::= { fxsMonitoring 14 }

fxsPortsMIBBoundary  OBJECT-TYPE
			SYNTAX     Integer32
			MAX-ACCESS read-only
			STATUS     current
			DESCRIPTION "Dummy object to prevent GETNEXT request from poking into neighbor table."
			::= { fxs72 11 }

fxsPorts OBJECT IDENTIFIER ::= { fxs72 12 }

	fxsPortsMonitoringTable OBJECT-TYPE
	SYNTAX                SEQUENCE OF FxsPortsMonitoringEntry
	MAX-ACCESS        not-accessible
	STATUS                current
	DESCRIPTION " "
	::= { fxsPorts 1 }

		fxsPortsMonitoringEntry OBJECT-TYPE
		SYNTAX		FxsPortsMonitoringEntry
		MAX-ACCESS	not-accessible
		STATUS		current
		DESCRIPTION " "
		INDEX { fxsPortNumber }
		::= { fxsPortsMonitoringTable 1 }

		FxsPortsMonitoringEntry ::= SEQUENCE {
			fxsPortNumber		Integer32,
			fxsPortPhoneNumber	DisplayString,
			fxsPortState		FxsPortState,
			fxsPortUserName 	DisplayString,
			fxsPortTalkingNum	DisplayString,
			fxsPortTalkingStartTime	DisplayString,
			fxsPortSipConnected DisplayString,
			fxsPortH323Connected DisplayString,
			fxsPortSipConnecteNext DisplayString,
			fxsPortSipConnecteState SipConnectState,
			fxsPortSipConnectHost DisplayString }
			
		
		fxsPortNumber  OBJECT-TYPE
			SYNTAX     Integer32 (1..72)
			MAX-ACCESS not-accessible
			STATUS     current
			DESCRIPTION "fxs port number
							TAU-SIP"
			::= { fxsPortsMonitoringEntry 1 }
		
		fxsPortPhoneNumber  OBJECT-TYPE
			SYNTAX     DisplayString
			MAX-ACCESS read-only
			STATUS     current
			DESCRIPTION "fxs port phone number
							TAU-SIP"
			::= { fxsPortsMonitoringEntry 2 }
							
		fxsPortState  OBJECT-TYPE
			SYNTAX     FxsPortState
			MAX-ACCESS read-only
			STATUS     current
			DESCRIPTION "fxs port state
							TAU-SIP"
			::= { fxsPortsMonitoringEntry 3 }
			
		fxsPortUserName  OBJECT-TYPE
			SYNTAX     DisplayString
			MAX-ACCESS read-only
			STATUS     current
			DESCRIPTION "fxs port user name
							TAU-SIP"
			::= { fxsPortsMonitoringEntry 4 }
			
		fxsPortTalkingNum  OBJECT-TYPE
			SYNTAX     DisplayString
			MAX-ACCESS read-only
			STATUS     current
			DESCRIPTION "Current phone number of remote party
							TAU-SIP"
			::= { fxsPortsMonitoringEntry 5 }
			
		fxsPortTalkingStartTime  OBJECT-TYPE
			SYNTAX     DisplayString
			MAX-ACCESS read-only
			STATUS     current
			DESCRIPTION "start talking time
							TAU-SIP"
			::= { fxsPortsMonitoringEntry 6 }
			
		fxsPortSipConnected  OBJECT-TYPE
			SYNTAX     DisplayString
			MAX-ACCESS read-only
			STATUS     current
			DESCRIPTION "time of last sip connect
							TAU-SIP"
			::= { fxsPortsMonitoringEntry 7 }
			
		fxsPortH323Connected  OBJECT-TYPE
			SYNTAX     DisplayString
			MAX-ACCESS read-only
			STATUS     current
			DESCRIPTION "time since h323 connect
							TAU-SIP"
			::= { fxsPortsMonitoringEntry 8 }
			
		fxsPortSipConnecteNext  OBJECT-TYPE
			SYNTAX     DisplayString
			MAX-ACCESS read-only
			STATUS     current
			DESCRIPTION "time of next sip connect
							TAU-SIP"
			::= { fxsPortsMonitoringEntry 9 }
			
		fxsPortSipConnecteState  OBJECT-TYPE
			SYNTAX     SipConnectState
			MAX-ACCESS read-only
			STATUS     current
			DESCRIPTION "sip connect state
							TAU-SIP"
			::= { fxsPortsMonitoringEntry 10 }
			
		fxsPortSipConnectHost  OBJECT-TYPE
			SYNTAX     DisplayString
			MAX-ACCESS read-only
			STATUS     current
			DESCRIPTION "sip connect host. 
							TAU-SIP 2.7"
			::= { fxsPortsMonitoringEntry 11 }
			
			
	fxsPortsConfigTable OBJECT-TYPE
	SYNTAX                SEQUENCE OF FxsPortsConfigEntry
	MAX-ACCESS        not-accessible
	STATUS                current
	DESCRIPTION " "
	::= { fxsPorts 2 }

		fxsPortsConfigEntry OBJECT-TYPE
		SYNTAX		FxsPortsConfigEntry
		MAX-ACCESS	not-accessible
		STATUS		current
		DESCRIPTION " "
		INDEX { fxsPortNumber }
		::= { fxsPortsConfigTable 1 }

		FxsPortsConfigEntry ::= SEQUENCE {
			--fxsPortNumber		Integer32, 
			fxsPortConfigPhone		DisplayString,
			fxsPortConfigUserName	DisplayString,
			fxsPortConfigAuthName  	DisplayString,
			fxsPortConfigAuthPass  	DisplayString,
			fxsPortConfigCustom  	TruthValue,
			fxsPortConfigPlaymoh  TruthValue,
			fxsPortConfigAON  FxsAON,
			fxsPortConfigAONHideDate  TruthValue,
			fxsPortConfigAONHideName  TruthValue,
			fxsPortConfigTaxophone  FxsTaxophoneType,
			fxsPortConfigMinFlashtime  Integer32,
			fxsPortConfigMaxFlashtime  Integer32,
			fxsPortConfigGainr  Integer32,
			fxsPortConfigGaint  Integer32,
			fxsPortConfigCategory  Integer32,
			fxsPortConfigCallTransfer  FxsProcessFlashType,
			fxsPortConfigCallWaiting  TruthValue,
			fxsPortConfigHotLine   TruthValue,
			fxsPortConfigHotNumber  DisplayString,
			fxsPortConfigHotTimeout  Integer32,
			fxsPortConfigDisabled  TruthValue,
			fxsPortConfigCtBusy  TruthValue,
			fxsPortConfigCtUnconditional  TruthValue,
			fxsPortConfigCtNoanswer  TruthValue,
			fxsPortConfigCtNumber  DisplayString,
			fxsPortConfigCtTimeout  Integer32,
			fxsPortConfigClir TruthValue,
			fxsPortConfigStopDial TruthValue,
			fxsPortConfigAltNumber  DisplayString,
			fxsPortConfigUseAltNumber TruthValue,
			fxsPortConfigPickUp  DisplayString,
			fxsPortConfigSipPort  Integer32,
			fxsPortConfigCfgPriOverCw TruthValue,
			fxsPortConfigRowStatus RowStatus,
			fxsPortConfigDvoCwEn TruthValue,
			fxsPortConfigDvoCtAttendedEn TruthValue,
			fxsPortConfigDvoCtUnattendedEn TruthValue,
			fxsPortConfigDvoUnconditionalEn TruthValue,
			fxsPortConfigDvoCfBusyEn TruthValue,
			fxsPortConfigDvoCfAnswerEn TruthValue,
			fxsPortConfigDvoCfServiceEn TruthValue,
			fxsPortConfigDvoDoDisturbEn TruthValue,
			fxsPortConfigCtOutofservice TruthValue,
			fxsPortConfigCfuNumber DisplayString,
			fxsPortConfigCfbNumber DisplayString,
			fxsPortConfigCfnrNumber DisplayString,
			fxsPortConfigCfoosNumber DisplayString,
			fxsPortConfigDnd TruthValue,
			fxsPortConfigFxoFlashTime Integer32,
			fxsPortConfigFxoDelTdm Integer32,
			fxsPortConfigFxoRingtdm Integer32,
			fxsPortConfigPstnNumberprefix DisplayString,
			fxsPortConfigPstnNameprefix DisplayString,
			fxsPortConfigUsePstnCid TruthValue,
			fxsPortConfigtdmhotline TruthValue,
			fxsPortConfigtdmhottimeout Integer32,
			fxsPortConfigtdmhotnumber DisplayString,
			fxsPortConfigEnableCpc TruthValue,
			fxsPortConfigCpcTime Integer32,
			fxsPortConfigDontDetectDT TruthValue,
			fxsPortConfigDelayDialingTimeout Integer32,
			fxsPortType DisplayString,
			fxsPortConfigDialing FxoDialingType,
			fxsPortConfigTransmitNumber TruthValue,
			fxsPortConfigDontTransmitPrefix TruthValue,
			fxsPortConfigPortProfileID Integer32,
			fxsPortConfigSipProfileID Integer32,
			fxsPortConfigDialToneDetectionParameters FxsToneParametrs,
			fxsPortConfigRingBackToneDetectionParameters FxsToneParametrs,
			fxsPortConfigBusyToneDetectionParameters FxsToneParametrs,
			fxsPortConfigDtDetectTime Integer32,
			fxsPortConfigDecadePulseTime Integer32,
			fxsPortConfigDecadePauseTime Integer32,
			fxsPortConfigNoOffhookAtRinging TruthValue,
			fxsPortConfigFxoCallBusy TruthValue,
			fxsPortConfigCpcRus Integer32,
			fxsPortConfigReversalPolarityAction ReversalPolarityAction,
			fxsPortConfigPstnActivity PstnActivityType,
			fxsPortConfigPstnRbDetectTimeout Integer32,
			fxsPortConfigDetectFxoLinePresence TruthValue,	
			fxsPortConfigBlockFxoLineInOutgoingDirection TruthValue,
			fxsPortConfigFxoMinLevelDetect Integer32,
			fxsPortConfigUseAltNumberAsContact TruthValue,
			fxsPortConfigModifier Integer32,
			fxsPortConfigMwiDialtone TruthValue
			 }
			
		fxsPortConfigPhone  OBJECT-TYPE
			SYNTAX     DisplayString
			MAX-ACCESS read-write
			STATUS     current
			DESCRIPTION "allowed symbols 0-9A-Za-z*#_+!~$-"
			::= { fxsPortsConfigEntry 1 }	

		fxsPortConfigUserName  OBJECT-TYPE
			SYNTAX     DisplayString
			MAX-ACCESS read-write
			STATUS     current
			DESCRIPTION " "
			::= { fxsPortsConfigEntry 2 }	

		fxsPortConfigAuthName  OBJECT-TYPE
			SYNTAX     DisplayString
			MAX-ACCESS read-write
			STATUS     current
			DESCRIPTION " "
			::= { fxsPortsConfigEntry 3 }	

		fxsPortConfigAuthPass  OBJECT-TYPE
			SYNTAX     DisplayString
			MAX-ACCESS read-write
			STATUS     current
			DESCRIPTION " "
			::= { fxsPortsConfigEntry 4 }	

		fxsPortConfigCustom  OBJECT-TYPE
			SYNTAX     TruthValue
			MAX-ACCESS read-write
			STATUS     current
			DESCRIPTION " "
			::= { fxsPortsConfigEntry 5 }

		fxsPortConfigPlaymoh  OBJECT-TYPE
			SYNTAX     TruthValue
			MAX-ACCESS read-write
			STATUS     current
			DESCRIPTION " "
			::= { fxsPortsConfigEntry 6 }

		fxsPortConfigAON  OBJECT-TYPE
			SYNTAX     FxsAON
			MAX-ACCESS read-write
			STATUS     current
			DESCRIPTION " "
			::= { fxsPortsConfigEntry 7 }

		fxsPortConfigAONHideDate  OBJECT-TYPE
			SYNTAX     TruthValue
			MAX-ACCESS read-write
			STATUS     current
			DESCRIPTION " "
			::= { fxsPortsConfigEntry 8 }
			
		fxsPortConfigAONHideName  OBJECT-TYPE
			SYNTAX     TruthValue
			MAX-ACCESS read-write
			STATUS     current
			DESCRIPTION " "
			::= { fxsPortsConfigEntry 9 }

		fxsPortConfigTaxophone  OBJECT-TYPE
			SYNTAX     FxsTaxophoneType
			MAX-ACCESS read-write
			STATUS     current
			DESCRIPTION " "
			::= { fxsPortsConfigEntry 10 }

		fxsPortConfigMinFlashtime  OBJECT-TYPE
			SYNTAX     Integer32
			MAX-ACCESS read-write
			STATUS     current
			DESCRIPTION "70-2000(from v2.8),1000(to v2.7)"
			::= { fxsPortsConfigEntry 11 }

		fxsPortConfigMaxFlashtime  OBJECT-TYPE
			SYNTAX     Integer32
			MAX-ACCESS read-write
			STATUS     current
			DESCRIPTION "70-2000(from v2.8),1000(to v2.7)"
			::= { fxsPortsConfigEntry 12 }

		fxsPortConfigGainr  OBJECT-TYPE
			SYNTAX     Integer32
			MAX-ACCESS read-write
			STATUS     current
			DESCRIPTION " "
			::= { fxsPortsConfigEntry 13 }

		fxsPortConfigGaint  OBJECT-TYPE
			SYNTAX     Integer32
			MAX-ACCESS read-write
			STATUS     current
			DESCRIPTION " "
			::= { fxsPortsConfigEntry 14 }

		fxsPortConfigCategory  OBJECT-TYPE
			SYNTAX     Integer32
			MAX-ACCESS read-write
			STATUS     current
			DESCRIPTION " "
			::= { fxsPortsConfigEntry 15 }

		fxsPortConfigCallTransfer  OBJECT-TYPE
			SYNTAX     FxsProcessFlashType
			MAX-ACCESS read-write
			STATUS     current
			DESCRIPTION " "
			::= { fxsPortsConfigEntry 16 }

		fxsPortConfigCallWaiting  OBJECT-TYPE
			SYNTAX     TruthValue
			MAX-ACCESS read-write
			STATUS     current
			DESCRIPTION " "
			::= { fxsPortsConfigEntry 17 }

		fxsPortConfigHotLine  OBJECT-TYPE
			SYNTAX     TruthValue
			MAX-ACCESS read-write
			STATUS     current
			DESCRIPTION " "
			::= { fxsPortsConfigEntry 18 }

		fxsPortConfigHotNumber  OBJECT-TYPE
			SYNTAX     DisplayString
			MAX-ACCESS read-write
			STATUS     current
			DESCRIPTION "allowed symbols 0-9A-Za-z*#_+!~$-"
			::= { fxsPortsConfigEntry 19 }

		fxsPortConfigHotTimeout  OBJECT-TYPE
			SYNTAX     Integer32
			MAX-ACCESS read-write
			STATUS     current
			DESCRIPTION " "
			::= { fxsPortsConfigEntry 20 }

		fxsPortConfigDisabled  OBJECT-TYPE
			SYNTAX     TruthValue
			MAX-ACCESS read-write
			STATUS     current
			DESCRIPTION " "
			::= { fxsPortsConfigEntry 21 }

		fxsPortConfigCtBusy  OBJECT-TYPE
			SYNTAX     TruthValue
			MAX-ACCESS read-write
			STATUS     current
			DESCRIPTION " "
			::= { fxsPortsConfigEntry 22 }

		fxsPortConfigCtUnconditional  OBJECT-TYPE
			SYNTAX     TruthValue
			MAX-ACCESS read-write
			STATUS     current
			DESCRIPTION " "
			::= { fxsPortsConfigEntry 23 }
			
		fxsPortConfigCtNoanswer  OBJECT-TYPE
			SYNTAX     TruthValue
			MAX-ACCESS read-write
			STATUS     current
			DESCRIPTION " "
			::= { fxsPortsConfigEntry 24 }

		fxsPortConfigCtNumber  OBJECT-TYPE
			SYNTAX     DisplayString
			MAX-ACCESS read-write
			STATUS     obsolete
			DESCRIPTION "allowed symbols 0-9A-Za-z*#_+!~$-"
			::= { fxsPortsConfigEntry 25 }

		fxsPortConfigCtTimeout  OBJECT-TYPE
			SYNTAX     Integer32
			MAX-ACCESS read-write
			STATUS     current
			DESCRIPTION " "
			::= { fxsPortsConfigEntry 26 }

		fxsPortConfigClir OBJECT-TYPE
			SYNTAX     TruthValue
			MAX-ACCESS read-write
			STATUS     current
			DESCRIPTION " "
			::= { fxsPortsConfigEntry 27 }

		fxsPortConfigStopDial OBJECT-TYPE
			SYNTAX     TruthValue
			MAX-ACCESS read-write
			STATUS     current
			DESCRIPTION " "
			::= { fxsPortsConfigEntry 28 }

		fxsPortConfigAltNumber  OBJECT-TYPE
			SYNTAX     DisplayString
			MAX-ACCESS read-write
			STATUS     current
			DESCRIPTION "allowed symbols 0-9A-Za-z*#_+!~$-"
			::= { fxsPortsConfigEntry 29 }

		fxsPortConfigUseAltNumber OBJECT-TYPE
			SYNTAX     TruthValue
			MAX-ACCESS read-write
			STATUS     current
			DESCRIPTION " "
			::= { fxsPortsConfigEntry 30 }

		fxsPortConfigPickUp  OBJECT-TYPE
			SYNTAX     DisplayString
			MAX-ACCESS read-write
			STATUS     current
			DESCRIPTION " "
			::= { fxsPortsConfigEntry 31 }

		fxsPortConfigSipPort  OBJECT-TYPE
			SYNTAX     Integer32
			MAX-ACCESS read-write
			STATUS     current
			DESCRIPTION " "
			::= { fxsPortsConfigEntry 32 }
			
		fxsPortConfigCfgPriOverCw  OBJECT-TYPE
			SYNTAX     TruthValue
			MAX-ACCESS read-write
			STATUS     current
			DESCRIPTION " "
			::= { fxsPortsConfigEntry 33 }	
			
		fxsPortConfigRowStatus OBJECT-TYPE
			SYNTAX     RowStatus
			MAX-ACCESS read-create
			STATUS     current
			DESCRIPTION " we will save all our fixes when Commit set to 1 "
			::= { fxsPortsConfigEntry 34 }
			
		fxsPortConfigDvoCwEn OBJECT-TYPE
			SYNTAX     TruthValue
			MAX-ACCESS read-write
			STATUS     current
			DESCRIPTION " "
			::= { fxsPortsConfigEntry 35 }
		fxsPortConfigDvoCtAttendedEn OBJECT-TYPE
			SYNTAX     TruthValue
			MAX-ACCESS read-write
			STATUS     current
			DESCRIPTION " "
			::= { fxsPortsConfigEntry 36 }
		fxsPortConfigDvoCtUnattendedEn OBJECT-TYPE
			SYNTAX     TruthValue
			MAX-ACCESS read-write
			STATUS     current
			DESCRIPTION " "
			::= { fxsPortsConfigEntry 37 }
		fxsPortConfigDvoUnconditionalEn OBJECT-TYPE
			SYNTAX     TruthValue
			MAX-ACCESS read-write
			STATUS     current
			DESCRIPTION " "
			::= { fxsPortsConfigEntry 38 }
		fxsPortConfigDvoCfBusyEn OBJECT-TYPE
			SYNTAX     TruthValue
			MAX-ACCESS read-write
			STATUS     current
			DESCRIPTION " "
			::= { fxsPortsConfigEntry 39 }
		fxsPortConfigDvoCfAnswerEn OBJECT-TYPE
			SYNTAX     TruthValue
			MAX-ACCESS read-write
			STATUS     current
			DESCRIPTION " "
			::= { fxsPortsConfigEntry 40 }
		fxsPortConfigDvoCfServiceEn OBJECT-TYPE
			SYNTAX     TruthValue
			MAX-ACCESS read-write
			STATUS     current
			DESCRIPTION " "
			::= { fxsPortsConfigEntry 41 }
		fxsPortConfigDvoDoDisturbEn OBJECT-TYPE
			SYNTAX     TruthValue
			MAX-ACCESS read-write
			STATUS     current
			DESCRIPTION " "
			::= { fxsPortsConfigEntry 42 }
		fxsPortConfigCtOutofservice OBJECT-TYPE
			SYNTAX     TruthValue
			MAX-ACCESS read-write
			STATUS     current
			DESCRIPTION " "
			::= { fxsPortsConfigEntry 43 }
		fxsPortConfigCfuNumber OBJECT-TYPE
			SYNTAX     DisplayString
			MAX-ACCESS read-write
			STATUS     current
			DESCRIPTION "allowed symbols 0-9A-Za-z*#_+!~$-"
			::= { fxsPortsConfigEntry 44 }
		fxsPortConfigCfbNumber OBJECT-TYPE
			SYNTAX     DisplayString
			MAX-ACCESS read-write
			STATUS     current
			DESCRIPTION "allowed symbols 0-9A-Za-z*#_+!~$-"
			::= { fxsPortsConfigEntry 45 }
		fxsPortConfigCfnrNumber OBJECT-TYPE
			SYNTAX     DisplayString
			MAX-ACCESS read-write
			STATUS     current
			DESCRIPTION "allowed symbols 0-9A-Za-z*#_+!~$-"
			::= { fxsPortsConfigEntry 46 }
		fxsPortConfigCfoosNumber OBJECT-TYPE
			SYNTAX     DisplayString
			MAX-ACCESS read-write
			STATUS     current
			DESCRIPTION "allowed symbols 0-9A-Za-z*#_+!~$-"
			::= { fxsPortsConfigEntry 47 }
		fxsPortConfigDnd OBJECT-TYPE
			SYNTAX     TruthValue
			MAX-ACCESS read-write
			STATUS     current
			DESCRIPTION " "
			::= { fxsPortsConfigEntry 48 }
			
		fxsPortConfigFxoFlashTime OBJECT-TYPE
			SYNTAX     Integer32
			MAX-ACCESS read-write
			STATUS     current
			DESCRIPTION "70 1000 def 300 ms"
			::= { fxsPortsConfigEntry 49 }
			
		fxsPortConfigFxoDelTdm OBJECT-TYPE
			SYNTAX     Integer32
			MAX-ACCESS read-write
			STATUS     current
			DESCRIPTION "100 1000 def 200 ms"
			::= { fxsPortsConfigEntry 50 }
			
		fxsPortConfigFxoRingtdm OBJECT-TYPE
			SYNTAX     Integer32
			MAX-ACCESS read-write
			STATUS     current
			DESCRIPTION "2 10 def 2"
			::= { fxsPortsConfigEntry 51 }
			
		fxsPortConfigPstnNumberprefix OBJECT-TYPE
			SYNTAX     DisplayString
			MAX-ACCESS read-write
			STATUS     current
			DESCRIPTION "max len 20. allowed symbols 0-9A-Za-z*#_+!~$-"
			::= { fxsPortsConfigEntry 52 }
			
		fxsPortConfigPstnNameprefix OBJECT-TYPE
			SYNTAX     DisplayString
			MAX-ACCESS read-write
			STATUS     current
			DESCRIPTION "max len 20"
			::= { fxsPortsConfigEntry 53 }
			
		fxsPortConfigUsePstnCid OBJECT-TYPE
			SYNTAX     TruthValue
			MAX-ACCESS read-write
			STATUS     current
			DESCRIPTION " "
			::= { fxsPortsConfigEntry 54 }
			
		fxsPortConfigtdmhotline OBJECT-TYPE
			SYNTAX     TruthValue
			MAX-ACCESS read-write
			STATUS     current
			DESCRIPTION " "
			::= { fxsPortsConfigEntry 55 }
			
		fxsPortConfigtdmhottimeout OBJECT-TYPE
			SYNTAX     Integer32
			MAX-ACCESS read-write
			STATUS     current
			DESCRIPTION "0 300 def 15. FXO only"
			::= { fxsPortsConfigEntry 56 }
			
		fxsPortConfigtdmhotnumber OBJECT-TYPE
			SYNTAX     DisplayString
			MAX-ACCESS read-write
			STATUS     current
			DESCRIPTION "max len 30. allowed symbols 0-9A-Za-z*#_+!~$-"
			::= { fxsPortsConfigEntry 57 }
			
		fxsPortConfigEnableCpc OBJECT-TYPE
			SYNTAX     TruthValue
			MAX-ACCESS read-write
			STATUS     current
			DESCRIPTION "def false"
			::= { fxsPortsConfigEntry 58 }
			
		fxsPortConfigCpcTime OBJECT-TYPE
			SYNTAX     Integer32
			MAX-ACCESS read-write
			STATUS     current
			DESCRIPTION "200-600 ms def 200"
			::= { fxsPortsConfigEntry 59 }
			
		fxsPortConfigDontDetectDT OBJECT-TYPE
			SYNTAX     TruthValue
			MAX-ACCESS read-write
			STATUS     current
			DESCRIPTION "def false"
			::= { fxsPortsConfigEntry 60 }
			
        fxsPortConfigDelayDialingTimeout OBJECT-TYPE
			SYNTAX     Integer32
			MAX-ACCESS read-write
			STATUS     current
			DESCRIPTION "0-10 ms def 2"
			::= { fxsPortsConfigEntry 61 }
			
		fxsPortType OBJECT-TYPE
			SYNTAX     DisplayString
			MAX-ACCESS read-only
			STATUS     current
			DESCRIPTION "FXS, FXO, NONE"
			::= { fxsPortsConfigEntry 62 }
			
		fxsPortConfigDialing  OBJECT-TYPE
			SYNTAX     FxoDialingType
			MAX-ACCESS read-write
			STATUS     current
			DESCRIPTION " "
			::= { fxsPortsConfigEntry 63 }
			
		fxsPortConfigTransmitNumber  OBJECT-TYPE
			SYNTAX     TruthValue
			MAX-ACCESS read-write
			STATUS     current
			DESCRIPTION " "
			::= { fxsPortsConfigEntry 64 }
			
		fxsPortConfigDontTransmitPrefix OBJECT-TYPE
			SYNTAX     TruthValue
			MAX-ACCESS read-write
			STATUS     current
			DESCRIPTION " "
			::= { fxsPortsConfigEntry 65 }
			
		fxsPortConfigPortProfileID OBJECT-TYPE
			SYNTAX     Integer32
			MAX-ACCESS read-write
			STATUS     current
			DESCRIPTION " "
			::= { fxsPortsConfigEntry 66 }
			
		fxsPortConfigSipProfileID OBJECT-TYPE
			SYNTAX     Integer32
			MAX-ACCESS read-write
			STATUS     current
			DESCRIPTION " "
			::= { fxsPortsConfigEntry 67 }
			
		fxsPortConfigDialToneDetectionParameters OBJECT-TYPE
			SYNTAX     FxsToneParametrs
			MAX-ACCESS read-write
			STATUS     current
			DESCRIPTION "FXO only"
			::= { fxsPortsConfigEntry 68 }
		
		fxsPortConfigRingBackToneDetectionParameters OBJECT-TYPE
			SYNTAX     FxsToneParametrs
			MAX-ACCESS read-write
			STATUS     current
			DESCRIPTION "FXO only"
			::= { fxsPortsConfigEntry 69 }
		
		fxsPortConfigBusyToneDetectionParameters OBJECT-TYPE
			SYNTAX     FxsToneParametrs
			MAX-ACCESS read-write
			STATUS     current
			DESCRIPTION "FXO only"
			::= { fxsPortsConfigEntry 70 }
		
		fxsPortConfigDtDetectTime  OBJECT-TYPE
			SYNTAX     Integer32
			MAX-ACCESS read-write
			STATUS     current
			DESCRIPTION " "
			::= { fxsPortsConfigEntry 71 }
		
		fxsPortConfigDecadePulseTime  OBJECT-TYPE
			SYNTAX     Integer32
			MAX-ACCESS read-write
			STATUS     current
			DESCRIPTION " "
			::= { fxsPortsConfigEntry 72 }
		
		fxsPortConfigDecadePauseTime  OBJECT-TYPE
			SYNTAX     Integer32
			MAX-ACCESS read-write
			STATUS     current
			DESCRIPTION " "
			::= { fxsPortsConfigEntry 73 }
			
		fxsPortConfigNoOffhookAtRinging  OBJECT-TYPE
			SYNTAX     TruthValue
			MAX-ACCESS read-write
			STATUS     current
			DESCRIPTION "only for FXO"
			::= { fxsPortsConfigEntry 74 }
		
		fxsPortConfigFxoCallBusy  OBJECT-TYPE
			SYNTAX     TruthValue
			MAX-ACCESS read-write
			STATUS     current
			DESCRIPTION "only for FXO. Send '503 Service unavailable' on busy (SIP)"
			::= { fxsPortsConfigEntry 75 }
			
		fxsPortConfigCpcRus  OBJECT-TYPE
			SYNTAX     Integer32 (0..10)
			MAX-ACCESS read-write
			STATUS     current
			DESCRIPTION "1..10 or 0 (off)"
			::= { fxsPortsConfigEntry 76 }
			
		fxsPortConfigReversalPolarityAction  OBJECT-TYPE
			SYNTAX     ReversalPolarityAction
			MAX-ACCESS read-write
			STATUS     obsolete
			DESCRIPTION "only for FXO. TAU-SIP 2.9. Deprecated by PstnActivity"
			::= { fxsPortsConfigEntry 77 }
			
		fxsPortConfigPstnActivity  OBJECT-TYPE
			SYNTAX     PstnActivityType
			MAX-ACCESS read-write
			STATUS     current
			DESCRIPTION "only for FXO. TAU-SIP 2.9. pstn_200_at_answer"
			::= { fxsPortsConfigEntry 78 }
			
		fxsPortConfigPstnRbDetectTimeout  OBJECT-TYPE
			SYNTAX     Integer32 (1..60)
			UNITS	   "sec"
			MAX-ACCESS read-write
			STATUS     current
			DESCRIPTION "only for FXO. TAU-SIP 2.9"
			::= { fxsPortsConfigEntry 79 }
			
		fxsPortConfigDetectFxoLinePresence  OBJECT-TYPE
			SYNTAX     TruthValue	
			MAX-ACCESS read-write
			STATUS     current
			DESCRIPTION "only for FXO. TAU-SIP 2.10"
			::= { fxsPortsConfigEntry 80 }
			
		fxsPortConfigBlockFxoLineInOutgoingDirection  OBJECT-TYPE
			SYNTAX     TruthValue	
			MAX-ACCESS read-write
			STATUS     current
			DESCRIPTION "only for FXO. TAU-SIP 2.10"
			::= { fxsPortsConfigEntry 81 }
			
		fxsPortConfigFxoMinLevelDetect  OBJECT-TYPE
			SYNTAX     Integer32
			MAX-ACCESS read-write
			STATUS     current
			DESCRIPTION "Minimum level of detectable signal (dBm): -40..-20 (def -36)
				TAU-SIP 2.10. FXO only"
			::= { fxsPortsConfigEntry 82 }
			
		fxsPortConfigUseAltNumberAsContact  OBJECT-TYPE
			SYNTAX     TruthValue
			MAX-ACCESS read-write
			STATUS     current
			DESCRIPTION "Use alternative number as contact (only for serial groups members)
				TAU-SIP 2.12"
			::= { fxsPortsConfigEntry 83 }

		fxsPortConfigModifier  OBJECT-TYPE
			SYNTAX     Integer32
			MAX-ACCESS read-write
			STATUS     current
			DESCRIPTION "modifierNumber (1..16) at modifiersTable or -1=off
				TAU-SIP 2.12"
			::= { fxsPortsConfigEntry 84 }
			
		fxsPortConfigMwiDialtone  OBJECT-TYPE
			SYNTAX     TruthValue
			MAX-ACCESS read-write
			STATUS     current
			DESCRIPTION "MWI Dialtone
				TAU-SIP 2.13"
			::= { fxsPortsConfigEntry 85 }
		
fxsPortsConfigCommon OBJECT IDENTIFIER ::= { fxsPorts 3 }

		fxsPortConfigCommonPlaymoh  OBJECT-TYPE
			SYNTAX     TruthValue
			MAX-ACCESS read-write
			STATUS     obsolete
			DESCRIPTION " "
			::= { fxsPortsConfigCommon 1 }

		fxsPortConfigCommonAON  OBJECT-TYPE
			SYNTAX     FxsAON
			MAX-ACCESS read-write
			STATUS     obsolete
			DESCRIPTION " "
			::= { fxsPortsConfigCommon 2 }
			
		fxsPortConfigCommonAONHideDate  OBJECT-TYPE
			SYNTAX     TruthValue
			MAX-ACCESS read-write
			STATUS     obsolete
			DESCRIPTION " "
			::= { fxsPortsConfigCommon 3 }
			
		fxsPortConfigCommonAONHideName  OBJECT-TYPE
			SYNTAX     TruthValue
			MAX-ACCESS read-write
			STATUS     obsolete
			DESCRIPTION " "
			::= { fxsPortsConfigCommon 4 }

		fxsPortConfigCommonTaxophone  OBJECT-TYPE
			SYNTAX     FxsTaxophoneType
			MAX-ACCESS read-write
			STATUS     obsolete
			DESCRIPTION " "
			::= { fxsPortsConfigCommon 5 }

		fxsPortConfigCommonMinFlashtime  OBJECT-TYPE
			SYNTAX     Integer32
			MAX-ACCESS read-write
			STATUS     obsolete
			DESCRIPTION " "
			::= { fxsPortsConfigCommon 6 }

		fxsPortConfigCommonMaxFlashtime  OBJECT-TYPE
			SYNTAX     Integer32
			MAX-ACCESS read-write
			STATUS     obsolete
			DESCRIPTION " "
			::= { fxsPortsConfigCommon 7 }

		fxsPortConfigCommonGainr  OBJECT-TYPE
			SYNTAX     Integer32
			MAX-ACCESS read-write
			STATUS     obsolete
			DESCRIPTION " "
			::= { fxsPortsConfigCommon 8 }

		fxsPortConfigCommonGaint  OBJECT-TYPE
			SYNTAX     Integer32
			MAX-ACCESS read-write
			STATUS     obsolete
			DESCRIPTION " "
			::= { fxsPortsConfigCommon 9 }

		fxsPortConfigCommonCategory  OBJECT-TYPE
			SYNTAX     Integer32
			MAX-ACCESS read-write
			STATUS     obsolete
			DESCRIPTION " "
			::= { fxsPortsConfigCommon 10 }

		fxsPortConfigCommonCallTransfer  OBJECT-TYPE
			SYNTAX     FxsProcessFlashType
			MAX-ACCESS read-write
			STATUS     obsolete
			DESCRIPTION " "
			::= { fxsPortsConfigCommon 11 }

		fxsPortConfigCommonCallWaiting  OBJECT-TYPE
			SYNTAX     TruthValue
			MAX-ACCESS read-write
			STATUS     obsolete
			DESCRIPTION " "
			::= { fxsPortsConfigCommon 12 }

		--fxsPortConfigCommonDisabled  OBJECT-TYPE
		--	SYNTAX     TruthValue
		--	MAX-ACCESS read-write
		--	STATUS     obsolete
		--	DESCRIPTION " "
		--	::= { fxsPortsConfigCommon 13 }
			
		fxsPortConfigCommonCfgPriOverCw OBJECT-TYPE
			SYNTAX     TruthValue
			MAX-ACCESS read-write
			STATUS     obsolete
			DESCRIPTION " "
			::= { fxsPortsConfigCommon 13 }
			
		fxsPortConfigCommonFxoFlashTime OBJECT-TYPE
			SYNTAX     Integer32
			MAX-ACCESS read-write
			STATUS     obsolete
			DESCRIPTION "70 1000 def 300 ms"
			::= { fxsPortsConfigCommon 14 }
			
		fxsPortConfigCommonFxoDelTdm OBJECT-TYPE
			SYNTAX     Integer32
			MAX-ACCESS read-write
			STATUS     obsolete
			DESCRIPTION "100 1000 def 200 ms"
			::= { fxsPortsConfigCommon 15 }
			
		fxsPortConfigCommonFxoRingtdm OBJECT-TYPE
			SYNTAX     Integer32
			MAX-ACCESS read-write
			STATUS     obsolete
			DESCRIPTION "2 10 def 2"
			::= { fxsPortsConfigCommon 16 }
			
		fxsPortConfigCommonPstnNumberprefix OBJECT-TYPE
			SYNTAX     DisplayString
			MAX-ACCESS read-write
			STATUS     obsolete
			DESCRIPTION "max len 20 "
			::= { fxsPortsConfigCommon 17 }
			
		fxsPortConfigCommonPstnNameprefix OBJECT-TYPE
			SYNTAX     DisplayString
			MAX-ACCESS read-write
			STATUS     obsolete
			DESCRIPTION "max len 20 "
			::= { fxsPortsConfigCommon 18 }
			
		fxsPortConfigCommonUsePstnCid OBJECT-TYPE
			SYNTAX     TruthValue
			MAX-ACCESS read-write
			STATUS     obsolete
			DESCRIPTION " "
			::= { fxsPortsConfigCommon 19 }
			
		fxsPortConfigCommonEnableCpc OBJECT-TYPE
			SYNTAX     TruthValue
			MAX-ACCESS read-write
			STATUS     obsolete
			DESCRIPTION " "
			::= { fxsPortsConfigCommon 20 }
			
		fxsPortConfigCommonCpcTime OBJECT-TYPE
			SYNTAX     TruthValue
			MAX-ACCESS read-write
			STATUS     obsolete
			DESCRIPTION " "
			::= { fxsPortsConfigCommon 21 }
			
		fxsPortConfigCommonDontDetectDT OBJECT-TYPE
			SYNTAX     TruthValue
			MAX-ACCESS read-write
			STATUS     obsolete
			DESCRIPTION "def false"
			::= { fxsPortsConfigCommon 22 }
			
        fxsPortConfigCommonDelayDialingTimeout OBJECT-TYPE
			SYNTAX     Integer32
			MAX-ACCESS read-write
			STATUS     obsolete
			DESCRIPTION "0-10 ms def 2"
			::= { fxsPortsConfigCommon 23 }
			
		fxsPortConfigCommonDialing  OBJECT-TYPE
			SYNTAX     FxoDialingType
			MAX-ACCESS read-write
			STATUS     obsolete
			DESCRIPTION " "
			::= { fxsPortsConfigCommon 24 }
			
		fxsPortConfigCommonTransmitNumber  OBJECT-TYPE
			SYNTAX     TruthValue
			MAX-ACCESS read-write
			STATUS     obsolete
			DESCRIPTION " "
			::= { fxsPortsConfigCommon 25 }
			
		fxsPortConfigCommonDontTransmitPrefix OBJECT-TYPE
			SYNTAX     TruthValue
			MAX-ACCESS read-write
			STATUS     obsolete
			DESCRIPTION " "
			::= { fxsPortsConfigCommon 26 }
			
		

	megacoPortsMonitoringTable OBJECT-TYPE
	SYNTAX				SEQUENCE OF MegacoPortsMonitoringEntry
	MAX-ACCESS        	not-accessible
	STATUS         		current
	DESCRIPTION "TAU-MEGACO RC03"
	::= { fxsPorts 4 }

		megacoPortsMonitoringEntry OBJECT-TYPE
		SYNTAX		MegacoPortsMonitoringEntry
		MAX-ACCESS	not-accessible
		STATUS		current
		DESCRIPTION " "
		INDEX { megacoPortNumber }
		::= { megacoPortsMonitoringTable 1 }

		MegacoPortsMonitoringEntry ::= SEQUENCE {
			megacoPortNumber			Integer32,
			megacoPortTerminationID		DisplayString,
			megacoPortComments			DisplayString,
			megacoPortState				PortMegacoState,
			megacoPortStateStartTime	DisplayString,
			megacoPortStateDuration		DisplayString,
			megacoPortJitter 			PortMegacoJitter,
			megacoPortTelNo				DisplayString }
			
		
		megacoPortNumber  OBJECT-TYPE
			SYNTAX     Integer32 (1..72)
			MAX-ACCESS not-accessible
			STATUS     current
			DESCRIPTION "megaco port number"
			::= { megacoPortsMonitoringEntry 1 }
		
		megacoPortTerminationID  OBJECT-TYPE
			SYNTAX     DisplayString
			MAX-ACCESS read-only
			STATUS     current
			DESCRIPTION "megaco port Termination ID (from cfg)"
			::= { megacoPortsMonitoringEntry 2 }
			
		megacoPortComments  OBJECT-TYPE
			SYNTAX     DisplayString
			MAX-ACCESS read-only
			STATUS     current
			DESCRIPTION "megaco port Comments (from cfg)"
			::= { megacoPortsMonitoringEntry 3 }
							
		megacoPortState  OBJECT-TYPE
			SYNTAX     PortMegacoState
			MAX-ACCESS read-only
			STATUS     current
			DESCRIPTION "megaco port state"
			::= { megacoPortsMonitoringEntry 4 }
			
		megacoPortStateStartTime  OBJECT-TYPE
			SYNTAX     DisplayString
			MAX-ACCESS read-only
			STATUS     current
			DESCRIPTION "current state start time"
			::= { megacoPortsMonitoringEntry 5 }
			
		megacoPortStateDuration  OBJECT-TYPE
			SYNTAX     DisplayString
			MAX-ACCESS read-only
			STATUS     current
			DESCRIPTION "or current state duration [DD hh:mm:ss]"
			::= { megacoPortsMonitoringEntry 6 }
			
		megacoPortJitter  OBJECT-TYPE
			SYNTAX     PortMegacoJitter
			MAX-ACCESS read-only
			STATUS     current
			DESCRIPTION "port jitter"
			::= { megacoPortsMonitoringEntry 7 }
			
		megacoPortTelNo  OBJECT-TYPE
			SYNTAX     DisplayString
			MAX-ACCESS read-only
			STATUS     current
			DESCRIPTION "megaco port TelNo (from cfg)"
			::= { megacoPortsMonitoringEntry 8 }

fxsDialMIBBoundary  OBJECT-TYPE
			SYNTAX     Integer32
			MAX-ACCESS read-only
			STATUS     current
			DESCRIPTION "Dummy object to prevent GETNEXT request from poking into neighbor table."
			::= { fxs72 13 }

fxsDial OBJECT IDENTIFIER ::= { fxs72 14 }

fxsDialPlanTable OBJECT-TYPE
	SYNTAX                SEQUENCE OF FxsDialPlanEntry
	MAX-ACCESS        not-accessible
	STATUS                obsolete
	DESCRIPTION " "
	::= { fxsDial 1 }

		fxsDialPlanEntry OBJECT-TYPE
		SYNTAX		FxsDialPlanEntry
		MAX-ACCESS	not-accessible
		STATUS		obsolete
		DESCRIPTION " "
		INDEX { fxsDialPlanNumber }
		::= { fxsDialPlanTable 1 }

		FxsDialPlanEntry ::= SEQUENCE {
			fxsDialPlanHost				DisplayString,
			fxsDialPlanDigits			DisplayString,
			fxsDialPlanTimeout			Integer32,
			fxsDialPlanMinDigits		Integer32,
			fxsDialPlanType				FxsDialPlanType,
			fxsDialPlanAccessMask		DisplayString,
			fxsDialPlanDialtone			TruthValue,
			fxsDialPlanModifier			DisplayString,
			fxsDialPlanNature			FxsDialPlanNatureType,
			fxsDialPlanDelnum			Integer32,
			fxsDialPlanPtime 			Integer32,
			fxsDialRowStatus			RowStatus,
			fxsDialPlanNumber			Integer32
		}

		fxsDialPlanHost  OBJECT-TYPE
			SYNTAX     DisplayString
			MAX-ACCESS read-create
			STATUS     obsolete
			DESCRIPTION " "
			::= { fxsDialPlanEntry 1 }
			
		fxsDialPlanDigits  OBJECT-TYPE
			SYNTAX     DisplayString
			MAX-ACCESS read-create
			STATUS     obsolete
			DESCRIPTION " "
			::= { fxsDialPlanEntry 2 }
			
		fxsDialPlanTimeout  OBJECT-TYPE
			SYNTAX     Integer32
			MAX-ACCESS read-create
			STATUS     obsolete
			DESCRIPTION " "
			::= { fxsDialPlanEntry 3 }
			
		fxsDialPlanMinDigits  OBJECT-TYPE
			SYNTAX     Integer32
			MAX-ACCESS read-create
			STATUS     obsolete
			DESCRIPTION " "
			::= { fxsDialPlanEntry 4 }
			
		fxsDialPlanType  OBJECT-TYPE
			SYNTAX     FxsDialPlanType
			MAX-ACCESS read-create
			STATUS     obsolete
			DESCRIPTION " "
			::= { fxsDialPlanEntry 5 }
			
		fxsDialPlanAccessMask  OBJECT-TYPE
			SYNTAX     DisplayString
			MAX-ACCESS read-create
			STATUS     obsolete
			DESCRIPTION " "
			::= { fxsDialPlanEntry 6 }
			
		fxsDialPlanDialtone  OBJECT-TYPE
			SYNTAX     TruthValue
			MAX-ACCESS read-create
			STATUS     obsolete
			DESCRIPTION " "
			::= { fxsDialPlanEntry 7 }
			
		fxsDialPlanModifier  OBJECT-TYPE
			SYNTAX     DisplayString
			MAX-ACCESS read-create
			STATUS     obsolete
			DESCRIPTION " "
			::= { fxsDialPlanEntry 8 }
			
		fxsDialPlanNature  OBJECT-TYPE
			SYNTAX     FxsDialPlanNatureType
			MAX-ACCESS read-create
			STATUS     obsolete
			DESCRIPTION " "
			::= { fxsDialPlanEntry 9 }
			
		fxsDialPlanDelnum  OBJECT-TYPE
			SYNTAX     Integer32
			MAX-ACCESS read-create
			STATUS     obsolete
			DESCRIPTION " "
			::= { fxsDialPlanEntry 10 }
			
		fxsDialPlanPtime  OBJECT-TYPE
			SYNTAX     Integer32
			MAX-ACCESS read-create
			STATUS     obsolete
			DESCRIPTION " "
			::= { fxsDialPlanEntry 11 }

		fxsDialRowStatus  OBJECT-TYPE
			SYNTAX     RowStatus
			MAX-ACCESS read-create
			STATUS     obsolete
			DESCRIPTION " "
			::= { fxsDialPlanEntry 12 }
			
		fxsDialPlanNumber  OBJECT-TYPE
			SYNTAX     Integer32 (1..300)
			MAX-ACCESS not-accessible
			STATUS     obsolete
			DESCRIPTION " "
			::= { fxsDialPlanEntry 13 }
			
fxsDialPlanNext OBJECT-TYPE
	SYNTAX		Integer32
	MAX-ACCESS	read-only
	STATUS		obsolete
	DESCRIPTION " Show next (empty) position in DialPlanTable "
	::= { fxsDial 2 }
	
tauDialPlansRegExp OBJECT IDENTIFIER        ::= { fxsDial 3 }

	tauDialRegularOn  OBJECT-TYPE
			SYNTAX     TruthValue
			MAX-ACCESS read-write
			STATUS     obsolete
			DESCRIPTION ""
			::= { tauDialPlansRegExp 1 }
			
	tauDialRegularProtocol  OBJECT-TYPE
			SYNTAX     TauDialProtocolType
			MAX-ACCESS read-write
			STATUS     obsolete
			DESCRIPTION ""
			::= { tauDialPlansRegExp 2 }
			
	tauDialRegularText  OBJECT-TYPE
			SYNTAX     OCTET STRING
			MAX-ACCESS read-write
			STATUS     obsolete
			DESCRIPTION ""
			::= { tauDialPlansRegExp 3 }

fxsConfigSave OBJECT-TYPE
	SYNTAX		Integer32
	MAX-ACCESS	read-write
	STATUS		current
	DESCRIPTION " SET 1 to save /etc "
::= { fxs72 15 }
	
fxsConfigApply OBJECT-TYPE
	SYNTAX		Integer32
	MAX-ACCESS	read-write
	STATUS		obsolete
	DESCRIPTION " SET 1 to reload all configuration "
::= { fxs72 16 }

fxsSerialGroupsMIBBoundary  OBJECT-TYPE
			SYNTAX     Integer32
			MAX-ACCESS read-only
			STATUS     current
			DESCRIPTION "Dummy object to prevent GETNEXT request from poking into neighbor table."
			::= { fxs72 17 }

fxsSerialGroups OBJECT IDENTIFIER ::= { fxs72 18 }

	fxsSerialGroupsTable OBJECT-TYPE
	SYNTAX			SEQUENCE OF FxsSerialGroupsEntry
	MAX-ACCESS		not-accessible
	STATUS			current
	DESCRIPTION " "
	::= { fxsSerialGroups 1 }

		fxsSerialGroupsEntry OBJECT-TYPE
		SYNTAX		FxsSerialGroupsEntry
		MAX-ACCESS	not-accessible
		STATUS		current
		DESCRIPTION " "
		INDEX { fxsDialPlanNumber }
		::= { fxsSerialGroupsTable 1 }

		FxsSerialGroupsEntry ::= SEQUENCE {
			fxsSerialGroupsPhone		DisplayString,
			fxsSerialGroupsEnabled		Integer32,
			fxsSerialGroupsSerialType	FxsGroupSerialType,
			fxsSerialGroupsBusyType		FxsGroupBusyType,
			fxsSerialGroupsTimeout 		Integer32,
			fxsSerialGroupsSipPort 		Integer32,
			fxsSerialGroupsAuthName 	DisplayString,
			fxsSerialGroupsAuthPass 	DisplayString,
			fxsSerialGroupsPorts 		DisplayString,
			fxsSerialGroupsSipProfile Integer32,
			fxsSerialGroupsRowStatus	RowStatus
		}

		fxsSerialGroupsPhone  OBJECT-TYPE
			SYNTAX     DisplayString
			MAX-ACCESS read-create
			STATUS     current
			DESCRIPTION " "
			::= { fxsSerialGroupsEntry 1 }
			
		fxsSerialGroupsEnabled  OBJECT-TYPE
			SYNTAX     FxsGroupSerialEnableType
			MAX-ACCESS read-create
			STATUS     current
			DESCRIPTION " "
			::= { fxsSerialGroupsEntry 2 }
			
		fxsSerialGroupsSerialType  OBJECT-TYPE
			SYNTAX     FxsGroupSerialType
			MAX-ACCESS read-create
			STATUS     current
			DESCRIPTION " "
			::= { fxsSerialGroupsEntry 3 }
			
		fxsSerialGroupsBusyType  OBJECT-TYPE
			SYNTAX     FxsGroupBusyType
			MAX-ACCESS read-create
			STATUS     current
			DESCRIPTION " "
			::= { fxsSerialGroupsEntry 4 }
			
		fxsSerialGroupsTimeout  OBJECT-TYPE
			SYNTAX     Integer32
			MAX-ACCESS read-create
			STATUS     current
			DESCRIPTION " "
			::= { fxsSerialGroupsEntry 5 }
			
		fxsSerialGroupsSipPort  OBJECT-TYPE
			SYNTAX     Integer32
			MAX-ACCESS read-create
			STATUS     current
			DESCRIPTION " "
			::= { fxsSerialGroupsEntry 6 }
			
		fxsSerialGroupsAuthName  OBJECT-TYPE
			SYNTAX     DisplayString
			MAX-ACCESS read-create
			STATUS     current
			DESCRIPTION " "
			::= { fxsSerialGroupsEntry 7 }
			
		fxsSerialGroupsAuthPass  OBJECT-TYPE
			SYNTAX     DisplayString
			MAX-ACCESS read-create
			STATUS     current
			DESCRIPTION " "
			::= { fxsSerialGroupsEntry 8 }
			
		fxsSerialGroupsPorts  OBJECT-TYPE
			SYNTAX     DisplayString
			MAX-ACCESS read-create
			STATUS     current
			DESCRIPTION " "
			::= { fxsSerialGroupsEntry 9 }
			
		fxsSerialGroupsSipProfile  OBJECT-TYPE
			SYNTAX     Integer32
			MAX-ACCESS read-create
			STATUS     current
			DESCRIPTION " "
			::= { fxsSerialGroupsEntry 10 }
			
		fxsSerialGroupsRowStatus  OBJECT-TYPE
			SYNTAX     RowStatus
			MAX-ACCESS read-create
			STATUS     current
			DESCRIPTION " "
			::= { fxsSerialGroupsEntry 11 }
			
		

	fxsSerialGroupsNextEmpty OBJECT-TYPE
	SYNTAX			Integer32
	MAX-ACCESS		read-only
	STATUS			current
	DESCRIPTION " "
	::= { fxsSerialGroups 2 }

fxsReboot OBJECT-TYPE
	SYNTAX		Integer32
	MAX-ACCESS	read-write
	STATUS		current
	DESCRIPTION " SET 1 to reboot device "
::= { fxs72 19 }

tauVoipDvo OBJECT IDENTIFIER        ::= { fxs72 20 }

	tauVoipDvoCallwaiting  OBJECT-TYPE
			SYNTAX     DisplayString
			MAX-ACCESS read-write
			STATUS     current
			DESCRIPTION "00..99"
			::= { tauVoipDvo 1 }
			
	tauVoipDvoCtAttended  OBJECT-TYPE
			SYNTAX     DisplayString
			MAX-ACCESS read-write
			STATUS     current
			DESCRIPTION " "
			::= { tauVoipDvo 2 }
			
	tauVoipDvoCtUnattended  OBJECT-TYPE
			SYNTAX     DisplayString
			MAX-ACCESS read-write
			STATUS     current
			DESCRIPTION " "
			::= { tauVoipDvo 3 }
			
	tauVoipDvoCfUnconditional  OBJECT-TYPE
			SYNTAX     DisplayString
			MAX-ACCESS read-write
			STATUS     current
			DESCRIPTION " "
			::= { tauVoipDvo 4 }
			
	tauVoipDvoCfBusy  OBJECT-TYPE
			SYNTAX     DisplayString
			MAX-ACCESS read-write
			STATUS     current
			DESCRIPTION " "
			::= { tauVoipDvo 5 }
			
	tauVoipDvoCfNoanswer  OBJECT-TYPE
			SYNTAX     DisplayString
			MAX-ACCESS read-write
			STATUS     current
			DESCRIPTION " "
			::= { tauVoipDvo 6 }
			
	tauVoipDvoCfService  OBJECT-TYPE
			SYNTAX     DisplayString
			MAX-ACCESS read-write
			STATUS     current
			DESCRIPTION " "
			::= { tauVoipDvo 7 }
			
	tauVoipDvoDoDisturb  OBJECT-TYPE
			SYNTAX     DisplayString
			MAX-ACCESS read-write
			STATUS     current
			DESCRIPTION " "
			::= { tauVoipDvo 8 }
			
			
tauSipConfig OBJECT IDENTIFIER        ::= { fxs72 21 }

    sipEnablesip  OBJECT-TYPE
			SYNTAX     TruthValue
			MAX-ACCESS read-write
			STATUS     obsolete
			DESCRIPTION ""
			::= { tauSipConfig 1 }
			
	sipObtimeout  OBJECT-TYPE
			SYNTAX     Integer32
			MAX-ACCESS read-write
			STATUS     obsolete
			DESCRIPTION ""
			::= { tauSipConfig 2 }
	
	sipMode  OBJECT-TYPE
			SYNTAX     ProxyMode
			MAX-ACCESS read-write
			STATUS     obsolete
			DESCRIPTION ""
			::= { tauSipConfig 3 }
	
		sipOptions  OBJECT-TYPE
			SYNTAX     OptionsHomeServerTest
			MAX-ACCESS read-write
			STATUS     obsolete
			DESCRIPTION ""
			::= { tauSipConfig 4 }
		
		sipKeepalivet  OBJECT-TYPE
			SYNTAX     Integer32
			MAX-ACCESS read-write
			STATUS     obsolete
			DESCRIPTION ""
			::= { tauSipConfig 5 }
			
		sipDomainToReg  OBJECT-TYPE
			SYNTAX     TruthValue
			MAX-ACCESS read-write
			STATUS     obsolete
			DESCRIPTION ""
			::= { tauSipConfig 6 }
			
		sipDomain  OBJECT-TYPE
			SYNTAX     DisplayString
			MAX-ACCESS read-write
			STATUS     obsolete
			DESCRIPTION ""
			::= { tauSipConfig 7 }
			
		sipRegisterRetryInterval  OBJECT-TYPE
			SYNTAX     Integer32
			MAX-ACCESS read-write
			STATUS     obsolete
			DESCRIPTION ""
			::= { tauSipConfig 8 }

		sipOutbound  OBJECT-TYPE
			SYNTAX     OutboundType
			MAX-ACCESS read-write
			STATUS     obsolete
			DESCRIPTION ""
			::= { tauSipConfig 9 }
			
		sipInboundProxy  OBJECT-TYPE
			SYNTAX     TruthValue
			MAX-ACCESS read-write
			STATUS     obsolete
			DESCRIPTION ""
			::= { tauSipConfig 10 }
			
		sipExpires  OBJECT-TYPE
			SYNTAX     Integer32
			MAX-ACCESS read-write
			STATUS     obsolete
			DESCRIPTION ""
			::= { tauSipConfig 11 }

		sipAuthentication  OBJECT-TYPE
			SYNTAX     AuthenticationType
			MAX-ACCESS read-write
			STATUS     obsolete
			DESCRIPTION ""
			::= { tauSipConfig 12 }

		sipUsername  OBJECT-TYPE
			SYNTAX     DisplayString
			MAX-ACCESS read-write
			STATUS     obsolete
			DESCRIPTION ""
			::= { tauSipConfig 13 }
			
		sipPassword  OBJECT-TYPE
			SYNTAX     DisplayString
			MAX-ACCESS read-write
			STATUS     obsolete
			DESCRIPTION ""
			::= { tauSipConfig 14 }

		sipProxy0  OBJECT-TYPE
			SYNTAX     DisplayString
			MAX-ACCESS read-write
			STATUS     obsolete
			DESCRIPTION ""
			::= { tauSipConfig 15 }
			
		sipRegrar0  OBJECT-TYPE
			SYNTAX     DisplayString
			MAX-ACCESS read-write
			STATUS     obsolete
			DESCRIPTION ""
			::= { tauSipConfig 16 }
			
		sipRegistration0  OBJECT-TYPE
			SYNTAX     TruthValue
			MAX-ACCESS read-write
			STATUS     obsolete
			DESCRIPTION ""
			::= { tauSipConfig 17 }

		sipProxy1  OBJECT-TYPE
			SYNTAX     DisplayString
			MAX-ACCESS read-write
			STATUS     obsolete
			DESCRIPTION ""
			::= { tauSipConfig 18 }
			
		sipRegrar1  OBJECT-TYPE
			SYNTAX     DisplayString
			MAX-ACCESS read-write
			STATUS     obsolete
			DESCRIPTION ""
			::= { tauSipConfig 19 }

		sipProxy2  OBJECT-TYPE
			SYNTAX     DisplayString
			MAX-ACCESS read-write
			STATUS     obsolete
			DESCRIPTION ""
			::= { tauSipConfig 20 }

		sipRegrar2  OBJECT-TYPE
			SYNTAX     DisplayString
			MAX-ACCESS read-write
			STATUS     obsolete
			DESCRIPTION ""
			::= { tauSipConfig 21 }

		sipProxy3  OBJECT-TYPE
			SYNTAX     DisplayString
			MAX-ACCESS read-write
			STATUS     obsolete
			DESCRIPTION ""
			::= { tauSipConfig 22 }
			
		sipRegrar3  OBJECT-TYPE
			SYNTAX     DisplayString
			MAX-ACCESS read-write
			STATUS     obsolete
			DESCRIPTION ""
			::= { tauSipConfig 23 }

		sipProxy4  OBJECT-TYPE
			SYNTAX     DisplayString
			MAX-ACCESS read-write
			STATUS     obsolete
			DESCRIPTION ""
			::= { tauSipConfig 24 }
			
		sipRegrar4  OBJECT-TYPE
			SYNTAX     DisplayString
			MAX-ACCESS read-write
			STATUS     obsolete
			DESCRIPTION ""
			::= { tauSipConfig 25 }

	sipDtmfmime  OBJECT-TYPE
			SYNTAX     DTMFMIMEType
			MAX-ACCESS read-write
			STATUS     obsolete
			DESCRIPTION ""
			::= { tauSipConfig 26 }
			
	sipHfmime  OBJECT-TYPE
			SYNTAX     HookFlashMIMEType
			MAX-ACCESS read-write
			STATUS     obsolete
			DESCRIPTION ""
			::= { tauSipConfig 27 }
			
	sipCtWithReplaces  OBJECT-TYPE
			SYNTAX     TruthValue
			MAX-ACCESS read-write
			STATUS     obsolete
			DESCRIPTION ""
			::= { tauSipConfig 28 }
			
	sipShortmode  OBJECT-TYPE
			SYNTAX     TruthValue
			MAX-ACCESS read-write
			STATUS     obsolete
			DESCRIPTION ""
			::= { tauSipConfig 29 }
			
	sipTransport  OBJECT-TYPE
			SYNTAX     TypeTransport
			MAX-ACCESS read-write
			STATUS     obsolete
			DESCRIPTION ""
			::= { tauSipConfig 30 }

	sipSipMtu  OBJECT-TYPE
			SYNTAX     Integer32
			MAX-ACCESS read-write
			STATUS     obsolete
			DESCRIPTION ""
			::= { tauSipConfig 31 }
			
	sip100Rel  OBJECT-TYPE
			SYNTAX     Type100rel
			MAX-ACCESS read-write
			STATUS     obsolete
			DESCRIPTION ""
			::= { tauSipConfig 32 }
			
	sipUserPhone  OBJECT-TYPE
			SYNTAX     TruthValue
			MAX-ACCESS read-write
			STATUS     obsolete
			DESCRIPTION ""
			::= { tauSipConfig 33 }

	sipUriEscapeHash  OBJECT-TYPE
			SYNTAX     TruthValue
			MAX-ACCESS read-write
			STATUS     obsolete
			DESCRIPTION ""
			::= { tauSipConfig 34 }
			
	sipInviteTotalT  OBJECT-TYPE
			SYNTAX     Integer32
			MAX-ACCESS read-write
			STATUS     obsolete
			DESCRIPTION ""
			::= { tauSipConfig 35 }
			
	sipInviteInitT  OBJECT-TYPE
			SYNTAX     Integer32
			MAX-ACCESS read-write
			STATUS     obsolete
			DESCRIPTION ""
			::= { tauSipConfig 36 }
			
	sipCwRingback  OBJECT-TYPE
			SYNTAX     CwRingbackRingbackAtCallwaiting
			MAX-ACCESS read-write
			STATUS     obsolete
			DESCRIPTION ""
			::= { tauSipConfig 37 }
			
	sipRingbackSdp  OBJECT-TYPE
			SYNTAX     RemoteRingback
			MAX-ACCESS read-write
			STATUS     obsolete
			DESCRIPTION ""
			::= { tauSipConfig 38 }
			
	sipRingback  OBJECT-TYPE
			SYNTAX     TruthValue
			MAX-ACCESS read-write
			STATUS     obsolete
			DESCRIPTION ""
			::= { tauSipConfig 39 }
			
	sipRegistration1  OBJECT-TYPE
			SYNTAX     TruthValue
			MAX-ACCESS read-write
			STATUS     obsolete
			DESCRIPTION ""
			::= { tauSipConfig 40 }
			
	sipRegistration2  OBJECT-TYPE
			SYNTAX     TruthValue
			MAX-ACCESS read-write
			STATUS     obsolete
			DESCRIPTION ""
			::= { tauSipConfig 41 }
			
	sipRegistration3  OBJECT-TYPE
			SYNTAX     TruthValue
			MAX-ACCESS read-write
			STATUS     obsolete
			DESCRIPTION ""
			::= { tauSipConfig 42 }
			
	sipRegistration4  OBJECT-TYPE
			SYNTAX     TruthValue
			MAX-ACCESS read-write
			STATUS     obsolete
			DESCRIPTION ""
			::= { tauSipConfig 43 }
			
	sipPRTPstat  OBJECT-TYPE
			SYNTAX     TruthValue
			MAX-ACCESS read-write
			STATUS     obsolete
			DESCRIPTION ""
			::= { tauSipConfig 44 }



fxsStatTable OBJECT-TYPE
	SYNTAX			SEQUENCE OF FxsStatEntry
	MAX-ACCESS		not-accessible
	STATUS			current
	DESCRIPTION " "
	::= { fxs72 23 }

	fxsStatEntry OBJECT-TYPE
		SYNTAX		FxsStatEntry
		MAX-ACCESS	not-accessible
		STATUS		current
		DESCRIPTION " "
		INDEX { fxsPortNumber }
		::= { fxsStatTable 1 }

		FxsStatEntry ::= SEQUENCE {
			termID Integer32,
			currentState FxsPortState,
			totalCallCount Integer32,
			lastCallPhone DisplayString,
			peakJitter Integer32,
			lostPackets Integer32,
			numTxPack Integer32,
			numTxOct Integer32,
			numRxPack Integer32,
			numRxOct Integer32
		}

		termID  OBJECT-TYPE
			SYNTAX     Integer32
			MAX-ACCESS read-only
			STATUS     current
			DESCRIPTION " "
			::= { fxsStatEntry 1 }
			
		currentState  OBJECT-TYPE
			SYNTAX     FxsPortState
			MAX-ACCESS read-only
			STATUS     current
			DESCRIPTION " "
			::= { fxsStatEntry 2 }
			
		totalCallCount  OBJECT-TYPE
			SYNTAX     Integer32
			MAX-ACCESS read-only
			STATUS     current
			DESCRIPTION " "
			::= { fxsStatEntry 3 }
			
		lastCallPhone  OBJECT-TYPE
			SYNTAX     DisplayString
			MAX-ACCESS read-only
			STATUS     current
			DESCRIPTION " "
			::= { fxsStatEntry 4 }
			
		peakJitter  OBJECT-TYPE
			SYNTAX     Integer32
			MAX-ACCESS read-only
			STATUS     current
			DESCRIPTION " "
			::= { fxsStatEntry 5 }
			
		lostPackets  OBJECT-TYPE
			SYNTAX     Integer32
			MAX-ACCESS read-only
			STATUS     current
			DESCRIPTION " "
			::= { fxsStatEntry 6 }
			
		numTxPack  OBJECT-TYPE
			SYNTAX     Integer32
			MAX-ACCESS read-only
			STATUS     current
			DESCRIPTION " "
			::= { fxsStatEntry 7 }
			
		numTxOct  OBJECT-TYPE
			SYNTAX     Integer32
			MAX-ACCESS read-only
			STATUS     current
			DESCRIPTION " "
			::= { fxsStatEntry 8 }
			
		numRxPack  OBJECT-TYPE
			SYNTAX     Integer32
			MAX-ACCESS read-only
			STATUS     current
			DESCRIPTION " "
			::= { fxsStatEntry 9 }
			
		numRxOct  OBJECT-TYPE
			SYNTAX     Integer32
			MAX-ACCESS read-only
			STATUS     current
			DESCRIPTION " "
			::= { fxsStatEntry 10 }
			
fxsUpdateFw OBJECT-TYPE
	SYNTAX		DisplayString
	MAX-ACCESS	read-write
	STATUS		current
	DESCRIPTION "SET: filename tftpaddr"
::= { fxs72 25 }

fxsProfiles OBJECT IDENTIFIER       ::= { fxs72 30 }

profilesSip OBJECT IDENTIFIER       ::= { fxsProfiles 1 }

profilesSipCommon OBJECT IDENTIFIER       ::= { profilesSip 1 }
    
    sipCommonEnablesip  OBJECT-TYPE
			SYNTAX     TruthValue
			MAX-ACCESS read-write
			STATUS     current
			DESCRIPTION ""
			::= { profilesSipCommon 1 }

	sipCommonShortmode  OBJECT-TYPE
			SYNTAX     TruthValue
			MAX-ACCESS read-write
			STATUS     current
			DESCRIPTION ""
			::= { profilesSipCommon 2 }
			
	sipCommonTransport  OBJECT-TYPE
			SYNTAX     TypeTransport
			MAX-ACCESS read-write
			STATUS     current
			DESCRIPTION ""
			::= { profilesSipCommon 3 }

	sipCommonSipMtu  OBJECT-TYPE
			SYNTAX     Integer32 (1300..1450)
			MAX-ACCESS read-write
			STATUS     current
			DESCRIPTION ""
			::= { profilesSipCommon 4 }

	sipCommonInviteTotalT  OBJECT-TYPE
			SYNTAX     Integer32 (1000..39000)
			UNITS		"ms"
			MAX-ACCESS read-write
			STATUS     current
			DESCRIPTION ""
			::= { profilesSipCommon 5 }
			
	sipCommonInviteInitT  OBJECT-TYPE
			SYNTAX     Integer32 (100..1000)
			UNITS		"ms"
			MAX-ACCESS read-write
			STATUS     current
			DESCRIPTION ""
			::= { profilesSipCommon 6 }
			
	sipCommonPortRegistrationDelay OBJECT-TYPE
			SYNTAX     Integer32 (0..5000)
			UNITS		"ms"
			MAX-ACCESS read-write
			STATUS     current
			DESCRIPTION "Port registration delay (ms)"
			DEFVAL     { 500 }
			::= { profilesSipCommon 7 }
			
	stunEnable OBJECT-TYPE
		SYNTAX TruthValue
		MAX-ACCESS read-write
		STATUS current
		DESCRIPTION
			" "
		::= { profilesSipCommon 8 }
        
    stunServer OBJECT-TYPE
		SYNTAX DisplayString 
		MAX-ACCESS read-write
		STATUS current
		DESCRIPTION
			"max 49 symbols"
		::= {  profilesSipCommon 9 }
					
    stunInterval OBJECT-TYPE
		SYNTAX Integer32 (10..1800)
		MAX-ACCESS read-write
		STATUS current
		DESCRIPTION
			" "
		::= {  profilesSipCommon 10 }
		
	sipPublicIp OBJECT-TYPE
		SYNTAX DisplayString 
		MAX-ACCESS read-write
		STATUS current
		DESCRIPTION
			"IPv4 address"
		::= {  profilesSipCommon 11 }
			
profilesSipMIBBoundary  OBJECT-TYPE
			SYNTAX     Integer32
			MAX-ACCESS read-only
			STATUS     current
			DESCRIPTION "Dummy object to prevent GETNEXT request from poking into neighbor table."
			::= { profilesSip 2 }


profilesSipTable OBJECT-TYPE
	SYNTAX			SEQUENCE OF ProfilesSipEntry
	MAX-ACCESS		not-accessible
	STATUS			current
	DESCRIPTION " "
	::= { profilesSip 3 }

		profilesSipEntry OBJECT-TYPE
		SYNTAX		ProfilesSipEntry
		MAX-ACCESS	not-accessible
		STATUS		current
		DESCRIPTION " "
		INDEX { profileNumber }
		::= { profilesSipTable 1 }

		ProfilesSipEntry ::= SEQUENCE {
			profileNumber Integer32,
			sipProfileObtimeout  Integer32,
			sipProfileMode  ProxyMode,
			sipProfileOptions  OptionsHomeServerTest,
			sipProfileKeepalivet  Integer32,
			sipProfileDomainToReg  TruthValue,
			sipProfileDomain DisplayString,
			sipProfileRegisterRetryInterval  Integer32,
			sipProfileOutbound  OutboundType,
			sipProfileInboundProxy  TruthValue,
			sipProfileExpires  Integer32,
			sipProfileAuthentication  AuthenticationType,
			sipProfileUsername  DisplayString,
			sipProfilePassword  DisplayString,
			sipProfileProxy0  DisplayString,
			sipProfileRegrar0  DisplayString,
			sipProfileRegistration0  TruthValue,
			sipProfileProxy1  DisplayString,
			sipProfileRegrar1  DisplayString,
			sipProfileProxy2  DisplayString,
			sipProfileRegrar2  DisplayString,
			sipProfileProxy3  DisplayString,
			sipProfileRegrar3  DisplayString,
			sipProfileProxy4  DisplayString,
			sipProfileRegrar4  DisplayString,
			sipProfileDtmfmime  DTMFMIMEType,
			sipProfileHfmime  HookFlashMIMEType,
			sipProfileCtWithReplaces  TruthValue,
			sipProfile100Rel  Type100rel,
			sipProfileUserPhone  TruthValue,
			sipProfileUriEscapeHash  TruthValue,
			sipProfileCwRingback  CwRingbackRingbackAtCallwaiting,
			sipProfileRingbackSdp  RemoteRingback,
			sipProfileRingback  TruthValue,
			sipProfileRegistration1  TruthValue,
			sipProfileRegistration2  TruthValue,
			sipProfileRegistration3  TruthValue,
			sipProfileRegistration4  TruthValue,
			sipProfilePRTPstat  TruthValue,
			sipProfileRowStatus RowStatus,
			sipProfileEnableTimer TruthValue,
			sipProfileMinSE Integer32,
			sipProfileSessionExpires Integer32,
			sipProfileRemoveInactiveMedia TruthValue,
			sipProfileKeepAliveInterval Integer32,
			sipProfileKeepAliveMode KeepAliveMode,
			sipProfileConferenceMode ConferenceMode,
			sipProfileConferenceServer DisplayString,
			sipProfileEnableIMS IMSMode,
			sipProfileXCAPNameForThreePartyConference DisplayString,
			sipProfileXCAPNameForHotline DisplayString,
			sipProfileXCAPNameForCallWaiting DisplayString,
			sipProfileXCAPNameForCallHold DisplayString,
			sipProfileXCAPNameForExplicitCallTransfer DisplayString,
			sipProfileUseAlertInfo TruthValue,
			sipProfileFullRuriCompliance TruthValue,
			sipProfileChangeover SipProfileChangeoverType
		}
		
		profileNumber OBJECT-TYPE
			SYNTAX     Integer32 (1..8)
			MAX-ACCESS read-only
			STATUS     current
			DESCRIPTION ""
			::= { profilesSipEntry 1 }
	
	sipProfileObtimeout  OBJECT-TYPE
			SYNTAX     Integer32
			MAX-ACCESS read-write
			STATUS     current
			DESCRIPTION ""
			::= { profilesSipEntry 2 }
	
	sipProfileMode  OBJECT-TYPE
			SYNTAX     ProxyMode
			MAX-ACCESS read-write
			STATUS     current
			DESCRIPTION ""
			::= { profilesSipEntry 3 }
	
		sipProfileOptions  OBJECT-TYPE
			SYNTAX     OptionsHomeServerTest
			MAX-ACCESS read-write
			STATUS     current
			DESCRIPTION ""
			::= { profilesSipEntry 4 }
		
		sipProfileKeepalivet  OBJECT-TYPE
			SYNTAX     Integer32
			MAX-ACCESS read-write
			STATUS     current
			DESCRIPTION ""
			::= { profilesSipEntry 5 }
			
		sipProfileDomainToReg  OBJECT-TYPE
			SYNTAX     TruthValue
			MAX-ACCESS read-write
			STATUS     current
			DESCRIPTION ""
			::= { profilesSipEntry 6 }
			
		sipProfileDomain  OBJECT-TYPE
			SYNTAX     DisplayString (SIZE (0..128))
			MAX-ACCESS read-write
			STATUS     current
			DESCRIPTION "2.13 - 128 symbols"
			::= { profilesSipEntry 7 }

		sipProfileRegisterRetryInterval  OBJECT-TYPE
			SYNTAX     Integer32
			MAX-ACCESS read-write
			STATUS     current
			DESCRIPTION ""
			::= { profilesSipEntry 8 }

		sipProfileOutbound  OBJECT-TYPE
			SYNTAX     OutboundType
			MAX-ACCESS read-write
			STATUS     current
			DESCRIPTION ""
			::= { profilesSipEntry 9 }
			
		sipProfileInboundProxy  OBJECT-TYPE
			SYNTAX     TruthValue
			MAX-ACCESS read-write
			STATUS     current
			DESCRIPTION ""
			::= { profilesSipEntry 10 }
			
		sipProfileExpires  OBJECT-TYPE
			SYNTAX     Integer32
			MAX-ACCESS read-write
			STATUS     current
			DESCRIPTION ""
			::= { profilesSipEntry 11 }

		sipProfileAuthentication  OBJECT-TYPE
			SYNTAX     AuthenticationType
			MAX-ACCESS read-write
			STATUS     current
			DESCRIPTION ""
			::= { profilesSipEntry 12 }

		sipProfileUsername  OBJECT-TYPE
			SYNTAX     DisplayString
			MAX-ACCESS read-write
			STATUS     current
			DESCRIPTION ""
			::= { profilesSipEntry 13 }
			
		sipProfilePassword  OBJECT-TYPE
			SYNTAX     DisplayString
			MAX-ACCESS read-write
			STATUS     current
			DESCRIPTION ""
			::= { profilesSipEntry 14 }

		sipProfileProxy0  OBJECT-TYPE
			SYNTAX     DisplayString (SIZE (0..128))
			MAX-ACCESS read-write
			STATUS     current
			DESCRIPTION "2.13 - 128 symbols"
			::= { profilesSipEntry 15 }
			
		sipProfileRegrar0  OBJECT-TYPE
			SYNTAX     DisplayString (SIZE (0..128))
			MAX-ACCESS read-write
			STATUS     current
			DESCRIPTION "2.13 - 128 symbols"
			::= { profilesSipEntry 16 }
			
		sipProfileRegistration0  OBJECT-TYPE
			SYNTAX     TruthValue
			MAX-ACCESS read-write
			STATUS     current
			DESCRIPTION ""
			::= { profilesSipEntry 17 }

		sipProfileProxy1  OBJECT-TYPE
			SYNTAX     DisplayString (SIZE (0..128))
			MAX-ACCESS read-write
			STATUS     current
			DESCRIPTION "2.13 - 128 symbols"
			::= { profilesSipEntry 18 }
			
		sipProfileRegrar1  OBJECT-TYPE
			SYNTAX     DisplayString (SIZE (0..128))
			MAX-ACCESS read-write
			STATUS     current
			DESCRIPTION "2.13 - 128 symbols"
			::= { profilesSipEntry 19 }

		sipProfileProxy2  OBJECT-TYPE
			SYNTAX     DisplayString (SIZE (0..128))
			MAX-ACCESS read-write
			STATUS     current
			DESCRIPTION "2.13 - 128 symbols"
			::= { profilesSipEntry 20 }

		sipProfileRegrar2  OBJECT-TYPE
			SYNTAX     DisplayString (SIZE (0..128))
			MAX-ACCESS read-write
			STATUS     current
			DESCRIPTION "2.13 - 128 symbols"
			::= { profilesSipEntry 21 }

		sipProfileProxy3  OBJECT-TYPE
			SYNTAX     DisplayString (SIZE (0..128))
			MAX-ACCESS read-write
			STATUS     current
			DESCRIPTION "2.13 - 128 symbols"
			::= { profilesSipEntry 22 }
			
		sipProfileRegrar3  OBJECT-TYPE
			SYNTAX     DisplayString (SIZE (0..128))
			MAX-ACCESS read-write
			STATUS     current
			DESCRIPTION "2.13 - 128 symbols"
			::= { profilesSipEntry 23 }

		sipProfileProxy4  OBJECT-TYPE
			SYNTAX     DisplayString (SIZE (0..128))
			MAX-ACCESS read-write
			STATUS     current
			DESCRIPTION "2.13 - 128 symbols"
			::= { profilesSipEntry 24 }
			
		sipProfileRegrar4  OBJECT-TYPE
			SYNTAX     DisplayString (SIZE (0..128))
			MAX-ACCESS read-write
			STATUS     current
			DESCRIPTION "2.13 - 128 symbols"
			::= { profilesSipEntry 25 }

	sipProfileDtmfmime  OBJECT-TYPE
			SYNTAX     DTMFMIMEType
			MAX-ACCESS read-write
			STATUS     current
			DESCRIPTION ""
			::= { profilesSipEntry 26 }
			
	sipProfileHfmime  OBJECT-TYPE
			SYNTAX     HookFlashMIMEType
			MAX-ACCESS read-write
			STATUS     current
			DESCRIPTION ""
			::= { profilesSipEntry 27 }
			
	sipProfileCtWithReplaces  OBJECT-TYPE
			SYNTAX     TruthValue
			MAX-ACCESS read-write
			STATUS     current
			DESCRIPTION ""
			::= { profilesSipEntry 28 }
	
	sipProfile100Rel  OBJECT-TYPE
			SYNTAX     Type100rel
			MAX-ACCESS read-write
			STATUS     current
			DESCRIPTION ""
			::= { profilesSipEntry 32 }
			
	sipProfileUserPhone  OBJECT-TYPE
			SYNTAX     TruthValue
			MAX-ACCESS read-write
			STATUS     current
			DESCRIPTION ""
			::= { profilesSipEntry 33 }

	sipProfileUriEscapeHash  OBJECT-TYPE
			SYNTAX     TruthValue
			MAX-ACCESS read-write
			STATUS     current
			DESCRIPTION ""
			::= { profilesSipEntry 34 }

	sipProfileCwRingback  OBJECT-TYPE
			SYNTAX     CwRingbackRingbackAtCallwaiting
			MAX-ACCESS read-write
			STATUS     current
			DESCRIPTION ""
			::= { profilesSipEntry 37 }
			
	sipProfileRingbackSdp  OBJECT-TYPE
			SYNTAX     RemoteRingback
			MAX-ACCESS read-write
			STATUS     current
			DESCRIPTION ""
			::= { profilesSipEntry 38 }
			
	sipProfileRingback  OBJECT-TYPE
			SYNTAX     TruthValue
			MAX-ACCESS read-write
			STATUS     current
			DESCRIPTION ""
			::= { profilesSipEntry 39 }
			
	sipProfileRegistration1  OBJECT-TYPE
			SYNTAX     TruthValue
			MAX-ACCESS read-write
			STATUS     current
			DESCRIPTION ""
			::= { profilesSipEntry 40 }
			
	sipProfileRegistration2  OBJECT-TYPE
			SYNTAX     TruthValue
			MAX-ACCESS read-write
			STATUS     current
			DESCRIPTION ""
			::= { profilesSipEntry 41 }
			
	sipProfileRegistration3  OBJECT-TYPE
			SYNTAX     TruthValue
			MAX-ACCESS read-write
			STATUS     current
			DESCRIPTION ""
			::= { profilesSipEntry 42 }
			
	sipProfileRegistration4  OBJECT-TYPE
			SYNTAX     TruthValue
			MAX-ACCESS read-write
			STATUS     current
			DESCRIPTION ""
			::= { profilesSipEntry 43 }
			
	sipProfilePRTPstat  OBJECT-TYPE
			SYNTAX     TruthValue
			MAX-ACCESS read-write
			STATUS     current
			DESCRIPTION ""
			::= { profilesSipEntry 44 }
			
	sipProfileRowStatus  OBJECT-TYPE
			SYNTAX     RowStatus
			MAX-ACCESS read-create
			STATUS     current
			DESCRIPTION ""
			::= { profilesSipEntry 45 }
			
			
	sipProfileEnableTimer  OBJECT-TYPE
			SYNTAX     TruthValue
			MAX-ACCESS read-write
			STATUS     current
			DESCRIPTION "Enable timer"
			::= { profilesSipEntry 46 }
	
	sipProfileMinSE  OBJECT-TYPE
			SYNTAX     Integer32
			MAX-ACCESS read-write
			STATUS     current
			DESCRIPTION "Min SE 90..1800 def 120"
			::= { profilesSipEntry 47 }
	
	sipProfileSessionExpires  OBJECT-TYPE
			SYNTAX     Integer32
			MAX-ACCESS read-write
			STATUS     current
			DESCRIPTION "SessionExpires 90..80000 or 0 def 0"
			::= { profilesSipEntry 48 } 
	
	sipProfileRemoveInactiveMedia  OBJECT-TYPE
			SYNTAX     TruthValue
			MAX-ACCESS read-write
			STATUS     current
			DESCRIPTION "Remove inactive media"
			::= { profilesSipEntry 49 }
			
	sipProfileKeepAliveInterval  OBJECT-TYPE
			SYNTAX     Integer32
			MAX-ACCESS read-write
			STATUS     current
			DESCRIPTION "keep alive interval 30..120 def 30. TAU-SIP 2.7"
			::= { profilesSipEntry 50 } 
			
	sipProfileKeepAliveMode  OBJECT-TYPE
			SYNTAX     KeepAliveMode
			MAX-ACCESS read-write
			STATUS     current
			DESCRIPTION "type of the keep alive message. TAU-SIP 2.7"
			::= { profilesSipEntry 51 }
	
	-- conference settings
			
	sipProfileConferenceMode  OBJECT-TYPE
			SYNTAX     ConferenceMode
			MAX-ACCESS read-write
			STATUS     current
			DESCRIPTION "Conference mode. TAU-SIP 2.8"
			::= { profilesSipEntry 52 }
	sipProfileConferenceServer  OBJECT-TYPE
			SYNTAX     DisplayString
			MAX-ACCESS read-write
			STATUS     current
			DESCRIPTION "Conference server name. TAU-SIP 2.8"
			::= { profilesSipEntry 53 }
	
	-- IMS settings
			
	sipProfileEnableIMS  OBJECT-TYPE
			SYNTAX     IMSMode
			MAX-ACCESS read-write
			STATUS     current
			DESCRIPTION "Enable IMS. TAU-SIP 2.8 TruthValue
							TAU-SIP 2.10 IMSMode"
			::= { profilesSipEntry 54 }
	sipProfileXCAPNameForThreePartyConference  OBJECT-TYPE
			SYNTAX     DisplayString
			MAX-ACCESS read-write
			STATUS     current
			DESCRIPTION "XCAP name for three-party conference. TAU-SIP 2.8"
			::= { profilesSipEntry 55 }
	sipProfileXCAPNameForHotline  OBJECT-TYPE
			SYNTAX     DisplayString
			MAX-ACCESS read-write
			STATUS     current
			DESCRIPTION "XCAP name for hotline. TAU-SIP 2.8"
			::= { profilesSipEntry 56 }
	sipProfileXCAPNameForCallWaiting  OBJECT-TYPE
			SYNTAX     DisplayString
			MAX-ACCESS read-write
			STATUS     current
			DESCRIPTION "XCAP name for call waiting. TAU-SIP 2.8"
			::= { profilesSipEntry 57 }
	sipProfileXCAPNameForCallHold  OBJECT-TYPE
			SYNTAX     DisplayString
			MAX-ACCESS read-write
			STATUS     current
			DESCRIPTION "XCAP name for call hold. TAU-SIP 2.8"
			::= { profilesSipEntry 58 }
			
	sipProfileXCAPNameForExplicitCallTransfer  OBJECT-TYPE
			SYNTAX     DisplayString
			MAX-ACCESS read-write
			STATUS     current
			DESCRIPTION "XCAP name for explicit call transfer. TAU-SIP 2.10"
			::= { profilesSipEntry 59 }
			
	sipProfileUseAlertInfo OBJECT-TYPE
			SYNTAX     TruthValue
			MAX-ACCESS read-write
			STATUS     current
			DESCRIPTION "Alert-Info"
			::= { profilesSipEntry 60 }
			
	sipProfileFullRuriCompliance OBJECT-TYPE
			SYNTAX     TruthValue
			MAX-ACCESS read-write
			STATUS     current
			DESCRIPTION "Full RURI compliance. TAU-SIP 2.12"
			::= { profilesSipEntry 61 }
			
	sipProfileChangeover OBJECT-TYPE
			SYNTAX     SipProfileChangeoverType
			MAX-ACCESS read-write
			STATUS     current
			DESCRIPTION "Changeover mode. TAU-SIP 2.12"
			::= { profilesSipEntry 62 }

profilesSipAlertInfoMIBBoundary  OBJECT-TYPE
			SYNTAX     Integer32
			MAX-ACCESS read-only
			STATUS     current
			DESCRIPTION "Dummy object to prevent GETNEXT request from poking into neighbor table."
			::= { profilesSip 4 }	
			
profilesSipAlertInfoTable OBJECT-TYPE
	SYNTAX			SEQUENCE OF ProfilesSipAlertInfoEntry
	MAX-ACCESS		not-accessible
	STATUS			current
	DESCRIPTION " "
	::= { profilesSip 5 }

	profilesSipAlertInfoEntry OBJECT-TYPE
		SYNTAX		ProfilesSipAlertInfoEntry
		MAX-ACCESS	not-accessible
		STATUS		current
		DESCRIPTION " "
		INDEX { profileNumber, cadenceNumber }
		::= { profilesSipAlertInfoTable 1 }

		ProfilesSipAlertInfoEntry ::= SEQUENCE {
			cadenceNumber Integer32,
			cadenceName DisplayString,
			cadenceRingRule DisplayString,
			cadenceRowStatus RowStatus }	
			
			cadenceNumber  OBJECT-TYPE
				SYNTAX     Integer32 (1..16)
				MAX-ACCESS	not-accessible
				STATUS     current
				DESCRIPTION ""
				::= { profilesSipAlertInfoEntry 1 }
			
			cadenceName  OBJECT-TYPE
				SYNTAX     DisplayString
				MAX-ACCESS read-write
				STATUS     current
				DESCRIPTION "Alert-Info string (max len 30)"
				::= { profilesSipAlertInfoEntry 2 }
			
			cadenceRingRule  OBJECT-TYPE
				SYNTAX     DisplayString
				MAX-ACCESS read-write
				STATUS     current
				DESCRIPTION "Distinctive Ring rule (max len 71)
					string of values (200-16000) devided by ',' or ';'
					allowed 2,4,6,8,10,12 elements"
				::= { profilesSipAlertInfoEntry 3 }
			
			cadenceRowStatus  OBJECT-TYPE
				SYNTAX     RowStatus
				MAX-ACCESS read-create	
				STATUS     current
				DESCRIPTION ""
				::= { profilesSipAlertInfoEntry 4 }			
			
			
profilesPortsMIBBoundary  OBJECT-TYPE
			SYNTAX     Integer32
			MAX-ACCESS read-only
			STATUS     current
			DESCRIPTION "Dummy object to prevent GETNEXT request from poking into neighbor table."
			::= { fxsProfiles 2 }

profilesPorts OBJECT IDENTIFIER     ::= { fxsProfiles 3 }

profilesPortsTable OBJECT-TYPE
	SYNTAX			SEQUENCE OF ProfilesPortsEntry
	MAX-ACCESS		not-accessible
	STATUS			current
	DESCRIPTION " "
	::= { profilesPorts 1 }

		profilesPortsEntry OBJECT-TYPE
		SYNTAX		ProfilesPortsEntry
		MAX-ACCESS	not-accessible
		STATUS		current
		DESCRIPTION " "
		INDEX { profileNumber }
		::= { profilesPortsTable 1 }

		ProfilesPortsEntry ::= SEQUENCE {
			profilePortsPlaymoh  TruthValue,
			profilePortsAON  FxsAON,
			profilePortsAONHideDate  TruthValue,
			profilePortsAONHideName  TruthValue,
			profilePortsTaxophone  FxsTaxophoneType,
			profilePortsMinFlashtime  Integer32,
			profilePortsMaxFlashtime  Integer32,
			profilePortsGainr  Integer32,
			profilePortsGaint  Integer32,
			profilePortsCategory  Integer32,
			profilePortsCallTransfer  FxsProcessFlashType,
			profilePortsCallWaiting TruthValue,
			profilePortsCfgPriOverCw TruthValue,
			profilePortsFxoFlashTime Integer32,
			profilePortsFxoDelTdm Integer32,
			profilePortsFxoRingtdm Integer32,
			profilePortsPstnNumberprefix DisplayString,
			profilePortsPstnNameprefix DisplayString,
			profilePortsUsePstnCid TruthValue,
			profilePortsEnableCpc TruthValue,
			profilePortsCpcTime Integer32,
			profilePortsDontDetectDT TruthValue,
	        profilePortsDelayDialingTimeout Integer32,
			profilePortsDialing  FxoDialingType,
			profilePortsTransmitNumber  TruthValue,
			profilePortsDontTransmitPrefix TruthValue,
			profilePortsRowStatus RowStatus,
			profilePortsDialToneDetectionParameters FxsToneParametrs,
			profilePortsRingBackToneDetectionParameters FxsToneParametrs,
			profilePortsBusyToneDetectionParameters FxsToneParametrs,
			profilePortsDtDetectTime Integer32,
			profilePortsDecadePulseTime Integer32,
			profilePortsDecadePauseTime Integer32,
			profilePortsFxoCallBusy TruthValue,
			profilePortsCpcRus Integer32,
			profilePortsReversalPolarityAction ReversalPolarityAction,
			profilePortsPstnActivity PstnActivityType,
			profilePortsPstnRbDetectTimeout Integer32,
			profilePortsDetectFxoLinePresence TruthValue,
			profilePortsBlockFxoLineInOutgoingDirection TruthValue,
			profilePortsStopDial TruthValue,
			profilePortsFxoMinLevelDetect Integer32,
			profilePortsModifier Integer32
		}
		
		profilePortsPlaymoh  OBJECT-TYPE
			SYNTAX     TruthValue
			MAX-ACCESS read-write
			STATUS     current
			DESCRIPTION " "
			::= { profilesPortsEntry 1 }

		profilePortsAON  OBJECT-TYPE
			SYNTAX     FxsAON
			MAX-ACCESS read-write
			STATUS     current
			DESCRIPTION " "
			::= { profilesPortsEntry 2 }
			
		profilePortsAONHideDate  OBJECT-TYPE
			SYNTAX     TruthValue
			MAX-ACCESS read-write
			STATUS     current
			DESCRIPTION " "
			::= { profilesPortsEntry 3 }
			
		profilePortsAONHideName  OBJECT-TYPE
			SYNTAX     TruthValue
			MAX-ACCESS read-write
			STATUS     current
			DESCRIPTION " "
			::= { profilesPortsEntry 4 }

		profilePortsTaxophone  OBJECT-TYPE
			SYNTAX     FxsTaxophoneType
			MAX-ACCESS read-write
			STATUS     current
			DESCRIPTION " "
			::= { profilesPortsEntry 5 }

		profilePortsMinFlashtime  OBJECT-TYPE
			SYNTAX     Integer32
			MAX-ACCESS read-write
			STATUS     current
			DESCRIPTION "70-2000(from v2.8),1000(to v2.7)"
			::= { profilesPortsEntry 6 }

		profilePortsMaxFlashtime  OBJECT-TYPE
			SYNTAX     Integer32
			MAX-ACCESS read-write
			STATUS     current
			DESCRIPTION "70-2000(from v2.8),1000(to v2.7)"
			::= { profilesPortsEntry 7 }

		profilePortsGainr  OBJECT-TYPE
			SYNTAX     Integer32
			MAX-ACCESS read-write
			STATUS     current
			DESCRIPTION " "
			::= { profilesPortsEntry 8 }

		profilePortsGaint  OBJECT-TYPE
			SYNTAX     Integer32
			MAX-ACCESS read-write
			STATUS     current
			DESCRIPTION " "
			::= { profilesPortsEntry 9 }

		profilePortsCategory  OBJECT-TYPE
			SYNTAX     Integer32
			MAX-ACCESS read-write
			STATUS     current
			DESCRIPTION " "
			::= { profilesPortsEntry 10 }

		profilePortsCallTransfer  OBJECT-TYPE
			SYNTAX     FxsProcessFlashType
			MAX-ACCESS read-write
			STATUS     obsolete
			DESCRIPTION " "
			::= { profilesPortsEntry 11 }

		profilePortsCallWaiting  OBJECT-TYPE
			SYNTAX     TruthValue
			MAX-ACCESS read-write
			STATUS     obsolete
			DESCRIPTION " "
			::= { profilesPortsEntry 12 }
			
		profilePortsCfgPriOverCw OBJECT-TYPE
			SYNTAX     TruthValue
			MAX-ACCESS read-write
			STATUS     current
			DESCRIPTION " "
			::= { profilesPortsEntry 13 }
			
		profilePortsFxoFlashTime OBJECT-TYPE
			SYNTAX     Integer32
			MAX-ACCESS read-write
			STATUS     current
			DESCRIPTION "70 1000 def 300 ms"
			::= { profilesPortsEntry 14 }
			
		profilePortsFxoDelTdm OBJECT-TYPE
			SYNTAX     Integer32
			MAX-ACCESS read-write
			STATUS     current
			DESCRIPTION "100 1000 def 200 ms"
			::= { profilesPortsEntry 15 }
			
		profilePortsFxoRingtdm OBJECT-TYPE
			SYNTAX     Integer32
			MAX-ACCESS read-write
			STATUS     current
			DESCRIPTION "2 10 def 2"
			::= { profilesPortsEntry 16 }
			
		profilePortsPstnNumberprefix OBJECT-TYPE
			SYNTAX     DisplayString
			MAX-ACCESS read-write
			STATUS     current
			DESCRIPTION "max len 20. allowed symbols 0-9A-Za-z*#_+!~$-"
			::= { profilesPortsEntry 17 }
			
		profilePortsPstnNameprefix OBJECT-TYPE
			SYNTAX     DisplayString
			MAX-ACCESS read-write
			STATUS     current
			DESCRIPTION "max len 20 "
			::= { profilesPortsEntry 18 }
			
		profilePortsUsePstnCid OBJECT-TYPE
			SYNTAX     TruthValue
			MAX-ACCESS read-write
			STATUS     current
			DESCRIPTION " "
			::= { profilesPortsEntry 19 }
			
		profilePortsEnableCpc OBJECT-TYPE
			SYNTAX     TruthValue
			MAX-ACCESS read-write
			STATUS     current
			DESCRIPTION " "
			::= { profilesPortsEntry 20 }
			
		profilePortsCpcTime OBJECT-TYPE
			SYNTAX     TruthValue
			MAX-ACCESS read-write
			STATUS     current
			DESCRIPTION " "
			::= { profilesPortsEntry 21 }
			
		profilePortsDontDetectDT OBJECT-TYPE
			SYNTAX     TruthValue
			MAX-ACCESS read-write
			STATUS     current
			DESCRIPTION "def false"
			::= { profilesPortsEntry 22 }
			
        profilePortsDelayDialingTimeout OBJECT-TYPE
			SYNTAX     Integer32
			MAX-ACCESS read-write
			STATUS     current
			DESCRIPTION "0-10 ms def 2"
			::= { profilesPortsEntry 23 }
			
		profilePortsDialing  OBJECT-TYPE
			SYNTAX     FxoDialingType
			MAX-ACCESS read-write
			STATUS     current
			DESCRIPTION " "
			::= { profilesPortsEntry 24 }
			
		profilePortsTransmitNumber  OBJECT-TYPE
			SYNTAX     TruthValue
			MAX-ACCESS read-write
			STATUS     current
			DESCRIPTION " "
			::= { profilesPortsEntry 25 }
			
		profilePortsDontTransmitPrefix OBJECT-TYPE
			SYNTAX     TruthValue
			MAX-ACCESS read-write
			STATUS     current
			DESCRIPTION " "
			::= { profilesPortsEntry 26 }
			
		profilePortsRowStatus OBJECT-TYPE
			SYNTAX     RowStatus
			MAX-ACCESS read-create
			STATUS     current
			DESCRIPTION " "
			::= { profilesPortsEntry 27 }
			
		profilePortsDialToneDetectionParameters OBJECT-TYPE
			SYNTAX     FxsToneParametrs
			MAX-ACCESS read-write
			STATUS     current
			DESCRIPTION "FXO only"
			::= { profilesPortsEntry 28 }
		
		profilePortsRingBackToneDetectionParameters OBJECT-TYPE
			SYNTAX     FxsToneParametrs
			MAX-ACCESS read-write
			STATUS     current
			DESCRIPTION "FXO only"
			::= { profilesPortsEntry 29 }
		
		profilePortsBusyToneDetectionParameters OBJECT-TYPE
			SYNTAX     FxsToneParametrs
			MAX-ACCESS read-write
			STATUS     current
			DESCRIPTION "FXO only"
			::= { profilesPortsEntry 30 }
		
		profilePortsDtDetectTime  OBJECT-TYPE
			SYNTAX     Integer32
			MAX-ACCESS read-write
			STATUS     current
			DESCRIPTION " "
			::= { profilesPortsEntry 31 }
		
		profilePortsDecadePulseTime  OBJECT-TYPE
			SYNTAX     Integer32
			MAX-ACCESS read-write
			STATUS     current
			DESCRIPTION " "
			::= { profilesPortsEntry 32 }
		
		profilePortsDecadePauseTime  OBJECT-TYPE
			SYNTAX     Integer32
			MAX-ACCESS read-write
			STATUS     current
			DESCRIPTION " "
			::= { profilesPortsEntry 33 }
			
		profilePortsFxoCallBusy  OBJECT-TYPE
			SYNTAX     TruthValue
			MAX-ACCESS read-write
			STATUS     current
			DESCRIPTION "Only for FXO. Send '503 Service unavailable' on busy (SIP)"
			::= { profilesPortsEntry 34 }
			
		profilePortsCpcRus OBJECT-TYPE
			SYNTAX     Integer32
			MAX-ACCESS read-write
			STATUS     current
			DESCRIPTION "1..10 or 0 (off)"
			::= { profilesPortsEntry 35 }
			
		profilePortsReversalPolarityAction OBJECT-TYPE
			SYNTAX     ReversalPolarityAction
			MAX-ACCESS read-write
			STATUS     obsolete
			DESCRIPTION "FXO port only. TAU-SIP 2.9. Deprecated by PstnActivity"
			::= { profilesPortsEntry 36 }
			
		profilePortsPstnActivity  OBJECT-TYPE
			SYNTAX     PstnActivityType
			MAX-ACCESS read-write
			STATUS     current
			DESCRIPTION "only for FXO. TAU-SIP 2.9. pstn_200_at_answer"
			::= { profilesPortsEntry 37 }
			
		profilePortsPstnRbDetectTimeout  OBJECT-TYPE
			SYNTAX     Integer32 (1..60)
			UNITS	   "sec"
			MAX-ACCESS read-write
			STATUS     current
			DESCRIPTION "only for FXO. TAU-SIP 2.9"
			::= { profilesPortsEntry 38 }

		profilePortsDetectFxoLinePresence  OBJECT-TYPE
			SYNTAX     TruthValue	
			MAX-ACCESS read-write
			STATUS     current
			DESCRIPTION "TAU-SIP 2.10. FXO only"
			::= { profilesPortsEntry 39 }
			
		profilePortsBlockFxoLineInOutgoingDirection  OBJECT-TYPE
			SYNTAX     TruthValue	
			MAX-ACCESS read-write
			STATUS     current
			DESCRIPTION "TAU-SIP 2.10. FXO only"
			::= { profilesPortsEntry 40 }
			
		profilePortsStopDial OBJECT-TYPE
			SYNTAX     TruthValue
			MAX-ACCESS read-write
			STATUS     current
			DESCRIPTION " "
			::= { profilesPortsEntry 41 }

		profilePortsFxoMinLevelDetect  OBJECT-TYPE
			SYNTAX     Integer32
			MAX-ACCESS read-write
			STATUS     current
			DESCRIPTION "Minimum level of detectable signal (dBm): -40..-20 (def -36)
				TAU-SIP 2.10. FXO only"
			::= { profilesPortsEntry 42 }

		profilePortsModifier  OBJECT-TYPE
			SYNTAX     Integer32
			MAX-ACCESS read-write
			STATUS     current
			DESCRIPTION "modifierNumber (1..16) at modifiersTable or -1=off
				TAU-SIP 2.12"
			::= { profilesPortsEntry 43 }
			
			
			
profilesDialPlansMIBBoundary  OBJECT-TYPE
			SYNTAX     Integer32
			MAX-ACCESS read-only
			STATUS     current
			DESCRIPTION "Dummy object to prevent GETNEXT request from poking into neighbor table."
			::= { fxsProfiles 4 }

profilesDialPlans OBJECT IDENTIFIER ::= { fxsProfiles 5 }

profilesDialPlansTable OBJECT-TYPE
	SYNTAX                SEQUENCE OF ProfilesDialPlansEntry
	MAX-ACCESS        not-accessible
	STATUS                current
	DESCRIPTION " "
	::= { profilesDialPlans 1 }

		profilesDialPlansEntry OBJECT-TYPE
		SYNTAX		ProfilesDialPlansEntry
		MAX-ACCESS	not-accessible
		STATUS		current
		DESCRIPTION " "
		INDEX { profileNumber, profileDialPlanNumber }
		::= { profilesDialPlansTable 1 }

		ProfilesDialPlansEntry ::= SEQUENCE {
			profileDialPlanHost				DisplayString,
			profileDialPlanDigits			DisplayString,
			profileDialPlanTimeout			Integer32,
			profileDialPlanMinDigits		Integer32,
			profileDialPlanType				FxsDialPlanType,
			profileDialPlanAccessMask		DisplayString,
			profileDialPlanDialtone			TruthValue,
			profileDialPlanModifier			DisplayString,
			profileDialPlanNature			FxsDialPlanNatureType,
			profileDialPlanDelnum			Integer32,
			profileDialPlanPtime 			Integer32,
			profileDialRowStatus			RowStatus,
			profileDialPlanNumber			Integer32
		}

		profileDialPlanHost  OBJECT-TYPE
			SYNTAX     DisplayString
			MAX-ACCESS read-create
			STATUS     current
			DESCRIPTION " "
			::= { profilesDialPlansEntry 1 }
			
		profileDialPlanDigits  OBJECT-TYPE
			SYNTAX     DisplayString
			MAX-ACCESS read-create
			STATUS     current
			DESCRIPTION " "
			::= { profilesDialPlansEntry 2 }
			
		profileDialPlanTimeout  OBJECT-TYPE
			SYNTAX     Integer32
			MAX-ACCESS read-create
			STATUS     current
			DESCRIPTION " "
			::= { profilesDialPlansEntry 3 }
			
		profileDialPlanMinDigits  OBJECT-TYPE
			SYNTAX     Integer32
			MAX-ACCESS read-create
			STATUS     current
			DESCRIPTION " "
			::= { profilesDialPlansEntry 4 }
			
		profileDialPlanType  OBJECT-TYPE
			SYNTAX     FxsDialPlanType
			MAX-ACCESS read-create
			STATUS     current
			DESCRIPTION " "
			::= { profilesDialPlansEntry 5 }
			
		profileDialPlanAccessMask  OBJECT-TYPE
			SYNTAX     DisplayString
			MAX-ACCESS read-create
			STATUS     current
			DESCRIPTION " "
			::= { profilesDialPlansEntry 6 }
			
		profileDialPlanDialtone  OBJECT-TYPE
			SYNTAX     TruthValue
			MAX-ACCESS read-create
			STATUS     current
			DESCRIPTION " "
			::= { profilesDialPlansEntry 7 }
			
		profileDialPlanModifier  OBJECT-TYPE
			SYNTAX     DisplayString
			MAX-ACCESS read-create
			STATUS     current
			DESCRIPTION " "
			::= { profilesDialPlansEntry 8 }
			
		profileDialPlanNature  OBJECT-TYPE
			SYNTAX     FxsDialPlanNatureType
			MAX-ACCESS read-create
			STATUS     current
			DESCRIPTION " "
			::= { profilesDialPlansEntry 9 }
			
		profileDialPlanDelnum  OBJECT-TYPE
			SYNTAX     Integer32
			MAX-ACCESS read-create
			STATUS     current
			DESCRIPTION " "
			::= { profilesDialPlansEntry 10 }
			
		profileDialPlanPtime  OBJECT-TYPE
			SYNTAX     Integer32
			MAX-ACCESS read-create
			STATUS     current
			DESCRIPTION " "
			::= { profilesDialPlansEntry 11 }

		profileDialRowStatus  OBJECT-TYPE
			SYNTAX     RowStatus
			MAX-ACCESS read-create
			STATUS     current
			DESCRIPTION " "
			::= { profilesDialPlansEntry 12 }
			
		profileDialPlanNumber  OBJECT-TYPE
			SYNTAX     Integer32 (1..300)
			MAX-ACCESS not-accessible
			STATUS     current
			DESCRIPTION " "
			::= { profilesDialPlansEntry 13 }
			
profilesRegExpDPTableMIBBoundary  OBJECT-TYPE
			SYNTAX     Integer32
			MAX-ACCESS read-only
			STATUS     current
			DESCRIPTION "Dummy object to prevent GETNEXT request from poking into neighbor table."
			::= { profilesDialPlans 2 }
			
profilesRegExpDPTable OBJECT-TYPE
	SYNTAX                SEQUENCE OF ProfilesRegExpDPEntry
	MAX-ACCESS        not-accessible
	STATUS                current
	DESCRIPTION " "
	::= { profilesDialPlans 3 }

		profilesRegExpDPEntry OBJECT-TYPE
		SYNTAX		ProfilesRegExpDPEntry
		MAX-ACCESS	not-accessible
		STATUS		current
		DESCRIPTION " "
		INDEX { profileNumber }
		::= { profilesRegExpDPTable 1 }

		ProfilesRegExpDPEntry ::= SEQUENCE {
			profileRegExpDialOn  TruthValue,
			profileRegExpDialProtocol  TauDialProtocolType,
			profileRegExpDialText  OCTET STRING,
			profileRegExpDialRowStatus RowStatus
		}
		
	profileRegExpDialOn  OBJECT-TYPE
			SYNTAX     TruthValue
			MAX-ACCESS read-write
			STATUS     current
			DESCRIPTION ""
			::= { profilesRegExpDPEntry 1 }
			
	profileRegExpDialProtocol  OBJECT-TYPE
			SYNTAX     TauDialProtocolType
			MAX-ACCESS read-write
			STATUS     current
			DESCRIPTION ""
			::= { profilesRegExpDPEntry 2 }
			
	profileRegExpDialText  OBJECT-TYPE
			SYNTAX     OCTET STRING
			MAX-ACCESS read-write
			STATUS     current
			DESCRIPTION ""
			::= { profilesRegExpDPEntry 3 }
			
	profileRegExpDialRowStatus  OBJECT-TYPE
			SYNTAX     RowStatus
			MAX-ACCESS read-create
			STATUS     current
			DESCRIPTION " "
			::= { profilesRegExpDPEntry 4 }
			
			
profilesCodecs OBJECT IDENTIFIER ::= { fxsProfiles 7 }

profilesCodecsTable OBJECT-TYPE
	SYNTAX                SEQUENCE OF ProfilesCodecsEntry
	MAX-ACCESS        not-accessible
	STATUS                current
	DESCRIPTION " "
	::= { profilesCodecs 1 }

		profilesCodecsEntry OBJECT-TYPE
		SYNTAX		ProfilesCodecsEntry
		MAX-ACCESS	not-accessible
		STATUS		current
		DESCRIPTION " "
		INDEX { profileNumber }
		::= { profilesCodecsTable 1 }

		ProfilesCodecsEntry ::= SEQUENCE {
			useG711A Integer32,
			useG711U Integer32,
			useG726to32 Integer32,
			useG723 Integer32,
			useG729B Integer32,
			useG729A Integer32,
			g711Ptime Integer32,
			g729Ptime Integer32,
			g723Ptime Integer32,
			g726to32Ptime Integer32,
			g726to32PT Integer32,	
			dtmfTransfer TauDtmfTransferType,
			flashTransfer TauFlashTransferType,
			faxDetectDirection TauFaxDirectionType,
			faxTransferCodec TauFaxTransferType,
			slaveFaxTransferCodec TauFaxTransferSlaveType,
			modemTransfer TauModemTransferType,
			rfc2833PT Integer32,	
			silenceSuppression TruthValue,	
			echoCanceller TruthValue, 	
			nlpDisable TruthValue, 	
			comfortNoise TruthValue,
			rtcpTimer Integer32,	 
			rtcpControlPeriod Integer32,	 
			ciscoNsePT Integer32,	
			t38MaxDatagramSize Integer32, 	
			t38Bitrate Integer32,
			modemFaxDelay Integer32,
			voiceMode TauVoiceModeType,
			voiceDelayMin Integer32,
			voiceDelayMax Integer32,
			voiceDeletionThreshold Integer32,
			voiceDeletionMode TauvoiceDeletionModeType,
			profilesCodecsRowStatus RowStatus,
			rtcpXR TruthValue,
			rfc3264PtCommon TruthValue
		}
					
		--Codecs configuration:
		--List of codecs in preffered order:
		
		useG711A  OBJECT-TYPE
			SYNTAX     Integer32
			MAX-ACCESS read-write
			STATUS     current
			DESCRIPTION "order by 1 to N or 0(not use)"
			::= { profilesCodecsEntry 1 }
			
		useG711U  OBJECT-TYPE
			SYNTAX     Integer32
			MAX-ACCESS read-write
			STATUS     current
			DESCRIPTION "order by 1 to N or 0(not use)"
			::= { profilesCodecsEntry 2 }
				
		useG726to32  OBJECT-TYPE
			SYNTAX     Integer32
			MAX-ACCESS read-write
			STATUS     current
			DESCRIPTION "order by 1 to N or 0(not use)"
			::= { profilesCodecsEntry 3 }
					
		useG723  OBJECT-TYPE
			SYNTAX     Integer32
			MAX-ACCESS read-write
			STATUS     current
			DESCRIPTION "order by 1 to N or 0(not use)"
			::= { profilesCodecsEntry 4 }
					
		useG729B  OBJECT-TYPE
			SYNTAX     Integer32
			MAX-ACCESS read-write
			STATUS     current
			DESCRIPTION "order by 1 to N or 0(not use)"
			::= { profilesCodecsEntry 6 }
					
		useG729A  OBJECT-TYPE
			SYNTAX     Integer32
			MAX-ACCESS read-write
			STATUS     current
			DESCRIPTION "order by 1 to N or 0(not use)"
			::= { profilesCodecsEntry 7 }
					
			
		--Packet coder time:
		
		g711Ptime  OBJECT-TYPE
			SYNTAX     Integer32
			MAX-ACCESS read-write
			STATUS     current
			DESCRIPTION "10,20,30..60"
			::= { profilesCodecsEntry 8 }
				
		g729Ptime  OBJECT-TYPE
			SYNTAX     Integer32
			MAX-ACCESS read-write
			STATUS     current
			DESCRIPTION "10,20,30..80"
			::= { profilesCodecsEntry 9 }
					
		g723Ptime  OBJECT-TYPE
			SYNTAX     Integer32
			MAX-ACCESS read-write
			STATUS     current
			DESCRIPTION "30,60,90"
			::= { profilesCodecsEntry 10 }
					
		g726to32Ptime  OBJECT-TYPE
			SYNTAX     Integer32
			MAX-ACCESS read-write
			STATUS     current
			DESCRIPTION "10,20,30"
			::= { profilesCodecsEntry 11 }
					
		g726to32PT  OBJECT-TYPE
			SYNTAX     Integer32
			MAX-ACCESS read-write
			STATUS     current
			DESCRIPTION "96..127"
			::= { profilesCodecsEntry 12 }
					
		
		--Features:
		
		dtmfTransfer  OBJECT-TYPE
			SYNTAX     TauDtmfTransferType
			MAX-ACCESS read-write
			STATUS     current
			DESCRIPTION ""
			::= { profilesCodecsEntry 13 }
				
		flashTransfer  OBJECT-TYPE
			SYNTAX     TauFlashTransferType
			MAX-ACCESS read-write
			STATUS     current
			DESCRIPTION ""
			::= { profilesCodecsEntry 14 }
				
		faxDetectDirection  OBJECT-TYPE
			SYNTAX     TauFaxDirectionType
			MAX-ACCESS read-write
			STATUS     current
			DESCRIPTION ""
			::= { profilesCodecsEntry 15 }
				
		faxTransferCodec  OBJECT-TYPE
			SYNTAX     TauFaxTransferType
			MAX-ACCESS read-write
			STATUS     current
			DESCRIPTION ""
			::= { profilesCodecsEntry 16 }
				
		slaveFaxTransferCodec  OBJECT-TYPE
			SYNTAX     TauFaxTransferSlaveType
			MAX-ACCESS read-write
			STATUS     current
			DESCRIPTION ""
			::= { profilesCodecsEntry 17 }
				
		modemTransfer  OBJECT-TYPE
			SYNTAX     TauModemTransferType
			MAX-ACCESS read-write
			STATUS     current
			DESCRIPTION ""
			::= { profilesCodecsEntry 18 }
				
		rfc2833PT  OBJECT-TYPE
			SYNTAX     Integer32 
			MAX-ACCESS read-write
			STATUS     current
			DESCRIPTION "96..127"
			::= { profilesCodecsEntry 19 }
					
		silenceSuppression  OBJECT-TYPE
			SYNTAX     TruthValue
			MAX-ACCESS read-write
			STATUS     current
			DESCRIPTION ""
			::= { profilesCodecsEntry 20 }
					
		echoCanceller  OBJECT-TYPE
			SYNTAX     TruthValue 
			MAX-ACCESS read-write
			STATUS     current
			DESCRIPTION ""
			::= { profilesCodecsEntry 21 }
					
		nlpDisable  OBJECT-TYPE
			SYNTAX     TruthValue 
			MAX-ACCESS read-write
			STATUS     current
			DESCRIPTION ""
			::= { profilesCodecsEntry 22 }
					
		comfortNoise  OBJECT-TYPE
			SYNTAX     TruthValue
			MAX-ACCESS read-write
			STATUS     current
			DESCRIPTION ""
			::= { profilesCodecsEntry 23 }
					
		
		--RTCP Configuration:
		
		rtcpTimer  OBJECT-TYPE
			SYNTAX     Integer32
			MAX-ACCESS read-write
			STATUS     current
			DESCRIPTION "5..65535"
			::= { profilesCodecsEntry 24 }
					 
		rtcpControlPeriod  OBJECT-TYPE
			SYNTAX     Integer32
			MAX-ACCESS read-write
			STATUS     current
			DESCRIPTION "2..65535"
			::= { profilesCodecsEntry 25 }
					 
		
		--Cisco NSE Configuration:
		
		ciscoNsePT  OBJECT-TYPE
			SYNTAX     Integer32
			MAX-ACCESS read-write
			STATUS     current
			DESCRIPTION "96..127"
			::= { profilesCodecsEntry 26 }
					
		
		--T.38 Configuration:
		
		t38MaxDatagramSize  OBJECT-TYPE
			SYNTAX     Integer32
			MAX-ACCESS read-write
			STATUS     current
			DESCRIPTION "272..512"
			::= { profilesCodecsEntry 27 }
				 	
		t38Bitrate  OBJECT-TYPE
			SYNTAX     Integer32
			MAX-ACCESS read-write
			STATUS     current
			DESCRIPTION "9600,14400"
			::= { profilesCodecsEntry 28 }
				
		
		--Jitter buffer Configuration:
		--Modem/Fax pass-thru:
		
		modemFaxDelay  OBJECT-TYPE
			SYNTAX     Integer32
			UNITS		"ms"
			MAX-ACCESS read-write
			STATUS     current
			DESCRIPTION "0..200"
			::= { profilesCodecsEntry 29 }
				
				
		--Voice:
		
		voiceMode  OBJECT-TYPE
			SYNTAX     TauVoiceModeType
			MAX-ACCESS read-write
			STATUS     current
			DESCRIPTION ""
			::= { profilesCodecsEntry 30 }
				
		voiceDelayMin  OBJECT-TYPE
			SYNTAX     Integer32
			UNITS		"ms"
			MAX-ACCESS read-write
			STATUS     current
			DESCRIPTION "0..200"
			::= { profilesCodecsEntry 31 }
				
		voiceDelayMax  OBJECT-TYPE
			SYNTAX     Integer32
			UNITS		"ms"
			MAX-ACCESS read-write
			STATUS     current
			DESCRIPTION "2..200"
			::= { profilesCodecsEntry 32 }
				
		voiceDeletionThreshold  OBJECT-TYPE
			SYNTAX     Integer32
			UNITS		"ms"
			MAX-ACCESS read-write
			STATUS     current
			DESCRIPTION "200..500"
			::= { profilesCodecsEntry 33 }
				
		voiceDeletionMode  OBJECT-TYPE
			SYNTAX     TauvoiceDeletionModeType
			MAX-ACCESS read-write
			STATUS     current
			DESCRIPTION ""
			::= { profilesCodecsEntry 34 }
			
		profilesCodecsRowStatus  OBJECT-TYPE
			SYNTAX     RowStatus
			MAX-ACCESS read-create
			STATUS     current
			DESCRIPTION " "
			::= { profilesCodecsEntry 35 }

		--RTCP Configuration (continuation):
		
		rtcpXR  OBJECT-TYPE
			SYNTAX     TruthValue 
			MAX-ACCESS read-write
			STATUS     current
			DESCRIPTION ""
			::= { profilesCodecsEntry 36 }
			
		rfc3264PtCommon  OBJECT-TYPE
			SYNTAX     TruthValue 
			MAX-ACCESS read-write
			STATUS     current
			DESCRIPTION "Decoding rfc2833 with PT from answer SDP
							TAU-SIP 2.9"
			::= { profilesCodecsEntry 37 }
				
				
tauSnmpConfiguration OBJECT IDENTIFIER ::= { fxs72 31 }
tauTrapSink  OBJECT-TYPE
			SYNTAX     OCTET STRING
			MAX-ACCESS read-write
			STATUS     current
			DESCRIPTION ""
			::= { tauSnmpConfiguration 1 }
tauTrapType  OBJECT-TYPE
			SYNTAX     TauTrapVersion
			MAX-ACCESS read-write
			STATUS     current
			DESCRIPTION "1,2"
			::= { tauSnmpConfiguration 2 }
tauSysName  OBJECT-TYPE
			SYNTAX     OCTET STRING
			MAX-ACCESS read-write
			STATUS     current
			DESCRIPTION ""
			::= { tauSnmpConfiguration 3 }
tauSysContact  OBJECT-TYPE
			SYNTAX     OCTET STRING
			MAX-ACCESS read-write
			STATUS     current
			DESCRIPTION ""
			::= { tauSnmpConfiguration 4 }
tauSysLocation  OBJECT-TYPE
			SYNTAX     OCTET STRING
			MAX-ACCESS read-write
			STATUS     current
			DESCRIPTION ""
			::= { tauSnmpConfiguration 5 }
tauRoCommunity  OBJECT-TYPE
			SYNTAX     OCTET STRING
			MAX-ACCESS read-write
			STATUS     current
			DESCRIPTION ""
			::= { tauSnmpConfiguration 6 }
tauRwCommunity  OBJECT-TYPE
			SYNTAX     OCTET STRING
			MAX-ACCESS read-write
			STATUS     current
			DESCRIPTION ""
			::= { tauSnmpConfiguration 7 }
tauTrapCommunity  OBJECT-TYPE
			SYNTAX     OCTET STRING
			MAX-ACCESS read-write
			STATUS     current
			DESCRIPTION ""
			::= { tauSnmpConfiguration 8 }

tauUserV3Name OBJECT-TYPE
			SYNTAX     OCTET STRING
			MAX-ACCESS read-write
			STATUS     current
			DESCRIPTION ""
			::= { tauSnmpConfiguration 9 }
tauUserV3Password OBJECT-TYPE
			SYNTAX     OCTET STRING
			MAX-ACCESS read-write
			STATUS     current
			DESCRIPTION ""
			::= { tauSnmpConfiguration 10 }
tauViewV3Type OBJECT-TYPE
			SYNTAX     TauUserViewType
			MAX-ACCESS read-write
			STATUS     current
			DESCRIPTION "1read,2readwrite"
			::= { tauSnmpConfiguration 11 }

tauRestartSnmp OBJECT-TYPE
			SYNTAX     TruthValue
			MAX-ACCESS read-write
			STATUS     current
			DESCRIPTION "set True to restart snmpd with new snmp-config"
			::= { tauSnmpConfiguration 12 }
			
			
tauMegacoTrapsTable OBJECT-TYPE
	SYNTAX                SEQUENCE OF TauMegacoTrapsEntry
	MAX-ACCESS        not-accessible
	STATUS                current
	DESCRIPTION "TAU-MEGACO traps table. also used for SMG SBC MSR"
	::= { fxs72 32 }

	tauMegacoTrapsEntry OBJECT-TYPE
		SYNTAX		TauMegacoTrapsEntry
		MAX-ACCESS	not-accessible
		STATUS		current
		DESCRIPTION " "
		INDEX { tauMegacoTrapId }
		::= { tauMegacoTrapsTable 1 }

		TauMegacoTrapsEntry ::= SEQUENCE {
			tauMegacoTrapId		Integer32,
			tauMegacoTrapType	TauMegacoTrapVersion,
			tauMegacoTrapHost   DisplayString,
			tauMegacoTrapCommunity DisplayString,
			tauMegacoTrapPort Integer32,
			tauMegacoTrapRowStatus RowStatus }
			
		
		tauMegacoTrapId  OBJECT-TYPE
			SYNTAX     Integer32 (1..100)
			MAX-ACCESS not-accessible
			STATUS     current
			DESCRIPTION ""
			::= { tauMegacoTrapsEntry 1 }
			
		tauMegacoTrapType  OBJECT-TYPE
			SYNTAX     TauMegacoTrapVersion
			MAX-ACCESS read-write
			STATUS     current
			DESCRIPTION ""
			::= { tauMegacoTrapsEntry 2 }
			
		tauMegacoTrapHost  OBJECT-TYPE
			SYNTAX     DisplayString
			MAX-ACCESS read-write
			STATUS     current
			DESCRIPTION ""
			::= { tauMegacoTrapsEntry 3 }
			
		tauMegacoTrapCommunity  OBJECT-TYPE
			SYNTAX     DisplayString
			MAX-ACCESS read-write
			STATUS     current
			DESCRIPTION ""
			::= { tauMegacoTrapsEntry 4 }
			
		tauMegacoTrapPort  OBJECT-TYPE
			SYNTAX     Integer32
			MAX-ACCESS read-write
			STATUS     current
			DESCRIPTION ""
			::= { tauMegacoTrapsEntry 5 }
			
		tauMegacoTrapRowStatus  OBJECT-TYPE
			SYNTAX     RowStatus
			MAX-ACCESS read-create
			STATUS     current
			DESCRIPTION ""
			::= { tauMegacoTrapsEntry 6 }


fxoSerialGroups OBJECT IDENTIFIER ::= { fxs72 34 }

	fxoSerialGroupsTable OBJECT-TYPE
        SYNTAX      SEQUENCE OF FxoSerialGroupsEntry
	    MAX-ACCESS  not-accessible
	    STATUS      current
	    DESCRIPTION " "
	::= { fxoSerialGroups 1 }

		fxoSerialGroupsEntry OBJECT-TYPE
		    SYNTAX		FxoSerialGroupsEntry
		    MAX-ACCESS  not-accessible
		    STATUS		current
	    	DESCRIPTION " "
		    INDEX       { fxsDialPlanNumber }
		::= { fxoSerialGroupsTable 1 }

		FxoSerialGroupsEntry ::= SEQUENCE {
			fxoSerialGroupsPhone		        DisplayString,
			fxoSerialGroupsEnabled		        Integer32,
			fxoSerialGroupsBusyType		        FxoGroupBusyType,
			fxoSerialGroupsSipPort 	            Integer32,
			fxoSerialGroupsAuthName 	        DisplayString,
			fxoSerialGroupsAuthPass 	        DisplayString,
			fxoSerialGroupsPorts 		        DisplayString,
			fxoSerialGroupsSipProfile           Integer32,
			fxoSerialGroupsTransmitNumber       TruthValue,
			fxoSerialGroupsDontTransmitPrefix   TruthValue,
			fxoSerialGroupsRowStatus	        RowStatus,
			fxoSerialGroupsSend503OnBusy   		TruthValue,
			fxoSerialGroupsType					FxoGroupType
		}

		fxoSerialGroupsPhone  OBJECT-TYPE
			SYNTAX     DisplayString
			MAX-ACCESS read-write
			STATUS     current
			DESCRIPTION " "
			::= { fxoSerialGroupsEntry 1 }
			
		fxoSerialGroupsEnabled  OBJECT-TYPE
			SYNTAX     FxsGroupSerialEnableType
			MAX-ACCESS read-write
			STATUS     current
			DESCRIPTION " "
			::= { fxoSerialGroupsEntry 2 }
			
		fxoSerialGroupsBusyType  OBJECT-TYPE
			SYNTAX     FxoGroupBusyType
			MAX-ACCESS read-write
			STATUS     current
			DESCRIPTION " "
			::= { fxoSerialGroupsEntry 3 }
			
		fxoSerialGroupsSipPort  OBJECT-TYPE
			SYNTAX     Integer32
			MAX-ACCESS read-write
			STATUS     current
			DESCRIPTION " "
			::= { fxoSerialGroupsEntry 4 }
			
		fxoSerialGroupsAuthName  OBJECT-TYPE
			SYNTAX     DisplayString
			MAX-ACCESS read-write
			STATUS     current
			DESCRIPTION " "

			::= { fxoSerialGroupsEntry 5 }
			
		fxoSerialGroupsAuthPass  OBJECT-TYPE
			SYNTAX     DisplayString
			MAX-ACCESS read-write
			STATUS     current
			DESCRIPTION " "
			::= { fxoSerialGroupsEntry 6 }
			
		fxoSerialGroupsPorts  OBJECT-TYPE
			SYNTAX     DisplayString
			MAX-ACCESS read-write
			STATUS     current
			DESCRIPTION " "
			::= { fxoSerialGroupsEntry 7 }
			
		fxoSerialGroupsSipProfile  OBJECT-TYPE
			SYNTAX     Integer32
			MAX-ACCESS read-write
			STATUS     current
			DESCRIPTION " "
			::= { fxoSerialGroupsEntry 8 }
        
		fxoSerialGroupsTransmitNumber  OBJECT-TYPE
			SYNTAX     TruthValue
			MAX-ACCESS read-write
			STATUS     current
			DESCRIPTION " "
			::= { fxoSerialGroupsEntry 9 }
            
		fxoSerialGroupsDontTransmitPrefix  OBJECT-TYPE
			SYNTAX     TruthValue
			MAX-ACCESS read-write
			STATUS     current
			DESCRIPTION " "
			::= { fxoSerialGroupsEntry 10 }
			
		fxoSerialGroupsRowStatus  OBJECT-TYPE
			SYNTAX     RowStatus
			MAX-ACCESS read-create
			STATUS     current
			DESCRIPTION " "
			::= { fxoSerialGroupsEntry 11 }
			
		fxoSerialGroupsSend503OnBusy  OBJECT-TYPE
			SYNTAX     TruthValue
			MAX-ACCESS read-write
			STATUS     current
			DESCRIPTION "Send 503 Service unavailable on busy (SIP) 
							TAU-SIP 2.7"
			::= { fxoSerialGroupsEntry 12 }
			
		fxoSerialGroupsType OBJECT-TYPE
			SYNTAX     FxoGroupType
			MAX-ACCESS read-write
			STATUS     current
			DESCRIPTION "group type 
							TAU-SIP 2.9"
			::= { fxoSerialGroupsEntry 13 }
	
	fxsNetwork OBJECT IDENTIFIER ::= { fxs72 35 }
	
		fxsAutoupdateSettings OBJECT IDENTIFIER ::= { fxsNetwork 1 }
		
			fxsEnableAutoupdate OBJECT-TYPE
				SYNTAX		TruthValue
				MAX-ACCESS	read-write
				STATUS		current
				DESCRIPTION	"true if autoupdate enabled, false otherwise"
			::= { fxsAutoupdateSettings 1 }
			
			fxsSource OBJECT-TYPE
				SYNTAX		FxsNetworkAutoupdateSourceType
				MAX-ACCESS	read-write
				STATUS		current
				DESCRIPTION	"dhcp, dhcpVlan1, dhcpVlan2, dhcpVlan3, noDhcp"
			::= { fxsAutoupdateSettings 2 }
			
			fxsTFTPServer OBJECT-TYPE
				SYNTAX		DisplayString (SIZE (0..128))
				MAX-ACCESS	read-write
				STATUS		current
				DESCRIPTION	"IP or domain name of tftp server
							2.13 - 128 symbols"
			::= { fxsAutoupdateSettings 3 }
			
			fxsConfigurationFile OBJECT-TYPE
				SYNTAX		DisplayString (SIZE (0..80))
				MAX-ACCESS	read-write
				STATUS		current
				DESCRIPTION	"path to configuration file (tau.dat)"
			::= { fxsAutoupdateSettings 4 }
			
			fxsFirmwareVersion OBJECT-TYPE
				SYNTAX		DisplayString (SIZE (0..80))
				MAX-ACCESS	read-write
				STATUS		current
				DESCRIPTION	"path to version file (tau.versions)"
			::= { fxsAutoupdateSettings 5 }
			
			fxsConfigurationUpdateInterval OBJECT-TYPE
				SYNTAX		Integer32 (0 | 60..65535)
				MAX-ACCESS	read-write
				STATUS		current
				DESCRIPTION	"configuration update interval (s): 0 - disabled or 60..65535"
			::= { fxsAutoupdateSettings 6 }
			
			fxsFirmwareUpdateInterval OBJECT-TYPE
				SYNTAX		Integer32 (0 | 60..65535)
				MAX-ACCESS	read-write
				STATUS		current
				DESCRIPTION	"firmware update interval (s): 0 - disabled or 60..65535"
			::= { fxsAutoupdateSettings 7 }
			
			autoupdateProtocol OBJECT-TYPE
				SYNTAX		AutoupdateProtocolType
				MAX-ACCESS	read-write
				STATUS		current
				DESCRIPTION	"tftp|ftp|http|https
							TAU-SIP 2.12"
			::= { fxsAutoupdateSettings 8 }
			
			autoupdateAuth OBJECT-TYPE
				SYNTAX		TruthValue
				MAX-ACCESS	read-write
				STATUS		current
				DESCRIPTION	"TAU-SIP 2.12"
			::= { fxsAutoupdateSettings 9 }
			
			autoupdateUser OBJECT-TYPE
				SYNTAX		DisplayString (SIZE (0..80))
				MAX-ACCESS	read-write
				STATUS		current
				DESCRIPTION	"TAU-SIP 2.12"
			::= { fxsAutoupdateSettings 10 }
			
			autoupdatePassword OBJECT-TYPE
				SYNTAX		DisplayString (SIZE (0..80))
				MAX-ACCESS	read-write
				STATUS		current
				DESCRIPTION	"TAU-SIP 2.12"
			::= { fxsAutoupdateSettings 11 }
			
			
		fxsVoipGeneral OBJECT IDENTIFIER ::= { fxs72 37 }
	
		fansForceEnable OBJECT-TYPE
				SYNTAX		TruthValue
				MAX-ACCESS	read-write
				STATUS		current
				DESCRIPTION	"true if fans ON, false otherwise"
			::= { fxsVoipGeneral 1 }
			
		fansThresholdTemperature OBJECT-TYPE
				SYNTAX		Integer32 (35..55)
				MAX-ACCESS	read-write
				STATUS		current
				DESCRIPTION	"fans_threshold_temperature (C): 35..55 default 55"
			::= { fxsVoipGeneral 2 }

		deviceName OBJECT-TYPE
				SYNTAX		DisplayString (SIZE (0..128))
				MAX-ACCESS	read-write
				STATUS		current
				DESCRIPTION	"Device name TAU-SIP 2.9. max 20 symbols
								2.13 - 128 symbols"
			::= { fxsVoipGeneral 3 }
			 	
		startTimer OBJECT-TYPE
				SYNTAX		Integer32
				MAX-ACCESS	read-write
				STATUS		current
				DESCRIPTION	"Start timer (sec, from 10 to 300) TAU-SIP 2.9"
			::= { fxsVoipGeneral 4 }
			
		durationTimer OBJECT-TYPE
				SYNTAX		Integer32
				MAX-ACCESS	read-write
				STATUS		current
				DESCRIPTION	"Duration timer (sec, from 10 to 300) TAU-SIP 2.9"
			::= { fxsVoipGeneral 5 }
			 
		waitAnswerTimer OBJECT-TYPE
				SYNTAX		Integer32
				MAX-ACCESS	read-write
				STATUS		current
				DESCRIPTION	"Wait answer timer (sec, from 40 to 300) TAU-SIP 2.9"
			::= { fxsVoipGeneral 6 } 
			
		powerMode OBJECT-TYPE
				SYNTAX		PowerMode
				MAX-ACCESS	read-write
				STATUS		current
				DESCRIPTION	"TAU-SIP 2.9. for 32M-revB"
			::= { fxsVoipGeneral 7 } 

		siptUsePrefix OBJECT-TYPE
				SYNTAX		TruthValue
				MAX-ACCESS	read-write
				STATUS		current
				DESCRIPTION	"Use prefix (SIP-T) TAU-SIP 2.10"
			::= { fxsVoipGeneral 8 }
			
		siptPrefix OBJECT-TYPE
				SYNTAX		DisplayString
				MAX-ACCESS	read-write
				STATUS		current
				DESCRIPTION	"Prefix (SIP-T) TAU-SIP 2.10. max 20 symbols"
			::= { fxsVoipGeneral 9 }
		
			
		fxsSyslog OBJECT IDENTIFIER ::= { fxs72 38 }
	
		-- Syslog configuration
		
		runSyslog OBJECT-TYPE
            SYNTAX TruthValue
            MAX-ACCESS read-write
            STATUS current
            DESCRIPTION
               "Run syslog on startup"
            ::= { fxsSyslog 1 }
            
        syslogAddr OBJECT-TYPE
            SYNTAX DisplayString
            MAX-ACCESS read-write
            STATUS current
            DESCRIPTION
               " "
            ::= { fxsSyslog 2 }
            
        syslogPort OBJECT-TYPE
            SYNTAX Integer32
            MAX-ACCESS read-write
            STATUS current
            DESCRIPTION
               " "
            ::= { fxsSyslog 3 }
        
        -- APPLICATION
        
        appAlarm OBJECT-TYPE
            SYNTAX TruthValue
            MAX-ACCESS read-write
            STATUS current
            DESCRIPTION
               " TAU-SIP 2.9"
            ::= { fxsSyslog 13 } 
         
        appErr OBJECT-TYPE
            SYNTAX TruthValue
            MAX-ACCESS read-write
            STATUS current
            DESCRIPTION
               " "
            ::= { fxsSyslog 4 }
            
        appWarn OBJECT-TYPE
            SYNTAX TruthValue
            MAX-ACCESS read-write
            STATUS current
            DESCRIPTION
               " "
            ::= { fxsSyslog 5 }
            
        appInfo OBJECT-TYPE
            SYNTAX TruthValue
            MAX-ACCESS read-write
            STATUS current
            DESCRIPTION
               " "
            ::= { fxsSyslog 6 }
            
        appDbg OBJECT-TYPE
            SYNTAX TruthValue
            MAX-ACCESS read-write
            STATUS current
            DESCRIPTION
               " "
            ::= { fxsSyslog 7 } 

        -- SIP
         
        sipLevel OBJECT-TYPE
            SYNTAX SipLogLevel
            MAX-ACCESS read-write
            STATUS current
            DESCRIPTION
               " "
            ::= { fxsSyslog 8 }
        
        -- H323
            
        h323Level OBJECT-TYPE
            SYNTAX H323LogLevel
            MAX-ACCESS read-write
            STATUS current
            DESCRIPTION
               " "
            ::= { fxsSyslog 9 }
        
        -- VAPI
         
        vapiEnabled OBJECT-TYPE
            SYNTAX TruthValue
            MAX-ACCESS read-write
            STATUS current
            DESCRIPTION
               " "
            ::= { fxsSyslog 10 }
         
        vapiLibLevel OBJECT-TYPE
            SYNTAX VapiLibLogLevel
            MAX-ACCESS read-write
            STATUS current
            DESCRIPTION
               " "
            ::= { fxsSyslog 11 }   
         
        vapiAppLevel OBJECT-TYPE
            SYNTAX VapiAppLogLevel
            MAX-ACCESS read-write
            STATUS current
            DESCRIPTION
               " "
            ::= { fxsSyslog 12 }   
           
       
    testPortsTable OBJECT-TYPE
		SYNTAX SEQUENCE OF TestPortsTableEntry
		MAX-ACCESS not-accessible
		STATUS current
		DESCRIPTION "TAU-SIP 2.7"
		::= {  fxs72 39 }

		testPortsTableEntry OBJECT-TYPE
			SYNTAX		TestPortsTableEntry
			MAX-ACCESS	not-accessible
			STATUS		current
			DESCRIPTION " "
			INDEX { fxsPortNumber }
			::= { testPortsTable 1 }
                  
			TestPortsTableEntry ::= SEQUENCE {
				portTestTestStatus FxsPortTestStatus,

				portTestTestStartTime Unsigned32,
				portTestLastTestStartTime Unsigned32,
				portTestLastTestEndTime Unsigned32,

				portTestResultFlag FxsPortTestFlag,
				portTestRingU DisplayString,
				portTestTipU DisplayString,
				portTestShortVbat DisplayString,
				portTestResistTr DisplayString,
				portTestResistTg DisplayString,
				portTestResistRg DisplayString,
				portTestCapacityTr DisplayString,
				portTestCapacityTg DisplayString,
				portTestCapacityRg DisplayString,
				
				portTestRunTest Integer32
			}
			
				portTestTestStatus OBJECT-TYPE
               		SYNTAX FxsPortTestStatus
               		MAX-ACCESS read-only
               		STATUS current
               		DESCRIPTION " "
               		::= { testPortsTableEntry 1 }

				portTestTestStartTime OBJECT-TYPE
               		SYNTAX Unsigned32
               		MAX-ACCESS read-only
               		STATUS current
               		DESCRIPTION "time in sec by epoch"
               		::= { testPortsTableEntry 2 }
				portTestLastTestStartTime OBJECT-TYPE
               		SYNTAX Unsigned32
               		MAX-ACCESS read-only
               		STATUS current
               		DESCRIPTION "time in sec by epoch"
               		::= { testPortsTableEntry 3 }
				portTestLastTestEndTime OBJECT-TYPE
               		SYNTAX Unsigned32
               		MAX-ACCESS read-only
               		STATUS current
               		DESCRIPTION "time in sec by epoch"
               		::= { testPortsTableEntry 4 }

				portTestResultFlag OBJECT-TYPE
               		SYNTAX FxsPortTestFlag
               		MAX-ACCESS read-only
               		STATUS current
               		DESCRIPTION " "
               		::= { testPortsTableEntry 5 }
				
				portTestRingU OBJECT-TYPE
               		SYNTAX DisplayString
               		UNITS "V"
               		MAX-ACCESS read-only
               		STATUS current
               		DESCRIPTION "Ub (External voltage RING)"
               		::= { testPortsTableEntry 6 }
				portTestTipU OBJECT-TYPE
               		SYNTAX DisplayString
               		UNITS "V"
               		MAX-ACCESS read-only
               		STATUS current
               		DESCRIPTION "Ua (External voltage TIP)"
               		::= { testPortsTableEntry 7 }
				portTestShortVbat OBJECT-TYPE
               		SYNTAX DisplayString
               		UNITS "V"
               		MAX-ACCESS read-only
               		STATUS current
               		DESCRIPTION "Ubat (Short line supply voltage)"
               		::= { testPortsTableEntry 8 }
				
				portTestResistTr OBJECT-TYPE
               		SYNTAX DisplayString
               		UNITS "kOhm"
               		MAX-ACCESS read-only
               		STATUS current
               		DESCRIPTION "Rab (Resist TIP-RING)"
               		::= { testPortsTableEntry 9 }
				portTestResistTg OBJECT-TYPE
               		SYNTAX DisplayString
               		UNITS "kOhm"
               		MAX-ACCESS read-only
               		STATUS current
               		DESCRIPTION "Ra (Resist TIP-GND)"
               		::= { testPortsTableEntry 10 }
				portTestResistRg OBJECT-TYPE
               		SYNTAX DisplayString
               		UNITS "kOhm"
               		MAX-ACCESS read-only
               		STATUS current
               		DESCRIPTION "Rb (Resist RING-GND)"
               		::= { testPortsTableEntry 11 }
				
				portTestCapacityTr OBJECT-TYPE
               		SYNTAX DisplayString
               		UNITS "uF"
               		MAX-ACCESS read-only
               		STATUS current
               		DESCRIPTION "Cab (Capacity TIP-RING)"
               		::= { testPortsTableEntry 12 }
				portTestCapacityTg OBJECT-TYPE
               		SYNTAX DisplayString
               		UNITS "uF"
               		MAX-ACCESS read-only
               		STATUS current
               		DESCRIPTION "Ca (Capacity TIP-GND)"
               		::= { testPortsTableEntry 13 }
				portTestCapacityRg OBJECT-TYPE
               		SYNTAX DisplayString
               		UNITS "uF"
               		MAX-ACCESS read-only
               		STATUS current
               		DESCRIPTION "Cb (Capacity RING-GND)"
               		::= { testPortsTableEntry 14 }
				
				portTestRunTest OBJECT-TYPE
               		SYNTAX Integer32
               		MAX-ACCESS read-write
               		STATUS current
               		DESCRIPTION "set 1 to run test"
               		::= { testPortsTableEntry 15 }    

monitorSerialGroupsMIBBoundary  OBJECT-TYPE
			SYNTAX     Integer32
			MAX-ACCESS read-only
			STATUS     current
			DESCRIPTION "Dummy object to prevent GETNEXT request from poking into neighbor table."
			::= { fxs72 40 }

monitorSerialGroupsTable OBJECT-TYPE
		SYNTAX SEQUENCE OF MonitorSerialGroupsEntry
		MAX-ACCESS not-accessible
		STATUS current
		DESCRIPTION "TAU-SIP 2.7"
		::= {  fxs72 41 }

		monitorSerialGroupsEntry OBJECT-TYPE
			SYNTAX		MonitorSerialGroupsEntry
			MAX-ACCESS	not-accessible
			STATUS		current
			DESCRIPTION " "
			INDEX { serialGroupNumber }
			::= { monitorSerialGroupsTable 1 }
                  
			MonitorSerialGroupsEntry ::= SEQUENCE {
				serialGroupNumber Unsigned32,
				serialGroupPhone DisplayString,
				serialGroupRegistrationState GroupRegistrationState,
				serialGroupRegistrationHost DisplayString,
				serialGroupLastRegistrationAt DisplayString,
				serialGroupNextRegistrationAfter DisplayString,
				serialGroupH323GK DisplayString
			}
               		
            serialGroupNumber OBJECT-TYPE
               		SYNTAX Unsigned32
               		MAX-ACCESS not-accessible
               		STATUS current
               		DESCRIPTION " "
               		::= { monitorSerialGroupsEntry 1 }
			serialGroupPhone OBJECT-TYPE
               		SYNTAX DisplayString
               		MAX-ACCESS read-only
               		STATUS current
               		DESCRIPTION " "
               		::= { monitorSerialGroupsEntry 2 }
			serialGroupRegistrationState OBJECT-TYPE
               		SYNTAX GroupRegistrationState
               		MAX-ACCESS read-only
               		STATUS current
               		DESCRIPTION " "
               		::= { monitorSerialGroupsEntry 3 }
			serialGroupRegistrationHost OBJECT-TYPE
               		SYNTAX DisplayString
               		MAX-ACCESS read-only
               		STATUS current
               		DESCRIPTION " "
               		::= { monitorSerialGroupsEntry 4 }
			serialGroupLastRegistrationAt OBJECT-TYPE
               		SYNTAX DisplayString
               		MAX-ACCESS read-only
               		STATUS current
               		DESCRIPTION " "
               		::= { monitorSerialGroupsEntry 5 }
			serialGroupNextRegistrationAfter OBJECT-TYPE
               		SYNTAX DisplayString
               		MAX-ACCESS read-only
               		STATUS current
               		DESCRIPTION " "
               		::= { monitorSerialGroupsEntry 6 }
			serialGroupH323GK OBJECT-TYPE
               		SYNTAX DisplayString
               		MAX-ACCESS read-only
               		STATUS current
               		DESCRIPTION " "
               		::= { monitorSerialGroupsEntry 7 }

monitorFxoGroupsTable OBJECT-TYPE
		SYNTAX SEQUENCE OF MonitorFxoGroupsEntry
		MAX-ACCESS not-accessible
		STATUS current
		DESCRIPTION " "
		::= {  fxs72 42 }

		monitorFxoGroupsEntry OBJECT-TYPE
			SYNTAX		MonitorFxoGroupsEntry
			MAX-ACCESS	not-accessible
			STATUS		current
			DESCRIPTION "TAU-SIP 2.7"
			INDEX { fxoGroupNumber }
			::= { monitorFxoGroupsTable 1 }
                  
			MonitorFxoGroupsEntry ::= SEQUENCE {
				fxoGroupNumber Unsigned32,
				fxoGroupPhone DisplayString,
				fxoGroupRegistrationState GroupRegistrationState,
				fxoGroupRegistrationHost DisplayString,
				fxoGroupLastRegistrationAt DisplayString,
				fxoGroupNextRegistrationAfter DisplayString,
				fxoGroupH323GK DisplayString
			}
            
            fxoGroupNumber OBJECT-TYPE
               		SYNTAX Unsigned32
               		MAX-ACCESS not-accessible
               		STATUS current
               		DESCRIPTION " "
               		::= { monitorFxoGroupsEntry 1 }   		
			fxoGroupPhone OBJECT-TYPE
               		SYNTAX DisplayString
               		MAX-ACCESS read-only
               		STATUS current
               		DESCRIPTION " "
               		::= { monitorFxoGroupsEntry 2 }
			fxoGroupRegistrationState OBJECT-TYPE
               		SYNTAX GroupRegistrationState
               		MAX-ACCESS read-only
               		STATUS current
               		DESCRIPTION " "
               		::= { monitorFxoGroupsEntry 3 }
			fxoGroupRegistrationHost OBJECT-TYPE
               		SYNTAX DisplayString
               		MAX-ACCESS read-only
               		STATUS current
               		DESCRIPTION " "
               		::= { monitorFxoGroupsEntry 4 }
			fxoGroupLastRegistrationAt OBJECT-TYPE
               		SYNTAX DisplayString
               		MAX-ACCESS read-only
               		STATUS current
               		DESCRIPTION " "
               		::= { monitorFxoGroupsEntry 5 }
			fxoGroupNextRegistrationAfter OBJECT-TYPE
               		SYNTAX DisplayString
               		MAX-ACCESS read-only
               		STATUS current
               		DESCRIPTION " "
               		::= { monitorFxoGroupsEntry 6 }
			fxoGroupH323GK OBJECT-TYPE
               		SYNTAX DisplayString
               		MAX-ACCESS read-only
               		STATUS current
               		DESCRIPTION " "
               		::= { monitorFxoGroupsEntry 7 }

firewallTableMIBBoundary  OBJECT-TYPE
			SYNTAX     Integer32
			MAX-ACCESS read-only
			STATUS     current
			DESCRIPTION "Dummy object to prevent GETNEXT request from poking into neighbor table."
			::= { fxs72 43 }

firewallConfig OBJECT IDENTIFIER ::= { fxs72 44 }

	firewallTable OBJECT-TYPE
		SYNTAX SEQUENCE OF FirewallEntry
		MAX-ACCESS not-accessible
		STATUS current
		DESCRIPTION "TAU-SIP 2.7"
		::= {  firewallConfig 1 }

		firewallEntry OBJECT-TYPE
			SYNTAX		FirewallEntry
			MAX-ACCESS	not-accessible
			STATUS		current
			DESCRIPTION " "
			INDEX { ruleNumber }
			::= { firewallTable 1 }
                  
			FirewallEntry ::= SEQUENCE {
				ruleNumber Unsigned32,
				startingSourceIpAddress DisplayString,
				numberOfSourceIpAddresses Unsigned32,
				allSourceIpAddresses TruthValue,
				ruleprotocol FirewallProtocol,
				typeOfMessageICMP TypeOfMessageICMP,
				startingSourcePort Unsigned32,
				numberOfSourcePorts Unsigned32,
				allSourcePorts TruthValue,
				startingDestinationPort Unsigned32,
				numberOfDestinationPorts Unsigned32 ,
				allDestinationPorts TruthValue,
				ruleTarget FirewallTarget,
				ruleMoveTo Unsigned32,
				ruleRowStatus RowStatus
			}

				ruleNumber OBJECT-TYPE
               		SYNTAX Unsigned32
					MAX-ACCESS not-accessible
					STATUS current
					DESCRIPTION
						" "
					::= { firewallEntry 1 }

				startingSourceIpAddress OBJECT-TYPE
               		SYNTAX DisplayString
					MAX-ACCESS read-write
					STATUS current
					DESCRIPTION
						"Starting source IP address"
					::= { firewallEntry 2 }
				 	
				numberOfSourceIpAddresses OBJECT-TYPE
               		SYNTAX Unsigned32
					MAX-ACCESS read-write
					STATUS current
					DESCRIPTION
						"Number of source IP addresses:"
					::= { firewallEntry 3 } 
	
				allSourceIpAddresses OBJECT-TYPE
               		SYNTAX TruthValue
					MAX-ACCESS read-write
					STATUS current
					DESCRIPTION
						"All source IP addresses"
					::= { firewallEntry 4 }	
					
				ruleprotocol OBJECT-TYPE
               		SYNTAX FirewallProtocol
					MAX-ACCESS read-write
					STATUS current
					DESCRIPTION
						"Protocol"
					::= { firewallEntry 5 }
					
				typeOfMessageICMP OBJECT-TYPE
               		SYNTAX TypeOfMessageICMP
					MAX-ACCESS read-write
					STATUS current
					DESCRIPTION
						"Type of message (ICMP): for protocol ICMP only"
					::= { firewallEntry 6 }
					 		
				startingSourcePort OBJECT-TYPE
               		SYNTAX Unsigned32
					MAX-ACCESS read-write
					STATUS current
					DESCRIPTION
						"Starting source port: from 1 to 65535, for protocols UDP, TCP only"
					::= { firewallEntry 7 }
	
				numberOfSourcePorts OBJECT-TYPE
               		SYNTAX Unsigned32
					MAX-ACCESS read-write
					STATUS current
					DESCRIPTION
						"Number of source ports: starting+number<=65535, for protocols UDP, TCP only"
					::= { firewallEntry 8 }

				allSourcePorts OBJECT-TYPE
               		SYNTAX TruthValue
					MAX-ACCESS read-write
					STATUS current
					DESCRIPTION
						"All source ports: for protocols UDP, TCP only"
					::= { firewallEntry 9 }

				startingDestinationPort OBJECT-TYPE
               		SYNTAX Unsigned32
					MAX-ACCESS read-write
					STATUS current
					DESCRIPTION
						"Starting destination port: from 1 to 65535, for protocols UDP, TCP only"
					::= { firewallEntry 10 }
	
				numberOfDestinationPorts OBJECT-TYPE
               		SYNTAX Unsigned32 
					MAX-ACCESS read-write
					STATUS current
					DESCRIPTION
						"Number of destination ports: starting+number<=65535, for protocols UDP, TCP only"
					::= { firewallEntry 11 }
	
				allDestinationPorts OBJECT-TYPE
               		SYNTAX TruthValue
					MAX-ACCESS read-write
					STATUS current
					DESCRIPTION
						"All destination ports: for protocols UDP, TCP only"
					::= { firewallEntry 12 }	

				ruleTarget OBJECT-TYPE
               		SYNTAX FirewallTarget
					MAX-ACCESS read-write
					STATUS current
					DESCRIPTION
						"Target"
					::= { firewallEntry 13 }
				
				ruleMoveTo OBJECT-TYPE
               		SYNTAX Unsigned32 
					MAX-ACCESS read-write
					STATUS current
					DESCRIPTION
						"set new position of rule (1..30)"
					::= { firewallEntry 14 }
					
				ruleRowStatus OBJECT-TYPE
               		SYNTAX RowStatus
               		MAX-ACCESS read-create
					STATUS current
					DESCRIPTION
						" "
					::= { firewallEntry 15 }
		
		firewallApply OBJECT-TYPE
			SYNTAX Integer32
			MAX-ACCESS read-write
			STATUS current
			DESCRIPTION
				"set to apply firewall config
				 it will rollback in ? second without firewallConfirm
				 TAU-SIP 2.7"
		::= {  firewallConfig 2 }
		
		firewallConfirm OBJECT-TYPE
			SYNTAX Integer32
			MAX-ACCESS read-write
			STATUS current
			DESCRIPTION
				"set to confirm firewall config
				 firewallCommit kill firewallApply-timer
				 TAU-SIP 2.7"
		::= {  firewallConfig 3 }



configTcpIp OBJECT IDENTIFIER ::= { fxs72 45 }
	
-- RTP port range (RTP)

rtpSipMin OBJECT-TYPE
	SYNTAX Integer32(1024..65500)
	MAX-ACCESS read-write
	STATUS current
	DESCRIPTION
		"RTP SIP min. TAU-SIP 2.9"
	DEFVAL { 23000 }
	::= { configTcpIp 1 }
	
rtpSipMax OBJECT-TYPE
	SYNTAX Integer32(1024..65500)
	MAX-ACCESS read-write
	STATUS current
	DESCRIPTION
		"RTP SIP max. TAU-SIP 2.9"
	DEFVAL { 23896 }
	::= { configTcpIp 2 }
	
-- Intercept port range

interceptPortMin OBJECT-TYPE
	SYNTAX Integer32(1024..65500)
	MAX-ACCESS read-write
	STATUS current
	DESCRIPTION
		"Intercept port min. TAU-SIP 2.9"
	DEFVAL { 50000 }
	::= { configTcpIp 3 }
	
interceptPortMax OBJECT-TYPE
	SYNTAX Integer32(1024..65500)
	MAX-ACCESS read-write
	STATUS current
	DESCRIPTION
		"Intercept port max. TAU-SIP 2.9"
	DEFVAL { 50100 }
	::= { configTcpIp 4 }
	
-- TOS configuration

diffservForSip OBJECT-TYPE
	SYNTAX Integer32(0..255)
	MAX-ACCESS read-write
	STATUS current
	DESCRIPTION
		"Diffserv for SIP. TAU-SIP 2.9"
	DEFVAL { 104 }
	::= { configTcpIp 5 }
	
diffservForRtp OBJECT-TYPE
	SYNTAX Integer32(0..255)
	MAX-ACCESS read-write
	STATUS current
	DESCRIPTION
		"Diffserv for RTP. TAU-SIP 2.9"
	DEFVAL { 184 }
	::= { configTcpIp 6 }
	
-- Other
verifyRemoteMediaAddress OBJECT-TYPE
	SYNTAX TruthValue
	MAX-ACCESS read-write
	STATUS current
	DESCRIPTION
		"Verify remote media address. TAU-SIP 2.9"
	DEFVAL { false }
	::= { configTcpIp 7 }
	

callLimitTable OBJECT-TYPE
		SYNTAX SEQUENCE OF CallLimitEntry
		MAX-ACCESS not-accessible
		STATUS current
		DESCRIPTION "TAU-SIP 2.9"
		::= {  fxs72 46 }

		callLimitEntry OBJECT-TYPE
			SYNTAX		CallLimitEntry
			MAX-ACCESS	not-accessible
			STATUS		current
			DESCRIPTION " "
			INDEX { clIndex }
			::= { callLimitTable 1 }
                  
			CallLimitEntry ::= SEQUENCE {
				clIndex Integer32,
				clType CallLimitType,
				clHostOfNeighbourGateway DisplayString,
				clSimultaneousCallsCount Integer32,
				clRowStatus RowStatus
			}
			
			clIndex OBJECT-TYPE
               		SYNTAX Integer32(1..30) 
					MAX-ACCESS not-accessible
					STATUS current
					DESCRIPTION
						" "
					::= {  callLimitEntry 1 }
					
			clType OBJECT-TYPE
               		SYNTAX CallLimitType 
					MAX-ACCESS read-write
					STATUS current
					DESCRIPTION
						"proxy/gk or host"
					::= {  callLimitEntry 2 }
					
			clHostOfNeighbourGateway OBJECT-TYPE
               		SYNTAX DisplayString 
					MAX-ACCESS read-write
					STATUS current
					DESCRIPTION
						"Host of neighbour gateway. max 255 symbols"
					::= {  callLimitEntry 3 }
					
			clSimultaneousCallsCount OBJECT-TYPE
               		SYNTAX Integer32 
					MAX-ACCESS read-write
					STATUS current
					DESCRIPTION
						"Simultaneous calls count"
					::= {  callLimitEntry 4 }
					
			clRowStatus OBJECT-TYPE
               		SYNTAX RowStatus 
					MAX-ACCESS read-create
					STATUS current
					DESCRIPTION
						" "
					::= {  callLimitEntry 5 }


distinctiveRingTable OBJECT-TYPE
		SYNTAX SEQUENCE OF DistinctiveRingEntry
		MAX-ACCESS not-accessible
		STATUS current
		DESCRIPTION "TAU-SIP 2.9"
		::= {  fxs72 47 }

		distinctiveRingEntry OBJECT-TYPE
			SYNTAX		DistinctiveRingEntry
			MAX-ACCESS	not-accessible
			STATUS		current
			DESCRIPTION " "
			INDEX { drId }
			::= { distinctiveRingTable 1 }
                  
			DistinctiveRingEntry ::= SEQUENCE {
				drId Integer32,
				drRule DisplayString,
				drRing Integer32,
				drPause Integer32,
				drSubscriberProfiles DRSubscriberProfilesType,
				drRowStatus	RowStatus
			}

			drId OBJECT-TYPE
               		SYNTAX Integer32(1..32) 
					MAX-ACCESS not-accessible
					STATUS current
					DESCRIPTION
						" "
					::= {  distinctiveRingEntry 1 }
					
			drRule OBJECT-TYPE
               		SYNTAX DisplayString 
					MAX-ACCESS read-write
					STATUS current
					DESCRIPTION
						"Rule. 50 symbol max"
					::= {  distinctiveRingEntry 2 }
					
			drRing OBJECT-TYPE
               		SYNTAX Integer32 (2..255)
					MAX-ACCESS read-write
					STATUS current
					DESCRIPTION
						"Ring, x100 msec"
					::= {  distinctiveRingEntry 3 }
					
			drPause OBJECT-TYPE
               		SYNTAX Integer32 (2..255) 
					MAX-ACCESS read-write
					STATUS current
					DESCRIPTION
						"Pause, x100 msec"
					::= {  distinctiveRingEntry 4 }
					
			drSubscriberProfiles OBJECT-TYPE
               		SYNTAX DRSubscriberProfilesType 
					MAX-ACCESS read-write
					STATUS current
					DESCRIPTION
						"Subscriber profiles 1-8, bit mask: 0 bit = 1 profile, 7 bit = 8 profile.
							more description at DRSubscriberProfilesType"
					::= {  distinctiveRingEntry 5 }
					
			drRowStatus OBJECT-TYPE
               		SYNTAX RowStatus 
					MAX-ACCESS read-create
					STATUS current
					DESCRIPTION
						" "
					::= {  distinctiveRingEntry 6 }

modifiersTable OBJECT-TYPE
	SYNTAX			SEQUENCE OF ModifiersEntry
	MAX-ACCESS		not-accessible
	STATUS			current
	DESCRIPTION " "
	::= { fxs72 48 }

	modifiersEntry OBJECT-TYPE
		SYNTAX		ModifiersEntry
		MAX-ACCESS	not-accessible
		STATUS		current
		DESCRIPTION " "
		INDEX { modifierNumber, modifierRule }
		::= { modifiersTable 1 }

		ModifiersEntry ::= SEQUENCE {
			modifierNumber Integer32,
			modifierRule Integer32,
			modifierDialedNumberRegexpRule DisplayString,	
			modifierDialedNumberModification DisplayString,	
			modifierCallingNumberModification DisplayString,
			modifierRowStatus RowStatus }	
			
			modifierNumber  OBJECT-TYPE
				SYNTAX     Integer32 (1..16)
				MAX-ACCESS	not-accessible
				STATUS     current
				DESCRIPTION ""
				::= { modifiersEntry 1 }
			
			modifierRule  OBJECT-TYPE
				SYNTAX     Integer32 (1..32)
				MAX-ACCESS	not-accessible
				STATUS     current
				DESCRIPTION ""
				::= { modifiersEntry 2 }
			
			modifierDialedNumberRegexpRule  OBJECT-TYPE
				SYNTAX     DisplayString
				MAX-ACCESS read-write
				STATUS     current
				DESCRIPTION "Dialed number regexp rule (max len 50)
					Allowed symbols:
						- '|' - OR (rule part divider)
						- 'X', 'x' - any digit, equals to [0-9]
						- 0-9 - digits from 0 to 9
						- '*', '#' - symbols
						- [] - borders of range for this symbol (example: [0-7], [138], [135*#])
						- {min,max} - min/max symbol repeats (example: 5{2,5})
						- '.' - previous digit, symbol or range is not mandatory or can has any repeats; exuals to 5{0,} (example: 35.*)
						- '+' - previous digit, symbol or range can has any repeats; exuals to 5{1,} (example: x5+#)"
				::= { modifiersEntry 3 }
				
			modifierDialedNumberModification  OBJECT-TYPE
				SYNTAX     DisplayString
				MAX-ACCESS read-write
				STATUS     current
				DESCRIPTION "Dialed number modification (max len 29)
					Allowed symbols:
						- '.', '-' - digit removing
						- 'X', 'x' - digit or symbol on this position is unchanging (mandatory);
						- '?' - digit or symbol on this position is unchanging (not mandatory);
						- '+' - next symblos will be added
						- '!' - end of parsing; all next symbols will be cutted
						- '$' - end of parsing; all next symbols will be unchanged
						- 0-9, '#', '*' (without '+') - digit or symbol on this position will be replaced"
				::= { modifiersEntry 4 }
					
			modifierCallingNumberModification  OBJECT-TYPE
				SYNTAX     DisplayString
				MAX-ACCESS read-write
				STATUS     current
				DESCRIPTION "Calling number modification (max len 29)
					Allowed symbols like modifierDialedNumberModification"
				::= { modifiersEntry 5 }
			
			modifierRowStatus  OBJECT-TYPE
				SYNTAX     RowStatus
				MAX-ACCESS read-create	
				STATUS     current
				DESCRIPTION ""
				::= { modifiersEntry 6 }		



						
	
	tauSubtypes OBJECT IDENTIFIER        ::= { fxs72 90 }
	tau72sip OBJECT IDENTIFIER        ::= { tauSubtypes 1 }
	tau36sip OBJECT IDENTIFIER        ::= { tauSubtypes 2 }
	tau32Msip OBJECT IDENTIFIER        ::= { tauSubtypes 3 }
	tau72megaco OBJECT IDENTIFIER        ::= { tauSubtypes 4 }
	tau72v30sip OBJECT IDENTIFIER        ::= { tauSubtypes 5 }
	tau36v30sip OBJECT IDENTIFIER        ::= { tauSubtypes 6 }
	fxs72sip OBJECT IDENTIFIER        ::= { tauSubtypes 7 }
	tau36megaco OBJECT IDENTIFIER        ::= { tauSubtypes 8 }
	tau72v30megaco OBJECT IDENTIFIER        ::= { tauSubtypes 9 }
	tau36v30megaco OBJECT IDENTIFIER        ::= { tauSubtypes 10 }
	fxs72megaco OBJECT IDENTIFIER        ::= { tauSubtypes 11 }
	fxs72v21 OBJECT IDENTIFIER        ::= { tauSubtypes 12 }
	tau72v40sip OBJECT IDENTIFIER        ::= { tauSubtypes 13 }
	tau36v40sip OBJECT IDENTIFIER        ::= { tauSubtypes 14 }
	tau72v40megaco OBJECT IDENTIFIER        ::= { tauSubtypes 15 }
	tau36v40megaco OBJECT IDENTIFIER        ::= { tauSubtypes 16 }
	tau32MrevBsip OBJECT IDENTIFIER ::= { tauSubtypes 17 } -- TAU-32M_1v5
	tau32Mmegaco OBJECT IDENTIFIER        ::= { tauSubtypes 18 }
	tau32MrevBmegaco OBJECT IDENTIFIER        ::= { tauSubtypes 19 }
	tau16sip OBJECT IDENTIFIER        ::= { tauSubtypes 20 }
	tau24sip OBJECT IDENTIFIER        ::= { tauSubtypes 21 }
	tau16megaco OBJECT IDENTIFIER        ::= { tauSubtypes 22 }
	tau24megaco OBJECT IDENTIFIER        ::= { tauSubtypes 23 }
	
	
fxsGroup  OBJECT-GROUP
	OBJECTS
	{
		fxsDevName,
		fxsDevType,
		fxsDevCfgBuild,
		fxsFreeSpace,
		fxsFreeRam,
		fxsSSwStatus,
		fxsSSwStatusTime,
		fxsCpuUsage,

		fxsMonitoringVMode,
		fxsMonitoringVBat,
		fxsMonitoringVRing1,
		fxsMonitoringVRing2,
		fxsMonitoringTemp1,
		fxsMonitoringTemp2,
		fxsMonitoringTemp3,
		fxsMonitoringTemp4,
		fxsMonitoringFanState,
		fxsMonitoringFan1Rotate,
		fxsMonitoringFan2Rotate,
		fxsMonitoringSubCooling,
		fxsMonitoringVinput,
		fxsMonitoringDevicePower,
		
		fxsPortsMIBBoundary,

		fxsPortPhoneNumber,
		fxsPortState,
		fxsPortUserName,
		fxsPortTalkingNum,
		fxsPortTalkingStartTime,
		fxsPortSipConnected,
		fxsPortH323Connected,
		fxsPortSipConnecteNext,
		fxsPortSipConnecteState,
		fxsPortSipConnectHost,
		
		fxsPortConfigPhone,
		fxsPortConfigUserName,
		fxsPortConfigAuthName,
		fxsPortConfigAuthPass,
		fxsPortConfigCustom,
		fxsPortConfigPlaymoh,
		fxsPortConfigAON,
		fxsPortConfigAONHideDate,
		fxsPortConfigAONHideName,
		fxsPortConfigTaxophone,
		fxsPortConfigMinFlashtime,
		fxsPortConfigMaxFlashtime,
		fxsPortConfigGainr,
		fxsPortConfigGaint,
		fxsPortConfigCategory,
		fxsPortConfigCallTransfer,
		fxsPortConfigCallWaiting,
		fxsPortConfigHotLine,
		fxsPortConfigHotNumber,
		fxsPortConfigHotTimeout,
		fxsPortConfigDisabled,
		fxsPortConfigCtBusy,
		fxsPortConfigCtUnconditional,
		fxsPortConfigCtNoanswer,
		fxsPortConfigCtTimeout,
		fxsPortConfigClir,
		fxsPortConfigStopDial,
		fxsPortConfigAltNumber,
		fxsPortConfigUseAltNumber,
		fxsPortConfigPickUp,
		fxsPortConfigSipPort,
		fxsPortConfigCfgPriOverCw,
		fxsPortConfigRowStatus,
		fxsPortConfigDvoCwEn,
		fxsPortConfigDvoCtAttendedEn,
		fxsPortConfigDvoCtUnattendedEn,
		fxsPortConfigDvoUnconditionalEn,
		fxsPortConfigDvoCfBusyEn,
		fxsPortConfigDvoCfAnswerEn,
		fxsPortConfigDvoCfServiceEn,
		fxsPortConfigDvoDoDisturbEn,
		fxsPortConfigCtOutofservice,
		fxsPortConfigCfuNumber,
		fxsPortConfigCfbNumber,
		fxsPortConfigCfnrNumber,
		fxsPortConfigCfoosNumber,
		fxsPortConfigDnd,
		fxsPortConfigCtNumber,
		fxsPortConfigEnableCpc,
		fxsPortConfigCpcTime,
		fxsPortConfigFxoFlashTime,
		fxsPortConfigFxoDelTdm,
		fxsPortConfigFxoRingtdm,
		fxsPortConfigPstnNumberprefix,
		fxsPortConfigPstnNameprefix,
		fxsPortConfigUsePstnCid,
		fxsPortConfigtdmhotline,
		fxsPortConfigtdmhottimeout,
		fxsPortConfigtdmhotnumber,
		fxsPortConfigDontDetectDT,
		fxsPortConfigDelayDialingTimeout,
		fxsPortType,
		fxsPortConfigDialing,
		fxsPortConfigTransmitNumber,
		fxsPortConfigDontTransmitPrefix,
		fxsPortConfigPortProfileID,
		fxsPortConfigSipProfileID,
		fxsPortConfigDialToneDetectionParameters,
		fxsPortConfigRingBackToneDetectionParameters,
		fxsPortConfigBusyToneDetectionParameters,
		fxsPortConfigDtDetectTime,
		fxsPortConfigDecadePulseTime,
		fxsPortConfigDecadePauseTime,
		fxsPortConfigNoOffhookAtRinging,
		fxsPortConfigFxoCallBusy,
		fxsPortConfigCpcRus,
		fxsPortConfigReversalPolarityAction,
		fxsPortConfigPstnActivity,
		fxsPortConfigPstnRbDetectTimeout,
		fxsPortConfigDetectFxoLinePresence,	
		fxsPortConfigBlockFxoLineInOutgoingDirection,
		fxsPortConfigFxoMinLevelDetect,
		fxsPortConfigUseAltNumberAsContact,
		fxsPortConfigModifier,
		fxsPortConfigMwiDialtone,
		
		fxsPortConfigCommonPlaymoh,
		fxsPortConfigCommonAON,
		fxsPortConfigCommonAONHideDate,

		fxsPortConfigCommonAONHideName,
		fxsPortConfigCommonTaxophone,
		fxsPortConfigCommonMinFlashtime,
		fxsPortConfigCommonMaxFlashtime,
		fxsPortConfigCommonGainr,
		fxsPortConfigCommonGaint,
		fxsPortConfigCommonCategory,
		fxsPortConfigCommonCallTransfer,
		fxsPortConfigCommonCallWaiting,
		fxsPortConfigCommonCfgPriOverCw,
		fxsPortConfigCommonFxoFlashTime,
		fxsPortConfigCommonFxoDelTdm,
		fxsPortConfigCommonFxoRingtdm,
		fxsPortConfigCommonPstnNumberprefix,
		fxsPortConfigCommonPstnNameprefix,
		fxsPortConfigCommonUsePstnCid,
		fxsPortConfigCommonEnableCpc,
		fxsPortConfigCommonCpcTime,
		fxsPortConfigCommonDontDetectDT,
        fxsPortConfigCommonDelayDialingTimeout,
        fxsPortConfigCommonDialing,
		fxsPortConfigCommonTransmitNumber,
		fxsPortConfigCommonDontTransmitPrefix,
		
		fxsDialMIBBoundary,

		fxsDialPlanHost,
		fxsDialPlanDigits,
		fxsDialPlanTimeout,
		fxsDialPlanMinDigits,
		fxsDialPlanType,
		fxsDialPlanAccessMask,
		fxsDialPlanDialtone,
		fxsDialPlanModifier,
		fxsDialPlanNature,
		fxsDialPlanDelnum,
		fxsDialPlanPtime,
		fxsDialRowStatus,

		fxsDialPlanNext,
		
		tauDialRegularOn,
		tauDialRegularProtocol,
		tauDialRegularText,

		fxsConfigSave,
		fxsConfigApply,
		
		fxsSerialGroupsMIBBoundary,

		fxsSerialGroupsPhone,
		fxsSerialGroupsEnabled,
		fxsSerialGroupsSerialType,
		fxsSerialGroupsBusyType,
		fxsSerialGroupsTimeout,
		fxsSerialGroupsSipPort,

		fxsSerialGroupsAuthName,
		fxsSerialGroupsAuthPass,
		fxsSerialGroupsPorts,
		fxsSerialGroupsRowStatus,
		fxsSerialGroupsSipProfile,
		
		fxsSerialGroupsNextEmpty,
		
		fxsReboot,
		
		tauVoipDvoCallwaiting,
		tauVoipDvoCtAttended,
		tauVoipDvoCtUnattended,
		tauVoipDvoCfUnconditional,
		tauVoipDvoCfBusy,
		tauVoipDvoCfNoanswer,
		tauVoipDvoCfService,
		tauVoipDvoDoDisturb,
		
		sipEnablesip,
		sipObtimeout,
		sipMode,
		sipOptions,
		sipKeepalivet,
		sipDomainToReg,
		sipDomain,
		sipRegisterRetryInterval,
		sipOutbound,
		sipInboundProxy,
		sipExpires,
		sipAuthentication,
		sipUsername,
		sipPassword,
		sipProxy0,
		sipRegrar0,
		sipRegistration0,
		sipProxy1,
		sipRegrar1,
		sipProxy2,
		sipRegrar2,
		sipProxy3,
		sipRegrar3,
		sipProxy4,
		sipRegrar4,
		sipDtmfmime,
		sipHfmime,
		sipCtWithReplaces,
		sipShortmode,
		sipTransport,
		sipSipMtu,
		sip100Rel,
		sipUserPhone,
		sipUriEscapeHash,
		sipInviteTotalT,
		sipInviteInitT,
		sipCwRingback,
		sipRingbackSdp,
		sipRingback,
		sipRegistration1,
		sipRegistration2,
		sipRegistration3,
		sipRegistration4,
		sipPRTPstat,
		
		termID,
		currentState,
		totalCallCount,
		lastCallPhone,
		peakJitter,
		lostPackets,
		numTxPack,
		numTxOct,
		numRxPack,
		numRxOct,
		
		fxsUpdateFw,
		
	   sipCommonEnablesip,
       sipCommonShortmode,
       sipCommonTransport,
       sipCommonSipMtu,
       sipCommonInviteTotalT,
       sipCommonInviteInitT,
       sipCommonPortRegistrationDelay,
       
       profilesSipMIBBoundary,
       
       profileNumber,
       sipProfileObtimeout,
       sipProfileMode,
       sipProfileOptions,
       sipProfileKeepalivet,
       sipProfileDomainToReg,
       sipProfileRegisterRetryInterval,
       sipProfileOutbound,
       sipProfileInboundProxy,
       sipProfileExpires,
       sipProfileAuthentication,
       sipProfileUsername,
       sipProfilePassword,
       sipProfileProxy0,
       sipProfileRegrar0,
       sipProfileRegistration0,
       sipProfileProxy1,
       sipProfileRegrar1,
       sipProfileProxy2,
       sipProfileRegrar2,
       sipProfileProxy3,
       sipProfileRegrar3,
       sipProfileProxy4,
       sipProfileRegrar4,
       sipProfileDtmfmime,
       sipProfileHfmime,
       sipProfileCtWithReplaces,
       sipProfile100Rel,
       sipProfileUserPhone,
       sipProfileUriEscapeHash,
       sipProfileCwRingback,
       sipProfileRingbackSdp,
       sipProfileRingback,
       sipProfileRegistration1,
       sipProfileRegistration2,
       sipProfileRegistration3,
       sipProfileRegistration4,
       sipProfilePRTPstat,
       sipProfileRowStatus,
       sipProfileDomain,
       sipProfileEnableTimer,
       sipProfileMinSE,
       sipProfileSessionExpires,
       sipProfileRemoveInactiveMedia,
       sipProfileKeepAliveInterval,
	   sipProfileKeepAliveMode,
	   sipProfileConferenceMode,
	   sipProfileConferenceServer,
	   sipProfileEnableIMS,
	   sipProfileXCAPNameForThreePartyConference,
	   sipProfileXCAPNameForHotline,
	   sipProfileXCAPNameForCallWaiting,
	   sipProfileXCAPNameForCallHold,
	   sipProfileXCAPNameForExplicitCallTransfer,
	   sipProfileUseAlertInfo,
	   sipProfileFullRuriCompliance,
	   sipProfileChangeover,
       
       profilesPortsMIBBoundary,
       
       profilePortsPlaymoh,
       profilePortsAON,
       profilePortsAONHideDate,
       profilePortsAONHideName,
       profilePortsTaxophone,
       profilePortsMinFlashtime,
       profilePortsMaxFlashtime,
       profilePortsGainr,
       profilePortsGaint,
       profilePortsCategory,
       profilePortsCallTransfer,
       profilePortsCallWaiting,
       profilePortsCfgPriOverCw,
       profilePortsFxoFlashTime,
       profilePortsFxoDelTdm,
       profilePortsFxoRingtdm,
       profilePortsPstnNumberprefix,
       profilePortsPstnNameprefix,
       profilePortsUsePstnCid,
       profilePortsEnableCpc,
       profilePortsCpcTime,
       profilePortsDontDetectDT,
       profilePortsDelayDialingTimeout,
       profilePortsDialing,
       profilePortsTransmitNumber,
       profilePortsDontTransmitPrefix,
       profilePortsRowStatus,
       profilePortsDialToneDetectionParameters,
	   profilePortsRingBackToneDetectionParameters,
	   profilePortsBusyToneDetectionParameters,
	   profilePortsDtDetectTime,
	   profilePortsDecadePulseTime,
	   profilePortsDecadePauseTime,
	   profilePortsFxoCallBusy,
	   profilePortsCpcRus,
	   profilePortsReversalPolarityAction,
	   profilePortsPstnActivity,
	   profilePortsPstnRbDetectTimeout,
	   profilePortsDetectFxoLinePresence,
	   profilePortsBlockFxoLineInOutgoingDirection,
	   profilePortsStopDial,
	   profilePortsFxoMinLevelDetect,
	   profilePortsModifier,
       
       profilesDialPlansMIBBoundary,
       
       profileDialPlanHost,
       profileDialPlanDigits,
       profileDialPlanTimeout,
       profileDialPlanMinDigits,
       profileDialPlanType,
       profileDialPlanAccessMask,
       profileDialPlanDialtone,
       profileDialPlanModifier,
       profileDialPlanNature,
       profileDialPlanDelnum,
       profileDialPlanPtime,
       profileDialRowStatus,
       
       profilesRegExpDPTableMIBBoundary,
       
       profileRegExpDialOn,
       profileRegExpDialProtocol,
       profileRegExpDialText,
       profileRegExpDialRowStatus,
       
       		useG711A,
			useG711U,
			useG726to32,
			useG723,
			useG729B,
			useG729A,
			g711Ptime,
			g729Ptime,
			g723Ptime,
			g726to32Ptime,
			g726to32PT,
			dtmfTransfer ,
			flashTransfer,
			faxDetectDirection,
			faxTransferCodec,
			slaveFaxTransferCodec,
			modemTransfer,
			rfc2833PT,	
			silenceSuppression,	
			echoCanceller, 	
			nlpDisable, 	
			comfortNoise,
			rtcpTimer,	 
			rtcpControlPeriod,	 
			ciscoNsePT,	
			t38MaxDatagramSize, 	
			t38Bitrate,
			modemFaxDelay,
			voiceMode,
			voiceDelayMin,
			voiceDelayMax,
			voiceDeletionThreshold,
			voiceDeletionMode,
			profilesCodecsRowStatus,
			rtcpXR,
			rfc3264PtCommon,
			
			tauTrapSink,
			tauTrapType,
			tauSysName,
			tauSysContact,
			tauSysLocation,
			tauRoCommunity,
			tauRwCommunity,
			tauTrapCommunity,
			tauUserV3Name,
			tauUserV3Password,
			tauViewV3Type,
			tauRestartSnmp,

			tauMegacoTrapType,
			tauMegacoTrapHost,
			tauMegacoTrapCommunity,
			tauMegacoTrapPort,
			tauMegacoTrapRowStatus,
            
			fxoSerialGroupsPhone,
			fxoSerialGroupsEnabled,
			fxoSerialGroupsBusyType,
			fxoSerialGroupsSipPort,
			fxoSerialGroupsAuthName,
			fxoSerialGroupsAuthPass,
			fxoSerialGroupsPorts,
			fxoSerialGroupsSipProfile,
			fxoSerialGroupsTransmitNumber,
			fxoSerialGroupsDontTransmitPrefix,
			fxoSerialGroupsRowStatus,
			fxoSerialGroupsSend503OnBusy,
			fxoSerialGroupsType,

			fxsEnableAutoupdate,
			fxsSource,
			fxsTFTPServer,
			fxsConfigurationFile,
			fxsFirmwareVersion,
			fxsConfigurationUpdateInterval,
			fxsFirmwareUpdateInterval,
			autoupdateProtocol,
			autoupdateAuth,
			autoupdateUser,
			autoupdatePassword,
			
			fansForceEnable,
			fansThresholdTemperature,
			
			runSyslog,
			syslogAddr,
			syslogPort,
			appAlarm,
			appErr,
			appWarn,
			appInfo,
			appDbg,
			sipLevel,
			h323Level,
			vapiEnabled,
			vapiLibLevel,
			vapiAppLevel,
			
			portTestTestStatus,
			portTestTestStartTime,
			portTestLastTestStartTime,
			portTestLastTestEndTime,
			portTestResultFlag,
			portTestRingU,
			portTestTipU,
			portTestShortVbat,
			portTestResistTr,
			portTestResistTg,
			portTestResistRg,
			portTestCapacityTr,
			portTestCapacityTg,
			portTestCapacityRg,	
			portTestRunTest,
			
			monitorSerialGroupsMIBBoundary,
			
			serialGroupPhone,
			serialGroupRegistrationState,
			serialGroupRegistrationHost,
			serialGroupLastRegistrationAt,
			serialGroupNextRegistrationAfter,
			serialGroupH323GK,
				
			fxoGroupPhone,
			fxoGroupRegistrationState,
			fxoGroupRegistrationHost,
			fxoGroupLastRegistrationAt,
			fxoGroupNextRegistrationAfter,
			fxoGroupH323GK,
			
			firewallTableMIBBoundary,

			startingSourceIpAddress,
			numberOfSourceIpAddresses,
			allSourceIpAddresses,
			ruleprotocol,
			typeOfMessageICMP,
			startingSourcePort,
			numberOfSourcePorts,
			allSourcePorts,
			startingDestinationPort,
			numberOfDestinationPorts ,
			allDestinationPorts,
			ruleTarget,
			ruleMoveTo,
			ruleRowStatus,
			firewallApply,
			firewallConfirm,
			
			megacoPortTerminationID,
			megacoPortState,
			megacoPortComments,
			megacoPortStateStartTime,
			megacoPortStateDuration,
			megacoPortJitter,
			megacoPortTelNo,
			
			deviceName,
			startTimer,
			durationTimer,
			waitAnswerTimer,
			powerMode,
			siptUsePrefix,
			siptPrefix,
			
			rtpSipMin,
			rtpSipMax,
			interceptPortMin,
			interceptPortMax,
			diffservForSip,
			diffservForRtp,
			verifyRemoteMediaAddress,
			
			clType,
			clHostOfNeighbourGateway,
			clSimultaneousCallsCount,
			clRowStatus,
			
			drRule,
			drRing,
			drPause,
			drSubscriberProfiles,
			drRowStatus,
			
			profilesSipAlertInfoMIBBoundary,

			cadenceName,
			cadenceRingRule,
			cadenceRowStatus,
			
			stunEnable,
			stunServer,
			stunInterval,
			sipPublicIp,
			
			modifierDialedNumberRegexpRule,	
			modifierDialedNumberModification,	
			modifierCallingNumberModification,
			modifierRowStatus
	}
	STATUS  current
	DESCRIPTION
		"none"
	::= { fxs72 200 }

END
