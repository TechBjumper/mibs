-- file automatically created


TELDAT-TRAP-CELL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


cellTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the CELL event subsystem."
    REVISION "201401200930Z"
    DESCRIPTION "Initial implementation"
        ::= { telEventTraps 208 }


cellEventsGroup	OBJECT IDENTIFIER	::= { cellTrapsMIB 1 }

cellNotifications	OBJECT IDENTIFIER	::= { cellTrapsMIB 2 }
cellNotificationsPrefix	OBJECT IDENTIFIER	::= { cellNotifications 0 }

cellEventObjects1 OBJECT-IDENTITY
    STATUS current
    DESCRIPTION
        "Event CELL.1
        Generic informational event."
    ::= { cellEventsGroup 1 }

cell1-info-string OBJECT-TYPE
    SYNTAX DisplayString
    MAX-ACCESS accessible-for-notify
    STATUS current
    DESCRIPTION
        "Parameter 'info-string' in event CELL.1"
    ::= { cellEventObjects1 1 }

cell1-ifcname OBJECT-TYPE
    SYNTAX DisplayString
    MAX-ACCESS accessible-for-notify
    STATUS current
    DESCRIPTION
        "Parameter 'ifcname' in event CELL.1"
    ::= { cellEventObjects1 2 }

cellEventObjects2 OBJECT-IDENTITY
    STATUS current
    DESCRIPTION
        "Event CELL.2
        Generic error report."
    ::= { cellEventsGroup 2 }

cell2-error-string OBJECT-TYPE
    SYNTAX DisplayString
    MAX-ACCESS accessible-for-notify
    STATUS current
    DESCRIPTION
        "Parameter 'error-string' in event CELL.2"
    ::= { cellEventObjects2 1 }

cell2-ifcname OBJECT-TYPE
    SYNTAX DisplayString
    MAX-ACCESS accessible-for-notify
    STATUS current
    DESCRIPTION
        "Parameter 'ifcname' in event CELL.2"
    ::= { cellEventObjects2 2 }

cellEventObjects3 OBJECT-IDENTITY
    STATUS current
    DESCRIPTION
        "Event CELL.3
        Registration state has changed."
    ::= { cellEventsGroup 3 }

cell3-state OBJECT-TYPE
    SYNTAX DisplayString
    MAX-ACCESS accessible-for-notify
    STATUS current
    DESCRIPTION
        "Parameter 'state' in event CELL.3"
    ::= { cellEventObjects3 1 }

cell3-ifcname OBJECT-TYPE
    SYNTAX DisplayString
    MAX-ACCESS accessible-for-notify
    STATUS current
    DESCRIPTION
        "Parameter 'ifcname' in event CELL.3"
    ::= { cellEventObjects3 2 }

cellEventObjects4 OBJECT-IDENTITY
    STATUS current
    DESCRIPTION
        "Event CELL.4
        The cellular interface now uses a different Public Land Mobile Network,
        (Mobile Operator) identified by the number displayed."
    ::= { cellEventsGroup 4 }

cell4-operator OBJECT-TYPE
    SYNTAX Integer32
    MAX-ACCESS accessible-for-notify
    STATUS current
    DESCRIPTION
        "Parameter 'operator' in event CELL.4"
    ::= { cellEventObjects4 1 }

cell4-ifcname OBJECT-TYPE
    SYNTAX DisplayString
    MAX-ACCESS accessible-for-notify
    STATUS current
    DESCRIPTION
        "Parameter 'ifcname' in event CELL.4"
    ::= { cellEventObjects4 2 }

cellEventObjects5 OBJECT-IDENTITY
    STATUS current
    DESCRIPTION
        "Event CELL.5
        The cellular interface is connected to a different base station,
        identified by the Location Area Code (LAC) and the Cell Identifier code
        (CiD)."
    ::= { cellEventsGroup 5 }

cell5-location-area-code OBJECT-TYPE
    SYNTAX Integer32
    MAX-ACCESS accessible-for-notify
    STATUS current
    DESCRIPTION
        "Parameter 'location-area-code' in event CELL.5"
    ::= { cellEventObjects5 1 }

cell5-cell-id OBJECT-TYPE
    SYNTAX Integer32
    MAX-ACCESS accessible-for-notify
    STATUS current
    DESCRIPTION
        "Parameter 'cell-id' in event CELL.5"
    ::= { cellEventObjects5 2 }

cell5-ifcname OBJECT-TYPE
    SYNTAX DisplayString
    MAX-ACCESS accessible-for-notify
    STATUS current
    DESCRIPTION
        "Parameter 'ifcname' in event CELL.5"
    ::= { cellEventObjects5 3 }

cellEventObjects6 OBJECT-IDENTITY
    STATUS current
    DESCRIPTION
        "Event CELL.6
        Notify a change of the used cellular technology, which implies different
        radio bands, coding methods and therefore different data rates."
    ::= { cellEventsGroup 6 }

cell6-technology OBJECT-TYPE
    SYNTAX DisplayString
    MAX-ACCESS accessible-for-notify
    STATUS current
    DESCRIPTION
        "Parameter 'technology' in event CELL.6"
    ::= { cellEventObjects6 1 }

cell6-ifcname OBJECT-TYPE
    SYNTAX DisplayString
    MAX-ACCESS accessible-for-notify
    STATUS current
    DESCRIPTION
        "Parameter 'ifcname' in event CELL.6"
    ::= { cellEventObjects6 2 }

cellEventObjects7 OBJECT-IDENTITY
    STATUS current
    DESCRIPTION
        "Event CELL.7
        Received Signal Strength Indication (RSSI) changed to the level
        displayed. This event depends of user's configuration thresholds and
        appears only if the used technology is GSM or GPRS."
    ::= { cellEventsGroup 7 }

cell7-rssi-level OBJECT-TYPE
    SYNTAX Integer32
    MAX-ACCESS accessible-for-notify
    STATUS current
    DESCRIPTION
        "Parameter 'rssi-level' in event CELL.7"
    ::= { cellEventObjects7 1 }

cell7-ifcname OBJECT-TYPE
    SYNTAX DisplayString
    MAX-ACCESS accessible-for-notify
    STATUS current
    DESCRIPTION
        "Parameter 'ifcname' in event CELL.7"
    ::= { cellEventObjects7 2 }

cellEventObjects8 OBJECT-IDENTITY
    STATUS current
    DESCRIPTION
        "Event CELL.8
        Received Signal Code Power (RSCP) has changed to the level displayed or
        the EcNo ratio (received energy per chip divided by the power density in
        the band) has changed to the value displayed. This event depends of
        user's configuration thresholds and appears only if the used technology
        is UMTS, HSDPA or CDMA."
    ::= { cellEventsGroup 8 }

cell8-rscp-level OBJECT-TYPE
    SYNTAX Integer32
    MAX-ACCESS accessible-for-notify
    STATUS current
    DESCRIPTION
        "Parameter 'rscp-level' in event CELL.8"
    ::= { cellEventObjects8 1 }

cell8-ecno-level OBJECT-TYPE
    SYNTAX Integer32
    MAX-ACCESS accessible-for-notify
    STATUS current
    DESCRIPTION
        "Parameter 'ecno-level' in event CELL.8"
    ::= { cellEventObjects8 2 }

cell8-ifcname OBJECT-TYPE
    SYNTAX DisplayString
    MAX-ACCESS accessible-for-notify
    STATUS current
    DESCRIPTION
        "Parameter 'ifcname' in event CELL.8"
    ::= { cellEventObjects8 3 }

cellEventObjects9 OBJECT-IDENTITY
    STATUS current
    DESCRIPTION
        "Event CELL.9
        Active SIM is placed in the displayed socked."
    ::= { cellEventsGroup 9 }

cell9-sim-socket OBJECT-TYPE
    SYNTAX DisplayString
    MAX-ACCESS accessible-for-notify
    STATUS current
    DESCRIPTION
        "Parameter 'sim-socket' in event CELL.9"
    ::= { cellEventObjects9 1 }

cell9-ifcname OBJECT-TYPE
    SYNTAX DisplayString
    MAX-ACCESS accessible-for-notify
    STATUS current
    DESCRIPTION
        "Parameter 'ifcname' in event CELL.9"
    ::= { cellEventObjects9 2 }

cellEventObjects10 OBJECT-IDENTITY
    STATUS current
    DESCRIPTION
        "Event CELL.10
        Interface call stated changed to the state displayed"
    ::= { cellEventsGroup 10 }

cell10-call-state-string OBJECT-TYPE
    SYNTAX DisplayString
    MAX-ACCESS accessible-for-notify
    STATUS current
    DESCRIPTION
        "Parameter 'call-state-string' in event CELL.10"
    ::= { cellEventObjects10 1 }

cell10-call-state-num OBJECT-TYPE
    SYNTAX Integer32
    MAX-ACCESS accessible-for-notify
    STATUS current
    DESCRIPTION
        "Parameter 'call-state-num' in event CELL.10"
    ::= { cellEventObjects10 2 }

cell10-ifcname OBJECT-TYPE
    SYNTAX DisplayString
    MAX-ACCESS accessible-for-notify
    STATUS current
    DESCRIPTION
        "Parameter 'ifcname' in event CELL.10"
    ::= { cellEventObjects10 3 }

cellEventObjects11 OBJECT-IDENTITY
    STATUS current
    DESCRIPTION
        "Event CELL.11
        A successful upgrade has been done to the displayed release"
    ::= { cellEventsGroup 11 }

cell11-frmwr-release OBJECT-TYPE
    SYNTAX DisplayString
    MAX-ACCESS accessible-for-notify
    STATUS current
    DESCRIPTION
        "Parameter 'frmwr-release' in event CELL.11"
    ::= { cellEventObjects11 1 }

cell11-ifcname OBJECT-TYPE
    SYNTAX DisplayString
    MAX-ACCESS accessible-for-notify
    STATUS current
    DESCRIPTION
        "Parameter 'ifcname' in event CELL.11"
    ::= { cellEventObjects11 2 }

cellEventObjects12 OBJECT-IDENTITY
    STATUS current
    DESCRIPTION
        "Event CELL.12
        Voice-call supervision has disabled voice-calls because of the reported
        reason. These are registration problems o low coverage."
    ::= { cellEventsGroup 12 }

cell12-cause OBJECT-TYPE
    SYNTAX DisplayString
    MAX-ACCESS accessible-for-notify
    STATUS current
    DESCRIPTION
        "Parameter 'cause' in event CELL.12"
    ::= { cellEventObjects12 1 }

cell12-ifcname OBJECT-TYPE
    SYNTAX DisplayString
    MAX-ACCESS accessible-for-notify
    STATUS current
    DESCRIPTION
        "Parameter 'ifcname' in event CELL.12"
    ::= { cellEventObjects12 2 }

cellEventObjects13 OBJECT-IDENTITY
    STATUS current
    DESCRIPTION
        "Event CELL.13
        Voice-call supervision allows voice-calls"
    ::= { cellEventsGroup 13 }

cell13-ifcname OBJECT-TYPE
    SYNTAX DisplayString
    MAX-ACCESS accessible-for-notify
    STATUS current
    DESCRIPTION
        "Parameter 'ifcname' in event CELL.13"
    ::= { cellEventObjects13 1 }

cellEventObjects14 OBJECT-IDENTITY
    STATUS current
    DESCRIPTION
        "Event CELL.14
        Module upgrade process has finish, FAILURE result."
    ::= { cellEventsGroup 14 }

cell14-ifcname OBJECT-TYPE
    SYNTAX DisplayString
    MAX-ACCESS accessible-for-notify
    STATUS current
    DESCRIPTION
        "Parameter 'ifcname' in event CELL.14"
    ::= { cellEventObjects14 1 }

cellEventObjects15 OBJECT-IDENTITY
    STATUS current
    DESCRIPTION
        "Event CELL.15
        Module upgrade process has finish, OK result."
    ::= { cellEventsGroup 15 }

cell15-ifcname OBJECT-TYPE
    SYNTAX DisplayString
    MAX-ACCESS accessible-for-notify
    STATUS current
    DESCRIPTION
        "Parameter 'ifcname' in event CELL.15"
    ::= { cellEventObjects15 1 }

cellEventObjects16 OBJECT-IDENTITY
    STATUS current
    DESCRIPTION
        "Event CELL.16
        SIM-LOCK process has finish, failure result."
    ::= { cellEventsGroup 16 }

cell16-cause OBJECT-TYPE
    SYNTAX DisplayString
    MAX-ACCESS accessible-for-notify
    STATUS current
    DESCRIPTION
        "Parameter 'cause' in event CELL.16"
    ::= { cellEventObjects16 1 }

cell16-ifcname OBJECT-TYPE
    SYNTAX DisplayString
    MAX-ACCESS accessible-for-notify
    STATUS current
    DESCRIPTION
        "Parameter 'ifcname' in event CELL.16"
    ::= { cellEventObjects16 2 }

cellEventObjects17 OBJECT-IDENTITY
    STATUS current
    DESCRIPTION
        "Event CELL.17
        SIM-LOCK process has finish, OK result."
    ::= { cellEventsGroup 17 }

cell17-ifcname OBJECT-TYPE
    SYNTAX DisplayString
    MAX-ACCESS accessible-for-notify
    STATUS current
    DESCRIPTION
        "Parameter 'ifcname' in event CELL.17"
    ::= { cellEventObjects17 1 }

cellEventObjects18 OBJECT-IDENTITY
    STATUS current
    DESCRIPTION
        "Event CELL.18
        GPS process has finish, OK result."
    ::= { cellEventsGroup 18 }

cell18-hour OBJECT-TYPE
    SYNTAX Integer32
    MAX-ACCESS accessible-for-notify
    STATUS current
    DESCRIPTION
        "Parameter 'hour' in event CELL.18"
    ::= { cellEventObjects18 1 }

cell18-min OBJECT-TYPE
    SYNTAX Integer32
    MAX-ACCESS accessible-for-notify
    STATUS current
    DESCRIPTION
        "Parameter 'min' in event CELL.18"
    ::= { cellEventObjects18 2 }

cell18-sec OBJECT-TYPE
    SYNTAX Integer32
    MAX-ACCESS accessible-for-notify
    STATUS current
    DESCRIPTION
        "Parameter 'sec' in event CELL.18"
    ::= { cellEventObjects18 3 }

cell18-latg OBJECT-TYPE
    SYNTAX Integer32
    MAX-ACCESS accessible-for-notify
    STATUS current
    DESCRIPTION
        "Parameter 'latg' in event CELL.18"
    ::= { cellEventObjects18 4 }

cell18-latm OBJECT-TYPE
    SYNTAX Integer32
    MAX-ACCESS accessible-for-notify
    STATUS current
    DESCRIPTION
        "Parameter 'latm' in event CELL.18"
    ::= { cellEventObjects18 5 }

cell18-latdm OBJECT-TYPE
    SYNTAX Integer32
    MAX-ACCESS accessible-for-notify
    STATUS current
    DESCRIPTION
        "Parameter 'latdm' in event CELL.18"
    ::= { cellEventObjects18 6 }

cell18-latc OBJECT-TYPE
    SYNTAX DisplayString
    MAX-ACCESS accessible-for-notify
    STATUS current
    DESCRIPTION
        "Parameter 'latc' in event CELL.18"
    ::= { cellEventObjects18 7 }

cell18-long OBJECT-TYPE
    SYNTAX Integer32
    MAX-ACCESS accessible-for-notify
    STATUS current
    DESCRIPTION
        "Parameter 'long' in event CELL.18"
    ::= { cellEventObjects18 8 }

cell18-lonm OBJECT-TYPE
    SYNTAX Integer32
    MAX-ACCESS accessible-for-notify
    STATUS current
    DESCRIPTION
        "Parameter 'lonm' in event CELL.18"
    ::= { cellEventObjects18 9 }

cell18-londm OBJECT-TYPE
    SYNTAX Integer32
    MAX-ACCESS accessible-for-notify
    STATUS current
    DESCRIPTION
        "Parameter 'londm' in event CELL.18"
    ::= { cellEventObjects18 10 }

cell18-lonc OBJECT-TYPE
    SYNTAX DisplayString
    MAX-ACCESS accessible-for-notify
    STATUS current
    DESCRIPTION
        "Parameter 'lonc' in event CELL.18"
    ::= { cellEventObjects18 11 }

cell18-altm OBJECT-TYPE
    SYNTAX Integer32
    MAX-ACCESS accessible-for-notify
    STATUS current
    DESCRIPTION
        "Parameter 'altm' in event CELL.18"
    ::= { cellEventObjects18 12 }

cell18-altdm OBJECT-TYPE
    SYNTAX Integer32
    MAX-ACCESS accessible-for-notify
    STATUS current
    DESCRIPTION
        "Parameter 'altdm' in event CELL.18"
    ::= { cellEventObjects18 13 }

cell18-nsat OBJECT-TYPE
    SYNTAX Integer32
    MAX-ACCESS accessible-for-notify
    STATUS current
    DESCRIPTION
        "Parameter 'nsat' in event CELL.18"
    ::= { cellEventObjects18 14 }

cellEventObjects19 OBJECT-IDENTITY
    STATUS current
    DESCRIPTION
        "Event CELL.19
        GPS synchronization, OK result."
    ::= { cellEventsGroup 19 }

cell19-month OBJECT-TYPE
    SYNTAX Integer32
    MAX-ACCESS accessible-for-notify
    STATUS current
    DESCRIPTION
        "Parameter 'month' in event CELL.19"
    ::= { cellEventObjects19 1 }

cell19-day OBJECT-TYPE
    SYNTAX Integer32
    MAX-ACCESS accessible-for-notify
    STATUS current
    DESCRIPTION
        "Parameter 'day' in event CELL.19"
    ::= { cellEventObjects19 2 }

cell19-year OBJECT-TYPE
    SYNTAX Integer32
    MAX-ACCESS accessible-for-notify
    STATUS current
    DESCRIPTION
        "Parameter 'year' in event CELL.19"
    ::= { cellEventObjects19 3 }

cell19-hour OBJECT-TYPE
    SYNTAX Integer32
    MAX-ACCESS accessible-for-notify
    STATUS current
    DESCRIPTION
        "Parameter 'hour' in event CELL.19"
    ::= { cellEventObjects19 4 }

cell19-min OBJECT-TYPE
    SYNTAX Integer32
    MAX-ACCESS accessible-for-notify
    STATUS current
    DESCRIPTION
        "Parameter 'min' in event CELL.19"
    ::= { cellEventObjects19 5 }

cell19-sec OBJECT-TYPE
    SYNTAX Integer32
    MAX-ACCESS accessible-for-notify
    STATUS current
    DESCRIPTION
        "Parameter 'sec' in event CELL.19"
    ::= { cellEventObjects19 6 }

cellEventObjects20 OBJECT-IDENTITY
    STATUS current
    DESCRIPTION
        "Event CELL.20
        GPS process has finish, OK result."
    ::= { cellEventsGroup 20 }

cell20-hdop OBJECT-TYPE
    SYNTAX Integer32
    MAX-ACCESS accessible-for-notify
    STATUS current
    DESCRIPTION
        "Parameter 'hdop' in event CELL.20"
    ::= { cellEventObjects20 1 }

cell20-latg OBJECT-TYPE
    SYNTAX Integer32
    MAX-ACCESS accessible-for-notify
    STATUS current
    DESCRIPTION
        "Parameter 'latg' in event CELL.20"
    ::= { cellEventObjects20 2 }

cell20-latm OBJECT-TYPE
    SYNTAX Integer32
    MAX-ACCESS accessible-for-notify
    STATUS current
    DESCRIPTION
        "Parameter 'latm' in event CELL.20"
    ::= { cellEventObjects20 3 }

cell20-latdm OBJECT-TYPE
    SYNTAX Integer32
    MAX-ACCESS accessible-for-notify
    STATUS current
    DESCRIPTION
        "Parameter 'latdm' in event CELL.20"
    ::= { cellEventObjects20 4 }

cell20-latc OBJECT-TYPE
    SYNTAX DisplayString
    MAX-ACCESS accessible-for-notify
    STATUS current
    DESCRIPTION
        "Parameter 'latc' in event CELL.20"
    ::= { cellEventObjects20 5 }

cell20-long OBJECT-TYPE
    SYNTAX Integer32
    MAX-ACCESS accessible-for-notify
    STATUS current
    DESCRIPTION
        "Parameter 'long' in event CELL.20"
    ::= { cellEventObjects20 6 }

cell20-lonm OBJECT-TYPE
    SYNTAX Integer32
    MAX-ACCESS accessible-for-notify
    STATUS current
    DESCRIPTION
        "Parameter 'lonm' in event CELL.20"
    ::= { cellEventObjects20 7 }

cell20-londm OBJECT-TYPE
    SYNTAX Integer32
    MAX-ACCESS accessible-for-notify
    STATUS current
    DESCRIPTION
        "Parameter 'londm' in event CELL.20"
    ::= { cellEventObjects20 8 }

cell20-lonc OBJECT-TYPE
    SYNTAX DisplayString
    MAX-ACCESS accessible-for-notify
    STATUS current
    DESCRIPTION
        "Parameter 'lonc' in event CELL.20"
    ::= { cellEventObjects20 9 }

cell20-altm OBJECT-TYPE
    SYNTAX Integer32
    MAX-ACCESS accessible-for-notify
    STATUS current
    DESCRIPTION
        "Parameter 'altm' in event CELL.20"
    ::= { cellEventObjects20 10 }

cell20-altdm OBJECT-TYPE
    SYNTAX Integer32
    MAX-ACCESS accessible-for-notify
    STATUS current
    DESCRIPTION
        "Parameter 'altdm' in event CELL.20"
    ::= { cellEventObjects20 11 }

cell20-nsat OBJECT-TYPE
    SYNTAX Integer32
    MAX-ACCESS accessible-for-notify
    STATUS current
    DESCRIPTION
        "Parameter 'nsat' in event CELL.20"
    ::= { cellEventObjects20 12 }

cellEventObjects22 OBJECT-IDENTITY
    STATUS current
    DESCRIPTION
        "Event CELL.22
        GPS Zone filter status change has occur."
    ::= { cellEventsGroup 22 }

cell22-zone OBJECT-TYPE
    SYNTAX Integer32
    MAX-ACCESS accessible-for-notify
    STATUS current
    DESCRIPTION
        "Parameter 'zone' in event CELL.22"
    ::= { cellEventObjects22 1 }

cell22-status OBJECT-TYPE
    SYNTAX Integer32
    MAX-ACCESS accessible-for-notify
    STATUS current
    DESCRIPTION
        "Parameter 'status' in event CELL.22"
    ::= { cellEventObjects22 2 }

cell22-state OBJECT-TYPE
    SYNTAX Integer32
    MAX-ACCESS accessible-for-notify
    STATUS current
    DESCRIPTION
        "Parameter 'state' in event CELL.22"
    ::= { cellEventObjects22 3 }

cellEventObjects23 OBJECT-IDENTITY
    STATUS current
    DESCRIPTION
        "Event CELL.23
        GPS Advisor status change has occur."
    ::= { cellEventsGroup 23 }

cell23-adv OBJECT-TYPE
    SYNTAX Integer32
    MAX-ACCESS accessible-for-notify
    STATUS current
    DESCRIPTION
        "Parameter 'adv' in event CELL.23"
    ::= { cellEventObjects23 1 }

cell23-status OBJECT-TYPE
    SYNTAX Integer32
    MAX-ACCESS accessible-for-notify
    STATUS current
    DESCRIPTION
        "Parameter 'status' in event CELL.23"
    ::= { cellEventObjects23 2 }


cellNotification1 NOTIFICATION-TYPE
    OBJECTS { 
              cell1-info-string, 
              cell1-ifcname 
            }
    STATUS current
    DESCRIPTION
        "Notification of Event CELL.1

        Message: '$1 intf $2'

        Parameters list:
              $1: cell1-info-string
              $2: cell1-ifcname

        Generic informational event."
    ::= { cellNotificationsPrefix 1 }

cellNotification2 NOTIFICATION-TYPE
    OBJECTS { 
              cell2-error-string, 
              cell2-ifcname 
            }
    STATUS current
    DESCRIPTION
        "Notification of Event CELL.2

        Message: '$1 intf $2'

        Parameters list:
              $1: cell2-error-string
              $2: cell2-ifcname

        Generic error report."
    ::= { cellNotificationsPrefix 2 }

cellNotification3 NOTIFICATION-TYPE
    OBJECTS { 
              cell3-state, 
              cell3-ifcname 
            }
    STATUS current
    DESCRIPTION
        "Notification of Event CELL.3

        Message: 'CHANGED Registration state to $1, on interface $2'

        Parameters list:
              $1: cell3-state
              $2: cell3-ifcname

        Registration state has changed."
    ::= { cellNotificationsPrefix 3 }

cellNotification4 NOTIFICATION-TYPE
    OBJECTS { 
              cell4-operator, 
              cell4-ifcname 
            }
    STATUS current
    DESCRIPTION
        "Notification of Event CELL.4

        Message: 'CHANGED PLMN to $1, on interface $2'

        Parameters list:
              $1: cell4-operator
              $2: cell4-ifcname

        The cellular interface now uses a different Public Land Mobile Network,
        (Mobile Operator) identified by the number displayed."
    ::= { cellNotificationsPrefix 4 }

cellNotification5 NOTIFICATION-TYPE
    OBJECTS { 
              cell5-location-area-code, 
              cell5-cell-id,
              cell5-ifcname 
            }
    STATUS current
    DESCRIPTION
        "Notification of Event CELL.5

        Message: 'CHANGE Connected cell LAC $1 CELL ID $2, on interface $3'

        Parameters list:
              $1: cell5-location-area-code
              $2: cell5-cell-id
              $3: cell5-ifcname

        The cellular interface is connected to a different base station,
        identified by the Location Area Code (LAC) and the Cell Identifier code
        (CiD)."
    ::= { cellNotificationsPrefix 5 }

cellNotification6 NOTIFICATION-TYPE
    OBJECTS { 
              cell6-technology, 
              cell6-ifcname 
            }
    STATUS current
    DESCRIPTION
        "Notification of Event CELL.6

        Message: 'CHANGED cellular technology to $1, on interface $2'

        Parameters list:
              $1: cell6-technology
              $2: cell6-ifcname

        Notify a change of the used cellular technology, which implies different
        radio bands, coding methods and therefore different data rates."
    ::= { cellNotificationsPrefix 6 }

cellNotification7 NOTIFICATION-TYPE
    OBJECTS { 
              cell7-rssi-level, 
              cell7-ifcname 
            }
    STATUS current
    DESCRIPTION
        "Notification of Event CELL.7

        Message: 'CHANGED GSM/GPRS Coverage, RSSI $1 dBm, on interface $2'

        Parameters list:
              $1: cell7-rssi-level
              $2: cell7-ifcname

        Received Signal Strength Indication (RSSI) changed to the level
        displayed. This event depends of user's configuration thresholds and
        appears only if the used technology is GSM or GPRS."
    ::= { cellNotificationsPrefix 7 }

cellNotification8 NOTIFICATION-TYPE
    OBJECTS { 
              cell8-rscp-level, 
              cell8-ecno-level,
              cell8-ifcname 
            }
    STATUS current
    DESCRIPTION
        "Notification of Event CELL.8

        Message: 'CHANGED 3GPP Coverage, RSCP to $1 dBm and EcNo to $2 dB, on interface $3'

        Parameters list:
              $1: cell8-rscp-level
              $2: cell8-ecno-level
              $3: cell8-ifcname

        Received Signal Code Power (RSCP) has changed to the level displayed or
        the EcNo ratio (received energy per chip divided by the power density in
        the band) has changed to the value displayed. This event depends of
        user's configuration thresholds and appears only if the used technology
        is UMTS, HSDPA or CDMA."
    ::= { cellNotificationsPrefix 8 }

cellNotification9 NOTIFICATION-TYPE
    OBJECTS { 
              cell9-sim-socket, 
              cell9-ifcname 
            }
    STATUS current
    DESCRIPTION
        "Notification of Event CELL.9

        Message: 'CHANGED Used SIM. Used SIM is located in the $1 socket, on interface $2'

        Parameters list:
              $1: cell9-sim-socket
              $2: cell9-ifcname

        Active SIM is placed in the displayed socked."
    ::= { cellNotificationsPrefix 9 }

cellNotification10 NOTIFICATION-TYPE
    OBJECTS { 
              cell10-call-state-string, 
              cell10-call-state-num,
              cell10-ifcname 
            }
    STATUS current
    DESCRIPTION
        "Notification of Event CELL.10

        Message: 'CHANGED Call state to $1 ($2), on interface $3'

        Parameters list:
              $1: cell10-call-state-string
              $2: cell10-call-state-num
              $3: cell10-ifcname

        Interface call stated changed to the state displayed"
    ::= { cellNotificationsPrefix 10 }

cellNotification11 NOTIFICATION-TYPE
    OBJECTS { 
              cell11-frmwr-release, 
              cell11-ifcname 
            }
    STATUS current
    DESCRIPTION
        "Notification of Event CELL.11

        Message: 'CHANGED cellular module firmware to release $1, on interface $2'

        Parameters list:
              $1: cell11-frmwr-release
              $2: cell11-ifcname

        A successful upgrade has been done to the displayed release"
    ::= { cellNotificationsPrefix 11 }

cellNotification12 NOTIFICATION-TYPE
    OBJECTS { 
              cell12-cause, 
              cell12-ifcname 
            }
    STATUS current
    DESCRIPTION
        "Notification of Event CELL.12

        Message: 'Voice calls disabled due to $1, on interface $2'

        Parameters list:
              $1: cell12-cause
              $2: cell12-ifcname

        Voice-call supervision has disabled voice-calls because of the reported
        reason. These are registration problems o low coverage."
    ::= { cellNotificationsPrefix 12 }

cellNotification13 NOTIFICATION-TYPE
    OBJECTS { 
              cell13-ifcname 
            }
    STATUS current
    DESCRIPTION
        "Notification of Event CELL.13

        Message: 'Voice calls enabled, on interface $1'

        Parameters list:
              $1: cell13-ifcname

        Voice-call supervision allows voice-calls"
    ::= { cellNotificationsPrefix 13 }

cellNotification14 NOTIFICATION-TYPE
    OBJECTS { 
              cell14-ifcname 
            }
    STATUS current
    DESCRIPTION
        "Notification of Event CELL.14

        Message: 'Module upgrade FAILURE, on interface $1'

        Parameters list:
              $1: cell14-ifcname

        Module upgrade process has finish, FAILURE result."
    ::= { cellNotificationsPrefix 14 }

cellNotification15 NOTIFICATION-TYPE
    OBJECTS { 
              cell15-ifcname 
            }
    STATUS current
    DESCRIPTION
        "Notification of Event CELL.15

        Message: 'Module upgrade OK, on interface $1'

        Parameters list:
              $1: cell15-ifcname

        Module upgrade process has finish, OK result."
    ::= { cellNotificationsPrefix 15 }

cellNotification16 NOTIFICATION-TYPE
    OBJECTS { 
              cell16-cause, 
              cell16-ifcname 
            }
    STATUS current
    DESCRIPTION
        "Notification of Event CELL.16

        Message: 'SIM-LOCK process failure($1), on interface $2'

        Parameters list:
              $1: cell16-cause
              $2: cell16-ifcname

        SIM-LOCK process has finish, failure result."
    ::= { cellNotificationsPrefix 16 }

cellNotification17 NOTIFICATION-TYPE
    OBJECTS { 
              cell17-ifcname 
            }
    STATUS current
    DESCRIPTION
        "Notification of Event CELL.17

        Message: 'SIM-LOCK process finish OK, on interface $1'

        Parameters list:
              $1: cell17-ifcname

        SIM-LOCK process has finish, OK result."
    ::= { cellNotificationsPrefix 17 }

cellNotification18 NOTIFICATION-TYPE
    OBJECTS { 
              cell18-hour, 
              cell18-min,
              cell18-sec,
              cell18-latg,
              cell18-latm,
              cell18-latdm,
              cell18-latc,
              cell18-long,
              cell18-lonm,
              cell18-londm,
              cell18-lonc,
              cell18-altm,
              cell18-altdm,
              cell18-nsat 
            }
    STATUS current
    DESCRIPTION
        "Notification of Event CELL.18

        Message: 'GPS process finish OK, information printed: T: $1:$2:$3 Lat: $4- $5.$6' $7 Lon: $8- $9.$10' $11 Alt: $12.$13 m N-sat: $14'

        Parameters list:
              $1: cell18-hour
              $2: cell18-min
              $3: cell18-sec
              $4: cell18-latg
              $5: cell18-latm
              $6: cell18-latdm
              $7: cell18-latc
              $8: cell18-long
              $9: cell18-lonm
              $10: cell18-londm
              $11: cell18-lonc
              $12: cell18-altm
              $13: cell18-altdm
              $14: cell18-nsat

        GPS process has finish, OK result."
    ::= { cellNotificationsPrefix 18 }

cellNotification19 NOTIFICATION-TYPE
    OBJECTS { 
              cell19-month, 
              cell19-day,
              cell19-year,
              cell19-hour,
              cell19-min,
              cell19-sec 
            }
    STATUS current
    DESCRIPTION
        "Notification of Event CELL.19

        Message: 'GPS synchronization OK, information printed: Date: $1/$2/$3 Time: $4:$5:$6'

        Parameters list:
              $1: cell19-month
              $2: cell19-day
              $3: cell19-year
              $4: cell19-hour
              $5: cell19-min
              $6: cell19-sec

        GPS synchronization, OK result."
    ::= { cellNotificationsPrefix 19 }

cellNotification20 NOTIFICATION-TYPE
    OBJECTS { 
              cell20-hdop, 
              cell20-latg,
              cell20-latm,
              cell20-latdm,
              cell20-latc,
              cell20-long,
              cell20-lonm,
              cell20-londm,
              cell20-lonc,
              cell20-altm,
              cell20-altdm,
              cell20-nsat 
            }
    STATUS current
    DESCRIPTION
        "Notification of Event CELL.20

        Message: 'GPS ADVISOR location OK, information: HDOP: $1, Lat: $2- $3.$4' $5 Lon: $6- $7.$8' $9 Alt: $10.$11 m N-sat: $12'

        Parameters list:
              $1: cell20-hdop
              $2: cell20-latg
              $3: cell20-latm
              $4: cell20-latdm
              $5: cell20-latc
              $6: cell20-long
              $7: cell20-lonm
              $8: cell20-londm
              $9: cell20-lonc
              $10: cell20-altm
              $11: cell20-altdm
              $12: cell20-nsat

        GPS process has finish, OK result."
    ::= { cellNotificationsPrefix 20 }

cellNotification21 NOTIFICATION-TYPE
    STATUS current
    DESCRIPTION
        "Notification of Event CELL.21

        Message: 'GPS Location failure due GPS don't detect signal'

        GPS don't get satellites signals."
    ::= { cellNotificationsPrefix 21 }

cellNotification22 NOTIFICATION-TYPE
    OBJECTS { 
              cell22-zone, 
              cell22-status,
              cell22-state 
            }
    STATUS current
    DESCRIPTION
        "Notification of Event CELL.22

        Message: 'GPS ZONE filter $1 status change to $2, zone state $3'

        Parameters list:
              $1: cell22-zone
              $2: cell22-status
              $3: cell22-state

        GPS Zone filter status change has occur."
    ::= { cellNotificationsPrefix 22 }

cellNotification23 NOTIFICATION-TYPE
    OBJECTS { 
              cell23-adv, 
              cell23-status 
            }
    STATUS current
    DESCRIPTION
        "Notification of Event CELL.23

        Message: 'GPS ADVISOR $1 status change to $2'

        Parameters list:
              $1: cell23-adv
              $2: cell23-status

        GPS Advisor status change has occur."
    ::= { cellNotificationsPrefix 23 }

cellNotification24 NOTIFICATION-TYPE
    STATUS current
    DESCRIPTION
        "Notification of Event CELL.24

        Message: 'GPS ADVISOR timeout waiting position'

        Timeout waiting GPS position."
    ::= { cellNotificationsPrefix 24 }


END
