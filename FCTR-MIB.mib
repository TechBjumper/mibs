--  =======================================================================
--  File        : FlowCtrl.mib
--  Description : Private Extention1 MIB for NBase Switch Communications
--                Flow Control Management
--  By          : Alex Ruzin
--  Version     : $Revision:   1.7  $
--  Date        : $Date:   22 Oct 1998 12:59:44  $
--  =======================================================================
--
--
-- Copyright (c) 1995 NBase Switch Communications.  All Rights Reserved.
--
-- Reproduction of this document is authorized on condition that this
-- copyright notice is included.  This NBase SNMP MIB Specification
-- embodies NBase's proprietary intellectual property.  NBase
-- retains all title and ownership in the specification, including any
-- revisions.
--
-- It is NBase's intent to encourage the widespread use of this
-- specification in connection with the management of NBase's
-- products. NBase grants vendor, end-users, and other interested
-- parties a non-exclusive license to use this specification in
-- connection with the management of NBase's products.
--
-- This specification is supplied "AS IS," and NBase makes no
-- warranty, either express or implied, as to the use, operation,
-- condition, or performance of the specification.
--
-- Copyright text courtesy of S. Rotenstein.
--
-- If you have any questions about this MIB, please call NBase
-- Technical Support Center at 1-800-858-7815 from inside USA or
-- 1-818-773-0900 from outside USA.
--
--
-- NBase retains the right to change this MIB without notification.
--

FCTR-MIB DEFINITIONS ::= BEGIN

        IMPORTS
                enterprises						FROM RFC1155-SMI
                OBJECT-TYPE						FROM RFC-1212;

		RequestedFlowControlMode ::= INTEGER  {
				disabled (1),
				enabled (2),
				auto (3)
				}

		GrantedFlowControlMode ::= INTEGER  {
				disabled (1),
				flowControl (2),
				backPressure (3),
                other (4)
				}

-- ************************************************************
-- Object Identifiers Definition
-- ************************************************************

nbase			OBJECT IDENTIFIER ::=	{ enterprises 629 }
nbSwitchG1		OBJECT IDENTIFIER ::=	{ nbase 1 }
nbSwitchG1Il	OBJECT IDENTIFIER ::=	{ nbSwitchG1 50}
nbFctr			OBJECT IDENTIFIER ::=	{ nbSwitchG1Il 2 }

--



-- Global fields (for the whole device)

nbFctrInfo	OBJECT IDENTIFIER ::= { nbFctr 1 }

nbFctrMgmtType	OBJECT-TYPE
    		SYNTAX  INTEGER {
				nonControl (1),
				perDeviceOnly (2),
				perPort (3)
				}
	        ACCESS  read-only
        	STATUS  mandatory
			DESCRIPTION
				"Describes type of Flow Controle of the device.
				The nbFctrPortsRunTable and nbFctrPortsPermTable tables may not
				be supported in the per-device-only(2) case.
				Set new value for nbFctrGlbReqRun and/or nbFctrGlbReqPerm in per-port (3)
				should change this value for all ports in nbFctrPortsRunTable and/or
				nbFctrPortsPermTable."
        	::= { nbFctrInfo 1 }

nbFctrGlbReqRun	OBJECT-TYPE
    		SYNTAX  RequestedFlowControlMode
	        ACCESS  read-write
        	STATUS  mandatory
			DESCRIPTION
				"Requested mode of the device immediately to be set."
        	::= { nbFctrInfo 2 }


nbFctrGlbGrntdRun	OBJECT-TYPE
    		SYNTAX  GrantedFlowControlMode
	        ACCESS  read-only
        	STATUS  mandatory
			DESCRIPTION
				"Actual mode of the device."
        	::= { nbFctrInfo 3 }

nbFctrGlbReqPerm	OBJECT-TYPE
    		SYNTAX  RequestedFlowControlMode
	        ACCESS  read-write
        	STATUS  mandatory
			DESCRIPTION
				"Requested mode of the device, will be implemented from begin
				after next reset/reboot."
        	::= { nbFctrInfo 4 }


--



-- Port Flow control Table
nbFctrPortsTable		OBJECT-TYPE
			SYNTAX  SEQUENCE OF NbFctrPortEntry
			ACCESS  not-accessible
			STATUS  mandatory
			DESCRIPTION
            	"Flow control per port configuration table."
        	::= { nbFctr 2 }

	nbFctrPortEntry OBJECT-TYPE
			SYNTAX  NbFctrPortEntry
			ACCESS  not-accessible
			STATUS  mandatory
			DESCRIPTION
				"Describes Flow control configuration of the port."
			INDEX   { nbFctrPort }
             ::= { nbFctrPortsTable 1 }

	NbFctrPortEntry ::=
			SEQUENCE {
				nbFctrPort			INTEGER,
				nbFctrPortRunReqMode	RequestedFlowControlMode,
				nbFctrPortRunGrntd		GrantedFlowControlMode,
				nbFctrPortPermReqMode	RequestedFlowControlMode
			}

	nbFctrPort OBJECT-TYPE
			SYNTAX  INTEGER   (0..65535)
	        ACCESS  read-only
	       	STATUS  mandatory
			DESCRIPTION
				"Number of Port to be managed."
        	::= { nbFctrPortEntry 1 }

	nbFctrPortRunReqMode OBJECT-TYPE
			SYNTAX  RequestedFlowControlMode
	        ACCESS  read-write
	       	STATUS  mandatory
			DESCRIPTION
				"Requested mode of the port immediately to be set."
        	::= { nbFctrPortEntry 2 }

	nbFctrPortRunGrntd OBJECT-TYPE
			SYNTAX  GrantedFlowControlMode
	        ACCESS  read-only
	       	STATUS  mandatory
			DESCRIPTION
				"Actual mode of the port."
        	::= { nbFctrPortEntry 3 }

	nbFctrPortPermReqMode OBJECT-TYPE
			SYNTAX  RequestedFlowControlMode
	        ACCESS  read-write
	       	STATUS  mandatory
			DESCRIPTION
				"Requested mode of the port immediately to be set."
        	::= { nbFctrPortEntry 4 }
            
END
