-- 	$Id: shiva-ether.asn,v 1.3 1996/01/16 16:38:53 dfox Exp $

--
-- 	Copyright 1992, 1993, 1995, 1996 Shiva Corporation
--

--	This MIB corresponds to the ethernet group in the
--	Kinetics/Excellan FastPath MIB which predates the "dot3" MIB.

SHIVA-ETHER-MIB DEFINITIONS ::= BEGIN

IMPORTS
	Counter
  		FROM RFC1155-SMI
	OBJECT-TYPE
		FROM RFC-1212		-- Concise MIB Definitions
	tEther
		FROM SHIVA-MIB;


    tEtherTable OBJECT-TYPE
	SYNTAX SEQUENCE OF TEtherEntry
	ACCESS not-accessible
	STATUS mandatory
	DESCRIPTION
		"Table of statistics for the ethernet interfaces of a device."
	::= { tEther 1 }

    tEtherEntry OBJECT-TYPE
	SYNTAX	TEtherEntry
	ACCESS	not-accessible
	STATUS	mandatory
	DESCRIPTION
		"The type of a row object in the ethernet table.  This
		represents a single Ethernet Interface.  If an interface
		is not an Ethernet interface, there will not be a row in
		this table for that interface's value of ifIndex."
				-- ifIndex
	--INDEX	{ INTEGER }
	::= { tEtherTable 1 }

    TEtherEntry ::= SEQUENCE {
	    etherCRCErrors	Counter,
	    etherAlignErrors	Counter,
	    etherResourceErrors	Counter,
	    etherOverrunErrors	Counter,
	    etherInPackets	Counter,
	    etherOutPackets	Counter,
	    etherBadTransmits	Counter,
	    etherOversizeFrames	Counter,
	    etherSpurRUReadys	Counter,
	    etherSpurCUActives	Counter,
	    etherSpurUnknowns	Counter,
	    etherBcastDrops	Counter,
	    etherReceiverRestarts Counter,
	    etherReinterrupts	Counter,
	    etherBufferReroutes	Counter,
	    etherBufferDrops	Counter,
	    etherCollisions	Counter,
	    etherDefers		Counter,
	    etherDMAUnderruns	Counter,
	    etherMaxCollisions	Counter,
	    etherNoCarriers	Counter,
	    etherNoCTSs		Counter,
	    etherNoSQEs		Counter
    }

    etherCRCErrors OBJECT-TYPE
	    SYNTAX  Counter
	    ACCESS  read-only
	    STATUS  mandatory
	    DESCRIPTION
		"The total number of CRC errors
		on this ethernet interface"
	    ::= { tEtherEntry 1 }

    etherAlignErrors OBJECT-TYPE
	    SYNTAX  Counter
	    ACCESS  read-only
	    STATUS  mandatory
	    DESCRIPTION
		"The total number of alignment errors
		on this ethernet interface."
	    ::= { tEtherEntry 2 }

    etherResourceErrors OBJECT-TYPE
	    SYNTAX  Counter
	    ACCESS  read-only
	    STATUS  mandatory
	    DESCRIPTION
		"The total number of errors due to lack of resources
		on this ethernet interface."
	    ::= { tEtherEntry 3 }

    etherOverrunErrors OBJECT-TYPE
	    SYNTAX  Counter
	    ACCESS  read-only
	    STATUS  mandatory
	    DESCRIPTION
		"The total number of overrun errors
		on this ethernet interface."
	    ::= { tEtherEntry 4 }

    etherInPackets OBJECT-TYPE
	    SYNTAX  Counter
	    ACCESS  read-only
	    STATUS  mandatory
	    DESCRIPTION
		"The total number of input packets on this ethernet interface."
	    ::= { tEtherEntry 5 }

    etherOutPackets OBJECT-TYPE
	    SYNTAX  Counter
	    ACCESS  read-only
	    STATUS  mandatory
	    DESCRIPTION
		"The total number of output packets
		on this ethernet interface."
	    ::= { tEtherEntry 6 }

    etherBadTransmits OBJECT-TYPE
	    SYNTAX  Counter
	    ACCESS  read-only
	    STATUS  mandatory
	    DESCRIPTION
		"The total number of transmission errors
		on this ethernet interface."
	    ::= { tEtherEntry 7 }

    etherOversizeFrames OBJECT-TYPE
	    SYNTAX  Counter
	    ACCESS  read-only
	    STATUS  mandatory
	    DESCRIPTION
		"The total number of oversize frame errors
		on this ethernet interface."
	    ::= { tEtherEntry 8 }

    etherSpurRUReadys OBJECT-TYPE
	    SYNTAX  Counter
	    ACCESS  read-only
	    STATUS  mandatory
	    DESCRIPTION
		"The total number of spurious RU Ready interrupts
		on this ethernet interface."
	    ::= { tEtherEntry 9 }

    etherSpurCUActives OBJECT-TYPE
	    SYNTAX  Counter
	    ACCESS  read-only
	    STATUS  mandatory
	    DESCRIPTION
		"The total number of spurious CU Active interrupts
		on this ethernet interface."
	    ::= { tEtherEntry 10 }

    etherSpurUnknowns OBJECT-TYPE
	    SYNTAX  Counter
	    ACCESS  read-only
	    STATUS  mandatory
	    DESCRIPTION
		"The total number of unknown spurious interrupts
		on this ethernet interface."
	    ::= { tEtherEntry 11 }

    etherBcastDrops OBJECT-TYPE
	    SYNTAX  Counter
	    ACCESS  read-only
	    STATUS  mandatory
	    DESCRIPTION
		"The total number of broadcast packets dropped
		to free resources on this ethernet interface."
	    ::= { tEtherEntry 12 }

    etherReceiverRestarts OBJECT-TYPE
	    SYNTAX  Counter
	    ACCESS  read-only
	    STATUS  mandatory
	    DESCRIPTION
		"The total number of receiver restarts
		on this ethernet interface."
	    ::= { tEtherEntry 13 }

    etherReinterrupts OBJECT-TYPE
	    SYNTAX  Counter
	    ACCESS  read-only
	    STATUS  mandatory
	    DESCRIPTION
		"The total number of reinterrupts on this ethernet interface."
	    ::= { tEtherEntry 14 }

    etherBufferReroutes OBJECT-TYPE
	    SYNTAX  Counter
	    ACCESS  read-only
	    STATUS  mandatory
	    DESCRIPTION
		"The total number of buffers taken off of queues
		to service incoming packets on this ethernet interface."
	    ::= { tEtherEntry 15 }

    etherBufferDrops OBJECT-TYPE
	    SYNTAX  Counter
	    ACCESS  read-only
	    STATUS  mandatory
	    DESCRIPTION
		"The total number of buffers dropped
		on this ethernet interface."
	    ::= { tEtherEntry 16 }

    etherCollisions OBJECT-TYPE
	    SYNTAX  Counter
	    ACCESS  read-only
	    STATUS  mandatory
	    DESCRIPTION
		"The total number of collisions encountered
		on this ethernet interface."
	    ::= { tEtherEntry 17 }

    etherDefers OBJECT-TYPE
	    SYNTAX  Counter
	    ACCESS  read-only
	    STATUS  mandatory
	    DESCRIPTION
		"The total number of deferrals encountered
		on this ethernet interface."
	    ::= { tEtherEntry 18 }

    etherDMAUnderruns OBJECT-TYPE
	    SYNTAX  Counter
	    ACCESS  read-only
	    STATUS  mandatory
	    DESCRIPTION
		"The total number of DMA Underruns
		on this ethernet interface."
	    ::= { tEtherEntry 19 }

    etherMaxCollisions OBJECT-TYPE
	    SYNTAX  Counter
	    ACCESS  read-only
	    STATUS  mandatory
	    DESCRIPTION
		"The total number of packets dropped
		on this ethernet interface because
		they encountered more than 16 collisions."
	    ::= { tEtherEntry 20 }

    etherNoCarriers OBJECT-TYPE
	    SYNTAX  Counter
	    ACCESS  read-only
	    STATUS  mandatory
	    DESCRIPTION
		"The total number of no carrier errors
		experienced on this ethernet interface."
	    ::= { tEtherEntry 21 }

    etherNoCTSs OBJECT-TYPE
	    SYNTAX  Counter
	    ACCESS  read-only
	    STATUS  mandatory
	    DESCRIPTION
		"The total number of no CTS errors
		experienced on this ethernet interface."
	    ::= { tEtherEntry 22 }

    etherNoSQEs OBJECT-TYPE
	    SYNTAX  Counter
	    ACCESS  read-only
	    STATUS  mandatory
	    DESCRIPTION
		"The total number of no SQE errors
		experienced on this ethernet interface."
	    ::= { tEtherEntry 23 }

END
