-- Toshiba MIB
-- UPS MIB for Toshiba Uninterruptible Power Supplies
--
--{ iso(1) org(3) dod(6) internet(1) private(4) enterprises(1) toshiba(186)
-- equ(1) equups(19) ticups(2) RMTI3(3) }

--=============================================================================

TOSHIBAUPS-MIB DEFINITIONS ::= BEGIN
--=============================================================================
-- Update : June 6, 2015
-- By     : Edwin Rubio, Toshiba International.
-- For    : Modified 'upsAlarmBypassOn', 'upsTrapBypassOn', and 'upsTrapBypassOnClear' description to warning.
--
-- Update : August 23, 2013
-- By     : Edwin Rubio, Toshiba International.
-- For    : Removed 'upsBatteryExtEntry' since it is not used.
--
-- Update : May 3, 2011
-- By     : Hung Huynh, Toshiba International.
-- For    : Modify 'upsStsCtlCfgModeRequest' to include none state.
--
-- Update : Mar 21, 2011
-- By     : Hung Huynh, Toshiba International.
-- For    : Modify 'upsInputPowerSupplyConfiguration','upsOutputPowerSupplyConfiguration','upsBypassPowerSupplyConfiguration'
-- 	    to include 120V and 220V, 50/60Hz options
--
-- Update : Mar 15, 2011
-- By     : Hung Huynh, Toshiba International.
-- For    : Modify 'upsInputFreqWithErr' to add 2 options to choose from rather than having manually enter a value
--
-- Update : Feb 16, 2011
-- By     : Hung Huynh, Toshiba International.
-- For    : Add 'upsBatteryRuntime'& 'upsBatteryCapacity' to upsBattery category
-- For    : Modify 'upsDisplayBuzzerMode' to remove 2 parameters
--
-- Update : Oct 10, 2010
-- By     : Hung Huynh, Toshiba International.
-- For    : Update Traps.
-- For    : Change 'Enterprise Toshiba' to 'Enterprise rmti3'.
--
-- Update : Jan 22, 2010
-- By     : Figo Chang, Ingrasys.
-- For    : Rearrange upsHistory group sequence.
-- For    : Modified upsAgentDefaultLanguage SYNTAX from DisplayString to INTEGER.
--
-- Update : Nov 24, 2009
-- By     : Figo Chang, Ingrasys.
-- For    : Add upsConnectedClientsConnectionTimeout and upsConnectedClientsShutdownTest to upsConnectedClientsTable.
--
-- Update : November 13, 2009
-- By     : Hung Huynh, Toshiba International Corp.
-- For    : Add Traps/alarms for LogIn errors
--
-- Update : November 10, 2009
-- By     : Hung Huynh, Toshiba International Corp.
-- For    : commented out record logs from MIB
--
-- Update : November 02, 2009
-- By     : Hung Huynh, Toshiba International Corp.
-- For    : Added RMTI Data Link Status/Removed PwdReset
--
-- Update : August 20, 2009
-- By     : Hung Huynh, Toshiba International Corp.
-- For    : Remove Alarm Entry no.4 - upsAlarmDescrString
--
-- Update : August 19, 2009
-- By     : Hung Huynh, Toshiba International Corp.
-- For    : Modify Agent Information
--
-- Update : August 06, 2009
-- By     : Hung Huynh, Toshiba International Corp.
-- For    : Modify EMD/Agent Information
--
-- Update : June 30, 2009
-- By     : Hung Huynh, Toshiba International Corp.
-- For    : Modify Password Access
--
-- Update : April 15, 2009
-- By     : Hung Huynh, Toshiba International Corp.
-- For    : Include Records in MIB
--
-- Update : March 23, 2009
-- By     : Hung Huynh, Toshiba International Corp.
-- For    : Modify MIB according Ingrasys recommendation
--
-- Update : January 13, 2009
-- By     : Tiffany Tye, Toshiba International Corp.
-- For    : Add Clear Alarms to each Trap
--
-- Update : September 09, 2008
-- By     : Hung Huynh, Toshiba International Corp.
-- For    : Review and revise Toshiba's SNMP Communication Specification
--=============================================================================

IMPORTS
  DisplayString, TimeStamp, TimeInterval, TestAndIncr, AutonomousType
    FROM SNMPv2-TC
  enterprises, Gauge32, IpAddress
    FROM RFC1155-SMI
  OBJECT-TYPE
    FROM RFC-1212
  TRAP-TYPE
    FROM RFC-1215;

PositiveInteger    ::= INTEGER (0..2147483647)
NonNegativeInteger ::= INTEGER (0..2147483647)

toshiba      OBJECT IDENTIFIER ::= { enterprises 186 }
equ          OBJECT IDENTIFIER ::= { toshiba 1 }
equUPS       OBJECT IDENTIFIER ::= { equ 19 }
ticUPS       OBJECT IDENTIFIER ::= { equUPS 2 }
rmti3        OBJECT IDENTIFIER ::= { ticUPS 3 }

upsIdent     OBJECT IDENTIFIER ::= { rmti3 1 }
upsInput     OBJECT IDENTIFIER ::= { rmti3 2 }
upsOutput    OBJECT IDENTIFIER ::= { rmti3 3 }
upsBypass    OBJECT IDENTIFIER ::= { rmti3 4 }
upsDCBus     OBJECT IDENTIFIER ::= { rmti3 5 }
upsBattery   OBJECT IDENTIFIER ::= { rmti3 6 }
upsStsCtlCfg OBJECT IDENTIFIER ::= { rmti3 7 }
upsHistory   OBJECT IDENTIFIER ::= { rmti3 8 }
upsDisplay   OBJECT IDENTIFIER ::= { rmti3 9 }
upsAlarm     OBJECT IDENTIFIER ::= { rmti3 10 }
upsPassword  OBJECT IDENTIFIER ::= { rmti3 11 }
upsAgent     OBJECT IDENTIFIER ::= { rmti3 12 }
upsConnectedClients   OBJECT IDENTIFIER ::= { rmti3 13 }
upsEmail     OBJECT IDENTIFIER ::= { rmti3 14 }
upsSNMP      OBJECT IDENTIFIER ::= { rmti3 15 }
upsEMD       OBJECT IDENTIFIER ::= { rmti3 16 }
upsTrap      OBJECT IDENTIFIER ::= { rmti3 21 }

-- ===========================================================================
-- upsIdent - RMTI3 Group 1
-- The UPS Identification Group
-- ===========================================================================

upsIdentManufacturer OBJECT-TYPE
    SYNTAX DisplayString (SIZE (0..16))
    ACCESS read-only
    STATUS mandatory
    DESCRIPTION
        "The name of the UPS manufacturer."
    ::= { upsIdent 1 }

upsIdentTypeform OBJECT-TYPE
    SYNTAX DisplayString (SIZE(0..16))
    ACCESS read-only
    STATUS mandatory
    DESCRIPTION
        "The UPS Typeform."
    ::= { upsIdent 2 }

upsIdentSerialNumber OBJECT-TYPE
    SYNTAX DisplayString (SIZE(0..16))
    ACCESS read-only
    STATUS mandatory
    DESCRIPTION
        "The UPS Serial Number."
    ::= { upsIdent 3 }

upsIdentMainFirmwareVersion OBJECT-TYPE
    SYNTAX DisplayString (SIZE(0..16))
    ACCESS read-only
    STATUS mandatory
    DESCRIPTION
        "The UPS firmware version of the main controller."
    ::= { upsIdent 4 }

upsIdentMainBootSectorVersion OBJECT-TYPE
    SYNTAX DisplayString (SIZE(0..16))
    ACCESS read-only
    STATUS mandatory
    DESCRIPTION
        "The UPS boot sector version of the main controller."
    ::= { upsIdent 5 }

upsIdentMainBootLoaderVersion OBJECT-TYPE
    SYNTAX DisplayString (SIZE(0..16))
    ACCESS read-only
    STATUS mandatory
    DESCRIPTION
        "The UPS Boot Loader version of the main controller."
    ::= { upsIdent 6 }

upsIdentJobNumber OBJECT-TYPE
    SYNTAX DisplayString (SIZE(0..16))
    ACCESS read-only
    STATUS mandatory
    DESCRIPTION
        "The UPS Job Number."
    ::= { upsIdent 7 }

upsIdentTestPerson OBJECT-TYPE
    SYNTAX DisplayString (SIZE(0..8))
    ACCESS read-only
    STATUS mandatory
    DESCRIPTION
        "The test person."
    ::= { upsIdent 8 }

upsIdentTestDate OBJECT-TYPE
    SYNTAX DisplayString (SIZE(0..8))
    ACCESS read-only
    STATUS mandatory
    DESCRIPTION
        "The test date displayed as YYYYMMDD format."
    ::= { upsIdent 9 }

upsIdentHardwareBuildDate OBJECT-TYPE
    SYNTAX DisplayString (SIZE(0..8))
    ACCESS read-only
    STATUS mandatory
    DESCRIPTION
        "The date that the UPS was built in YYYYMMDD format."
    ::= { upsIdent 10 }

upsIdentEEPROMVersion OBJECT-TYPE
    SYNTAX DisplayString (SIZE(0..16))
    ACCESS read-only
    STATUS mandatory
    DESCRIPTION
        "The UPS Main controller's EEPROM version."
    ::= { upsIdent 11 }

upsIdentSysName OBJECT-TYPE
    SYNTAX DisplayString (SIZE(0..16))
    ACCESS read-write
    STATUS mandatory
    DESCRIPTION
        "A string identifying the UPS. This object should be
         set by the administrator."
    ::= { upsIdent 12 }

upsIdentAttachedDevices OBJECT-TYPE
    SYNTAX DisplayString (SIZE(0..16))
    ACCESS read-write
    STATUS mandatory
    DESCRIPTION
        "A string identifying the devices attached to the
         output(s) of the UPS. This object should be set by
         the administrator."
    ::= { upsIdent 13 }

upsIdentInstallationDate OBJECT-TYPE
    SYNTAX DisplayString (SIZE(8))
    ACCESS read-write
    STATUS mandatory
    DESCRIPTION
        "The UPS installation date in YYYYMMDD format."
    ::= { upsIdent 14 }

-- ===========================================================================
-- upsInput - RMTI3 Group 2
-- The UPS Input Data Group
-- ===========================================================================
upsInputPowerSupplyConfiguration OBJECT-TYPE
    SYNTAX INTEGER {
        undefined(1),
        volt200Hz60(2),
        volt200Hz50(3),
        volt208Hz60(4),
        volt208Hz50(5),
        volt230Hz60(6),
        volt230Hz50(7),
        volt240Hz60(8),
        volt240Hz50(9),
        volt220Hz60(10),
        volt220Hz50(11),
        volt120Hz60(12),
        volt120Hz50(13),
        reserved0(14),
        reserved1(15),
        reserved2(16)
    }
    ACCESS read-only
    STATUS mandatory
    DESCRIPTION
        "This parameter summarizes the measured and collected data describing
         the input power supply."
    ::= { upsInput 1 }

upsInputNumLines OBJECT-TYPE
    SYNTAX INTEGER {
        one(1),
        two(2)
    }
    ACCESS read-only
    STATUS mandatory
    DESCRIPTION
        "The number of input lines utilized in this device.
         This variable indicates the number of rows in the
         input table."
    ::= { upsInput 2 }

upsInputTable OBJECT-TYPE
    SYNTAX SEQUENCE OF UpsInputEntry
    ACCESS not-accessible
    STATUS mandatory
    DESCRIPTION
        "A list of input table entries. The number of entries
         is given by the value of upsInputNumLine."
    ::= { upsInput  3 }

upsInputEntry OBJECT-TYPE
    SYNTAX UpsInputEntry
    ACCESS not-accessible
    STATUS mandatory
    DESCRIPTION
        "An entry containing information applicable to a
         particular input line."
    INDEX { upsInputIndex }
    ::= { upsInputTable  1 }

UpsInputEntry ::=
    SEQUENCE {
        upsInputIndex      PositiveInteger,
        upsInputFrequency  INTEGER,
        upsInputVoltage    INTEGER,
        upsInputCurrent    INTEGER
    }

-- ===========================================================================
-- upsInputTable/upsInputEntry/upsInputIndex
-- ===========================================================================
upsInputIndex OBJECT-TYPE
    SYNTAX PositiveInteger
    ACCESS not-accessible
    STATUS mandatory
    DESCRIPTION
        "The input line identifier"
    ::= { upsInputEntry 1 }

upsInputFrequency OBJECT-TYPE
    SYNTAX INTEGER
    UNITS  "0.1 Hertz"
    ACCESS read-only
    STATUS mandatory
    DESCRIPTION
        "The present input frequency to the UPS system in 1/10 of Hz."
    ::= { upsInputEntry 2 }

upsInputVoltage OBJECT-TYPE
    SYNTAX INTEGER
    UNITS  "RMS Volts"
    ACCESS read-only
    STATUS mandatory
    DESCRIPTION
        "The input utility line voltage in RMS volts."
    ::= { upsInputEntry 3 }

upsInputCurrent OBJECT-TYPE
    SYNTAX INTEGER
    UNITS  "0.1 RMS Amp"
    ACCESS read-only
    STATUS mandatory
    DESCRIPTION
        "The magnitude of the present input Current in 1/10 RMS Amp."
    ::= { upsInputEntry 4 }

upsInputActivePower OBJECT-TYPE
    SYNTAX INTEGER
    UNITS  "Watt"
    ACCESS read-only
    STATUS mandatory
    DESCRIPTION
        "The UPS active power in Watt. -1 if value is invalid."
    ::= { upsInput 4 }

upsInputApparentPower OBJECT-TYPE
    SYNTAX INTEGER
    UNITS  "Volt-Amp"
    ACCESS read-only
    STATUS mandatory
    DESCRIPTION
        "The input apparent power in Volt-Amp."
    ::= { upsInput 5 }

upsInputPowerFactor OBJECT-TYPE
    SYNTAX INTEGER
    UNITS  "0.01"
    ACCESS read-only
    STATUS mandatory
    DESCRIPTION
        "Ratio of actual power to apparent power. -1 if value is invalid."
    ::= { upsInput 6 }

upsInputRatedTable OBJECT-TYPE
    SYNTAX SEQUENCE OF UpsInputRatedEntry
    ACCESS not-accessible
    STATUS mandatory
    DESCRIPTION
        "A list of input table entries. The number of entries
         is given by the value of upsInputNumLine."
    ::= { upsInput  7 }

upsInputRatedEntry OBJECT-TYPE
    SYNTAX UpsInputRatedEntry
    ACCESS not-accessible
    STATUS mandatory
    DESCRIPTION
        "An entry containing information applicable to a
         particular input line."
    INDEX { upsInputSlotIndex }
    ::= { upsInputRatedTable  1 }

UpsInputRatedEntry ::=
    SEQUENCE {
        upsInputSlotIndex       PositiveInteger,
        upsInputRatedFrequency  INTEGER,
        upsInputRatedVoltage    INTEGER,
        upsInputRatedCurrent    INTEGER
    }

-- ===========================================================================
-- upsInputTable/upsInputEntry/upsInputIndex
-- ===========================================================================
upsInputSlotIndex OBJECT-TYPE
    SYNTAX PositiveInteger
    ACCESS not-accessible
    STATUS mandatory
    DESCRIPTION
        "The input line identifier"
    ::= { upsInputRatedEntry 1 }

upsInputRatedFrequency OBJECT-TYPE
    SYNTAX INTEGER
    UNITS  "0.1 Hertz"
    ACCESS read-only
    STATUS mandatory
    DESCRIPTION
        "The present rated input frequency of the UPS system in 1/10 of Hz."
    ::= { upsInputRatedEntry 2 }

upsInputRatedVoltage OBJECT-TYPE
    SYNTAX INTEGER
    UNITS  "RMS Volts"
    ACCESS read-write
    STATUS mandatory
    DESCRIPTION
        "The magnitude of the rated input voltage in RMS volts. This is set
         by the administrator."
    ::= { upsInputRatedEntry 3 }

upsInputRatedCurrent OBJECT-TYPE
    SYNTAX INTEGER
    UNITS  "0.1 RMS Amp"
    ACCESS read-only
    STATUS mandatory
    DESCRIPTION
        "The magnitude of the rated input current in 1/10 RMS Amp."
    ::= { upsInputRatedEntry 4 }

upsInputOverVoltage OBJECT-TYPE
    SYNTAX INTEGER
    UNITS  "RMS Volt"
    ACCESS read-only
    STATUS mandatory
    DESCRIPTION
        "This is the maximum limit of the input voltage before the
         UPS enters the over voltage state."
    ::= { upsInput 8 }

upsInputOverVoltageRecoverylevel OBJECT-TYPE
    SYNTAX INTEGER
    UNITS  "RMS Volt"
    ACCESS read-only
    STATUS mandatory
    DESCRIPTION
        "The over voltage recovery level. It is the limit
         at which the UPS returns from over voltage state."
    ::= { upsInput 9 }

upsInputVoltagePercent OBJECT-TYPE
    SYNTAX INTEGER
    UNITS  "Percent"
    ACCESS read-only
    STATUS mandatory
    DESCRIPTION
        "The input voltage displayed as a percent."
    ::= { upsInput 10 }

upsInputCurrentPercent OBJECT-TYPE
    SYNTAX INTEGER
    UNITS  "Percent"
    ACCESS read-only
    STATUS mandatory
    DESCRIPTION
        "The input current displayed as a percent."
    ::= { upsInput 11 }

upsInputUnderVoltageDetectlevel OBJECT-TYPE
    SYNTAX INTEGER
    UNITS  "RMS Volt"
    ACCESS read-only
    STATUS mandatory
    DESCRIPTION
        "The input under voltage detection level in RMS volt."
    ::= { upsInput 12 }

upsInputUnderVoltageRecoverylevel OBJECT-TYPE
    SYNTAX INTEGER
    UNITS  "RMS Volt"
    ACCESS read-only
    STATUS mandatory
    DESCRIPTION
        "The input under voltage recovery level in RMS volt."
    ::= { upsInput 13 }

upsInputRatedActivePower OBJECT-TYPE
    SYNTAX INTEGER
    UNITS  "Watt"
    ACCESS read-only
    STATUS mandatory
    DESCRIPTION
        "The rated input active power in Watt."
    ::= { upsInput 14 }

upsInputFreqWithErr OBJECT-TYPE
    SYNTAX INTEGER {
        hz50(1),
        hz60(2)
    }
    ACCESS read-write
    STATUS mandatory
    DESCRIPTION
        "The input frequency configuration in 1/10 Hz when detection
         error occurred. This is set by the administrator."
    ::= { upsInput 15 }

-- ===========================================================================
-- upsOutput - RMTI3 Group 3
-- The UPS Output Data Group
-- ===========================================================================
upsOutputPowerSupplyConfiguration OBJECT-TYPE
    SYNTAX INTEGER {
        undefined(1),
        volt200Hz60(2),
        volt200Hz50(3),
        volt208Hz60(4),
        volt208Hz50(5),
        volt230Hz60(6),
        volt230Hz50(7),
        volt240Hz60(8),
        volt240Hz50(9),
        volt220Hz60(10),
        volt220Hz50(11),
        volt120Hz60(12),
        volt120Hz50(13),
        reserved0(14),
        reserved1(15),
        reserved2(16)
    }
    ACCESS read-only
    STATUS mandatory
    DESCRIPTION
        "This parameter summarizes the measured and collected data describing
         the output power supply."
    ::= { upsOutput 1 }

upsOutputNumLines OBJECT-TYPE
    SYNTAX INTEGER {
        one(1),
        two(2)
    }
    ACCESS read-only
    STATUS mandatory
    DESCRIPTION
        "The number of output lines utilized in this device.
         This variable indicates the number of rows in the
         output table."
    ::= { upsOutput 2 }

upsOutputTable OBJECT-TYPE
    SYNTAX SEQUENCE OF UpsOutputEntry
    ACCESS not-accessible
    STATUS mandatory
    DESCRIPTION
        "A list of Output table entries. The number of entries
         is given by the value of upsOutputNumLines."
    ::= { upsOutput  3 }

upsOutputEntry OBJECT-TYPE
    SYNTAX UpsOutputEntry
    ACCESS not-accessible
    STATUS mandatory
    DESCRIPTION
        "An entry containing information applicable to a
         particular Output line."
    INDEX { upsOutputIndex }
    ::= { upsOutputTable 1 }

UpsOutputEntry ::=
    SEQUENCE {
        upsOutputIndex         PositiveInteger,
        upsOutputFrequency     INTEGER,
        upsOutputVoltage       INTEGER,
        upsOutputCurrent       INTEGER,
        upsOutputActivePower   INTEGER,
        upsOutputApparentPower INTEGER
    }

-- ===========================================================================
-- upsOutputTable/upsOutputEntry/upsOutputIndex
-- ===========================================================================
upsOutputIndex OBJECT-TYPE
    SYNTAX PositiveInteger
    ACCESS not-accessible
    STATUS mandatory
    DESCRIPTION
        "The Output line identifier."
    ::= { upsOutputEntry 1 }

upsOutputFrequency OBJECT-TYPE
    SYNTAX INTEGER
    UNITS  "0.1 Hertz"
    ACCESS read-only
    STATUS mandatory
    DESCRIPTION
        "The present output frequency of the UPS system in 1/10 of Hz."
    ::= { upsOutputEntry 2 }

upsOutputVoltage OBJECT-TYPE
    SYNTAX INTEGER
    UNITS  "RMS Volts"
    ACCESS read-only
    STATUS mandatory
    DESCRIPTION
        "The Output voltage in RMS volts."
    ::= { upsOutputEntry 3 }

upsOutputCurrent OBJECT-TYPE
    SYNTAX INTEGER
    UNITS  "0.1 RMS Amp"
    ACCESS read-only
    STATUS mandatory
    DESCRIPTION
        "The magnitude of the present output current in 1/10 RMS Amps."
    ::= { upsOutputEntry 4 }

upsOutputActivePower OBJECT-TYPE
    SYNTAX INTEGER
    UNITS  "Watt"
    ACCESS read-only
    STATUS mandatory
    DESCRIPTION
        "The present output active power in Watt."
    ::= { upsOutputEntry 5 }

upsOutputApparentPower OBJECT-TYPE
    SYNTAX INTEGER
    UNITS  "Volt-Amp"
    ACCESS read-only
    STATUS mandatory
    DESCRIPTION
        "The output apparent power in Volt-Amp."
    ::= { upsOutputEntry 6 }

upsOutputLoadPercentage OBJECT-TYPE
    SYNTAX INTEGER
    UNITS  "Percent"
    ACCESS read-only
    STATUS mandatory
    DESCRIPTION
        "The present UPS ouput load percentage which is current percent or
         active power whichever greater."
    ::= { upsOutput 4 }

upsOutputRatedTable OBJECT-TYPE
    SYNTAX SEQUENCE OF UpsOutputRatedEntry
    ACCESS not-accessible
    STATUS mandatory
    DESCRIPTION
        "A list of Output table entries. The number of entries
         is given by the value of upsOutputNumLines."
    ::= { upsOutput  5 }

upsOutputRatedEntry OBJECT-TYPE
    SYNTAX UpsOutputRatedEntry
    ACCESS not-accessible
    STATUS mandatory
    DESCRIPTION
        "An entry containing information applicable to a
         particular Output line."
    INDEX {upsOutputIndex }
    ::= { upsOutputRatedTable 1 }

UpsOutputRatedEntry ::=
    SEQUENCE {
        upsOutputSlotIndex          PositiveInteger,
        upsOutputRatedFrequency     INTEGER,
        upsOutputRatedVoltage       INTEGER,
        upsOutputRatedCurrent       INTEGER,
        upsOutputRatedActivePower   INTEGER,
        upsOutputRatedApparentPower INTEGER
    }

-- ===========================================================================
-- upsOutputTable/upsOutputEntry/upsOutputIndex
-- ===========================================================================
upsOutputSlotIndex OBJECT-TYPE
    SYNTAX PositiveInteger
    ACCESS not-accessible
    STATUS mandatory
    DESCRIPTION
        "The Output line identifier."
    ::= { upsOutputRatedEntry 1 }

upsOutputRatedFrequency OBJECT-TYPE
    SYNTAX INTEGER
    UNITS  "0.1 Hertz"
    ACCESS read-only
    STATUS mandatory
    DESCRIPTION
        "The present output rated frequency of the UPS system in 1/10 of Hz."
    ::= { upsOutputRatedEntry 2 }

upsOutputRatedVoltage OBJECT-TYPE
    SYNTAX INTEGER
    UNITS  "RMS Volts"
    ACCESS read-write
    STATUS mandatory
    DESCRIPTION
        "The rated output voltage in RMS volts. This is set by the
          administrator"
    ::= { upsOutputRatedEntry 3 }

upsOutputRatedCurrent OBJECT-TYPE
    SYNTAX INTEGER
    UNITS  "0.1 RMS Amp"
    ACCESS read-only
    STATUS mandatory
    DESCRIPTION
        "The output rated current in 1/10 RMS Amp."
    ::= { upsOutputRatedEntry 4 }

upsOutputRatedActivePower OBJECT-TYPE
    SYNTAX INTEGER
    UNITS  "Watt"
    ACCESS read-only
    STATUS mandatory
    DESCRIPTION
        "The output rated active power in Watt."
    ::= { upsOutputRatedEntry 5 }

upsOutputRatedApparentPower OBJECT-TYPE
    SYNTAX INTEGER
    UNITS  "Volt-Amp"
    ACCESS read-only
    STATUS mandatory
    DESCRIPTION
        "The output rated apparent power in Volt-Amp."
    ::= { upsOutputRatedEntry 6 }

upsOutputUndervoltagelevel OBJECT-TYPE
    SYNTAX INTEGER
    UNITS  "Percent"
    ACCESS read-only
    STATUS mandatory
    DESCRIPTION
        "This parameter displays the minimum allowable voltage before
         it falls into under voltage range."
    ::= { upsOutput 6 }

upsOutputOverVoltagelevel OBJECT-TYPE
    SYNTAX INTEGER
    UNITS  "Percent"
    ACCESS read-only
    STATUS mandatory
    DESCRIPTION
        "This is the maximum limit of the output voltage before the
         UPS enters the over voltage state."
    ::= { upsOutput 7 }

upsOutputFrequencySynchRange OBJECT-TYPE
    SYNTAX NonNegativeInteger
    UNITS  "0.1 Hertz"
    ACCESS read-only
    STATUS mandatory
    DESCRIPTION
        "The allowable range for synchronizing output frequency in 1/10 of Hz."
    ::= { upsOutput 8 }

upsOutputVoltageAdjust OBJECT-TYPE
    SYNTAX INTEGER
    ACCESS read-write
    STATUS mandatory
    DESCRIPTION
        "This parameter allows UPS to be configured to have
         adjustable voltages. This is set by the administrator."
    ::= { upsOutput 9 }

upsOutputRatedPowerFactor OBJECT-TYPE
    SYNTAX INTEGER
    UNITS  "0.01"
    ACCESS read-only
    STATUS mandatory
    DESCRIPTION
        "The rated output power factor."
    ::= { upsOutput 10 }

-- ===========================================================================
-- upsBypass - RMTI3 Group 4
-- The UPS Output Data Group
-- ===========================================================================
upsBypassPowerSupplyConfiguration OBJECT-TYPE
    SYNTAX INTEGER {
        undefined(1),
        volt200Hz60(2),
        volt200Hz50(3),
        volt208Hz60(4),
        volt208Hz50(5),
        volt230Hz60(6),
        volt230Hz50(7),
        volt240Hz60(8),
        volt240Hz50(9),
        volt220Hz60(10),
        volt220Hz50(11),
        volt120Hz60(12),
        volt120Hz50(13),
        reserved0(14),
        reserved1(15),
        reserved2(16)
    }
    ACCESS read-only
    STATUS mandatory
    DESCRIPTION
        "This parameter summarizes the measured and collected data
         describing the power supply into the bypass circuit."
    ::= { upsBypass 1 }

upsBypassNumLine OBJECT-TYPE
    SYNTAX INTEGER {
        one(1),
        two(2)
    }
    ACCESS read-only
    STATUS mandatory
    DESCRIPTION
        "The number of bypass lines utilized in this device.
         This variable indicates the number of rows in the
         bypass table."
    ::= { upsBypass 2 }

upsBypassTable OBJECT-TYPE
    SYNTAX SEQUENCE OF UpsBypassEntry
    ACCESS not-accessible
    STATUS mandatory
    DESCRIPTION
        "A list of Bypass table entries. The number of entries
         is given by the value of upsBypassNumLines."
    ::= { upsBypass  3 }

upsBypassEntry OBJECT-TYPE
    SYNTAX UpsBypassEntry
    ACCESS not-accessible
    STATUS mandatory
    DESCRIPTION
        "An entry containing information applicable to a
         particular line."
    INDEX {upsBypassIndex }
    ::= { upsBypassTable 1 }

UpsBypassEntry ::=
    SEQUENCE {
        upsBypassIndex      PositiveInteger,
        upsBypassFrequency  INTEGER,
        upsBypassVoltage    INTEGER,
        upsBypassCurrent    INTEGER
    }

-- ===========================================================================
-- upsBypassTable/upsBypassEntry/upsBypassIndex
-- ===========================================================================
upsBypassIndex OBJECT-TYPE
    SYNTAX PositiveInteger
    ACCESS not-accessible
    STATUS mandatory
    DESCRIPTION
        "The Bypass line identifier."
    ::= { upsBypassEntry 1 }

upsBypassFrequency OBJECT-TYPE
    SYNTAX INTEGER
    UNITS  "0.1 Hertz"
    ACCESS read-only
    STATUS mandatory
    DESCRIPTION
        "The present Bypass frequency of the UPS system in 1/10 of Hz
         of each phase."
    ::= { upsBypassEntry 2 }

upsBypassVoltage OBJECT-TYPE
    SYNTAX INTEGER
    UNITS  "RMS Volts"
    ACCESS read-only
    STATUS mandatory
    DESCRIPTION
        "The Bypass utility line voltage in RMS volts."
    ::= { upsBypassEntry 3 }

upsBypassCurrent OBJECT-TYPE
    SYNTAX INTEGER
    UNITS  "0.1 RMS Amp"
    ACCESS read-only
    STATUS mandatory
    DESCRIPTION
        "The magnitude of the present bypass Current in 1/10 RMS Amp."
    ::= { upsBypassEntry 4 }

upsBypassApparentPower OBJECT-TYPE
    SYNTAX INTEGER
    UNITS  "Volt-Amp"
    ACCESS read-only
    STATUS mandatory
    DESCRIPTION
        "The Bypass Apparent power in Volt-Amp."
    ::= { upsBypass 4 }

upsBypassUnderVoltageDetectionlevel OBJECT-TYPE
    SYNTAX INTEGER
    UNITS  "Percent"
    ACCESS read-only
    STATUS mandatory
    DESCRIPTION
        "This parameter displays the minimum allowable voltage before
         it falls into bypass undervoltage range."
    ::= { upsBypass 5 }

upsBypassUnderVoltageRecoverylevel OBJECT-TYPE
    SYNTAX INTEGER
    UNITS  "Percent"
    ACCESS read-only
    STATUS mandatory
    DESCRIPTION
        "This parameter displays the allowable voltage that it can recover from."
    ::= { upsBypass 6 }

upsBypassOverVoltageDetectionlevel OBJECT-TYPE
    SYNTAX INTEGER
    UNITS  "RMS Volt"
    ACCESS read-only
    STATUS mandatory
    DESCRIPTION
        "This parameter displays the maximum allowable voltage before
         it falls into over voltage range."
    ::= { upsBypass 7 }

upsBypassOverVoltageRecoverylevel OBJECT-TYPE
    SYNTAX INTEGER
    UNITS  "RMS Volt"
    ACCESS read-only
    STATUS mandatory
    DESCRIPTION
        "This parameter displays the allowable voltage that it can recover from."
    ::= { upsBypass 8 }

-- ===========================================================================
-- upsDCBus - RMTI3 Group 5
-- The UPS DC Bus Data Group
-- ===========================================================================
upsDCBusTotalVoltage OBJECT-TYPE
    SYNTAX INTEGER
    UNITS  "DC Volts"
    ACCESS read-only
    STATUS mandatory
    DESCRIPTION
        "The DC Bus voltage in DC volts."
    ::= { upsDCBus 1 }

upsDCBusPositiveVoltage OBJECT-TYPE
    SYNTAX INTEGER
    UNITS  "DC Volts"
    ACCESS read-only
    STATUS mandatory
    DESCRIPTION
        "The DC Bus positive voltage in DC volts."
    ::= { upsDCBus 2 }

upsDCBusNegativeVoltage OBJECT-TYPE
    SYNTAX INTEGER
    UNITS  "DC Volts"
    ACCESS read-only
    STATUS mandatory
    DESCRIPTION
        "The DC Bus negative voltage in DC volts."
    ::= { upsDCBus 3 }

upsDCBusRatedVoltage OBJECT-TYPE
    SYNTAX INTEGER
    UNITS  "DC Volts"
    ACCESS read-only
    STATUS mandatory
    DESCRIPTION
        "The DC Bus rated voltage in DC volts."
    ::= { upsDCBus 4 }

-- ===========================================================================
-- upsBattery RMTI3 Group 6
-- The UPS Battery Data Group
-- ===========================================================================

upsBatteryStatus OBJECT-TYPE
    SYNTAX INTEGER {
         unknown(1),
         batteryNormal(2),
         batteryLow(3),
         batteryDepleted(4),
         batteryDischarging(5),
         batteryFailure(6)
    }
    ACCESS read-only
    STATUS mandatory
    DESCRIPTION
        "The indication of the capacity remaining in the UPS system's batteries.
         A value of batteryNormal indicates that the remaining run-time sufficient
         to handle the load. A value of batteryLow indicates the battery level is
         low. Continued operation in battery mode will deplate batteries. A value
         of batteryDepleted indicates that the UPS will be unable to sustain the
         present load when and if the utility power is lost (including the
         possibility that the utility power is currently absent and the UPS is
         unable to sustain the output). A value of batteryDischarging indicates UPS
         system is in Battery power."
    ::= { upsBattery 1 }

upsSecondsOnBattery OBJECT-TYPE
    SYNTAX NonNegativeInteger
    UNITS   "Second"
    ACCESS read-only
    STATUS mandatory
    DESCRIPTION
        "If the unit is on battery power, the elapsed time
         since the UPS on battery power, or the
         time since the network management subsystem was last
         restarted, whichever is less. Zero shall be returned
         if the unit is not on battery power."
    ::= { upsBattery 2 }

upsBatteryVoltage OBJECT-TYPE
    SYNTAX INTEGER
    UNITS  "DC Volt"
    ACCESS read-only
    STATUS mandatory
    DESCRIPTION
        "The magnitude of the present battery voltage in DC Volt."
    ::= { upsBattery 3 }

upsBatteryDischargeCurrent OBJECT-TYPE
    SYNTAX INTEGER
    UNITS  "0.1 DC Amp"
    ACCESS read-only
    STATUS mandatory
    DESCRIPTION
        "The present battery discharge current in 1/10 DC Amp."
    ::= { upsBattery 4 }

upsBatteryChargeStatus OBJECT-TYPE
    SYNTAX INTEGER {
        normal-charging(1),
        preventative-charging(2),
        stop-charging(3)
    }
    ACCESS read-only
    STATUS mandatory
    DESCRIPTION
        "The UPS charger status."
    ::= { upsBattery 5 }

upsBatteryNumberofDischarge OBJECT-TYPE
    SYNTAX NonNegativeInteger
    ACCESS read-only
    STATUS mandatory
    DESCRIPTION
        "This will increment when ups goes into backup mode which is longer than 10
         seconds."
    ::= { upsBattery 6 }

upsBatteryCalculatedShutdownVoltage OBJECT-TYPE
    SYNTAX INTEGER
    UNITS  "DC Volt"
    ACCESS read-only
    STATUS mandatory
    DESCRIPTION
        "The battery's shutdown voltage in DC Volt."
    ::= { upsBattery 7 }

upsBatteryLifeRemaining OBJECT-TYPE
    SYNTAX NonNegativeInteger
    UNITS  "Hours"
    ACCESS read-only
    STATUS mandatory
    DESCRIPTION
        "The number of hours of UPS operation in the present environment
         until the batteries must be replaced."
    ::= { upsBattery 8 }

upsBatteryRatedAmpereHour OBJECT-TYPE
    SYNTAX INTEGER
    UNITS  "Amp-Hour"
    ACCESS read-only
    STATUS mandatory
    DESCRIPTION
        "The battery capacity in Amp-Hour."
    ::= { upsBattery 9 }

upsBatteryInSeries OBJECT-TYPE
    SYNTAX INTEGER
    ACCESS read-only
    STATUS mandatory
    DESCRIPTION
        "The number of batteries in each string connected in series."
    ::= { upsBattery 10 }

upsBatteryInParallel OBJECT-TYPE
    SYNTAX INTEGER
    ACCESS read-only
    STATUS mandatory
    DESCRIPTION
        "The number of batteries connected in parallel."
    ::= { upsBattery 11 }

upsBatteryInstallationDate OBJECT-TYPE
    SYNTAX DisplayString (SIZE(0..8))
    ACCESS read-only
    STATUS mandatory
    DESCRIPTION
        "The battery installation date in YYYYMMDD format."
    ::= { upsBattery 12 }

upsBatteryVoltageShutdownLevel OBJECT-TYPE
    SYNTAX INTEGER
    UNITS  "Percent"
    ACCESS read-only
    STATUS mandatory
    DESCRIPTION
        "The UPS battery voltage shutdown level."
    ::= { upsBattery 13 }

upsBatteryExtTable OBJECT-TYPE
    SYNTAX SEQUENCE OF UpsBatteryExtEntry
    ACCESS not-accessible
    STATUS mandatory
    DESCRIPTION
        "A list of Battery table entries."
    ::= { upsBattery 14 }

upsBatteryExtEntry OBJECT-TYPE
    SYNTAX UpsBatteryExtEntry
    ACCESS not-accessible
    STATUS mandatory
    DESCRIPTION
        "An entry containing information applicable to a
         particular Battery."
    INDEX {upsBatteryExtIndex }
    ::= { upsBatteryExtTable 1 }

UpsBatteryExtEntry ::=
    SEQUENCE {
        upsBatteryExtIndex               PositiveInteger,
        upsBatteryExtInSeries            INTEGER,
        upsBatteryExtInParallel          INTEGER,
        upsBatteryExtRatedAmpereHour     INTEGER,
        upsBatteryExtCRate               INTEGER,
        upsBatteryExtInstallDate         DisplayString
    }

-- ===========================================================================
-- upsBatteryTable/upsBattery/upsBatteryIndex
-- ===========================================================================
upsBatteryExtIndex OBJECT-TYPE
    SYNTAX PositiveInteger
    ACCESS not-accessible
    STATUS mandatory
    DESCRIPTION
        "The Battery line identifier"
    ::= { upsBatteryExtEntry 1 }


upsBatteryExtInSeries OBJECT-TYPE
    SYNTAX INTEGER
    ACCESS read-only
    STATUS mandatory
    DESCRIPTION
        "Specifies the number of batteries in the external cabinet
         that are connected in series."
    ::= { upsBatteryExtEntry 2 }

upsBatteryExtInParallel OBJECT-TYPE
    SYNTAX INTEGER
    ACCESS read-only
    STATUS mandatory
    DESCRIPTION
        "Specifies the number of batteries in the external cabinet
         that are connected in parallel."
    ::= { upsBatteryExtEntry 3 }

upsBatteryExtRatedAmpereHour OBJECT-TYPE
    SYNTAX INTEGER
    UNITS  "Amp-Hour"
    ACCESS read-only
    STATUS mandatory
    DESCRIPTION
        "The external battery's capacity in Amp-Hour."
    ::= { upsBatteryExtEntry 4 }

upsBatteryExtCRate OBJECT-TYPE
    SYNTAX INTEGER
    ACCESS read-only
    STATUS mandatory
    DESCRIPTION
        "The external battery's C rate."
    ::= { upsBatteryExtEntry 5 }

upsBatteryExtInstallDate OBJECT-TYPE
    SYNTAX DisplayString (SIZE(0..8))
    ACCESS read-only
    STATUS mandatory
    DESCRIPTION
        "The battery installation date in YYYYMMDD format."
    ::= { upsBatteryExtEntry 6 }

upsBatteryLowBattLevel OBJECT-TYPE
    SYNTAX INTEGER
    UNITS  "Percent"
    ACCESS read-only
    STATUS mandatory
    DESCRIPTION
        "The low battery level of the UPS."
    ::= { upsBattery 15 }

upsBatteryChargerOverVoltageDelay OBJECT-TYPE
    SYNTAX INTEGER
    UNITS  "Second"
    ACCESS read-only
    STATUS mandatory
    DESCRIPTION
        "The UPS's charger over voltage detection delay in seconds."
    ::= { upsBattery 16 }

upsBatteryCalcLBLevel OBJECT-TYPE
    SYNTAX INTEGER
    UNITS  "Volt DC"
    ACCESS read-only
    STATUS mandatory
    DESCRIPTION
        "The calculated low battery level."
    ::= { upsBattery 17 }

upsBatteryCapacity OBJECT-TYPE
    SYNTAX INTEGER
    UNITS  "Percent"
    ACCESS read-only
    STATUS mandatory
    DESCRIPTION
        "The UPS battery capacity in percent."
    ::= { upsBattery 18 }

upsBatteryRuntime OBJECT-TYPE
    SYNTAX INTEGER
    UNITS  "Second"
    ACCESS read-only
    STATUS mandatory
    DESCRIPTION
        "The UPS battery runtime in minutes. It will return -1 or N/A if not available."
    ::= { upsBattery 19 }


-- ===========================================================================
-- upsStsCtlCfg RMTI3 Group 7
-- The UPS status, control and configuration
-- ===========================================================================
upsStsCtlCfgSystemTemperature OBJECT-TYPE
    SYNTAX INTEGER
    UNITS  "Celsius"
    ACCESS read-only
    STATUS mandatory
    DESCRIPTION
        "The UPS system temperature in Celsius."
    ::= { upsStsCtlCfg 1 }

upsStsCtlCfgBatteryTemperature OBJECT-TYPE
    SYNTAX INTEGER
    UNITS  "Celsius"
    ACCESS read-only
    STATUS mandatory
    DESCRIPTION
        "The UPS Battery temperature in Celsius."
    ::= { upsStsCtlCfg 2 }

upsStsCtlCfgPresentMode OBJECT-TYPE
    SYNTAX INTEGER {
        shutdown0(1),
        shutdown1(2),
        shutdown2(3),
        online(4),
        backup(5),
        battery-test(6),
        bypass6(7),
        bypass7(8),
        bypass8(9),
        startup(10)
    }
    ACCESS read-only
    STATUS mandatory
    DESCRIPTION
        "The present mode of the UPS system."
    ::= { upsStsCtlCfg 3 }

upsStsCtlCfgModeRequest OBJECT-TYPE
    SYNTAX INTEGER {
        none(1),
	shutdown(2),
        bypass(3),
        online(4),
        battery-test(5)
    }
    ACCESS read-write
    STATUS mandatory
    DESCRIPTION
        "The mode of the UPS system requested by the user."
    ::= { upsStsCtlCfg 4 }

upsStsCtlCfgModeTransitionTimer OBJECT-TYPE
    SYNTAX NonNegativeInteger
    UNITS  "Second"
    ACCESS read-write
    STATUS mandatory
    DESCRIPTION
        "The timer upon whose expiration a mode transition will be
         attempted by the system."
    ::= { upsStsCtlCfg 5 }

upsStsCtlCfgEPOContactState OBJECT-TYPE
    SYNTAX INTEGER {
        open(1),
        closed(2)
    }
    ACCESS read-only
    STATUS mandatory
    DESCRIPTION
        "The EPO contact state of the UPS system."
    ::= { upsStsCtlCfg 6 }

upsStsCtlCfgRunStopSwitchState OBJECT-TYPE
    SYNTAX INTEGER {
        stop(1),
        run(2)
    }
    ACCESS read-only
    STATUS mandatory
    DESCRIPTION
        "The Run/Stop switch state of the UPS system."
    ::= { upsStsCtlCfg 7 }

upsStsCtlCfgServicePortCommStatus OBJECT-TYPE
    SYNTAX INTEGER {
        unknown(1),
        normal-OK(2),
        off(3),
        error(4)
    }
    ACCESS read-only
    STATUS mandatory
    DESCRIPTION
        "The service port communication status."
    ::= { upsStsCtlCfg 8 }

upsStsCtlCfgInternalCommStatus OBJECT-TYPE
    SYNTAX INTEGER {
        unknown(1),
        normal-OK(2),
        off(3),
        error(4)
    }
    ACCESS read-only
    STATUS mandatory
    DESCRIPTION
        "The internal communication status of the UPS system such as display panel."
    ::= { upsStsCtlCfg 9 }

upsStsCtlCfgSecurityLevel OBJECT-TYPE
    SYNTAX DisplayString (SIZE(0..16))
    ACCESS read-write
    STATUS mandatory
    DESCRIPTION
        "The current security level of the UPS system"
    ::= { upsStsCtlCfg 10 }

upsStsCtlCfgPresentDate OBJECT-TYPE
    SYNTAX NonNegativeInteger
    ACCESS read-write
    STATUS mandatory
    DESCRIPTION
        "The present date of the UPS. This is configurable by Administrator."
    ::= { upsStsCtlCfg 11 }

upsStsCtlCfgPresentTime OBJECT-TYPE
    SYNTAX NonNegativeInteger
    ACCESS read-write
    STATUS mandatory
    DESCRIPTION
        "The present time of the UPS. This is configurable by Administrator."
    ::= { upsStsCtlCfg 12 }

upsStsCtlCfgPresentTimeStamp OBJECT-TYPE
    SYNTAX INTEGER
    ACCESS read-only
    STATUS mandatory
    DESCRIPTION
        "Present system timestamp."
    ::= { upsStsCtlCfg 13 }

upsStsCtlCfgEnableRMTIToControlMode OBJECT-TYPE
    SYNTAX INTEGER {
        disable(1),
        enable(2)
    }
    ACCESS read-write
    STATUS mandatory
    DESCRIPTION
        "Allow to enable or disable SNMP to control the UPS Shutdown and Online Mode."
    ::= { upsStsCtlCfg 14 }

upsStsCtlCfgEnableStartupDelay OBJECT-TYPE
    SYNTAX INTEGER {
        disable(1),
        enable(2)
    }
    ACCESS read-write
    STATUS mandatory
    DESCRIPTION
        "This delay timer, when enabled, will begin counting down at UPS startup
         immediately following a UPS shutdown by any means other than battery
         exhaustion. UPS output of any kind will be prohibited."
    ::= { upsStsCtlCfg 15 }

upsStsCtlCfgStartUpDelayMode OBJECT-TYPE
    SYNTAX INTEGER {
        bypass(1),
        online(2)
    }
    ACCESS read-write
    STATUS mandatory
    DESCRIPTION
        "UPS mode into which the UPS will transition at the expiration
         of the Start-Up delay timer."
    ::= { upsStsCtlCfg 16 }

upsStsCtlCfgStartUpDelay OBJECT-TYPE
    SYNTAX NonNegativeInteger
    UNITS  "Second"
    ACCESS read-write
    STATUS mandatory
    DESCRIPTION
        "When the timer is counting down, its changing value is reflected,
         otherwise its starting value is reported."
    ::= { upsStsCtlCfg 17 }

upsStsCtlCfgRemoteShutDownContactState OBJECT-TYPE
    SYNTAX INTEGER {
        open(1),
        closed(2)
    }
    ACCESS read-only
    STATUS mandatory
    DESCRIPTION
        "The state of the Remote Contacts Shutdown Control."
    ::= { upsStsCtlCfg 18 }

upsStsCtlCfgRemoteShutdownContactMode OBJECT-TYPE
    SYNTAX INTEGER {
        bypass(1),
        shutdown-while-contact-closed(2)
    }
    ACCESS read-write
    STATUS mandatory
    DESCRIPTION
        "The mode of the Remote Contacts Shutdown control."
    ::= { upsStsCtlCfg 19 }

upsStsCtlCfgEnableDryContactLANShutdown OBJECT-TYPE
    SYNTAX INTEGER {
        disable(1),
        enable(2)
    }
    ACCESS read-write
    STATUS mandatory
    DESCRIPTION
        "When enable, UPS will accept LAN signal request for UPS shutdown
         but only in accordance with restrictions of the following timer."
    ::= { upsStsCtlCfg 20 }

upsStsCtlCfgDryContactLANShutdownTimer OBJECT-TYPE
    SYNTAX NonNegativeInteger
    UNITS  "Second"
    ACCESS read-write
    STATUS mandatory
    DESCRIPTION
        "Timer begins upon input power recovery and during its lifetime, allows
         the LAN input signal to affect a UPS Shutdown control."
    ::= { upsStsCtlCfg 21 }

upsStsCtlCfgDryContactOnBattDelay OBJECT-TYPE
    SYNTAX NonNegativeInteger
    UNITS  "Second"
    ACCESS read-write
    STATUS mandatory
    DESCRIPTION
        "Time delay between actual event occurrence and dry contact
         closure to signal external devices of the event."
    ::= { upsStsCtlCfg 22 }

upsStsCtlCfgDryContactLowBattDelay OBJECT-TYPE
    SYNTAX NonNegativeInteger
    UNITS  "Second"
    ACCESS read-write
    STATUS mandatory
    DESCRIPTION
        "Delay timer between actual event occurrence and dry contact
         closure to signal external devices of the event."
    ::= { upsStsCtlCfg 23 }

upsStsCtlCfgEnableStartupBattTest OBJECT-TYPE
    SYNTAX INTEGER {
        disable(1),
        enable(2)
    }
    ACCESS read-write
    STATUS mandatory
    DESCRIPTION
        "Forces a battery test when UPS starts."
    ::= { upsStsCtlCfg 24 }

upsStsCtlCfgEnableBatteryTest OBJECT-TYPE
    SYNTAX INTEGER {
        disable(1),
        enable(2)
    }
    ACCESS read-write
    STATUS mandatory
    DESCRIPTION
        "Allow to enable or disable battery test."
    ::= { upsStsCtlCfg 25 }

upsStsCtlCfgBatteryTestConditionStatus OBJECT-TYPE
    SYNTAX INTEGER {
        battery-test-prohibited(1),
        battery-test-ok(2)
    }
    ACCESS read-only
    STATUS mandatory
    DESCRIPTION
        "This notifies the user of the availability of the battery test feature."
    ::= { upsStsCtlCfg 26 }

upsStsCtlCfgMaxBatteryTestFreq OBJECT-TYPE
    SYNTAX INTEGER {
        daily(1),
        weekly(2),
        monthly(3)
    }
    ACCESS read-write
    STATUS mandatory
    DESCRIPTION
        "This specified how often the battery test should occur. This is set by
         the administrator"
    ::= { upsStsCtlCfg 27 }

upsStsCtlCfgEnableRestartAfterBattShutdown OBJECT-TYPE
    SYNTAX INTEGER {
        disable(1),
        enable(2)
    }
    ACCESS read-write
    STATUS mandatory
    DESCRIPTION
        "Mode set for UPS input power detection immediately after a shutdown while
         on batteries. This is set by the administrator."
    ::= { upsStsCtlCfg 28 }

upsStsCtlCfgRestartDelay OBJECT-TYPE
    SYNTAX INTEGER
    UNITS  "Second"
    ACCESS read-write
    STATUS mandatory
    DESCRIPTION
        "Countdown begins only when UPS input power is restored immediately
         following a UPS Shutdown while on batteries."
    ::= { upsStsCtlCfg 29 }

upsStsCtlCfgEnableAutoTransferMode OBJECT-TYPE
    SYNTAX INTEGER {
        disable(1),
        enable(2)
    }
    ACCESS read-write
    STATUS mandatory
    DESCRIPTION
        "This feature allows the administrators to enable or to disable the auto
         transfer feature of the UPS."
    ::= { upsStsCtlCfg 30 }

upsStsCtlCfgAutoRetransferDelay OBJECT-TYPE
    SYNTAX INTEGER
    UNITS  "Second"
    ACCESS read-write
    STATUS mandatory
    DESCRIPTION
        "Time period to wait after fault occurrence before attempting transfer
          back Online"
    ::= { upsStsCtlCfg 31 }

upsStsCtlCfgServicePortCommSetting OBJECT-TYPE
    SYNTAX INTEGER {
        bd9600(1),
        bd19200(2),
        bd38400(3),
        bd57600(4)
    }
    ACCESS read-write
    STATUS mandatory
    DESCRIPTION
        "The UPS baud rate settings."
    ::= { upsStsCtlCfg 32 }

upsStsCtlCfgInvertRemoteShutdownLogic OBJECT-TYPE
    SYNTAX INTEGER {
        not-inverted(1),
        inverted(2)
    }
    ACCESS read-write
    STATUS mandatory
    DESCRIPTION
        "Remote Shutdown logic."
    ::= { upsStsCtlCfg 33 }

upsStsCtlCfgRestartMode OBJECT-TYPE
    SYNTAX INTEGER {
        bypass(1),
        online(2)
    }
    ACCESS read-write
    STATUS mandatory
    DESCRIPTION
        "Restart Mode."
    ::= { upsStsCtlCfg 34 }

-- ===========================================================================
-- upsHistory RMTI3 Group 8
-- The UPS History Data Group
-- ===========================================================================
upsHistorySysOperationTime OBJECT-TYPE
    SYNTAX NonNegativeInteger
    UNITS  "Second"
    ACCESS read-only
    STATUS mandatory
    DESCRIPTION
        "The amount of time the UPS has been on."
    ::= { upsHistory 1 }

upsHistoryInverterOperationTime OBJECT-TYPE
    SYNTAX NonNegativeInteger
    UNITS  "Second"
    ACCESS read-only
    STATUS mandatory
    DESCRIPTION
        "The amount of time the UPS has been in On-Line Mode."
    ::= { upsHistory 2 }

upsHistoryBackupOperationTime OBJECT-TYPE
    SYNTAX NonNegativeInteger
    UNITS  "Second"
    ACCESS read-only
    STATUS mandatory
    DESCRIPTION
        "The amount of time the UPS has been in BackUp Mode."
    ::= { upsHistory 3 }

upsHistoryLifetimeRemaining OBJECT-TYPE
    SYNTAX NonNegativeInteger
    UNITS  "Hour"
    ACCESS read-only
    STATUS mandatory
    DESCRIPTION
        "The remaining lifetime of the UPS."
    ::= { upsHistory 4 }

upsHistoryHighestSystemTemp OBJECT-TYPE
    SYNTAX INTEGER
    UNITS  "Celsius"
    ACCESS read-only
    STATUS mandatory
    DESCRIPTION
        "The highest system temperature of the UPS."
    ::= { upsHistory 5 }

upsHistoryHighestBatteryTemp OBJECT-TYPE
    SYNTAX INTEGER
    UNITS  "Celsius"
    ACCESS read-only
    STATUS mandatory
    DESCRIPTION
        "The highest battery temperature."
    ::= { upsHistory 6 }

upsHistoryTotalNumInputUnderVolt OBJECT-TYPE
    SYNTAX NonNegativeInteger
    ACCESS read-only
    STATUS mandatory
    DESCRIPTION
        "Total number of times the UPS has entered under voltage state."
    ::= { upsHistory 7 }

upsHistoryTotalNumOverload OBJECT-TYPE
    SYNTAX NonNegativeInteger
    ACCESS read-only
    STATUS mandatory
    DESCRIPTION
        "Total number of times the UPS has been overloaded."
    ::= { upsHistory 8 }

upsHistoryTotalNumTest OBJECT-TYPE
    SYNTAX NonNegativeInteger
    ACCESS read-only
    STATUS mandatory
    DESCRIPTION
        "Total number of tests that has been conducted on the UPS."
    ::= { upsHistory 9 }

--upsHistoryTestReportTable OBJECT-TYPE
--    SYNTAX SEQUENCE OF UpsHistoryTestReportEntry
--    ACCESS not-accessible
--    STATUS mandatory
--    DESCRIPTION
--        ""
--    ::= { upsHistory 10 }

--upsHistoryTestReportEntry OBJECT-TYPE
--    SYNTAX UpsHistoryTestReportEntry
--    ACCESS not-accessible
--    STATUS mandatory
--    DESCRIPTION
--        "An entry containing information applicable to a
--         particular input line."
--    INDEX { upsHistoryTestReportIndex }
--    ::= { upsHistoryTestReportTable  1 }

--UpsHistoryTestReportEntry ::=
--    SEQUENCE {
--        upsHistoryTestReportIndex          PositiveInteger,
--       upsHistoryTestReportDateTime       DisplayString,
--        upsHistoryTestReportInputSys       INTEGER,
--        upsHistoryTestReportOutputSys      INTEGER,
--        upsHistoryTestReportVin            INTEGER,
--        upsHistoryTestReportVout           INTEGER,
--        upsHistoryTestReportIout           INTEGER,
--        upsHistoryTestReportVdc            INTEGER,
--        upsHistoryTestReportVb             INTEGER,
--        upsHistoryTestReportTestType       INTEGER,
--        upsHistoryTestReportRSV            INTEGER,
--        upsHistoryTestReportResult         INTEGER,
--        upsHistoryTestReportTriggerSource  INTEGER

--    }

-- ===========================================================================
-- upsHistoryTestReportTable/upsHistoryTestReportEntry/upsHistoryTestReportIndex
-- ===========================================================================
--upsHistoryTestReportIndex OBJECT-TYPE
--    SYNTAX PositiveInteger
--    ACCESS not-accessible
--    STATUS mandatory
--    DESCRIPTION
--        ""
--    ::= { upsHistoryTestReportEntry 1 }

--upsHistoryTestReportDateTime OBJECT-TYPE
--    SYNTAX DisplayString (SIZE(0..31))
--    ACCESS read-only
--    STATUS mandatory
--    DESCRIPTION
--        ""
--    ::= { upsHistoryTestReportEntry 2 }

--upsHistoryTestReportInputSys OBJECT-TYPE
--    SYNTAX INTEGER
--    ACCESS read-only
--    STATUS mandatory
--    DESCRIPTION
--        ""
--    ::= { upsHistoryTestReportEntry 3 }

--upsHistoryTestReportOutputSys OBJECT-TYPE
--    SYNTAX INTEGER
--    ACCESS read-only
--    STATUS mandatory
--    DESCRIPTION
--        ""
--    ::= { upsHistoryTestReportEntry 4 }

--upsHistoryTestReportVin OBJECT-TYPE
--    SYNTAX INTEGER
--    UNITS  "%"
--    ACCESS read-only
--    STATUS mandatory
--    DESCRIPTION
--        ""
--    ::= { upsHistoryTestReportEntry 5 }

--upsHistoryTestReportVout OBJECT-TYPE
--    SYNTAX INTEGER
--    UNITS  "%"
--    ACCESS read-only
--    STATUS mandatory
--    DESCRIPTION
--        ""
--    ::= { upsHistoryTestReportEntry 6 }

--upsHistoryTestReportIout OBJECT-TYPE
--    SYNTAX INTEGER
--    UNITS  "%"
--    ACCESS read-only
--    STATUS mandatory
--    DESCRIPTION
--        ""
--    ::= { upsHistoryTestReportEntry 7 }

--upsHistoryTestReportVdc OBJECT-TYPE
--    SYNTAX INTEGER
--    UNITS  "%"
--    ACCESS read-only
--    STATUS mandatory
--    DESCRIPTION
--        ""
--    ::= { upsHistoryTestReportEntry 8 }

--upsHistoryTestReportVb OBJECT-TYPE
--    SYNTAX INTEGER
--    UNITS  "%"
--    ACCESS read-only
--    STATUS mandatory
--    DESCRIPTION
--        ""
--    ::= { upsHistoryTestReportEntry 9 }

--upsHistoryTestReportTestType OBJECT-TYPE
--    SYNTAX INTEGER
--    ACCESS read-only
--    STATUS mandatory
--    DESCRIPTION
--        ""
--    ::= { upsHistoryTestReportEntry 10 }

--upsHistoryTestReportRSV OBJECT-TYPE
--    SYNTAX INTEGER
--    ACCESS read-only
--    STATUS mandatory
--    DESCRIPTION
--        ""
--    ::= { upsHistoryTestReportEntry 11 }

--upsHistoryTestReportResult OBJECT-TYPE
--    SYNTAX INTEGER
--    ACCESS read-only
--    STATUS mandatory
--    DESCRIPTION
--        ""
--    ::= { upsHistoryTestReportEntry 12 }

--upsHistoryTestReportTriggerSource OBJECT-TYPE
--    SYNTAX INTEGER
--    ACCESS read-only
--    STATUS mandatory
--    DESCRIPTION
--        ""
--    ::= { upsHistoryTestReportEntry 13 }

upsHistoryTotalNumBackup OBJECT-TYPE
    SYNTAX NonNegativeInteger
    ACCESS read-only
    STATUS mandatory
    DESCRIPTION
        "Total number of times the UPS has been in Back-Up mode."
    ::= { upsHistory 10 }

--upsHistoryBackupReportTable OBJECT-TYPE
--    SYNTAX SEQUENCE OF UpsHistoryBackupReportEntry
--    ACCESS not-accessible
--    STATUS mandatory
--    DESCRIPTION
--        ""
--    ::= { upsHistory 12 }

--upsHistoryBackupReportEntry OBJECT-TYPE
--    SYNTAX UpsHistoryBackupReportEntry
--    ACCESS not-accessible
--    STATUS mandatory
--    DESCRIPTION
--        "An entry containing information applicable to a
--         particular input line."
--    INDEX { upsHistoryBackupReportIndex }
--    ::= { upsHistoryBackupReportTable  1 }

--UpsHistoryBackupReportEntry ::=
--    SEQUENCE {
--        upsHistoryBackupReportIndex         PositiveInteger,
--        upsHistoryBackupReportDateTime      DisplayString,
--        upsHistoryBackupReportInputSys      INTEGER,
--        upsHistoryBackupReportOutputSys     INTEGER,
--        upsHistoryBackupReportVin           INTEGER,
--        upsHistoryBackupReportVout          INTEGER,
--        upsHistoryBackupReportIout          INTEGER,
--        upsHistoryBackupReportVdc           INTEGER,
--        upsHistoryBackupReportVbStart       INTEGER,
--        upsHistoryBackupReportVbEnd         INTEGER,
--        upsHistoryBackupReportTriggerSource INTEGER,
--        upsHistoryBackupReportDuration      INTEGER
--    }

-- ===========================================================================
-- upsHistoryBackupReportTable/upsHistoryBackupReportEntry/upsHistoryBackupReportIndex
-- ===========================================================================
--upsHistoryBackupReportIndex OBJECT-TYPE
--    SYNTAX PositiveInteger
--    ACCESS not-accessible
--    STATUS mandatory
--    DESCRIPTION
--        ""
--    ::= { upsHistoryBackupReportEntry 1 }

--upsHistoryBackupReportDateTime OBJECT-TYPE
--    SYNTAX DisplayString (SIZE(0..31))
--    ACCESS read-only
--    STATUS mandatory
--    DESCRIPTION
--        ""
--    ::= { upsHistoryBackupReportEntry 2 }

--upsHistoryBackupReportInputSys OBJECT-TYPE
--    SYNTAX INTEGER
--    ACCESS read-only
--    STATUS mandatory
--    DESCRIPTION
--        ""
--    ::= { upsHistoryBackupReportEntry 3 }

--upsHistoryBackupReportOutputSys OBJECT-TYPE
--    SYNTAX INTEGER
--    ACCESS read-only
--    STATUS mandatory
--    DESCRIPTION
--        ""
--    ::= { upsHistoryBackupReportEntry 4 }

--upsHistoryBackupReportVin OBJECT-TYPE
--    SYNTAX INTEGER
--    UNITS  "%"
--    ACCESS read-only
--    STATUS mandatory
--    DESCRIPTION
--        ""
--    ::= { upsHistoryBackupReportEntry 5 }

--upsHistoryBackupReportVout OBJECT-TYPE
--    SYNTAX INTEGER
--    UNITS  "%"
--    ACCESS read-only
--    STATUS mandatory
--    DESCRIPTION
--        ""
--    ::= { upsHistoryBackupReportEntry 6 }

--upsHistoryBackupReportIout OBJECT-TYPE
--    SYNTAX INTEGER
--    UNITS  "%"
--    ACCESS read-only
--    STATUS mandatory
--    DESCRIPTION
--        ""
--    ::= { upsHistoryBackupReportEntry 7 }

--upsHistoryBackupReportVdc OBJECT-TYPE
--    SYNTAX INTEGER
--    UNITS  "%"
--    ACCESS read-only
--    STATUS mandatory
--    DESCRIPTION
--        ""
--    ::= { upsHistoryBackupReportEntry 8 }

--upsHistoryBackupReportVbStart OBJECT-TYPE
--    SYNTAX INTEGER
--    UNITS  "%"
--    ACCESS read-only
--    STATUS mandatory
--    DESCRIPTION
--        ""
--    ::= { upsHistoryBackupReportEntry 9 }

--upsHistoryBackupReportVbEnd OBJECT-TYPE
--    SYNTAX INTEGER
--    UNITS  "%"
--    ACCESS read-only
--    STATUS mandatory
--    DESCRIPTION
--        ""
--    ::= { upsHistoryBackupReportEntry 10 }

--upsHistoryBackupReportTriggerSource OBJECT-TYPE
--    SYNTAX INTEGER
--    ACCESS read-only
--    STATUS mandatory
--    DESCRIPTION
--        ""
--    ::= { upsHistoryBackupReportEntry 11 }

--upsHistoryBackupReportDuration OBJECT-TYPE
--    SYNTAX INTEGER
--    UNITS  "1 Second"
--    ACCESS read-only
--    STATUS mandatory
--    DESCRIPTION
--        ""
--    ::= { upsHistoryBackupReportEntry 12 }

upsHistoryTotalNumFaults OBJECT-TYPE
    SYNTAX NonNegativeInteger
    ACCESS read-only
    STATUS mandatory
    DESCRIPTION
        "Total number of faults that has occurred on the UPS."
    ::= { upsHistory 11 }

--upsHistoryFaultReportTable OBJECT-TYPE
--    SYNTAX SEQUENCE OF UpsHistoryFaultReportEntry
--    ACCESS not-accessible
--    STATUS mandatory
--    DESCRIPTION
--        ""
--    ::= { upsHistory 14 }

--upsHistoryFaultReportEntry OBJECT-TYPE
--    SYNTAX UpsHistoryFaultReportEntry
--    ACCESS not-accessible
--    STATUS mandatory
--    DESCRIPTION
--        "An entry containing information applicable to a
--         particular input line."
--    INDEX { upsHistoryFaultReportIndex }
--    ::= { upsHistoryFaultReportTable  1 }

--UpsHistoryFaultReportEntry ::=
--    SEQUENCE {
--        upsHistoryFaultReportIndex         PositiveInteger,
--        upsHistoryFaultReportDateTime      DisplayString,
--        upsHistoryFaultReportInputSys      INTEGER,
--        upsHistoryFaultReportOutputSys     INTEGER,
--        upsHistoryFaultReportVin           INTEGER,
--        upsHistoryFaultReportVout          INTEGER,
--        upsHistoryFaultReportIout          INTEGER,
--        upsHistoryFaultReportVdc           INTEGER,
--        upsHistoryFaultReportVb            INTEGER,
--        upsHistoryFaultReportSlotlocation  INTEGER,
--        upsHistoryFaultReportFault1        INTEGER,
--        upsHistoryFaultReportFault2        INTEGER,
--        upsHistoryFaultReportFault3        INTEGER
--    }

-- ===========================================================================
-- upsHistoryFaultReportTable/upsHistoryFaultReportEntry/upsHistoryFaultReportIndex
-- ===========================================================================
--upsHistoryFaultReportIndex OBJECT-TYPE
--    SYNTAX PositiveInteger
--    ACCESS not-accessible
--    STATUS mandatory
--    DESCRIPTION
--        ""
--    ::= { upsHistoryFaultReportEntry 1 }

--upsHistoryFaultReportDateTime OBJECT-TYPE
--    SYNTAX DisplayString (SIZE(0..31))
--    ACCESS read-only
--    STATUS mandatory
--    DESCRIPTION
--        ""
--    ::= { upsHistoryFaultReportEntry 2 }

--upsHistoryFaultReportInputSys OBJECT-TYPE
--    SYNTAX INTEGER
--    ACCESS read-only
--    STATUS mandatory
--    DESCRIPTION
--        ""
--    ::= { upsHistoryFaultReportEntry 3 }

--upsHistoryFaultReportOutputSys OBJECT-TYPE
--    SYNTAX INTEGER
--    ACCESS read-only
--    STATUS mandatory
--    DESCRIPTION
--        ""
--    ::= { upsHistoryFaultReportEntry 4 }

--upsHistoryFaultReportVin OBJECT-TYPE
--    SYNTAX INTEGER
--    UNITS  "%"
--    ACCESS read-only
--    STATUS mandatory
--    DESCRIPTION
--        ""
--    ::= { upsHistoryFaultReportEntry 5 }

--upsHistoryFaultReportVout OBJECT-TYPE
--    SYNTAX INTEGER
--    UNITS  "%"
--    ACCESS read-only
--    STATUS mandatory
--    DESCRIPTION
--       ""
--    ::= { upsHistoryFaultReportEntry 6 }

--upsHistoryFaultReportIout OBJECT-TYPE
--    SYNTAX INTEGER
--    UNITS  "%"
--    ACCESS read-only
--    STATUS mandatory
--    DESCRIPTION
--        ""
--    ::= { upsHistoryFaultReportEntry 7 }

--upsHistoryFaultReportVdc OBJECT-TYPE
--    SYNTAX INTEGER
--    UNITS  "%"
--    ACCESS read-only
--    STATUS mandatory
--    DESCRIPTION
--        ""
--    ::= { upsHistoryFaultReportEntry 8 }

--upsHistoryFaultReportVb OBJECT-TYPE
--    SYNTAX INTEGER
--    UNITS  "%"
--    ACCESS read-only
--    STATUS mandatory
--    DESCRIPTION
--        ""
--    ::= { upsHistoryFaultReportEntry 9 }

--upsHistoryFaultReportSlotlocation OBJECT-TYPE
--    SYNTAX INTEGER
--    ACCESS read-only
--    STATUS mandatory
--    DESCRIPTION
--        ""
--    ::= { upsHistoryFaultReportEntry 10 }

--upsHistoryFaultReportFault1 OBJECT-TYPE
--    SYNTAX INTEGER
--    ACCESS read-only
--    STATUS mandatory
--    DESCRIPTION
--        ""
--    ::= { upsHistoryFaultReportEntry 11 }

--upsHistoryFaultReportFault2 OBJECT-TYPE
--    SYNTAX INTEGER
--    ACCESS read-only
--    STATUS mandatory
--    DESCRIPTION
--        ""
--    ::= { upsHistoryFaultReportEntry 12 }

--upsHistoryFaultReportFault3 OBJECT-TYPE
--    SYNTAX INTEGER
--    ACCESS read-only
--    STATUS mandatory
--    DESCRIPTION
--        ""
--    ::= { upsHistoryFaultReportEntry 13 }

upsHistoryTotalNumOperationModeChange OBJECT-TYPE
    SYNTAX NonNegativeInteger
    ACCESS read-only
    STATUS mandatory
    DESCRIPTION
        "The number of mode changes that has occurred."
    ::= { upsHistory 12 }

--upsHistoryOperationModeChangeReportTable OBJECT-TYPE
--    SYNTAX SEQUENCE OF UpsHistoryOperationModeChangeReportEntry
--    ACCESS not-accessible
--    STATUS mandatory
--    DESCRIPTION
--        ""
--    ::= { upsHistory 16 }

--upsHistoryOperationModeChangeReportEntry OBJECT-TYPE
--    SYNTAX UpsHistoryOperationModeChangeReportEntry
--    ACCESS not-accessible
--    STATUS mandatory
--    DESCRIPTION
--        "An entry containing information applicable to a
--         particular input line."
--    INDEX { upsHistoryOperationModeChangeReportIndex }
--    ::= { upsHistoryOperationModeChangeReportTable  1 }

--UpsHistoryOperationModeChangeReportEntry ::=
--    SEQUENCE {
--        upsHistoryOperationModeChangeReportIndex         PositiveInteger,
--        upsHistoryOperationModeChangeReportDateTime      DisplayString,
--        upsHistoryOperationModeChangeReportInputSys      INTEGER,
--        upsHistoryOperationModeChangeReportOutputSys     INTEGER,
--        upsHistoryOperationModeChangeReportVin           INTEGER,
--        upsHistoryOperationModeChangeReportVout          INTEGER,
--        upsHistoryOperationModeChangeReportIout          INTEGER,
--        upsHistoryOperationModeChangeReportVdc           INTEGER,
--        upsHistoryOperationModeChangeReportVb            INTEGER,
--        upsHistoryOperationModeChangeReportFromState     INTEGER,
--        upsHistoryOperationModeChangeReportToState       INTEGER,
--        upsHistoryOperationModeChangeReportBranch        INTEGER,
--        upsHistoryOperationModeChangeReportCause         INTEGER
--    }

-- =========================================================================================================================
-- upsHistoryOperationModeChangeReportTable/upsHistoryOperationModeChangeReportEntry/upsHistoryOperationModeChangeReportIndex
-- =========================================================================================================================
--upsHistoryOperationModeChangeReportIndex OBJECT-TYPE
--    SYNTAX PositiveInteger
--    ACCESS not-accessible
--    STATUS mandatory
--    DESCRIPTION
--        ""
--    ::= { upsHistoryOperationModeChangeReportEntry 1 }

--upsHistoryOperationModeChangeReportDateTime OBJECT-TYPE
--    SYNTAX DisplayString (SIZE(0..31))
--    ACCESS read-only
--    STATUS mandatory
--    DESCRIPTION
--        ""
--    ::= { upsHistoryOperationModeChangeReportEntry 2 }

--upsHistoryOperationModeChangeReportInputSys OBJECT-TYPE
--    SYNTAX INTEGER
--    ACCESS read-only
--    STATUS mandatory
--    DESCRIPTION
--        ""
--    ::= { upsHistoryOperationModeChangeReportEntry 3 }

--upsHistoryOperationModeChangeReportOutputSys OBJECT-TYPE
--    SYNTAX INTEGER
--    ACCESS read-only
--    STATUS mandatory
--    DESCRIPTION
--        ""
--    ::= { upsHistoryOperationModeChangeReportEntry 4 }

--upsHistoryOperationModeChangeReportVin OBJECT-TYPE
--   SYNTAX INTEGER
--    UNITS  "%"
--    ACCESS read-only
--    STATUS mandatory
--    DESCRIPTION
--        ""
--    ::= { upsHistoryOperationModeChangeReportEntry 5 }

--upsHistoryOperationModeChangeReportVout OBJECT-TYPE
--    SYNTAX INTEGER
--    UNITS  "%"
--    ACCESS read-only
--    STATUS mandatory
--    DESCRIPTION
--        ""
--    ::= { upsHistoryOperationModeChangeReportEntry 6 }

--upsHistoryOperationModeChangeReportIout OBJECT-TYPE
--    SYNTAX INTEGER
--    UNITS  "%"
--    ACCESS read-only
--    STATUS mandatory
--    DESCRIPTION
--        ""
--    ::= { upsHistoryOperationModeChangeReportEntry 7 }

--upsHistoryOperationModeChangeReportVdc OBJECT-TYPE
--    SYNTAX INTEGER
--    UNITS  "%"
--    ACCESS read-only
--    STATUS mandatory
--    DESCRIPTION
--        ""
--    ::= { upsHistoryOperationModeChangeReportEntry 8 }

--upsHistoryOperationModeChangeReportVb OBJECT-TYPE
--    SYNTAX INTEGER
--    UNITS  "%"
--    ACCESS read-only
--    STATUS mandatory
--    DESCRIPTION
--        ""
--    ::= { upsHistoryOperationModeChangeReportEntry 9 }

--upsHistoryOperationModeChangeReportFromState OBJECT-TYPE
--    SYNTAX INTEGER
--    ACCESS read-only
--    STATUS mandatory
--    DESCRIPTION
--        ""
--    ::= { upsHistoryOperationModeChangeReportEntry 10 }

--upsHistoryOperationModeChangeReportToState OBJECT-TYPE
--    SYNTAX INTEGER
--    ACCESS read-only
--    STATUS mandatory
--    DESCRIPTION
--        ""
--    ::= { upsHistoryOperationModeChangeReportEntry 11 }

--upsHistoryOperationModeChangeReportBranch OBJECT-TYPE
--    SYNTAX INTEGER
--    ACCESS read-only
--    STATUS mandatory
--    DESCRIPTION
--        ""
--    ::= { upsHistoryOperationModeChangeReportEntry 12 }

--upsHistoryOperationModeChangeReportCause OBJECT-TYPE
--    SYNTAX INTEGER
--    ACCESS read-only
--    STATUS mandatory
--    DESCRIPTION
--        ""
--    ::= { upsHistoryOperationModeChangeReportEntry 13 }

upsHistoryTotalNumWarnings OBJECT-TYPE
    SYNTAX NonNegativeInteger
    ACCESS read-only
    STATUS mandatory
    DESCRIPTION
        "The number of warnings that has occurred on the UPS."
    ::= { upsHistory 13 }

--upsHistoryWarningReportTable OBJECT-TYPE
--    SYNTAX SEQUENCE OF UpsHistoryWarningReportEntry
--    ACCESS not-accessible
--    STATUS mandatory
--    DESCRIPTION
--        ""
--    ::= { upsHistory 18 }

--upsHistoryWarningReportEntry OBJECT-TYPE
--    SYNTAX UpsHistoryWarningReportEntry
--    ACCESS not-accessible
--    STATUS mandatory
--    DESCRIPTION
--        "An entry containing information applicable to a
--         particular input line."
--    INDEX { upsHistoryWarningReportIndex }
--    ::= { upsHistoryWarningReportTable  1 }

--UpsHistoryWarningReportEntry ::=
--    SEQUENCE {
--        upsHistoryWarningReportIndex         PositiveInteger,
--        upsHistoryWarningReportDateTime      DisplayString,
--        upsHistoryWarningReportInputSys      INTEGER,
--        upsHistoryWarningReportOutputSys     INTEGER,
--        upsHistoryWarningReportVin           INTEGER,
--        upsHistoryWarningReportVout          INTEGER,
--        upsHistoryWarningReportIout          INTEGER,
--        upsHistoryWarningReportVdc           INTEGER,
--        upsHistoryWarningReportVb            INTEGER,
--        upsHistoryWarningReportSlotlocation  INTEGER,
--        upsHistoryWarningReportWarning1      INTEGER,
--        upsHistoryWarningReportWarning2      INTEGER,
--        upsHistoryWarningReportWarning3      INTEGER
--    }

-- =========================================================================================================================
-- upsHistoryWarningReportTable/upsHistoryWarningReportEntry/upsHistoryWarningReportIndex
-- =========================================================================================================================
--upsHistoryWarningReportIndex OBJECT-TYPE
--    SYNTAX PositiveInteger
--    ACCESS not-accessible
--    STATUS mandatory
--    DESCRIPTION
--        ""
--    ::= { upsHistoryWarningReportEntry 1 }

--upsHistoryWarningReportDateTime OBJECT-TYPE
--    SYNTAX DisplayString (SIZE(0..31))
--    ACCESS read-only
--    STATUS mandatory
--    DESCRIPTION
--        ""
--    ::= { upsHistoryWarningReportEntry 2 }

--upsHistoryWarningReportInputSys OBJECT-TYPE
--    SYNTAX INTEGER
--    ACCESS read-only
--    STATUS mandatory
--    DESCRIPTION
--        ""
--    ::= { upsHistoryWarningReportEntry 3 }

--upsHistoryWarningReportOutputSys OBJECT-TYPE
--    SYNTAX INTEGER
--    ACCESS read-only
--    STATUS mandatory
--    DESCRIPTION
--        ""
--    ::= { upsHistoryWarningReportEntry 4 }

--upsHistoryWarningReportVin OBJECT-TYPE
--    SYNTAX INTEGER
--    UNITS  "%"
--    ACCESS read-only
--    STATUS mandatory
--    DESCRIPTION
--        ""
--    ::= { upsHistoryWarningReportEntry 5 }

--upsHistoryWarningReportVout OBJECT-TYPE
--    SYNTAX INTEGER
--    UNITS  "%"
--    ACCESS read-only
--    STATUS mandatory
--    DESCRIPTION
--        ""
--    ::= { upsHistoryWarningReportEntry 6 }

--upsHistoryWarningReportIout OBJECT-TYPE
--    SYNTAX INTEGER
--    UNITS  "%"
--    ACCESS read-only
--    STATUS mandatory
--    DESCRIPTION
--        ""
--    ::= { upsHistoryWarningReportEntry 7 }

--upsHistoryWarningReportVdc OBJECT-TYPE
--    SYNTAX INTEGER
--    UNITS  "%"
--    ACCESS read-only
--    STATUS mandatory
--    DESCRIPTION
--        ""
--    ::= { upsHistoryWarningReportEntry 8 }

--upsHistoryWarningReportVb OBJECT-TYPE
--    SYNTAX INTEGER
--    UNITS  "%"
--    ACCESS read-only
--    STATUS mandatory
--    DESCRIPTION
--        ""
--    ::= { upsHistoryWarningReportEntry 9 }

--upsHistoryWarningReportSlotlocation OBJECT-TYPE
--    SYNTAX INTEGER
--    ACCESS read-only
--    STATUS mandatory
--    DESCRIPTION
--        ""
--    ::= { upsHistoryWarningReportEntry 10 }

--upsHistoryWarningReportWarning1 OBJECT-TYPE
--    SYNTAX INTEGER
--    ACCESS read-only
--    STATUS mandatory
--    DESCRIPTION
--        ""
--    ::= { upsHistoryWarningReportEntry 11 }

--upsHistoryWarningReportWarning2 OBJECT-TYPE
--    SYNTAX INTEGER
--    ACCESS read-only
--    STATUS mandatory
--    DESCRIPTION
--        ""
--    ::= { upsHistoryWarningReportEntry 12 }

--upsHistoryWarningReportWarning3 OBJECT-TYPE
--    SYNTAX INTEGER
--    ACCESS read-only
--    STATUS mandatory
--    DESCRIPTION
--        ""
--    ::= { upsHistoryWarningReportEntry 13 }

upsHistoryTotalNumSystemSettingsChanged OBJECT-TYPE
    SYNTAX NonNegativeInteger
    ACCESS read-only
    STATUS mandatory
    DESCRIPTION
        "The number of times the System settings have been changed."
    ::= { upsHistory 14 }

--upsHistorySystemSettingReportTable OBJECT-TYPE
--    SYNTAX SEQUENCE OF UpsHistorySystemSettingReportEntry
--    ACCESS not-accessible
--    STATUS mandatory
--    DESCRIPTION
--        ""
--    ::= { upsHistory 20 }

--upsHistorySystemSettingReportEntry OBJECT-TYPE
--    SYNTAX UpsHistorySystemSettingReportEntry
--    ACCESS not-accessible
--    STATUS mandatory
--    DESCRIPTION
--        "An entry containing information applicable to a
--         particular input line."
--    INDEX { upsHistorySystemSettingReportIndex }
--    ::= { upsHistorySystemSettingReportTable  1 }

--UpsHistorySystemSettingReportEntry ::=
--    SEQUENCE {
--        upsHistorySystemSettingReportIndex          PositiveInteger,
--        upsHistorySystemSettingReportDateTime       DisplayString,
--        upsHistorySystemSettingReportInputSys       INTEGER,
--        upsHistorySystemSettingReportOutputSys      INTEGER,
--        upsHistorySystemSettingReportVin            INTEGER,
--        upsHistorySystemSettingReportVout           INTEGER,
--        upsHistorySystemSettingReportIout           INTEGER,
--        upsHistorySystemSettingReportVdc            INTEGER,
--        upsHistorySystemSettingReportVb             INTEGER,
--        upsHistorySystemSettingReportBlock          INTEGER,
--        upsHistorySystemSettingReportItem           INTEGER,
--        upsHistorySystemSettingReportWritten        INTEGER,
--        upsHistorySystemSettingReportTriggerSource  INTEGER

--    }

-- ========================================================================================================
-- upsHistorySystemSettingReportTable/upsHistorySystemSettingReportEntry/upsHistorySystemSettingReportIndex
-- ========================================================================================================
--upsHistorySystemSettingReportIndex OBJECT-TYPE
--    SYNTAX PositiveInteger
--    ACCESS not-accessible
--    STATUS mandatory
--    DESCRIPTION
--        ""
--    ::= { upsHistorySystemSettingReportEntry 1 }

--upsHistorySystemSettingReportDateTime OBJECT-TYPE
--    SYNTAX DisplayString (SIZE(0..31))
--    ACCESS read-only
--    STATUS mandatory
--    DESCRIPTION
--        ""
--    ::= { upsHistorySystemSettingReportEntry 2 }

--upsHistorySystemSettingReportInputSys OBJECT-TYPE
--    SYNTAX INTEGER
--    ACCESS read-only
--    STATUS mandatory
--    DESCRIPTION
--        ""
--    ::= { upsHistorySystemSettingReportEntry 3 }

--upsHistorySystemSettingReportOutputSys OBJECT-TYPE
--    SYNTAX INTEGER
--    ACCESS read-only
--    STATUS mandatory
--    DESCRIPTION
--        ""
--    ::= { upsHistorySystemSettingReportEntry 4 }

--upsHistorySystemSettingReportVin OBJECT-TYPE
--    SYNTAX INTEGER
--    UNITS  "%"
--    ACCESS read-only
--    STATUS mandatory
--    DESCRIPTION
--        ""
--    ::= { upsHistorySystemSettingReportEntry 5 }

--upsHistorySystemSettingReportVout OBJECT-TYPE
--    SYNTAX INTEGER
--    UNITS  "%"
--    ACCESS read-only
--    STATUS mandatory
--    DESCRIPTION
--        ""
--    ::= { upsHistorySystemSettingReportEntry 6 }

--upsHistorySystemSettingReportIout OBJECT-TYPE
--    SYNTAX INTEGER
--    UNITS  "%"
--    ACCESS read-only
--    STATUS mandatory
--    DESCRIPTION
--        ""
--    ::= { upsHistorySystemSettingReportEntry 7 }

--upsHistorySystemSettingReportVdc OBJECT-TYPE
--    SYNTAX INTEGER
--    UNITS  "%"
--    ACCESS read-only
--    STATUS mandatory
--    DESCRIPTION
--        ""
--    ::= { upsHistorySystemSettingReportEntry 8 }

--upsHistorySystemSettingReportVb OBJECT-TYPE
--    SYNTAX INTEGER
--    UNITS  "%"
--    ACCESS read-only
--    STATUS mandatory
--    DESCRIPTION
--        ""
--    ::= { upsHistorySystemSettingReportEntry 9 }

--upsHistorySystemSettingReportBlock OBJECT-TYPE
--    SYNTAX INTEGER
--    UNITS  "%"
--    ACCESS read-only
--    STATUS mandatory
--    DESCRIPTION
--        ""
--    ::= { upsHistorySystemSettingReportEntry 10 }

--upsHistorySystemSettingReportItem OBJECT-TYPE
--    SYNTAX INTEGER
--    ACCESS read-only
--    STATUS mandatory
--    DESCRIPTION
--        ""
--    ::= { upsHistorySystemSettingReportEntry 11 }

--upsHistorySystemSettingReportWritten OBJECT-TYPE
--    SYNTAX INTEGER
--    ACCESS read-only
--    STATUS mandatory
--    DESCRIPTION
--        ""
--    ::= { upsHistorySystemSettingReportEntry 12 }

--upsHistorySystemSettingReportTriggerSource OBJECT-TYPE
--    SYNTAX INTEGER
--    ACCESS read-only
--    STATUS mandatory
--    DESCRIPTION
--        ""
--    ::= { upsHistorySystemSettingReportEntry 13 }

upsHistoryTotalNumResets OBJECT-TYPE
    SYNTAX NonNegativeInteger
    ACCESS read-only
    STATUS mandatory
    DESCRIPTION
        "The number of times the UPS has reset."
    ::= { upsHistory 15 }

-- ===========================================================================
-- upsDisplay RMTI3 Group 9
-- The UPS Display Data Group
-- ===========================================================================
upsDisplayFirmwareVersion OBJECT-TYPE
    SYNTAX DisplayString (SIZE(0..15))
    ACCESS read-only
    STATUS mandatory
    DESCRIPTION
        "The firmware version of the display."
    ::= { upsDisplay 1 }

upsDisplayBootSectorVersion OBJECT-TYPE
    SYNTAX DisplayString (SIZE(0..15))
    ACCESS read-only
    STATUS mandatory
    DESCRIPTION
        "The boot sector version of the display."
    ::= { upsDisplay 2 }

upsDisplayBootLoaderVersion OBJECT-TYPE
    SYNTAX DisplayString (SIZE(0..15))
    ACCESS read-only
    STATUS mandatory
    DESCRIPTION
        "The boot loader version of the display."
    ::= { upsDisplay 3 }

upsDisplaySleepTimer OBJECT-TYPE
    SYNTAX NonNegativeInteger
    UNITS  "Minutes"
    ACCESS read-write
    STATUS mandatory
    DESCRIPTION
        "The sleep timer for the display."
    ::= { upsDisplay 4 }

upsDisplayBuzzerMode OBJECT-TYPE
    SYNTAX INTEGER {
        disable(1),
        enable(2)
    }
    ACCESS read-write
    STATUS mandatory
    DESCRIPTION
        "Configures buzzer mode."
    ::= { upsDisplay 5 }

upsDisplayBuzzerStatus OBJECT-TYPE
    SYNTAX INTEGER {
        off(1),
        idle(2),
        sound(3),
        silenced(4)
    }
    ACCESS read-only
    STATUS mandatory
    DESCRIPTION
        "Shows the current state of the buzzer."
    ::= { upsDisplay 6 }

upsDisplayRMTIInstallDate OBJECT-TYPE
    SYNTAX DisplayString(SIZE(8))
    ACCESS read-only
    STATUS mandatory
    DESCRIPTION
        "The RMTI installation date."
    ::= { upsDisplay 7 }

upsDisplayRMTIInstallStatus OBJECT-TYPE
    SYNTAX INTEGER {
        uninstalled(1),
        installed(2)
    }
    ACCESS read-only
    STATUS mandatory
    DESCRIPTION
        "Shows the installation status of the RMTI."
    ::= { upsDisplay 8 }

upsDisplayRMTIBaudRate OBJECT-TYPE
    SYNTAX INTEGER {
        bd9600(1),
        bd19200(2),
        bd38400(3),
        bd57600(4)
    }
    ACCESS read-only
    STATUS mandatory
    DESCRIPTION
        "Configures the baud rate."
    ::= { upsDisplay 9 }

upsDisplayRMTIDataLink OBJECT-TYPE
    SYNTAX INTEGER {
        unknown(1),
        link-down(2),
        link-up(3)
    }
    ACCESS read-only
    STATUS mandatory
    DESCRIPTION
        "Shows the data status of the RMTI."
    ::= { upsDisplay 10 }

upsDisplayRMTINetworkLink OBJECT-TYPE
    SYNTAX INTEGER {
        unknown(1),
        link-down(2),
        link-up(3)
    }
    ACCESS read-only
    STATUS mandatory
    DESCRIPTION
        "Shows the network status of the RMTI."
    ::= { upsDisplay 11 }

-- ===========================================================================
-- upsAlarm RMTI3 Group 10
-- The UPS Alarm List
-- ===========================================================================
upsAlarmsPresent OBJECT-TYPE
    SYNTAX Gauge32
    ACCESS read-only
    STATUS mandatory
    DESCRIPTION
        "The present number of active alarm conditions."
    ::= { upsAlarm 1 }

upsAlarmTable OBJECT-TYPE
    SYNTAX SEQUENCE OF UpsAlarmEntry
    ACCESS not-accessible
    STATUS mandatory
    DESCRIPTION
        "A list of alarm table entries. The table contains
         zero, one, or many rows at any moment, depending upon
         the number of alarm conditions in effect. The table
         is initially empty at agent startup. The agent
         creates a row in the table each time a condition is
         detected and deletes that row when that condition no
         longer pertains. The agent creates the first row with
         upsAlarmId equal to 1, and increments the value of
         upsAlarmId each time a new row is created, wrapping to
         the first free value greater than or equal to 1 when
         the maximum value of upsAlarmId would otherwise be
         exceeded. Consequently, after multiple operations,
         the table may become sparse, e.g., containing entries
         for rows 95, 100, 101, and 203 and the entries should
         not be assumed to be in chronological order because
         upsAlarmId might have wrapped.

         Alarms are named by an OBJECT IDENTIFIER,
         upsAlarmDescr, to allow a single table to
         reflect well known alarms plus alarms defined by a
         particular implementation, i.e., as documented in the
         private enterprise MIB definition for the device. No
         two rows will have the same value of upsAlarmDescr,
         since alarms define conditions. In order to meet this
         requirement, care should be taken in the definition of
         alarm conditions to insure that a system cannot enter
         the same condition multiple times simultaneously.

         The number of rows in the table at any given time is
         reflected by the value of upsAlarmsPresent."
    ::= { upsAlarm  2 }

upsAlarmEntry OBJECT-TYPE
    SYNTAX UpsAlarmEntry
    ACCESS not-accessible
    STATUS mandatory
    DESCRIPTION
        "An entry containing information applicable to a
         particular alarm."
    INDEX { upsAlarmId }
    ::= { upsAlarmTable  1 }

UpsAlarmEntry ::=
    SEQUENCE {
        upsAlarmId              PositiveInteger,
        upsAlarmDescr           AutonomousType,
        upsAlarmTime            TimeStamp
    }

-- ===========================================================================
-- upsAlarmTable/upsAlarmEntry/upsAlarmId
-- ===========================================================================
upsAlarmId OBJECT-TYPE
    SYNTAX PositiveInteger
    ACCESS not-accessible
    STATUS mandatory
    DESCRIPTION
        "An unique identifier for an alarm condition. This
         value must remain constant."
    ::= { upsAlarmEntry 1 }

upsAlarmDescr OBJECT-TYPE
    SYNTAX AutonomousType
    ACCESS read-only
    STATUS mandatory
    DESCRIPTION
        "A reference to an alarm description object. The
         object referenced should not be accessible, but rather
         be used to provide a unique description of the alarm
         condition."
    ::= { upsAlarmEntry 2 }

-- ===========================================================================
-- .../upsAlarmTime
-- ===========================================================================
upsAlarmTime OBJECT-TYPE
    SYNTAX TimeStamp
    ACCESS read-only
    STATUS mandatory
    DESCRIPTION
        "The value of upsConfigSystemTime when the alarm condition was
          detected. If the alarm condition was detected at the
          time of agent startup and presumably existed before
          agent startup, the value of upsAlarmTime shall equal 0."
    ::= { upsAlarmEntry 3 }

upsWellKnownAlarms OBJECT IDENTIFIER ::= { upsAlarm  3 }

upsAlarmFault OBJECT-TYPE
    SYNTAX INTEGER
    ACCESS read-only
    STATUS mandatory
    DESCRIPTION
        "Fault: One or more fault reported."
    ::= { upsWellKnownAlarms 1 }

upsAlarmOpenFuse OBJECT-TYPE
    SYNTAX INTEGER
    ACCESS read-only
    STATUS mandatory
    DESCRIPTION
        "Fault: An open fuse reported."
    ::= { upsWellKnownAlarms 2 }

upsAlarmCurrentLimitFault OBJECT-TYPE
    SYNTAX INTEGER
    ACCESS read-only
    STATUS mandatory
    DESCRIPTION
        "Fault: A current limit reported."
    ::= { upsWellKnownAlarms 3 }

upsAlarmDCBusOverCurrent OBJECT-TYPE
    SYNTAX INTEGER
    ACCESS read-only
    STATUS mandatory
    DESCRIPTION
        "Fault: A DC bus overcurrent reported."
    ::= { upsWellKnownAlarms 4 }

upsAlarmDCOverVoltage OBJECT-TYPE
    SYNTAX INTEGER
    ACCESS read-only
    STATUS mandatory
    DESCRIPTION
        "Fault: A DC bus overvoltage repoprted."
    ::= { upsWellKnownAlarms 5 }

upsAlarmDCBusImbalance OBJECT-TYPE
    SYNTAX INTEGER
    ACCESS read-only
    STATUS mandatory
    DESCRIPTION
        "Fault: A DC bus imbalance reported."
    ::= { upsWellKnownAlarms 6 }

upsAlarmOutputUnderVoltage OBJECT-TYPE
    SYNTAX INTEGER
    ACCESS read-only
    STATUS mandatory
    DESCRIPTION
        "Fault: An inverter output undervoltage reported."
    ::= { upsWellKnownAlarms 7 }

upsAlarmOutputOverVoltage OBJECT-TYPE
    SYNTAX INTEGER
    ACCESS read-only
    STATUS mandatory
    DESCRIPTION
        "Fault: An inverter output overvoltage reported."
    ::= { upsWellKnownAlarms 8 }

upsAlarmHeatSinkOverheat OBJECT-TYPE
    SYNTAX INTEGER
    ACCESS read-only
    STATUS mandatory
    DESCRIPTION
        "Fault: Heat sink or device overheat reported."
    ::= { upsWellKnownAlarms 9 }

upsAlarmBypassOverload OBJECT-TYPE
    SYNTAX INTEGER
    ACCESS read-only
    STATUS mandatory
    DESCRIPTION
        "Fault: A bypass overload reported."
    ::= { upsWellKnownAlarms 10 }

upsAlarmChargerOverVoltageFault OBJECT-TYPE
    SYNTAX INTEGER
    ACCESS read-only
    STATUS mandatory
    DESCRIPTION
        "Fault: Charger overvoltage reported."
    ::= { upsWellKnownAlarms 11 }

upsAlarmOutputOverCurrent OBJECT-TYPE
    SYNTAX INTEGER
    ACCESS read-only
    STATUS mandatory
    DESCRIPTION
        "Fault: A output overcurrent reported."
    ::= { upsWellKnownAlarms 12 }

upsAlarmDCUnderVoltAtBoostUp OBJECT-TYPE
    SYNTAX INTEGER
    ACCESS read-only
    STATUS mandatory
    DESCRIPTION
        "Fault: A DC bus undervoltage reported during DC bus boost-up."
    ::= { upsWellKnownAlarms 13 }

upsAlarmDCUnderVoltAtCharge OBJECT-TYPE
    SYNTAX INTEGER
    ACCESS read-only
    STATUS mandatory
    DESCRIPTION
        "Fault: A DC bus undervoltage during DC bus charging reported."
    ::= { upsWellKnownAlarms 14 }

upsAlarmBypassOverheat OBJECT-TYPE
    SYNTAX INTEGER
    ACCESS read-only
    STATUS mandatory
    DESCRIPTION
        "Fault: A bypass Overheat reported."
    ::= { upsWellKnownAlarms 15 }

upsAlarmResettableInverterOverload OBJECT-TYPE
    SYNTAX INTEGER
    ACCESS read-only
    STATUS mandatory
    DESCRIPTION
        "Fault: An inverter overload reported. It is resetable."
    ::= { upsWellKnownAlarms 16 }

upsAlarmUnresettableInverterOverload OBJECT-TYPE
    SYNTAX INTEGER
    ACCESS read-only
    STATUS mandatory
    DESCRIPTION
        "Fault: An inverter overload reported. It is not resetable."
    ::= { upsWellKnownAlarms 17 }

upsAlarmInputOverVoltage OBJECT-TYPE
    SYNTAX INTEGER
    ACCESS read-only
    STATUS mandatory
    DESCRIPTION
        "Warning: An input overvoltage reported."
    ::= { upsWellKnownAlarms 18 }

upsAlarmInputUnderVoltage OBJECT-TYPE
    SYNTAX INTEGER
    ACCESS read-only
    STATUS mandatory
    DESCRIPTION
        "Warning: An input undervoltage reported."
    ::= { upsWellKnownAlarms 19 }

upsAlarmInputFrequencyError OBJECT-TYPE
    SYNTAX INTEGER
    ACCESS read-only
    STATUS mandatory
    DESCRIPTION
        "Warning: An input frequency error reported."
    ::= { upsWellKnownAlarms 20 }

upsAlarmBypassOverVoltage OBJECT-TYPE
    SYNTAX INTEGER
    ACCESS read-only
    STATUS mandatory
    DESCRIPTION
        "Warning: A bypass overvoltage reported."
    ::= { upsWellKnownAlarms 21 }

upsAlarmBypassUnderVoltage OBJECT-TYPE
    SYNTAX INTEGER
    ACCESS read-only
    STATUS mandatory
    DESCRIPTION
        "Warning: A bypass undervoltage reported."
    ::= { upsWellKnownAlarms 22 }

upsAlarmBypassFrequencyError OBJECT-TYPE
    SYNTAX INTEGER
    ACCESS read-only
    STATUS mandatory
    DESCRIPTION
        "Warning: An bypass frequency error reported."
    ::= { upsWellKnownAlarms 23 }

upsAlarmDCBusUnderVoltAtBattTest OBJECT-TYPE
    SYNTAX INTEGER
    ACCESS read-only
    STATUS mandatory
    DESCRIPTION
        "Warning: A DC bus undervoltage reported during battery test"
    ::= { upsWellKnownAlarms 24 }

upsAlarmBatteryLow OBJECT-TYPE
    SYNTAX INTEGER
    ACCESS read-only
    STATUS mandatory
    DESCRIPTION
        "Warning: A Low battery reported."
    ::= { upsWellKnownAlarms 25 }

upsAlarmBatteryAtShutdownlevel OBJECT-TYPE
    SYNTAX INTEGER
    ACCESS read-only
    STATUS mandatory
    DESCRIPTION
        "Warning: A Battery shutdown voltage level reported."
    ::= { upsWellKnownAlarms 26 }

upsAlarmReplaceBattery OBJECT-TYPE
    SYNTAX INTEGER
    ACCESS read-only
    STATUS mandatory
    DESCRIPTION
        "Warning: Batteries are in need of replacement."
    ::= { upsWellKnownAlarms 27 }

upsAlarmChargerOverVoltageWarning OBJECT-TYPE
    SYNTAX INTEGER
    ACCESS read-only
    STATUS mandatory
    DESCRIPTION
        "Warning: Charger overvoltage reported."
    ::= { upsWellKnownAlarms 28 }

upsAlarmBatteryTestFailed OBJECT-TYPE
    SYNTAX INTEGER
    ACCESS read-only
    STATUS mandatory
    DESCRIPTION
        "Warning: A battery test failed event reported."
    ::= { upsWellKnownAlarms 29 }

upsAlarmBatteryDepleted OBJECT-TYPE
    SYNTAX INTEGER
    ACCESS read-only
    STATUS mandatory
    DESCRIPTION
        "Warning: A battery depleted event reported. It will not be able to support critical loads."
    ::= { upsWellKnownAlarms 30 }

upsAlarmBatteryOverheat OBJECT-TYPE
    SYNTAX INTEGER
    ACCESS read-only
    STATUS mandatory
    DESCRIPTION
        "Warning: A Battery overheat reported."
    ::= { upsWellKnownAlarms 31 }

upsAlarmSystemOverheat OBJECT-TYPE
    SYNTAX INTEGER
    ACCESS read-only
    STATUS mandatory
    DESCRIPTION
        "Warning: A system overheat reported."
    ::= { upsWellKnownAlarms 32 }

upsAlarmOutputOverloadWarning OBJECT-TYPE
    SYNTAX INTEGER
    ACCESS read-only
    STATUS mandatory
    DESCRIPTION
        "Warning: An inverter output overload reported. UPS will switch to bypass operation or shut down if no action is taken. Shut down excess equipment to reduce Load."
    ::= { upsWellKnownAlarms 33 }

upsAlarmCurrentLimitWarning OBJECT-TYPE
    SYNTAX INTEGER
    ACCESS read-only
    STATUS mandatory
    DESCRIPTION
        "Warning: A current limit reported."
    ::= { upsWellKnownAlarms 34 }

upsAlarmAsyncOperation OBJECT-TYPE
    SYNTAX INTEGER
    ACCESS read-only
    STATUS mandatory
    DESCRIPTION
        "Warning: An Asynchronous operation reported."
    ::= { upsWellKnownAlarms 35 }

upsAlarmServiceUPS OBJECT-TYPE
    SYNTAX INTEGER
    ACCESS read-only
    STATUS mandatory
    DESCRIPTION
        "Warning: UPS is in need of service. Please contact authorized Toshiba service center for assistance."
    ::= { upsWellKnownAlarms 36 }

upsAlarmBatteryNearExpiration OBJECT-TYPE
    SYNTAX INTEGER
    ACCESS read-only
    STATUS mandatory
    DESCRIPTION
        "Warning: Batteries are nearing the end of their expected lifetime."
    ::= { upsWellKnownAlarms 37 }

upsAlarmBatteryExpired OBJECT-TYPE
    SYNTAX INTEGER
    ACCESS read-only
    STATUS mandatory
    DESCRIPTION
        "Warning: Batteries have reached their expected lifetime."
    ::= { upsWellKnownAlarms 38 }

upsAlarmDisplayCableError OBJECT-TYPE
    SYNTAX INTEGER
    ACCESS read-only
    STATUS mandatory
    DESCRIPTION
        "Warning: A display cable error reported."
    ::= { upsWellKnownAlarms 39 }

upsAlarmRemotEyeCommError OBJECT-TYPE
    SYNTAX INTEGER
    ACCESS read-only
    STATUS mandatory
    DESCRIPTION
        "Warning: A Communication error between the main control and the RemotEye reported."
    ::= { upsWellKnownAlarms 40 }

upsAlarmRemotEyeUplinkCommError OBJECT-TYPE
    SYNTAX INTEGER
    ACCESS read-only
    STATUS mandatory
    DESCRIPTION
        "Warning: A communication error between the RemotEye III and the network reported."
    ::= { upsWellKnownAlarms 41 }

upsAlarmServicePortCommError OBJECT-TYPE
    SYNTAX INTEGER
    ACCESS read-only
    STATUS mandatory
    DESCRIPTION
        "Warning: A communication error between the main controller and the service communication
         port reported."
    ::= { upsWellKnownAlarms 42 }

upsAlarmDispCommError OBJECT-TYPE
    SYNTAX INTEGER
    ACCESS read-only
    STATUS mandatory
    DESCRIPTION
        "Warning: A communication error between the main controller and display controller reported."
    ::= { upsWellKnownAlarms 43 }

upsAlarmSystemTestFailed OBJECT-TYPE
    SYNTAX INTEGER
    ACCESS read-only
    STATUS mandatory
    DESCRIPTION
        "Warning: A system test failed event reported."
    ::= { upsWellKnownAlarms 44 }

upsAlarmBypassOn OBJECT-TYPE
    SYNTAX INTEGER
    ACCESS read-only
    STATUS mandatory
    DESCRIPTION
        "Warning: The UPS is in Stop (Bypass) mode"
    ::= { upsWellKnownAlarms 45 }

upsAlarmPowerFailure OBJECT-TYPE
    SYNTAX INTEGER
    ACCESS read-only
    STATUS mandatory
    DESCRIPTION
        "Info: A power failure reported."
    ::= { upsWellKnownAlarms 46 }

upsAlarmShutdownPending OBJECT-TYPE
    SYNTAX INTEGER
    ACCESS read-only
    STATUS mandatory
    DESCRIPTION
        "Info: An output shutdown in progress reported. Output will turn off after delay."
    ::= { upsWellKnownAlarms 47 }

upsAlarmOutputOffAsRequested OBJECT-TYPE
    SYNTAX INTEGER
    ACCESS read-only
    STATUS mandatory
    DESCRIPTION
        "Info: An output shutdown mode requested."
    ::= { upsWellKnownAlarms 48 }

upsAlarmOutputOff OBJECT-TYPE
    SYNTAX INTEGER
    ACCESS read-only
    STATUS mandatory
    DESCRIPTION
        "Info: An output off reported."
    ::= { upsWellKnownAlarms 49 }

upsAlarmBatteryTestInProgress OBJECT-TYPE
    SYNTAX INTEGER
    ACCESS read-only
    STATUS mandatory
    DESCRIPTION
        "Info: A battery test in progress reported."
    ::= { upsWellKnownAlarms 50 }

upsAlarmBatteryOn OBJECT-TYPE
    SYNTAX INTEGER
    ACCESS read-only
    STATUS mandatory
    DESCRIPTION
        "Info: The UPS is on Battery mode; it is supplying output power from its batteries."
    ::= { upsWellKnownAlarms 51 }

upsAlarmEMDSensor1AlarmTriggered OBJECT-TYPE
    SYNTAX INTEGER
    ACCESS read-only
    STATUS mandatory
    DESCRIPTION
        "Info: EMD sensor 1 alarm is triggered."
    ::= { upsWellKnownAlarms 52 }

upsAlarmEMDSensor2AlarmTriggered OBJECT-TYPE
    SYNTAX INTEGER
    ACCESS read-only
    STATUS mandatory
    DESCRIPTION
        "Info: EMD sensor 2 alarm is triggered."
    ::= { upsWellKnownAlarms 53 }

upsAlarmEMDHumidityAtLowCriticalPoint OBJECT-TYPE
    SYNTAX INTEGER
    ACCESS read-only
    STATUS mandatory
    DESCRIPTION
        "Info: EMD humidity is at low critical point."
    ::= { upsWellKnownAlarms 54 }

upsAlarmEMDHumidityAtHighCriticalPoint OBJECT-TYPE
    SYNTAX INTEGER
    ACCESS read-only
    STATUS mandatory
    DESCRIPTION
        "Info: EMD humidity is at high critical point."
    ::= { upsWellKnownAlarms 55 }

upsAlarmEMDHumidityAtLowWarningPoint OBJECT-TYPE
    SYNTAX INTEGER
    ACCESS read-only
    STATUS mandatory
    DESCRIPTION
        "Info: EMD humidity is at low warning point."
    ::= { upsWellKnownAlarms 56 }

upsAlarmEMDHumidityAtHighWarningPoint OBJECT-TYPE
    SYNTAX INTEGER
    ACCESS read-only
    STATUS mandatory
    DESCRIPTION
        "Info: EMD humidity is at high warning point."
    ::= { upsWellKnownAlarms 57 }

upsAlarmEMDTemperatureAtLowCriticalPoint OBJECT-TYPE
    SYNTAX INTEGER
    ACCESS read-only
    STATUS mandatory
    DESCRIPTION
        "Info: EMD Temperature is at low critical point."
    ::= { upsWellKnownAlarms 58 }

upsAlarmEMDTemperatureAtHighCriticalPoint OBJECT-TYPE
    SYNTAX INTEGER
    ACCESS read-only
    STATUS mandatory
    DESCRIPTION
        "Info: EMD Temperature is at high critical point."
    ::= { upsWellKnownAlarms 59 }

upsAlarmEMDTemperatureAtLowWarningPoint OBJECT-TYPE
    SYNTAX INTEGER
    ACCESS read-only
    STATUS mandatory
    DESCRIPTION
        "Info: EMD Temperature is at low warning point."
    ::= { upsWellKnownAlarms 60 }

upsAlarmEMDTemperatureAtHighWarningPoint OBJECT-TYPE
    SYNTAX INTEGER
    ACCESS read-only
    STATUS mandatory
    DESCRIPTION
        "Info: EMD Temperature is at high warning point."
    ::= { upsWellKnownAlarms 61 }

upsAlarmLogInError OBJECT-TYPE
    SYNTAX INTEGER
    ACCESS read-only
    STATUS mandatory
    DESCRIPTION
        "Info: Username/Password information is incorrect."
    ::= { upsWellKnownAlarms 62 }

-- ===========================================================================
-- upsPassword  RMTI3 Group 11
-- The UPS Password group
-- ===========================================================================
upsPwdAdminCurrentAccessLevel OBJECT-TYPE
    SYNTAX DisplayString (SIZE (0..15))
    ACCESS read-only
    STATUS mandatory
    DESCRIPTION
        "The administrator access level."
    ::= { upsPassword 1 }

upsPwdAdminCurrentLogin OBJECT-TYPE
    SYNTAX DisplayString (SIZE (0..31))
    ACCESS read-write
    STATUS mandatory
    DESCRIPTION
        "The administrator access login name."
    ::= { upsPassword 2 }

upsPwdAdminNewLoginAccess OBJECT-TYPE
    SYNTAX DisplayString (SIZE (0..31))
    ACCESS read-write
    STATUS mandatory
    DESCRIPTION
        "The administrator access login name."
    ::= { upsPassword 3 }

upsPwdAdminCurrentPswd OBJECT-TYPE
    SYNTAX DisplayString (SIZE (0..15))
    ACCESS read-write
    STATUS mandatory
    DESCRIPTION
        "The current password."
    ::= { upsPassword 4 }

upsPwdAdminNewPswd OBJECT-TYPE
    SYNTAX DisplayString (SIZE (0..7))
    ACCESS read-write
    STATUS mandatory
    DESCRIPTION
        "The current password."
    ::= { upsPassword 5 }


-- ===========================================================================
-- upsAgent RMTI3 Group 12
-- The Agent (RemotEye III) Data
-- ===========================================================================
upsAgentSoftwareVersion OBJECT-TYPE
    SYNTAX DisplayString (SIZE(0..15))
    ACCESS read-only
    STATUS mandatory
    DESCRIPTION
        "The RemotEye III version number"
    ::= { upsAgent 1 }

upsAgentHardwareAddress OBJECT-TYPE
    SYNTAX DisplayString (SIZE(20))
    ACCESS read-only
    STATUS mandatory
    DESCRIPTION
        "The hardware/MAC address that NMS can identify the managed device"
    ::= { upsAgent 2 }

upsAgentIPAddress OBJECT-TYPE
    SYNTAX IpAddress
    ACCESS read-write
    STATUS mandatory
    DESCRIPTION
        "The ip address that NMS can identify the managed device"
    ::= { upsAgent 3 }

upsAgentGatewayAddress OBJECT-TYPE
    SYNTAX IpAddress
    ACCESS read-write
    STATUS mandatory
    DESCRIPTION
        "The default gateway that allow device managed through routers"
    ::= { upsAgent 4 }

upsAgentSubnetMask OBJECT-TYPE
    SYNTAX IpAddress
    ACCESS read-write
    STATUS mandatory
    DESCRIPTION
        "Internet address subnet mask"
    ::= { upsAgent 5 }

upsAgentDate OBJECT-TYPE
    SYNTAX DisplayString (SIZE(10))
    ACCESS read-write
    STATUS mandatory
    DESCRIPTION
         "The date in agent, format is MM/DD/YYYY."
    ::= { upsAgent 6 }

upsAgentTime OBJECT-TYPE
    SYNTAX DisplayString (SIZE(8))
    ACCESS read-write
    STATUS mandatory
    DESCRIPTION
        "The time in agent, format is HH:MM:SS."
    ::= { upsAgent 7 }

upsAgentGeneralRecordLogFrequency OBJECT-TYPE
    SYNTAX INTEGER (5..28800) -- in seconds
    ACCESS read-write
    STATUS mandatory
    DESCRIPTION
        "The interval frequency of the general record log. The value is in seconds."
    ::= { upsAgent 8 }

upsAgentPollingRate OBJECT-TYPE
    SYNTAX INTEGER (1..999)
    UNITS  "Second"
    ACCESS read-write
    STATUS mandatory
    DESCRIPTION
        "The frequency that proxy agent polls the connected
         UPS in RemotEye III protocols."
    ::= { upsAgent 9 }

upsAgentDHCPControl OBJECT-TYPE
    SYNTAX INTEGER {
        enable(1),
        disable(2)
    }
    ACCESS read-write
    STATUS mandatory
    DESCRIPTION
        "Enable or disable DHCP/BootP capability"
    ::= { upsAgent 10 }

upsAgentTelnetControl OBJECT-TYPE
    SYNTAX INTEGER {
        enable(1),
        disable(2)
    }
    ACCESS read-write
    STATUS mandatory
    DESCRIPTION
        "Enable or disable telnet access"
    ::= { upsAgent 11 }

upsAgentTFTPControl OBJECT-TYPE
    SYNTAX INTEGER {
        enable(1),
        disable(2)
    }
    ACCESS read-write
    STATUS mandatory
    DESCRIPTION
        "Enable or disable network upgrade capability"
    ::= { upsAgent 12 }

upsAgentResetToDefault OBJECT-TYPE
    SYNTAX INTEGER {
        enable(1),
        disable(2)
    }
    ACCESS read-write
    STATUS mandatory
    DESCRIPTION
        "Reset all parameters of REMOTEYE III to default value"
    ::= { upsAgent 13 }

upsAgentRestart OBJECT-TYPE
    SYNTAX INTEGER {
        enable(1),
        disable(2)
    }
    ACCESS read-write
    STATUS mandatory
    DESCRIPTION
        "Restart REMOTEYE III"
    ::= { upsAgent 14 }

upsAgentSystemName OBJECT-TYPE
    SYNTAX DisplayString (SIZE(0..31))
    ACCESS read-write
    STATUS mandatory
    DESCRIPTION
        "The Agent System name"
    ::= { upsAgent 15 }

upsAgentSystemContact OBJECT-TYPE
    SYNTAX DisplayString (SIZE(0..31))
    ACCESS read-write
    STATUS mandatory
    DESCRIPTION
        "Contact Information"
    ::= { upsAgent 16 }

upsAgentSystemLocation OBJECT-TYPE
    SYNTAX DisplayString (SIZE(0..31))
    ACCESS read-write
    STATUS mandatory
    DESCRIPTION
        "Agent Location"
    ::= { upsAgent 17 }

upsAgentDefaultLanguage OBJECT-TYPE
    SYNTAX INTEGER {
        auto(1),
        english(2)
    }
    ACCESS read-write
    STATUS mandatory
    DESCRIPTION
        "Current Default Language"
    ::= { upsAgent 18 }

upsAgentClearGeneralHistory OBJECT-TYPE
    SYNTAX INTEGER {
        enable(1),
        disable(2)
    }
    ACCESS read-write
    STATUS mandatory
    DESCRIPTION
        "Clear general history log data"
    ::= { upsAgent 19 }

upsAgentClearTestHistory OBJECT-TYPE
    SYNTAX INTEGER {
        enable(1),
        disable(2)
    }
    ACCESS read-write
    STATUS mandatory
    DESCRIPTION
        "Clear test history log data"
    ::= { upsAgent 20 }

upsAgentClearBackupHistory OBJECT-TYPE
    SYNTAX INTEGER {
        enable(1),
        disable(2)
    }
    ACCESS read-write
    STATUS mandatory
    DESCRIPTION
        "Clear Backup history log data"
    ::= { upsAgent 21 }

upsAgentClearFaultHistory OBJECT-TYPE
    SYNTAX INTEGER {
        enable(1),
        disable(2)
    }
    ACCESS read-write
    STATUS mandatory
    DESCRIPTION
        "Clear Fault history log data"
    ::= { upsAgent 22 }

upsAgentClearOperationModeHistory OBJECT-TYPE
    SYNTAX INTEGER {
        enable(1),
        disable(2)
    }
    ACCESS read-write
    STATUS mandatory
    DESCRIPTION
        "Clear operation mode history log data"
    ::= { upsAgent 23 }

upsAgentClearWarningHistory OBJECT-TYPE
    SYNTAX INTEGER {
        enable(1),
        disable(2)
    }
    ACCESS read-write
    STATUS mandatory
    DESCRIPTION
        "Clear warning history log data"
    ::= { upsAgent 24 }

upsAgentClearSystemsettingsChangeHistory OBJECT-TYPE
    SYNTAX INTEGER {
        enable(1),
        disable(2)
    }
    ACCESS read-write
    STATUS mandatory
    DESCRIPTION
        "Clear System settings change history log data"
    ::= { upsAgent 25 }

upsAgentClearRMTIEventHistory OBJECT-TYPE
    SYNTAX INTEGER {
        enable(1),
        disable(2)
    }
    ACCESS read-write
    STATUS mandatory
    DESCRIPTION
        "Clear RemotEye Event History log data"
    ::= { upsAgent 26 }

-- ===========================================================================
--
-- upsClients Group 13
--
-- ===========================================================================
upsConnectedClientsNum OBJECT-TYPE
    SYNTAX NonNegativeInteger
    ACCESS read-only
    STATUS mandatory
    DESCRIPTION
        "The count of clients which have registered for UPS
         Shutdown control."
    ::= { upsConnectedClients 1 }

upsConnectedClientsTable OBJECT-TYPE
    SYNTAX SEQUENCE OF UpsConnectedClientsEntry
    ACCESS not-accessible
    STATUS mandatory
    DESCRIPTION
        "The devices powered by UPS and registered to RemotEye III"
    ::= { upsConnectedClients 2 }

upsConnectedClientsEntry OBJECT-TYPE
    SYNTAX UpsConnectedClientsEntry
    ACCESS not-accessible
    STATUS mandatory
    DESCRIPTION
        "The devices protected by RemotEye III"
    INDEX  { upsConnectedClientsIndex }
    ::= { upsConnectedClientsTable 1 }

UpsConnectedClientsEntry ::=
    SEQUENCE {
        upsConnectedClientsIndex               PositiveInteger,
        upsConnectedClientsIPAddress           IpAddress,
        upsConnectedClientsName                DisplayString,
        upsConnectedClientsTimeAtConnection    DisplayString,
        upsConnectedClientsShutdownDelay       DisplayString,
        upsConnectedClientsConnectionTimeout   INTEGER,
        upsConnectedClientsShutdownTest        INTEGER
    }

-- ===========================================================================
-- upsConnectedClientsTable/upsConnectedClientsEntry/upsConnectedClientsIndex
-- ===========================================================================

upsConnectedClientsIndex OBJECT-TYPE
    SYNTAX PositiveInteger
    ACCESS not-accessible
    STATUS mandatory
    DESCRIPTION
        "The index of the device that is plugged into the UPS."
    ::= { upsConnectedClientsEntry 1 }

upsConnectedClientsIPAddress OBJECT-TYPE
    SYNTAX IpAddress
    ACCESS read-only
    STATUS mandatory
    DESCRIPTION
        "The ip address of the device."
    ::= { upsConnectedClientsEntry 2 }

upsConnectedClientsName OBJECT-TYPE
    SYNTAX DisplayString (SIZE(0..31))
    ACCESS read-only
    STATUS mandatory
    DESCRIPTION
        "The name/description of the device plugged into the UPS."
    ::= { upsConnectedClientsEntry 3 }

upsConnectedClientsTimeAtConnection OBJECT-TYPE
    SYNTAX DisplayString (SIZE(0..31))
    ACCESS read-only
    STATUS mandatory
    DESCRIPTION
        "The time that the device registered to REMOTEYE III"
    ::= { upsConnectedClientsEntry 4 }

upsConnectedClientsShutdownDelay OBJECT-TYPE
    SYNTAX DisplayString
    ACCESS read-only
    STATUS mandatory
    DESCRIPTION
        "The shutdown delay set on REMOTEYE III"
    ::= { upsConnectedClientsEntry 5 }

upsConnectedClientsConnectionTimeout OBJECT-TYPE
    SYNTAX INTEGER
    ACCESS read-only
    STATUS mandatory
    DESCRIPTION
            "The device timeout counter. Unit: 10 seconds"
    ::= { upsConnectedClientsEntry 6 }

upsConnectedClientsShutdownTest OBJECT-TYPE
    SYNTAX INTEGER
    ACCESS read-only
    STATUS mandatory
    DESCRIPTION
            "The client will shutdown test after receive
             shutdown request from REMOTEYE III."
    ::= { upsConnectedClientsEntry 7 }

-- ===========================================================================
--
-- upsEmail - Group 14
--
-- ===========================================================================

upsEmailMailServer OBJECT-TYPE
    SYNTAX DisplayString (SIZE (0..31))
    ACCESS read-write
    STATUS mandatory
    DESCRIPTION
        "The Email mail server for REMOTEYE III."
    ::= { upsEmail 1 }

upsEmailUserAccount OBJECT-TYPE
    SYNTAX DisplayString (SIZE (0..15))
    ACCESS read-write
    STATUS mandatory
    DESCRIPTION
        "The Email mail server login name."
    ::= { upsEmail 2 }

upsEmailUserPassword OBJECT-TYPE
    SYNTAX DisplayString (SIZE (0..15))
    ACCESS read-write
    STATUS mandatory
    DESCRIPTION
        "The Email mail server password."
    ::= { upsEmail 3 }

upsEmailDomainName OBJECT-TYPE
    SYNTAX DisplayString (SIZE (0..31))
    ACCESS read-write
    STATUS mandatory
    DESCRIPTION
        "The Email mail server domain name"
    ::= { upsEmail 4 }

upsEmailDNSServer OBJECT-TYPE
    SYNTAX DisplayString (SIZE (0..31))
    ACCESS read-write
    STATUS mandatory
    DESCRIPTION
        "The Email DNS server name"
    ::= { upsEmail 5 }

upsEmailStatusReportSendTime OBJECT-TYPE
    SYNTAX DisplayString (SIZE(6))
    ACCESS read-write
    STATUS mandatory
    DESCRIPTION
        "The Email Status Report Send Time"
    ::= { upsEmail 6 }

upsEmailClientsTable OBJECT-TYPE
    SYNTAX SEQUENCE OF UpsEmailClientsEntry
    ACCESS not-accessible
    STATUS mandatory
    DESCRIPTION
        "The email addresses that RemotEye III will send logs and status reports to."
    ::= { upsEmail 7 }

upsEmailClientsEntry OBJECT-TYPE
    SYNTAX UpsEmailClientsEntry
    ACCESS not-accessible
    STATUS mandatory
    DESCRIPTION
        "The email addresses that RemotEye III will send logs and status
         reports to."
    INDEX  { upsEmailClientsIndex }
    ::= { upsEmailClientsTable 1 }

UpsEmailClientsEntry ::=
    SEQUENCE {
        upsEmailClientsIndex        		PositiveInteger,
        upsEmailClientsEmailAddress 		DisplayString,
        upsEmailClientsDescription  		DisplayString,
        upsEmailClientsDailyStatusReportType    INTEGER,
        upsEmailClientsEventStatusReportType	INTEGER,
        upsEmailClientsInfoLevel    		INTEGER
    }

-- ===========================================================================
-- upsEmailClientsTable/upsEmailClientsEntry/upsEmailClientsIndex
-- ===========================================================================

upsEmailClientsIndex OBJECT-TYPE
    SYNTAX PositiveInteger
    ACCESS read-only
    STATUS mandatory
    DESCRIPTION
        "The index of the email clients."
    ::= { upsEmailClientsEntry 1 }

upsEmailClientsEmailAddress OBJECT-TYPE
    SYNTAX DisplayString (SIZE(0..128))
    ACCESS read-write
    STATUS mandatory
    DESCRIPTION
        "The email address of the clients."
    ::= { upsEmailClientsEntry 2 }

upsEmailClientsDescription OBJECT-TYPE
    SYNTAX DisplayString (SIZE(0..31))
    ACCESS read-write
    STATUS mandatory
    DESCRIPTION
        "The name/description of the clients."
    ::= { upsEmailClientsEntry 3 }

upsEmailClientsDailyStatusReportType OBJECT-TYPE
    SYNTAX INTEGER {
        general-test(1),
	  test-records(2),
	  backup-Records(3),
	  fault-Records(4),
	  operation-Mode-Records(5),
	  warning-Records(6),
	  system-Setting-Change-Record(7),
	  remotEye-III-Events-Log(8)
    }
    ACCESS read-write
    STATUS mandatory
    DESCRIPTION
        "The type of daily information that clients would like to receive."
    ::= { upsEmailClientsEntry 4 }

upsEmailClientsEventStatusReportType OBJECT-TYPE
    SYNTAX INTEGER {
        general-test(1),
	  test-records(2),
	  backup-Records(3),
	  fault-Records(4),
	  operation-Mode-Records(5),
	  warning-Records(6),
	  system-Setting-Change-Record(7),
	  remotEye-III-Events-Log(8)
    }
    ACCESS read-write
    STATUS mandatory
    DESCRIPTION
        "The type of event information that clients would like to receive when event occurs."
    ::= { upsEmailClientsEntry 5 }

upsEmailClientsInfoLevel OBJECT-TYPE
    SYNTAX INTEGER {
        fault(1),
        warning(2),
        informational(3)
    }
    ACCESS read-write
    STATUS mandatory
    DESCRIPTION
        "The type of information that clients would like to receive."
    ::= { upsEmailClientsEntry 6 }

-- ===========================================================================
--
-- upsSNMP - Group 15
--
-- ===========================================================================
upsSNMPVersion OBJECT-TYPE
    SYNTAX INTEGER {
        disable(1),
        snmpv1(2),
        snmpv3(3)
    }
    ACCESS read-only
    STATUS mandatory
    DESCRIPTION
        "The SNMP version"
    ::= { upsSNMP 1 }

upsSNMPTrapsReceiversTable OBJECT-TYPE
    SYNTAX SEQUENCE OF UpsSNMPTrapsReceiversEntry
    ACCESS not-accessible
    STATUS mandatory
    DESCRIPTION
        "A list of managers to send traps to. The number of
         entries is given by the value of upsSNMPNumTrapReceivers"
    ::= { upsSNMP 2 }

upsSNMPTrapsReceiversEntry OBJECT-TYPE
    SYNTAX UpsSNMPTrapsReceiversEntry
    ACCESS not-accessible
    STATUS mandatory
    DESCRIPTION
        "The managers to send traps to."
    INDEX  { upsSNMPTrapsReceiversIndex }
    ::= { upsSNMPTrapsReceiversTable 1 }

UpsSNMPTrapsReceiversEntry ::=
    SEQUENCE {
        upsSNMPTrapsReceiversIndex                     PositiveInteger,
        upsSNMPTrapsReceiversIPAddress                 IpAddress,
        upsSNMPTrapReceiversCommunityString            DisplayString,
        upsSNMPTrapReceiversTrapType                   INTEGER,
        upsSNMPTrapReceiversInfoReceivingSeverityLevel INTEGER,
        upsSNMPTrapReceiversDescription                DisplayString
    }

-- ===========================================================================
-- upsSNMPTrapsReceiversTable/upsSNMPTrapsReceiversEntry/upsSNMPTrapsReceiversIndex
-- ===========================================================================
upsSNMPTrapsReceiversIndex OBJECT-TYPE
    SYNTAX PositiveInteger
    ACCESS read-only
    STATUS mandatory
    DESCRIPTION
        "The index to a trap receiver entry."
    ::= { upsSNMPTrapsReceiversEntry 1 }

upsSNMPTrapsReceiversIPAddress OBJECT-TYPE
    SYNTAX IpAddress
    ACCESS read-write
    STATUS mandatory
    DESCRIPTION
        "The IP address of the manager to send a trap to."
    ::= { upsSNMPTrapsReceiversEntry 2 }

upsSNMPTrapReceiversCommunityString OBJECT-TYPE
    SYNTAX DisplayString (SIZE(0..19))
    ACCESS read-write
    STATUS mandatory
    DESCRIPTION
        "The community name to use in the trap when
         sent to the manager."
    ::= { upsSNMPTrapsReceiversEntry 3 }

upsSNMPTrapReceiversTrapType OBJECT-TYPE
    SYNTAX INTEGER {
        none(1),
        toshiba-trap(2),
        jema-trap(3),
        rfc1628-trap(4)
    }
    ACCESS read-write
    STATUS mandatory
    DESCRIPTION
        "The trap group that NMS desired."
    ::= { upsSNMPTrapsReceiversEntry 4 }

upsSNMPTrapReceiversInfoReceivingSeverityLevel OBJECT-TYPE
    SYNTAX INTEGER {
        informational(1),
        warning(2),
        fault(3)
    }
    ACCESS read-write
    STATUS mandatory
    DESCRIPTION
        "The severity level of traps to be received by this manager."
    ::= { upsSNMPTrapsReceiversEntry 5 }

upsSNMPTrapReceiversDescription OBJECT-TYPE
    SYNTAX DisplayString (SIZE(0..31))
    ACCESS read-write
    STATUS mandatory
    DESCRIPTION
        "Description of trap receivers"
    ::= { upsSNMPTrapsReceiversEntry 6 }

upsSNMPCommunitiesTable OBJECT-TYPE
    SYNTAX SEQUENCE OF UpsSNMPCommunitiesEntry
    ACCESS not-accessible
    STATUS mandatory
    DESCRIPTION
        "A list of managers which can access REMOTEYE III with private
         community string."
    ::= { upsSNMP 3 }

upsSNMPCommunitiesEntry OBJECT-TYPE
    SYNTAX UpsSNMPCommunitiesEntry
    ACCESS not-accessible
    STATUS mandatory
    DESCRIPTION
        "The managers."
    INDEX  { upsSNMPCommunitiesIndex}
    ::= { upsSNMPCommunitiesTable 1 }

UpsSNMPCommunitiesEntry ::=
    SEQUENCE {
        upsSNMPCommunitiesIndex             PositiveInteger,
        upsSNMPCommunitiesIPAddress         IpAddress,
        upsSNMPCommunitiesAccessString      DisplayString,
        upsSNMPCommunitiesAccessMode        INTEGER
    }

-- ===========================================================================
-- upsSNMPCommunitiesTable/upsSNMPCommunitiesEntry/upsSNMPCommunitiesIndex
-- ===========================================================================

upsSNMPCommunitiesIndex OBJECT-TYPE
    SYNTAX PositiveInteger
    ACCESS read-only
    STATUS mandatory
    DESCRIPTION
        "The index to a access control entry."
    ::= { upsSNMPCommunitiesEntry 1 }

upsSNMPCommunitiesIPAddress OBJECT-TYPE
    SYNTAX IpAddress
    ACCESS read-write
    STATUS mandatory
    DESCRIPTION
        "The IP address of the manager to access REMOTEYE III"
    ::= { upsSNMPCommunitiesEntry 2 }

upsSNMPCommunitiesAccessString OBJECT-TYPE
    SYNTAX DisplayString (SIZE(0..19))
    ACCESS read-write
    STATUS mandatory
    DESCRIPTION
        "The community name to use in the manager when
         access REMOTEYE III"
    ::= { upsSNMPCommunitiesEntry 3 }

upsSNMPCommunitiesAccessMode OBJECT-TYPE
    SYNTAX INTEGER {
        readOnly(1),
        read-write(2),
        notAccess(3)
    }
    ACCESS read-write
    STATUS mandatory
    DESCRIPTION
        "Access type, only read/Write access type can change parameter
         of REMOTEYE III"
    ::= { upsSNMPCommunitiesEntry 4 }

-- ===========================================================================
--
-- upsEMD - Group 16
--
-- ===========================================================================
upsEMDType OBJECT-TYPE
    SYNTAX DisplayString
    ACCESS read-only
    STATUS mandatory
    DESCRIPTION
        "The name assign to specific EMD."
    ::= { upsEMD 1 }

upsEMDTemperature OBJECT-TYPE
    SYNTAX INTEGER
    ACCESS read-only
    STATUS mandatory
    DESCRIPTION
        "The EMD temperature."
    ::= { upsEMD 2 }

upsEMDTemperatureLowWarningSetPoint OBJECT-TYPE
    SYNTAX INTEGER
    ACCESS read-write
    STATUS mandatory
    DESCRIPTION
        "The EMD temperature low warning set point."
    ::= { upsEMD 3 }

upsEMDTemperatureLowCriticalSetPoint OBJECT-TYPE
    SYNTAX INTEGER
    ACCESS read-write
    STATUS mandatory
    DESCRIPTION
        "The EMD temperature low critical set point."
    ::= { upsEMD 4 }

upsEMDTemperatureHighWarningSetPoint OBJECT-TYPE
    SYNTAX INTEGER
    ACCESS read-write
    STATUS mandatory
    DESCRIPTION
        "The EMD temperature high warning set point."
    ::= { upsEMD 5 }

upsEMDTemperatureHighCriticalSetPoint OBJECT-TYPE
    SYNTAX INTEGER
    ACCESS read-write
    STATUS mandatory
    DESCRIPTION
        "The EMD temperature high critical set point."
    ::= { upsEMD 6 }

upsEMDTemperatureHysteresis OBJECT-TYPE
    SYNTAX INTEGER
    ACCESS read-write
    STATUS mandatory
    DESCRIPTION
        "The EMD temperature hysteresis."
    ::= { upsEMD 7 }

upsEMDTemperatureCalibrationOffset OBJECT-TYPE
    SYNTAX INTEGER
    ACCESS read-write
    STATUS mandatory
    DESCRIPTION
        "The EMD temperature calibration offset."
    ::= { upsEMD 8 }

upsEMDHumidity OBJECT-TYPE
    SYNTAX INTEGER
    ACCESS read-only
    STATUS mandatory
    DESCRIPTION
        "The EMD Humidity."
    ::= { upsEMD 9 }

upsEMDHumidityLowWarningSetPoint OBJECT-TYPE
    SYNTAX INTEGER
    ACCESS read-write
    STATUS mandatory
    DESCRIPTION
        "The EMD Humidity low warning set point."
    ::= { upsEMD 10 }

upsEMDHumidityLowCriticalSetPoint OBJECT-TYPE
    SYNTAX INTEGER
    ACCESS read-write
    STATUS mandatory
    DESCRIPTION
        "The EMD Humidity low critical set point."
    ::= { upsEMD 11 }

upsEMDHumidityHighWarningSetPoint OBJECT-TYPE
    SYNTAX INTEGER
    ACCESS read-write
    STATUS mandatory
    DESCRIPTION
        "The EMD Humidity high warning set point."
    ::= { upsEMD 12 }

upsEMDHumidityHighCriticalSetPoint OBJECT-TYPE
    SYNTAX INTEGER
    ACCESS read-write
    STATUS mandatory
    DESCRIPTION
        "The EMD Humidity high critical set point."
    ::= { upsEMD 13 }

upsEMDHumidityHysteresis OBJECT-TYPE
    SYNTAX INTEGER
    ACCESS read-write
    STATUS mandatory
    DESCRIPTION
        "The EMD Humidity hysteresis."
    ::= { upsEMD 14 }

upsEMDHumidityCalibrationOffset OBJECT-TYPE
    SYNTAX INTEGER
    ACCESS read-write
    STATUS mandatory
    DESCRIPTION
        "The EMD Humidity calibration offset."
    ::= { upsEMD 15 }

upsEMDR1Status OBJECT-TYPE
    SYNTAX INTEGER {
        unknown(1),
        disabled(2),
        active(3),
        inactive(4)
    }
    ACCESS read-only
    STATUS mandatory
    DESCRIPTION
        "The EMD dry contact 1 status."
    ::= { upsEMD 16 }

upsEMDAlarmR1Enable OBJECT-TYPE
    SYNTAX INTEGER {
        disable(1),
        normalClose(2),
        normalOpen(3),
        highActive(4),
        lowActive(5)
    }
    ACCESS read-write
    STATUS mandatory
    DESCRIPTION
        "The EMD contact R1 alarm enable setting."
    ::= { upsEMD 17 }

upsEMDAlarmR1Hysteresis OBJECT-TYPE
    SYNTAX INTEGER
    ACCESS read-write
    STATUS mandatory
    DESCRIPTION
        "The EMD Contact R1 alarm hysteresis."
    ::= { upsEMD 18 }

upsEMDR2Status OBJECT-TYPE
    SYNTAX INTEGER {
        unknown(1),
        disabled(2),
        active(3),
        inactive(4)
    }
    ACCESS read-only
    STATUS mandatory
    DESCRIPTION
        "The EMD dry contact 2 status."
    ::= { upsEMD 19 }

upsEMDAlarmR2Enable OBJECT-TYPE
    SYNTAX INTEGER {
        disable(1),
        normalClose(2),
        normalOpen(3),
        highActive(4),
        lowActive(5)
    }
    ACCESS read-write
    STATUS mandatory
    DESCRIPTION
        "The EMD contact R2 alarm enable setting."
    ::= { upsEMD 20 }

upsEMDAlarmR2Hysteresis OBJECT-TYPE
    SYNTAX INTEGER
    ACCESS read-write
    STATUS mandatory
    DESCRIPTION
        "The EMD Contact R2 alarm hysteresis."
    ::= { upsEMD 21 }

-- ===========================================================================
-- upsTraps - Group 21
-- Traps group
-- ===========================================================================
upsTrapFault TRAP-TYPE
    ENTERPRISE rmti3
    DESCRIPTION
        "Fault: One or more fault reported."
   --#TYPE "Fault: One or more fault reported."
   --#SUMMARY "Fault: One or more fault reported."
   --#SEVERITY INFORMATIONAL
   --#TIMEINDEX 1
   --#HELP ""
   --#HELPTAG 0
   --#STATE OPERATIONAL
    ::= 1

upsTrapFaultClear TRAP-TYPE
    ENTERPRISE rmti3
    DESCRIPTION
        "Fault Clear: One or more fault reported."
	--#TYPE "Fault Clear: One or more fault reported."
   --#SUMMARY "Fault Clear: One or more fault reported."
   --#SEVERITY INFORMATIONAL
   --#TIMEINDEX 1
   --#HELP ""
   --#HELPTAG 0
   --#STATE OPERATIONAL
    ::= 2

upsTrapOpenFuse TRAP-TYPE
    ENTERPRISE rmti3
    DESCRIPTION
        "Fault: An open fuse reported."
		--#TYPE "Fault: An open fuse reported."
   --#SUMMARY "Fault: An open fuse reported."
   --#SEVERITY INFORMATIONAL
   --#TIMEINDEX 1
   --#HELP ""
   --#HELPTAG 0
   --#STATE OPERATIONAL
    ::= 3

upsTrapOpenFuseClear TRAP-TYPE
    ENTERPRISE rmti3
    DESCRIPTION
        "Fault Clear: An open fuse reported."
		--#TYPE "Fault Clear: An open fuse reported."
   --#SUMMARY "Fault Clear: An open fuse reported."
   --#SEVERITY INFORMATIONAL
   --#TIMEINDEX 1
   --#HELP ""
   --#HELPTAG 0
   --#STATE OPERATIONAL
    ::= 4

upsTrapCurrentLimitFault TRAP-TYPE
    ENTERPRISE rmti3
    DESCRIPTION
        "Fault: A current limit fault reported. Contact your Toshiba authorized service center for examination."
		 --#TYPE "Fault: A current limit fault reported. Contact your Toshiba authorized service center for examination."
   --#SUMMARY "Fault: A current limit fault reported. Contact your Toshiba authorized service center for examination."
   --#SEVERITY INFORMATIONAL
   --#TIMEINDEX 1
   --#HELP ""
   --#HELPTAG 0
   --#STATE OPERATIONAL
    ::= 5

upsTrapCurrentLimitFaultClear TRAP-TYPE
    ENTERPRISE rmti3
    DESCRIPTION
        "Fault Clear: A current limit fault reported. Contact your Toshiba authorized service center for examination."
		--#TYPE "Fault Clear: A current limit fault reported. Contact your Toshiba authorized service center for examination."
   --#SUMMARY "Fault Clear: A current limit fault reported. Contact your Toshiba authorized service center for examination."
   --#SEVERITY INFORMATIONAL
   --#TIMEINDEX 1
   --#HELP ""
   --#HELPTAG 0
   --#STATE OPERATIONAL
    ::= 6

upsTrapDCBusOverCurrent TRAP-TYPE
    ENTERPRISE rmti3
    DESCRIPTION
        "Fault: A DC bus overcurrent reported. Contact your Toshiba authorized service center for examination."
		 --#TYPE "Fault: A DC bus overcurrent reported. Contact your Toshiba authorized service center for examination."
   --#SUMMARY "Fault: A DC bus overcurrent reported. Contact your Toshiba authorized service center for examination."
   --#SEVERITY INFORMATIONAL
   --#TIMEINDEX 1
   --#HELP ""
   --#HELPTAG 0
   --#STATE OPERATIONAL
    ::= 7

upsTrapDCBusOverCurrentClear TRAP-TYPE
    ENTERPRISE rmti3
    DESCRIPTION
        "Fault Clear: A DC bus overcurrent reported. Contact your Toshiba authorized service center for examination."
		--#TYPE "Fault Clear: A DC bus overcurrent reported. Contact your Toshiba authorized service center for examination."
   --#SUMMARY "Fault Clear: A DC bus overcurrent reported. Contact your Toshiba authorized service center for examination."
   --#SEVERITY INFORMATIONAL
   --#TIMEINDEX 1
   --#HELP ""
   --#HELPTAG 0
   --#STATE OPERATIONAL
    ::= 8

upsTrapDCBusOverVoltage TRAP-TYPE
    ENTERPRISE rmti3
    DESCRIPTION
        "Fault: A DC bus overvoltage reported. Contact your Toshiba authorized service center for examination."
		 --#TYPE "Fault: A DC bus overvoltage reported. Contact your Toshiba authorized service center for examination."
   --#SUMMARY "Fault: A DC bus overvoltage reported. Contact your Toshiba authorized service center for examination."
   --#SEVERITY INFORMATIONAL
   --#TIMEINDEX 1
   --#HELP ""
   --#HELPTAG 0
   --#STATE OPERATIONAL
    ::= 9

upsTrapDCBusOverVoltageClear TRAP-TYPE
    ENTERPRISE rmti3
    DESCRIPTION
        "Fault Clear: A DC bus overvoltage reported. Contact your Toshiba authorized service center for examination."
		--#TYPE "Fault Clear: A DC bus overvoltage reported. Contact your Toshiba authorized service center for examination."
   --#SUMMARY "Fault Clear: A DC bus overvoltage reported. Contact your Toshiba authorized service center for examination."
   --#SEVERITY INFORMATIONAL
   --#TIMEINDEX 1
   --#HELP ""
   --#HELPTAG 0
   --#STATE OPERATIONAL
    ::= 10

upsTrapDCBusImbalance TRAP-TYPE
    ENTERPRISE rmti3
    DESCRIPTION
        "Fault: A DC bus imbalance reported. Contact your Toshiba authorized service center for examination."
		 --#TYPE "Fault: A DC bus imbalance reported. Contact your Toshiba authorized service center for examination."
   --#SUMMARY "Fault: A DC bus imbalance reported. Contact your Toshiba authorized service center for examination."
   --#SEVERITY INFORMATIONAL
   --#TIMEINDEX 1
   --#HELP ""
   --#HELPTAG 0
   --#STATE OPERATIONAL
    ::= 11

upsTrapDCBusImbalanceClear TRAP-TYPE
    ENTERPRISE rmti3
    DESCRIPTION
        "Fault Clear: A DC bus imbalance reported. Contact your Toshiba authorized service center for examination."
		 --#TYPE "Fault Clear: A DC bus imbalance reported. Contact your Toshiba authorized service center for examination."
   --#SUMMARY "Fault Clear: A DC bus imbalance reported. Contact your Toshiba authorized service center for examination."
   --#SEVERITY INFORMATIONAL
   --#TIMEINDEX 1
   --#HELP ""
   --#HELPTAG 0
   --#STATE OPERATIONAL
    ::= 12

upsTrapOutputUnderVoltage TRAP-TYPE
    ENTERPRISE rmti3
    DESCRIPTION
        "Fault: An output undervoltage reported. Contact your Toshiba authorized service center for examination."
		 --#TYPE "Fault: An output undervoltage reported. Contact your Toshiba authorized service center for examination."
   --#SUMMARY "Fault: An output undervoltage reported. Contact your Toshiba authorized service center for examination."
   --#SEVERITY INFORMATIONAL
   --#TIMEINDEX 1
   --#HELP ""
   --#HELPTAG 0
   --#STATE OPERATIONAL
    ::= 13

upsTrapOutputUnderVoltageClear TRAP-TYPE
    ENTERPRISE rmti3
    DESCRIPTION
        "Fault Clear: An output undervoltage reported. Contact your Toshiba authorized service center for examination."
		 --#TYPE "Fault Clear: An output undervoltage reported. Contact your Toshiba authorized service center for examination."
   --#SUMMARY "Fault Clear: An output undervoltage reported. Contact your Toshiba authorized service center for examination."
   --#SEVERITY INFORMATIONAL
   --#TIMEINDEX 1
   --#HELP ""
   --#HELPTAG 0
   --#STATE OPERATIONAL
    ::= 14

upsTrapOutputOverVoltage TRAP-TYPE
    ENTERPRISE rmti3
    DESCRIPTION
        "Fault: An output overvoltage reported. Contact your Toshiba authorized service center for examination."
		 --#TYPE "Fault: An output overvoltage reported. Contact your Toshiba authorized service center for examination."
   --#SUMMARY "Fault: An output overvoltage reported. Contact your Toshiba authorized service center for examination."
   --#SEVERITY INFORMATIONAL
   --#TIMEINDEX 1
   --#HELP ""
   --#HELPTAG 0
   --#STATE OPERATIONAL
    ::= 15

upsTrapOutputOverVoltageClear TRAP-TYPE
    ENTERPRISE rmti3
    DESCRIPTION
        "Fault Clear: An output overvoltage reported. Contact your Toshiba authorized service center for examination."
		--#TYPE "Fault Clear: An output overvoltage reported. Contact your Toshiba service center for examination."
   --#SUMMARY "Fault Clear: An output overvoltage reported. Contact your Toshiba authorized service center for examination."
   --#SEVERITY INFORMATIONAL
   --#TIMEINDEX 1
   --#HELP ""
   --#HELPTAG 0
   --#STATE OPERATIONAL
    ::= 16

upsTrapHeatSinkOverheat TRAP-TYPE
    ENTERPRISE rmti3
    DESCRIPTION
        "Fault: A Heat sink or device overheat reported."
		--#TYPE "Fault: A Heat sink or device overheat reported."
   --#SUMMARY "Fault: A Heat sink or device overheat reported."
   --#SEVERITY INFORMATIONAL
   --#TIMEINDEX 1
   --#HELP ""
   --#HELPTAG 0
   --#STATE OPERATIONAL
    ::= 17

upsTrapHeatSinkOverheatClear TRAP-TYPE
    ENTERPRISE rmti3
    DESCRIPTION
        "Fault Clear: A Heat sink or device overheat reported."
			--#TYPE "Fault Clear: A Heat sink or device overheat reported."
   --#SUMMARY "Fault Clear: A Heat sink or device overheat reported."
   --#SEVERITY INFORMATIONAL
   --#TIMEINDEX 1
   --#HELP ""
   --#HELPTAG 0
   --#STATE OPERATIONAL
    ::= 18

upsTrapBypassOverload TRAP-TYPE
    ENTERPRISE rmti3
    DESCRIPTION
        "Fault: A bypass overload reported."
		--#TYPE "Fault: A bypass overload reported."
   --#SUMMARY "Fault: A bypass overload reported."
   --#SEVERITY INFORMATIONAL
   --#TIMEINDEX 1
   --#HELP ""
   --#HELPTAG 0
   --#STATE OPERATIONAL
    ::= 19

upsTrapBypassOverloadClear TRAP-TYPE
    ENTERPRISE rmti3
    DESCRIPTION
        "Fault Clear: A bypass overload reported."
		--#TYPE "Fault Clear: A bypass overload reported."
   --#SUMMARY "Fault Clear: A bypass overload reported."
   --#SEVERITY INFORMATIONAL
   --#TIMEINDEX 1
   --#HELP ""
   --#HELPTAG 0
   --#STATE OPERATIONAL
    ::= 20


upsTrapChargerOvervoltageFault TRAP-TYPE
    ENTERPRISE rmti3
    DESCRIPTION
        "Warning: Charger overvoltage reported."
		--#TYPE "Warning: Charger overvoltage reported."
   --#SUMMARY "Warning: Charger overvoltage reported."
   --#SEVERITY INFORMATIONAL
   --#TIMEINDEX 1
   --#HELP ""
   --#HELPTAG 0
   --#STATE OPERATIONAL
    ::= 21

upsTrapChargerOvervoltageFaultClear TRAP-TYPE
    ENTERPRISE rmti3
    DESCRIPTION
        "Warning Clear: Charger overvoltage reported."
		--#TYPE "Warning Clear: Charger overvoltage reported."
   --#SUMMARY "Warning Clear: Charger overvoltage reported."
   --#SEVERITY INFORMATIONAL
   --#TIMEINDEX 1
   --#HELP ""
   --#HELPTAG 0
   --#STATE OPERATIONAL
    ::= 22

upsTrapOutputOvercurrent TRAP-TYPE
    ENTERPRISE rmti3
    DESCRIPTION
        "Warning: An output overcurrent reported."
		--#TYPE "Warning: An output overcurrent reported."
   --#SUMMARY "Warning: An output overcurrent reported."
   --#SEVERITY INFORMATIONAL
   --#TIMEINDEX 1
   --#HELP ""
   --#HELPTAG 0
   --#STATE OPERATIONAL
    ::= 23

upsTrapOutputOvercurrentClear TRAP-TYPE
    ENTERPRISE rmti3
    DESCRIPTION
        "Warning Clear: An output overcurrent reported."
		--#TYPE "Warning Clear: An output overcurrent reported."
   --#SUMMARY "Warning Clear: An output overcurrent reported."
   --#SEVERITY INFORMATIONAL
   --#TIMEINDEX 1
   --#HELP ""
   --#HELPTAG 0
   --#STATE OPERATIONAL
    ::= 24

upsTrapDCUnderVoltageAtBoostUp TRAP-TYPE
    ENTERPRISE rmti3
    DESCRIPTION
        "Fault: A DC bus undervoltage during boost-up reported."
		--#TYPE "Fault: A DC bus undervoltage during boost-up reported."
   --#SUMMARY "Fault: A DC bus undervoltage during boost-up reported."
   --#SEVERITY INFORMATIONAL
   --#TIMEINDEX 1
   --#HELP ""
   --#HELPTAG 0
   --#STATE OPERATIONAL
    ::= 25

upsTrapDCUnderVoltageAtBoostUpClear TRAP-TYPE
    ENTERPRISE rmti3
    DESCRIPTION
        "Fault Clear: A DC bus undervoltage during boost-up reported."
		--#TYPE "Fault Clear: A DC bus undervoltage during boost-up reported."
   --#SUMMARY "Fault Clear: A DC bus undervoltage during boost-up reported."
   --#SEVERITY INFORMATIONAL
   --#TIMEINDEX 1
   --#HELP ""
   --#HELPTAG 0
   --#STATE OPERATIONAL
    ::= 26

upsTrapDCUnderVoltageAtCharge TRAP-TYPE
    ENTERPRISE rmti3
    DESCRIPTION
        "Fault: A DC bus undervoltage during charging reported."
		--#TYPE "Fault: A DC bus undervoltage during charging reported."
   --#SUMMARY "Fault: A DC bus undervoltage during charging reported."
   --#SEVERITY INFORMATIONAL
   --#TIMEINDEX 1
   --#HELP ""
   --#HELPTAG 0
   --#STATE OPERATIONAL
    ::= 27

upsTrapDCUnderVoltageAtChargeClear TRAP-TYPE
    ENTERPRISE rmti3
    DESCRIPTION
        "Fault Clear: A DC bus undervoltage during charging reported."
			--#TYPE "Fault Clear: A DC bus undervoltage during charging reported."
   --#SUMMARY "Fault Clear: A DC bus undervoltage during charging reported."
   --#SEVERITY INFORMATIONAL
   --#TIMEINDEX 1
   --#HELP ""
   --#HELPTAG 0
   --#STATE OPERATIONAL
    ::= 28

upsTrapBypassOverheat TRAP-TYPE
    ENTERPRISE rmti3
    DESCRIPTION
        "Fault: A Bypass overheat reported."
			--#TYPE "Fault: A Bypass overheat reported."
   --#SUMMARY "Fault: A Bypass overheat reported."
   --#SEVERITY INFORMATIONAL
   --#TIMEINDEX 1
   --#HELP ""
   --#HELPTAG 0
   --#STATE OPERATIONAL
    ::= 29

upsTrapBypassOverheatClear TRAP-TYPE
    ENTERPRISE rmti3
    DESCRIPTION
        "Fault Clear: A Bypass overheat reported."
		--#TYPE "Fault Clear: A Bypass overheat reported."
   --#SUMMARY "Fault Clear: A Bypass overheat reported."
   --#SEVERITY INFORMATIONAL
   --#TIMEINDEX 1
   --#HELP ""
   --#HELPTAG 0
   --#STATE OPERATIONAL
    ::= 30

upsTrapResettableInverterOverload TRAP-TYPE
    ENTERPRISE rmti3
    DESCRIPTION
        "Fault: An inverter overload reported. It is resettable."
			--#TYPE "Fault: An inverter overload reported. It is resettable."
   --#SUMMARY "Fault: An inverter overload reported. It is resettable."
   --#SEVERITY INFORMATIONAL
   --#TIMEINDEX 1
   --#HELP ""
   --#HELPTAG 0
   --#STATE OPERATIONAL
    ::= 31

upsTrapResettableInverterOverloadClear TRAP-TYPE
    ENTERPRISE rmti3
    DESCRIPTION
        "Fault Clear: An inverter overload reported. It is resettable."
		--#TYPE "Fault Clear: An inverter overload reported. It is resettable."
   --#SUMMARY "Fault Clear: An inverter overload reported. It is resettable."
   --#SEVERITY INFORMATIONAL
   --#TIMEINDEX 1
   --#HELP ""
   --#HELPTAG 0
   --#STATE OPERATIONAL
    ::= 32

upsTrapUnResettableInverterOverload TRAP-TYPE
    ENTERPRISE rmti3
    DESCRIPTION
        "Fault: An inverter overload reported. It is not resettable."
		--#TYPE "Fault: An inverter overload reported. It is not resettable."
   --#SUMMARY "Fault: An inverter overload reported. It is not resettable."
   --#SEVERITY INFORMATIONAL
   --#TIMEINDEX 1
   --#HELP ""
   --#HELPTAG 0
   --#STATE OPERATIONAL
    ::= 33

upsTrapUnResettableInverterOverloadClear TRAP-TYPE
    ENTERPRISE rmti3
    DESCRIPTION
        "Fault Clear: An inverter overload reported. It is not resettable."
		--#TYPE "Fault Clear: An inverter overload reported. It is not resettable."
   --#SUMMARY "Fault Clear: An inverter overload reported. It is not resettable."
   --#SEVERITY INFORMATIONAL
   --#TIMEINDEX 1
   --#HELP ""
   --#HELPTAG 0
   --#STATE OPERATIONAL
    ::= 34

upsTrapInputOverVoltage TRAP-TYPE
    ENTERPRISE rmti3
    DESCRIPTION
        "Warning: An input overvoltage reported."
		--#TYPE "Warning: An input overvoltage reported."
   --#SUMMARY "Warning: An input overvoltage reported."
   --#SEVERITY INFORMATIONAL
   --#TIMEINDEX 1
   --#HELP ""
   --#HELPTAG 0
   --#STATE OPERATIONAL
    ::= 35

upsTrapInputOverVoltageClear TRAP-TYPE
    ENTERPRISE rmti3
    DESCRIPTION
        "Warning Clear: An input overvoltage reported."
		--#TYPE "Warning Clear: An input overvoltage reported."
   --#SUMMARY "Warning Clear: An input overvoltage reported."
   --#SEVERITY INFORMATIONAL
   --#TIMEINDEX 1
   --#HELP ""
   --#HELPTAG 0
   --#STATE OPERATIONAL
    ::= 36

upsTrapInputUnderVoltage TRAP-TYPE
    ENTERPRISE rmti3
    DESCRIPTION
        "Warning: An input undervoltage reported."
		--#TYPE "Warning: An input undervoltage reported."
   --#SUMMARY "Warning: An input undervoltage reported."
   --#SEVERITY INFORMATIONAL
   --#TIMEINDEX 1
   --#HELP ""
   --#HELPTAG 0
   --#STATE OPERATIONAL
    ::= 37

upsTrapInputUnderVoltageClear TRAP-TYPE
    ENTERPRISE rmti3
    DESCRIPTION
        "Warning Clear: An input undervoltage reported."
			--#TYPE "Warning Clear: An input undervoltage reported."
   --#SUMMARY "Warning Clear: An input undervoltage reported."
   --#SEVERITY INFORMATIONAL
   --#TIMEINDEX 1
   --#HELP ""
   --#HELPTAG 0
   --#STATE OPERATIONAL
    ::= 38

upsTrapInputFrequencyError TRAP-TYPE
    ENTERPRISE rmti3
    DESCRIPTION
        "Warning: An input frequency error reported."
			--#TYPE "Warning: An input frequency error reported."
   --#SUMMARY "Warning: An input frequency error reported."
   --#SEVERITY INFORMATIONAL
   --#TIMEINDEX 1
   --#HELP ""
   --#HELPTAG 0
   --#STATE OPERATIONAL
    ::= 39


upsTrapInputFrequencyErrorClear TRAP-TYPE
    ENTERPRISE rmti3
    DESCRIPTION
        "Warning Clear: An input frequency error reported."
		--#TYPE "Warning Clear: An input frequency error reported."
   --#SUMMARY "Warning Clear: An input frequency error reported."
   --#SEVERITY INFORMATIONAL
   --#TIMEINDEX 1
   --#HELP ""
   --#HELPTAG 0
   --#STATE OPERATIONAL
    ::= 40

upsTrapBypassOverVoltage TRAP-TYPE
    ENTERPRISE rmti3
    DESCRIPTION
        "Warning: A bypass overvoltage reported."
		--#TYPE "Warning: A bypass overvoltage reported."
   --#SUMMARY "Warning: A bypass overvoltage reported."
   --#SEVERITY INFORMATIONAL
   --#TIMEINDEX 1
   --#HELP ""
   --#HELPTAG 0
   --#STATE OPERATIONAL
    ::= 41

upsTrapBypassOverVoltageClear TRAP-TYPE
    ENTERPRISE rmti3
    DESCRIPTION
        "Warning Clear: A bypass overvoltage reported."
		--#TYPE "Warning Clear: A bypass overvoltage reported."
   --#SUMMARY "Warning Clear: A bypass overvoltage reported."
   --#SEVERITY INFORMATIONAL
   --#TIMEINDEX 1
   --#HELP ""
   --#HELPTAG 0
   --#STATE OPERATIONAL
    ::= 42

upsTrapBypassUnderVoltage TRAP-TYPE
    ENTERPRISE rmti3
    DESCRIPTION
        "Warning: A bypass undervoltage reported."
		--#TYPE "Warning: A bypass undervoltage reported."
   --#SUMMARY "Warning: A bypass undervoltage reported."
   --#SEVERITY INFORMATIONAL
   --#TIMEINDEX 1
   --#HELP ""
   --#HELPTAG 0
   --#STATE OPERATIONAL
    ::= 43

upsTrapBypassUnderVoltageClear TRAP-TYPE
    ENTERPRISE rmti3
    DESCRIPTION
        "Warning Clear: A bypass undervoltage reported."
		--#TYPE "Warning Clear: A bypass undervoltage reported."
   --#SUMMARY "Warning Clear: A bypass undervoltage reported."
   --#SEVERITY INFORMATIONAL
   --#TIMEINDEX 1
   --#HELP ""
   --#HELPTAG 0
   --#STATE OPERATIONAL
    ::= 44

upsTrapBypassFrequencyError TRAP-TYPE
    ENTERPRISE rmti3
    DESCRIPTION
        "Warning: A bypass frequency error reported."
		--#TYPE "Warning: A bypass frequency error reported."
   --#SUMMARY "Warning: A bypass frequency error reported."
   --#SEVERITY INFORMATIONAL
   --#TIMEINDEX 1
   --#HELP ""
   --#HELPTAG 0
   --#STATE OPERATIONAL
    ::= 45

upsTrapBypassFrequencyErrorClear TRAP-TYPE
    ENTERPRISE rmti3
    DESCRIPTION
        "Warning Clear: A bypass frequency error reported."
		--#TYPE "Warning Clear: A bypass frequency error reported."
   --#SUMMARY "Warning Clear: A bypass frequency error reported."
   --#SEVERITY INFORMATIONAL
   --#TIMEINDEX 1
   --#HELP ""
   --#HELPTAG 0
   --#STATE OPERATIONAL
    ::= 46

upsTrapDCUnderVoltageAtTest TRAP-TYPE
    ENTERPRISE rmti3
    DESCRIPTION
        "Warning: A DC bus undervoltage during battery test reported."
		--#TYPE "Warning: A DC bus undervoltage during battery test reported."
   --#SUMMARY "Warning: A DC bus undervoltage during battery test reported."
   --#SEVERITY INFORMATIONAL
   --#TIMEINDEX 1
   --#HELP ""
   --#HELPTAG 0
   --#STATE OPERATIONAL
    ::= 47

upsTrapDCUnderVoltageAtTestClear TRAP-TYPE
    ENTERPRISE rmti3
    DESCRIPTION
        "Warning Clear: A DC bus undervoltage during battery test reported."
		--#TYPE "Warning Clear: A DC bus undervoltage during battery test reported."
   --#SUMMARY "Warning Clear: A DC bus undervoltage during battery test reported."
   --#SEVERITY INFORMATIONAL
   --#TIMEINDEX 1
   --#HELP ""
   --#HELPTAG 0
   --#STATE OPERATIONAL
    ::= 48

upsTrapBatteryLow TRAP-TYPE
    ENTERPRISE rmti3
    DESCRIPTION
        "Warning: A low battery level reported."
		--#TYPE "Warning: A low battery level reported."
   --#SUMMARY "Warning: A low battery level reported."
   --#SEVERITY INFORMATIONAL
   --#TIMEINDEX 1
   --#HELP ""
   --#HELPTAG 0
   --#STATE OPERATIONAL
    ::= 49


upsTrapBatteryLowClear TRAP-TYPE
    ENTERPRISE rmti3
    DESCRIPTION
        "Warning Clear: A low battery level reported."
		--#TYPE "Warning Clear: A low battery level reported."
   --#SUMMARY "Warning Clear: A low battery level reported."
   --#SEVERITY INFORMATIONAL
   --#TIMEINDEX 1
   --#HELP ""
   --#HELPTAG 0
   --#STATE OPERATIONAL
    ::= 50

upsTrapBatteryAtShutdownlevel TRAP-TYPE
    ENTERPRISE rmti3
    DESCRIPTION
        "Warning: A shutdown battery level reported."
		--#TYPE "Warning: A shutdown battery level reported."
   --#SUMMARY "Warning: A shutdown battery level reported."
   --#SEVERITY INFORMATIONAL
   --#TIMEINDEX 1
   --#HELP ""
   --#HELPTAG 0
   --#STATE OPERATIONAL
    ::= 51

upsTrapBatteryAtShutdownlevelClear TRAP-TYPE
    ENTERPRISE rmti3
    DESCRIPTION
        "Warning Clear: A shutdown battery level reported."
		--#TYPE "Warning Clear: A shutdown battery level reported."
   --#SUMMARY "Warning Clear: A shutdown battery level reported."
   --#SEVERITY INFORMATIONAL
   --#TIMEINDEX 1
   --#HELP ""
   --#HELPTAG 0
   --#STATE OPERATIONAL
    ::= 52

upsTrapReplaceBattery TRAP-TYPE
    ENTERPRISE rmti3
    DESCRIPTION
        "Warning: A replacement of batteries reported."
		--#TYPE "Warning: A replacement of batteries reported."
   --#SUMMARY "Warning: A replacement of batteries reported."
   --#SEVERITY INFORMATIONAL
   --#TIMEINDEX 1
   --#HELP ""
   --#HELPTAG 0
   --#STATE OPERATIONAL
    ::= 53

upsTrapReplaceBatteryClear TRAP-TYPE
    ENTERPRISE rmti3
    DESCRIPTION
        "Warning Clear: A replacement of batteries reported."
		--#TYPE "Warning Clear: A replacement of batteries reported."
   --#SUMMARY "Warning Clear: A replacement of batteries reported."
   --#SEVERITY INFORMATIONAL
   --#TIMEINDEX 1
   --#HELP ""
   --#HELPTAG 0
   --#STATE OPERATIONAL
    ::= 54

upsTrapChargerOverVoltageWarning TRAP-TYPE
    ENTERPRISE rmti3
    DESCRIPTION
        "Warning: A charger overvoltage reported."
		--#TYPE "Warning: A charger overvoltage reported."
   --#SUMMARY "Warning: A charger overvoltage reported."
   --#SEVERITY INFORMATIONAL
   --#TIMEINDEX 1
   --#HELP ""
   --#HELPTAG 0
   --#STATE OPERATIONAL
    ::= 55

upsTrapChargerOverVoltageWarningClear TRAP-TYPE
    ENTERPRISE rmti3
    DESCRIPTION
        "Warning Clear: A charger overvoltage reported."
		--#TYPE "Warning Clear: A charger overvoltage reported."
   --#SUMMARY "Warning Clear: A charger overvoltage reported."
   --#SEVERITY INFORMATIONAL
   --#TIMEINDEX 1
   --#HELP ""
   --#HELPTAG 0
   --#STATE OPERATIONAL
    ::= 56

upsTrapBatteryTestFailed TRAP-TYPE
    ENTERPRISE rmti3
    DESCRIPTION
        "Warning: A battery test failed event reported."
		--#TYPE "Warning: A battery test failed event reported."
   --#SUMMARY "Warning: A battery test failed event reported."
   --#SEVERITY INFORMATIONAL
   --#TIMEINDEX 1
   --#HELP ""
   --#HELPTAG 0
   --#STATE OPERATIONAL
    ::= 57

upsTrapBatteryTestFailedClear TRAP-TYPE
    ENTERPRISE rmti3
    DESCRIPTION
        "Warning Clear: A battery test failed event reported."
		--#TYPE "Warning Clear: A battery test failed event reported."
   --#SUMMARY "Warning Clear: A battery test failed event reported."
   --#SEVERITY INFORMATIONAL
   --#TIMEINDEX 1
   --#HELP ""
   --#HELPTAG 0
   --#STATE OPERATIONAL
    ::= 58

upsTrapBatteryDepleted TRAP-TYPE
    ENTERPRISE rmti3
    DESCRIPTION
        "Warning: A battery depleted event reported."
		--#TYPE "Warning: A battery depleted event reported."
   --#SUMMARY "Warning: A battery depleted event reported."
   --#SEVERITY INFORMATIONAL
   --#TIMEINDEX 1
   --#HELP ""
   --#HELPTAG 0
   --#STATE OPERATIONAL
    ::= 59

upsTrapBatteryDepletedClear TRAP-TYPE
    ENTERPRISE rmti3
    DESCRIPTION
        "Warning Clear: A battery depleted event reported."
		--#TYPE "Warning Clear: A battery depleted event reported."
   --#SUMMARY "Warning Clear: A battery depleted event reported."
   --#SEVERITY INFORMATIONAL
   --#TIMEINDEX 1
   --#HELP ""
   --#HELPTAG 0
   --#STATE OPERATIONAL
    ::= 60

upsTrapBatteryOverheat TRAP-TYPE
    ENTERPRISE rmti3
    DESCRIPTION
        "Warning: A battery overheat reported."
		--#TYPE "Warning: A battery overheat reported."
   --#SUMMARY "Warning: A battery overheat reported."
   --#SEVERITY INFORMATIONAL
   --#TIMEINDEX 1
   --#HELP ""
   --#HELPTAG 0
   --#STATE OPERATIONAL
    ::= 61

upsTrapBatteryOverheatClear TRAP-TYPE
    ENTERPRISE rmti3
    DESCRIPTION
        "Warning Clear: A battery overheat reported."
		--#TYPE "Warning Clear: A battery overheat reported."
   --#SUMMARY "Warning Clear: A battery overheat reported."
   --#SEVERITY INFORMATIONAL
   --#TIMEINDEX 1
   --#HELP ""
   --#HELPTAG 0
   --#STATE OPERATIONAL
    ::= 62

upsTrapSystemOverheat TRAP-TYPE
    ENTERPRISE rmti3
    DESCRIPTION
        "Warning: A system overheat reported."
		--#TYPE "Warning: A system overheat reported."
   --#SUMMARY "Warning: A system overheat reported."
   --#SEVERITY INFORMATIONAL
   --#TIMEINDEX 1
   --#HELP ""
   --#HELPTAG 0
   --#STATE OPERATIONAL
    ::= 63

upsTrapSystemOverheatClear TRAP-TYPE
    ENTERPRISE rmti3
    DESCRIPTION
        "Warning Clear: A system overheat reported."
		--#TYPE "Warning Clear: A system overheat reported."
   --#SUMMARY "Warning Clear: A system overheat reported."
   --#SEVERITY INFORMATIONAL
   --#TIMEINDEX 1
   --#HELP ""
   --#HELPTAG 0
   --#STATE OPERATIONAL
    ::= 64

upsTrapOutputOverloadWarning TRAP-TYPE
    ENTERPRISE rmti3
    DESCRIPTION
        "Warning: An output overload reported."
		--#TYPE "Warning: An output overload reported."
   --#SUMMARY "Warning: An output overload reported."
   --#SEVERITY INFORMATIONAL
   --#TIMEINDEX 1
   --#HELP ""
   --#HELPTAG 0
   --#STATE OPERATIONAL
    ::= 65

upsTrapOutputOverloadWarningClear TRAP-TYPE
    ENTERPRISE rmti3
    DESCRIPTION
        "Warning Clear: An output overload reported."
			--#TYPE "Warning Clear: An output overload reported."
   --#SUMMARY "Warning Clear: An output overload reported."
   --#SEVERITY INFORMATIONAL
   --#TIMEINDEX 1
   --#HELP ""
   --#HELPTAG 0
   --#STATE OPERATIONAL
    ::= 66

upsTrapCurrentLimitWarning TRAP-TYPE
    ENTERPRISE rmti3
    DESCRIPTION
        "Warning: A current limit reported."
			--#TYPE "Warning: A current limit reported."
   --#SUMMARY "Warning: A current limit reported."
   --#SEVERITY INFORMATIONAL
   --#TIMEINDEX 1
   --#HELP ""
   --#HELPTAG 0
   --#STATE OPERATIONAL
    ::= 67

upsTrapCurrentLimitWarningClear TRAP-TYPE
    ENTERPRISE rmti3
    DESCRIPTION
        "Warning Clear: A current limit reported."
		--#TYPE "Warning Clear: A current limit reported."
   --#SUMMARY "Warning Clear: A current limit reported."
   --#SEVERITY INFORMATIONAL
   --#TIMEINDEX 1
   --#HELP ""
   --#HELPTAG 0
   --#STATE OPERATIONAL
    ::= 68

upsTrapAsyncOperation TRAP-TYPE
    ENTERPRISE rmti3
    DESCRIPTION
        "Warning: An Asynchronous operation reported."
		--#TYPE "Warning: An Asynchronous operation reported."
   --#SUMMARY "Warning: An Asynchronous operation reported."
   --#SEVERITY INFORMATIONAL
   --#TIMEINDEX 1
   --#HELP ""
   --#HELPTAG 0
   --#STATE OPERATIONAL
    ::= 69

upsTrapAsyncOperationClear TRAP-TYPE
    ENTERPRISE rmti3
    DESCRIPTION
        "Warning Clear: An Asynchronous operation reported."
		--#TYPE "Warning Clear: An Asynchronous operation reported."
   --#SUMMARY "Warning Clear: An Asynchronous operation reported."
   --#SEVERITY INFORMATIONAL
   --#TIMEINDEX 1
   --#HELP ""
   --#HELPTAG 0
   --#STATE OPERATIONAL
    ::= 70

upsTrapServiceUPS TRAP-TYPE
    ENTERPRISE rmti3
    DESCRIPTION
        "Warning: UPS is in need of service."
		--#TYPE "Warning: UPS is in need of service."
   --#SUMMARY "Warning: UPS is in need of service."
   --#SEVERITY INFORMATIONAL
   --#TIMEINDEX 1
   --#HELP ""
   --#HELPTAG 0
   --#STATE OPERATIONAL
    ::= 71

upsTrapServiceUPSClear TRAP-TYPE
    ENTERPRISE rmti3
    DESCRIPTION
        "Warning Clear: UPS is in need of service."
			--#TYPE "Warning Clear: UPS is in need of service."
   --#SUMMARY "Warning Clear: UPS is in need of service."
   --#SEVERITY INFORMATIONAL
   --#TIMEINDEX 1
   --#HELP ""
   --#HELPTAG 0
   --#STATE OPERATIONAL
    ::= 72

upsTrapBatteryNearExpiration TRAP-TYPE
    ENTERPRISE rmti3
    DESCRIPTION
        "Warning: A near expiration of batteries reported."
			--#TYPE "Warning: A near expiration of batteries reported."
   --#SUMMARY "Warning: A near expiration of batteries reported."
   --#SEVERITY INFORMATIONAL
   --#TIMEINDEX 1
   --#HELP ""
   --#HELPTAG 0
   --#STATE OPERATIONAL
    ::= 73

upsTrapBatteryNearExpirationClear TRAP-TYPE
    ENTERPRISE rmti3
    DESCRIPTION
        "Warning Clear: A near expiration of batteries reported."
		--#TYPE "Warning Clear: A near expiration of batteries reported."
   --#SUMMARY "Warning Clear: A near expiration of batteries reported."
   --#SEVERITY INFORMATIONAL
   --#TIMEINDEX 1
   --#HELP ""
   --#HELPTAG 0
   --#STATE OPERATIONAL
    ::= 74

upsTrapBatteryExpired TRAP-TYPE
    ENTERPRISE rmti3
    DESCRIPTION
        "Warning: A expiration of batteries reported."
		--#TYPE "Warning: A expiration of batteries reported."
   --#SUMMARY "Warning: A expiration of batteries reported."
   --#SEVERITY INFORMATIONAL
   --#TIMEINDEX 1
   --#HELP ""
   --#HELPTAG 0
   --#STATE OPERATIONAL
    ::= 75

upsTrapBatteryExpiredClear TRAP-TYPE
    ENTERPRISE rmti3
    DESCRIPTION
        "Warning Clear: A expiration of batteries reported."
		--#TYPE "Warning Clear: A expiration of batteries reported."
   --#SUMMARY "Warning Clear: A expiration of batteries reported."
   --#SEVERITY INFORMATIONAL
   --#TIMEINDEX 1
   --#HELP ""
   --#HELPTAG 0
   --#STATE OPERATIONAL
    ::= 76

upsTrapDisplayCableError TRAP-TYPE
    ENTERPRISE rmti3
    DESCRIPTION
        "Warning: A display cable error reported."
		--#TYPE "Warning: A display cable error reported."
   --#SUMMARY "Warning: A display cable error reported."
   --#SEVERITY INFORMATIONAL
   --#TIMEINDEX 1
   --#HELP ""
   --#HELPTAG 0
   --#STATE OPERATIONAL
    ::= 77

upsTrapDisplayCableErrorClear TRAP-TYPE
    ENTERPRISE rmti3
    DESCRIPTION
        "Warning Clear: A display cable error reported."
		--#TYPE "Warning Clear: A display cable error reported."
   --#SUMMARY "Warning Clear: A display cable error reported."
   --#SEVERITY INFORMATIONAL
   --#TIMEINDEX 1
   --#HELP ""
   --#HELPTAG 0
   --#STATE OPERATIONAL
    ::= 78

upsTrapRemotEyeCommError TRAP-TYPE
    ENTERPRISE rmti3
    DESCRIPTION
        "Warning: A communication error between the main control and the RemotEye III reported."
		--#TYPE "Warning: A communication error between the main control and the RemotEye III reported."
   --#SUMMARY "Warning: A communication error between the main control and the RemotEye III reported."
   --#SEVERITY INFORMATIONAL
   --#TIMEINDEX 1
   --#HELP ""
   --#HELPTAG 0
   --#STATE OPERATIONAL
    ::= 79

upsTrapRemotEyeCommErrorClear TRAP-TYPE
    ENTERPRISE rmti3
    DESCRIPTION
        "Warning Clear: A communication error between the main control and the RemotEye III reported."
		--#TYPE "Warning Clear: A communication error between the main control and the RemotEye III reported."
   --#SUMMARY "Warning Clear: A communication error between the main control and the RemotEye III reported."
   --#SEVERITY INFORMATIONAL
   --#TIMEINDEX 1
   --#HELP ""
   --#HELPTAG 0
   --#STATE OPERATIONAL
    ::= 80

upsTrapRemotEyeUplinkCommError TRAP-TYPE
    ENTERPRISE rmti3
    DESCRIPTION
        "Warning: A communication error between the RemotEye III and the network reported."
		--#TYPE "Warning: A communication error between the RemotEye III and the network reported."
   --#SUMMARY "Warning: A communication error between the RemotEye III and the network reported."
   --#SEVERITY INFORMATIONAL
   --#TIMEINDEX 1
   --#HELP ""
   --#HELPTAG 0
   --#STATE OPERATIONAL
    ::= 81

upsTrapRemotEyeUplinkCommErrorClear TRAP-TYPE
    ENTERPRISE rmti3
    DESCRIPTION
        "Warning Clear: A communication error between the RemotEye III and the network reported."
			--#TYPE "Warning Clear: A communication error between the RemotEye III and the network reported."
   --#SUMMARY "Warning Clear: A communication error between the RemotEye III and the network reported."
   --#SEVERITY INFORMATIONAL
   --#TIMEINDEX 1
   --#HELP ""
   --#HELPTAG 0
   --#STATE OPERATIONAL
    ::= 82

upsTrapServicePortCommError TRAP-TYPE
    ENTERPRISE rmti3
    DESCRIPTION
        "Warning: A communication error between the main controller and the service port reported."
			--#TYPE "Warning: A communication error between the main controller and the service port reported."
   --#SUMMARY "Warning: A communication error between the main controller and the service port reported."
   --#SEVERITY INFORMATIONAL
   --#TIMEINDEX 1
   --#HELP ""
   --#HELPTAG 0
   --#STATE OPERATIONAL
    ::= 83

upsTrapServicePortCommErrorClear TRAP-TYPE
    ENTERPRISE rmti3
    DESCRIPTION
        "Warning Clear: A communication error between the main controller and the service port reported."
			--#TYPE "Warning Clear: A communication error between the main controller and the service port reported."
   --#SUMMARY "Warning Clear: A communication error between the main controller and the service port reported."
   --#SEVERITY INFORMATIONAL
   --#TIMEINDEX 1
   --#HELP ""
   --#HELPTAG 0
   --#STATE OPERATIONAL
    ::= 84

upsTrapDispCommError TRAP-TYPE
    ENTERPRISE rmti3
    DESCRIPTION
        "Warning: A communication error between the main controller and the display controller reported."
	--#TYPE "Warning: A communication error between the main controller and the display controller reported."
   --#SUMMARY "Warning: A communication error between the main controller and the display controller reported."
   --#SEVERITY INFORMATIONAL
   --#TIMEINDEX 1
   --#HELP ""
   --#HELPTAG 0
   --#STATE OPERATIONAL
    ::= 85

upsTrapDispCommErrorClear TRAP-TYPE
    ENTERPRISE rmti3
    DESCRIPTION
        "Warning Clear: A communication error between the main controller and the display controller reported."
	--#TYPE "Warning Clear: A communication error between the main controller and the display controller reported."
   --#SUMMARY "Warning Clear: A communication error between the main controller and the display controller reported."
   --#SEVERITY INFORMATIONAL
   --#TIMEINDEX 1
   --#HELP ""
   --#HELPTAG 0
   --#STATE OPERATIONAL
    ::= 86

upsTrapSystemTestFailed TRAP-TYPE
    ENTERPRISE rmti3
    DESCRIPTION
        "Warning: A system test failed event reported."
	--#TYPE "Warning: A system test failed event reported."
   --#SUMMARY "Warning: A system test failed event reported."
   --#SEVERITY INFORMATIONAL
   --#TIMEINDEX 1
   --#HELP ""
   --#HELPTAG 0
   --#STATE OPERATIONAL
    ::= 87

upsTrapSystemTestFailedClear TRAP-TYPE
    ENTERPRISE rmti3
    DESCRIPTION
        "Warning Clear: A system test failed event reported."
		--#TYPE "Warning Clear: A system test failed event reported."
   --#SUMMARY "Warning Clear: A system test failed event reported."
   --#SEVERITY INFORMATIONAL
   --#TIMEINDEX 1
   --#HELP ""
   --#HELPTAG 0
   --#STATE OPERATIONAL
    ::= 88

upsTrapBypassOn TRAP-TYPE
    ENTERPRISE rmti3
    DESCRIPTION
        "Warning: The UPS is in Stop (Bypass) mode."
		--#TYPE "Info: The UPS is in Stop (Bypass) mode."
   --#SUMMARY "Info: The UPS is in Stop (Bypass) mode."
   --#SEVERITY INFORMATIONAL
   --#TIMEINDEX 1
   --#HELP ""
   --#HELPTAG 0
   --#STATE OPERATIONAL
    ::= 89

upsTrapBypassOnClear TRAP-TYPE
    ENTERPRISE rmti3
    DESCRIPTION
        "Warning Clear: The UPS is in Stop (Bypass) mode."
		--#TYPE "Info Clear: The UPS is in Stop (Bypass) mode."
   --#SUMMARY "Info Clear: The UPS is in Stop (Bypass) mode."
   --#SEVERITY INFORMATIONAL
   --#TIMEINDEX 1
   --#HELP ""
   --#HELPTAG 0
   --#STATE OPERATIONAL
    ::= 90

upsTrapPowerFailure TRAP-TYPE
    ENTERPRISE rmti3
    DESCRIPTION
        "Info: A power failure reported."
		--#TYPE "Info: A power failure reported."
   --#SUMMARY "Info: A power failure reported."
   --#SEVERITY INFORMATIONAL
   --#TIMEINDEX 1
   --#HELP ""
   --#HELPTAG 0
   --#STATE OPERATIONAL
    ::= 91

upsTrapPowerFailureClear TRAP-TYPE
    ENTERPRISE rmti3
    DESCRIPTION
        "Info Clear: A power failure reported."
			--#TYPE "Info Clear: A power failure reported."
   --#SUMMARY "Info Clear: A power failure reported."
   --#SEVERITY INFORMATIONAL
   --#TIMEINDEX 1
   --#HELP ""
   --#HELPTAG 0
   --#STATE OPERATIONAL
    ::= 92

upsTrapShutdownPending TRAP-TYPE
    ENTERPRISE rmti3
    DESCRIPTION
        "Info: A output shutdown in progress reported. Output will turn off after delay."
			--#TYPE "Info: A output shutdown in progress reported. Output will turn off after delay."
   --#SUMMARY "Info: A output shutdown in progress reported. Output will turn off after delay."
   --#SEVERITY INFORMATIONAL
   --#TIMEINDEX 1
   --#HELP ""
   --#HELPTAG 0
   --#STATE OPERATIONAL
    ::= 93

upsTrapShutdownPendingClear TRAP-TYPE
    ENTERPRISE rmti3
    DESCRIPTION
        "Info Clear: A output shutdown in progress reported. Output will turn off after delay."
				--#TYPE "Info Clear: A output shutdown in progress reported. Output will turn off after delay."
   --#SUMMARY "Info Clear: A output shutdown in progress reported. Output will turn off after delay."
   --#SEVERITY INFORMATIONAL
   --#TIMEINDEX 1
   --#HELP ""
   --#HELPTAG 0
   --#STATE OPERATIONAL
    ::= 94

upsTrapOutputOffAsRequested TRAP-TYPE
    ENTERPRISE rmti3
    DESCRIPTION
        "Info: An output shutdown mode requested."
	--#TYPE "Info: An output shutdown mode requested."
   --#SUMMARY "Info: An output shutdown mode requested."
   --#SEVERITY INFORMATIONAL
   --#TIMEINDEX 1
   --#HELP ""
   --#HELPTAG 0
   --#STATE OPERATIONAL
    ::= 95

upsTrapOutputOffAsRequestedClear TRAP-TYPE
    ENTERPRISE rmti3
    DESCRIPTION
        "Info Clear: An output shutdown mode requested."
		--#TYPE "Info Clear: An output shutdown mode requested."
   --#SUMMARY "Info Clear: An output shutdown mode requested."
   --#SEVERITY INFORMATIONAL
   --#TIMEINDEX 1
   --#HELP ""
   --#HELPTAG 0
   --#STATE OPERATIONAL
    ::= 96

upsTrapOutputOff TRAP-TYPE
    ENTERPRISE rmti3
    DESCRIPTION
        "Info: The UPS system output is off."
		--#TYPE "Info: The UPS system output is off."
   --#SUMMARY "Info: The UPS system output is off."
   --#SEVERITY INFORMATIONAL
   --#TIMEINDEX 1
   --#HELP ""
   --#HELPTAG 0
   --#STATE OPERATIONAL
    ::= 97

upsTrapOutputOffClear TRAP-TYPE
    ENTERPRISE rmti3
    DESCRIPTION
        "Info Clear: The UPS system output is off."
		--#TYPE "Info Clear: The UPS system output is off."
   --#SUMMARY "Info Clear: The UPS system output is off."
   --#SEVERITY INFORMATIONAL
   --#TIMEINDEX 1
   --#HELP ""
   --#HELPTAG 0
   --#STATE OPERATIONAL
    ::= 98

upsTrapBatteryTestInProgress TRAP-TYPE
    ENTERPRISE rmti3
    DESCRIPTION
        "Info: A battery test in progress reported."
		--#TYPE "Info: A battery test in progress reported."
   --#SUMMARY "Info: A battery test in progress reported."
   --#SEVERITY INFORMATIONAL
   --#TIMEINDEX 1
   --#HELP ""
   --#HELPTAG 0
   --#STATE OPERATIONAL
    ::= 99

upsTrapBatteryTestInProgressClear TRAP-TYPE
    ENTERPRISE rmti3
    DESCRIPTION
        "Info Clear: A battery test in progress reported."
		--#TYPE "Info Clear: A battery test in progress reported."
   --#SUMMARY "Info Clear: A battery test in progress reported."
   --#SEVERITY INFORMATIONAL
   --#TIMEINDEX 1
   --#HELP ""
   --#HELPTAG 0
   --#STATE OPERATIONAL
    ::= 100

upsTrapBatteryOn TRAP-TYPE
    ENTERPRISE rmti3
    DESCRIPTION
        "Info: The UPS is on Battery mode; it is supplying output power from its batteries."
		 --#TYPE "Info: The UPS is on Battery mode; it is supplying output power from  its batteries."
   --#SUMMARY "Info: The UPS is on Battery mode; it is supplying output power from its batteries."
   --#SEVERITY INFORMATIONAL
   --#TIMEINDEX 1
   --#HELP ""
   --#HELPTAG 0
   --#STATE OPERATIONAL
    ::= 101

upsTrapBatteryOnClear TRAP-TYPE
    ENTERPRISE rmti3
    DESCRIPTION
        "Info Clear: The UPS is on Battery mode; it is supplying output power from its batteries."
		 --#TYPE "Info Clear: The UPS is on Battery mode; it is supplying output power from its batteries."
   --#SUMMARY "Info Clear: The UPS is on Battery mode; it is supplying output power from its batteries."
   --#SEVERITY INFORMATIONAL
   --#TIMEINDEX 1
   --#HELP ""
   --#HELPTAG 0
   --#STATE OPERATIONAL
    ::= 102

upsTrapEMDSensor1AlarmTriggered TRAP-TYPE
    ENTERPRISE rmti3
    DESCRIPTION
        "Warning: EMD sensor 1 alarm is triggered."
		--#TYPE "Warning: EMD sensor 1 alarm is triggered."
   --#SUMMARY "Warning: EMD sensor 1 alarm is triggered."
   --#SEVERITY INFORMATIONAL
   --#TIMEINDEX 1
   --#HELP ""
   --#HELPTAG 0
   --#STATE OPERATIONAL
    ::= 103

upsTrapEMDSensor1AlarmTriggeredClear TRAP-TYPE
    ENTERPRISE rmti3
    DESCRIPTION
        "Warning Clear: EMD sensor 1 alarm is triggered."
		--#TYPE "Warning Clear: EMD sensor 1 alarm is triggered."
   --#SUMMARY "Warning Clear: EMD sensor 1 alarm is triggered."
   --#SEVERITY INFORMATIONAL
   --#TIMEINDEX 1
   --#HELP ""
   --#HELPTAG 0
   --#STATE OPERATIONAL
    ::= 104

upsTrapEMDSensor2AlarmTriggered TRAP-TYPE
    ENTERPRISE rmti3
    DESCRIPTION
        "Warning: EMD sensor 2 alarm is triggered."
		--#TYPE "Warning: EMD sensor 2 alarm is triggered."
   --#SUMMARY "Warning: EMD sensor 2 alarm is triggered."
   --#SEVERITY INFORMATIONAL
   --#TIMEINDEX 1
   --#HELP ""
   --#HELPTAG 0
   --#STATE OPERATIONAL
    ::= 105

upsTrapEMDSensor2AlarmTriggeredClear TRAP-TYPE
    ENTERPRISE rmti3
    DESCRIPTION
        "Warning Clear: EMD sensor 2 alarm is triggered."
		--#TYPE "Warning Clear: EMD sensor 2 alarm is triggered."
   --#SUMMARY "Warning Clear: EMD sensor 2 alarm is triggered."
   --#SEVERITY INFORMATIONAL
   --#TIMEINDEX 1
   --#HELP ""
   --#HELPTAG 0
   --#STATE OPERATIONAL
    ::= 106

upsTrapEMDHumidityAtLowCiriticalPoint TRAP-TYPE
    ENTERPRISE rmti3
    DESCRIPTION
        "Warning: EMD humidity is at low critical point."
		--#TYPE "Warning: EMD humidity is at low critical point."
   --#SUMMARY "Warning: EMD humidity is at low critical point."
   --#SEVERITY INFORMATIONAL
   --#TIMEINDEX 1
   --#HELP ""
   --#HELPTAG 0
   --#STATE OPERATIONAL
    ::= 107

upsTrapEMDHumidityAtLowCiriticalPointClear TRAP-TYPE
    ENTERPRISE rmti3
    DESCRIPTION
        "Warning Clear: EMD humidity is at low critical point."
		--#TYPE "Warning Clear: EMD humidity is at low critical point."
   --#SUMMARY "Warning Clear: EMD humidity is at low critical point."
   --#SEVERITY INFORMATIONAL
   --#TIMEINDEX 1
   --#HELP ""
   --#HELPTAG 0
   --#STATE OPERATIONAL
    ::= 108

upsTrapEMDHumidityAtHighCiriticalPoint TRAP-TYPE
    ENTERPRISE rmti3
    DESCRIPTION
        "Warning: EMD humidity is at high critical point."
		--#TYPE "Warning: EMD humidity is at high critical point."
   --#SUMMARY "Warning: EMD humidity is at high critical point."
   --#SEVERITY INFORMATIONAL
   --#TIMEINDEX 1
   --#HELP ""
   --#HELPTAG 0
   --#STATE OPERATIONAL
    ::= 109

upsTrapEMDHumidityAtHighCiriticalPointClear TRAP-TYPE
    ENTERPRISE rmti3
    DESCRIPTION
        "Warning Clear: EMD humidity is at high critical point."
		--#TYPE "Warning Clear: EMD humidity is at high critical point."
   --#SUMMARY "Warning Clear: EMD humidity is at high critical point."
   --#SEVERITY INFORMATIONAL
   --#TIMEINDEX 1
   --#HELP ""
   --#HELPTAG 0
   --#STATE OPERATIONAL
    ::= 110

upsTrapEMDHumidityAtLowWarningPoint TRAP-TYPE
    ENTERPRISE rmti3
    DESCRIPTION
        "Warning: EMD humidity is at low warning point."
		--#TYPE "Warning: EMD humidity is at low warning point."
   --#SUMMARY "Warning: EMD humidity is at low warning point."
   --#SEVERITY INFORMATIONAL
   --#TIMEINDEX 1
   --#HELP ""
   --#HELPTAG 0
   --#STATE OPERATIONAL
    ::= 111

upsTrapEMDHumidityAtLowWarningPointClear TRAP-TYPE
    ENTERPRISE rmti3
    DESCRIPTION
        "Warning Clear: EMD humidity is at low warning point."
		--#TYPE "Warning Clear: EMD humidity is at low warning point."
   --#SUMMARY "Warning Clear: EMD humidity is at low warning point."
   --#SEVERITY INFORMATIONAL
   --#TIMEINDEX 1
   --#HELP ""
   --#HELPTAG 0
   --#STATE OPERATIONAL
    ::= 112

upsTrapEMDHumidityAtHighWarningPoint TRAP-TYPE
    ENTERPRISE rmti3
    DESCRIPTION
        "Warning: EMD humidity is at high warning point."
		--#TYPE "Warning: EMD humidity is at high warning point."
   --#SUMMARY "Warning: EMD humidity is at high warning point."
   --#SEVERITY INFORMATIONAL
   --#TIMEINDEX 1
   --#HELP ""
   --#HELPTAG 0
   --#STATE OPERATIONAL
    ::= 113

upsTrapEMDHumidityAtHighWarningPointClear TRAP-TYPE
    ENTERPRISE rmti3
    DESCRIPTION
        "Warning Clear: EMD humidity is at high warning point."
		--#TYPE "Warning Clear: EMD humidity is at high warning point."
   --#SUMMARY "Warning Clear: EMD humidity is at high warning point."
   --#SEVERITY INFORMATIONAL
   --#TIMEINDEX 1
   --#HELP ""
   --#HELPTAG 0
   --#STATE OPERATIONAL
    ::= 114

upsTrapEMDTemperatureAtLowCiriticalPoint TRAP-TYPE
    ENTERPRISE rmti3
    DESCRIPTION
        "Warning: EMD Temperature is at low critical point."
		--#TYPE "Warning: EMD Temperature is at low critical point."
   --#SUMMARY "Warning: EMD Temperature is at low critical point."
   --#SEVERITY INFORMATIONAL
   --#TIMEINDEX 1
   --#HELP ""
   --#HELPTAG 0
   --#STATE OPERATIONAL
    ::= 115

upsTrapEMDTemperatureAtLowCiriticalPointClear TRAP-TYPE
    ENTERPRISE rmti3
    DESCRIPTION
        "Warning Clear: EMD Temperature is at low critical point."
		--#TYPE "Warning Clear: EMD Temperature is at low critical point."
   --#SUMMARY "Warning Clear: EMD Temperature is at low critical point."
   --#SEVERITY INFORMATIONAL
   --#TIMEINDEX 1
   --#HELP ""
   --#HELPTAG 0
   --#STATE OPERATIONAL
    ::= 116

upsTrapEMDTemperatureAtHighCiriticalPoint TRAP-TYPE
    ENTERPRISE rmti3
    DESCRIPTION
        "Warning: EMD Temperature is at high critical point."
	--#TYPE "Warning: EMD Temperature is at high critical point."
   --#SUMMARY "Warning: EMD Temperature is at high critical point."
   --#SEVERITY INFORMATIONAL
   --#TIMEINDEX 1
   --#HELP ""
   --#HELPTAG 0
   --#STATE OPERATIONAL
    ::= 117

upsTrapEMDTemperatureAtHighCiriticalPointClear TRAP-TYPE
    ENTERPRISE rmti3
    DESCRIPTION
        "Warning Clear: EMD Temperature is at high critical point."
		--#TYPE "Warning Clear: EMD Temperature is at high critical point."
   --#SUMMARY "Warning Clear: EMD Temperature is at high critical point."
   --#SEVERITY INFORMATIONAL
   --#TIMEINDEX 1
   --#HELP ""
   --#HELPTAG 0
   --#STATE OPERATIONAL
    ::= 118

upsTrapEMDTemperatureAtLowWarningPoint TRAP-TYPE
    ENTERPRISE rmti3
    DESCRIPTION
        "Warning: EMD Temperature is at low warning point."
		--#TYPE "Warning: EMD Temperature is at low warning point."
   --#SUMMARY "Warning: EMD Temperature is at low warning point."
   --#SEVERITY INFORMATIONAL
   --#TIMEINDEX 1
   --#HELP ""
   --#HELPTAG 0
   --#STATE OPERATIONAL
    ::= 119

upsTrapEMDTemperatureAtLowWarningPointClear TRAP-TYPE
    ENTERPRISE rmti3
    DESCRIPTION
        "Warning Clear: EMD Temperature is at low warning point."
		--#TYPE "Warning Clear: EMD Temperature is at low warning point."
   --#SUMMARY "Warning Clear: EMD Temperature is at low warning point."
   --#SEVERITY INFORMATIONAL
   --#TIMEINDEX 1
   --#HELP ""
   --#HELPTAG 0
   --#STATE OPERATIONAL
    ::= 120

upsTrapEMDTemperatureAtHighWarningPoint TRAP-TYPE
    ENTERPRISE rmti3
    DESCRIPTION
        "Warning: EMD Temperature is at high warning point."
		--#TYPE "Warning: EMD Temperature is at high warning point."
   --#SUMMARY "Warning: EMD Temperature is at high warning point."
   --#SEVERITY INFORMATIONAL
   --#TIMEINDEX 1
   --#HELP ""
   --#HELPTAG 0
   --#STATE OPERATIONAL
    ::= 121

upsTrapEMDTemperatureAtHighWarningPointClear TRAP-TYPE
    ENTERPRISE rmti3
    DESCRIPTION
        "Warning Clear: EMD Temperature is at high warning point."
		--#TYPE "Warning Clear: EMD Temperature is at high warning point."
   --#SUMMARY "Warning Clear: EMD Temperature is at high warning point."
   --#SEVERITY INFORMATIONAL
   --#TIMEINDEX 1
   --#HELP ""
   --#HELPTAG 0
   --#STATE OPERATIONAL
    ::= 122

upsTrapLogInError TRAP-TYPE
    ENTERPRISE rmti3
    DESCRIPTION
        "Info: Username/Password information is incorrect."
		--#TYPE "Info: Username/Password information is incorrect."
   --#SUMMARY "Info: Username/Password information is incorrect."
   --#SEVERITY INFORMATIONAL
   --#TIMEINDEX 1
   --#HELP ""
   --#HELPTAG 0
   --#STATE OPERATIONAL
    ::= 123

upsTrapLogInErrorClear TRAP-TYPE
    ENTERPRISE rmti3
    DESCRIPTION
        "Info Clear: Username/Password information is incorrect."
	--#TYPE "Info Clear: Username/Password information is incorrect."
   --#SUMMARY "Info Clear: Username/Password information is incorrect."
   --#SEVERITY INFORMATIONAL
   --#TIMEINDEX 1
   --#HELP ""
   --#HELPTAG 0
   --#STATE OPERATIONAL
    ::= 124
END
