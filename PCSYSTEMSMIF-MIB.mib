PCSYSTEMSMIF-MIB DEFINITIONS ::= BEGIN


 -- This is the result of the Systems Working Group effort to define major
 -- system components. The definitions are not intended to be exhaustive
 -- nor are all possible groups listed. Additional work should be done by
 -- new working groups to further define these components. Each of the above
 -- physical components will have a corresponding MIF group in each company
 -- System component.

IMPORTS
    OBJECT-TYPE
    FROM RFC-1212
    Counter, enterprises
    FROM RFC1155-SMI
    DisplayString
    FROM RFC1213-MIB;

DmiCounter                      ::= INTEGER (0..4294967295)
DmiInteger                      ::= INTEGER
DmiInteger64            ::= INTEGER (-18446744073709551615..18446744073709551615)
DmiOctetstring          ::= OCTET STRING
DmiDisplaystring        ::= DisplayString
DmiDate                         ::= OCTET STRING (SIZE (28))
DmiComponentIndex       ::= INTEGER

ibm			OBJECT IDENTIFIER ::= { enterprises 2 }
ibmProd                 OBJECT IDENTIFIER ::= { ibm 6 }
netFinity               OBJECT IDENTIFIER ::= { ibmProd 71 }
dmiMibs			OBJECT IDENTIFIER ::= { netFinity 200 }
netFinitySystemsMIB     OBJECT IDENTIFIER ::= { dmiMibs 1 }

dmtfGroups1              OBJECT IDENTIFIER ::= {netFinitySystemsMIB 1}

SComponentid ::= SEQUENCE {
        a1Manufacturer                                  DmiDisplaystring,
        a1Product                                       DmiDisplaystring,
        a1Version                                       DmiDisplaystring,
        a1SerialNumber                                  DmiDisplaystring
}

tComponentid1 OBJECT-TYPE
        SYNTAX          SEQUENCE OF SComponentid
        ACCESS          not-accessible
        STATUS          mandatory
        DESCRIPTION     "This group defines the attributes common to all components.
This group is required."
        ::= {dmtfGroups1 1}

eComponentid1 OBJECT-TYPE
        SYNTAX          SComponentid
        ACCESS          not-accessible
        STATUS          mandatory
        DESCRIPTION     ""
        --INDEX           {DmiComponentIndex}
        ::= {tComponentid1 1}

a1Manufacturer OBJECT-TYPE
        SYNTAX          DmiDisplaystring
        ACCESS          read-only
        STATUS          mandatory
        DESCRIPTION     "Manufacturer of this system described by this component."
        ::= {eComponentid1 1}

a1Product OBJECT-TYPE
        SYNTAX          DmiDisplaystring
        ACCESS          read-only
        STATUS          mandatory
        DESCRIPTION     "Product name for the system described by this component."
        ::= {eComponentid1 2}

a1Version OBJECT-TYPE
        SYNTAX          DmiDisplaystring
        ACCESS          read-only
        STATUS          mandatory
        DESCRIPTION     "Version number of this component."
        ::= {eComponentid1 3}

a1SerialNumber OBJECT-TYPE
        SYNTAX          DmiDisplaystring
        ACCESS          read-only
        STATUS          mandatory
        DESCRIPTION     "Serial number for the system described by this component."
        ::= {eComponentid1 4}

SGeneralInformation ::= SEQUENCE {
        a2SystemName                                    DmiDisplaystring,
        a2SystemLocation                                DmiDisplaystring,
        a2SystemPrimaryUserName                         DmiDisplaystring,
        a2SystemPrimaryUserPhone                        DmiDisplaystring,
        a2SystemBootUpTime                              DmiDate,
        a2SystemDateTime                                DmiDate
}

tGeneralInformation OBJECT-TYPE
        SYNTAX          SEQUENCE OF SGeneralInformation
        ACCESS          not-accessible
        STATUS          mandatory
        DESCRIPTION     "This group defines general information about this system."
        ::= {dmtfGroups1 2}

eGeneralInformation OBJECT-TYPE
        SYNTAX          SGeneralInformation
        ACCESS          not-accessible
        STATUS          mandatory
        DESCRIPTION     ""
        --INDEX           {DmiComponentIndex}
        ::= {tGeneralInformation 1}

a2SystemName OBJECT-TYPE
        SYNTAX          DmiDisplaystring
        ACCESS          read-write
        STATUS          mandatory
        DESCRIPTION     "A name to identify this system."
        ::= {eGeneralInformation 1}

a2SystemLocation OBJECT-TYPE
        SYNTAX          DmiDisplaystring
        ACCESS          read-write
        STATUS          mandatory
        DESCRIPTION     "The physical location of this system."
        ::= {eGeneralInformation 2}

a2SystemPrimaryUserName OBJECT-TYPE
        SYNTAX          DmiDisplaystring
        ACCESS          read-write
        STATUS          mandatory
        DESCRIPTION     "The name of the primary user or owner of this system."
        ::= {eGeneralInformation 3}

a2SystemPrimaryUserPhone OBJECT-TYPE
        SYNTAX          DmiDisplaystring
        ACCESS          read-write
        STATUS          mandatory
        DESCRIPTION     "The phone number of the primary user of this system."
        ::= {eGeneralInformation 4}

a2SystemBootUpTime OBJECT-TYPE
        SYNTAX          DmiDate
        ACCESS          read-only
        STATUS          mandatory
        DESCRIPTION     "The time at which the system was last booted"
        ::= {eGeneralInformation 5}

a2SystemDateTime OBJECT-TYPE
        SYNTAX          DmiDate
        ACCESS          read-write
        STATUS          mandatory
        DESCRIPTION     "This attribute returns the actual system date and  time."
        ::= {eGeneralInformation 6}

SOperatingSystem ::= SEQUENCE {
        a3OperatingSystemIndex                          DmiInteger,
        a3OperatingSystemName                           DmiDisplaystring,
        a3OperatingSystemVersion                        DmiDisplaystring,
        a3PrimaryOperatingSystem                        DmiInteger,
        a3OperatingSystemBootDeviceStorageType          DmiInteger,
        a3OperatingSystemBootDeviceIndex                DmiInteger,
        a3OperatingSystemBootPartitionIndex             DmiInteger,
        a3OperatingSystemDescription                    DmiDisplaystring
}

tOperatingSystem OBJECT-TYPE
        SYNTAX          SEQUENCE OF SOperatingSystem
        ACCESS          not-accessible
        STATUS          mandatory
        DESCRIPTION     "This group defines general information about operating systems
installed on this system."
        ::= {dmtfGroups1 3}

eOperatingSystem OBJECT-TYPE
        SYNTAX          SOperatingSystem
        ACCESS          not-accessible
        STATUS          mandatory
        DESCRIPTION     ""
        --INDEX           {DmiComponentIndex, a3OperatingSystemIndex}
        ::= {tOperatingSystem 1}

a3OperatingSystemIndex OBJECT-TYPE
        SYNTAX          DmiInteger
        ACCESS          read-only
        STATUS          mandatory
        DESCRIPTION     "The index into the operating system table."
        ::= {eOperatingSystem 1}

a3OperatingSystemName OBJECT-TYPE
        SYNTAX          DmiDisplaystring
        ACCESS          read-only
        STATUS          mandatory
        DESCRIPTION     "The name of this operating system."
        ::= {eOperatingSystem 2}

a3OperatingSystemVersion OBJECT-TYPE
        SYNTAX          DmiDisplaystring
        ACCESS          read-only
        STATUS          mandatory
        DESCRIPTION     "The version number of this operating system."
        ::= {eOperatingSystem 3}

a3PrimaryOperatingSystem OBJECT-TYPE
        SYNTAX          INTEGER {
                vFalse                                          (0),
                vTrue                                           (1)
        }
        ACCESS          read-only
        STATUS          mandatory
        DESCRIPTION     "If true, this is the primary operating system."
        ::= {eOperatingSystem 4}

a3OperatingSystemBootDeviceStorageType OBJECT-TYPE
        SYNTAX          INTEGER {
                vOther                                          (1),
                vUnknown                                        (2),
                vHard-disk                                      (3),
                vFloppy-disk                                    (4),
                vOptical-rom                                    (5),
                vOptical-worm                                   (6),
                vOptical-rw                                     (7),
                vCompact-disk                                   (8),
                vFlash-disk                                     (9),
                vBernoulli                                      (10),
                vOpticalFloppyDisk                              (11)
        }
        ACCESS          read-only
        STATUS          mandatory
        DESCRIPTION     "An index into the Disks Table to indicate the device from
which this operating system was booted. To fully access the Disks Table,
this index must be combined with the attribute Boot Device Index"
        ::= {eOperatingSystem 5}

a3OperatingSystemBootDeviceIndex OBJECT-TYPE
        SYNTAX          DmiInteger
        ACCESS          read-only
        STATUS          mandatory
        DESCRIPTION     "An index into the Disks Table"
        ::= {eOperatingSystem 6}

a3OperatingSystemBootPartitionIndex OBJECT-TYPE
        SYNTAX          DmiInteger
        ACCESS          read-only
        STATUS          mandatory
        DESCRIPTION     "An index into the Partition table indicating the partition
from which this operating system booted."
        ::= {eOperatingSystem 7}

a3OperatingSystemDescription OBJECT-TYPE
        SYNTAX          DmiDisplaystring
        ACCESS          read-only
        STATUS          mandatory
        DESCRIPTION     "A description of this operating system."
        ::= {eOperatingSystem 8}

SSystemBios ::= SEQUENCE {
        a4BiosIndex                                     DmiInteger,
        a4Manufacturer                                  DmiDisplaystring,
        a4Version                                       DmiDisplaystring,
        a4BiosRomSize                                   DmiInteger,
        a4StartingAddress                               DmiInteger64,
        a4EndingAddress                                 DmiInteger64,
        a4LoaderVersion                                 DmiDisplaystring,
        a4BiosReleaseDate                               DmiDate,
        a4PrimaryBios                                   DmiInteger
}

tSystemBios OBJECT-TYPE
        SYNTAX          SEQUENCE OF SSystemBios
        ACCESS          not-accessible
        STATUS          mandatory
        DESCRIPTION     "This group defines the attributes for the System BIOS."
        ::= {dmtfGroups1 4}

eSystemBios OBJECT-TYPE
        SYNTAX          SSystemBios
        ACCESS          not-accessible
        STATUS          mandatory
        DESCRIPTION     ""
        --INDEX           {DmiComponentIndex, a4BiosIndex}
        ::= {tSystemBios 1}

a4BiosIndex OBJECT-TYPE
        SYNTAX          DmiInteger
        ACCESS          read-only
        STATUS          mandatory
        DESCRIPTION     "The index into the system BIOS table."
        ::= {eSystemBios 1}

a4Manufacturer OBJECT-TYPE
        SYNTAX          DmiDisplaystring
        ACCESS          read-only
        STATUS          mandatory
        DESCRIPTION     "The name of the company that wrote this System BIOS."
        ::= {eSystemBios 2}

a4Version OBJECT-TYPE
        SYNTAX          DmiDisplaystring
        ACCESS          read-only
        STATUS          mandatory
        DESCRIPTION     "The version number or version string of this BIOS."
        ::= {eSystemBios 3}

a4BiosRomSize OBJECT-TYPE
        SYNTAX          DmiInteger
        ACCESS          read-only
        STATUS          mandatory
        DESCRIPTION     "The physical size of this BIOS ROM device in Kilo Bytes"
        ::= {eSystemBios 4}

a4StartingAddress OBJECT-TYPE
        SYNTAX          DmiInteger64
        ACCESS          read-only
        STATUS          mandatory
        DESCRIPTION     "The starting physical address for the memory which the BIOS
occupies"
        ::= {eSystemBios 5}

a4EndingAddress OBJECT-TYPE
        SYNTAX          DmiInteger64
        ACCESS          read-only
        STATUS          mandatory
        DESCRIPTION     "The ending physical address for the memory which the BIOS
occupies"
        ::= {eSystemBios 6}

a4LoaderVersion OBJECT-TYPE
        SYNTAX          DmiDisplaystring
        ACCESS          read-only
        STATUS          mandatory
        DESCRIPTION     "The BIOS flash loader version number or string."
        ::= {eSystemBios 7}

a4BiosReleaseDate OBJECT-TYPE
        SYNTAX          DmiDate
        ACCESS          read-only
        STATUS          mandatory
        DESCRIPTION     "The BIOS release date."
        ::= {eSystemBios 8}

a4PrimaryBios OBJECT-TYPE
        SYNTAX          INTEGER {
                vFalse                                          (0),
                vTrue                                           (1)
        }
        ACCESS          read-only
        STATUS          mandatory
        DESCRIPTION     "If true, this is the primary System BIOS."
        ::= {eSystemBios 9}

SSystemBiosCharacteristic ::= SEQUENCE {
        a5BiosCharacteristicsIndex                      DmiInteger,
        a5BiosNumber                                    DmiInteger,
        a5BiosCharacteristics                           DmiInteger,
        a5BiosCharacteristicsDescription                DmiDisplaystring
}

tSystemBiosCharacteristic OBJECT-TYPE
        SYNTAX          SEQUENCE OF SSystemBiosCharacteristic
        ACCESS          not-accessible
        STATUS          mandatory
        DESCRIPTION     "This group defines the characteristics for the System BIOS."
        ::= {dmtfGroups1 5}

eSystemBiosCharacteristic OBJECT-TYPE
        SYNTAX          SSystemBiosCharacteristic
        ACCESS          not-accessible
        STATUS          mandatory
        DESCRIPTION     ""
        --INDEX           {DmiComponentIndex, a5BiosCharacteristicsIndex, a5BiosNumber}
        ::= {tSystemBiosCharacteristic 1}

a5BiosCharacteristicsIndex OBJECT-TYPE
        SYNTAX          DmiInteger
        ACCESS          read-only
        STATUS          mandatory
        DESCRIPTION     "This is an index into the BIOS Characteristics table. "
        ::= {eSystemBiosCharacteristic 1}

a5BiosNumber OBJECT-TYPE
        SYNTAX          DmiInteger
        ACCESS          read-only
        STATUS          mandatory
        DESCRIPTION     "This field refers to the BIOS number, which correlates to
the System BIOS Index. "
        ::= {eSystemBiosCharacteristic 2}

a5BiosCharacteristics OBJECT-TYPE
        SYNTAX          INTEGER {
                vOther                                          (1),
                vUnknown                                        (2),
                vUnsupported                                    (3),
                vIsa-support                                    (4),
                vMca-support                                    (5),
                vEisa-support                                   (6),
                vPci-support                                    (7),
                vPcmcia-support                                 (8),
                vPnp-support                                    (9),
                vApmSupport                                     (10),
                vUpgradeable-bios                               (11),
                vBios-shadowing-allowed                         (12),
                vVl-vesa-support                                (13),
                vEscdSupport                                    (14)
        }
        ACCESS          read-only
        STATUS          mandatory
        DESCRIPTION     "The different attributes supported by this version of the
BIOS"
        ::= {eSystemBiosCharacteristic 3}

a5BiosCharacteristicsDescription OBJECT-TYPE
        SYNTAX          DmiDisplaystring
        ACCESS          read-only
        STATUS          mandatory
        DESCRIPTION     "An expanded description of this BIOS Characteristic."
        ::= {eSystemBiosCharacteristic 4}

SProcessor ::= SEQUENCE {
        a6ProcessorIndex                                DmiInteger,
        a6Type                                          DmiInteger,
        a6ProcessorFamily                               DmiInteger,
        a6VersionInformation                            DmiDisplaystring,
        a6MaximumSpeed                                  DmiInteger,
        a6CurrentSpeed                                  DmiInteger,
        a6ProcessorUpgrade                              DmiInteger,
        a6FruGroupIndex                                 DmiInteger,
        a6OperationalGroupIndex                         DmiInteger
}

tProcessor OBJECT-TYPE
        SYNTAX          SEQUENCE OF SProcessor
        ACCESS          not-accessible
        STATUS          mandatory
        DESCRIPTION     "This group defines the attributes for each and every processor
installed in this system."
        ::= {dmtfGroups1 6}

eProcessor OBJECT-TYPE
        SYNTAX          SProcessor
        ACCESS          not-accessible
        STATUS          mandatory
        DESCRIPTION     ""
        --INDEX           {DmiComponentIndex, a6ProcessorIndex}
        ::= {tProcessor 1}

a6ProcessorIndex OBJECT-TYPE
        SYNTAX          DmiInteger
        ACCESS          read-only
        STATUS          mandatory
        DESCRIPTION     "An index into the processor table."
        ::= {eProcessor 1}

a6Type OBJECT-TYPE
        SYNTAX          INTEGER {
                vOther                                          (1),
                vUnknown                                        (2),
                vCentralProcessor                               (3),
                vMath-processor                                 (4),
                vDsp-processor                                  (5),
                vVideo-processor                                (6)
        }
        ACCESS          read-only
        STATUS          mandatory
        DESCRIPTION     "The type of processor currently in the system."
        ::= {eProcessor 2}

a6ProcessorFamily OBJECT-TYPE
        SYNTAX          INTEGER {
                vOther                                          (1),
                vUnknown                                        (2),
                v8086                                           (3),
                v80286                                          (4),
                v80386                                          (5),
                v80486                                          (6),
                v8087                                           (7),
                v80287                                          (8),
                v80387                                          (9),
                v80487                                          (10),
                vPentiumFamily                                  (11),
                vPowerPcFamily                                  (32),
                vAlphaFamily                                    (48),
                vMipsFamily                                     (64),
                vSparcFamily                                    (80),
                v68040Family                                    (96),
                vHobbitFamily                                   (112),
                vWeitek                                         (128),
                vPa-riscFamily                                  (144)
        }
        ACCESS          read-only
        STATUS          mandatory
        DESCRIPTION     "The family of processors to which this processor belongs."
        ::= {eProcessor 3}

a6VersionInformation OBJECT-TYPE
        SYNTAX          DmiDisplaystring
        ACCESS          read-only
        STATUS          mandatory
        DESCRIPTION     "The version number or string for this processor."
        ::= {eProcessor 4}

a6MaximumSpeed OBJECT-TYPE
        SYNTAX          DmiInteger
        ACCESS          read-only
        STATUS          mandatory
        DESCRIPTION     "The maximum speed (in MHz) of this processor."
        ::= {eProcessor 5}

a6CurrentSpeed OBJECT-TYPE
        SYNTAX          DmiInteger
        ACCESS          read-only
        STATUS          mandatory
        DESCRIPTION     "The current speed (in MHz) of this processor."
        ::= {eProcessor 6}

a6ProcessorUpgrade OBJECT-TYPE
        SYNTAX          INTEGER {
                vOther                                          (1),
                vUnknown                                        (2),
                vDaughterBoard                                  (3),
                vZifSocket                                      (4),
                vReplacementpiggyBack                           (5),
                vNone                                           (6)
        }
        ACCESS          read-only
        STATUS          mandatory
        DESCRIPTION     "The method by which this processor can be upgraded, if upgrades
are supported. "
        ::= {eProcessor 7}

a6FruGroupIndex OBJECT-TYPE
        SYNTAX          DmiInteger
        ACCESS          read-only
        STATUS          mandatory
        DESCRIPTION     "If this is a Field Replaceable Unit or if it is partof another
FRU, this provides index into the FRU table.A Value = -1 means that the group
is not a FRU"
        ::= {eProcessor 8}

a6OperationalGroupIndex OBJECT-TYPE
        SYNTAX          DmiInteger
        ACCESS          read-only
        STATUS          mandatory
        DESCRIPTION     "The index into the Operational State Table for this device
if applicable"
        ::= {eProcessor 9}

SMotherboard ::= SEQUENCE {
        a7NumberOfExpansionSlots                        DmiInteger,
        a7FruGroupIndex                                 DmiInteger,
        a7OperationalGroupIndex                         DmiInteger
}

tMotherboard OBJECT-TYPE
        SYNTAX          SEQUENCE OF SMotherboard
        ACCESS          not-accessible
        STATUS          mandatory
        DESCRIPTION     "This group defines attributes for the mother board"
        ::= {dmtfGroups1 7}

eMotherboard OBJECT-TYPE
        SYNTAX          SMotherboard
        ACCESS          not-accessible
        STATUS          mandatory
        DESCRIPTION     ""
        --INDEX           {DmiComponentIndex}
        ::= {tMotherboard 1}

a7NumberOfExpansionSlots OBJECT-TYPE
        SYNTAX          DmiInteger
        ACCESS          read-only
        STATUS          mandatory
        DESCRIPTION     "This attribute indicates the total number of expansion slots
which physically exist on the motherboard whether occupied or not (See System
Slots groups)"
        ::= {eMotherboard 1}

a7FruGroupIndex OBJECT-TYPE
        SYNTAX          DmiInteger
        ACCESS          read-only
        STATUS          mandatory
        DESCRIPTION     "If this is a Field Replaceable Unit or if it is partof another
FRU, this provides index into the FRU table.A Value = -1 means that the group
is not a FRU"
        ::= {eMotherboard 2}

a7OperationalGroupIndex OBJECT-TYPE
        SYNTAX          DmiInteger
        ACCESS          read-only
        STATUS          mandatory
        DESCRIPTION     "The index into the Operational State Table for this device
if applicable"
        ::= {eMotherboard 3}

SPhysicalMemory ::= SEQUENCE {
        a8PhysicalMemoryIndex                           DmiInteger,
        a8PhysicalMemoryLocation                        DmiInteger,
        a8MemoryStartingAddress                         DmiInteger64,
        a8MemoryEndingAddress                           DmiInteger64,
        a8MemoryUsage                                   DmiInteger,
        a8MaximumMemoryCapacity                         DmiInteger,
        a8NumberOfSimmSlots                             DmiInteger,
        a8NumberOfSimmSlotsUsed                         DmiInteger,
        a8MemorySpeed                                   DmiInteger,
        a8MemoryErrorCorrection                         DmiInteger,
        a8FruGroupIndex                                 DmiInteger,
        a8OperationalGroupIndex                         DmiInteger
}

tPhysicalMemory OBJECT-TYPE
        SYNTAX          SEQUENCE OF SPhysicalMemory
        ACCESS          not-accessible
        STATUS          mandatory
        DESCRIPTION     "This group defines the physical attributes for system memory
and any add- on memory installed in this system."
        ::= {dmtfGroups1 8}

ePhysicalMemory OBJECT-TYPE
        SYNTAX          SPhysicalMemory
        ACCESS          not-accessible
        STATUS          mandatory
        DESCRIPTION     ""
        --INDEX           {DmiComponentIndex, a8PhysicalMemoryIndex}
        ::= {tPhysicalMemory 1}

a8PhysicalMemoryIndex OBJECT-TYPE
        SYNTAX          DmiInteger
        ACCESS          read-only
        STATUS          mandatory
        DESCRIPTION     "An index into the physical memory table."
        ::= {ePhysicalMemory 1}

a8PhysicalMemoryLocation OBJECT-TYPE
        SYNTAX          INTEGER {
                vOther                                          (1),
                vUnknown                                        (2),
                vSystemBoardOrMotherBoard                       (3),
                vIsaAddOnCard                                   (4),
                vEisaAddOnCard                                  (5),
                vPciAddOnCard                                   (6),
                vMcaAddOnCard                                   (7),
                vPcmciaAddOnCard                                (8),
                vProprietaryAddOnCard                           (9)
        }
        ACCESS          read-only
        STATUS          mandatory
        DESCRIPTION     "The location of the memory modules, whether on the system
board or an add on board."
        ::= {ePhysicalMemory 2}

a8MemoryStartingAddress OBJECT-TYPE
        SYNTAX          DmiInteger64
        ACCESS          read-only
        STATUS          mandatory
        DESCRIPTION     "This is the starting physical address mapped by this memory
component"
        ::= {ePhysicalMemory 3}

a8MemoryEndingAddress OBJECT-TYPE
        SYNTAX          DmiInteger64
        ACCESS          read-only
        STATUS          mandatory
        DESCRIPTION     "This is the ending physical address mapped by this memory
component"
        ::= {ePhysicalMemory 4}

a8MemoryUsage OBJECT-TYPE
        SYNTAX          INTEGER {
                vOther                                          (1),
                vUnknown                                        (2),
                vSystemMemory                                   (3),
                vVideoMemory                                    (4),
                vFlashMemory                                    (5),
                vNonVolatileRam                                 (6)
        }
        ACCESS          read-only
        STATUS          mandatory
        DESCRIPTION     "What this memory component is used for."
        ::= {ePhysicalMemory 5}

a8MaximumMemoryCapacity OBJECT-TYPE
        SYNTAX          DmiInteger
        ACCESS          read-only
        STATUS          mandatory
        DESCRIPTION     "The maximum memory capacity, in MegaBytes on this device."
        ::= {ePhysicalMemory 6}

a8NumberOfSimmSlots OBJECT-TYPE
        SYNTAX          DmiInteger
        ACCESS          read-only
        STATUS          mandatory
        DESCRIPTION     "The number of SIMM slots available for this type of memory
on this device."
        ::= {ePhysicalMemory 7}

a8NumberOfSimmSlotsUsed OBJECT-TYPE
        SYNTAX          DmiInteger
        ACCESS          read-only
        STATUS          mandatory
        DESCRIPTION     "The number of SIMM slots in use for this type of memory on
this device"
        ::= {ePhysicalMemory 8}

a8MemorySpeed OBJECT-TYPE
        SYNTAX          DmiInteger
        ACCESS          read-only
        STATUS          mandatory
        DESCRIPTION     "The speed of this memory component in nano seconds"
        ::= {ePhysicalMemory 9}

a8MemoryErrorCorrection OBJECT-TYPE
        SYNTAX          INTEGER {
                vOther                                          (1),
                vUnknown                                        (2),
                vNone                                           (3),
                vParity                                         (4),
                vSingleBitEcc                                   (5),
                vMultibitEcc                                    (6)
        }
        ACCESS          read-only
        STATUS          mandatory
        DESCRIPTION     "The main type of error correction scheme supported by this
memory component."
        ::= {ePhysicalMemory 10}

a8FruGroupIndex OBJECT-TYPE
        SYNTAX          DmiInteger
        ACCESS          read-only
        STATUS          mandatory
        DESCRIPTION     "If this is a Field Replaceable Unit or if it is partof another
FRU, this provides index into the FRU table.A Value = -1 means that the group
is not a FRU"
        ::= {ePhysicalMemory 11}

a8OperationalGroupIndex OBJECT-TYPE
        SYNTAX          DmiInteger
        ACCESS          read-only
        STATUS          mandatory
        DESCRIPTION     "The index into the Operational State Table for this device
if applicable"
        ::= {ePhysicalMemory 12}

SLogicalMemory ::= SEQUENCE {
        a9BaseMemorySize                                DmiInteger,
        a9FreeBaseMemorySize                            DmiInteger,
        a9ExtendedMemorySize                            DmiInteger,
        a9FreeExtendedMemorySize                        DmiInteger,
        a9ExtendedMemoryManagerName                     DmiDisplaystring,
        a9ExtendedMemoryManagerVersion                  DmiDisplaystring,
        a9ExpandedMemorySize                            DmiInteger,
        a9FreeExpandedMemorySize                        DmiInteger,
        a9ExpandedMemoryManagerName                     DmiDisplaystring,
        a9ExpandedMemoryManagerVersion                  DmiDisplaystring,
        a9ExpandedMemoryPageFrameAddress                DmiInteger64,
        a9ExpandedMemoryPageFrameSize                   DmiInteger,
        a9ExpandedMemoryPageSize                        DmiInteger
}

tLogicalMemory OBJECT-TYPE
        SYNTAX          SEQUENCE OF SLogicalMemory
        ACCESS          not-accessible
        STATUS          mandatory
        DESCRIPTION     "This group defines the logical memory attributes for system
memory and any add-on memory  installed in this system."
        ::= {dmtfGroups1 9}

eLogicalMemory OBJECT-TYPE
        SYNTAX          SLogicalMemory
        ACCESS          not-accessible
        STATUS          mandatory
        DESCRIPTION     ""
        --INDEX           {DmiComponentIndex}
        ::= {tLogicalMemory 1}

a9BaseMemorySize OBJECT-TYPE
        SYNTAX          DmiInteger
        ACCESS          read-only
        STATUS          mandatory
        DESCRIPTION     "The total size of the base memory in Kilo Bytes."
        ::= {eLogicalMemory 1}

a9FreeBaseMemorySize OBJECT-TYPE
        SYNTAX          DmiInteger
        ACCESS          read-only
        STATUS          mandatory
        DESCRIPTION     "The size of free base memory in Kilo Bytes."
        ::= {eLogicalMemory 2}

a9ExtendedMemorySize OBJECT-TYPE
        SYNTAX          DmiInteger
        ACCESS          read-only
        STATUS          mandatory
        DESCRIPTION     "The total size of the extended memory in Kilo Bytes."
        ::= {eLogicalMemory 3}

a9FreeExtendedMemorySize OBJECT-TYPE
        SYNTAX          DmiInteger
        ACCESS          read-only
        STATUS          mandatory
        DESCRIPTION     "The size of free extended memory in Kilo Bytes."
        ::= {eLogicalMemory 4}

a9ExtendedMemoryManagerName OBJECT-TYPE
        SYNTAX          DmiDisplaystring
        ACCESS          read-only
        STATUS          mandatory
        DESCRIPTION     "The name of the extended memory manager."
        ::= {eLogicalMemory 5}

a9ExtendedMemoryManagerVersion OBJECT-TYPE
        SYNTAX          DmiDisplaystring
        ACCESS          read-only
        STATUS          mandatory
        DESCRIPTION     "The version information of the extended memory manager."
        ::= {eLogicalMemory 6}

a9ExpandedMemorySize OBJECT-TYPE
        SYNTAX          DmiInteger
        ACCESS          read-only
        STATUS          mandatory
        DESCRIPTION     "The total size of the expanded  memory in Kilo Bytes."
        ::= {eLogicalMemory 7}

a9FreeExpandedMemorySize OBJECT-TYPE
        SYNTAX          DmiInteger
        ACCESS          read-only
        STATUS          mandatory
        DESCRIPTION     "The size of free expanded memory in Kilo Bytes."
        ::= {eLogicalMemory 8}

a9ExpandedMemoryManagerName OBJECT-TYPE
        SYNTAX          DmiDisplaystring
        ACCESS          read-only
        STATUS          mandatory
        DESCRIPTION     "The name of the expanded memory manager."
        ::= {eLogicalMemory 9}

a9ExpandedMemoryManagerVersion OBJECT-TYPE
        SYNTAX          DmiDisplaystring
        ACCESS          read-only
        STATUS          mandatory
        DESCRIPTION     "The version information of the expanded memory manager."
        ::= {eLogicalMemory 10}

a9ExpandedMemoryPageFrameAddress OBJECT-TYPE
        SYNTAX          DmiInteger64
        ACCESS          read-only
        STATUS          mandatory
        DESCRIPTION     "The starting physical address of the expanded memory page
frame."
        ::= {eLogicalMemory 11}

a9ExpandedMemoryPageFrameSize OBJECT-TYPE
        SYNTAX          DmiInteger
        ACCESS          read-only
        STATUS          mandatory
        DESCRIPTION     "The size in Kilo Bytes of the expanded memory page frame."
        ::= {eLogicalMemory 12}

a9ExpandedMemoryPageSize OBJECT-TYPE
        SYNTAX          DmiInteger
        ACCESS          read-only
        STATUS          mandatory
        DESCRIPTION     "The size in Kilo Bytes of an expanded memory page, as opposed
to the expanded memory page frame, which consists of a number of memory pages."
        ::= {eLogicalMemory 13}

SSystemCache ::= SEQUENCE {
        a10SystemCacheIndex                             DmiInteger,
        a10SystemCacheLevel                             DmiInteger,
        a10SystemCacheSpeed                             DmiInteger,
        a10SystemCacheSize                              DmiInteger,
        a10SystemCacheWritePolicy                       DmiInteger,
        a10SystemCacheErrorCorrection                   DmiInteger,
        a10FruGroupIndex                                DmiInteger,
        a10OperationalGroupIndex                        DmiInteger
}

tSystemCache OBJECT-TYPE
        SYNTAX          SEQUENCE OF SSystemCache
        ACCESS          not-accessible
        STATUS          mandatory
        DESCRIPTION     "This group defines the attributes for different System Caches
installed in this system."
        ::= {dmtfGroups1 10}

eSystemCache OBJECT-TYPE
        SYNTAX          SSystemCache
        ACCESS          not-accessible
        STATUS          mandatory
        DESCRIPTION     ""
        --INDEX           {DmiComponentIndex, a10SystemCacheIndex}
        ::= {tSystemCache 1}

a10SystemCacheIndex OBJECT-TYPE
        SYNTAX          DmiInteger
        ACCESS          read-only
        STATUS          mandatory
        DESCRIPTION     "An index into the System Cache table."
        ::= {eSystemCache 1}

a10SystemCacheLevel OBJECT-TYPE
        SYNTAX          INTEGER {
                vOther                                          (1),
                vUnknown                                        (2),
                vPrimary                                        (3),
                vSecondary                                      (4),
                vTertiary                                       (5)
        }
        ACCESS          read-only
        STATUS          mandatory
        DESCRIPTION     "Defines primary or secondary System Cache, or a subsidiary
cache."
        ::= {eSystemCache 2}

a10SystemCacheSpeed OBJECT-TYPE
        SYNTAX          DmiInteger
        ACCESS          read-only
        STATUS          mandatory
        DESCRIPTION     "The speed of this System Cache module in nano seconds"
        ::= {eSystemCache 3}

a10SystemCacheSize OBJECT-TYPE
        SYNTAX          DmiInteger
        ACCESS          read-only
        STATUS          mandatory
        DESCRIPTION     "The size of this System Cache module in Kilo Bytes."
        ::= {eSystemCache 4}

a10SystemCacheWritePolicy OBJECT-TYPE
        SYNTAX          INTEGER {
                vOther                                          (1),
                vUnknown                                        (2),
                vWriteBack                                      (3),
                vWriteThrough                                   (4)
        }
        ACCESS          read-only
        STATUS          mandatory
        DESCRIPTION     "Is this a write-back or a write-through cache?"
        ::= {eSystemCache 5}

a10SystemCacheErrorCorrection OBJECT-TYPE
        SYNTAX          INTEGER {
                vOther                                          (1),
                vUnknown                                        (2),
                vNone                                           (3),
                vParity                                         (4),
                vSingleBitEcc                                   (5),
                vMultibitEcc                                    (6)
        }
        ACCESS          read-only
        STATUS          mandatory
        DESCRIPTION     "This field describes the main type of error correction scheme
supported by thiscache component."
        ::= {eSystemCache 6}

a10FruGroupIndex OBJECT-TYPE
        SYNTAX          DmiInteger
        ACCESS          read-only
        STATUS          mandatory
        DESCRIPTION     "If this is a Field Replaceable Unit or if it is partof another
FRU, this provides an index into the FRU table.A Value = -1 means that the
group is not a FRU"
        ::= {eSystemCache 7}

a10OperationalGroupIndex OBJECT-TYPE
        SYNTAX          DmiInteger
        ACCESS          read-only
        STATUS          mandatory
        DESCRIPTION     "The index into the Operational State Table for this device
if applicable"
        ::= {eSystemCache 8}

SParallelPorts ::= SEQUENCE {
        a11ParallelPortIndex                            DmiInteger,
        a11ParallelBaseIoAddress                        DmiInteger64,
        a11IrqUsed                                      DmiInteger,
        a11LogicalName                                  DmiDisplaystring,
        a11ConnectorType                                DmiInteger,
        a11ConnectorPinout                              DmiInteger,
        a11DmaSupport                                   DmiInteger,
        a11ParallelPortCapabilities                     DmiInteger,
        a11OperationalGroupIndex                        DmiInteger
}

tParallelPorts OBJECT-TYPE
        SYNTAX          SEQUENCE OF SParallelPorts
        ACCESS          not-accessible
        STATUS          mandatory
        DESCRIPTION     "This group defines the attributes for parallel ports in this
system."
        ::= {dmtfGroups1 11}

eParallelPorts OBJECT-TYPE
        SYNTAX          SParallelPorts
        ACCESS          not-accessible
        STATUS          mandatory
        DESCRIPTION     ""
        --INDEX           {DmiComponentIndex, a11ParallelPortIndex}
        ::= {tParallelPorts 1}

a11ParallelPortIndex OBJECT-TYPE
        SYNTAX          DmiInteger
        ACCESS          read-only
        STATUS          mandatory
        DESCRIPTION     "An index into the parallel ports table."
        ::= {eParallelPorts 1}

a11ParallelBaseIoAddress OBJECT-TYPE
        SYNTAX          DmiInteger64
        ACCESS          read-only
        STATUS          mandatory
        DESCRIPTION     "Base I/O address for this parallel port."
        ::= {eParallelPorts 2}

a11IrqUsed OBJECT-TYPE
        SYNTAX          DmiInteger
        ACCESS          read-only
        STATUS          mandatory
        DESCRIPTION     "IRQ number that is being used by this parallel port."
        ::= {eParallelPorts 3}

a11LogicalName OBJECT-TYPE
        SYNTAX          DmiDisplaystring
        ACCESS          read-only
        STATUS          mandatory
        DESCRIPTION     "The logical name of the I/O device on this parallel port,
under this operating environment."
        ::= {eParallelPorts 4}

a11ConnectorType OBJECT-TYPE
        SYNTAX          INTEGER {
                vOther                                          (1),
                vUnknown                                        (2),
                vDb-25Female                                    (3),
                vDb-25Male                                      (4),
                vCentronics                                     (5),
                vMini-centronics                                (6),
                vProprietary                                    (7)
        }
        ACCESS          read-only
        STATUS          mandatory
        DESCRIPTION     "The connector used to interface with this I/O device on this
parallel port."
        ::= {eParallelPorts 5}

a11ConnectorPinout OBJECT-TYPE
        SYNTAX          INTEGER {
                vOther                                          (1),
                vUnknown                                        (2),
                vXtat                                           (3),
                vPs2                                            (4),
                vIeee1284                                       (5),
                vProprietary                                    (6)
        }
        ACCESS          read-only
        STATUS          mandatory
        DESCRIPTION     "The pinout used by the I/O device on this parallel port."
        ::= {eParallelPorts 6}

a11DmaSupport OBJECT-TYPE
        SYNTAX          INTEGER {
                vFalse                                          (0),
                vTrue                                           (1)
        }
        ACCESS          read-only
        STATUS          mandatory
        DESCRIPTION     "If true, DMA is supported."
        ::= {eParallelPorts 7}

a11ParallelPortCapabilities OBJECT-TYPE
        SYNTAX          DmiInteger
        ACCESS          read-only
        STATUS          mandatory
        DESCRIPTION     "Capabilities of this parallel port.  This is a bit field
mask with the bits defined as follows:  Bit 0 set = XT/AT compatible Bit
1 set = PS/2 compatible Bit 2 set = ECP Bit 3 set = EPP"
        ::= {eParallelPorts 8}

a11OperationalGroupIndex OBJECT-TYPE
        SYNTAX          DmiInteger
        ACCESS          read-only
        STATUS          mandatory
        DESCRIPTION     "The index into the Operational State Table for this device
if applicable"
        ::= {eParallelPorts 9}

SSerialPorts ::= SEQUENCE {
        a12SerialPortIndex                              DmiInteger,
        a12SerialBaseIo                                 DmiInteger64,
        a12IrqUsed                                      DmiInteger,
        a12LogicalName                                  DmiDisplaystring,
        a12ConnectorType                                DmiInteger,
        a12MaximumSpeed                                 DmiInteger,
        a12SerialPortCapabilities                       DmiInteger,
        a12OperationalGroupIndex                        DmiInteger
}

tSerialPorts OBJECT-TYPE
        SYNTAX          SEQUENCE OF SSerialPorts
        ACCESS          not-accessible
        STATUS          mandatory
        DESCRIPTION     "This group defines the attributes for serial ports in this
system."
        ::= {dmtfGroups1 12}

eSerialPorts OBJECT-TYPE
        SYNTAX          SSerialPorts
        ACCESS          not-accessible
        STATUS          mandatory
        DESCRIPTION     ""
        --INDEX           {DmiComponentIndex, a12SerialPortIndex}
        ::= {tSerialPorts 1}

a12SerialPortIndex OBJECT-TYPE
        SYNTAX          DmiInteger
        ACCESS          read-only
        STATUS          mandatory
        DESCRIPTION     "An index into the serial ports table."
        ::= {eSerialPorts 1}

a12SerialBaseIo OBJECT-TYPE
        SYNTAX          DmiInteger64
        ACCESS          read-only
        STATUS          mandatory
        DESCRIPTION     "Base I/O address for this serial port."
        ::= {eSerialPorts 2}

a12IrqUsed OBJECT-TYPE
        SYNTAX          DmiInteger
        ACCESS          read-only
        STATUS          mandatory
        DESCRIPTION     "IRQ number that is being used by this serial port."
        ::= {eSerialPorts 3}

a12LogicalName OBJECT-TYPE
        SYNTAX          DmiDisplaystring
        ACCESS          read-only
        STATUS          mandatory
        DESCRIPTION     "The logical name of this serial port under this operating
environment."
        ::= {eSerialPorts 4}

a12ConnectorType OBJECT-TYPE
        SYNTAX          INTEGER {
                vOther                                          (1),
                vUnknown                                        (2),
                vDb-9PinMale                                    (3),
                vDb-9PinFemale                                  (4),
                vDb-25PinMale                                   (5),
                vDb-25PinFemale                                 (6),
                vRj-11                                          (7),
                vRj-45                                          (8),
                vProprietary                                    (9)
        }
        ACCESS          read-only
        STATUS          mandatory
        DESCRIPTION     "The connector used to interface with the I/O device on this
serial port."
        ::= {eSerialPorts 5}

a12MaximumSpeed OBJECT-TYPE
        SYNTAX          DmiInteger
        ACCESS          read-only
        STATUS          mandatory
        DESCRIPTION     "Maximum transfer speed of the device on this serial port
in bits per second."
        ::= {eSerialPorts 6}

a12SerialPortCapabilities OBJECT-TYPE
        SYNTAX          INTEGER {
                vOther                                          (1),
                vUnknown                                        (2),
                vXtatCcompatible                                (3),
                v16450Compatible                                (4),
                v16550Compatible                                (5),
                v16550aCompatible                               (6)
        }
        ACCESS          read-only
        STATUS          mandatory
        DESCRIPTION     "The capabilities of this Serial port."
        ::= {eSerialPorts 7}

a12OperationalGroupIndex OBJECT-TYPE
        SYNTAX          DmiInteger
        ACCESS          read-only
        STATUS          mandatory
        DESCRIPTION     "The index into the Operational State Table for this device
if applicable"
        ::= {eSerialPorts 8}

SIrq ::= SEQUENCE {
        a13IrqNumber                                    DmiInteger,
        a13AvailabilityOfIrq                            DmiInteger,
        a13IrqTriggerType                               DmiInteger,
        a13IrqShareable                                 DmiInteger,
        a13IrqDescription                               DmiDisplaystring
}

tIrq OBJECT-TYPE
        SYNTAX          SEQUENCE OF SIrq
        ACCESS          not-accessible
        STATUS          mandatory
        DESCRIPTION     "This groups defines attributes for IRQs in this system."
        ::= {dmtfGroups1 13}

eIrq OBJECT-TYPE
        SYNTAX          SIrq
        ACCESS          not-accessible
        STATUS          mandatory
        DESCRIPTION     ""
        --INDEX           {DmiComponentIndex, a13IrqNumber}
        ::= {tIrq 1}

a13IrqNumber OBJECT-TYPE
        SYNTAX          DmiInteger
        ACCESS          read-only
        STATUS          mandatory
        DESCRIPTION     "The current IRQ number for this IRQ."
        ::= {eIrq 1}

a13AvailabilityOfIrq OBJECT-TYPE
        SYNTAX          INTEGER {
                vOther                                          (1),
                vUnknown                                        (2),
                vAvailable                                      (3),
                vInUse                                          (4)
        }
        ACCESS          read-only
        STATUS          mandatory
        DESCRIPTION     "Is this IRQ available or in use."
        ::= {eIrq 2}

a13IrqTriggerType OBJECT-TYPE
        SYNTAX          INTEGER {
                vOther                                          (1),
                vUnknown                                        (2),
                vLevel                                          (3),
                vEdge                                           (4)
        }
        ACCESS          read-only
        STATUS          mandatory
        DESCRIPTION     "The attribute indicates the trigger type of the IRQ"
        ::= {eIrq 3}

a13IrqShareable OBJECT-TYPE
        SYNTAX          INTEGER {
                vFalse                                          (0),
                vTrue                                           (1)
        }
        ACCESS          read-only
        STATUS          mandatory
        DESCRIPTION     "If true, this IRQ is shareable."
        ::= {eIrq 4}

a13IrqDescription OBJECT-TYPE
        SYNTAX          DmiDisplaystring
        ACCESS          read-only
        STATUS          mandatory
        DESCRIPTION     "The name of the logical device name that is currently using
this IRQ."
        ::= {eIrq 5}

SDma ::= SEQUENCE {
        a14DmaNumber                                    DmiInteger,
        a14AvailabilityOfDma                            DmiInteger,
        a14DmaBurstMode                                 DmiInteger,
        a14DmaDescription                               DmiDisplaystring
}

tDma OBJECT-TYPE
        SYNTAX          SEQUENCE OF SDma
        ACCESS          not-accessible
        STATUS          mandatory
        DESCRIPTION     "This group defines various attributes for the various DMA
channels in this system."
        ::= {dmtfGroups1 14}

eDma OBJECT-TYPE
        SYNTAX          SDma
        ACCESS          not-accessible
        STATUS          mandatory
        DESCRIPTION     ""
        --INDEX           {DmiComponentIndex, a14DmaNumber}
        ::= {tDma 1}

a14DmaNumber OBJECT-TYPE
        SYNTAX          DmiInteger
        ACCESS          read-only
        STATUS          mandatory
        DESCRIPTION     "The current DMA channel number."
        ::= {eDma 1}

a14AvailabilityOfDma OBJECT-TYPE
        SYNTAX          INTEGER {
                vFalse                                          (0),
                vTrue                                           (1)
        }
        ACCESS          read-only
        STATUS          mandatory
        DESCRIPTION     "If true, this DMA channel is available."
        ::= {eDma 2}

a14DmaBurstMode OBJECT-TYPE
        SYNTAX          INTEGER {
                vFalse                                          (0),
                vTrue                                           (1)
        }
        ACCESS          read-only
        STATUS          mandatory
        DESCRIPTION     "If true, this DMA channel supports burst mode."
        ::= {eDma 3}

a14DmaDescription OBJECT-TYPE
        SYNTAX          DmiDisplaystring
        ACCESS          read-only
        STATUS          mandatory
        DESCRIPTION     "The name of the logical device that is currently using this
DMA channel."
        ::= {eDma 4}

SMemoryMappedIo ::= SEQUENCE {
        a15MemoryMappedIoStartingAddress                DmiInteger64,
        a15MemoryMappedIoEndingAddress                  DmiInteger64,
        a15MemoryMappedIoDescription                    DmiDisplaystring
}

tMemoryMappedIo OBJECT-TYPE
        SYNTAX          SEQUENCE OF SMemoryMappedIo
        ACCESS          not-accessible
        STATUS          mandatory
        DESCRIPTION     "This group defines various attributes for memory mapped I/O
on this system."
        ::= {dmtfGroups1 15}

eMemoryMappedIo OBJECT-TYPE
        SYNTAX          SMemoryMappedIo
        ACCESS          not-accessible
        STATUS          mandatory
        DESCRIPTION     ""
        --INDEX           {DmiComponentIndex, a15MemoryMappedIoStartingAddress}
        ::= {tMemoryMappedIo 1}

a15MemoryMappedIoStartingAddress OBJECT-TYPE
        SYNTAX          DmiInteger64
        ACCESS          read-only
        STATUS          mandatory
        DESCRIPTION     "The starting address of a contiguous System memory mapped
I/O region."
        ::= {eMemoryMappedIo 1}

a15MemoryMappedIoEndingAddress OBJECT-TYPE
        SYNTAX          DmiInteger64
        ACCESS          read-only
        STATUS          mandatory
        DESCRIPTION     "The ending address of a contiguous System memory mapped I/O
region."
        ::= {eMemoryMappedIo 2}

a15MemoryMappedIoDescription OBJECT-TYPE
        SYNTAX          DmiDisplaystring
        ACCESS          read-only
        STATUS          mandatory
        DESCRIPTION     "The name of the logical device currently using this Memory
Mapped I/O."
        ::= {eMemoryMappedIo 3}

SSystemEnclosure ::= SEQUENCE {
        a16EnclosureOrChassis                           DmiInteger,
        a16AssetTag                                     DmiDisplaystring,
        a16ChassisLockPresent                           DmiInteger,
        a16BootUpState                                  DmiInteger,
        a16PowerState                                   DmiInteger,
        a16ThermalState                                 DmiInteger,
        a16FruGroupIndex                                DmiInteger,
        a16OperationalGroupIndex                        DmiInteger
}

tSystemEnclosure OBJECT-TYPE
        SYNTAX          SEQUENCE OF SSystemEnclosure
        ACCESS          not-accessible
        STATUS          mandatory
        DESCRIPTION     "This group defines the attributes for the system enclosure."
        ::= {dmtfGroups1 16}

eSystemEnclosure OBJECT-TYPE
        SYNTAX          SSystemEnclosure
        ACCESS          not-accessible
        STATUS          mandatory
        DESCRIPTION     ""
        --INDEX           {DmiComponentIndex}
        ::= {tSystemEnclosure 1}

a16EnclosureOrChassis OBJECT-TYPE
        SYNTAX          INTEGER {
                vOther                                          (1),
                vUnknown                                        (2),
                vDesktop                                        (3),
                vLowProfileDesktop                              (4),
                vPizzaBox                                       (5),
                vMiniTower                                      (6),
                vTower                                          (7),
                vPortable                                       (8),
                vLaptop                                         (9),
                vNotebook                                       (10),
                vHandHeld                                       (11),
                vDockingStation                                 (12)
        }
        ACCESS          read-only
        STATUS          mandatory
        DESCRIPTION     "The type of Enclosure."
        ::= {eSystemEnclosure 1}

a16AssetTag OBJECT-TYPE
        SYNTAX          DmiDisplaystring
        ACCESS          read-write
        STATUS          mandatory
        DESCRIPTION     "The system asset tag number or string"
        ::= {eSystemEnclosure 2}

a16ChassisLockPresent OBJECT-TYPE
        SYNTAX          INTEGER {
                vFalse                                          (0),
                vTrue                                           (1)
        }
        ACCESS          read-only
        STATUS          mandatory
        DESCRIPTION     "If true, a chassis lock is present."
        ::= {eSystemEnclosure 3}

a16BootUpState OBJECT-TYPE
        SYNTAX          INTEGER {
                vOther                                          (1),
                vUnknown                                        (2),
                vSafe                                           (3),
                vWarning                                        (4),
                vCritical                                       (5)
        }
        ACCESS          read-only
        STATUS          mandatory
        DESCRIPTION     "The current state of this system when it booted."
        ::= {eSystemEnclosure 4}

a16PowerState OBJECT-TYPE
        SYNTAX          INTEGER {
                vOther                                          (1),
                vUnknown                                        (2),
                vSafe                                           (3),
                vWarning                                        (4),
                vCritical                                       (5)
        }
        ACCESS          read-only
        STATUS          mandatory
        DESCRIPTION     "The current state of the power supply state for this system."
        ::= {eSystemEnclosure 5}

a16ThermalState OBJECT-TYPE
        SYNTAX          INTEGER {
                vOther                                          (1),
                vUnknown                                        (2),
                vSafe                                           (3),
                vWarning                                        (4),
                vCritical                                       (5)
        }
        ACCESS          read-only
        STATUS          mandatory
        DESCRIPTION     "The current thermal state of this system."
        ::= {eSystemEnclosure 6}

a16FruGroupIndex OBJECT-TYPE
        SYNTAX          DmiInteger
        ACCESS          read-only
        STATUS          mandatory
        DESCRIPTION     "If this is a Field Replaceable Unit or if it is partof another
FRU, this provides index into the FRU table.A Value = -1 means that the group
is not a FRU"
        ::= {eSystemEnclosure 7}

a16OperationalGroupIndex OBJECT-TYPE
        SYNTAX          DmiInteger
        ACCESS          read-only
        STATUS          mandatory
        DESCRIPTION     "The index into the Operational State Table for this device
if applicable"
        ::= {eSystemEnclosure 8}

SPowerSupply ::= SEQUENCE {
        a17PowerSupplyIndex                             DmiInteger,
        a17FruGroupIndex                                DmiInteger,
        a17OperationalGroupIndex                        DmiInteger
}

tPowerSupply OBJECT-TYPE
        SYNTAX          SEQUENCE OF SPowerSupply
        ACCESS          not-accessible
        STATUS          mandatory
        DESCRIPTION     "This group defines various attributes for power supplies
in this system."
        ::= {dmtfGroups1 17}

ePowerSupply OBJECT-TYPE
        SYNTAX          SPowerSupply
        ACCESS          not-accessible
        STATUS          mandatory
        DESCRIPTION     ""
        --INDEX           {DmiComponentIndex, a17PowerSupplyIndex}
        ::= {tPowerSupply 1}

a17PowerSupplyIndex OBJECT-TYPE
        SYNTAX          DmiInteger
        ACCESS          read-only
        STATUS          mandatory
        DESCRIPTION     "The index number of the current power supply."
        ::= {ePowerSupply 1}

a17FruGroupIndex OBJECT-TYPE
        SYNTAX          DmiInteger
        ACCESS          read-only
        STATUS          mandatory
        DESCRIPTION     "If this is a Field Replaceable Unit or if it is partof another
FRU, this provides index into the FRU table.A Value = -1 means that the group
is not a FRU"
        ::= {ePowerSupply 2}

a17OperationalGroupIndex OBJECT-TYPE
        SYNTAX          DmiInteger
        ACCESS          read-only
        STATUS          mandatory
        DESCRIPTION     "The index into the Operational State Table for this device
if applicable"
        ::= {ePowerSupply 3}

SCoolingDevice ::= SEQUENCE {
        a18CoolingDeviceIndex                           DmiInteger,
        a18FruGroupIndex                                DmiInteger,
        a18OperationalGroupIndex                        DmiInteger
}

tCoolingDevice OBJECT-TYPE
        SYNTAX          SEQUENCE OF SCoolingDevice
        ACCESS          not-accessible
        STATUS          mandatory
        DESCRIPTION     "This group defines various attributes for cooling devices
in this system."
        ::= {dmtfGroups1 18}

eCoolingDevice OBJECT-TYPE
        SYNTAX          SCoolingDevice
        ACCESS          not-accessible
        STATUS          mandatory
        DESCRIPTION     ""
        --INDEX           {DmiComponentIndex, a18CoolingDeviceIndex}
        ::= {tCoolingDevice 1}

a18CoolingDeviceIndex OBJECT-TYPE
        SYNTAX          DmiInteger
        ACCESS          read-only
        STATUS          mandatory
        DESCRIPTION     "An index into the cooling device table."
        ::= {eCoolingDevice 1}

a18FruGroupIndex OBJECT-TYPE
        SYNTAX          DmiInteger
        ACCESS          read-only
        STATUS          mandatory
        DESCRIPTION     "If this is a Field Replaceable Unit or if it is partof another
FRU, this provides index into the FRU table.A Value = -1 means that the group
is not a FRU"
        ::= {eCoolingDevice 2}

a18OperationalGroupIndex OBJECT-TYPE
        SYNTAX          DmiInteger
        ACCESS          read-only
        STATUS          mandatory
        DESCRIPTION     "The index into the Operational State Table for this device
if applicable"
        ::= {eCoolingDevice 3}

SSystemSlots ::= SEQUENCE {
        a19SlotIndex                                    DmiInteger,
        a19SlotType                                     DmiInteger,
        a19SlotWidth                                    DmiInteger,
        a19CurrentUsage                                 DmiInteger,
        a19SlotDescription                              DmiDisplaystring
}

tSystemSlots OBJECT-TYPE
        SYNTAX          SEQUENCE OF SSystemSlots
        ACCESS          not-accessible
        STATUS          mandatory
        DESCRIPTION     "This group defines the attributes for the different system
expansion slots supported in this system."
        ::= {dmtfGroups1 19}

eSystemSlots OBJECT-TYPE
        SYNTAX          SSystemSlots
        ACCESS          not-accessible
        STATUS          mandatory
        DESCRIPTION     ""
        --INDEX           {DmiComponentIndex, a19SlotIndex}
        ::= {tSystemSlots 1}

a19SlotIndex OBJECT-TYPE
        SYNTAX          DmiInteger
        ACCESS          read-only
        STATUS          mandatory
        DESCRIPTION     "An index into the system slot table. This is the hardware
ID number for each expansion slot, whether it is occupied or not (starting
with 1)"
        ::= {eSystemSlots 1}

a19SlotType OBJECT-TYPE
        SYNTAX          INTEGER {
                vUnknown                                        (1),
                vIsa                                            (2),
                vEisa                                           (4),
                vMca                                            (8),
                vPci                                            (16),
                vPciIsa                                         (18),
                vPciEisa                                        (20),
                vPciMca                                         (24)
        }
        ACCESS          read-only
        STATUS          mandatory
        DESCRIPTION     "The bus type supported in this slot. This is a bit field
with the following definitions.Bit 0, if set, means it is a long-length card;
if 0, it is a short-length cardBit 1, if set, is ISA, Bit 2 is EISA, Bit
3 is MCA, Bit 4 is PCI, Bit 5 is VL, and Bit 6 is PCMCIA."
        ::= {eSystemSlots 2}

a19SlotWidth OBJECT-TYPE
        SYNTAX          INTEGER {
                vOther                                          (1),
                vUnknown                                        (2),
                v8BitCard                                       (3),
                v16BitCard                                      (4),
                v32BitCard                                      (5),
                v64BitCard                                      (6),
                v128BitCard                                     (7)
        }
        ACCESS          read-only
        STATUS          mandatory
        DESCRIPTION     "The maximum bus width of cards accepted in this slot."
        ::= {eSystemSlots 3}

a19CurrentUsage OBJECT-TYPE
        SYNTAX          INTEGER {
                vOther                                          (1),
                vUnknown                                        (2),
                vAvailable                                      (3),
                vInUse1                                         (4)
        }
        ACCESS          read-only
        STATUS          mandatory
        DESCRIPTION     "Is this slot is currently in use?"
        ::= {eSystemSlots 4}

a19SlotDescription OBJECT-TYPE
        SYNTAX          DmiDisplaystring
        ACCESS          read-only
        STATUS          mandatory
        DESCRIPTION     "The field describes the card currently occupying this slot."
        ::= {eSystemSlots 5}

SVideo ::= SEQUENCE {
        a20VideoIndex                                   DmiInteger,
        a20VideoType                                    DmiInteger,
        a20CurrentVideoMode                             DmiInteger,
        a20MinimumRefreshRate                           DmiInteger,
        a20MaximumRefreshRate                           DmiInteger,
        a20VideoMemoryType                              DmiInteger,
        a20VideoRamMemorySize                           DmiInteger,
        a20ScanMode                                     DmiInteger,
        a20VideoPhysicalLocation                        DmiInteger,
        a20CurrentVerticalResolution                    DmiInteger,
        a20CurrentHorizontalResolution                  DmiInteger,
        a20CurrentNumberOfBitsPerPixel                  DmiInteger,
        a20CurrentNumberOfRows                          DmiInteger,
        a20CurrentNumberOfColumns                       DmiInteger,
        a20CurrentRefreshRate                           DmiInteger,
        a20FruGroupIndex                                DmiInteger,
        a20OperationalGroupIndex                        DmiInteger
}

tVideo OBJECT-TYPE
        SYNTAX          SEQUENCE OF SVideo
        ACCESS          not-accessible
        STATUS          mandatory
        DESCRIPTION     "This group defines the attributes of video devices in this
system."
        ::= {dmtfGroups1 20}

eVideo OBJECT-TYPE
        SYNTAX          SVideo
        ACCESS          not-accessible
        STATUS          mandatory
        DESCRIPTION     ""
        --INDEX           {DmiComponentIndex, a20VideoIndex}
        ::= {tVideo 1}

a20VideoIndex OBJECT-TYPE
        SYNTAX          DmiInteger
        ACCESS          read-only
        STATUS          mandatory
        DESCRIPTION     "An index into the video table."
        ::= {eVideo 1}

a20VideoType OBJECT-TYPE
        SYNTAX          INTEGER {
                vOther                                          (1),
                vUnknown                                        (2),
                vCga                                            (3),
                vEga                                            (4),
                vVga                                            (5),
                vSvga                                           (6),
                vMda                                            (7),
                vHgc                                            (8),
                vMcga                                           (9),
                v8514a                                          (10),
                vXga                                            (11),
                vLinearFrameBuffer                              (12)
        }
        ACCESS          read-only
        STATUS          mandatory
        DESCRIPTION     "The architecture of the video subsystem in this system."
        ::= {eVideo 2}

a20CurrentVideoMode OBJECT-TYPE
        SYNTAX          DmiInteger
        ACCESS          read-only
        STATUS          mandatory
        DESCRIPTION     "The current video mode in this system"
        ::= {eVideo 3}

a20MinimumRefreshRate OBJECT-TYPE
        SYNTAX          DmiInteger
        ACCESS          read-only
        STATUS          mandatory
        DESCRIPTION     "The minimum refresh rate for this video subsystem in Hz."
        ::= {eVideo 4}

a20MaximumRefreshRate OBJECT-TYPE
        SYNTAX          DmiInteger
        ACCESS          read-only
        STATUS          mandatory
        DESCRIPTION     "The maximum refresh rate for this video subsystem in Hz."
        ::= {eVideo 5}

a20VideoMemoryType OBJECT-TYPE
        SYNTAX          INTEGER {
                vOther                                          (1),
                vUnknown                                        (2),
                vVram                                           (3),
                vDram                                           (4),
                vSram                                           (5)
        }
        ACCESS          read-only
        STATUS          mandatory
        DESCRIPTION     "The type of Video Memory for this adapter."
        ::= {eVideo 6}

a20VideoRamMemorySize OBJECT-TYPE
        SYNTAX          DmiInteger
        ACCESS          read-only
        STATUS          mandatory
        DESCRIPTION     "Video adapter memory size in Kilo Bytes."
        ::= {eVideo 7}

a20ScanMode OBJECT-TYPE
        SYNTAX          INTEGER {
                vOther                                          (1),
                vUnknown                                        (2),
                vInterlaced                                     (3),
                vNonInterlaced                                  (4)
        }
        ACCESS          read-only
        STATUS          mandatory
        DESCRIPTION     "The scan mode for this video device."
        ::= {eVideo 8}

a20VideoPhysicalLocation OBJECT-TYPE
        SYNTAX          INTEGER {
                vOther                                          (1),
                vUnknown                                        (2),
                vIntegrated                                     (3),
                vAddOnCard                                      (4)
        }
        ACCESS          read-only
        STATUS          mandatory
        DESCRIPTION     "The location of the video controller circuitry."
        ::= {eVideo 9}

a20CurrentVerticalResolution OBJECT-TYPE
        SYNTAX          DmiInteger
        ACCESS          read-only
        STATUS          mandatory
        DESCRIPTION     "The current number of vertical pixels."
        ::= {eVideo 10}

a20CurrentHorizontalResolution OBJECT-TYPE
        SYNTAX          DmiInteger
        ACCESS          read-only
        STATUS          mandatory
        DESCRIPTION     "The current number of horizontal pixels."
        ::= {eVideo 11}

a20CurrentNumberOfBitsPerPixel OBJECT-TYPE
        SYNTAX          DmiInteger
        ACCESS          read-only
        STATUS          mandatory
        DESCRIPTION     "The number of bits used to display each pixel for this video
device."
        ::= {eVideo 12}

a20CurrentNumberOfRows OBJECT-TYPE
        SYNTAX          DmiInteger
        ACCESS          read-only
        STATUS          mandatory
        DESCRIPTION     "The number of rows in character mode for this video device."
        ::= {eVideo 13}

a20CurrentNumberOfColumns OBJECT-TYPE
        SYNTAX          DmiInteger
        ACCESS          read-only
        STATUS          mandatory
        DESCRIPTION     "The number of columns in character mode for this video device."
        ::= {eVideo 14}

a20CurrentRefreshRate OBJECT-TYPE
        SYNTAX          DmiInteger
        ACCESS          read-only
        STATUS          mandatory
        DESCRIPTION     "The current refresh rate in Hz for this video device."
        ::= {eVideo 15}

a20FruGroupIndex OBJECT-TYPE
        SYNTAX          DmiInteger
        ACCESS          read-only
        STATUS          mandatory
        DESCRIPTION     "If this is a Field Replaceable Unit or if it is part of another
RU, this provides an index into the FRU table. A value = -1 means that the
group is not a FRU."
        ::= {eVideo 16}

a20OperationalGroupIndex OBJECT-TYPE
        SYNTAX          DmiInteger
        ACCESS          read-only
        STATUS          mandatory
        DESCRIPTION     "The index into the Operational State Table for this device"
        ::= {eVideo 17}

SVideoBios ::= SEQUENCE {
        a21VideoBiosIndex                               DmiInteger,
        a21VideoBiosManufacturer                        DmiDisplaystring,
        a21VideoBiosVersion                             DmiDisplaystring,
        a21VideoBiosReleaseDate                         DmiDate,
        a21VideoBiosShadowingState                      DmiInteger
}

tVideoBios OBJECT-TYPE
        SYNTAX          SEQUENCE OF SVideoBios
        ACCESS          not-accessible
        STATUS          mandatory
        DESCRIPTION     "This group defines the attributes for the Video BIOS."
        ::= {dmtfGroups1 21}

eVideoBios OBJECT-TYPE
        SYNTAX          SVideoBios
        ACCESS          not-accessible
        STATUS          mandatory
        DESCRIPTION     ""
        --INDEX           {DmiComponentIndex, a21VideoBiosIndex}
        ::= {tVideoBios 1}

a21VideoBiosIndex OBJECT-TYPE
        SYNTAX          DmiInteger
        ACCESS          read-only
        STATUS          mandatory
        DESCRIPTION     "The index into the Video BIOS table."
        ::= {eVideoBios 1}

a21VideoBiosManufacturer OBJECT-TYPE
        SYNTAX          DmiDisplaystring
        ACCESS          read-only
        STATUS          mandatory
        DESCRIPTION     "The name of the company that wrote this Video BIOS."
        ::= {eVideoBios 2}

a21VideoBiosVersion OBJECT-TYPE
        SYNTAX          DmiDisplaystring
        ACCESS          read-only
        STATUS          mandatory
        DESCRIPTION     "The version number or version string of this Video BIOS."
        ::= {eVideoBios 3}

a21VideoBiosReleaseDate OBJECT-TYPE
        SYNTAX          DmiDate
        ACCESS          read-only
        STATUS          mandatory
        DESCRIPTION     "The Video BIOS release date."
        ::= {eVideoBios 4}

a21VideoBiosShadowingState OBJECT-TYPE
        SYNTAX          INTEGER {
                vFalse                                          (0),
                vTrue                                           (1)
        }
        ACCESS          read-only
        STATUS          mandatory
        DESCRIPTION     "If true, the Video BIOS is currently being shadowed "
        ::= {eVideoBios 5}

SVideoBiosCharacteristic ::= SEQUENCE {
        a22VideoBiosCharacteristicsIndex                DmiInteger,
        a22VideoBiosNumber                              DmiInteger,
        a22VideoBiosCharacteristics                     DmiInteger,
        a22VideoBiosCharacteristicsDescription          DmiDisplaystring
}

tVideoBiosCharacteristic OBJECT-TYPE
        SYNTAX          SEQUENCE OF SVideoBiosCharacteristic
        ACCESS          not-accessible
        STATUS          mandatory
        DESCRIPTION     "This group defines the characteristics for the Video BIOS."
        ::= {dmtfGroups1 22}

eVideoBiosCharacteristic OBJECT-TYPE
        SYNTAX          SVideoBiosCharacteristic
        ACCESS          not-accessible
        STATUS          mandatory
        DESCRIPTION     ""
        --INDEX           {DmiComponentIndex, a22VideoBiosCharacteristicsIndex, a22VideoBiosNumber}
        ::= {tVideoBiosCharacteristic 1}

a22VideoBiosCharacteristicsIndex OBJECT-TYPE
        SYNTAX          DmiInteger
        ACCESS          read-only
        STATUS          mandatory
        DESCRIPTION     "This is an index into the Video BIOS Characteristics table.
"
        ::= {eVideoBiosCharacteristic 1}

a22VideoBiosNumber OBJECT-TYPE
        SYNTAX          DmiInteger
        ACCESS          read-only
        STATUS          mandatory
        DESCRIPTION     "This is the Video BIOS number which correlates to the Video
BIOS Index. "
        ::= {eVideoBiosCharacteristic 2}

a22VideoBiosCharacteristics OBJECT-TYPE
        SYNTAX          INTEGER {
                vOther                                          (1),
                vUnknown                                        (2),
                vUnsupported                                    (3),
                vStandardVideoBios                              (4),
                vVesaBiosExtensionsSupported                    (5),
                vVesaPowerManagementSupported                   (6),
                vVesaDisplayDataChannelSupported                (7),
                vVideoBios-shadowing-allowed                    (8),
                vVideoBiosUpgradable                            (9)
        }
        ACCESS          read-only
        STATUS          mandatory
        DESCRIPTION     "The attributes and extensions supported by this version of
the Video BIOS"
        ::= {eVideoBiosCharacteristic 3}

a22VideoBiosCharacteristicsDescription OBJECT-TYPE
        SYNTAX          DmiDisplaystring
        ACCESS          read-only
        STATUS          mandatory
        DESCRIPTION     "Expanded description of this VIDEO BIOS Characteristic."
        ::= {eVideoBiosCharacteristic 4}

SDiskDrives ::= SEQUENCE {
        a23StorageType                                  DmiInteger,
        a23DiskIndex                                    DmiInteger,
        a23StorageInterfaceType                         DmiInteger,
        a23InterfaceDescription                         DmiDisplaystring,
        a23MediaLoaded                                  DmiInteger,
        a23RemovableMedia                               DmiInteger,
        a23DeviceId                                     DmiInteger,
        a23LogicalUnitNumber                            DmiInteger,
        a23NumberOfPhysicalCylinders                    DmiInteger,
        a23NumberOfPhysicalSectorsPerTrack              DmiInteger,
        a23NumberOfPhysicalHeads                        DmiInteger,
        a23SectorSize                                   DmiInteger,
        a23TotalPhysicalSize                            DmiInteger,
        a23Partitions                                   DmiInteger,
        a23FruGroupIndex                                DmiInteger
}

tDiskDrives OBJECT-TYPE
        SYNTAX          SEQUENCE OF SDiskDrives
        ACCESS          not-accessible
        STATUS          mandatory
        DESCRIPTION     "This group defines the physical attributes of disk mass storage
devices in this system."
        ::= {dmtfGroups1 23}

eDiskDrives OBJECT-TYPE
        SYNTAX          SDiskDrives
        ACCESS          not-accessible
        STATUS          mandatory
        DESCRIPTION     ""
        --INDEX           {DmiComponentIndex, a23StorageType, a23DiskIndex}
        ::= {tDiskDrives 1}

a23StorageType OBJECT-TYPE
        SYNTAX          INTEGER {
                vOther                                          (1),
                vUnknown                                        (2),
                vHard-disk                                      (3),
                vFloppy-disk                                    (4),
                vOptical-rom                                    (5),
                vOptical-worm                                   (6),
                vOptical-rw                                     (7),
                vCompact-disk                                   (8),
                vFlash-disk                                     (9),
                vBernoulli                                      (10),
                vOpticalFloppyDisk                              (11)
        }
        ACCESS          read-only
        STATUS          mandatory
        DESCRIPTION     "The type of this mass storage device"
        ::= {eDiskDrives 1}

a23DiskIndex OBJECT-TYPE
        SYNTAX          DmiInteger
        ACCESS          read-only
        STATUS          mandatory
        DESCRIPTION     "An index into the disk table."
        ::= {eDiskDrives 2}

a23StorageInterfaceType OBJECT-TYPE
        SYNTAX          INTEGER {
                vOther                                          (1),
                vUnknown                                        (2),
                vScsi                                           (3),
                vEsdi                                           (4),
                vIde                                            (5),
                vCmd                                            (6),
                vIpi                                            (7),
                vSt506                                          (8),
                vDssi                                           (9),
                vParallel-port                                  (10),
                vHippi                                          (11),
                vQic2                                           (12),
                vFloppy-disk-interface                          (13),
                vPcmcia                                         (14),
                vEnhancedAtaide                                 (15)
        }
        ACCESS          read-only
        STATUS          mandatory
        DESCRIPTION     "The interface used by this mass storage device"
        ::= {eDiskDrives 3}

a23InterfaceDescription OBJECT-TYPE
        SYNTAX          DmiDisplaystring
        ACCESS          read-only
        STATUS          mandatory
        DESCRIPTION     "A longer description of the mass storage interface.For Example,
SCSI2 fast wide"
        ::= {eDiskDrives 4}

a23MediaLoaded OBJECT-TYPE
        SYNTAX          INTEGER {
                vFalse                                          (0),
                vTrue                                           (1)
        }
        ACCESS          read-only
        STATUS          mandatory
        DESCRIPTION     "If true, the media is loaded"
        ::= {eDiskDrives 5}

a23RemovableMedia OBJECT-TYPE
        SYNTAX          INTEGER {
                vFalse                                          (0),
                vTrue                                           (1)
        }
        ACCESS          read-only
        STATUS          mandatory
        DESCRIPTION     "If true, the media in this drive is removable"
        ::= {eDiskDrives 6}

a23DeviceId OBJECT-TYPE
        SYNTAX          DmiInteger
        ACCESS          read-only
        STATUS          mandatory
        DESCRIPTION     "The SCSI address of this device"
        ::= {eDiskDrives 7}

a23LogicalUnitNumber OBJECT-TYPE
        SYNTAX          DmiInteger
        ACCESS          read-only
        STATUS          mandatory
        DESCRIPTION     "The logical unit number of this SCSI device. "
        ::= {eDiskDrives 8}

a23NumberOfPhysicalCylinders OBJECT-TYPE
        SYNTAX          DmiInteger
        ACCESS          read-only
        STATUS          mandatory
        DESCRIPTION     "The number of reported Physical Cylinders on this device"
        ::= {eDiskDrives 9}

a23NumberOfPhysicalSectorsPerTrack OBJECT-TYPE
        SYNTAX          DmiInteger
        ACCESS          read-only
        STATUS          mandatory
        DESCRIPTION     "The number of reported Physical sectors per track for this
device"
        ::= {eDiskDrives 10}

a23NumberOfPhysicalHeads OBJECT-TYPE
        SYNTAX          DmiInteger
        ACCESS          read-only
        STATUS          mandatory
        DESCRIPTION     "The number of reported Physical heads for this device"
        ::= {eDiskDrives 11}

a23SectorSize OBJECT-TYPE
        SYNTAX          DmiInteger
        ACCESS          read-only
        STATUS          mandatory
        DESCRIPTION     "The Size in bytes of the physical disk sector as reported
by the disk. "
        ::= {eDiskDrives 12}

a23TotalPhysicalSize OBJECT-TYPE
        SYNTAX          DmiInteger
        ACCESS          read-only
        STATUS          mandatory
        DESCRIPTION     "The total size in KiloBytes (1024 bytes) of this device.
"
        ::= {eDiskDrives 13}

a23Partitions OBJECT-TYPE
        SYNTAX          DmiInteger
        ACCESS          read-only
        STATUS          mandatory
        DESCRIPTION     "The number of partitions on this storage unit"
        ::= {eDiskDrives 14}

a23FruGroupIndex OBJECT-TYPE
        SYNTAX          DmiInteger
        ACCESS          read-only
        STATUS          mandatory
        DESCRIPTION     "If this is a Field Replaceable Unit or if it is part of another
FRU, this provides an index into the FRU table. A value = -1 means that the
group is not a FRU."
        ::= {eDiskDrives 15}

SDiskMappingTable ::= SEQUENCE {
        a24StorageType                                  DmiInteger,
        a24DiskIndex                                    DmiInteger,
        a24PartitionIndex                               DmiInteger
}

tDiskMappingTable OBJECT-TYPE
        SYNTAX          SEQUENCE OF SDiskMappingTable
        ACCESS          not-accessible
        STATUS          mandatory
        DESCRIPTION     "A table relating disks to partitions. May have an instance
of a disk or partition more than once"
        ::= {dmtfGroups1 24}

eDiskMappingTable OBJECT-TYPE
        SYNTAX          SDiskMappingTable
        ACCESS          not-accessible
        STATUS          mandatory
        DESCRIPTION     ""
        --INDEX           {DmiComponentIndex, a24StorageType, a24DiskIndex, a24PartitionIndex}
        ::= {tDiskMappingTable 1}

a24StorageType OBJECT-TYPE
        SYNTAX          INTEGER {
                vOther                                          (1),
                vUnknown                                        (2),
                vHard-disk                                      (3),
                vFloppy-disk                                    (4),
                vOptical-rom                                    (5),
                vOptical-worm                                   (6),
                vOptical-rw                                     (7),
                vCompact-disk                                   (8),
                vFlash-disk                                     (9),
                vBernoulli                                      (10),
                vOpticalFloppyDisk                              (11)
        }
        ACCESS          read-only
        STATUS          mandatory
        DESCRIPTION     "An index value into the Disk Table"
        ::= {eDiskMappingTable 1}

a24DiskIndex OBJECT-TYPE
        SYNTAX          DmiInteger
        ACCESS          read-only
        STATUS          mandatory
        DESCRIPTION     "An index value into the Disk Table"
        ::= {eDiskMappingTable 2}

a24PartitionIndex OBJECT-TYPE
        SYNTAX          DmiInteger
        ACCESS          read-only
        STATUS          mandatory
        DESCRIPTION     "An index value into the partition table"
        ::= {eDiskMappingTable 3}

SPartition ::= SEQUENCE {
        a25PartitionIndex                               DmiInteger,
        a25PartitionName                                DmiDisplaystring,
        a25PartitionSize                                DmiInteger64,
        a25FreeSpace                                    DmiInteger64,
        a25PartitionLabel                               DmiOctetstring,
        a25FileSystem                                   DmiInteger,
        a25Compressed                                   DmiInteger,
        a25Encrypted                                    DmiInteger,
        a25NumberOfDisksOccupied                        DmiInteger
}

tPartition OBJECT-TYPE
        SYNTAX          SEQUENCE OF SPartition
        ACCESS          not-accessible
        STATUS          mandatory
        DESCRIPTION     "This group describes the partitions on particular disks."
        ::= {dmtfGroups1 25}

ePartition OBJECT-TYPE
        SYNTAX          SPartition
        ACCESS          not-accessible
        STATUS          mandatory
        DESCRIPTION     ""
        --INDEX           {DmiComponentIndex, a25PartitionIndex}
        ::= {tPartition 1}

a25PartitionIndex OBJECT-TYPE
        SYNTAX          DmiInteger
        ACCESS          read-only
        STATUS          mandatory
        DESCRIPTION     "The index into the partition table."
        ::= {ePartition 1}

a25PartitionName OBJECT-TYPE
        SYNTAX          DmiDisplaystring
        ACCESS          read-only
        STATUS          mandatory
        DESCRIPTION     "The name used by the system to identify the partition. This
is normally the drive letter."
        ::= {ePartition 2}

a25PartitionSize OBJECT-TYPE
        SYNTAX          DmiInteger64
        ACCESS          read-only
        STATUS          mandatory
        DESCRIPTION     "The size of this partition in Kilo Bytes."
        ::= {ePartition 3}

a25FreeSpace OBJECT-TYPE
        SYNTAX          DmiInteger64
        ACCESS          read-only
        STATUS          mandatory
        DESCRIPTION     "The number of free Kilo Bytes on this partition"
        ::= {ePartition 4}

a25PartitionLabel OBJECT-TYPE
        SYNTAX          DmiOctetstring
        ACCESS          read-only
        STATUS          mandatory
        DESCRIPTION     "The Partition label or the unique volume label field for
this physical volume. (For DOS, this is the volume label plus the 32 bit
Volume ID field if available.)"
        ::= {ePartition 5}

a25FileSystem OBJECT-TYPE
        SYNTAX          INTEGER {
                vOther                                          (1),
                vUnknown                                        (2),
                vFat                                            (3),
                vHpfs                                           (4),
                vNtfs                                           (5),
                vOfs                                            (6),
                vMfs                                            (7),
                vHfs                                            (8),
                vVxfs                                           (9),
                vSfs                                            (10),
                vS5                                             (11),
                vS52k                                           (12),
                vUfs                                            (13),
                vFfs                                            (14),
                vNetware286                                     (15),
                vNetware386                                     (16)
        }
        ACCESS          read-only
        STATUS          mandatory
        DESCRIPTION     ""
        ::= {ePartition 6}

a25Compressed OBJECT-TYPE
        SYNTAX          INTEGER {
                vFalse                                          (0),
                vTrue                                           (1)
        }
        ACCESS          read-only
        STATUS          mandatory
        DESCRIPTION     "If true, this partition is compressed"
        ::= {ePartition 7}

a25Encrypted OBJECT-TYPE
        SYNTAX          INTEGER {
                vFalse                                          (0),
                vTrue                                           (1)
        }
        ACCESS          read-only
        STATUS          mandatory
        DESCRIPTION     "If true, this partition is encrypted"
        ::= {ePartition 8}

a25NumberOfDisksOccupied OBJECT-TYPE
        SYNTAX          DmiInteger
        ACCESS          read-only
        STATUS          mandatory
        DESCRIPTION     "The number of disks this partition occupies"
        ::= {ePartition 9}

SDiskController ::= SEQUENCE {
        a26DiskControllerIndex                          DmiInteger,
        a26FruGroupIndex                                DmiInteger,
        a26OperationalGroupIndex                        DmiInteger
}

tDiskController OBJECT-TYPE
        SYNTAX          SEQUENCE OF SDiskController
        ACCESS          not-accessible
        STATUS          mandatory
        DESCRIPTION     "This group defines the disk controller in this system."
        ::= {dmtfGroups1 26}

eDiskController OBJECT-TYPE
        SYNTAX          SDiskController
        ACCESS          not-accessible
        STATUS          mandatory
        DESCRIPTION     ""
        --INDEX           {DmiComponentIndex, a26DiskControllerIndex}
        ::= {tDiskController 1}

a26DiskControllerIndex OBJECT-TYPE
        SYNTAX          DmiInteger
        ACCESS          read-only
        STATUS          mandatory
        DESCRIPTION     "Index value used by the system to identify the disk controller"
        ::= {eDiskController 1}

a26FruGroupIndex OBJECT-TYPE
        SYNTAX          DmiInteger
        ACCESS          read-only
        STATUS          mandatory
        DESCRIPTION     "If this is a Field Replaceable Unit or if it is part of another
FRU, this provides an index into the FRU table. A value = -1 means that the
group is not a FRU"
        ::= {eDiskController 2}

a26OperationalGroupIndex OBJECT-TYPE
        SYNTAX          DmiInteger
        ACCESS          read-only
        STATUS          mandatory
        DESCRIPTION     "The index into the Operational State Table for this device"
        ::= {eDiskController 3}

SLogicalDrives ::= SEQUENCE {
        a27LogicalDriveIndex                            DmiInteger,
        a27LogicalDriveName                             DmiDisplaystring,
        a27LogicalDriveType                             DmiInteger,
        a27LogicalDriveSize                             DmiInteger,
        a27FreeLogicalDriveSize                         DmiInteger,
        a27LogicalDrivePath                             DmiDisplaystring
}

tLogicalDrives OBJECT-TYPE
        SYNTAX          SEQUENCE OF SLogicalDrives
        ACCESS          not-accessible
        STATUS          mandatory
        DESCRIPTION     ""
        ::= {dmtfGroups1 27}

eLogicalDrives OBJECT-TYPE
        SYNTAX          SLogicalDrives
        ACCESS          not-accessible
        STATUS          mandatory
        DESCRIPTION     ""
        --INDEX           {DmiComponentIndex, a27LogicalDriveIndex}
        ::= {tLogicalDrives 1}

a27LogicalDriveIndex OBJECT-TYPE
        SYNTAX          DmiInteger
        ACCESS          read-only
        STATUS          mandatory
        DESCRIPTION     "An index into the Logical Drives Table"
        ::= {eLogicalDrives 1}

a27LogicalDriveName OBJECT-TYPE
        SYNTAX          DmiDisplaystring
        ACCESS          read-only
        STATUS          mandatory
        DESCRIPTION     "Name used by the system to identify this logical driveFor
DOS, this could be the logical drive letter (A,B,C...)"
        ::= {eLogicalDrives 2}

a27LogicalDriveType OBJECT-TYPE
        SYNTAX          INTEGER {
                vOther                                          (1),
                vUnknown                                        (2),
                vFixedDrive                                     (3),
                vRemovableDrive                                 (4),
                vRemoteDrive                                    (5),
                vCdrom                                          (6),
                vFloppyDrive                                    (7),
                vRamDrive                                       (8),
                vDriveArray                                     (9)
        }
        ACCESS          read-only
        STATUS          mandatory
        DESCRIPTION     "This defines the Logical Drive type"
        ::= {eLogicalDrives 3}

a27LogicalDriveSize OBJECT-TYPE
        SYNTAX          DmiInteger
        ACCESS          read-only
        STATUS          mandatory
        DESCRIPTION     "The size of this Logical Drive in Kilo Bytes"
        ::= {eLogicalDrives 4}

a27FreeLogicalDriveSize OBJECT-TYPE
        SYNTAX          DmiInteger
        ACCESS          read-only
        STATUS          mandatory
        DESCRIPTION     "The remaining space on this Logical Drive in Kilo Bytes"
        ::= {eLogicalDrives 5}

a27LogicalDrivePath OBJECT-TYPE
        SYNTAX          DmiDisplaystring
        ACCESS          read-only
        STATUS          mandatory
        DESCRIPTION     "The path used to access this Logical Drive (for remote drives)"
        ::= {eLogicalDrives 6}

SMouse ::= SEQUENCE {
        a28MouseInterface                               DmiInteger,
        a28MouseIrq                                     DmiInteger,
        a28MouseButtons                                 DmiInteger,
        a28MousePortName                                DmiDisplaystring,
        a28MouseDriverName                              DmiDisplaystring,
        a28MouseDriverVersion                           DmiDisplaystring,
        a28FruGroupIndex                                DmiInteger,
        a28OperationalGroupIndex                        DmiInteger
}

tMouse OBJECT-TYPE
        SYNTAX          SEQUENCE OF SMouse
        ACCESS          not-accessible
        STATUS          mandatory
        DESCRIPTION     ""
        ::= {dmtfGroups1 28}

eMouse OBJECT-TYPE
        SYNTAX          SMouse
        ACCESS          not-accessible
        STATUS          mandatory
        DESCRIPTION     ""
        --INDEX           {DmiComponentIndex}
        ::= {tMouse 1}

a28MouseInterface OBJECT-TYPE
        SYNTAX          INTEGER {
                vOther                                          (1),
                vUnknown                                        (2),
                vSerial                                         (3),
                vPs2                                            (4),
                vInfrared                                       (5),
                vHp-hil                                         (6),
                vBusMouse                                       (7)
        }
        ACCESS          read-only
        STATUS          mandatory
        DESCRIPTION     "The interface type of this mouse."
        ::= {eMouse 1}

a28MouseIrq OBJECT-TYPE
        SYNTAX          DmiInteger
        ACCESS          read-only
        STATUS          mandatory
        DESCRIPTION     "The IRQ number used by this mouse."
        ::= {eMouse 2}

a28MouseButtons OBJECT-TYPE
        SYNTAX          DmiInteger
        ACCESS          read-only
        STATUS          mandatory
        DESCRIPTION     "The number of mouse buttons on this mouse."
        ::= {eMouse 3}

a28MousePortName OBJECT-TYPE
        SYNTAX          DmiDisplaystring
        ACCESS          read-only
        STATUS          mandatory
        DESCRIPTION     "The name of the port currently being used by this mouse."
        ::= {eMouse 4}

a28MouseDriverName OBJECT-TYPE
        SYNTAX          DmiDisplaystring
        ACCESS          read-only
        STATUS          mandatory
        DESCRIPTION     "The name of the mouse driver."
        ::= {eMouse 5}

a28MouseDriverVersion OBJECT-TYPE
        SYNTAX          DmiDisplaystring
        ACCESS          read-only
        STATUS          mandatory
        DESCRIPTION     "The version number of the mouse driver."
        ::= {eMouse 6}

a28FruGroupIndex OBJECT-TYPE
        SYNTAX          DmiInteger
        ACCESS          read-only
        STATUS          mandatory
        DESCRIPTION     "If this is a Field Replaceable Unit or if it is part of another
FRU, this attribute provides an index into the FRU table. A value = -1 means
that the group is not a FRU"
        ::= {eMouse 7}

a28OperationalGroupIndex OBJECT-TYPE
        SYNTAX          DmiInteger
        ACCESS          read-only
        STATUS          mandatory
        DESCRIPTION     "The index into the Operational State Table for this device"
        ::= {eMouse 8}

SKeyboard ::= SEQUENCE {
        a29KeyboardLayout                               DmiDisplaystring,
        a29KeyboardType                                 DmiDisplaystring,
        a29KeyboardConnectorType                        DmiInteger,
        a29FruGroupIndex                                DmiInteger,
        a29OperationalGroupIndex                        DmiInteger
}

tKeyboard OBJECT-TYPE
        SYNTAX          SEQUENCE OF SKeyboard
        ACCESS          not-accessible
        STATUS          mandatory
        DESCRIPTION     "This group defines the characteristics of the PC keyboard"
        ::= {dmtfGroups1 29}

eKeyboard OBJECT-TYPE
        SYNTAX          SKeyboard
        ACCESS          not-accessible
        STATUS          mandatory
        DESCRIPTION     ""
        --INDEX           {DmiComponentIndex}
        ::= {tKeyboard 1}

a29KeyboardLayout OBJECT-TYPE
        SYNTAX          DmiDisplaystring
        ACCESS          read-only
        STATUS          mandatory
        DESCRIPTION     "A description of the layout description  of this keyboard."
        ::= {eKeyboard 1}

a29KeyboardType OBJECT-TYPE
        SYNTAX          DmiDisplaystring
        ACCESS          read-only
        STATUS          mandatory
        DESCRIPTION     "The type description of this keyboard."
        ::= {eKeyboard 2}

a29KeyboardConnectorType OBJECT-TYPE
        SYNTAX          INTEGER {
                vOther                                          (1),
                vUnknown                                        (2),
                vMini-din                                       (3),
                vMicro-din                                      (4),
                vPs2                                            (5),
                vInfrared                                       (6),
                vHp-hil                                         (7),
                vDb-9                                           (8),
                vAccessbus                                      (9)
        }
        ACCESS          read-only
        STATUS          mandatory
        DESCRIPTION     "The type description of the keyboard connector used by this
keyboard."
        ::= {eKeyboard 3}

a29FruGroupIndex OBJECT-TYPE
        SYNTAX          DmiInteger
        ACCESS          read-only
        STATUS          mandatory
        DESCRIPTION     "If this is a Field Replaceable Unit or if it is part of another
FRU, this provides an FRU index into the FRU table. A value = -1 means that
the group is not a FRU"
        ::= {eKeyboard 4}

a29OperationalGroupIndex OBJECT-TYPE
        SYNTAX          DmiInteger
        ACCESS          read-only
        STATUS          mandatory
        DESCRIPTION     "The index into the Operational State Table for this device"
        ::= {eKeyboard 5}

SFieldReplacableUnit ::= SEQUENCE {
        a30FruIndex                                     DmiInteger,
        a30DeviceGroupIndex                             DmiInteger,
        a30Description                                  DmiDisplaystring,
        a30Manufacturer                                 DmiDisplaystring,
        a30Model                                        DmiDisplaystring,
        a30PartNumber                                   DmiDisplaystring,
        a30FruSerialNumber                              DmiDisplaystring,
        a30RevisionLevel                                DmiDisplaystring
}

tFieldReplacableUnit OBJECT-TYPE
        SYNTAX          SEQUENCE OF SFieldReplacableUnit
        ACCESS          not-accessible
        STATUS          mandatory
        DESCRIPTION     "An FRU, or Field Replaceable Unit, is defined as a hardware
component which is designed to be separately removable for replacement or
repair. For the purposes of this definition, a motherboard and a fixed hard
disk are FRU's, whereas a fixed hard disk platter or a chip fixed in place
on the motherboard are not FRU's since they are not designed to be separately
removable. Each instance within the FRU table should contain the device group
and instance data for the associated hardware component"
        ::= {dmtfGroups1 30}

eFieldReplacableUnit OBJECT-TYPE
        SYNTAX          SFieldReplacableUnit
        ACCESS          not-accessible
        STATUS          mandatory
        DESCRIPTION     ""
        --INDEX           {DmiComponentIndex, a30FruIndex}
        ::= {tFieldReplacableUnit 1}

a30FruIndex OBJECT-TYPE
        SYNTAX          DmiInteger
        ACCESS          read-only
        STATUS          mandatory
        DESCRIPTION     "The index into the FRU table"
        ::= {eFieldReplacableUnit 1}

a30DeviceGroupIndex OBJECT-TYPE
        SYNTAX          DmiInteger
        ACCESS          read-only
        STATUS          mandatory
        DESCRIPTION     "The group ID of the group referencing this FRU instance"
        ::= {eFieldReplacableUnit 2}

a30Description OBJECT-TYPE
        SYNTAX          DmiDisplaystring
        ACCESS          read-write
        STATUS          mandatory
        DESCRIPTION     "A clear description of this FRU"
        ::= {eFieldReplacableUnit 3}

a30Manufacturer OBJECT-TYPE
        SYNTAX          DmiDisplaystring
        ACCESS          read-write
        STATUS          mandatory
        DESCRIPTION     "The name of the company manufacturing or providing this FRU"
        ::= {eFieldReplacableUnit 4}

a30Model OBJECT-TYPE
        SYNTAX          DmiDisplaystring
        ACCESS          read-write
        STATUS          mandatory
        DESCRIPTION     "The manufacturer's model number for this FRU"
        ::= {eFieldReplacableUnit 5}

a30PartNumber OBJECT-TYPE
        SYNTAX          DmiDisplaystring
        ACCESS          read-write
        STATUS          mandatory
        DESCRIPTION     "A part number by which a replacement part can be ordered
for this FRU"
        ::= {eFieldReplacableUnit 6}

a30FruSerialNumber OBJECT-TYPE
        SYNTAX          DmiDisplaystring
        ACCESS          read-write
        STATUS          mandatory
        DESCRIPTION     "The manufacturer's serial number for this FRU"
        ::= {eFieldReplacableUnit 7}

a30RevisionLevel OBJECT-TYPE
        SYNTAX          DmiDisplaystring
        ACCESS          read-write
        STATUS          mandatory
        DESCRIPTION     "The revision level of this FRU"
        ::= {eFieldReplacableUnit 8}

SOperationalState ::= SEQUENCE {
        a31OperationalStateInstanceIndex                DmiInteger,
        a31DeviceGroupIndex                             DmiInteger,
        a31OperationalStatus                            DmiInteger,
        a31UsageState                                   DmiInteger,
        a31AvailabilityStatus                           DmiInteger,
        a31AdministrativeState                          DmiInteger,
        a31FatalErrorCount                              DmiCounter,
        a31MajorErrorCount                              DmiCounter,
        a31WarningErrorCount                            DmiCounter
}

tOperationalState OBJECT-TYPE
        SYNTAX          SEQUENCE OF SOperationalState
        ACCESS          not-accessible
        STATUS          mandatory
        DESCRIPTION     "This group provides the operational state, usage, and availabili
y status, and administrative state indicators for specific Device Group instance
."
        ::= {dmtfGroups1 31}

eOperationalState OBJECT-TYPE
        SYNTAX          SOperationalState
        ACCESS          not-accessible
        STATUS          mandatory
        DESCRIPTION     ""
        --INDEX           {DmiComponentIndex, a31OperationalStateInstanceIndex}
        ::= {tOperationalState 1}

a31OperationalStateInstanceIndex OBJECT-TYPE
        SYNTAX          DmiInteger
        ACCESS          read-only
        STATUS          mandatory
        DESCRIPTION     "The Index into the Operational State table"
        ::= {eOperationalState 1}

a31DeviceGroupIndex OBJECT-TYPE
        SYNTAX          DmiInteger
        ACCESS          read-only
        STATUS          mandatory
        DESCRIPTION     "The group ID of the group referencing this instance"
        ::= {eOperationalState 2}

a31OperationalStatus OBJECT-TYPE
        SYNTAX          INTEGER {
                vOther                                          (1),
                vUnknown                                        (2),
                vEnabled                                        (3),
                vDisabled                                       (4),
                vNotApplicable                                  (5)
        }
        ACCESS          read-only
        STATUS          mandatory
        DESCRIPTION     "The operational status of the Device group instance"
        ::= {eOperationalState 3}

a31UsageState OBJECT-TYPE
        SYNTAX          INTEGER {
                vOther                                          (1),
                vUnknown                                        (2),
                vIdle                                           (3),
                vActive                                         (4),
                vBusy                                           (5),
                vNotApplicable1                                 (6)
        }
        ACCESS          read-only
        STATUS          mandatory
        DESCRIPTION     "The usage state of the Device Group instance"
        ::= {eOperationalState 4}

a31AvailabilityStatus OBJECT-TYPE
        SYNTAX          INTEGER {
                vOther                                          (1),
                vUnknown                                        (2),
                vRunning                                        (3),
                vWarning                                        (4),
                vInTest                                         (5),
                vNotApplicable                                  (6),
                vPowerOff                                       (7),
                vOffLine                                        (8),
                vOffDuty                                        (9),
                vDegraded                                       (10),
                vNotInstalled                                   (11),
                vInstallError                                   (12),
                vPowerSave                                      (13)
        }
        ACCESS          read-only
        STATUS          mandatory
        DESCRIPTION     "The availability status of the Device Group instance"
        ::= {eOperationalState 5}

a31AdministrativeState OBJECT-TYPE
        SYNTAX          INTEGER {
                vOther                                          (1),
                vUnknown                                        (2),
                vLocked                                         (3),
                vUnlocked                                       (4),
                vNotApplicable                                  (5),
                vShuttingDown                                   (6)
        }
        ACCESS          read-only
        STATUS          mandatory
        DESCRIPTION     "The administrative state of the Device Group instance"
        ::= {eOperationalState 6}

a31FatalErrorCount OBJECT-TYPE
        SYNTAX          DmiCounter
        ACCESS          read-only
        STATUS          mandatory
        DESCRIPTION     "The accumulated fatal error count for this Device Group Instance"
        ::= {eOperationalState 7}

a31MajorErrorCount OBJECT-TYPE
        SYNTAX          DmiCounter
        ACCESS          read-only
        STATUS          mandatory
        DESCRIPTION     "The accumulated major error count for this Device Group Instance"
        ::= {eOperationalState 8}

a31WarningErrorCount OBJECT-TYPE
        SYNTAX          DmiCounter
        ACCESS          read-only
        STATUS          mandatory
        DESCRIPTION     "The accumulated warning error count for this Device Group
Instance"
        ::= {eOperationalState 9}

SSystemResourcesDescription ::= SEQUENCE {
        a32DeviceCount                                  DmiInteger,
        a32SystemResourceCount                          DmiInteger
}

tSystemResourcesDescription OBJECT-TYPE
        SYNTAX          SEQUENCE OF SSystemResourcesDescription
        ACCESS          not-accessible
        STATUS          mandatory
        DESCRIPTION     "The System Resources Description group describes the number
of entries in the System Resources Group. "
        ::= {dmtfGroups1 32}

eSystemResourcesDescription OBJECT-TYPE
        SYNTAX          SSystemResourcesDescription
        ACCESS          not-accessible
        STATUS          mandatory
        DESCRIPTION     ""
        --INDEX           {DmiComponentIndex, a32DeviceCount}
        ::= {tSystemResourcesDescription 1}

a32DeviceCount OBJECT-TYPE
        SYNTAX          DmiInteger
        ACCESS          read-only
        STATUS          mandatory
        DESCRIPTION     "A counter of the number of different hardware devices represente
 in this table."
        ::= {eSystemResourcesDescription 1}

a32SystemResourceCount OBJECT-TYPE
        SYNTAX          DmiInteger
        ACCESS          read-only
        STATUS          mandatory
        DESCRIPTION     "A count of the total number of system resources on this sytemins
ances in this table."
        ::= {eSystemResourcesDescription 2}

SSystemResources ::= SEQUENCE {
        a33ResourceInstance                             DmiInteger,
        a33ResourceParentGroupIndex                     DmiInteger,
        a33ResourceType                                 DmiInteger,
        a33ResourceBase                                 DmiInteger,
        a33ResourceSize                                 DmiInteger,
        a33ResourceFlags                                DmiInteger
}

tSystemResources OBJECT-TYPE
        SYNTAX          SEQUENCE OF SSystemResources
        ACCESS          not-accessible
        STATUS          mandatory
        DESCRIPTION     "The System Resources group contains hardware descriptions
which are commonly used in PC style computers such as IRQs, IO ports and
memory address ranges."
        ::= {dmtfGroups1 33}

eSystemResources OBJECT-TYPE
        SYNTAX          SSystemResources
        ACCESS          not-accessible
        STATUS          mandatory
        DESCRIPTION     ""
        --INDEX           {DmiComponentIndex, a33ResourceInstance, a33ResourceParentGroupIndex}
        ::= {tSystemResources 1}

a33ResourceInstance OBJECT-TYPE
        SYNTAX          DmiInteger
        ACCESS          read-only
        STATUS          mandatory
        DESCRIPTION     "Instance identifier for a group in this table."
        ::= {eSystemResources 1}

a33ResourceParentGroupIndex OBJECT-TYPE
        SYNTAX          DmiInteger
        ACCESS          read-only
        STATUS          mandatory
        DESCRIPTION     "The group ID of the group referencing this instance in the
table"
        ::= {eSystemResources 2}

a33ResourceType OBJECT-TYPE
        SYNTAX          INTEGER {
                vOther                                          (1),
                vUnknown                                        (2),
                vMemoryRange                                    (3),
                vIoPort                                         (4),
                vIrq                                            (5),
                vDma                                            (6)
        }
        ACCESS          read-only
        STATUS          mandatory
        DESCRIPTION     "The type of system resource represented by this entry."
        ::= {eSystemResources 3}

a33ResourceBase OBJECT-TYPE
        SYNTAX          DmiInteger
        ACCESS          read-only
        STATUS          mandatory
        DESCRIPTION     "The starting address of the system resource in the appropriatead
ress space."
        ::= {eSystemResources 4}

a33ResourceSize OBJECT-TYPE
        SYNTAX          DmiInteger
        ACCESS          read-only
        STATUS          mandatory
        DESCRIPTION     "The size of the system resource."
        ::= {eSystemResources 5}

a33ResourceFlags OBJECT-TYPE
        SYNTAX          DmiInteger
        ACCESS          read-only
        STATUS          mandatory
        DESCRIPTION     "This attribute contains fields representing the status of
this resource entry. The meaning of this field varies according to the the
Resource Type field in this group."
        ::= {eSystemResources 6}

SNetfinityDmiInstall ::= SEQUENCE {
        a34ProductName                                  DmiDisplaystring
}

tNetfinityDmiInstall OBJECT-TYPE
        SYNTAX          SEQUENCE OF SNetfinityDmiInstall
        ACCESS          not-accessible
        STATUS          mandatory
        DESCRIPTION     "This group uniquely identifies NetFinity's instrumentation
of this PC Systems MIF."
        ::= {dmtfGroups1 34}

eNetfinityDmiInstall OBJECT-TYPE
        SYNTAX          SNetfinityDmiInstall
        ACCESS          not-accessible
        STATUS          mandatory
        DESCRIPTION     ""
        --INDEX           {DmiComponentIndex}
        ::= {tNetfinityDmiInstall 1}

a34ProductName OBJECT-TYPE
        SYNTAX          DmiDisplaystring
        ACCESS          read-only
        STATUS          mandatory
        DESCRIPTION     "Name of this product"
        ::= {eNetfinityDmiInstall 1}

SMicrochannelAdapterInformation ::= SEQUENCE {
        a35AdapterIndex                                 DmiInteger,
        a35SlotNumber                                   DmiInteger,
        a35AdapterId                                    DmiDisplaystring,
        a35PosData                                      DmiDisplaystring,
        a35AdapterName                                  DmiDisplaystring
}

tMicrochannelAdapterInformation OBJECT-TYPE
        SYNTAX          SEQUENCE OF SMicrochannelAdapterInformation
        ACCESS          not-accessible
        STATUS          mandatory
        DESCRIPTION     "This group provides detailed information about the Microchannel
devices detected in your system"
        ::= {dmtfGroups1 35}

eMicrochannelAdapterInformation OBJECT-TYPE
        SYNTAX          SMicrochannelAdapterInformation
        ACCESS          not-accessible
        STATUS          mandatory
        DESCRIPTION     ""
        --INDEX           {DmiComponentIndex, a35AdapterIndex}
        ::= {tMicrochannelAdapterInformation 1}

a35AdapterIndex OBJECT-TYPE
        SYNTAX          DmiInteger
        ACCESS          read-only
        STATUS          mandatory
        DESCRIPTION     "Index into the MCA adapter table "
        ::= {eMicrochannelAdapterInformation 1}

a35SlotNumber OBJECT-TYPE
        SYNTAX          DmiInteger
        ACCESS          read-only
        STATUS          mandatory
        DESCRIPTION     "The slot in which the adapter was detected."
        ::= {eMicrochannelAdapterInformation 2}

a35AdapterId OBJECT-TYPE
        SYNTAX          DmiDisplaystring
        ACCESS          read-only
        STATUS          mandatory
        DESCRIPTION     "The unique number that identifies the adapter."
        ::= {eMicrochannelAdapterInformation 3}

a35PosData OBJECT-TYPE
        SYNTAX          DmiDisplaystring
        ACCESS          read-only
        STATUS          mandatory
        DESCRIPTION     "This is Programmable Option Select data used to automatically
configure the system."
        ::= {eMicrochannelAdapterInformation 4}

a35AdapterName OBJECT-TYPE
        SYNTAX          DmiDisplaystring
        ACCESS          read-only
        STATUS          mandatory
        DESCRIPTION     "The name of this adapter."
        ::= {eMicrochannelAdapterInformation 5}

SPciDeviceInformation ::= SEQUENCE {
        a36DeviceIndex                                  DmiInteger,
        a36ClassCode                                    DmiDisplaystring,
        a36PciDeviceName                                DmiDisplaystring,
        a36VendorId                                     DmiDisplaystring,
        a36DeviceId                                     DmiDisplaystring,
        a36BusNumber                                    DmiInteger,
        a36DeviceNumber                                 DmiDisplaystring,
        a36RevisionId                                   DmiDisplaystring
}

tPciDeviceInformation OBJECT-TYPE
        SYNTAX          SEQUENCE OF SPciDeviceInformation
        ACCESS          not-accessible
        STATUS          mandatory
        DESCRIPTION     "This group provides detailed information about the PCI devices
detected in your system"
        ::= {dmtfGroups1 36}

ePciDeviceInformation OBJECT-TYPE
        SYNTAX          SPciDeviceInformation
        ACCESS          not-accessible
        STATUS          mandatory
        DESCRIPTION     ""
        --INDEX           {DmiComponentIndex, a36DeviceIndex}
        ::= {tPciDeviceInformation 1}

a36DeviceIndex OBJECT-TYPE
        SYNTAX          DmiInteger
        ACCESS          read-only
        STATUS          mandatory
        DESCRIPTION     "Index into the PCI device table "
        ::= {ePciDeviceInformation 1}

a36ClassCode OBJECT-TYPE
        SYNTAX          DmiDisplaystring
        ACCESS          read-only
        STATUS          mandatory
        DESCRIPTION     "Number that identifies the base class, sub-class, and programmin
 interface"
        ::= {ePciDeviceInformation 2}

a36PciDeviceName OBJECT-TYPE
        SYNTAX          DmiDisplaystring
        ACCESS          read-only
        STATUS          mandatory
        DESCRIPTION     "Description of device that includes manufacturer and device
function"
        ::= {ePciDeviceInformation 3}

a36VendorId OBJECT-TYPE
        SYNTAX          DmiDisplaystring
        ACCESS          read-only
        STATUS          mandatory
        DESCRIPTION     "Number that uniquely identifies the manufacturer"
        ::= {ePciDeviceInformation 4}

a36DeviceId OBJECT-TYPE
        SYNTAX          DmiDisplaystring
        ACCESS          read-only
        STATUS          mandatory
        DESCRIPTION     "Number assigned by the manufacturer that uniquely identifes
the device"
        ::= {ePciDeviceInformation 5}

a36BusNumber OBJECT-TYPE
        SYNTAX          DmiInteger
        ACCESS          read-only
        STATUS          mandatory
        DESCRIPTION     "PCI bus that this device is on"
        ::= {ePciDeviceInformation 6}

a36DeviceNumber OBJECT-TYPE
        SYNTAX          DmiDisplaystring
        ACCESS          read-only
        STATUS          mandatory
        DESCRIPTION     "Number in the range 0..31 that uniquely selects a device
on a PCI bus"
        ::= {ePciDeviceInformation 7}

a36RevisionId OBJECT-TYPE
        SYNTAX          DmiDisplaystring
        ACCESS          read-only
        STATUS          mandatory
        DESCRIPTION     ""
        ::= {ePciDeviceInformation 8}

SEisaDeviceInformation ::= SEQUENCE {
        a37DeviceIndex                                  DmiInteger,
        a37ProductId                                    DmiDisplaystring,
        a37EisaDeviceName                               DmiDisplaystring,
        a37Manufacturer                                 DmiDisplaystring,
        a37SlotLocation                                 DmiInteger,
        a37SlotType                                     DmiInteger,
        a37NumberOfDeviceFunctions                      DmiInteger,
        a37IdType                                       DmiInteger
}

tEisaDeviceInformation OBJECT-TYPE
        SYNTAX          SEQUENCE OF SEisaDeviceInformation
        ACCESS          not-accessible
        STATUS          mandatory
        DESCRIPTION     "This group provides detailed information about the EISA devices
detected in your system"
        ::= {dmtfGroups1 37}

eEisaDeviceInformation OBJECT-TYPE
        SYNTAX          SEisaDeviceInformation
        ACCESS          not-accessible
        STATUS          mandatory
        DESCRIPTION     ""
        --INDEX           {DmiComponentIndex, a37DeviceIndex}
        ::= {tEisaDeviceInformation 1}

a37DeviceIndex OBJECT-TYPE
        SYNTAX          DmiInteger
        ACCESS          read-only
        STATUS          mandatory
        DESCRIPTION     "Index into the EISA device table "
        ::= {eEisaDeviceInformation 1}

a37ProductId OBJECT-TYPE
        SYNTAX          DmiDisplaystring
        ACCESS          read-only
        STATUS          mandatory
        DESCRIPTION     "Number that uniquely identifies the device"
        ::= {eEisaDeviceInformation 2}

a37EisaDeviceName OBJECT-TYPE
        SYNTAX          DmiDisplaystring
        ACCESS          read-only
        STATUS          mandatory
        DESCRIPTION     "Description of device"
        ::= {eEisaDeviceInformation 3}

a37Manufacturer OBJECT-TYPE
        SYNTAX          DmiDisplaystring
        ACCESS          read-only
        STATUS          mandatory
        DESCRIPTION     "Name of manufacturer of the system board or adapter"
        ::= {eEisaDeviceInformation 4}

a37SlotLocation OBJECT-TYPE
        SYNTAX          DmiInteger
        ACCESS          read-only
        STATUS          mandatory
        DESCRIPTION     "The physical or logical slot number in the system of the
device.  Thesystem board is always slot 0.  Slots 1-15 are physical slots.
 Slots 16-64 are for virtual devices."
        ::= {eEisaDeviceInformation 5}

a37SlotType OBJECT-TYPE
        SYNTAX          INTEGER {
                vExpansionSlot                                  (0),
                vEmbeddedDevice                                 (1),
                vVirtual                                        (2)
        }
        ACCESS          read-only
        STATUS          mandatory
        DESCRIPTION     "An expansion slot is a physical slot.  An embedded device
is an EISA I/O device integrated onto the system board.  A virtual device
is generally a software driver that may needsystem resources."
        ::= {eEisaDeviceInformation 6}

a37NumberOfDeviceFunctions OBJECT-TYPE
        SYNTAX          DmiInteger
        ACCESS          read-only
        STATUS          mandatory
        DESCRIPTION     "Number of device functions associated with the device (i.e.
memory function, serial function, parallel function, etc)."
        ::= {eEisaDeviceInformation 7}

a37IdType OBJECT-TYPE
        SYNTAX          INTEGER {
                vReadable                                       (0),
                vNotReadable                                    (1)
        }
        ACCESS          read-only
        STATUS          mandatory
        DESCRIPTION     "An EISA system may have EISA and ISA adapters.  ISA adapters
will nothave readable IDs"
        ::= {eEisaDeviceInformation 8}

SRaidAdapterInformation ::= SEQUENCE {
        a38RaidAdapterIndex                             DmiInteger,
        a38NumberOfLogicalVolumes                       DmiInteger,
        a38NumberOfPhysicalDevices                      DmiInteger,
        a38NumberOfPhysicalDrivesOffline                DmiInteger,
        a38NumberOfCriticalVirtualDrives                DmiInteger,
        a38NumberOfDefunctPhysicalDrives                DmiInteger
}

tRaidAdapterInformation OBJECT-TYPE
        SYNTAX          SEQUENCE OF SRaidAdapterInformation
        ACCESS          not-accessible
        STATUS          mandatory
        DESCRIPTION     "This group provides detailed information about the RAID adapters
in your system"
        ::= {dmtfGroups1 38}

eRaidAdapterInformation OBJECT-TYPE
        SYNTAX          SRaidAdapterInformation
        ACCESS          not-accessible
        STATUS          mandatory
        DESCRIPTION     ""
        --INDEX           {DmiComponentIndex, a38RaidAdapterIndex}
        ::= {tRaidAdapterInformation 1}

a38RaidAdapterIndex OBJECT-TYPE
        SYNTAX          DmiInteger
        ACCESS          read-only
        STATUS          mandatory
        DESCRIPTION     "Index into the RAID Adapter table "
        ::= {eRaidAdapterInformation 1}

a38NumberOfLogicalVolumes OBJECT-TYPE
        SYNTAX          DmiInteger
        ACCESS          read-only
        STATUS          mandatory
        DESCRIPTION     "Number of Logical Volumes for this adapter"
        ::= {eRaidAdapterInformation 2}

a38NumberOfPhysicalDevices OBJECT-TYPE
        SYNTAX          DmiInteger
        ACCESS          read-only
        STATUS          mandatory
        DESCRIPTION     "Number of Physical Devices for this adapter"
        ::= {eRaidAdapterInformation 3}

a38NumberOfPhysicalDrivesOffline OBJECT-TYPE
        SYNTAX          DmiInteger
        ACCESS          read-only
        STATUS          mandatory
        DESCRIPTION     "Name of Physical Drives Offline for this adapter"
        ::= {eRaidAdapterInformation 4}

a38NumberOfCriticalVirtualDrives OBJECT-TYPE
        SYNTAX          DmiInteger
        ACCESS          read-only
        STATUS          mandatory
        DESCRIPTION     "Number of Critical Virtual Drives for this adapter"
        ::= {eRaidAdapterInformation 5}

a38NumberOfDefunctPhysicalDrives OBJECT-TYPE
        SYNTAX          DmiInteger
        ACCESS          read-only
        STATUS          mandatory
        DESCRIPTION     "Number of Defunct Physical Drives for this adapter"
        ::= {eRaidAdapterInformation 6}

SRaidVirtualDrivesInformation ::= SEQUENCE {
        a39RaidVirtualDriveIndex                        DmiInteger,
        a39RaidAdapterIndex                             DmiInteger,
        a39VirtualDriveState                            DmiInteger,
        a39VirtualDriveSize                             DmiInteger
}

tRaidVirtualDrivesInformation OBJECT-TYPE
        SYNTAX          SEQUENCE OF SRaidVirtualDrivesInformation
        ACCESS          not-accessible
        STATUS          mandatory
        DESCRIPTION     "This group provides detailed information about the RAID Virtual
drivesin your system"
        ::= {dmtfGroups1 39}

eRaidVirtualDrivesInformation OBJECT-TYPE
        SYNTAX          SRaidVirtualDrivesInformation
        ACCESS          not-accessible
        STATUS          mandatory
        DESCRIPTION     ""
        --INDEX           {DmiComponentIndex, a39RaidVirtualDriveIndex, a39RaidAdapterIndex}
        ::= {tRaidVirtualDrivesInformation 1}

a39RaidVirtualDriveIndex OBJECT-TYPE
        SYNTAX          DmiInteger
        ACCESS          read-only
        STATUS          mandatory
        DESCRIPTION     "Index into the RAID Virtual Drives table "
        ::= {eRaidVirtualDrivesInformation 1}

a39RaidAdapterIndex OBJECT-TYPE
        SYNTAX          DmiInteger
        ACCESS          read-only
        STATUS          mandatory
        DESCRIPTION     "Index into RAID Adapter Table"
        ::= {eRaidVirtualDrivesInformation 2}

a39VirtualDriveState OBJECT-TYPE
        SYNTAX          INTEGER {
                vOnline                                         (0),
                vOffline                                        (1),
                vCritical                                       (2)
        }
        ACCESS          read-only
        STATUS          mandatory
        DESCRIPTION     "State of Virtual Drive"
        ::= {eRaidVirtualDrivesInformation 3}

a39VirtualDriveSize OBJECT-TYPE
        SYNTAX          DmiInteger
        ACCESS          read-only
        STATUS          mandatory
        DESCRIPTION     "Size of Virtual Drive in Kilobytes"
        ::= {eRaidVirtualDrivesInformation 4}

SRaidPhysicalDriveInformation ::= SEQUENCE {
        a40RaidPhysicalDriveIndex                       DmiInteger,
        a40RaidAdapterIndex                             DmiInteger,
        a40PhysicalDriveSize                            DmiInteger,
        a40ChannelNumber                                DmiInteger,
        a40TargetNumber                                 DmiInteger,
        a40RaidPhysicalDeviceState                      DmiInteger
}

tRaidPhysicalDriveInformation OBJECT-TYPE
        SYNTAX          SEQUENCE OF SRaidPhysicalDriveInformation
        ACCESS          not-accessible
        STATUS          mandatory
        DESCRIPTION     "This group provides detailed information about the RAID physical
drivesin your system"
        ::= {dmtfGroups1 40}

eRaidPhysicalDriveInformation OBJECT-TYPE
        SYNTAX          SRaidPhysicalDriveInformation
        ACCESS          not-accessible
        STATUS          mandatory
        DESCRIPTION     ""
        --INDEX           {DmiComponentIndex, a40RaidPhysicalDriveIndex, a40RaidAdapterIndex}
        ::= {tRaidPhysicalDriveInformation 1}

a40RaidPhysicalDriveIndex OBJECT-TYPE
        SYNTAX          DmiInteger
        ACCESS          read-only
        STATUS          mandatory
        DESCRIPTION     "Index into the RAID Physical Drives table "
        ::= {eRaidPhysicalDriveInformation 1}

a40RaidAdapterIndex OBJECT-TYPE
        SYNTAX          DmiInteger
        ACCESS          read-only
        STATUS          mandatory
        DESCRIPTION     "Index into RAID Adapter Table"
        ::= {eRaidPhysicalDriveInformation 2}

a40PhysicalDriveSize OBJECT-TYPE
        SYNTAX          DmiInteger
        ACCESS          read-only
        STATUS          mandatory
        DESCRIPTION     "Size of Physical Drive in Kilobytes"
        ::= {eRaidPhysicalDriveInformation 3}

a40ChannelNumber OBJECT-TYPE
        SYNTAX          DmiInteger
        ACCESS          read-only
        STATUS          mandatory
        DESCRIPTION     "Channel on RAID Adapter on which this physical drive is located"
        ::= {eRaidPhysicalDriveInformation 4}

a40TargetNumber OBJECT-TYPE
        SYNTAX          DmiInteger
        ACCESS          read-only
        STATUS          mandatory
        DESCRIPTION     "Target number on RAID Adapter on which this physical drive
is located"
        ::= {eRaidPhysicalDriveInformation 5}

a40RaidPhysicalDeviceState OBJECT-TYPE
        SYNTAX          INTEGER {
                vOnline                                         (0),
                vOffline                                        (1),
                vDefunct                                        (2),
                vHotspare                                       (3),
                vStandbyHotspare                                (4),
                vDeadHotspare                                   (5),
                vReady                                          (6),
                vRebuild                                        (7),
                vStandby                                        (8)
        }
        ACCESS          read-only
        STATUS          mandatory
        DESCRIPTION     "Device state of the Physical Drive"
        ::= {eRaidPhysicalDriveInformation 6}

END
