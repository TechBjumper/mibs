-- ES1000 Switch MIB Ver 0.01                           1999/06/16

ES1000-MIB

DEFINITIONS ::= BEGIN
    IMPORTS
        enterprises, TimeTicks, Counter FROM RFC1155-SMI
        OBJECT-TYPE                     FROM RFC-1212
        DisplayString                   FROM RFC1213-MIB
        MacAddress                      FROM BRIDGE-MIB
        TRAP-TYPE                       FROM RFC-1215;
    
    marconi                 OBJECT IDENTIFIER ::= { enterprises 326 }
    systems                 OBJECT IDENTIFIER ::= { marconi 2 }
    external                OBJECT IDENTIFIER ::= { systems 20 }

    dlink                   OBJECT IDENTIFIER ::= { external 1 }
    dlinkcommon             OBJECT IDENTIFIER ::= { dlink 1 }
    golf                    OBJECT IDENTIFIER ::= { dlink 2 }

    golfproducts            OBJECT IDENTIFIER ::= { golf 1 }
    golfcommon              OBJECT IDENTIFIER ::= { golf 2 }

    es1000                  OBJECT IDENTIFIER ::= { golfproducts 1 }

    marconi-products        OBJECT IDENTIFIER ::= { golfcommon 1 }
    marconi-mgmt            OBJECT IDENTIFIER ::= { golfcommon 2 }

    marconi-es1000Prod      OBJECT IDENTIFIER ::= { marconi-products 24 }
    swProperty              OBJECT IDENTIFIER ::= { marconi-es1000Prod 1 }
    swModule                OBJECT IDENTIFIER ::= { swProperty 1 }

    es1000Series            OBJECT IDENTIFIER ::= { marconi-mgmt 24 }
    swDevPackage            OBJECT IDENTIFIER ::= { es1000Series 1 }
    swModulePackage         OBJECT IDENTIFIER ::= { es1000Series 2 }
    swPortPackage           OBJECT IDENTIFIER ::= { es1000Series 3 }
    swFdbPackage            OBJECT IDENTIFIER ::= { es1000Series 4 }
  
    swDevInfo               OBJECT IDENTIFIER ::= { swDevPackage 1 }

    swDevInfoSystemUpTime OBJECT-TYPE
        SYNTAX TimeTicks
        ACCESS read-only
        STATUS mandatory
        DESCRIPTION
            "The value of sysUpTime at the time the switch entered its 
            current operational state. If the current state was entered 
            prior to the last re-initialization, then this object contains
            a zero value. This value is in units of seconds."
        ::= { swDevInfo 1 }

    swDevInfoMaxNumOfModule OBJECT-TYPE
        SYNTAX INTEGER
        ACCESS read-only
        STATUS mandatory
        DESCRIPTION
            "The maximum number of modules in this device."
        ::= { swDevInfo 2 }

    swDevInfoTotalNumOfModule OBJECT-TYPE
        SYNTAX INTEGER
        ACCESS read-only
        STATUS mandatory
        DESCRIPTION
            "The current actual number of modules in this device.The values range is 
            1..swDevInfoMaxNumOfModule."
        ::= { swDevInfo 3 }

    swDevInfoTotalNumOfPort OBJECT-TYPE
        SYNTAX INTEGER
        ACCESS read-only
        STATUS mandatory
        DESCRIPTION
            "The number of ports within this switch. This value is the sum
             of the ports within this switch."
        ::= { swDevInfo 4 }

    swDevInfoNumOfPortInUse OBJECT-TYPE
        SYNTAX INTEGER
        ACCESS read-only
        STATUS mandatory
        DESCRIPTION
            "The number of ports in this switch connected to the segment or
             the end stations."
        ::= { swDevInfo 5 }

    swDevInfoConsoleInUse   OBJECT-TYPE
        SYNTAX INTEGER {
               other(1),
               in-use(2),
               not-in-use(3)
               }
        ACCESS read-only
        STATUS mandatory
        DESCRIPTION
            "This usage indication of console system."
        ::= { swDevInfo 6 }

    swDevInfoSystemLedStatus OBJECT-TYPE
        SYNTAX OCTET STRING (SIZE (0..127))
        ACCESS read-only
        STATUS mandatory
        DESCRIPTION
            "This object is a set of system LED indications. The first four octets is 
             defined as system LED. The first LED is power LED. The second LED
             is console LED. The third LED is GIGA module existing LED. The fourth LED
             is GIGA module link LED. The other octets following the fourth octets
             are the port LED. Every two bytes are presented to a port. The first
             byte is presentd to the Link/Activity LED. The second byte is presented
             to the Speed LED.
             
             There is one byte per LED.

             The most significant bit is used for blink/solid:
                Off = The LED is lit permanently.
                On = The LED blinks.

             The three least significant bits are used for color:
                1 = not lit,
                2 = green,
                3 = yellow,(orange)
                4 = blue,
                5 = red,
                0+6+7 not used

             The four remaining bits are currently unused and must be 0.

             The lastest two octects are defined as slot module type. The first octect
             is slot 1 module type. The second octect is slot 2 module type, and so on.
             
             The module type representation for each byte is listed below:
                 1 = no slot module,
                 2 = 1 port BNC,
                 3 = 2 port Fiber MTRJ,
                 4 = 2 port TX UTP,
                 5 = 1 port Fiber SC,
                 6 = SX Gigabit,
                 7 = LX Gigabit,
                 8 = TX Gigabit
                 other not used"
        ::= { swDevInfo 7 }

    swDevInfoSaveCfg OBJECT-TYPE
        SYNTAX INTEGER {
               other(1),
               proceeding(2),
               completed(3),
               changed-not-save(4),
               failed(5)
               }
        ACCESS read-only
        STATUS mandatory
        DESCRIPTION
            "This object indicates the status of the device configuration.
            
            other(1) - this entry is currently in use but the conditions 
                     under which it will remain so are different from each 
                     of the following values.
            proceeding(2) - the device configuration is saving into the NV-RAM.
            completed(3) - all of the device configuration parameters have been
                     saved into NV-RAM.
            changed-not-save - some of the device configuration parameters have
                     been changed but not saved into NV-RAM.
            failed(5) - The processing of saving device configuration is failed."
        ::= { swDevInfo 8 }

    swDevCtrl               OBJECT IDENTIFIER ::= { swDevPackage 2 }

    swDevCtrlStpState OBJECT-TYPE
        SYNTAX INTEGER {
               other(1),
               disabled(2),
               enabled(3)
               }
        ACCESS read-write
        STATUS mandatory
        DESCRIPTION
            "This object can be enabled or disabled spanning tree algorithm
             during runtime of the system."
        ::= { swDevCtrl 1 }

    swDevIGMPCaptureState OBJECT-TYPE
        SYNTAX INTEGER {
               other(1),
               disabled(2),
               enabled(3)
               }
        ACCESS read-write
        STATUS mandatory
        DESCRIPTION
            "This object indicates Internet Group Management Protocol (IGMP) capture
             function is enabled or disabled."
        ::= { swDevCtrl 2 }

    swDevCtrlPartitionModeState OBJECT-TYPE
        SYNTAX INTEGER {
               other(1),
               disabled(2),
               enabled(3)
               }
        ACCESS read-write
        STATUS mandatory
        DESCRIPTION
            "This object used to enable or disable port auto partition. When the
             object apply for all ports of the device"
        ::= { swDevCtrl 3 }

    swDevCtrlTableLockState OBJECT-TYPE
       SYNTAX  INTEGER {
               other(1),
               disabled(2),
               enabled(3)
               }
       ACCESS  read-write
       STATUS  mandatory
       DESCRIPTION
           "This object indicates whether the address table is locked.
           In other words, the address table doesn't learn any more new address.
           The aging timer is suspended when the address table is locked. As long
           as the table is locked, all of the frames are dropped if the destination
           can not be found in the address. When swVlanInfoStatus is in MAC-Base
           VLAN mode, this object is always disabled."
       ::= { swDevCtrl 4 }

    swDevCtrlSaveCfg OBJECT-TYPE
        SYNTAX INTEGER
        ACCESS write-only
        STATUS mandatory
        DESCRIPTION
            "As the object is set, the current device configuration is save 
             into to NV-RAM."
        ::= { swDevCtrl 5 }

    swDevCtrlHOLState OBJECT-TYPE
        SYNTAX INTEGER {
               other(1),
               disabled(2),
               enabled(3)
               }
        ACCESS read-write
        STATUS mandatory
        DESCRIPTION
            "The object provides a way to prevent HOL (Head Of Line) blocking
            between ports. HOL protection may prevent forwarding a packet to
            a blocking port.The idea relies on the assumption that it is better
            to discard packets destined to blocking ports, then to let them consume
            more and more buffers in the input-port's Rx-counters because eventually 
            these input ports may become totally blocked. The meanings of the values
            are:

            other(1) - this entry is currently in use but the conditions under
                which it will remain so are different from each of the following
                values.
            disabled(2) - HOL function disable for device.
            enabled(3) - HOL function enable for device." 
        ::= { swDevCtrl 6 }

    swDevCtrlAddrLookupModesAndHitRate OBJECT-TYPE
        SYNTAX INTEGER {
               level0(1),
               level1(2),
               level2(3),
               level3(4),
               level4(5),
               level5(6),
               level6(7),
               level7(8)
               }
        ACCESS read-write
        STATUS mandatory
        DESCRIPTION
            "According to the differnet address looke mode setting, to enlarge the
             address table size is possible in device. But there is side effect as
             the higher level you have, the lower thorughput device has. That means
             Level 0 get the smallest table size, but get better performace. We 
             recommand the user use the Level 1 as defualt setting." 
        ::= { swDevCtrl 7 }

    swDevCtrlUploadImageFileName OBJECT-TYPE
        SYNTAX  DisplayString  (SIZE (0..64))
        ACCESS  read-write
        STATUS  mandatory
        DESCRIPTION
            "The name of the image file to be uploaded from the device to TFTP server 
             when enabling image upload function (by writing swDevCtrlUploadImage)."
        ::= { swDevCtrl 8 }

    swDevCtrlUploadImage OBJECT-TYPE
        SYNTAX  INTEGER
        ACCESS  write-only
        STATUS  mandatory
        DESCRIPTION
            "Image file upload control. Writing it by any value will
             immediately invoke image upload function." 
        ::= { swDevCtrl 9 }

    swDevAlarm              OBJECT IDENTIFIER ::= { swDevPackage 3 }

    swDevAlarmPartition OBJECT-TYPE
        SYNTAX INTEGER {
               other(1),
               disabled(2),
               enabled(3)
               }
        ACCESS read-write
        STATUS mandatory
        DESCRIPTION
            "Depending on this object, the device send a trap or not when
             any one of the device's ports was partitioned."
       ::= { swDevAlarm 1 } 

    swDevAlarmNewRoot OBJECT-TYPE
        SYNTAX INTEGER {
               other(1),
               disabled(2),
               enabled(3)
               }
        ACCESS read-write
        STATUS mandatory
        DESCRIPTION
            "When the device has become the new root of the Spanning Tree, this
             object decide whether to send a new root trap."
        ::= { swDevAlarm 2 }

    swDevAlarmTopologyChange OBJECT-TYPE
        SYNTAX INTEGER {
               other(1),
               disabled(2),
               enabled(3)
               }
        ACCESS read-write
        STATUS mandatory
        DESCRIPTION
            "This object determine to send a trap or not when the switch topology
             was changed. If the object is enabled(3), the topologyChange trap is
             sent by the device when any of its configured ports transitions from
             the Learning state to the Forwarding state, or from the Forwarding state
             to the Blocking state. For the same port tranition, the device doesn't
             send the trap if this object value is disabled or other."
        ::= { swDevAlarm 3 }

    swDevAlarmLinkChange OBJECT-TYPE
        SYNTAX INTEGER {
               other(1),
               disabled(2),
               enabled(3)
               }
        ACCESS read-write
        STATUS mandatory
        DESCRIPTION
            "This object determine to send a trap or not when the link 
             was changed. If the object is enabled(3), the Link Change trap is
             sent by the device when any of its ports link change. The device doesn't
             send the trap if this object value is disabled or other."
        ::= { swDevAlarm 4 }

    swModuleInfoTable OBJECT-TYPE
        SYNTAX  SEQUENCE OF SwModuleInfoEntry
        ACCESS  not-accessible
        STATUS  mandatory
        DESCRIPTION
            "A table that contains information about every module."
        ::= { swModulePackage 1 }

    swModuleInfoEntry OBJECT-TYPE
        SYNTAX  SwModuleInfoEntry
        ACCESS  not-accessible
        STATUS  mandatory
        DESCRIPTION
            "A list of information for each module of the device."
        INDEX   { swModuleInfoIndex }
        ::= { swModuleInfoTable 1 }

    SwModuleInfoEntry ::= 
        SEQUENCE {
            swModuleInfoIndex
                INTEGER,
            swModuleInfoDesc
                DisplayString,
            swModuleInfoType
                INTEGER,
            swModuleInfoTotalNumOfPort
                INTEGER,
            swModuleInfoNumOfPortInUse
                INTEGER,
            swModuleInfoPortLedStatus
                OCTET STRING
        }

    swModuleInfoIndex OBJECT-TYPE
        SYNTAX INTEGER
        ACCESS read-only
        STATUS mandatory
        DESCRIPTION
            "This object indicates switch module number.(1..swDevInfoMaxNumOfModule)"
        ::= { swModuleInfoEntry 1 }

    swModuleInfoDesc OBJECT-TYPE
        SYNTAX  DisplayString
        ACCESS  read-only
        STATUS  mandatory
        DESCRIPTION
            "A textual description of the module for memorization ."
        ::= { swModuleInfoEntry 2 }

    swModuleInfoType OBJECT-TYPE
        SYNTAX INTEGER {
               other(1),
               baseModule-UTP(2),
               optionModule-2PortFiber-MTRJ(3),
               optionModule-2PortTX-UTP(4),
               optionModule-1PortFiber-SC(5),
               optionModule-1000Base-SX(6),
               optionModule-1000Base-LX(7),
               optionModule-1000Base-TX(8)
               }
        ACCESS read-only
        STATUS mandatory
        DESCRIPTION
            "This object indicates the type of this module."
        ::= { swModuleInfoEntry 3 }

    swModuleInfoTotalNumOfPort OBJECT-TYPE
        SYNTAX INTEGER
        ACCESS read-only
        STATUS mandatory
        DESCRIPTION
            "The number of ports within this module. This value is the sum
             of the ports within this module."
        ::= { swModuleInfoEntry 4 }

    swModuleInfoNumOfPortInUse OBJECT-TYPE
        SYNTAX INTEGER
        ACCESS read-only
        STATUS mandatory
        DESCRIPTION
            "The number of ports in this module connected to the segment or
             the end stations."
        ::= { swModuleInfoEntry 5 }

    swModuleInfoPortLedStatus OBJECT-TYPE
        SYNTAX OCTET STRING (SIZE (0..127))
        ACCESS read-only
        STATUS mandatory
        DESCRIPTION
            "This object is a set of module's port LED indications. Every two bytes are
             presented to a port. Except the module 3 (Gigabit module) ,the first byte 
             is presentd to the Link/Activity LED. The second byte is presented to the
             Speed LED. For the module 3 ,the first byte is presentd to the module's 
             existing LED. The second byte is presented to the Link/Activity LED.
             
             There is one byte per LED.

             The most significant bit is used for blink/solid:
                Off = The LED is lit permanently.
                On = The LED blinks.

             The three least significant bits are used for color:
                1 = not lit,
                2 = green,
                3 = yellow,(orange)
                4 = blue,
                5 = red,
                0+6+7 not used

             The four remaining bits are currently unused and must be 0."
        ::= { swModuleInfoEntry 6 }

    swPortInfoTable OBJECT-TYPE
        SYNTAX  SEQUENCE OF SwPortInfoEntry
        ACCESS  not-accessible
        STATUS  mandatory
        DESCRIPTION
            "A table that contains information about every port."
        ::= { swPortPackage 1 }

    swPortInfoEntry OBJECT-TYPE
        SYNTAX  SwPortInfoEntry
        ACCESS  not-accessible
        STATUS  mandatory
        DESCRIPTION
            "A list of information for each port of the device."
        INDEX   { swPortInfoModuleIndex ,swPortInfoPortIndex }
        ::= { swPortInfoTable 1 }

    SwPortInfoEntry ::= 
        SEQUENCE {
            swPortInfoModuleIndex
                INTEGER,
            swPortInfoPortIndex
                INTEGER,
            swPortInfoType
                INTEGER,
            swPortInfoLinkStatus
                INTEGER,
            swPortInfoNwayStatus
                INTEGER,
            swPortInfoFlowCtrlStatus
                INTEGER
        }

    swPortInfoModuleIndex OBJECT-TYPE
        SYNTAX INTEGER
        ACCESS read-only
        STATUS mandatory
        DESCRIPTION
            "This object indicates switch module number.(1..Max module number)"
        ::= { swPortInfoEntry 1 }

    swPortInfoPortIndex OBJECT-TYPE
        SYNTAX INTEGER
        ACCESS read-only
        STATUS mandatory
        DESCRIPTION
            "This object indicates the module's port number.(1..Max port number in
             the module)"
        ::= { swPortInfoEntry 2 }

    swPortInfoType OBJECT-TYPE
        SYNTAX INTEGER {
               other(1),
               portType-UTP(2),
               portType-AUI(3),
               portType-Fiber-MTRJ(4),
               portType-Fiber-SC(5),
               portType-BNC(6)
               }
        ACCESS read-only
        STATUS mandatory
        DESCRIPTION
            "This object indicates the connector type of this port."
        ::= { swPortInfoEntry 3 }

    swPortInfoLinkStatus OBJECT-TYPE
        SYNTAX INTEGER {
               other(1),
               link-pass(2),
               link-fail(3)
               }
        ACCESS read-only
        STATUS mandatory
        DESCRIPTION
            "This object indicates the port link status."
        ::= { swPortInfoEntry 4 }

    swPortInfoNwayStatus OBJECT-TYPE
        SYNTAX INTEGER {
               other(1),
               half-10Mbps(2),
               full-10Mbps(3),
               half-100Mbps(4),
               full-100Mbps(5),
               half-1Gigabps(6),
               full-1Gigabps(7)
               }
        ACCESS read-only
        STATUS mandatory
        DESCRIPTION
            "This object indicates the port speed and duplex mode."
        ::= { swPortInfoEntry 5 }

    swPortInfoFlowCtrlStatus OBJECT-TYPE
        SYNTAX INTEGER {
               other(1),
               flowctrl-disabled(2),
               flowctrl-enabled(3),
               backpressure-disabled(4),
               backpressure-enabled(5)
               }
        ACCESS read-only
        STATUS mandatory
        DESCRIPTION
            "This object indicates the port flow control status."
        ::= { swPortInfoEntry 6 }

    swPortCtrlTable OBJECT-TYPE
        SYNTAX SEQUENCE OF SwPortCtrlEntry
        ACCESS not-accessible
        STATUS mandatory
        DESCRIPTION
            "A table that contains control information about every port."
        ::= { swPortPackage 2 }

    swPortCtrlEntry OBJECT-TYPE
        SYNTAX SwPortCtrlEntry
        ACCESS not-accessible
        STATUS mandatory
        DESCRIPTION
            "A list of control information for each port of the device."
        INDEX  { swPortCtrlModuleIndex,swPortCtrlPortIndex }
        ::= { swPortCtrlTable 1 }

    SwPortCtrlEntry ::= 
        SEQUENCE {
            swPortCtrlModuleIndex
                INTEGER,
            swPortCtrlPortIndex
                INTEGER,
            swPortCtrlAdminState
                INTEGER,
            swPortCtrlLinkStatusAlarmState
                INTEGER,
            swPortCtrlNwayState
                INTEGER,
            swPortCtrlFlowCtrlState
                INTEGER,
            swPortCtrlBackPressState
                INTEGER,
            swPortCtrlLockState
                INTEGER,
            swPortCtrlPriority
                INTEGER,
            swPortCtrlStpState
                INTEGER,
            swPortCtrlHOLState
                INTEGER,
            swPortCtrlBroadcastRisingThr
                INTEGER,
            swPortCtrlBroadcastFallingThr
                INTEGER,
            swPortCtrlBroadcastRisingAct
                INTEGER,
            swPortCtrlBroadcastFallingAct
                INTEGER,
            swPortCtrlCleanAllStatisticCounter
                INTEGER
        }

    swPortCtrlModuleIndex OBJECT-TYPE
        SYNTAX INTEGER
        ACCESS read-only
        STATUS mandatory
        DESCRIPTION
            "This object indicates the device module number.(1..Max module number)"
        ::= { swPortCtrlEntry 1 }

    swPortCtrlPortIndex OBJECT-TYPE
        SYNTAX INTEGER
        ACCESS read-only
        STATUS mandatory
        DESCRIPTION
            "This object indicates the module's port number.(1..Max port number in
             the module)"
        ::= { swPortCtrlEntry 2 }

    swPortCtrlAdminState OBJECT-TYPE
        SYNTAX INTEGER {
               other(1),
               disabled(2),
               enabled(3)
               }
        ACCESS read-write
        STATUS mandatory
        DESCRIPTION
            "This object decide the port enabled or disabled."
        ::= { swPortCtrlEntry 3 }

    swPortCtrlLinkStatusAlarmState OBJECT-TYPE
        SYNTAX INTEGER {
               other(1),
               disabled(2),
               enabled(3)
               }
        ACCESS read-write
        STATUS mandatory
        DESCRIPTION
            "Depending on this object to determine to send a trap or
            not when link status changes ."
        ::= { swPortCtrlEntry 4 }
 
    swPortCtrlNwayState OBJECT-TYPE
        SYNTAX INTEGER {
               other(1),
               nway-enabled(2),
               nway-disabled-10Mbps-Half(3),
               nway-disabled-10Mbps-Full(4),
               nway-disabled-100Mbps-Half(5),
               nway-disabled-100Mbps-Full(6),
               nway-disabled-1Gigabps-Half(7),
               nway-disabled-1Gigabps-Full(8)
               }
        ACCESS read-write
        STATUS mandatory
        DESCRIPTION
            "Chose the port speed, duplex mode, and N-Way function mode."
        ::= { swPortCtrlEntry 5 }

    swPortCtrlFlowCtrlState OBJECT-TYPE
        SYNTAX INTEGER {
               other(1),
               disabled(2),
               enabled(3)
               }
        ACCESS read-write
        STATUS mandatory
        DESCRIPTION
            "Set IEEE 802.3x compliant flow control function as enabled or disabled.
             And IEEE 802.3x compliant flow control function work only when the port
             is in full duplex mode.If the port is set Auto-negotiation enabled, the 
             object stands for flow control capability. The results should be referred 
             to swPortInfoFlowCtrlStatus object. If the port is in force mode, this
             objects is simply used to set the flow control state (on/off). In force
             mode, if you change it from enabled to disabled state, it will work after
             next system restart. But the flow control changing from disabled to enabled
             state, it will immediately work."
        ::= { swPortCtrlEntry 6 }

    swPortCtrlBackPressState OBJECT-TYPE
        SYNTAX INTEGER {
               other(1),
               disabled(2),
               enabled(3)
               }
        ACCESS read-write
        STATUS mandatory
        DESCRIPTION
            "Depending on this object determine to enable or disable the 
             backpressure function when the port is working in half duplex mode."
        ::= { swPortCtrlEntry 7 }

    swPortCtrlLockState OBJECT-TYPE
        SYNTAX INTEGER {
               other(1),
               disable(2),
               enable(3)
               }
        ACCESS read-write
        STATUS mandatory
        DESCRIPTION
            "The state of this entry.  When the swDevCtrlTableLockState object is 
             enabled, the state is not changed. When swVlanInfoStatus is in
             MAC-Base VLAN mode, this object is always disabled. The meanings of
             the values are:

            other(1)   - this entry is currently in use but the conditions under
                         which it will remain so are different from each of the 
                         following values.
            disable(2) - Port lock funtion disable.
            enable(3) -  Locking a port. Once the port is locked, it will not
                         learn new SA addresses, and drop unknown/moved-SA packets
                         forwarding to/from such ports. This is a way to prevent
                         undesired traffic from being received or transmmited on
                         the port. Note that locking a port doesn't lock the MAC
                         address entries associated with the locked port, i.e. the
                         existing address entries of the locked port will be age
                         out even though it is locked."
        ::= { swPortCtrlEntry 8 }

    swPortCtrlPriority OBJECT-TYPE
        SYNTAX INTEGER {
               other(1),
               default(2),
               force-low-priority(3),
               force-high-priority(4)
               }
        ACCESS read-write
        STATUS mandatory
        DESCRIPTION
            "The priority queueing for packets received on this port, except for
            BPDU/IGMP packets and packets with unknown unicast destination address.
            IGMP and BPDU packets are always routed with high priority; packets with 
            unknown unicast destination addresses are always routed with low priority.
            Other packets follow the rules below:

            other(1)   - this entry is currently in use but the conditions under
                         which it will remain so are different from each of the 
                         following values.
                         
            default(2) - A packet is normally classified as low priority
                         ,unless at least one of the following is true:
                         
                         .The packet contained a TAG (per 802.1Q definition) with the 
                          priority greater or equal to 4.
                         .The address-table entry for the destination address had Pd=HIGH.
                         
            force-low_priority(3) - A packet is normally classified as low priority.
            force-high_priority(4) - A packet is normally classified as high
                                     priority."
        ::= { swPortCtrlEntry 9 }

    swPortCtrlStpState OBJECT-TYPE
        SYNTAX INTEGER {
               other(1),
               disabled(2),
               enabled(3)
               }
        ACCESS read-write
        STATUS mandatory
        DESCRIPTION
            "The state of STP(spanning tree algorithm) operation on this port. That's
             meaning the port whether add in the STP. The value enabled(3) indicates 
             that STP is enabled on this port, as long as swDevCtrlStpState is also 
             enabled for this device. When disabled(2) but swDevCtrlStpState is still
             enabled for the device, STP is disabled on this port : any BPDU packets 
             received will be discarded and no BPDU packets will be propagated from 
             the port.When the device is in 802.1Q Vlan mode, this object will be 
             enabled and cannot be disabled."
        ::= { swPortCtrlEntry 10 }

    swPortCtrlHOLState OBJECT-TYPE
        SYNTAX INTEGER {
               other(1),
               disabled(2),
               enabled(3)
               }
        ACCESS read-write
        STATUS mandatory
        DESCRIPTION
            "The object provides a way to prevent HOL (Head Of Line) blocking
            between ports. HOL protection may prevent forwarding a packet to
            a blocking port.The idea relies on the assumption that it is better
            to discard packets destined to blocking ports, then to let them consume
            more and more buffers in the input-port's Rx-counters because eventually 
            these input ports may become totally blocked. The value enabled(3)
            indicates that HOL function is enabled on this port, as long as 
            swDevCtrlHOLState is also enabled for this device. When disabled(2) but
            swDevCtrlHOLState is still enabled for the device, HOL function is disabled
            on this port. The meanings of the values are:

            other(1) - this entry is currently in use but the conditions under
                which it will remain so are different from each of the following
                values.
            disabled(2) - HOL function disable.
            enabled(3) - HOL function enable." 
        ::= { swPortCtrlEntry 11 }

    swPortCtrlBroadcastRisingThr OBJECT-TYPE
        SYNTAX INTEGER (1..1488000)
        ACCESS read-write
        STATUS mandatory
        DESCRIPTION
            "This allows the user to specify the broadcast packets per second.
             Broadcast traffic above this rate activates broadcast storm control
             (i.e. swPortCtrlBroadcastRisingAct) on the port. The default value
             is 500 broadcast packets per second. The setting must be bigger
             than the value in swPortCtrlBroadcastFallingThr."
        ::= { swPortCtrlEntry 12 }

    swPortCtrlBroadcastFallingThr OBJECT-TYPE
        SYNTAX INTEGER (1..1488000)
        ACCESS read-write
        STATUS mandatory
        DESCRIPTION
            "This allows the user to specify the broadcast packets per second. 
             If broadcast traffic is below this rate and rising threshold
             condition has been met at least once before this falling threshold
             is met, the device will apply the action described in
             swPortCtrlBroadcastFallingAct. The default value 250. The setting
             must be fewer than the value in swPortCtrlBroadcastRisingThr."
        ::= { swPortCtrlEntry 13 }

    swPortCtrlBroadcastRisingAct OBJECT-TYPE
        SYNTAX INTEGER {
               other(1),
               do-nothing(2),
               blocking(3),
               blocking-trap(4)
               }
        ACCESS read-write
        STATUS mandatory
        DESCRIPTION
            "This object indicates the system action when broadcast storm 
             rising threshold is met.
            other(1) - this entry is currently in use but the conditions under
                which it will remain so are different from each of the following
                values.
            do-nothing(2) - no action.
            blocking(3) - the port can discard any coming broadcast frame.
            blocking-trap(4) - the port can discard any coming broadcast frame. And
            the device can send a broadcast rising trap."
        ::= { swPortCtrlEntry 14 }

    swPortCtrlBroadcastFallingAct OBJECT-TYPE
        SYNTAX INTEGER {
               other(1),
               do-nothing(2),
               forwarding(3),
               forwarding-trap(4)
               }
        ACCESS read-write
        STATUS mandatory
        DESCRIPTION
            "This object indicates the device action when broadcast storm 
            falling threshold is met.
            other(1) - this entry is currently in use but the conditions under
                which it will remain so are different from each of the following
                values.
            do-nothing(2) - no action.
            forwarding(3) - the port has returned to normal operation mode.
            forwarding-trap(4) - the port has returned to normal operation mode. And
            the device can send a broadcast falling trap."
        ::= { swPortCtrlEntry 15 }

    swPortCtrlCleanAllStatisticCounter OBJECT-TYPE
        SYNTAX INTEGER
        ACCESS write-only
        STATUS mandatory
        DESCRIPTION
            "Setting this object will reset current device's all statistic counters."
        ::= { swPortCtrlEntry 16 }

    swPortStTable OBJECT-TYPE
        SYNTAX SEQUENCE OF SwPortStEntry
        ACCESS not-accessible
        STATUS mandatory
        DESCRIPTION
            "A list of port statistic Counter entries."
        ::= { swPortPackage 3 }

    swPortStEntry OBJECT-TYPE
        SYNTAX SwPortStEntry
        ACCESS not-accessible
        STATUS mandatory
        DESCRIPTION
            "This entry include all the port statistic Counter which support
            by the device, like Bytes received, Bytes Sent ..."
        INDEX  { swPortStModuleIndex,swPortStPortIndex }
        ::= { swPortStTable 1 }

    SwPortStEntry ::= 
        SEQUENCE {
            swPortStModuleIndex
                INTEGER,
            swPortStPortIndex
                INTEGER,
            swPortStByteRx
                Counter,
            swPortStByteTx
                Counter,
            swPortStFrameRx
                Counter,
            swPortStFrameTx
                Counter,
            swPortStTotalBytesRx
                Counter,
            swPortStTotalFramesRx
                Counter,
            swPortStBroadcastFramesRx
                Counter,
            swPortStMulticastFramesRx
                Counter,
            swPortStCRCError
                Counter,
            swPortStOversizeFrames
                Counter,
            swPortStFragments
                Counter,
            swPortStJabber
                Counter,
            swPortStCollision
                Counter,
            swPortStLateCollision
                Counter,
            swPortStFrames-64-bytes
                Counter,
            swPortStFrames-65-127-bytes
                Counter,
            swPortStFrames-128-255-bytes
                Counter,
            swPortStFrames-256-511-bytes
                Counter,
            swPortStFrames-512-1023-bytes
                Counter,
            swPortStFrames-1024-1536-bytes
                Counter,
            swPortStFramesDroppedFrames
                Counter,
            swPortStMulticastFramesTx
                Counter,
            swPortStBroadcastFramesTx
                Counter,
            swPortStUndersizeFrames
                Counter
        }

    swPortStModuleIndex OBJECT-TYPE
        SYNTAX INTEGER
        ACCESS read-only
        STATUS mandatory
        DESCRIPTION
            "This object indicates the device module number.(1..Max module number)"
        ::= { swPortStEntry 1 }

    swPortStPortIndex OBJECT-TYPE
        SYNTAX INTEGER
        ACCESS read-only
        STATUS mandatory
        DESCRIPTION
            "This object indicates the module's port number.(1..Max port number in
             the module)"
        ::= { swPortStEntry 2 }

    swPortStByteRx OBJECT-TYPE
        SYNTAX Counter
        ACCESS read-only
        STATUS mandatory
        DESCRIPTION
            "swDevCtrlCounterMode = 2(switched-frames):This counter is incre-
            mented once for every data octet of good packets(unicast + multi-
            cast + broadcast) received.
            
             swDevCtrlCounterMode = 3(all-frames):This counter is incremented
            once for every data octet of good packets(unicast + multicast + 
            broadcast packets) and for local and dropped packets."
        ::= { swPortStEntry 3 }

    swPortStByteTx OBJECT-TYPE
        SYNTAX Counter
        ACCESS read-only
        STATUS mandatory
        DESCRIPTION
            "This counter is incremented once for every data octet of a trans-
            mitted good packet."
        ::= { swPortStEntry 4 }

    swPortStFrameRx OBJECT-TYPE
        SYNTAX Counter
        ACCESS read-only
        STATUS mandatory
        DESCRIPTION
            "swDevCtrlCounterMode = 2(switched-frames):This counter is incre-
            mented once for every good packet(unicast + multicast + broadcast
            ) received.
            
             swDevCtrlCounterMode = 3(all-frames):This counter is incremented
            once for every good packet(unicast + multicast + broadcast packets)
            and for local and dropped packets received."
        ::= { swPortStEntry 5 }

    swPortStFrameTx OBJECT-TYPE
        SYNTAX Counter
        ACCESS read-only
        STATUS mandatory
        DESCRIPTION
            "This counter is incremented once for every transmitted good packet."
        ::= { swPortStEntry 6 }

    swPortStTotalBytesRx OBJECT-TYPE
        SYNTAX Counter
        ACCESS read-only
        STATUS mandatory
        DESCRIPTION
            "This counter is incremented once for every data octet of all 
            received packets. This include data octets of rejected and local
            packets which are not forwarded to the switching core for trans-
            mission. This counter should reflect all the data octets received 
            on the line. Note: A nibble is not counted as a whole byte."
        ::= { swPortStEntry 7 }

    swPortStTotalFramesRx OBJECT-TYPE
        SYNTAX Counter
        ACCESS read-only
        STATUS mandatory
        DESCRIPTION
            "This counter is incremented once for every received packets. This
            include rejected and local packets which are not forwarded to the
            switching core for transmission. This counter should reflect all
            packets received on the line."
        ::= { swPortStEntry 8 }

    swPortStBroadcastFramesRx OBJECT-TYPE
        SYNTAX Counter
        ACCESS read-only
        STATUS mandatory
        DESCRIPTION
            "swDevCtrlCounterMode = 2(switched-frames):This counter is incre-
            mented once for every good broadcast packet received.
            
             swDevCtrlCounterMode = 3(all-frames):This counter is incremented
            once for every good broadcast packet received and for local and 
            dropped broadcast packets."
        ::= { swPortStEntry 9 }

    swPortStMulticastFramesRx OBJECT-TYPE
        SYNTAX Counter
        ACCESS read-only
        STATUS mandatory
        DESCRIPTION
            "swDevCtrlCounterMode = 2(switched-frames):This counter is incre-
            mented once for every good multicast packet received.
            
             swDevCtrlCounterMode = 3(all-frames):This counter is incremented
            once for every good multicast packet received and for local and 
            dropped multicast packets. This counter does not include broad-
            cast packets."
        ::= { swPortStEntry 10 }

    swPortStCRCError OBJECT-TYPE
        SYNTAX Counter
        ACCESS read-only
        STATUS mandatory
        DESCRIPTION
            "This counter is incremented once for every received packet which
            meets all the following conditions:
            1.Packet data length is between 64 and 1518 bytes inclusive.
            2.Packet has invalid CRC.
            3.Collision event , late collision event and receive error event
              have not been detected."
        ::= { swPortStEntry 11 }

    swPortStOversizeFrames OBJECT-TYPE
        SYNTAX Counter
        ACCESS read-only
        STATUS mandatory
        DESCRIPTION
            "The number of good frames with length more than 1518 bytes."
        ::= { swPortStEntry 12 }

    swPortStFragments OBJECT-TYPE
        SYNTAX Counter
        ACCESS read-only
        STATUS mandatory
        DESCRIPTION
            "This counter is incremented once for every received packet which
            meets all the following conditions:
            1.Packet data length is less than 64 bytes or packet withourt SFD
              and is less than 64 bytes in length.
            2.Packet has invalid CRC.
            3.Collision event , late collision event and receive error event
              have not been detected."
        ::= { swPortStEntry 13 }

    swPortStJabber OBJECT-TYPE
        SYNTAX Counter
        ACCESS read-only
        STATUS mandatory
        DESCRIPTION
            "The number of frames with length more than 1518 bytes and with
            CRC error or misaligned."
        ::= { swPortStEntry 14 }

    swPortStCollision OBJECT-TYPE
        SYNTAX Counter
        ACCESS read-only
        STATUS mandatory
        DESCRIPTION
            "The number of Collisions"
        ::= { swPortStEntry 15 }

    swPortStLateCollision OBJECT-TYPE
        SYNTAX Counter
        ACCESS read-only
        STATUS mandatory
        DESCRIPTION
            "The number of Late Collision(collision occurring later than
            576th transmitted bit)."
        ::= { swPortStEntry 16 }

    swPortStFrames-64-bytes OBJECT-TYPE
        SYNTAX Counter
        ACCESS read-only
        STATUS mandatory
        DESCRIPTION
            "This counter is incremented once for every received and trans-
            mitted packet with size of 64 bytes. This counter includes reject-
            ed received and transmitted packets."
        ::= { swPortStEntry 17 }

    swPortStFrames-65-127-bytes OBJECT-TYPE
        SYNTAX Counter
        ACCESS read-only
        STATUS mandatory
        DESCRIPTION
            "This counter is incremented once for every received and trans-
            mitted packet with size of 65 to 127 bytes. This counter includes
            rejected received and transmitted packets."
        ::= { swPortStEntry 18 }

    swPortStFrames-128-255-bytes OBJECT-TYPE
        SYNTAX Counter
        ACCESS read-only
        STATUS mandatory
        DESCRIPTION
            "This counter is incremented once for every received and trans-
            mitted packet with size of 128 to 255 bytes. This counter includes
            rejected received and transmitted packets."
        ::= { swPortStEntry 19 }

    swPortStFrames-256-511-bytes OBJECT-TYPE
        SYNTAX Counter
        ACCESS read-only
        STATUS mandatory
        DESCRIPTION
            "This counter is incremented once for every received and trans-
            mitted packet with size of 256 to 511 bytes. This counter includes
            rejected received and transmitted packets."
        ::= { swPortStEntry 20 }

    swPortStFrames-512-1023-bytes OBJECT-TYPE
        SYNTAX Counter
        ACCESS read-only
        STATUS mandatory
        DESCRIPTION
            "This counter is incremented once for every received and trans-
            mitted packet with size of 512 to 1023 bytes. This counter includ-
            es rejected received and transmitted packets."
        ::= { swPortStEntry 21 }

    swPortStFrames-1024-1536-bytes OBJECT-TYPE
        SYNTAX Counter
        ACCESS read-only
        STATUS mandatory
        DESCRIPTION
            "This counter is incremented once for every received and trans-
            mitted packet with size of 1024 to 1536 bytes. This counter includ-
            es rejected received and transmitted packets."
        ::= { swPortStEntry 22 }

    swPortStFramesDroppedFrames OBJECT-TYPE
        SYNTAX Counter
        ACCESS read-only
        STATUS mandatory
        DESCRIPTION
            "This counter is incremented once for every received dropped pack-
            et."
        ::= { swPortStEntry 23 }

    swPortStMulticastFramesTx OBJECT-TYPE
        SYNTAX Counter
        ACCESS read-only
        STATUS mandatory
        DESCRIPTION
            "The number of multicast frames sent. This counter does not include
            broadcast packets."
        ::= { swPortStEntry 24 }

    swPortStBroadcastFramesTx OBJECT-TYPE
        SYNTAX Counter
        ACCESS read-only
        STATUS mandatory
        DESCRIPTION
            "The number of broadcast frames sent."
        ::= { swPortStEntry 25 }

    swPortStUndersizeFrames OBJECT-TYPE
        SYNTAX Counter
        ACCESS read-only
        STATUS mandatory
        DESCRIPTION
            "This counter is incremented once for every received packet which
            meets all the following conditions:
            1.Packet data length is less than 64 bytes.
            2.Packet has valid CRC.
            3.Collision event , late collision event and receive error event
              have not been detected."
        ::= { swPortStEntry 26 }

    swFdbStaticTable OBJECT-TYPE
        SYNTAX SEQUENCE OF SwFdbStaticEntry
        ACCESS not-accessible
        STATUS mandatory
        DESCRIPTION
            "Like typical legacy bridge devices, FDB table records the mapping
             of Source MAC Address and its associated source port, and forward
             incoming packets to its destination port according to the Destination
             MAC Address of the packet as well as the MAC-port pair entries of the
             FDB table. Note that the priority of FDB table entries is lower than
             Filtering Table, i.e. if there is a table hash collision between the
             entries of FDB Table and Filtering Table inside the switch H/W address
             table, then Filtering Table entry overwrite the colliding entry of
             FDB Table. See swFdbFilterTable description also."
        ::= { swFdbPackage 1 }

    swFdbStaticEntry OBJECT-TYPE
        SYNTAX SwFdbStaticEntry
        ACCESS not-accessible
        STATUS mandatory
        DESCRIPTION
            "A list of information specifies which ports the frames with specific 
             destination MAC address to go. "
        INDEX  { swFdbStaticVid , swFdbStaticAddressIndex }
        ::= { swFdbStaticTable 1 }

    SwFdbStaticEntry ::= 
        SEQUENCE {
            swFdbStaticVid
                INTEGER,
            swFdbStaticAddressIndex
                MacAddress,
            swFdbStaticPortMap
                OCTET STRING,
            swFdbStaticState
                INTEGER,
            swFdbStaticStatus
                INTEGER
        }

    swFdbStaticVid OBJECT-TYPE
        SYNTAX INTEGER
        ACCESS read-only
        STATUS mandatory
        DESCRIPTION
            "This object indicates the VLAN-ID. If VLAN is in mac-based
             mode or disabled, the object indicates the default VLAN-ID (0)."
        ::= { swFdbStaticEntry 1 }

    swFdbStaticAddressIndex OBJECT-TYPE
        SYNTAX MacAddress
        ACCESS read-only
        STATUS mandatory
        DESCRIPTION
            "The destination MAC address in a frame to which this entry's 
            forwarding information applies. This object can take the value of
            an unicast address or the multicast address."
        ::= { swFdbStaticEntry 2 }

    swFdbStaticPortMap OBJECT-TYPE
        SYNTAX OCTET STRING (SIZE (1..4))
        ACCESS read-write
        STATUS mandatory
        DESCRIPTION
            "The set of ports to which frames received from a specific port
            and destined for a specific MAC address, are allowed to be 
            forwarded.  Each octet within the value of this object specifies
            a set of eight ports, with the first octet specifying ports 1 
            through 8, the second octet specifying ports 9 through 16, etc.
            Within each octet, the most significant bit represents the lowest
            numbered port, and the least significant bit represents the highest
            numbered port.  Thus, each port of the bridge is represented by 
            a single bit within the value of this object.  If that bit has a
            value of '1' then that port is included in the set of ports; the
            port is not included if its bit has a value of '0'.(Note that the
            setting of the bit corresponding to the port from which a frame 
            is received is irrelevant.). In module 1 (base module), there are
            22 100M twisted-pair ports (port 1..22) which is mapped to the PortMap's
            port 1 to 22 respectively. In module 2 (slot 1 module), there are 2 100M
            FX/100 TX (or a single port 100M FX) ports which is mapped to the 
            PortMap's port 23, 24 respectively (if the module is a single port 100M FX
            , it is just mapped to port 23 and port 24 is ignored). Module 3 (slot 2 
            module) is a single-port Gigabit Ethernet and it is mapped to the PortMap's
            port 25."
        ::= { swFdbStaticEntry 3 }

    swFdbStaticState OBJECT-TYPE
        SYNTAX INTEGER {
               other(1),
               invalid(2),
               valid(3)
               }
        ACCESS read-write
        STATUS mandatory
        DESCRIPTION
            "This object indicates the status of this entry.
 
            other(1) - this entry is currently in use but the conditions under
                which it will remain so are different from each of the following
                values.
            invalid(2) - writing this value to the object, and then the corresponding
                entry will be removed from the table.
            valid(3) - this entry is reside in the table."
        ::= { swFdbStaticEntry 4 }

    swFdbStaticStatus OBJECT-TYPE
        SYNTAX INTEGER {
               other(1),
               apply(2),
               not-apply(3)
               }
        ACCESS read-only
        STATUS mandatory
        DESCRIPTION
            "This object indicates the status of this entry.
 
            other(1) - this entry is currently in use but the conditions under
                which it will remain so are different from each of the following
                values.
            apply(2) - this entry is currently in use and reside in the table.
            not-apply(3) - this entry is reside in the table but currently not
                           in use due to conflict with filter table."
        ::= { swFdbStaticEntry 5 }

    swFdbFilterTable OBJECT-TYPE
        SYNTAX SEQUENCE OF SwFdbFilterEntry
        ACCESS not-accessible
        STATUS mandatory
        DESCRIPTION
            "A table which contains the filtering information of the
            unicast/multicast entries. This table is used by the transparent
            switching function in determining how to filter the received frames.
            The Filtering Table entries' priority overrides Static FDB Table
            as well as IGMP table entries, say, if there is a hash table entry
            collision between Filtering Table and Static FDB Table setting in
            the switch device's H/W address table, then Filter Table entry setting
            overwrites the colliding entry in Static FDB Table. See swFdbStaticTable
            description also."
        ::= { swFdbPackage 2 }

    swFdbFilterEntry OBJECT-TYPE
        SYNTAX SwFdbFilterEntry
        ACCESS not-accessible
        STATUS mandatory
        DESCRIPTION
            "A list of information about a specific unicast/multicast MAC address
            for which the switch has filtering information."
        INDEX  { swFdbFilterVid , swFdbFilterAddressIndex }
        ::= { swFdbFilterTable 1 }

    SwFdbFilterEntry ::= 
        SEQUENCE {
            swFdbFilterVid
                INTEGER,
            swFdbFilterAddressIndex
                MacAddress,
            swFdbFilterState
                INTEGER
        }

    swFdbFilterVid OBJECT-TYPE
        SYNTAX INTEGER
        ACCESS read-only
        STATUS mandatory
        DESCRIPTION
            "This object indicates the VLAN-ID.If VLAN is in mac-based mode
             or disabled, the object indicates the default VLAN-ID (0)."
        ::= { swFdbFilterEntry 1 }

    swFdbFilterAddressIndex OBJECT-TYPE
        SYNTAX MacAddress
        ACCESS read-only
        STATUS mandatory
        DESCRIPTION
            "This object indicates a unicast/multicast MAC address for which the bridge
            has filtering information."
        ::= { swFdbFilterEntry 2 }

    swFdbFilterState OBJECT-TYPE
        SYNTAX INTEGER {
               other(1),
               dst-src-addr(2),
               invalid(3)
               }
        ACCESS read-write
        STATUS mandatory
        DESCRIPTION
            "This object indicates the status of this entry. 

            other(1) - this entry is currently in use but the conditions under
                which it will remain so are different from each of the following
                values.
            dst-src-addr(2) - recieved frames's destination address or source
                address are currently used to be filtered as it meets with 
                the MAC address entry of the table.
            invalid(3) - writing this value to the object, and then the corresponding
                entry will be removed from the table."
        ::= { swFdbFilterEntry 3 }

    portPartition TRAP-TYPE
              ENTERPRISE es1000
              VARIABLES {
	      swPortInfoModuleIndex,swPortInfoPortIndex
              }
              DESCRIPTION
                      "The trap is sent whenever the port state enter the 
                      Partion mode when more than 61 collisions occur while
                      trasmitting."
		::= 1

    linkChangeEvent TRAP-TYPE
              ENTERPRISE es1000
              VARIABLES { 
              swPortInfoModuleIndex,swPortInfoPortIndex
              }
              DESCRIPTION
                      "The trap is sent whenever the link state of a port changes
                      from link up to link down or from link down to link up"
                ::= 2

    broadcastRisingStorm TRAP-TYPE
              ENTERPRISE es1000
              VARIABLES { 
              swPortInfoModuleIndex,swPortInfoPortIndex
              }
              DESCRIPTION
                      "The trap indicates that broadcast higher rising threshold
                      . This trap including the port ID"
                ::= 3

    broadcastFallingStorm TRAP-TYPE
              ENTERPRISE es1000
              VARIABLES { 
              swPortInfoModuleIndex,swPortInfoPortIndex
              }
              DESCRIPTION
                      "The trap indicates that broadcast higher falling threshold
                      . This trap including the port ID"
                ::= 4

    addressTableFull TRAP-TYPE
              ENTERPRISE es1000
              DESCRIPTION
                      "The trap is sent whenever the address table is full . "
                ::= 5
END
