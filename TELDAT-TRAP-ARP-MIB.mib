-- file automatically created


TELDAT-TRAP-ARP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


arpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ARP event subsystem."
    REVISION "201401200930Z"
    DESCRIPTION "Initial implementation"
        ::= { telEventTraps 5 }


arpEventsGroup	OBJECT IDENTIFIER	::= { arpTrapsMIB 1 }

arpNotifications	OBJECT IDENTIFIER	::= { arpTrapsMIB 2 }
arpNotificationsPrefix	OBJECT IDENTIFIER	::= { arpNotifications 0 }

arpEventObjects1 OBJECT-IDENTITY
    STATUS current
    DESCRIPTION
        "Event ARP.1
        A packet was discarded because the queue of pending ARP packets
        to process is too long. This means the number of received ARP packets
        is so high that they cannot be processed."
    ::= { arpEventsGroup 1 }

arp1-interface OBJECT-TYPE
    SYNTAX DisplayString
    MAX-ACCESS accessible-for-notify
    STATUS current
    DESCRIPTION
        "Parameter 'interface' in event ARP.1"
    ::= { arpEventObjects1 1 }

arpEventObjects2 OBJECT-IDENTITY
    STATUS current
    DESCRIPTION
        "Event ARP.2
        An ARP packet of the type indicated has just arrived for processing."
    ::= { arpEventsGroup 2 }

arp2-operation-type OBJECT-TYPE
    SYNTAX Integer32
    MAX-ACCESS accessible-for-notify
    STATUS current
    DESCRIPTION
        "Parameter 'operation-type' in event ARP.2"
    ::= { arpEventObjects2 1 }

arp2-hardware-type OBJECT-TYPE
    SYNTAX Integer32
    MAX-ACCESS accessible-for-notify
    STATUS current
    DESCRIPTION
        "Parameter 'hardware-type' in event ARP.2"
    ::= { arpEventObjects2 2 }

arp2-protocol-type OBJECT-TYPE
    SYNTAX Integer32
    MAX-ACCESS accessible-for-notify
    STATUS current
    DESCRIPTION
        "Parameter 'protocol-type' in event ARP.2"
    ::= { arpEventObjects2 3 }

arp2-interface OBJECT-TYPE
    SYNTAX DisplayString
    MAX-ACCESS accessible-for-notify
    STATUS current
    DESCRIPTION
        "Parameter 'interface' in event ARP.2"
    ::= { arpEventObjects2 4 }

arpEventObjects3 OBJECT-IDENTITY
    STATUS current
    DESCRIPTION
        "Event ARP.3
        An ARP reply is being sent as the result of a request for a translation
        from another host."
    ::= { arpEventsGroup 3 }

arp3-hardware-type OBJECT-TYPE
    SYNTAX Integer32
    MAX-ACCESS accessible-for-notify
    STATUS current
    DESCRIPTION
        "Parameter 'hardware-type' in event ARP.3"
    ::= { arpEventObjects3 1 }

arp3-protocol-type OBJECT-TYPE
    SYNTAX Integer32
    MAX-ACCESS accessible-for-notify
    STATUS current
    DESCRIPTION
        "Parameter 'protocol-type' in event ARP.3"
    ::= { arpEventObjects3 2 }

arp3-interface OBJECT-TYPE
    SYNTAX DisplayString
    MAX-ACCESS accessible-for-notify
    STATUS current
    DESCRIPTION
        "Parameter 'interface' in event ARP.3"
    ::= { arpEventObjects3 3 }

arpEventObjects4 OBJECT-IDENTITY
    STATUS current
    DESCRIPTION
        "Event ARP.4
        A translation cache entry timed out (which was not used or refreshed
        recently) has been deleted."
    ::= { arpEventsGroup 4 }

arp4-hardware-type OBJECT-TYPE
    SYNTAX Integer32
    MAX-ACCESS accessible-for-notify
    STATUS current
    DESCRIPTION
        "Parameter 'hardware-type' in event ARP.4"
    ::= { arpEventObjects4 1 }

arp4-protocol-type OBJECT-TYPE
    SYNTAX Integer32
    MAX-ACCESS accessible-for-notify
    STATUS current
    DESCRIPTION
        "Parameter 'protocol-type' in event ARP.4"
    ::= { arpEventObjects4 2 }

arp4-interface OBJECT-TYPE
    SYNTAX DisplayString
    MAX-ACCESS accessible-for-notify
    STATUS current
    DESCRIPTION
        "Parameter 'interface' in event ARP.4"
    ::= { arpEventObjects4 3 }

arpEventObjects5 OBJECT-IDENTITY
    STATUS current
    DESCRIPTION
        "Event ARP.5
        An ARP translation request is being sent as a result of the transmission
        of a frame to another host. As the host address is unknown, the ARP
        address resolution process is started broadcasting an ARP request."
    ::= { arpEventsGroup 5 }

arp5-hardware-type OBJECT-TYPE
    SYNTAX Integer32
    MAX-ACCESS accessible-for-notify
    STATUS current
    DESCRIPTION
        "Parameter 'hardware-type' in event ARP.5"
    ::= { arpEventObjects5 1 }

arp5-protocol-type OBJECT-TYPE
    SYNTAX Integer32
    MAX-ACCESS accessible-for-notify
    STATUS current
    DESCRIPTION
        "Parameter 'protocol-type' in event ARP.5"
    ::= { arpEventObjects5 2 }

arp5-interface OBJECT-TYPE
    SYNTAX DisplayString
    MAX-ACCESS accessible-for-notify
    STATUS current
    DESCRIPTION
        "Parameter 'interface' in event ARP.5"
    ::= { arpEventObjects5 3 }

arpEventObjects6 OBJECT-IDENTITY
    STATUS current
    DESCRIPTION
        "Event ARP.6
        An ARP translation request is being sent as the result of
        the auto-refresh mechanism: the refresh timer for a dynamic entry is
        going to expire. When available, this request is sent directly to the
        MAC address in the current translation instead of a broadcast to all
        hosts."
    ::= { arpEventsGroup 6 }

arp6-hardware-type OBJECT-TYPE
    SYNTAX Integer32
    MAX-ACCESS accessible-for-notify
    STATUS current
    DESCRIPTION
        "Parameter 'hardware-type' in event ARP.6"
    ::= { arpEventObjects6 1 }

arp6-protocol-type OBJECT-TYPE
    SYNTAX Integer32
    MAX-ACCESS accessible-for-notify
    STATUS current
    DESCRIPTION
        "Parameter 'protocol-type' in event ARP.6"
    ::= { arpEventObjects6 2 }

arp6-interface OBJECT-TYPE
    SYNTAX DisplayString
    MAX-ACCESS accessible-for-notify
    STATUS current
    DESCRIPTION
        "Parameter 'interface' in event ARP.6"
    ::= { arpEventObjects6 3 }

arpEventObjects7 OBJECT-IDENTITY
    STATUS current
    DESCRIPTION
        "Event ARP.7
        During the input processing of an ARP packet, the router did not have
        memory available to make a new dynamic ARP entry for the given protocol."
    ::= { arpEventsGroup 7 }

arp7-protocol-type OBJECT-TYPE
    SYNTAX Integer32
    MAX-ACCESS accessible-for-notify
    STATUS current
    DESCRIPTION
        "Parameter 'protocol-type' in event ARP.7"
    ::= { arpEventObjects7 1 }

arp7-interface OBJECT-TYPE
    SYNTAX DisplayString
    MAX-ACCESS accessible-for-notify
    STATUS current
    DESCRIPTION
        "Parameter 'interface' in event ARP.7"
    ::= { arpEventObjects7 2 }

arpEventObjects8 OBJECT-IDENTITY
    STATUS current
    DESCRIPTION
        "Event ARP.8
        An ARP packet of the type indicated has just arrived for processing."
    ::= { arpEventsGroup 8 }

arp8-operation-type OBJECT-TYPE
    SYNTAX DisplayString
    MAX-ACCESS accessible-for-notify
    STATUS current
    DESCRIPTION
        "Parameter 'operation-type' in event ARP.8"
    ::= { arpEventObjects8 1 }

arp8-src-address OBJECT-TYPE
    SYNTAX IpAddress
    MAX-ACCESS accessible-for-notify
    STATUS current
    DESCRIPTION
        "Parameter 'src-address' in event ARP.8"
    ::= { arpEventObjects8 2 }

arp8-dest-address OBJECT-TYPE
    SYNTAX IpAddress
    MAX-ACCESS accessible-for-notify
    STATUS current
    DESCRIPTION
        "Parameter 'dest-address' in event ARP.8"
    ::= { arpEventObjects8 3 }

arp8-interface OBJECT-TYPE
    SYNTAX DisplayString
    MAX-ACCESS accessible-for-notify
    STATUS current
    DESCRIPTION
        "Parameter 'interface' in event ARP.8"
    ::= { arpEventObjects8 4 }

arpEventObjects9 OBJECT-IDENTITY
    STATUS current
    DESCRIPTION
        "Event ARP.9
        An ARP reply is being sent as the result of a request for a translation
        from another host."
    ::= { arpEventsGroup 9 }

arp9-operation-type OBJECT-TYPE
    SYNTAX DisplayString
    MAX-ACCESS accessible-for-notify
    STATUS current
    DESCRIPTION
        "Parameter 'operation-type' in event ARP.9"
    ::= { arpEventObjects9 1 }

arp9-src-address OBJECT-TYPE
    SYNTAX IpAddress
    MAX-ACCESS accessible-for-notify
    STATUS current
    DESCRIPTION
        "Parameter 'src-address' in event ARP.9"
    ::= { arpEventObjects9 2 }

arp9-dest-address OBJECT-TYPE
    SYNTAX IpAddress
    MAX-ACCESS accessible-for-notify
    STATUS current
    DESCRIPTION
        "Parameter 'dest-address' in event ARP.9"
    ::= { arpEventObjects9 3 }

arp9-interface OBJECT-TYPE
    SYNTAX DisplayString
    MAX-ACCESS accessible-for-notify
    STATUS current
    DESCRIPTION
        "Parameter 'interface' in event ARP.9"
    ::= { arpEventObjects9 4 }

arpEventObjects10 OBJECT-IDENTITY
    STATUS current
    DESCRIPTION
        "Event ARP.10
        An ARP packet has been dropped while it was being sent out."
    ::= { arpEventsGroup 10 }

arp10-operation-type OBJECT-TYPE
    SYNTAX DisplayString
    MAX-ACCESS accessible-for-notify
    STATUS current
    DESCRIPTION
        "Parameter 'operation-type' in event ARP.10"
    ::= { arpEventObjects10 1 }

arp10-protocol-type OBJECT-TYPE
    SYNTAX Integer32
    MAX-ACCESS accessible-for-notify
    STATUS current
    DESCRIPTION
        "Parameter 'protocol-type' in event ARP.10"
    ::= { arpEventObjects10 2 }

arp10-interface OBJECT-TYPE
    SYNTAX DisplayString
    MAX-ACCESS accessible-for-notify
    STATUS current
    DESCRIPTION
        "Parameter 'interface' in event ARP.10"
    ::= { arpEventObjects10 3 }

arpEventObjects11 OBJECT-IDENTITY
    STATUS current
    DESCRIPTION
        "Event ARP.11
        Auto-refresh process was launched as a result of using an entry near its
        expiration time."
    ::= { arpEventsGroup 11 }

arp11-hardware-type OBJECT-TYPE
    SYNTAX Integer32
    MAX-ACCESS accessible-for-notify
    STATUS current
    DESCRIPTION
        "Parameter 'hardware-type' in event ARP.11"
    ::= { arpEventObjects11 1 }

arp11-protocol-type OBJECT-TYPE
    SYNTAX Integer32
    MAX-ACCESS accessible-for-notify
    STATUS current
    DESCRIPTION
        "Parameter 'protocol-type' in event ARP.11"
    ::= { arpEventObjects11 2 }

arp11-protocol-address OBJECT-TYPE
    SYNTAX DisplayString
    MAX-ACCESS accessible-for-notify
    STATUS current
    DESCRIPTION
        "Parameter 'protocol-address' in event ARP.11"
    ::= { arpEventObjects11 3 }

arp11-interface OBJECT-TYPE
    SYNTAX DisplayString
    MAX-ACCESS accessible-for-notify
    STATUS current
    DESCRIPTION
        "Parameter 'interface' in event ARP.11"
    ::= { arpEventObjects11 4 }

arpEventObjects12 OBJECT-IDENTITY
    STATUS current
    DESCRIPTION
        "Event ARP.12
        Hardware address has been cleared from protocol caches. This may be due
        to hardware address learning, refresh process, network failure, or
        configuration changes."
    ::= { arpEventsGroup 12 }

arp12-hardware-type OBJECT-TYPE
    SYNTAX Integer32
    MAX-ACCESS accessible-for-notify
    STATUS current
    DESCRIPTION
        "Parameter 'hardware-type' in event ARP.12"
    ::= { arpEventObjects12 1 }

arp12-protocol-type OBJECT-TYPE
    SYNTAX Integer32
    MAX-ACCESS accessible-for-notify
    STATUS current
    DESCRIPTION
        "Parameter 'protocol-type' in event ARP.12"
    ::= { arpEventObjects12 2 }

arp12-protocol-address OBJECT-TYPE
    SYNTAX DisplayString
    MAX-ACCESS accessible-for-notify
    STATUS current
    DESCRIPTION
        "Parameter 'protocol-address' in event ARP.12"
    ::= { arpEventObjects12 3 }

arp12-interface OBJECT-TYPE
    SYNTAX DisplayString
    MAX-ACCESS accessible-for-notify
    STATUS current
    DESCRIPTION
        "Parameter 'interface' in event ARP.12"
    ::= { arpEventObjects12 4 }

arpEventObjects13 OBJECT-IDENTITY
    STATUS current
    DESCRIPTION
        "Event ARP.13
        An ARP request is being sent for an address translation of another host."
    ::= { arpEventsGroup 13 }

arp13-operation-type OBJECT-TYPE
    SYNTAX DisplayString
    MAX-ACCESS accessible-for-notify
    STATUS current
    DESCRIPTION
        "Parameter 'operation-type' in event ARP.13"
    ::= { arpEventObjects13 1 }

arp13-src-address OBJECT-TYPE
    SYNTAX IpAddress
    MAX-ACCESS accessible-for-notify
    STATUS current
    DESCRIPTION
        "Parameter 'src-address' in event ARP.13"
    ::= { arpEventObjects13 2 }

arp13-dest-address OBJECT-TYPE
    SYNTAX IpAddress
    MAX-ACCESS accessible-for-notify
    STATUS current
    DESCRIPTION
        "Parameter 'dest-address' in event ARP.13"
    ::= { arpEventObjects13 3 }

arp13-interface OBJECT-TYPE
    SYNTAX DisplayString
    MAX-ACCESS accessible-for-notify
    STATUS current
    DESCRIPTION
        "Parameter 'interface' in event ARP.13"
    ::= { arpEventObjects13 4 }

arpEventObjects14 OBJECT-IDENTITY
    STATUS current
    DESCRIPTION
        "Event ARP.14
        An ARP translation request is being sent as the result of the 
        auto-refresh mechanism for this IP and mac address."
    ::= { arpEventsGroup 14 }

arp14-mac-address OBJECT-TYPE
    SYNTAX DisplayString
    MAX-ACCESS accessible-for-notify
    STATUS current
    DESCRIPTION
        "Parameter 'mac-address' in event ARP.14"
    ::= { arpEventObjects14 1 }

arp14-ip-address OBJECT-TYPE
    SYNTAX IpAddress
    MAX-ACCESS accessible-for-notify
    STATUS current
    DESCRIPTION
        "Parameter 'ip-address' in event ARP.14"
    ::= { arpEventObjects14 2 }

arp14-interface OBJECT-TYPE
    SYNTAX DisplayString
    MAX-ACCESS accessible-for-notify
    STATUS current
    DESCRIPTION
        "Parameter 'interface' in event ARP.14"
    ::= { arpEventObjects14 3 }

arpEventObjects15 OBJECT-IDENTITY
    STATUS current
    DESCRIPTION
        "Event ARP.15
        A translation cache entry timed out with this IP and mac address has 
        been deleted."
    ::= { arpEventsGroup 15 }

arp15-mac-address OBJECT-TYPE
    SYNTAX DisplayString
    MAX-ACCESS accessible-for-notify
    STATUS current
    DESCRIPTION
        "Parameter 'mac-address' in event ARP.15"
    ::= { arpEventObjects15 1 }

arp15-ip-address OBJECT-TYPE
    SYNTAX IpAddress
    MAX-ACCESS accessible-for-notify
    STATUS current
    DESCRIPTION
        "Parameter 'ip-address' in event ARP.15"
    ::= { arpEventObjects15 2 }

arp15-interface OBJECT-TYPE
    SYNTAX DisplayString
    MAX-ACCESS accessible-for-notify
    STATUS current
    DESCRIPTION
        "Parameter 'interface' in event ARP.15"
    ::= { arpEventObjects15 3 }

arpEventObjects16 OBJECT-IDENTITY
    STATUS current
    DESCRIPTION
        "Event ARP.16
        An ARP translation is being setup this IP and mac address."
    ::= { arpEventsGroup 16 }

arp16-mac-address OBJECT-TYPE
    SYNTAX DisplayString
    MAX-ACCESS accessible-for-notify
    STATUS current
    DESCRIPTION
        "Parameter 'mac-address' in event ARP.16"
    ::= { arpEventObjects16 1 }

arp16-ip-address OBJECT-TYPE
    SYNTAX IpAddress
    MAX-ACCESS accessible-for-notify
    STATUS current
    DESCRIPTION
        "Parameter 'ip-address' in event ARP.16"
    ::= { arpEventObjects16 2 }

arp16-interface OBJECT-TYPE
    SYNTAX DisplayString
    MAX-ACCESS accessible-for-notify
    STATUS current
    DESCRIPTION
        "Parameter 'interface' in event ARP.16"
    ::= { arpEventObjects16 3 }

arpEventObjects17 OBJECT-IDENTITY
    STATUS current
    DESCRIPTION
        "Event ARP.17
        An ARP translation mac address is being changed for this IP."
    ::= { arpEventsGroup 17 }

arp17-mac-address-old OBJECT-TYPE
    SYNTAX DisplayString
    MAX-ACCESS accessible-for-notify
    STATUS current
    DESCRIPTION
        "Parameter 'mac-address-old' in event ARP.17"
    ::= { arpEventObjects17 1 }

arp17-mac-address-new OBJECT-TYPE
    SYNTAX DisplayString
    MAX-ACCESS accessible-for-notify
    STATUS current
    DESCRIPTION
        "Parameter 'mac-address-new' in event ARP.17"
    ::= { arpEventObjects17 2 }

arp17-ip-address OBJECT-TYPE
    SYNTAX IpAddress
    MAX-ACCESS accessible-for-notify
    STATUS current
    DESCRIPTION
        "Parameter 'ip-address' in event ARP.17"
    ::= { arpEventObjects17 3 }

arp17-interface OBJECT-TYPE
    SYNTAX DisplayString
    MAX-ACCESS accessible-for-notify
    STATUS current
    DESCRIPTION
        "Parameter 'interface' in event ARP.17"
    ::= { arpEventObjects17 4 }

arpEventObjects18 OBJECT-IDENTITY
    STATUS current
    DESCRIPTION
        "Event ARP.18
        An ARP packet was received with a local address. The received mac and IP
        addresses are shown, as well as the interface."
    ::= { arpEventsGroup 18 }

arp18-mac-address OBJECT-TYPE
    SYNTAX DisplayString
    MAX-ACCESS accessible-for-notify
    STATUS current
    DESCRIPTION
        "Parameter 'mac-address' in event ARP.18"
    ::= { arpEventObjects18 1 }

arp18-ip-address OBJECT-TYPE
    SYNTAX IpAddress
    MAX-ACCESS accessible-for-notify
    STATUS current
    DESCRIPTION
        "Parameter 'ip-address' in event ARP.18"
    ::= { arpEventObjects18 2 }

arp18-interface OBJECT-TYPE
    SYNTAX DisplayString
    MAX-ACCESS accessible-for-notify
    STATUS current
    DESCRIPTION
        "Parameter 'interface' in event ARP.18"
    ::= { arpEventObjects18 3 }


arpNotification1 NOTIFICATION-TYPE
    OBJECTS { 
              arp1-interface 
            }
    STATUS current
    DESCRIPTION
        "Notification of Event ARP.1

        Message: 'Queue overflow on interface $1'

        Parameters list:
              $1: arp1-interface

        A packet was discarded because the queue of pending ARP packets
        to process is too long. This means the number of received ARP packets
        is so high that they cannot be processed."
    ::= { arpNotificationsPrefix 1 }

arpNotification2 NOTIFICATION-TYPE
    OBJECTS { 
              arp2-operation-type, 
              arp2-hardware-type,
              arp2-protocol-type,
              arp2-interface 
            }
    STATUS current
    DESCRIPTION
        "Notification of Event ARP.2

        Message: 'Packet received $1 $2 $3 interface $4'

        Parameters list:
              $1: arp2-operation-type
              $2: arp2-hardware-type
              $3: arp2-protocol-type
              $4: arp2-interface

        An ARP packet of the type indicated has just arrived for processing."
    ::= { arpNotificationsPrefix 2 }

arpNotification3 NOTIFICATION-TYPE
    OBJECTS { 
              arp3-hardware-type, 
              arp3-protocol-type,
              arp3-interface 
            }
    STATUS current
    DESCRIPTION
        "Notification of Event ARP.3

        Message: 'Reply sent $1 $2 interface $3'

        Parameters list:
              $1: arp3-hardware-type
              $2: arp3-protocol-type
              $3: arp3-interface

        An ARP reply is being sent as the result of a request for a translation
        from another host."
    ::= { arpNotificationsPrefix 3 }

arpNotification4 NOTIFICATION-TYPE
    OBJECTS { 
              arp4-hardware-type, 
              arp4-protocol-type,
              arp4-interface 
            }
    STATUS current
    DESCRIPTION
        "Notification of Event ARP.4

        Message: 'Deleting translation entry $1 $2 interface $3'

        Parameters list:
              $1: arp4-hardware-type
              $2: arp4-protocol-type
              $3: arp4-interface

        A translation cache entry timed out (which was not used or refreshed
        recently) has been deleted."
    ::= { arpNotificationsPrefix 4 }

arpNotification5 NOTIFICATION-TYPE
    OBJECTS { 
              arp5-hardware-type, 
              arp5-protocol-type,
              arp5-interface 
            }
    STATUS current
    DESCRIPTION
        "Notification of Event ARP.5

        Message: 'Translation request sent ARP $1 $2 interface $3'

        Parameters list:
              $1: arp5-hardware-type
              $2: arp5-protocol-type
              $3: arp5-interface

        An ARP translation request is being sent as a result of the transmission
        of a frame to another host. As the host address is unknown, the ARP
        address resolution process is started broadcasting an ARP request."
    ::= { arpNotificationsPrefix 5 }

arpNotification6 NOTIFICATION-TYPE
    OBJECTS { 
              arp6-hardware-type, 
              arp6-protocol-type,
              arp6-interface 
            }
    STATUS current
    DESCRIPTION
        "Notification of Event ARP.6

        Message: 'Auto-refresh $1 $2 interface $3'

        Parameters list:
              $1: arp6-hardware-type
              $2: arp6-protocol-type
              $3: arp6-interface

        An ARP translation request is being sent as the result of
        the auto-refresh mechanism: the refresh timer for a dynamic entry is
        going to expire. When available, this request is sent directly to the
        MAC address in the current translation instead of a broadcast to all
        hosts."
    ::= { arpNotificationsPrefix 6 }

arpNotification7 NOTIFICATION-TYPE
    OBJECTS { 
              arp7-protocol-type, 
              arp7-interface 
            }
    STATUS current
    DESCRIPTION
        "Notification of Event ARP.7

        Message: 'No memory for entry, protocol $1 interface $2'

        Parameters list:
              $1: arp7-protocol-type
              $2: arp7-interface

        During the input processing of an ARP packet, the router did not have
        memory available to make a new dynamic ARP entry for the given protocol."
    ::= { arpNotificationsPrefix 7 }

arpNotification8 NOTIFICATION-TYPE
    OBJECTS { 
              arp8-operation-type, 
              arp8-src-address,
              arp8-dest-address,
              arp8-interface 
            }
    STATUS current
    DESCRIPTION
        "Notification of Event ARP.8

        Message: 'Packet received, type $1, for IP protocol from $2 to $3 interface $4'

        Parameters list:
              $1: arp8-operation-type
              $2: arp8-src-address
              $3: arp8-dest-address
              $4: arp8-interface

        An ARP packet of the type indicated has just arrived for processing."
    ::= { arpNotificationsPrefix 8 }

arpNotification9 NOTIFICATION-TYPE
    OBJECTS { 
              arp9-operation-type, 
              arp9-src-address,
              arp9-dest-address,
              arp9-interface 
            }
    STATUS current
    DESCRIPTION
        "Notification of Event ARP.9

        Message: 'Reply sent, type $1, for IP protocol from $2 to $3 interface $4'

        Parameters list:
              $1: arp9-operation-type
              $2: arp9-src-address
              $3: arp9-dest-address
              $4: arp9-interface

        An ARP reply is being sent as the result of a request for a translation
        from another host."
    ::= { arpNotificationsPrefix 9 }

arpNotification10 NOTIFICATION-TYPE
    OBJECTS { 
              arp10-operation-type, 
              arp10-protocol-type,
              arp10-interface 
            }
    STATUS current
    DESCRIPTION
        "Notification of Event ARP.10

        Message: 'Packet sent dropped, type $1, protocol $2 interface $3'

        Parameters list:
              $1: arp10-operation-type
              $2: arp10-protocol-type
              $3: arp10-interface

        An ARP packet has been dropped while it was being sent out."
    ::= { arpNotificationsPrefix 10 }

arpNotification11 NOTIFICATION-TYPE
    OBJECTS { 
              arp11-hardware-type, 
              arp11-protocol-type,
              arp11-protocol-address,
              arp11-interface 
            }
    STATUS current
    DESCRIPTION
        "Notification of Event ARP.11

        Message: 'Auto-refresh process launched $1 $2 $3 interface $4'

        Parameters list:
              $1: arp11-hardware-type
              $2: arp11-protocol-type
              $3: arp11-protocol-address
              $4: arp11-interface

        Auto-refresh process was launched as a result of using an entry near its
        expiration time."
    ::= { arpNotificationsPrefix 11 }

arpNotification12 NOTIFICATION-TYPE
    OBJECTS { 
              arp12-hardware-type, 
              arp12-protocol-type,
              arp12-protocol-address,
              arp12-interface 
            }
    STATUS current
    DESCRIPTION
        "Notification of Event ARP.12

        Message: 'Cache cleared $1 $2 $3 interface $4'

        Parameters list:
              $1: arp12-hardware-type
              $2: arp12-protocol-type
              $3: arp12-protocol-address
              $4: arp12-interface

        Hardware address has been cleared from protocol caches. This may be due
        to hardware address learning, refresh process, network failure, or
        configuration changes."
    ::= { arpNotificationsPrefix 12 }

arpNotification13 NOTIFICATION-TYPE
    OBJECTS { 
              arp13-operation-type, 
              arp13-src-address,
              arp13-dest-address,
              arp13-interface 
            }
    STATUS current
    DESCRIPTION
        "Notification of Event ARP.13

        Message: 'Request sent, type $1, for IP protocol from $2 to $3 interface $4'

        Parameters list:
              $1: arp13-operation-type
              $2: arp13-src-address
              $3: arp13-dest-address
              $4: arp13-interface

        An ARP request is being sent for an address translation of another host."
    ::= { arpNotificationsPrefix 13 }

arpNotification14 NOTIFICATION-TYPE
    OBJECTS { 
              arp14-mac-address, 
              arp14-ip-address,
              arp14-interface 
            }
    STATUS current
    DESCRIPTION
        "Notification of Event ARP.14

        Message: 'Refresh request sent for mac $1 associated with IP $2 interface $3'

        Parameters list:
              $1: arp14-mac-address
              $2: arp14-ip-address
              $3: arp14-interface

        An ARP translation request is being sent as the result of the 
        auto-refresh mechanism for this IP and mac address."
    ::= { arpNotificationsPrefix 14 }

arpNotification15 NOTIFICATION-TYPE
    OBJECTS { 
              arp15-mac-address, 
              arp15-ip-address,
              arp15-interface 
            }
    STATUS current
    DESCRIPTION
        "Notification of Event ARP.15

        Message: 'Deleting translation entry with mac $1 and IP $2 interface $3'

        Parameters list:
              $1: arp15-mac-address
              $2: arp15-ip-address
              $3: arp15-interface

        A translation cache entry timed out with this IP and mac address has 
        been deleted."
    ::= { arpNotificationsPrefix 15 }

arpNotification16 NOTIFICATION-TYPE
    OBJECTS { 
              arp16-mac-address, 
              arp16-ip-address,
              arp16-interface 
            }
    STATUS current
    DESCRIPTION
        "Notification of Event ARP.16

        Message: 'New entry mac $1 associated with IP $2 interface $3'

        Parameters list:
              $1: arp16-mac-address
              $2: arp16-ip-address
              $3: arp16-interface

        An ARP translation is being setup this IP and mac address."
    ::= { arpNotificationsPrefix 16 }

arpNotification17 NOTIFICATION-TYPE
    OBJECTS { 
              arp17-mac-address-old, 
              arp17-mac-address-new,
              arp17-ip-address,
              arp17-interface 
            }
    STATUS current
    DESCRIPTION
        "Notification of Event ARP.17

        Message: 'Change entry mac $1 to $2 associated with IP $3 interface $4'

        Parameters list:
              $1: arp17-mac-address-old
              $2: arp17-mac-address-new
              $3: arp17-ip-address
              $4: arp17-interface

        An ARP translation mac address is being changed for this IP."
    ::= { arpNotificationsPrefix 17 }

arpNotification18 NOTIFICATION-TYPE
    OBJECTS { 
              arp18-mac-address, 
              arp18-ip-address,
              arp18-interface 
            }
    STATUS current
    DESCRIPTION
        "Notification of Event ARP.18

        Message: 'Duplicated address received from mac $1 with IP $2 interface $3'

        Parameters list:
              $1: arp18-mac-address
              $2: arp18-ip-address
              $3: arp18-interface

        An ARP packet was received with a local address. The received mac and IP
        addresses are shown, as well as the interface."
    ::= { arpNotificationsPrefix 18 }


END
