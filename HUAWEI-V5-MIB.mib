-- ============================================================================
-- Copyright (C) 2003 by  HUAWEI TECHNOLOGIES. All rights reserved.
--
-- Description:  
-- Reference:  
-- Version: V3.00
-- History:
-- liu chenglong 2003-04-28 Added IPR Decriptions and updated all MIB version to V3.00
-- ============================================================================
	HUAWEI-V5-MIB DEFINITIONS ::= BEGIN

		IMPORTS 
			huaweiUtility			
				FROM HUAWEI-MIB			
			OBJECT-TYPE, MODULE-IDENTITY,Unsigned32			
				FROM SNMPv2-SMI			
			TruthValue, RowStatus			
				FROM SNMPv2-TC;
	
	
		hwV5 MODULE-IDENTITY
			LAST-UPDATED "0304280900Z"
			ORGANIZATION "Fix-Net Dep, Huawei Technologies Co.,Ltd."
			CONTACT-INFO 
				"Floot 5 ,Block 4, R&D Building,
				Huawei Longgang Production Base,
				Shenzhen,  P.R.C.
				http://www.huawei.com
				Zip:518057
				"
			DESCRIPTION 
				"huawei V5  MIb	"
			REVISION "0211290900Z"
			DESCRIPTION
				"
				V2.00		
				reunification version based on the  Fix-Net MIBs baseline by the MIB Standard community.
						
				"
			::= { huaweiUtility 16 }
		
	
	
--
-- Node definitions
--
	
		hwV5MibObjects OBJECT IDENTIFIER ::= { hwV5 1 }
		
		hwV5InterfaceConfigTable OBJECT-TYPE
			SYNTAX SEQUENCE OF HwV5InterfaceConfigEntry
			MAX-ACCESS not-accessible
			STATUS current
			DESCRIPTION
				"The table lists the V5 groups that have been
				configured on the system."
			::= { hwV5MibObjects 1 }
		
		hwV5InterfaceConfigEntry OBJECT-TYPE
			SYNTAX HwV5InterfaceConfigEntry
			MAX-ACCESS not-accessible
			STATUS current
			DESCRIPTION ""
			INDEX { hwV5InterfaceID }
			::= { hwV5InterfaceConfigTable 1 }
		
		HwV5InterfaceConfigEntry ::=
			SEQUENCE { 
				hwV5InterfaceID
					INTEGER,
				hwV5cfgUpperV5InterfaceID
					INTEGER,
				hwV5cfgV5InterfaceType
					INTEGER,
				hwV5cfgV5InterfaceVersion
					INTEGER,
				hwV5cfgPSTNlogicCID
					INTEGER,
				hwV5cfgV5Variable
					INTEGER,
				hwV5cfgLinkIDIdentify0
					TruthValue,
				hwV5cfgLinkIDIdentify1
					TruthValue,
				hwV5cfgLinkIDIdentify2
					TruthValue,
				hwV5cfgLinkIDIdentify3
					TruthValue,
				hwV5cfgRowStatus
					RowStatus
			 }

		hwV5InterfaceID OBJECT-TYPE
			SYNTAX INTEGER (0..16777215)
			MAX-ACCESS not-accessible
			STATUS current
			DESCRIPTION
				" "
			::= { hwV5InterfaceConfigEntry 1 }
		
		hwV5cfgUpperV5InterfaceID OBJECT-TYPE
			SYNTAX INTEGER (0..16777215)
			MAX-ACCESS read-create
			STATUS current
			DESCRIPTION
				" "
			::= { hwV5InterfaceConfigEntry 2 }
		
		hwV5cfgV5InterfaceType OBJECT-TYPE
			SYNTAX INTEGER
				{
				an(1),
				le(2)
				}
			MAX-ACCESS read-create
			STATUS current
			DESCRIPTION
				" "
			::= { hwV5InterfaceConfigEntry 3 }
		
		hwV5cfgV5InterfaceVersion OBJECT-TYPE
			SYNTAX INTEGER
				{
				v51(1),
				v52(2)
				}
			MAX-ACCESS read-create
			STATUS current
			DESCRIPTION
				" "
			::= { hwV5InterfaceConfigEntry 4 }
		
		hwV5cfgPSTNlogicCID OBJECT-TYPE
			SYNTAX INTEGER (0..65535)
			MAX-ACCESS read-create
			STATUS current
			DESCRIPTION
				" "
			::= { hwV5InterfaceConfigEntry 5 }
		
		hwV5cfgV5Variable OBJECT-TYPE
			SYNTAX INTEGER (0..127)
			MAX-ACCESS read-create
			STATUS current
			DESCRIPTION
				" "
			::= { hwV5InterfaceConfigEntry 6 }
		
		hwV5cfgLinkIDIdentify0 OBJECT-TYPE
			SYNTAX TruthValue
			MAX-ACCESS read-create
			STATUS current
			DESCRIPTION
				" "
			::= { hwV5InterfaceConfigEntry 7 }
		
		hwV5cfgLinkIDIdentify1 OBJECT-TYPE
			SYNTAX TruthValue
			MAX-ACCESS read-create
			STATUS current
			DESCRIPTION
				" "
			::= { hwV5InterfaceConfigEntry 8 }
		
		hwV5cfgLinkIDIdentify2 OBJECT-TYPE
			SYNTAX TruthValue
			MAX-ACCESS read-create
			STATUS current
			DESCRIPTION
				" "
			::= { hwV5InterfaceConfigEntry 9 }
		
		hwV5cfgLinkIDIdentify3 OBJECT-TYPE
			SYNTAX TruthValue
			MAX-ACCESS read-create
			STATUS current
			DESCRIPTION
				" "
			::= { hwV5InterfaceConfigEntry 10 }
		
		hwV5cfgRowStatus OBJECT-TYPE
			SYNTAX RowStatus
			MAX-ACCESS read-create
			STATUS current
			DESCRIPTION
				" "
			::= { hwV5InterfaceConfigEntry 11 }
		
		hwV5InterfaceLinkConfigTable OBJECT-TYPE
			SYNTAX SEQUENCE OF HwV5InterfaceLinkConfigEntry
			MAX-ACCESS not-accessible
			STATUS current
			DESCRIPTION
				"The table lists the V5 groups that have been
				configured on the system."
			::= { hwV5MibObjects 2 }
		
		hwV5InterfaceLinkConfigEntry OBJECT-TYPE
			SYNTAX HwV5InterfaceLinkConfigEntry
			MAX-ACCESS not-accessible
			STATUS current
			DESCRIPTION ""
			INDEX { hwV5InterfaceID, hwV5FrameID, hwV5SlotID, hwV5PortID }
			::= { hwV5InterfaceLinkConfigTable 1 }
		
		HwV5InterfaceLinkConfigEntry ::=
			SEQUENCE { 
				hwV5FrameID
					INTEGER,
				hwV5SlotID
					INTEGER,
				hwV5PortID
					INTEGER,
				hwV5LinkID
					INTEGER,
				hwV5RowStatus
					RowStatus
			 }

		hwV5FrameID OBJECT-TYPE
			SYNTAX INTEGER (0..63)
			MAX-ACCESS not-accessible
			STATUS current
			DESCRIPTION
				" "
			::= { hwV5InterfaceLinkConfigEntry 1 }
		
		hwV5SlotID OBJECT-TYPE
			SYNTAX INTEGER (0..63)
			MAX-ACCESS not-accessible
			STATUS current
			DESCRIPTION
				" "
			::= { hwV5InterfaceLinkConfigEntry 2 }
		
		hwV5PortID OBJECT-TYPE
			SYNTAX INTEGER (0..63)
			MAX-ACCESS not-accessible
			STATUS current
			DESCRIPTION
				" "
			::= { hwV5InterfaceLinkConfigEntry 3 }
		
		hwV5LinkID OBJECT-TYPE
			SYNTAX INTEGER (0..255)
			MAX-ACCESS read-create
			STATUS current
			DESCRIPTION
				" "
			::= { hwV5InterfaceLinkConfigEntry 4 }
		
		hwV5RowStatus OBJECT-TYPE
			SYNTAX RowStatus
			MAX-ACCESS read-create
			STATUS current
			DESCRIPTION
				" "
			::= { hwV5InterfaceLinkConfigEntry 5 }
		
		hwV5CChannelConfigTable OBJECT-TYPE
			SYNTAX SEQUENCE OF HwV5CChannelConfigEntry
			MAX-ACCESS not-accessible
			STATUS current
			DESCRIPTION
				"The table lists the V5 groups that have been
				configured on the system."
			::= { hwV5MibObjects 3 }
		
		hwV5CChannelConfigEntry OBJECT-TYPE
			SYNTAX HwV5CChannelConfigEntry
			MAX-ACCESS not-accessible
			STATUS current
			DESCRIPTION ""
			INDEX { hwV5InterfaceID, hwV5channelPhyCNo }
			::= { hwV5CChannelConfigTable 1 }
		
		HwV5CChannelConfigEntry ::=
			SEQUENCE { 
				hwV5channelPhyCNo
					INTEGER,
				hwV5channelFrameID
					INTEGER,
				hwV5channelSlotID
					INTEGER,
				hwV5channelPortID
					INTEGER,
				hwV5channelTsNo
					INTEGER,
				hwV5channelProtectType
					INTEGER,
				hwV5channelLogicCChannelID
					INTEGER,
				hwV5channelRowStatus
					RowStatus
			 }

		hwV5channelPhyCNo OBJECT-TYPE
			SYNTAX INTEGER (0..255)
			MAX-ACCESS not-accessible
			STATUS current
			DESCRIPTION
				" "
			::= { hwV5CChannelConfigEntry 1 }
		
		hwV5channelFrameID OBJECT-TYPE
			SYNTAX INTEGER (0..63)
			MAX-ACCESS read-create
			STATUS current
			DESCRIPTION
				" "
			::= { hwV5CChannelConfigEntry 2 }
		
		hwV5channelSlotID OBJECT-TYPE
			SYNTAX INTEGER (0..63)
			MAX-ACCESS read-create
			STATUS current
			DESCRIPTION
				" "
			::= { hwV5CChannelConfigEntry 3 }
		
		hwV5channelPortID OBJECT-TYPE
			SYNTAX INTEGER (0..63)
			MAX-ACCESS read-create
			STATUS current
			DESCRIPTION
				" "
			::= { hwV5CChannelConfigEntry 4 }
		
		hwV5channelTsNo OBJECT-TYPE
			SYNTAX INTEGER
				{
				t15(1),
				t16(2),
				t31(3)
				}
			MAX-ACCESS read-create
			STATUS current
			DESCRIPTION
				" "
			::= { hwV5CChannelConfigEntry 5 }
		
		hwV5channelProtectType OBJECT-TYPE
			SYNTAX INTEGER
				{
				p1master(1),
				p1slaver(2),
				p2master(3),
				p2slaver(4)
				}
			MAX-ACCESS read-create
			STATUS current
			DESCRIPTION
				" "
			::= { hwV5CChannelConfigEntry 6 }
		
		hwV5channelLogicCChannelID OBJECT-TYPE
			SYNTAX INTEGER (0..65535)
			MAX-ACCESS read-create
			STATUS current
			DESCRIPTION
				" "
			::= { hwV5CChannelConfigEntry 7 }
		
		hwV5channelRowStatus OBJECT-TYPE
			SYNTAX RowStatus
			MAX-ACCESS read-create
			STATUS current
			DESCRIPTION
				" "
			::= { hwV5CChannelConfigEntry 8 }
		
		hwV5ProtSwitchOprTable OBJECT-TYPE
			SYNTAX SEQUENCE OF HwV5ProtSwitchOprEntry
			MAX-ACCESS not-accessible
			STATUS current
			DESCRIPTION
				"The table lists the V5 groups that have been
				configured on the system."
			::= { hwV5MibObjects 4 }
		
		hwV5ProtSwitchOprEntry OBJECT-TYPE
			SYNTAX HwV5ProtSwitchOprEntry
			MAX-ACCESS not-accessible
			STATUS current
			DESCRIPTION ""
			INDEX { hwV5InterfaceID, hwV5SwitchLogicCchannelID }
			::= { hwV5ProtSwitchOprTable 1 }
		
		HwV5ProtSwitchOprEntry ::=
			SEQUENCE { 
				hwV5SwitchLogicCchannelID
					INTEGER,
				hwV5SwitchPhyCLinkID
					INTEGER,
				hwV5SwitchPhyCTsNo
					INTEGER,
				hwV5SwitchSwitchover
					INTEGER
			 }

		hwV5SwitchLogicCchannelID OBJECT-TYPE
			SYNTAX INTEGER (0..65535)
			MAX-ACCESS not-accessible
			STATUS current
			DESCRIPTION
				" "
			::= { hwV5ProtSwitchOprEntry 1 }
		
		hwV5SwitchPhyCLinkID OBJECT-TYPE
			SYNTAX INTEGER (0..255)
			MAX-ACCESS read-create
			STATUS current
			DESCRIPTION
				" "
			::= { hwV5ProtSwitchOprEntry 2 }
		
		hwV5SwitchPhyCTsNo OBJECT-TYPE
			SYNTAX INTEGER
				{
				t15(1),
				t16(2),
				t31(3)
				}
			MAX-ACCESS read-create
			STATUS current
			DESCRIPTION
				" "
			::= { hwV5ProtSwitchOprEntry 3 }
		
		hwV5SwitchSwitchover OBJECT-TYPE
			SYNTAX INTEGER { yes(1) }
			MAX-ACCESS read-create
			STATUS current
			DESCRIPTION
				" "
			::= { hwV5ProtSwitchOprEntry 4 }
		
		hwV5InterfaceTable OBJECT-TYPE
			SYNTAX SEQUENCE OF HwV5InterfaceEntry
			MAX-ACCESS not-accessible
			STATUS current
			DESCRIPTION
				"The table lists the V5 groups that have been
				configured on the system."
			::= { hwV5MibObjects 5 }
		
		hwV5InterfaceEntry OBJECT-TYPE
			SYNTAX HwV5InterfaceEntry
			MAX-ACCESS not-accessible
			STATUS current
			DESCRIPTION ""
			INDEX { hwV5InterfaceID }
			::= { hwV5InterfaceTable 1 }
		
		HwV5InterfaceEntry ::=
			SEQUENCE { 
				hwV5IfInterfaceType
					INTEGER,
				hwV5IfcurrentVarIdx
					INTEGER,
				hwV5IfPrimaryLinkid
					INTEGER,
				hwV5IfSecondaryLinkid
					INTEGER,
				hwV5IfLinkNum
					INTEGER,
				hwV5IfLinkIDIdentify0
					TruthValue,
				hwV5IfLinkIDIdentify1
					TruthValue,
				hwV5IfLinkIDIdentify2
					TruthValue,
				hwV5IfLinkIDIdentify3
					TruthValue,
				hwV5IfInterfacestate
					INTEGER,
				hwV5IfPstnDataLinkState
					INTEGER,
				hwV5IfBccDataLinkState
					INTEGER,
				hwV5IfCtrlDataLinkState
					INTEGER,
				hwV5IfProtectDataLink1State
					INTEGER,
				hwV5IfProtectDataLink2state
					INTEGER,
				hwV5IfLinkCtrlDataLinkState
					INTEGER,
				hwV5IfOprtype
					INTEGER,
				hwV5IfOprResult
					INTEGER
			 }

		hwV5IfInterfaceType OBJECT-TYPE
			SYNTAX INTEGER
				{
				an(1),
				le(2)
				}
			MAX-ACCESS read-only
			STATUS current
			DESCRIPTION
				" "
			::= { hwV5InterfaceEntry 1 }
		
		hwV5IfcurrentVarIdx OBJECT-TYPE
			SYNTAX INTEGER (0..127)
			MAX-ACCESS read-only
			STATUS current
			DESCRIPTION
				" "
			::= { hwV5InterfaceEntry 2 }
		
		hwV5IfPrimaryLinkid OBJECT-TYPE
			SYNTAX INTEGER (0..255)
			MAX-ACCESS read-only
			STATUS current
			DESCRIPTION
				" "
			::= { hwV5InterfaceEntry 3 }
		
		hwV5IfSecondaryLinkid OBJECT-TYPE
			SYNTAX INTEGER (0..255)
			MAX-ACCESS read-only
			STATUS current
			DESCRIPTION
				" "
			::= { hwV5InterfaceEntry 4 }
		
		hwV5IfLinkNum OBJECT-TYPE
			SYNTAX INTEGER (0..16)
			MAX-ACCESS read-only
			STATUS current
			DESCRIPTION
				" "
			::= { hwV5InterfaceEntry 5 }
		
		hwV5IfLinkIDIdentify0 OBJECT-TYPE
			SYNTAX TruthValue
			MAX-ACCESS read-only
			STATUS current
			DESCRIPTION
				" "
			::= { hwV5InterfaceEntry 6 }
		
		hwV5IfLinkIDIdentify1 OBJECT-TYPE
			SYNTAX TruthValue
			MAX-ACCESS read-only
			STATUS current
			DESCRIPTION
				" "
			::= { hwV5InterfaceEntry 7 }
		
		hwV5IfLinkIDIdentify2 OBJECT-TYPE
			SYNTAX TruthValue
			MAX-ACCESS read-write
			STATUS current
			DESCRIPTION
				" "
			::= { hwV5InterfaceEntry 8 }
		
		hwV5IfLinkIDIdentify3 OBJECT-TYPE
			SYNTAX TruthValue
			MAX-ACCESS read-only
			STATUS current
			DESCRIPTION
				" "
			::= { hwV5InterfaceEntry 9 }
		
		hwV5IfInterfacestate OBJECT-TYPE
			SYNTAX INTEGER
				{
				nostartif(1),
				iffree(2),
				wait2buildlink(3),
				reqifvar(4),
				reqlinkid(5),
				waitrestart(6),
				ifnormal(7),
				ifclose(8)
				}
			MAX-ACCESS read-only
			STATUS current
			DESCRIPTION
				" "
			::= { hwV5InterfaceEntry 10 }
		
		hwV5IfPstnDataLinkState OBJECT-TYPE
			SYNTAX INTEGER
				{
				linknormal(1),
				linkwaitbuild(2),
				linknouse(3),
				linknocfg(4)
				}
			MAX-ACCESS read-only
			STATUS current
			DESCRIPTION
				" "
			::= { hwV5InterfaceEntry 11 }
		
		hwV5IfBccDataLinkState OBJECT-TYPE
			SYNTAX INTEGER
				{
				linknormal(1),
				linkwaitbuild(2),
				linknouse(3),
				linknocfg(4)
				}
			MAX-ACCESS read-only
			STATUS current
			DESCRIPTION
				" "
			::= { hwV5InterfaceEntry 12 }
		
		hwV5IfCtrlDataLinkState OBJECT-TYPE
			SYNTAX INTEGER
				{
				linknormal(1),
				linkwaitbuild(2),
				linknouse(3),
				linknocfg(4)
				}
			MAX-ACCESS read-only
			STATUS current
			DESCRIPTION
				" "
			::= { hwV5InterfaceEntry 13 }
		
		hwV5IfProtectDataLink1State OBJECT-TYPE
			SYNTAX INTEGER
				{
				linknormal(1),
				linkwaitbuild(2),
				linknouse(3),
				linknocfg(4)
				}
			MAX-ACCESS read-only
			STATUS current
			DESCRIPTION
				" "
			::= { hwV5InterfaceEntry 14 }
		
		hwV5IfProtectDataLink2state OBJECT-TYPE
			SYNTAX INTEGER
				{
				linknormal(1),
				linkwaitbuild(2),
				linknouse(3),
				linknocfg(4)
				}
			MAX-ACCESS read-only
			STATUS current
			DESCRIPTION
				" "
			::= { hwV5InterfaceEntry 15 }
		
		hwV5IfLinkCtrlDataLinkState OBJECT-TYPE
			SYNTAX INTEGER
				{
				linknormal(1),
				linkwaitbuild(2),
				linknouse(3),
				linknocfg(4)
				}
			MAX-ACCESS read-only
			STATUS current
			DESCRIPTION
				" "
			::= { hwV5InterfaceEntry 16 }
		
		hwV5IfOprtype OBJECT-TYPE
			SYNTAX INTEGER
				{
				reset(1),
				restart(2),
				close(3)
				}
			MAX-ACCESS read-create
			STATUS current
			DESCRIPTION
				" "
			::= { hwV5InterfaceEntry 18 }
		
		hwV5IfOprResult OBJECT-TYPE
			SYNTAX INTEGER
				{
				success(1),
				failure(2)
				}
			MAX-ACCESS read-only
			STATUS current
			DESCRIPTION
				" "
			::= { hwV5InterfaceEntry 19 }
		
		hwV5LogicCChannelTable OBJECT-TYPE
			SYNTAX SEQUENCE OF HwV5LogicCChannelEntry
			MAX-ACCESS not-accessible
			STATUS current
			DESCRIPTION
				"The table lists the V5 groups that have been
				configured on the system."
			::= { hwV5MibObjects 6 }
		
		hwV5LogicCChannelEntry OBJECT-TYPE
			SYNTAX HwV5LogicCChannelEntry
			MAX-ACCESS not-accessible
			STATUS current
			DESCRIPTION ""
			INDEX { hwV5InterfaceID, hwV5LCChannelLogicCID }
			::= { hwV5LogicCChannelTable 1 }
		
		HwV5LogicCChannelEntry ::=
			SEQUENCE { 
				hwV5LCChannelLogicCID
					INTEGER,
				hwV5LCChanneLogicCLinkID
					INTEGER,
				hwV5LCChannelFrameID
					INTEGER,
				hwV5LCChannelSlotID
					INTEGER,
				hwV5LCChannelPortID
					INTEGER,
				hwV5LCChannelTsNo
					INTEGER,
				hwV5LCChannelProtectGroup
					INTEGER,
				hwV5LCChannelPSTNProtocolBear
					TruthValue,
				hwV5LCChannelCTRLProtocolBear
					TruthValue,
				hwV5LCChannelBCCProtocolBear
					TruthValue,
				hwV5LCChannelPROTProtocolBear
					TruthValue,
				hwV5LCChannelLCTRLProtocolBear
					TruthValue,
				hwV5LCChannelISDNDsProtocolBear
					TruthValue,
				hwV5LCChannelISDNpProtocolBear
					TruthValue,
				hwV5LCChannelISDNfProtocolBear
					TruthValue
			 }

		hwV5LCChannelLogicCID OBJECT-TYPE
			SYNTAX INTEGER (0..65535)
			MAX-ACCESS not-accessible
			STATUS current
			DESCRIPTION
				" "
			::= { hwV5LogicCChannelEntry 1 }
		
		hwV5LCChanneLogicCLinkID OBJECT-TYPE
			SYNTAX INTEGER (0..255)
			MAX-ACCESS read-only
			STATUS current
			DESCRIPTION
				" "
			::= { hwV5LogicCChannelEntry 2 }
		
		hwV5LCChannelFrameID OBJECT-TYPE
			SYNTAX INTEGER (0..63)
			MAX-ACCESS read-only
			STATUS current
			DESCRIPTION
				" "
			::= { hwV5LogicCChannelEntry 3 }
		
		hwV5LCChannelSlotID OBJECT-TYPE
			SYNTAX INTEGER (0..63)
			MAX-ACCESS read-only
			STATUS current
			DESCRIPTION
				" "
			::= { hwV5LogicCChannelEntry 4 }
		
		hwV5LCChannelPortID OBJECT-TYPE
			SYNTAX INTEGER (0..63)
			MAX-ACCESS read-only
			STATUS current
			DESCRIPTION
				" "
			::= { hwV5LogicCChannelEntry 5 }
		
		hwV5LCChannelTsNo OBJECT-TYPE
			SYNTAX INTEGER
				{
				t15(1),
				t16(2),
				t31(3)
				}
			MAX-ACCESS read-only
			STATUS current
			DESCRIPTION
				" "
			::= { hwV5LogicCChannelEntry 6 }
		
		hwV5LCChannelProtectGroup OBJECT-TYPE
			SYNTAX INTEGER
				{
				pm(1),
				ps(2),
				p2m(3),
				p2s(4)
				}
			MAX-ACCESS read-only
			STATUS current
			DESCRIPTION
				" "
			::= { hwV5LogicCChannelEntry 7 }
		
		hwV5LCChannelPSTNProtocolBear OBJECT-TYPE
			SYNTAX TruthValue
			MAX-ACCESS read-only
			STATUS current
			DESCRIPTION
				" "
			::= { hwV5LogicCChannelEntry 8 }
		
		hwV5LCChannelCTRLProtocolBear OBJECT-TYPE
			SYNTAX TruthValue
			MAX-ACCESS read-only
			STATUS current
			DESCRIPTION
				" "
			::= { hwV5LogicCChannelEntry 9 }
		
		hwV5LCChannelBCCProtocolBear OBJECT-TYPE
			SYNTAX TruthValue
			MAX-ACCESS read-only
			STATUS current
			DESCRIPTION
				" "
			::= { hwV5LogicCChannelEntry 10 }
		
		hwV5LCChannelPROTProtocolBear OBJECT-TYPE
			SYNTAX TruthValue
			MAX-ACCESS read-only
			STATUS current
			DESCRIPTION
				" "
			::= { hwV5LogicCChannelEntry 11 }
		
		hwV5LCChannelLCTRLProtocolBear OBJECT-TYPE
			SYNTAX TruthValue
			MAX-ACCESS read-only
			STATUS current
			DESCRIPTION
				" "
			::= { hwV5LogicCChannelEntry 12 }
		
		hwV5LCChannelISDNDsProtocolBear OBJECT-TYPE
			SYNTAX TruthValue
			MAX-ACCESS read-only
			STATUS current
			DESCRIPTION
				" "
			::= { hwV5LogicCChannelEntry 13 }
		
		hwV5LCChannelISDNpProtocolBear OBJECT-TYPE
			SYNTAX TruthValue
			MAX-ACCESS read-only
			STATUS current
			DESCRIPTION
				" "
			::= { hwV5LogicCChannelEntry 14 }
		
		hwV5LCChannelISDNfProtocolBear OBJECT-TYPE
			SYNTAX TruthValue
			MAX-ACCESS read-only
			STATUS current
			DESCRIPTION
				" "
			::= { hwV5LogicCChannelEntry 15 }
		
		hwV5StandbyPhyCChannelTable OBJECT-TYPE
			SYNTAX SEQUENCE OF HwV5StandbyPhyCChannelEntry
			MAX-ACCESS not-accessible
			STATUS current
			DESCRIPTION
				"The table lists the V5 groups that have been
				configured on the system."
			::= { hwV5MibObjects 7 }
		
		hwV5StandbyPhyCChannelEntry OBJECT-TYPE
			SYNTAX HwV5StandbyPhyCChannelEntry
			MAX-ACCESS not-accessible
			STATUS current
			DESCRIPTION ""
			INDEX { hwV5InterfaceID, hwV5StandbyPhyLogicStdPhyCNo }
			::= { hwV5StandbyPhyCChannelTable 1 }
		
		HwV5StandbyPhyCChannelEntry ::=
			SEQUENCE { 
				hwV5StandbyPhyLogicStdPhyCNo
					INTEGER,
				hwV5StandbyPhyPhyCLinkID
					INTEGER,
				hwV5StandbyPhyFrameID
					INTEGER,
				hwV5StandbyPhySlotID
					INTEGER,
				hwV5StandbyPhyPortID
					INTEGER,
				hwV5StandbyPhyTsNo
					INTEGER,
				hwV5StandbyPhyPhyCProtectGroup
					INTEGER
			 }

		hwV5StandbyPhyLogicStdPhyCNo OBJECT-TYPE
			SYNTAX INTEGER
				{
				protectgroup1(1),
				protectgroup2(2),
				protectgroup3(3),
				protectgroup4(4)
				}
			MAX-ACCESS not-accessible
			STATUS current
			DESCRIPTION
				" "
			::= { hwV5StandbyPhyCChannelEntry 1 }
		
		hwV5StandbyPhyPhyCLinkID OBJECT-TYPE
			SYNTAX INTEGER (0..255)
			MAX-ACCESS read-only
			STATUS current
			DESCRIPTION
				" "
			::= { hwV5StandbyPhyCChannelEntry 2 }
		
		hwV5StandbyPhyFrameID OBJECT-TYPE
			SYNTAX INTEGER (0..63)
			MAX-ACCESS read-only
			STATUS current
			DESCRIPTION
				" "
			::= { hwV5StandbyPhyCChannelEntry 3 }
		
		hwV5StandbyPhySlotID OBJECT-TYPE
			SYNTAX INTEGER (0..63)
			MAX-ACCESS read-only
			STATUS current
			DESCRIPTION
				" "
			::= { hwV5StandbyPhyCChannelEntry 4 }
		
		hwV5StandbyPhyPortID OBJECT-TYPE
			SYNTAX INTEGER (0..63)
			MAX-ACCESS read-only
			STATUS current
			DESCRIPTION
				" "
			::= { hwV5StandbyPhyCChannelEntry 5 }
		
		hwV5StandbyPhyTsNo OBJECT-TYPE
			SYNTAX INTEGER
				{
				t15(1),
				t16(2),
				t31(3)
				}
			MAX-ACCESS read-only
			STATUS current
			DESCRIPTION
				" "
			::= { hwV5StandbyPhyCChannelEntry 6 }
		
		hwV5StandbyPhyPhyCProtectGroup OBJECT-TYPE
			SYNTAX INTEGER
				{
				pm(1),
				ps(2),
				p2m(3),
				p2s(4)
				}
			MAX-ACCESS read-only
			STATUS current
			DESCRIPTION
				" "
			::= { hwV5StandbyPhyCChannelEntry 7 }
		
		hwV5LinkTable OBJECT-TYPE
			SYNTAX SEQUENCE OF HwV5LinkEntry
			MAX-ACCESS not-accessible
			STATUS current
			DESCRIPTION
				"The table lists the V5 groups that have been
				configured on the system."
			::= { hwV5MibObjects 8 }
		
		hwV5LinkEntry OBJECT-TYPE
			SYNTAX HwV5LinkEntry
			MAX-ACCESS not-accessible
			STATUS current
			DESCRIPTION ""
			INDEX { hwV5InterfaceID, hwV5LinkLinkID }
			::= { hwV5LinkTable 1 }
		
		HwV5LinkEntry ::=
			SEQUENCE { 
				hwV5LinkLinkID
					INTEGER,
				hwV5LinkLinkState
					INTEGER,
				hwV5LinkCRC4
					TruthValue,
				hwV5LinkLIDState
					INTEGER,
				hwV5LinkOprType
					INTEGER,
	                        hwV5LinkTsState	
                                        Unsigned32
			 }

		hwV5LinkLinkID OBJECT-TYPE
			SYNTAX INTEGER (0..255)
			MAX-ACCESS not-accessible
			STATUS current
			DESCRIPTION
				" "
			::= { hwV5LinkEntry 1 }
		
		hwV5LinkLinkState OBJECT-TYPE
			SYNTAX INTEGER
				{
				linkfail(1),
				linkfailblock(2),
				linkblock(3),
				linlockunblock(4),
				linremkunblock(5),
				linknomal(6),
				remotelinkid(7),
				locallinkid(8),
				linknotcfged(9)
				}
			MAX-ACCESS read-only
			STATUS current
			DESCRIPTION
				" "
			::= { hwV5LinkEntry 3 }
		
		hwV5LinkCRC4 OBJECT-TYPE
			SYNTAX TruthValue
			MAX-ACCESS read-only
			STATUS current
			DESCRIPTION
				" "
			::= { hwV5LinkEntry 4 }
		
		hwV5LinkLIDState OBJECT-TYPE
			SYNTAX INTEGER
				{
				linkidnoreq(1),
				linkidsuccess(2),
				linkidfail(3),
				linkidreject(4),
				linkid(5),
				linkidlenores(6),
				linkidgiveinres(7)
				}
			MAX-ACCESS read-only
			STATUS current
			DESCRIPTION
				" "
			::= { hwV5LinkEntry 5 }
		
		hwV5LinkOprType OBJECT-TYPE
			SYNTAX INTEGER
				{
				imclose(1),
				delayclose(2),
				nodeclose(3),
				unclose(4),
				linkidoper(5)
				}
			MAX-ACCESS read-create
			STATUS current
			DESCRIPTION
				" "
			::= { hwV5LinkEntry 6 }
			
    		hwV5LinkTsState         OBJECT-TYPE
        		SYNTAX      Unsigned32(0..4294967295)  
        		MAX-ACCESS  read-only
        		STATUS      current
        		DESCRIPTION
         			" "
    			::= { hwV5LinkEntry 7 }
		
		hwV5ReProvisionOperatorTable OBJECT-TYPE
			SYNTAX SEQUENCE OF HwV5ReProvisionOperatorEntry
			MAX-ACCESS not-accessible
			STATUS current
			DESCRIPTION
				"The table lists the V5 groups that have been
				configured on the system."
			::= { hwV5MibObjects 9 }
		
		hwV5ReProvisionOperatorEntry OBJECT-TYPE
			SYNTAX HwV5ReProvisionOperatorEntry
			MAX-ACCESS not-accessible
			STATUS current
			DESCRIPTION ""
			INDEX { hwV5InterfaceID }
			::= { hwV5ReProvisionOperatorTable 1 }
		
		HwV5ReProvisionOperatorEntry ::=
			SEQUENCE { 
				hwV5ReProvisionv5variable
					INTEGER,
				hwV5ReProvisionrejectreason
					INTEGER,
				hwV5ReProvisionOperType
					INTEGER
			 }

		hwV5ReProvisionv5variable OBJECT-TYPE
			SYNTAX INTEGER (0..127)
			MAX-ACCESS read-create
			STATUS current
			DESCRIPTION
				" "
			::= { hwV5ReProvisionOperatorEntry 1 }
		
		hwV5ReProvisionrejectreason OBJECT-TYPE
			SYNTAX INTEGER
				{
				varunkown(1),
				varunprepare(2),
				provision(3)
				}
			MAX-ACCESS read-create
			STATUS current
			DESCRIPTION
				" "
			::= { hwV5ReProvisionOperatorEntry 2 }
		
		hwV5ReProvisionOperType OBJECT-TYPE
			SYNTAX INTEGER
				{
				dateuse(1),
				checkre(2),
				changevar(3),
				reqvarifid(4),
				reprovision(5),
				reprovisionunprepare(6),
				reprovisionstart(7),
				unablereprovision(8)
				}
			MAX-ACCESS read-create
			STATUS current
			DESCRIPTION
				" "
			::= { hwV5ReProvisionOperatorEntry 3 }
		
		hwV5IsdnCChannelConfigTable OBJECT-TYPE
			SYNTAX SEQUENCE OF HwV5IsdnCChannelConfigEntry
			MAX-ACCESS not-accessible
			STATUS current
			DESCRIPTION
				"The table lists the V5 groups that have been
				configured on the system."
			::= { hwV5MibObjects 10 }
		
		hwV5IsdnCChannelConfigEntry OBJECT-TYPE
			SYNTAX HwV5IsdnCChannelConfigEntry
			MAX-ACCESS not-accessible
			STATUS current
			DESCRIPTION
				" "
			INDEX { hwV5InterfaceID, hwV5IsdnCCIsdnPortGroupNo }
			::= { hwV5IsdnCChannelConfigTable 1 }
		
		HwV5IsdnCChannelConfigEntry ::=
			SEQUENCE { 
				hwV5IsdnCCIsdnPortGroupNo
					INTEGER,
				hwV5IsdnCCLogicCID
					INTEGER,
				hwV5IsdnCCDChannelType
					INTEGER,
				hwV5IsdnCCUpperIsdnPortGroupNo
					INTEGER,
				hwV5IsdnCCRowStatus
					RowStatus
			 }

		hwV5IsdnCCIsdnPortGroupNo OBJECT-TYPE
			SYNTAX INTEGER (0..255)
			MAX-ACCESS not-accessible
			STATUS current
			DESCRIPTION
				" "
			::= { hwV5IsdnCChannelConfigEntry 1 }
		
		hwV5IsdnCCLogicCID OBJECT-TYPE
			SYNTAX INTEGER (0..65535)
			MAX-ACCESS read-create
			STATUS current
			DESCRIPTION
				" "
			::= { hwV5IsdnCChannelConfigEntry 2 }
		
		hwV5IsdnCCDChannelType OBJECT-TYPE
			SYNTAX INTEGER
				{
				d(1),
				f(2),
				p(3)
				}
			MAX-ACCESS read-create
			STATUS current
			DESCRIPTION
				" "
			::= { hwV5IsdnCChannelConfigEntry 3 }
		
		hwV5IsdnCCUpperIsdnPortGroupNo OBJECT-TYPE
			SYNTAX INTEGER (0..255)
			MAX-ACCESS read-create
			STATUS current
			DESCRIPTION
				" "
			::= { hwV5IsdnCChannelConfigEntry 4 }
		
		hwV5IsdnCCRowStatus OBJECT-TYPE
			SYNTAX RowStatus
			MAX-ACCESS read-create
			STATUS current
			DESCRIPTION
				" "
			::= { hwV5IsdnCChannelConfigEntry 5 }
		
		hwV5RingTypeMapConfigTable OBJECT-TYPE
			SYNTAX SEQUENCE OF HwV5RingTypeMapConfigEntry
			MAX-ACCESS not-accessible
			STATUS current
			DESCRIPTION
				"The table lists the V5 groups that have been
				configured on the system."
			::= { hwV5MibObjects 11 }
		
		hwV5RingTypeMapConfigEntry OBJECT-TYPE
			SYNTAX HwV5RingTypeMapConfigEntry
			MAX-ACCESS not-accessible
			STATUS current
			DESCRIPTION
				" "
			INDEX { hwV5InterfaceID, hwV5RingPeerRingType }
			::= { hwV5RingTypeMapConfigTable 1 }
		
		HwV5RingTypeMapConfigEntry ::=
			SEQUENCE { 
				hwV5RingPeerRingType
					INTEGER,
				hwV5RingCascadeRingType
					INTEGER,
				hwV5RingInitRingType
					INTEGER,
				hwV5RingRowStatus
					RowStatus
			 }

		hwV5RingPeerRingType OBJECT-TYPE
			SYNTAX INTEGER (0..127)
			MAX-ACCESS not-accessible
			STATUS current
			DESCRIPTION
				" "
			::= { hwV5RingTypeMapConfigEntry 1 }
		
		hwV5RingCascadeRingType OBJECT-TYPE
			SYNTAX INTEGER
				{
				r1(1),
				r2(2),
				r3(3),
				r4(4),
				r5(5),
				r6(6),
				r7(7),
				r8(8),
				r9(9),
				r10(10),
				r11(11),
				r12(12),
				r13(13),
				r14(14),
				r15(15),
				r16(16),
				r17(17),
				r18(18),
				r19(19),
				r20(20),
				r21(21),
				r22(22),
				r23(23),
				r24(24),
				r25(25),
				r26(26),
				r27(27),
				r28(28),
				r29(29),
				r30(30)
				}
			MAX-ACCESS read-create
			STATUS current
			DESCRIPTION
				" "
			::= { hwV5RingTypeMapConfigEntry 2 }
		
		hwV5RingInitRingType OBJECT-TYPE
			SYNTAX INTEGER
				{
				r1(1),
				r2(2),
				r3(3),
				r4(4),
				r5(5),
				r6(6),
				r7(7),
				r8(8),
				r9(9),
				r10(10),
				r11(11),
				r12(12),
				r13(13),
				r14(14),
				r15(15),
				r16(16),
				r17(17),
				r18(18),
				r19(19),
				r20(20),
				r21(21),
				r22(22),
				r23(23),
				r24(24),
				r25(25),
				r26(26),
				r27(27)
				}
			MAX-ACCESS read-create
			STATUS current
			DESCRIPTION
				" "
			::= { hwV5RingTypeMapConfigEntry 3 }
		
		hwV5RingRowStatus OBJECT-TYPE
			SYNTAX RowStatus
			MAX-ACCESS read-create
			STATUS current
			DESCRIPTION
				" "
			::= { hwV5RingTypeMapConfigEntry 4 }
		
		hwUserDefineRingTypeTable OBJECT-TYPE
			SYNTAX SEQUENCE OF HwUserDefineRingTypeEntry
			MAX-ACCESS not-accessible
			STATUS current
			DESCRIPTION
				"The table lists the V5 groups that have been
				configured on the system."
			::= { hwV5MibObjects 12 }
		
		hwUserDefineRingTypeEntry OBJECT-TYPE
			SYNTAX HwUserDefineRingTypeEntry
			MAX-ACCESS not-accessible
			STATUS current
			DESCRIPTION
				" "
			INDEX { hwV5UserTypeRingType }
			::= { hwUserDefineRingTypeTable 1 }
		
		HwUserDefineRingTypeEntry ::=
			SEQUENCE { 
				hwV5UserTypeRingType
					INTEGER,
				hwV5UserTypePara1
					INTEGER,
				hwV5UserTypePara2
					INTEGER,
				hwV5UserTypePara3
					INTEGER,
				hwV5UserTypePara4
					INTEGER,
				hwV5UserTypePara5
					INTEGER,
				hwV5UserTypePara6
					INTEGER
			 }

		hwV5UserTypeRingType OBJECT-TYPE
			SYNTAX INTEGER (1..16)
			MAX-ACCESS not-accessible
			STATUS current
			DESCRIPTION
				" "
			::= { hwUserDefineRingTypeEntry 1 }
		
		hwV5UserTypePara1 OBJECT-TYPE
			SYNTAX INTEGER (0..12000)
			MAX-ACCESS read-create
			STATUS current
			DESCRIPTION
				" "
			::= { hwUserDefineRingTypeEntry 2 }
		
		hwV5UserTypePara2 OBJECT-TYPE
			SYNTAX INTEGER (0..12000)
			MAX-ACCESS read-create
			STATUS current
			DESCRIPTION
				" "
			::= { hwUserDefineRingTypeEntry 3 }
		
		hwV5UserTypePara3 OBJECT-TYPE
			SYNTAX INTEGER (0..12000)
			MAX-ACCESS read-create
			STATUS current
			DESCRIPTION
				" "
			::= { hwUserDefineRingTypeEntry 4 }
		
		hwV5UserTypePara4 OBJECT-TYPE
			SYNTAX INTEGER (0..12000)
			MAX-ACCESS read-create
			STATUS current
			DESCRIPTION
				" "
			::= { hwUserDefineRingTypeEntry 5 }
		
		hwV5UserTypePara5 OBJECT-TYPE
			SYNTAX INTEGER (0..12000)
			MAX-ACCESS read-create
			STATUS current
			DESCRIPTION
				" "
			::= { hwUserDefineRingTypeEntry 6 }
		
		hwV5UserTypePara6 OBJECT-TYPE
			SYNTAX INTEGER (0..12000)
			MAX-ACCESS read-create
			STATUS current
			DESCRIPTION
				" "
			::= { hwUserDefineRingTypeEntry 7 }

    		hwV5channelNextAllocPhyCNo    OBJECT-TYPE
     			SYNTAX      INTEGER(0..255)
       			MAX-ACCESS  read-only
      			STATUS      current
    			DESCRIPTION
       			        "The leaf will alloc next valid physics C channel "
  			::= { hwV5MibObjects 13 }
  			
    		hwV5IsdnNextAllocPortGroup    OBJECT-TYPE
        		SYNTAX      INTEGER(0..254)
        		MAX-ACCESS  read-only
        		STATUS      current
    			DESCRIPTION
         			"The leaf will alloc next valid port-group"
    			::= { hwV5MibObjects 14 }  			
  			
		
		hwV5MibTrap OBJECT IDENTIFIER ::= { hwV5 2 }
		
		hwV5TrapOid OBJECT IDENTIFIER ::= { hwV5MibTrap 1 }
		
		hwV5TrapsDefine OBJECT IDENTIFIER ::= { hwV5MibTrap 2 }
		
		hwV5Traps OBJECT IDENTIFIER ::= { hwV5TrapsDefine 0 }
		
		hwV5MibCompance OBJECT IDENTIFIER ::= { hwV5 3 }
		
	
	END

--
-- HUAWEI-V5-MIB.my
--
