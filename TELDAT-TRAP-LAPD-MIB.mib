-- file automatically created


TELDAT-TRAP-LAPD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


lapdTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LAPD event subsystem."
    REVISION "201401200930Z"
    DESCRIPTION "Initial implementation"
        ::= { telEventTraps 119 }


lapdEventsGroup	OBJECT IDENTIFIER	::= { lapdTrapsMIB 1 }

lapdNotifications	OBJECT IDENTIFIER	::= { lapdTrapsMIB 2 }
lapdNotificationsPrefix	OBJECT IDENTIFIER	::= { lapdNotifications 0 }

lapdEventObjects1 OBJECT-IDENTITY
    STATUS current
    DESCRIPTION
        "Event LAPD.1
        Unnumebered frame transmitted."
    ::= { lapdEventsGroup 1 }

lapd1-SAPI OBJECT-TYPE
    SYNTAX Integer32
    MAX-ACCESS accessible-for-notify
    STATUS current
    DESCRIPTION
        "Parameter 'SAPI' in event LAPD.1"
    ::= { lapdEventObjects1 1 }

lapd1-TEI OBJECT-TYPE
    SYNTAX Integer32
    MAX-ACCESS accessible-for-notify
    STATUS current
    DESCRIPTION
        "Parameter 'TEI' in event LAPD.1"
    ::= { lapdEventObjects1 2 }

lapd1-frame OBJECT-TYPE
    SYNTAX DisplayString
    MAX-ACCESS accessible-for-notify
    STATUS current
    DESCRIPTION
        "Parameter 'frame' in event LAPD.1"
    ::= { lapdEventObjects1 3 }

lapd1-bit-pf OBJECT-TYPE
    SYNTAX Integer32
    MAX-ACCESS accessible-for-notify
    STATUS current
    DESCRIPTION
        "Parameter 'bit-pf' in event LAPD.1"
    ::= { lapdEventObjects1 4 }

lapd1-interface OBJECT-TYPE
    SYNTAX DisplayString
    MAX-ACCESS accessible-for-notify
    STATUS current
    DESCRIPTION
        "Parameter 'interface' in event LAPD.1"
    ::= { lapdEventObjects1 5 }

lapdEventObjects2 OBJECT-IDENTITY
    STATUS current
    DESCRIPTION
        "Event LAPD.2
        Supervisory frame transmitted."
    ::= { lapdEventsGroup 2 }

lapd2-SAPI OBJECT-TYPE
    SYNTAX Integer32
    MAX-ACCESS accessible-for-notify
    STATUS current
    DESCRIPTION
        "Parameter 'SAPI' in event LAPD.2"
    ::= { lapdEventObjects2 1 }

lapd2-TEI OBJECT-TYPE
    SYNTAX Integer32
    MAX-ACCESS accessible-for-notify
    STATUS current
    DESCRIPTION
        "Parameter 'TEI' in event LAPD.2"
    ::= { lapdEventObjects2 2 }

lapd2-frame OBJECT-TYPE
    SYNTAX DisplayString
    MAX-ACCESS accessible-for-notify
    STATUS current
    DESCRIPTION
        "Parameter 'frame' in event LAPD.2"
    ::= { lapdEventObjects2 3 }

lapd2-bit-pf OBJECT-TYPE
    SYNTAX Integer32
    MAX-ACCESS accessible-for-notify
    STATUS current
    DESCRIPTION
        "Parameter 'bit-pf' in event LAPD.2"
    ::= { lapdEventObjects2 4 }

lapd2-nr OBJECT-TYPE
    SYNTAX Integer32
    MAX-ACCESS accessible-for-notify
    STATUS current
    DESCRIPTION
        "Parameter 'nr' in event LAPD.2"
    ::= { lapdEventObjects2 5 }

lapd2-interface OBJECT-TYPE
    SYNTAX DisplayString
    MAX-ACCESS accessible-for-notify
    STATUS current
    DESCRIPTION
        "Parameter 'interface' in event LAPD.2"
    ::= { lapdEventObjects2 6 }

lapdEventObjects3 OBJECT-IDENTITY
    STATUS current
    DESCRIPTION
        "Event LAPD.3
        RNR or REJ Supervisory frame transmitted."
    ::= { lapdEventsGroup 3 }

lapd3-SAPI OBJECT-TYPE
    SYNTAX Integer32
    MAX-ACCESS accessible-for-notify
    STATUS current
    DESCRIPTION
        "Parameter 'SAPI' in event LAPD.3"
    ::= { lapdEventObjects3 1 }

lapd3-TEI OBJECT-TYPE
    SYNTAX Integer32
    MAX-ACCESS accessible-for-notify
    STATUS current
    DESCRIPTION
        "Parameter 'TEI' in event LAPD.3"
    ::= { lapdEventObjects3 2 }

lapd3-frame OBJECT-TYPE
    SYNTAX DisplayString
    MAX-ACCESS accessible-for-notify
    STATUS current
    DESCRIPTION
        "Parameter 'frame' in event LAPD.3"
    ::= { lapdEventObjects3 3 }

lapd3-bit-pf OBJECT-TYPE
    SYNTAX Integer32
    MAX-ACCESS accessible-for-notify
    STATUS current
    DESCRIPTION
        "Parameter 'bit-pf' in event LAPD.3"
    ::= { lapdEventObjects3 4 }

lapd3-nr OBJECT-TYPE
    SYNTAX Integer32
    MAX-ACCESS accessible-for-notify
    STATUS current
    DESCRIPTION
        "Parameter 'nr' in event LAPD.3"
    ::= { lapdEventObjects3 5 }

lapd3-interface OBJECT-TYPE
    SYNTAX DisplayString
    MAX-ACCESS accessible-for-notify
    STATUS current
    DESCRIPTION
        "Parameter 'interface' in event LAPD.3"
    ::= { lapdEventObjects3 6 }

lapdEventObjects4 OBJECT-IDENTITY
    STATUS current
    DESCRIPTION
        "Event LAPD.4
        Info frame transmitted."
    ::= { lapdEventsGroup 4 }

lapd4-SAPI OBJECT-TYPE
    SYNTAX Integer32
    MAX-ACCESS accessible-for-notify
    STATUS current
    DESCRIPTION
        "Parameter 'SAPI' in event LAPD.4"
    ::= { lapdEventObjects4 1 }

lapd4-TEI OBJECT-TYPE
    SYNTAX Integer32
    MAX-ACCESS accessible-for-notify
    STATUS current
    DESCRIPTION
        "Parameter 'TEI' in event LAPD.4"
    ::= { lapdEventObjects4 2 }

lapd4-frame OBJECT-TYPE
    SYNTAX DisplayString
    MAX-ACCESS accessible-for-notify
    STATUS current
    DESCRIPTION
        "Parameter 'frame' in event LAPD.4"
    ::= { lapdEventObjects4 3 }

lapd4-bit-pf OBJECT-TYPE
    SYNTAX Integer32
    MAX-ACCESS accessible-for-notify
    STATUS current
    DESCRIPTION
        "Parameter 'bit-pf' in event LAPD.4"
    ::= { lapdEventObjects4 4 }

lapd4-ns OBJECT-TYPE
    SYNTAX Integer32
    MAX-ACCESS accessible-for-notify
    STATUS current
    DESCRIPTION
        "Parameter 'ns' in event LAPD.4"
    ::= { lapdEventObjects4 5 }

lapd4-nr OBJECT-TYPE
    SYNTAX Integer32
    MAX-ACCESS accessible-for-notify
    STATUS current
    DESCRIPTION
        "Parameter 'nr' in event LAPD.4"
    ::= { lapdEventObjects4 6 }

lapd4-interface OBJECT-TYPE
    SYNTAX DisplayString
    MAX-ACCESS accessible-for-notify
    STATUS current
    DESCRIPTION
        "Parameter 'interface' in event LAPD.4"
    ::= { lapdEventObjects4 7 }

lapdEventObjects5 OBJECT-IDENTITY
    STATUS current
    DESCRIPTION
        "Event LAPD.5
        Unnumebered frame received."
    ::= { lapdEventsGroup 5 }

lapd5-SAPI OBJECT-TYPE
    SYNTAX Integer32
    MAX-ACCESS accessible-for-notify
    STATUS current
    DESCRIPTION
        "Parameter 'SAPI' in event LAPD.5"
    ::= { lapdEventObjects5 1 }

lapd5-TEI OBJECT-TYPE
    SYNTAX Integer32
    MAX-ACCESS accessible-for-notify
    STATUS current
    DESCRIPTION
        "Parameter 'TEI' in event LAPD.5"
    ::= { lapdEventObjects5 2 }

lapd5-frame OBJECT-TYPE
    SYNTAX DisplayString
    MAX-ACCESS accessible-for-notify
    STATUS current
    DESCRIPTION
        "Parameter 'frame' in event LAPD.5"
    ::= { lapdEventObjects5 3 }

lapd5-bit-pf OBJECT-TYPE
    SYNTAX Integer32
    MAX-ACCESS accessible-for-notify
    STATUS current
    DESCRIPTION
        "Parameter 'bit-pf' in event LAPD.5"
    ::= { lapdEventObjects5 4 }

lapd5-interface OBJECT-TYPE
    SYNTAX DisplayString
    MAX-ACCESS accessible-for-notify
    STATUS current
    DESCRIPTION
        "Parameter 'interface' in event LAPD.5"
    ::= { lapdEventObjects5 5 }

lapdEventObjects6 OBJECT-IDENTITY
    STATUS current
    DESCRIPTION
        "Event LAPD.6
        RR Supervisory frame received."
    ::= { lapdEventsGroup 6 }

lapd6-SAPI OBJECT-TYPE
    SYNTAX Integer32
    MAX-ACCESS accessible-for-notify
    STATUS current
    DESCRIPTION
        "Parameter 'SAPI' in event LAPD.6"
    ::= { lapdEventObjects6 1 }

lapd6-TEI OBJECT-TYPE
    SYNTAX Integer32
    MAX-ACCESS accessible-for-notify
    STATUS current
    DESCRIPTION
        "Parameter 'TEI' in event LAPD.6"
    ::= { lapdEventObjects6 2 }

lapd6-frame OBJECT-TYPE
    SYNTAX DisplayString
    MAX-ACCESS accessible-for-notify
    STATUS current
    DESCRIPTION
        "Parameter 'frame' in event LAPD.6"
    ::= { lapdEventObjects6 3 }

lapd6-bit-pf OBJECT-TYPE
    SYNTAX Integer32
    MAX-ACCESS accessible-for-notify
    STATUS current
    DESCRIPTION
        "Parameter 'bit-pf' in event LAPD.6"
    ::= { lapdEventObjects6 4 }

lapd6-nr OBJECT-TYPE
    SYNTAX Integer32
    MAX-ACCESS accessible-for-notify
    STATUS current
    DESCRIPTION
        "Parameter 'nr' in event LAPD.6"
    ::= { lapdEventObjects6 5 }

lapd6-interface OBJECT-TYPE
    SYNTAX DisplayString
    MAX-ACCESS accessible-for-notify
    STATUS current
    DESCRIPTION
        "Parameter 'interface' in event LAPD.6"
    ::= { lapdEventObjects6 6 }

lapdEventObjects7 OBJECT-IDENTITY
    STATUS current
    DESCRIPTION
        "Event LAPD.7
        RNR or REJ Supervisory frame received."
    ::= { lapdEventsGroup 7 }

lapd7-SAPI OBJECT-TYPE
    SYNTAX Integer32
    MAX-ACCESS accessible-for-notify
    STATUS current
    DESCRIPTION
        "Parameter 'SAPI' in event LAPD.7"
    ::= { lapdEventObjects7 1 }

lapd7-TEI OBJECT-TYPE
    SYNTAX Integer32
    MAX-ACCESS accessible-for-notify
    STATUS current
    DESCRIPTION
        "Parameter 'TEI' in event LAPD.7"
    ::= { lapdEventObjects7 2 }

lapd7-frame OBJECT-TYPE
    SYNTAX DisplayString
    MAX-ACCESS accessible-for-notify
    STATUS current
    DESCRIPTION
        "Parameter 'frame' in event LAPD.7"
    ::= { lapdEventObjects7 3 }

lapd7-bit-pf OBJECT-TYPE
    SYNTAX Integer32
    MAX-ACCESS accessible-for-notify
    STATUS current
    DESCRIPTION
        "Parameter 'bit-pf' in event LAPD.7"
    ::= { lapdEventObjects7 4 }

lapd7-nr OBJECT-TYPE
    SYNTAX Integer32
    MAX-ACCESS accessible-for-notify
    STATUS current
    DESCRIPTION
        "Parameter 'nr' in event LAPD.7"
    ::= { lapdEventObjects7 5 }

lapd7-interface OBJECT-TYPE
    SYNTAX DisplayString
    MAX-ACCESS accessible-for-notify
    STATUS current
    DESCRIPTION
        "Parameter 'interface' in event LAPD.7"
    ::= { lapdEventObjects7 6 }

lapdEventObjects8 OBJECT-IDENTITY
    STATUS current
    DESCRIPTION
        "Event LAPD.8
        Info frame transmitted."
    ::= { lapdEventsGroup 8 }

lapd8-SAPI OBJECT-TYPE
    SYNTAX Integer32
    MAX-ACCESS accessible-for-notify
    STATUS current
    DESCRIPTION
        "Parameter 'SAPI' in event LAPD.8"
    ::= { lapdEventObjects8 1 }

lapd8-TEI OBJECT-TYPE
    SYNTAX Integer32
    MAX-ACCESS accessible-for-notify
    STATUS current
    DESCRIPTION
        "Parameter 'TEI' in event LAPD.8"
    ::= { lapdEventObjects8 2 }

lapd8-frame OBJECT-TYPE
    SYNTAX DisplayString
    MAX-ACCESS accessible-for-notify
    STATUS current
    DESCRIPTION
        "Parameter 'frame' in event LAPD.8"
    ::= { lapdEventObjects8 3 }

lapd8-bit-pf OBJECT-TYPE
    SYNTAX Integer32
    MAX-ACCESS accessible-for-notify
    STATUS current
    DESCRIPTION
        "Parameter 'bit-pf' in event LAPD.8"
    ::= { lapdEventObjects8 4 }

lapd8-ns OBJECT-TYPE
    SYNTAX Integer32
    MAX-ACCESS accessible-for-notify
    STATUS current
    DESCRIPTION
        "Parameter 'ns' in event LAPD.8"
    ::= { lapdEventObjects8 5 }

lapd8-nr OBJECT-TYPE
    SYNTAX Integer32
    MAX-ACCESS accessible-for-notify
    STATUS current
    DESCRIPTION
        "Parameter 'nr' in event LAPD.8"
    ::= { lapdEventObjects8 6 }

lapd8-interface OBJECT-TYPE
    SYNTAX DisplayString
    MAX-ACCESS accessible-for-notify
    STATUS current
    DESCRIPTION
        "Parameter 'interface' in event LAPD.8"
    ::= { lapdEventObjects8 7 }

lapdEventObjects9 OBJECT-IDENTITY
    STATUS current
    DESCRIPTION
        "Event LAPD.9
        Informational. Lapd error detectec according Q.921."
    ::= { lapdEventsGroup 9 }

lapd9-SAPI OBJECT-TYPE
    SYNTAX Integer32
    MAX-ACCESS accessible-for-notify
    STATUS current
    DESCRIPTION
        "Parameter 'SAPI' in event LAPD.9"
    ::= { lapdEventObjects9 1 }

lapd9-TEI OBJECT-TYPE
    SYNTAX Integer32
    MAX-ACCESS accessible-for-notify
    STATUS current
    DESCRIPTION
        "Parameter 'TEI' in event LAPD.9"
    ::= { lapdEventObjects9 2 }

lapd9-Code OBJECT-TYPE
    SYNTAX DisplayString
    MAX-ACCESS accessible-for-notify
    STATUS current
    DESCRIPTION
        "Parameter 'Code' in event LAPD.9"
    ::= { lapdEventObjects9 3 }

lapd9-interface OBJECT-TYPE
    SYNTAX DisplayString
    MAX-ACCESS accessible-for-notify
    STATUS current
    DESCRIPTION
        "Parameter 'interface' in event LAPD.9"
    ::= { lapdEventObjects9 4 }

lapdEventObjects10 OBJECT-IDENTITY
    STATUS current
    DESCRIPTION
        "Event LAPD.10
        Notify port state changed"
    ::= { lapdEventsGroup 10 }

lapd10-SAPI OBJECT-TYPE
    SYNTAX Integer32
    MAX-ACCESS accessible-for-notify
    STATUS current
    DESCRIPTION
        "Parameter 'SAPI' in event LAPD.10"
    ::= { lapdEventObjects10 1 }

lapd10-TEI OBJECT-TYPE
    SYNTAX Integer32
    MAX-ACCESS accessible-for-notify
    STATUS current
    DESCRIPTION
        "Parameter 'TEI' in event LAPD.10"
    ::= { lapdEventObjects10 2 }

lapd10-state OBJECT-TYPE
    SYNTAX DisplayString
    MAX-ACCESS accessible-for-notify
    STATUS current
    DESCRIPTION
        "Parameter 'state' in event LAPD.10"
    ::= { lapdEventObjects10 3 }

lapd10-interface OBJECT-TYPE
    SYNTAX DisplayString
    MAX-ACCESS accessible-for-notify
    STATUS current
    DESCRIPTION
        "Parameter 'interface' in event LAPD.10"
    ::= { lapdEventObjects10 4 }

lapdEventObjects11 OBJECT-IDENTITY
    STATUS current
    DESCRIPTION
        "Event LAPD.11
        Notify port state changed"
    ::= { lapdEventsGroup 11 }

lapd11-SAPI OBJECT-TYPE
    SYNTAX Integer32
    MAX-ACCESS accessible-for-notify
    STATUS current
    DESCRIPTION
        "Parameter 'SAPI' in event LAPD.11"
    ::= { lapdEventObjects11 1 }

lapd11-TEI OBJECT-TYPE
    SYNTAX Integer32
    MAX-ACCESS accessible-for-notify
    STATUS current
    DESCRIPTION
        "Parameter 'TEI' in event LAPD.11"
    ::= { lapdEventObjects11 2 }

lapd11-state OBJECT-TYPE
    SYNTAX DisplayString
    MAX-ACCESS accessible-for-notify
    STATUS current
    DESCRIPTION
        "Parameter 'state' in event LAPD.11"
    ::= { lapdEventObjects11 3 }

lapd11-interface OBJECT-TYPE
    SYNTAX DisplayString
    MAX-ACCESS accessible-for-notify
    STATUS current
    DESCRIPTION
        "Parameter 'interface' in event LAPD.11"
    ::= { lapdEventObjects11 4 }


lapdNotification1 NOTIFICATION-TYPE
    OBJECTS { 
              lapd1-SAPI, 
              lapd1-TEI,
              lapd1-frame,
              lapd1-bit-pf,
              lapd1-interface 
            }
    STATUS current
    DESCRIPTION
        "Notification of Event LAPD.1

        Message: 'S:$1 T:$2 Tx $3 P/F=$4 interface $5'

        Parameters list:
              $1: lapd1-SAPI
              $2: lapd1-TEI
              $3: lapd1-frame
              $4: lapd1-bit-pf
              $5: lapd1-interface

        Unnumebered frame transmitted."
    ::= { lapdNotificationsPrefix 1 }

lapdNotification2 NOTIFICATION-TYPE
    OBJECTS { 
              lapd2-SAPI, 
              lapd2-TEI,
              lapd2-frame,
              lapd2-bit-pf,
              lapd2-nr,
              lapd2-interface 
            }
    STATUS current
    DESCRIPTION
        "Notification of Event LAPD.2

        Message: 'S:$1 T:$2 Tx $3 P/F=$4		N(R)=$5 interface $6'

        Parameters list:
              $1: lapd2-SAPI
              $2: lapd2-TEI
              $3: lapd2-frame
              $4: lapd2-bit-pf
              $5: lapd2-nr
              $6: lapd2-interface

        Supervisory frame transmitted."
    ::= { lapdNotificationsPrefix 2 }

lapdNotification3 NOTIFICATION-TYPE
    OBJECTS { 
              lapd3-SAPI, 
              lapd3-TEI,
              lapd3-frame,
              lapd3-bit-pf,
              lapd3-nr,
              lapd3-interface 
            }
    STATUS current
    DESCRIPTION
        "Notification of Event LAPD.3

        Message: 'S:$1 T:$2 Tx $3 P/F=$4		N(R)=$5 interface $6'

        Parameters list:
              $1: lapd3-SAPI
              $2: lapd3-TEI
              $3: lapd3-frame
              $4: lapd3-bit-pf
              $5: lapd3-nr
              $6: lapd3-interface

        RNR or REJ Supervisory frame transmitted."
    ::= { lapdNotificationsPrefix 3 }

lapdNotification4 NOTIFICATION-TYPE
    OBJECTS { 
              lapd4-SAPI, 
              lapd4-TEI,
              lapd4-frame,
              lapd4-bit-pf,
              lapd4-ns,
              lapd4-nr,
              lapd4-interface 
            }
    STATUS current
    DESCRIPTION
        "Notification of Event LAPD.4

        Message: 'S:$1 T:$2 Tx $3 P/F=$4 N(S)=$5 N(R)=$6 interface $7'

        Parameters list:
              $1: lapd4-SAPI
              $2: lapd4-TEI
              $3: lapd4-frame
              $4: lapd4-bit-pf
              $5: lapd4-ns
              $6: lapd4-nr
              $7: lapd4-interface

        Info frame transmitted."
    ::= { lapdNotificationsPrefix 4 }

lapdNotification5 NOTIFICATION-TYPE
    OBJECTS { 
              lapd5-SAPI, 
              lapd5-TEI,
              lapd5-frame,
              lapd5-bit-pf,
              lapd5-interface 
            }
    STATUS current
    DESCRIPTION
        "Notification of Event LAPD.5

        Message: 'S:$1 T:$2 Rx $3 P/F=$4 interface $5'

        Parameters list:
              $1: lapd5-SAPI
              $2: lapd5-TEI
              $3: lapd5-frame
              $4: lapd5-bit-pf
              $5: lapd5-interface

        Unnumebered frame received."
    ::= { lapdNotificationsPrefix 5 }

lapdNotification6 NOTIFICATION-TYPE
    OBJECTS { 
              lapd6-SAPI, 
              lapd6-TEI,
              lapd6-frame,
              lapd6-bit-pf,
              lapd6-nr,
              lapd6-interface 
            }
    STATUS current
    DESCRIPTION
        "Notification of Event LAPD.6

        Message: 'S:$1 T:$2 Rx $3 P/F=$4		N(R)=$5 interface $6'

        Parameters list:
              $1: lapd6-SAPI
              $2: lapd6-TEI
              $3: lapd6-frame
              $4: lapd6-bit-pf
              $5: lapd6-nr
              $6: lapd6-interface

        RR Supervisory frame received."
    ::= { lapdNotificationsPrefix 6 }

lapdNotification7 NOTIFICATION-TYPE
    OBJECTS { 
              lapd7-SAPI, 
              lapd7-TEI,
              lapd7-frame,
              lapd7-bit-pf,
              lapd7-nr,
              lapd7-interface 
            }
    STATUS current
    DESCRIPTION
        "Notification of Event LAPD.7

        Message: 'S:$1 T:$2 Rx $3 P/F=$4		N(R)=$5 interface $6'

        Parameters list:
              $1: lapd7-SAPI
              $2: lapd7-TEI
              $3: lapd7-frame
              $4: lapd7-bit-pf
              $5: lapd7-nr
              $6: lapd7-interface

        RNR or REJ Supervisory frame received."
    ::= { lapdNotificationsPrefix 7 }

lapdNotification8 NOTIFICATION-TYPE
    OBJECTS { 
              lapd8-SAPI, 
              lapd8-TEI,
              lapd8-frame,
              lapd8-bit-pf,
              lapd8-ns,
              lapd8-nr,
              lapd8-interface 
            }
    STATUS current
    DESCRIPTION
        "Notification of Event LAPD.8

        Message: 'S:$1 T:$2 Rx $3 P/F=$4 N(S)=$5 N(R)=$6 interface $7'

        Parameters list:
              $1: lapd8-SAPI
              $2: lapd8-TEI
              $3: lapd8-frame
              $4: lapd8-bit-pf
              $5: lapd8-ns
              $6: lapd8-nr
              $7: lapd8-interface

        Info frame transmitted."
    ::= { lapdNotificationsPrefix 8 }

lapdNotification9 NOTIFICATION-TYPE
    OBJECTS { 
              lapd9-SAPI, 
              lapd9-TEI,
              lapd9-Code,
              lapd9-interface 
            }
    STATUS current
    DESCRIPTION
        "Notification of Event LAPD.9

        Message: 'S:$1 T:$2 Error Description $3 interface $4'

        Parameters list:
              $1: lapd9-SAPI
              $2: lapd9-TEI
              $3: lapd9-Code
              $4: lapd9-interface

        Informational. Lapd error detectec according Q.921."
    ::= { lapdNotificationsPrefix 9 }

lapdNotification10 NOTIFICATION-TYPE
    OBJECTS { 
              lapd10-SAPI, 
              lapd10-TEI,
              lapd10-state,
              lapd10-interface 
            }
    STATUS current
    DESCRIPTION
        "Notification of Event LAPD.10

        Message: 'S:$1 T:$2 State changed to $3 interface $4'

        Parameters list:
              $1: lapd10-SAPI
              $2: lapd10-TEI
              $3: lapd10-state
              $4: lapd10-interface

        Notify port state changed"
    ::= { lapdNotificationsPrefix 10 }

lapdNotification11 NOTIFICATION-TYPE
    OBJECTS { 
              lapd11-SAPI, 
              lapd11-TEI,
              lapd11-state,
              lapd11-interface 
            }
    STATUS current
    DESCRIPTION
        "Notification of Event LAPD.11

        Message: 'S:$1 T:$2 Operational state changed to $3 interface $4'

        Parameters list:
              $1: lapd11-SAPI
              $2: lapd11-TEI
              $3: lapd11-state
              $4: lapd11-interface

        Notify port state changed"
    ::= { lapdNotificationsPrefix 11 }


END
