-- file automatically created


TELDAT-TRAP-FR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


frTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FR event subsystem."
    REVISION "201401200930Z"
    DESCRIPTION "Initial implementation"
        ::= { telEventTraps 92 }


frEventsGroup	OBJECT IDENTIFIER	::= { frTrapsMIB 1 }

frNotifications	OBJECT IDENTIFIER	::= { frTrapsMIB 2 }
frNotificationsPrefix	OBJECT IDENTIFIER	::= { frNotifications 0 }

frEventObjects1 OBJECT-IDENTITY
    STATUS current
    DESCRIPTION
        "Event FR.1
        A frame had been received on the FR interface."
    ::= { frEventsGroup 1 }

fr1-circuit OBJECT-TYPE
    SYNTAX Integer32
    MAX-ACCESS accessible-for-notify
    STATUS current
    DESCRIPTION
        "Parameter 'circuit' in event FR.1"
    ::= { frEventObjects1 1 }

fr1-protocol OBJECT-TYPE
    SYNTAX DisplayString
    MAX-ACCESS accessible-for-notify
    STATUS current
    DESCRIPTION
        "Parameter 'protocol' in event FR.1"
    ::= { frEventObjects1 2 }

fr1-size OBJECT-TYPE
    SYNTAX Integer32
    MAX-ACCESS accessible-for-notify
    STATUS current
    DESCRIPTION
        "Parameter 'size' in event FR.1"
    ::= { frEventObjects1 3 }

fr1-ifcname OBJECT-TYPE
    SYNTAX DisplayString
    MAX-ACCESS accessible-for-notify
    STATUS current
    DESCRIPTION
        "Parameter 'ifcname' in event FR.1"
    ::= { frEventObjects1 4 }

fr1-buffer OBJECT-TYPE
    SYNTAX DisplayString
    MAX-ACCESS accessible-for-notify
    STATUS current
    DESCRIPTION
        "Parameter 'buffer' in event FR.1"
    ::= { frEventObjects1 5 }

frEventObjects2 OBJECT-IDENTITY
    STATUS current
    DESCRIPTION
        "Event FR.2
        A frame had been transmitted on the FR interface."
    ::= { frEventsGroup 2 }

fr2-circuit OBJECT-TYPE
    SYNTAX Integer32
    MAX-ACCESS accessible-for-notify
    STATUS current
    DESCRIPTION
        "Parameter 'circuit' in event FR.2"
    ::= { frEventObjects2 1 }

fr2-protocol OBJECT-TYPE
    SYNTAX DisplayString
    MAX-ACCESS accessible-for-notify
    STATUS current
    DESCRIPTION
        "Parameter 'protocol' in event FR.2"
    ::= { frEventObjects2 2 }

fr2-size OBJECT-TYPE
    SYNTAX Integer32
    MAX-ACCESS accessible-for-notify
    STATUS current
    DESCRIPTION
        "Parameter 'size' in event FR.2"
    ::= { frEventObjects2 3 }

fr2-ifcname OBJECT-TYPE
    SYNTAX DisplayString
    MAX-ACCESS accessible-for-notify
    STATUS current
    DESCRIPTION
        "Parameter 'ifcname' in event FR.2"
    ::= { frEventObjects2 4 }

fr2-buffer OBJECT-TYPE
    SYNTAX DisplayString
    MAX-ACCESS accessible-for-notify
    STATUS current
    DESCRIPTION
        "Parameter 'buffer' in event FR.2"
    ::= { frEventObjects2 5 }

frEventObjects3 OBJECT-IDENTITY
    STATUS current
    DESCRIPTION
        "Event FR.3
        A protocol frame had been discarded due to the PVC congested condition."
    ::= { frEventsGroup 3 }

fr3-circuit OBJECT-TYPE
    SYNTAX Integer32
    MAX-ACCESS accessible-for-notify
    STATUS current
    DESCRIPTION
        "Parameter 'circuit' in event FR.3"
    ::= { frEventObjects3 1 }

fr3-protocol OBJECT-TYPE
    SYNTAX DisplayString
    MAX-ACCESS accessible-for-notify
    STATUS current
    DESCRIPTION
        "Parameter 'protocol' in event FR.3"
    ::= { frEventObjects3 2 }

fr3-ifcname OBJECT-TYPE
    SYNTAX DisplayString
    MAX-ACCESS accessible-for-notify
    STATUS current
    DESCRIPTION
        "Parameter 'ifcname' in event FR.3"
    ::= { frEventObjects3 3 }

frEventObjects4 OBJECT-IDENTITY
    STATUS current
    DESCRIPTION
        "Event FR.4
        The circuit is now experiencing congestion in the outbound direction."
    ::= { frEventsGroup 4 }

fr4-circuit OBJECT-TYPE
    SYNTAX Integer32
    MAX-ACCESS accessible-for-notify
    STATUS current
    DESCRIPTION
        "Parameter 'circuit' in event FR.4"
    ::= { frEventObjects4 1 }

fr4-ifcname OBJECT-TYPE
    SYNTAX DisplayString
    MAX-ACCESS accessible-for-notify
    STATUS current
    DESCRIPTION
        "Parameter 'ifcname' in event FR.4"
    ::= { frEventObjects4 2 }

frEventObjects5 OBJECT-IDENTITY
    STATUS current
    DESCRIPTION
        "Event FR.5
        The circuit is now not experiencing congestion in the outbound
        direction."
    ::= { frEventsGroup 5 }

fr5-circuit OBJECT-TYPE
    SYNTAX Integer32
    MAX-ACCESS accessible-for-notify
    STATUS current
    DESCRIPTION
        "Parameter 'circuit' in event FR.5"
    ::= { frEventObjects5 1 }

fr5-ifcname OBJECT-TYPE
    SYNTAX DisplayString
    MAX-ACCESS accessible-for-notify
    STATUS current
    DESCRIPTION
        "Parameter 'ifcname' in event FR.5"
    ::= { frEventObjects5 2 }

frEventObjects6 OBJECT-IDENTITY
    STATUS current
    DESCRIPTION
        "Event FR.6
        The circuit enters the active state."
    ::= { frEventsGroup 6 }

fr6-circuit OBJECT-TYPE
    SYNTAX Integer32
    MAX-ACCESS accessible-for-notify
    STATUS current
    DESCRIPTION
        "Parameter 'circuit' in event FR.6"
    ::= { frEventObjects6 1 }

fr6-ifcname OBJECT-TYPE
    SYNTAX DisplayString
    MAX-ACCESS accessible-for-notify
    STATUS current
    DESCRIPTION
        "Parameter 'ifcname' in event FR.6"
    ::= { frEventObjects6 2 }

frEventObjects7 OBJECT-IDENTITY
    STATUS current
    DESCRIPTION
        "Event FR.7
        The LMI signalled present and active a circuit which had not been
        statically configured."
    ::= { frEventsGroup 7 }

fr7-circuit OBJECT-TYPE
    SYNTAX Integer32
    MAX-ACCESS accessible-for-notify
    STATUS current
    DESCRIPTION
        "Parameter 'circuit' in event FR.7"
    ::= { frEventObjects7 1 }

fr7-ifcname OBJECT-TYPE
    SYNTAX DisplayString
    MAX-ACCESS accessible-for-notify
    STATUS current
    DESCRIPTION
        "Parameter 'ifcname' in event FR.7"
    ::= { frEventObjects7 2 }

frEventObjects8 OBJECT-IDENTITY
    STATUS current
    DESCRIPTION
        "Event FR.8
        The circuit enters the inactive state."
    ::= { frEventsGroup 8 }

fr8-circuit OBJECT-TYPE
    SYNTAX Integer32
    MAX-ACCESS accessible-for-notify
    STATUS current
    DESCRIPTION
        "Parameter 'circuit' in event FR.8"
    ::= { frEventObjects8 1 }

fr8-ifcname OBJECT-TYPE
    SYNTAX DisplayString
    MAX-ACCESS accessible-for-notify
    STATUS current
    DESCRIPTION
        "Parameter 'ifcname' in event FR.8"
    ::= { frEventObjects8 2 }

frEventObjects9 OBJECT-IDENTITY
    STATUS current
    DESCRIPTION
        "Event FR.9
        The circuit is no longer available on the network."
    ::= { frEventsGroup 9 }

fr9-circuit OBJECT-TYPE
    SYNTAX Integer32
    MAX-ACCESS accessible-for-notify
    STATUS current
    DESCRIPTION
        "Parameter 'circuit' in event FR.9"
    ::= { frEventObjects9 1 }

fr9-ifcname OBJECT-TYPE
    SYNTAX DisplayString
    MAX-ACCESS accessible-for-notify
    STATUS current
    DESCRIPTION
        "Parameter 'ifcname' in event FR.9"
    ::= { frEventObjects9 2 }

frEventObjects10 OBJECT-IDENTITY
    STATUS current
    DESCRIPTION
        "Event FR.10
        The circuit is now available on the network."
    ::= { frEventsGroup 10 }

fr10-circuit OBJECT-TYPE
    SYNTAX Integer32
    MAX-ACCESS accessible-for-notify
    STATUS current
    DESCRIPTION
        "Parameter 'circuit' in event FR.10"
    ::= { frEventObjects10 1 }

fr10-ifcname OBJECT-TYPE
    SYNTAX DisplayString
    MAX-ACCESS accessible-for-notify
    STATUS current
    DESCRIPTION
        "Parameter 'ifcname' in event FR.10"
    ::= { frEventObjects10 2 }

frEventObjects11 OBJECT-IDENTITY
    STATUS current
    DESCRIPTION
        "Event FR.11
        A LMI sequence number exchange has been requested."
    ::= { frEventsGroup 11 }

fr11-rcvseq OBJECT-TYPE
    SYNTAX Integer32
    MAX-ACCESS accessible-for-notify
    STATUS current
    DESCRIPTION
        "Parameter 'rcvseq' in event FR.11"
    ::= { frEventObjects11 1 }

fr11-xmtseq OBJECT-TYPE
    SYNTAX Integer32
    MAX-ACCESS accessible-for-notify
    STATUS current
    DESCRIPTION
        "Parameter 'xmtseq' in event FR.11"
    ::= { frEventObjects11 2 }

fr11-ifcname OBJECT-TYPE
    SYNTAX DisplayString
    MAX-ACCESS accessible-for-notify
    STATUS current
    DESCRIPTION
        "Parameter 'ifcname' in event FR.11"
    ::= { frEventObjects11 3 }

frEventObjects12 OBJECT-IDENTITY
    STATUS current
    DESCRIPTION
        "Event FR.12
        A LMI full Status Enquiry has been requested."
    ::= { frEventsGroup 12 }

fr12-ifcname OBJECT-TYPE
    SYNTAX DisplayString
    MAX-ACCESS accessible-for-notify
    STATUS current
    DESCRIPTION
        "Parameter 'ifcname' in event FR.12"
    ::= { frEventObjects12 1 }

frEventObjects13 OBJECT-IDENTITY
    STATUS current
    DESCRIPTION
        "Event FR.13
        A solicited LMI Status Enquiry response has been received."
    ::= { frEventsGroup 13 }

fr13-ifcname OBJECT-TYPE
    SYNTAX DisplayString
    MAX-ACCESS accessible-for-notify
    STATUS current
    DESCRIPTION
        "Parameter 'ifcname' in event FR.13"
    ::= { frEventObjects13 1 }

frEventObjects14 OBJECT-IDENTITY
    STATUS current
    DESCRIPTION
        "Event FR.14
        A LMI full Status Enquiry response has been received."
    ::= { frEventsGroup 14 }

fr14-ifcname OBJECT-TYPE
    SYNTAX DisplayString
    MAX-ACCESS accessible-for-notify
    STATUS current
    DESCRIPTION
        "Parameter 'ifcname' in event FR.14"
    ::= { frEventObjects14 1 }

frEventObjects15 OBJECT-IDENTITY
    STATUS current
    DESCRIPTION
        "Event FR.15
        A modem status change has occurred. The present state is described."
    ::= { frEventsGroup 15 }

fr15-dcd OBJECT-TYPE
    SYNTAX DisplayString
    MAX-ACCESS accessible-for-notify
    STATUS current
    DESCRIPTION
        "Parameter 'dcd' in event FR.15"
    ::= { frEventObjects15 1 }

fr15-cts OBJECT-TYPE
    SYNTAX DisplayString
    MAX-ACCESS accessible-for-notify
    STATUS current
    DESCRIPTION
        "Parameter 'cts' in event FR.15"
    ::= { frEventObjects15 2 }

fr15-ifcname OBJECT-TYPE
    SYNTAX DisplayString
    MAX-ACCESS accessible-for-notify
    STATUS current
    DESCRIPTION
        "Parameter 'ifcname' in event FR.15"
    ::= { frEventObjects15 3 }

frEventObjects16 OBJECT-IDENTITY
    STATUS current
    DESCRIPTION
        "Event FR.16
        A multicast frame had been transmitted on the FR interface."
    ::= { frEventsGroup 16 }

fr16-circuit OBJECT-TYPE
    SYNTAX Integer32
    MAX-ACCESS accessible-for-notify
    STATUS current
    DESCRIPTION
        "Parameter 'circuit' in event FR.16"
    ::= { frEventObjects16 1 }

fr16-protocol OBJECT-TYPE
    SYNTAX DisplayString
    MAX-ACCESS accessible-for-notify
    STATUS current
    DESCRIPTION
        "Parameter 'protocol' in event FR.16"
    ::= { frEventObjects16 2 }

fr16-ifcname OBJECT-TYPE
    SYNTAX DisplayString
    MAX-ACCESS accessible-for-notify
    STATUS current
    DESCRIPTION
        "Parameter 'ifcname' in event FR.16"
    ::= { frEventObjects16 3 }

frEventObjects17 OBJECT-IDENTITY
    STATUS current
    DESCRIPTION
        "Event FR.17
        The circuit is remaining in the outbound congested state toward
        the network."
    ::= { frEventsGroup 17 }

fr17-circuit OBJECT-TYPE
    SYNTAX Integer32
    MAX-ACCESS accessible-for-notify
    STATUS current
    DESCRIPTION
        "Parameter 'circuit' in event FR.17"
    ::= { frEventObjects17 1 }

fr17-ifcname OBJECT-TYPE
    SYNTAX DisplayString
    MAX-ACCESS accessible-for-notify
    STATUS current
    DESCRIPTION
        "Parameter 'ifcname' in event FR.17"
    ::= { frEventObjects17 2 }

frEventObjects18 OBJECT-IDENTITY
    STATUS current
    DESCRIPTION
        "Event FR.18
        A protocol frame had been discarded due to the PVC exceeding the CIR on
        the circuit."
    ::= { frEventsGroup 18 }

fr18-circuit OBJECT-TYPE
    SYNTAX Integer32
    MAX-ACCESS accessible-for-notify
    STATUS current
    DESCRIPTION
        "Parameter 'circuit' in event FR.18"
    ::= { frEventObjects18 1 }

fr18-protocol OBJECT-TYPE
    SYNTAX DisplayString
    MAX-ACCESS accessible-for-notify
    STATUS current
    DESCRIPTION
        "Parameter 'protocol' in event FR.18"
    ::= { frEventObjects18 2 }

fr18-ifcname OBJECT-TYPE
    SYNTAX DisplayString
    MAX-ACCESS accessible-for-notify
    STATUS current
    DESCRIPTION
        "Parameter 'ifcname' in event FR.18"
    ::= { frEventObjects18 3 }

frEventObjects19 OBJECT-IDENTITY
    STATUS current
    DESCRIPTION
        "Event FR.19
        The LMI signalled present and active a circuit which had not been
        statically configured or allowed."
    ::= { frEventsGroup 19 }

fr19-circuit OBJECT-TYPE
    SYNTAX Integer32
    MAX-ACCESS accessible-for-notify
    STATUS current
    DESCRIPTION
        "Parameter 'circuit' in event FR.19"
    ::= { frEventObjects19 1 }

fr19-ifcname OBJECT-TYPE
    SYNTAX DisplayString
    MAX-ACCESS accessible-for-notify
    STATUS current
    DESCRIPTION
        "Parameter 'ifcname' in event FR.19"
    ::= { frEventObjects19 2 }

frEventObjects20 OBJECT-IDENTITY
    STATUS current
    DESCRIPTION
        "Event FR.20
        The LMI signalled present and active a circuit which cannot join
        the interface, maximum circuits have been exceeded."
    ::= { frEventsGroup 20 }

fr20-circuit OBJECT-TYPE
    SYNTAX Integer32
    MAX-ACCESS accessible-for-notify
    STATUS current
    DESCRIPTION
        "Parameter 'circuit' in event FR.20"
    ::= { frEventObjects20 1 }

fr20-ifcname OBJECT-TYPE
    SYNTAX DisplayString
    MAX-ACCESS accessible-for-notify
    STATUS current
    DESCRIPTION
        "Parameter 'ifcname' in event FR.20"
    ::= { frEventObjects20 2 }

frEventObjects21 OBJECT-IDENTITY
    STATUS current
    DESCRIPTION
        "Event FR.21
        The LMI signalled present and active a circuit which cannot join
        the interface, memory is unavailable."
    ::= { frEventsGroup 21 }

fr21-circuit OBJECT-TYPE
    SYNTAX Integer32
    MAX-ACCESS accessible-for-notify
    STATUS current
    DESCRIPTION
        "Parameter 'circuit' in event FR.21"
    ::= { frEventObjects21 1 }

fr21-ifcname OBJECT-TYPE
    SYNTAX DisplayString
    MAX-ACCESS accessible-for-notify
    STATUS current
    DESCRIPTION
        "Parameter 'ifcname' in event FR.21"
    ::= { frEventObjects21 2 }

frEventObjects22 OBJECT-IDENTITY
    STATUS current
    DESCRIPTION
        "Event FR.22
        An unsupported management information element has been encountered."
    ::= { frEventsGroup 22 }

fr22-type OBJECT-TYPE
    SYNTAX Integer32
    MAX-ACCESS accessible-for-notify
    STATUS current
    DESCRIPTION
        "Parameter 'type' in event FR.22"
    ::= { frEventObjects22 1 }

fr22-ifcname OBJECT-TYPE
    SYNTAX DisplayString
    MAX-ACCESS accessible-for-notify
    STATUS current
    DESCRIPTION
        "Parameter 'ifcname' in event FR.22"
    ::= { frEventObjects22 2 }

frEventObjects23 OBJECT-IDENTITY
    STATUS current
    DESCRIPTION
        "Event FR.23
        An unsupported management message has been encountered."
    ::= { frEventsGroup 23 }

fr23-type OBJECT-TYPE
    SYNTAX Integer32
    MAX-ACCESS accessible-for-notify
    STATUS current
    DESCRIPTION
        "Parameter 'type' in event FR.23"
    ::= { frEventObjects23 1 }

fr23-ifcname OBJECT-TYPE
    SYNTAX DisplayString
    MAX-ACCESS accessible-for-notify
    STATUS current
    DESCRIPTION
        "Parameter 'ifcname' in event FR.23"
    ::= { frEventObjects23 2 }

frEventObjects24 OBJECT-IDENTITY
    STATUS current
    DESCRIPTION
        "Event FR.24
        The LMI signalled present and active a multicast circuit."
    ::= { frEventsGroup 24 }

fr24-circuit OBJECT-TYPE
    SYNTAX Integer32
    MAX-ACCESS accessible-for-notify
    STATUS current
    DESCRIPTION
        "Parameter 'circuit' in event FR.24"
    ::= { frEventObjects24 1 }

fr24-group OBJECT-TYPE
    SYNTAX Integer32
    MAX-ACCESS accessible-for-notify
    STATUS current
    DESCRIPTION
        "Parameter 'group' in event FR.24"
    ::= { frEventObjects24 2 }

fr24-ifcname OBJECT-TYPE
    SYNTAX DisplayString
    MAX-ACCESS accessible-for-notify
    STATUS current
    DESCRIPTION
        "Parameter 'ifcname' in event FR.24"
    ::= { frEventObjects24 3 }

frEventObjects25 OBJECT-IDENTITY
    STATUS current
    DESCRIPTION
        "Event FR.25
        The LMI signalled present and active a multicast circuit."
    ::= { frEventsGroup 25 }

fr25-circuit OBJECT-TYPE
    SYNTAX Integer32
    MAX-ACCESS accessible-for-notify
    STATUS current
    DESCRIPTION
        "Parameter 'circuit' in event FR.25"
    ::= { frEventObjects25 1 }

fr25-group OBJECT-TYPE
    SYNTAX Integer32
    MAX-ACCESS accessible-for-notify
    STATUS current
    DESCRIPTION
        "Parameter 'group' in event FR.25"
    ::= { frEventObjects25 2 }

fr25-ifcname OBJECT-TYPE
    SYNTAX DisplayString
    MAX-ACCESS accessible-for-notify
    STATUS current
    DESCRIPTION
        "Parameter 'ifcname' in event FR.25"
    ::= { frEventObjects25 3 }

frEventObjects26 OBJECT-IDENTITY
    STATUS current
    DESCRIPTION
        "Event FR.26
        An unsupported network layer protocol NLPID has been encountered."
    ::= { frEventsGroup 26 }

fr26-type OBJECT-TYPE
    SYNTAX Integer32
    MAX-ACCESS accessible-for-notify
    STATUS current
    DESCRIPTION
        "Parameter 'type' in event FR.26"
    ::= { frEventObjects26 1 }

fr26-circuit OBJECT-TYPE
    SYNTAX Integer32
    MAX-ACCESS accessible-for-notify
    STATUS current
    DESCRIPTION
        "Parameter 'circuit' in event FR.26"
    ::= { frEventObjects26 2 }

fr26-size OBJECT-TYPE
    SYNTAX Integer32
    MAX-ACCESS accessible-for-notify
    STATUS current
    DESCRIPTION
        "Parameter 'size' in event FR.26"
    ::= { frEventObjects26 3 }

fr26-ifcname OBJECT-TYPE
    SYNTAX DisplayString
    MAX-ACCESS accessible-for-notify
    STATUS current
    DESCRIPTION
        "Parameter 'ifcname' in event FR.26"
    ::= { frEventObjects26 4 }

frEventObjects27 OBJECT-IDENTITY
    STATUS current
    DESCRIPTION
        "Event FR.27
        An unsupported Ethernet type has been encountered."
    ::= { frEventsGroup 27 }

fr27-type OBJECT-TYPE
    SYNTAX Integer32
    MAX-ACCESS accessible-for-notify
    STATUS current
    DESCRIPTION
        "Parameter 'type' in event FR.27"
    ::= { frEventObjects27 1 }

fr27-circuit OBJECT-TYPE
    SYNTAX Integer32
    MAX-ACCESS accessible-for-notify
    STATUS current
    DESCRIPTION
        "Parameter 'circuit' in event FR.27"
    ::= { frEventObjects27 2 }

fr27-size OBJECT-TYPE
    SYNTAX Integer32
    MAX-ACCESS accessible-for-notify
    STATUS current
    DESCRIPTION
        "Parameter 'size' in event FR.27"
    ::= { frEventObjects27 3 }

fr27-ifcname OBJECT-TYPE
    SYNTAX DisplayString
    MAX-ACCESS accessible-for-notify
    STATUS current
    DESCRIPTION
        "Parameter 'ifcname' in event FR.27"
    ::= { frEventObjects27 4 }

frEventObjects28 OBJECT-IDENTITY
    STATUS current
    DESCRIPTION
        "Event FR.28
        The LMI signalled present and active a multicast circuit that is not
        supported on the interface."
    ::= { frEventsGroup 28 }

fr28-circuit OBJECT-TYPE
    SYNTAX Integer32
    MAX-ACCESS accessible-for-notify
    STATUS current
    DESCRIPTION
        "Parameter 'circuit' in event FR.28"
    ::= { frEventObjects28 1 }

fr28-group OBJECT-TYPE
    SYNTAX Integer32
    MAX-ACCESS accessible-for-notify
    STATUS current
    DESCRIPTION
        "Parameter 'group' in event FR.28"
    ::= { frEventObjects28 2 }

fr28-ifcname OBJECT-TYPE
    SYNTAX DisplayString
    MAX-ACCESS accessible-for-notify
    STATUS current
    DESCRIPTION
        "Parameter 'ifcname' in event FR.28"
    ::= { frEventObjects28 3 }

frEventObjects29 OBJECT-IDENTITY
    STATUS current
    DESCRIPTION
        "Event FR.29
        Data has been received on a circuit not configured or learned
        dynamically but not yet active on network."
    ::= { frEventsGroup 29 }

fr29-circuit OBJECT-TYPE
    SYNTAX Integer32
    MAX-ACCESS accessible-for-notify
    STATUS current
    DESCRIPTION
        "Parameter 'circuit' in event FR.29"
    ::= { frEventObjects29 1 }

fr29-ifcname OBJECT-TYPE
    SYNTAX DisplayString
    MAX-ACCESS accessible-for-notify
    STATUS current
    DESCRIPTION
        "Parameter 'ifcname' in event FR.29"
    ::= { frEventObjects29 2 }

frEventObjects30 OBJECT-IDENTITY
    STATUS current
    DESCRIPTION
        "Event FR.30
        A LMI sequence number exchange has been received."
    ::= { frEventsGroup 30 }

fr30-rcvseq OBJECT-TYPE
    SYNTAX Integer32
    MAX-ACCESS accessible-for-notify
    STATUS current
    DESCRIPTION
        "Parameter 'rcvseq' in event FR.30"
    ::= { frEventObjects30 1 }

fr30-xmtseq OBJECT-TYPE
    SYNTAX Integer32
    MAX-ACCESS accessible-for-notify
    STATUS current
    DESCRIPTION
        "Parameter 'xmtseq' in event FR.30"
    ::= { frEventObjects30 2 }

fr30-ifcname OBJECT-TYPE
    SYNTAX DisplayString
    MAX-ACCESS accessible-for-notify
    STATUS current
    DESCRIPTION
        "Parameter 'ifcname' in event FR.30"
    ::= { frEventObjects30 3 }

frEventObjects31 OBJECT-IDENTITY
    STATUS current
    DESCRIPTION
        "Event FR.31
        An LMI unsolicited single status update message has been received."
    ::= { frEventsGroup 31 }

fr31-ifcname OBJECT-TYPE
    SYNTAX DisplayString
    MAX-ACCESS accessible-for-notify
    STATUS current
    DESCRIPTION
        "Parameter 'ifcname' in event FR.31"
    ::= { frEventObjects31 1 }

frEventObjects32 OBJECT-IDENTITY
    STATUS current
    DESCRIPTION
        "Event FR.32
        A frame containing less than the 2 octet minimum address length
        had been encountered."
    ::= { frEventsGroup 32 }

fr32-ifcname OBJECT-TYPE
    SYNTAX DisplayString
    MAX-ACCESS accessible-for-notify
    STATUS current
    DESCRIPTION
        "Parameter 'ifcname' in event FR.32"
    ::= { frEventObjects32 1 }

frEventObjects33 OBJECT-IDENTITY
    STATUS current
    DESCRIPTION
        "Event FR.33
        A frame containing greater than the 2 octet maximum address length
        supported had been encountered.
        Currently, only 2 octet addressing is supported."
    ::= { frEventsGroup 33 }

fr33-ifcname OBJECT-TYPE
    SYNTAX DisplayString
    MAX-ACCESS accessible-for-notify
    STATUS current
    DESCRIPTION
        "Parameter 'ifcname' in event FR.33"
    ::= { frEventObjects33 1 }

frEventObjects34 OBJECT-IDENTITY
    STATUS current
    DESCRIPTION
        "Event FR.34
        The LMI status message contained a reserved management channel address."
    ::= { frEventsGroup 34 }

fr34-circuit OBJECT-TYPE
    SYNTAX Integer32
    MAX-ACCESS accessible-for-notify
    STATUS current
    DESCRIPTION
        "Parameter 'circuit' in event FR.34"
    ::= { frEventObjects34 1 }

fr34-ifcname OBJECT-TYPE
    SYNTAX DisplayString
    MAX-ACCESS accessible-for-notify
    STATUS current
    DESCRIPTION
        "Parameter 'ifcname' in event FR.34"
    ::= { frEventObjects34 2 }

frEventObjects35 OBJECT-IDENTITY
    STATUS current
    DESCRIPTION
        "Event FR.35
        An unsupported link layer control frame encountered."
    ::= { frEventsGroup 35 }

fr35-type OBJECT-TYPE
    SYNTAX Integer32
    MAX-ACCESS accessible-for-notify
    STATUS current
    DESCRIPTION
        "Parameter 'type' in event FR.35"
    ::= { frEventObjects35 1 }

fr35-circuit OBJECT-TYPE
    SYNTAX Integer32
    MAX-ACCESS accessible-for-notify
    STATUS current
    DESCRIPTION
        "Parameter 'circuit' in event FR.35"
    ::= { frEventObjects35 2 }

fr35-ifcname OBJECT-TYPE
    SYNTAX DisplayString
    MAX-ACCESS accessible-for-notify
    STATUS current
    DESCRIPTION
        "Parameter 'ifcname' in event FR.35"
    ::= { frEventObjects35 3 }

frEventObjects36 OBJECT-IDENTITY
    STATUS current
    DESCRIPTION
        "Event FR.36
        An unsupported network layer protocol descriptor has been encountered."
    ::= { frEventsGroup 36 }

fr36-type OBJECT-TYPE
    SYNTAX Integer32
    MAX-ACCESS accessible-for-notify
    STATUS current
    DESCRIPTION
        "Parameter 'type' in event FR.36"
    ::= { frEventObjects36 1 }

fr36-ifcname OBJECT-TYPE
    SYNTAX DisplayString
    MAX-ACCESS accessible-for-notify
    STATUS current
    DESCRIPTION
        "Parameter 'ifcname' in event FR.36"
    ::= { frEventObjects36 2 }

frEventObjects37 OBJECT-IDENTITY
    STATUS current
    DESCRIPTION
        "Event FR.37
        An unsupported network layer call reference field has been encountered."
    ::= { frEventsGroup 37 }

fr37-ifcname OBJECT-TYPE
    SYNTAX DisplayString
    MAX-ACCESS accessible-for-notify
    STATUS current
    DESCRIPTION
        "Parameter 'ifcname' in event FR.37"
    ::= { frEventObjects37 1 }

frEventObjects38 OBJECT-IDENTITY
    STATUS current
    DESCRIPTION
        "Event FR.38
        The received ANSI management frame did not include required
        locking shift information element."
    ::= { frEventsGroup 38 }

fr38-ifcname OBJECT-TYPE
    SYNTAX DisplayString
    MAX-ACCESS accessible-for-notify
    STATUS current
    DESCRIPTION
        "Parameter 'ifcname' in event FR.38"
    ::= { frEventObjects38 1 }

frEventObjects39 OBJECT-IDENTITY
    STATUS current
    DESCRIPTION
        "Event FR.39
        The received management frame information element was incorrectly
        formated."
    ::= { frEventsGroup 39 }

fr39-ifcname OBJECT-TYPE
    SYNTAX DisplayString
    MAX-ACCESS accessible-for-notify
    STATUS current
    DESCRIPTION
        "Parameter 'ifcname' in event FR.39"
    ::= { frEventObjects39 1 }

frEventObjects40 OBJECT-IDENTITY
    STATUS current
    DESCRIPTION
        "Event FR.40
        An incorrect LMI receive sequence number has been received."
    ::= { frEventsGroup 40 }

fr40-rcvseq OBJECT-TYPE
    SYNTAX Integer32
    MAX-ACCESS accessible-for-notify
    STATUS current
    DESCRIPTION
        "Parameter 'rcvseq' in event FR.40"
    ::= { frEventObjects40 1 }

fr40-xmtseq OBJECT-TYPE
    SYNTAX Integer32
    MAX-ACCESS accessible-for-notify
    STATUS current
    DESCRIPTION
        "Parameter 'xmtseq' in event FR.40"
    ::= { frEventObjects40 2 }

fr40-ifcname OBJECT-TYPE
    SYNTAX DisplayString
    MAX-ACCESS accessible-for-notify
    STATUS current
    DESCRIPTION
        "Parameter 'ifcname' in event FR.40"
    ::= { frEventObjects40 3 }

frEventObjects41 OBJECT-IDENTITY
    STATUS current
    DESCRIPTION
        "Event FR.41
        The LMI failed to signal the mentioned circuit is last network status
        update message.
        Circuit assumed removed from network."
    ::= { frEventsGroup 41 }

fr41-circuit OBJECT-TYPE
    SYNTAX Integer32
    MAX-ACCESS accessible-for-notify
    STATUS current
    DESCRIPTION
        "Parameter 'circuit' in event FR.41"
    ::= { frEventObjects41 1 }

fr41-ifcname OBJECT-TYPE
    SYNTAX DisplayString
    MAX-ACCESS accessible-for-notify
    STATUS current
    DESCRIPTION
        "Parameter 'ifcname' in event FR.41"
    ::= { frEventObjects41 2 }

frEventObjects42 OBJECT-IDENTITY
    STATUS current
    DESCRIPTION
        "Event FR.42
        The circuit is now experiencing congestion in the inbound direction."
    ::= { frEventsGroup 42 }

fr42-circuit OBJECT-TYPE
    SYNTAX Integer32
    MAX-ACCESS accessible-for-notify
    STATUS current
    DESCRIPTION
        "Parameter 'circuit' in event FR.42"
    ::= { frEventObjects42 1 }

fr42-ifcname OBJECT-TYPE
    SYNTAX DisplayString
    MAX-ACCESS accessible-for-notify
    STATUS current
    DESCRIPTION
        "Parameter 'ifcname' in event FR.42"
    ::= { frEventObjects42 2 }

frEventObjects43 OBJECT-IDENTITY
    STATUS current
    DESCRIPTION
        "Event FR.43
        The address header on received management frame had BECN, FECN,
        DE or CR bits set."
    ::= { frEventsGroup 43 }

fr43-ifcname OBJECT-TYPE
    SYNTAX DisplayString
    MAX-ACCESS accessible-for-notify
    STATUS current
    DESCRIPTION
        "Parameter 'ifcname' in event FR.43"
    ::= { frEventObjects43 1 }

frEventObjects44 OBJECT-IDENTITY
    STATUS current
    DESCRIPTION
        "Event FR.44
        LMI Link Integrity Verification message was received from the network
        without the router polling for it."
    ::= { frEventsGroup 44 }

fr44-ifcname OBJECT-TYPE
    SYNTAX DisplayString
    MAX-ACCESS accessible-for-notify
    STATUS current
    DESCRIPTION
        "Parameter 'ifcname' in event FR.44"
    ::= { frEventObjects44 1 }

frEventObjects45 OBJECT-IDENTITY
    STATUS current
    DESCRIPTION
        "Event FR.45
        LMI Full Status message was received from the network without the
        router polling for it."
    ::= { frEventsGroup 45 }

fr45-ifcname OBJECT-TYPE
    SYNTAX DisplayString
    MAX-ACCESS accessible-for-notify
    STATUS current
    DESCRIPTION
        "Parameter 'ifcname' in event FR.45"
    ::= { frEventObjects45 1 }

frEventObjects46 OBJECT-IDENTITY
    STATUS current
    DESCRIPTION
        "Event FR.46
        A frame was received of a bridge type defined in RFC 1490.
        However, since bridging has not been enabled on this circuit, frame
        is being discarded."
    ::= { frEventsGroup 46 }

fr46-circuit OBJECT-TYPE
    SYNTAX Integer32
    MAX-ACCESS accessible-for-notify
    STATUS current
    DESCRIPTION
        "Parameter 'circuit' in event FR.46"
    ::= { frEventObjects46 1 }

fr46-ifcname OBJECT-TYPE
    SYNTAX DisplayString
    MAX-ACCESS accessible-for-notify
    STATUS current
    DESCRIPTION
        "Parameter 'ifcname' in event FR.46"
    ::= { frEventObjects46 2 }

frEventObjects47 OBJECT-IDENTITY
    STATUS current
    DESCRIPTION
        "Event FR.47
        A bridge frame is being discarded as a bridge port is not in
        forwarding state."
    ::= { frEventsGroup 47 }

fr47-circuit OBJECT-TYPE
    SYNTAX Integer32
    MAX-ACCESS accessible-for-notify
    STATUS current
    DESCRIPTION
        "Parameter 'circuit' in event FR.47"
    ::= { frEventObjects47 1 }

fr47-ifcname OBJECT-TYPE
    SYNTAX DisplayString
    MAX-ACCESS accessible-for-notify
    STATUS current
    DESCRIPTION
        "Parameter 'ifcname' in event FR.47"
    ::= { frEventObjects47 2 }

frEventObjects48 OBJECT-IDENTITY
    STATUS current
    DESCRIPTION
        "Event FR.48
        A bridged frame has been received and is being discarded due to mismatch
        in the frame type versus the bridge port behavior."
    ::= { frEventsGroup 48 }

fr48-source-mac OBJECT-TYPE
    SYNTAX DisplayString
    MAX-ACCESS accessible-for-notify
    STATUS current
    DESCRIPTION
        "Parameter 'source-mac' in event FR.48"
    ::= { frEventObjects48 1 }

fr48-dest-mac OBJECT-TYPE
    SYNTAX DisplayString
    MAX-ACCESS accessible-for-notify
    STATUS current
    DESCRIPTION
        "Parameter 'dest-mac' in event FR.48"
    ::= { frEventObjects48 2 }

fr48-circuit OBJECT-TYPE
    SYNTAX Integer32
    MAX-ACCESS accessible-for-notify
    STATUS current
    DESCRIPTION
        "Parameter 'circuit' in event FR.48"
    ::= { frEventObjects48 3 }

fr48-ifcname OBJECT-TYPE
    SYNTAX DisplayString
    MAX-ACCESS accessible-for-notify
    STATUS current
    DESCRIPTION
        "Parameter 'ifcname' in event FR.48"
    ::= { frEventObjects48 4 }

frEventObjects49 OBJECT-IDENTITY
    STATUS current
    DESCRIPTION
        "Event FR.49
        An unsupported bridge frame type has been encountered."
    ::= { frEventsGroup 49 }

fr49-type OBJECT-TYPE
    SYNTAX Integer32
    MAX-ACCESS accessible-for-notify
    STATUS current
    DESCRIPTION
        "Parameter 'type' in event FR.49"
    ::= { frEventObjects49 1 }

fr49-circuit OBJECT-TYPE
    SYNTAX Integer32
    MAX-ACCESS accessible-for-notify
    STATUS current
    DESCRIPTION
        "Parameter 'circuit' in event FR.49"
    ::= { frEventObjects49 2 }

fr49-ifcname OBJECT-TYPE
    SYNTAX DisplayString
    MAX-ACCESS accessible-for-notify
    STATUS current
    DESCRIPTION
        "Parameter 'ifcname' in event FR.49"
    ::= { frEventObjects49 3 }

frEventObjects50 OBJECT-IDENTITY
    STATUS current
    DESCRIPTION
        "Event FR.50
        An unrecognized outgoing bridge frame type. Bridge has asked the
        Frame Relay interface to send out a frame whose type cannot be
        translated into encapsulation defined in RFC 1490."
    ::= { frEventsGroup 50 }

fr50-type OBJECT-TYPE
    SYNTAX Integer32
    MAX-ACCESS accessible-for-notify
    STATUS current
    DESCRIPTION
        "Parameter 'type' in event FR.50"
    ::= { frEventObjects50 1 }

fr50-circuit OBJECT-TYPE
    SYNTAX Integer32
    MAX-ACCESS accessible-for-notify
    STATUS current
    DESCRIPTION
        "Parameter 'circuit' in event FR.50"
    ::= { frEventObjects50 2 }

fr50-ifcname OBJECT-TYPE
    SYNTAX DisplayString
    MAX-ACCESS accessible-for-notify
    STATUS current
    DESCRIPTION
        "Parameter 'ifcname' in event FR.50"
    ::= { frEventObjects50 3 }

frEventObjects51 OBJECT-IDENTITY
    STATUS current
    DESCRIPTION
        "Event FR.51
        A protocol frame has been discarded because it could not be queued
        for transmission."
    ::= { frEventsGroup 51 }

fr51-circuit OBJECT-TYPE
    SYNTAX Integer32
    MAX-ACCESS accessible-for-notify
    STATUS current
    DESCRIPTION
        "Parameter 'circuit' in event FR.51"
    ::= { frEventObjects51 1 }

fr51-protocol OBJECT-TYPE
    SYNTAX DisplayString
    MAX-ACCESS accessible-for-notify
    STATUS current
    DESCRIPTION
        "Parameter 'protocol' in event FR.51"
    ::= { frEventObjects51 2 }

fr51-ifcname OBJECT-TYPE
    SYNTAX DisplayString
    MAX-ACCESS accessible-for-notify
    STATUS current
    DESCRIPTION
        "Parameter 'ifcname' in event FR.51"
    ::= { frEventObjects51 3 }

frEventObjects52 OBJECT-IDENTITY
    STATUS current
    DESCRIPTION
        "Event FR.52
        An LMI send sequence number of 0 has been received."
    ::= { frEventsGroup 52 }

fr52-sndseq OBJECT-TYPE
    SYNTAX Integer32
    MAX-ACCESS accessible-for-notify
    STATUS current
    DESCRIPTION
        "Parameter 'sndseq' in event FR.52"
    ::= { frEventObjects52 1 }

fr52-ifcname OBJECT-TYPE
    SYNTAX DisplayString
    MAX-ACCESS accessible-for-notify
    STATUS current
    DESCRIPTION
        "Parameter 'ifcname' in event FR.52"
    ::= { frEventObjects52 2 }

frEventObjects53 OBJECT-IDENTITY
    STATUS current
    DESCRIPTION
        "Event FR.53
        A FRF.12 fragment is processed and a event is reported."
    ::= { frEventsGroup 53 }

fr53-message OBJECT-TYPE
    SYNTAX DisplayString
    MAX-ACCESS accessible-for-notify
    STATUS current
    DESCRIPTION
        "Parameter 'message' in event FR.53"
    ::= { frEventObjects53 1 }

fr53-header OBJECT-TYPE
    SYNTAX Integer32
    MAX-ACCESS accessible-for-notify
    STATUS current
    DESCRIPTION
        "Parameter 'header' in event FR.53"
    ::= { frEventObjects53 2 }

fr53-circuit OBJECT-TYPE
    SYNTAX Integer32
    MAX-ACCESS accessible-for-notify
    STATUS current
    DESCRIPTION
        "Parameter 'circuit' in event FR.53"
    ::= { frEventObjects53 3 }

fr53-size OBJECT-TYPE
    SYNTAX Integer32
    MAX-ACCESS accessible-for-notify
    STATUS current
    DESCRIPTION
        "Parameter 'size' in event FR.53"
    ::= { frEventObjects53 4 }

fr53-ifcname OBJECT-TYPE
    SYNTAX DisplayString
    MAX-ACCESS accessible-for-notify
    STATUS current
    DESCRIPTION
        "Parameter 'ifcname' in event FR.53"
    ::= { frEventObjects53 5 }


frNotification1 NOTIFICATION-TYPE
    OBJECTS { 
              fr1-circuit, 
              fr1-protocol,
              fr1-size,
              fr1-ifcname,
              fr1-buffer 
            }
    STATUS current
    DESCRIPTION
        "Notification of Event FR.1

        Message: 'Frame received, PVC = $1 protocol type = $2 size $3 bytes, on interface $4HexadecimalData: $5'

        Parameters list:
              $1: fr1-circuit
              $2: fr1-protocol
              $3: fr1-size
              $4: fr1-ifcname
              $5: fr1-buffer

        A frame had been received on the FR interface."
    ::= { frNotificationsPrefix 1 }

frNotification2 NOTIFICATION-TYPE
    OBJECTS { 
              fr2-circuit, 
              fr2-protocol,
              fr2-size,
              fr2-ifcname,
              fr2-buffer 
            }
    STATUS current
    DESCRIPTION
        "Notification of Event FR.2

        Message: 'Frame transmitted PVC = $1 protocol type = $2 size $3 bytes, on interface $4HexadecimalData: $5'

        Parameters list:
              $1: fr2-circuit
              $2: fr2-protocol
              $3: fr2-size
              $4: fr2-ifcname
              $5: fr2-buffer

        A frame had been transmitted on the FR interface."
    ::= { frNotificationsPrefix 2 }

frNotification3 NOTIFICATION-TYPE
    OBJECTS { 
              fr3-circuit, 
              fr3-protocol,
              fr3-ifcname 
            }
    STATUS current
    DESCRIPTION
        "Notification of Event FR.3

        Message: 'Transmit frame discarded PVC = $1 protocol type = $2, on interface $3'

        Parameters list:
              $1: fr3-circuit
              $2: fr3-protocol
              $3: fr3-ifcname

        A protocol frame had been discarded due to the PVC congested condition."
    ::= { frNotificationsPrefix 3 }

frNotification4 NOTIFICATION-TYPE
    OBJECTS { 
              fr4-circuit, 
              fr4-ifcname 
            }
    STATUS current
    DESCRIPTION
        "Notification of Event FR.4

        Message: 'Circuit outbound congestion PVC = $1, on interface $2'

        Parameters list:
              $1: fr4-circuit
              $2: fr4-ifcname

        The circuit is now experiencing congestion in the outbound direction."
    ::= { frNotificationsPrefix 4 }

frNotification5 NOTIFICATION-TYPE
    OBJECTS { 
              fr5-circuit, 
              fr5-ifcname 
            }
    STATUS current
    DESCRIPTION
        "Notification of Event FR.5

        Message: 'Circuit outbound uncongested PVC = $1, on interface $2'

        Parameters list:
              $1: fr5-circuit
              $2: fr5-ifcname

        The circuit is now not experiencing congestion in the outbound
        direction."
    ::= { frNotificationsPrefix 5 }

frNotification6 NOTIFICATION-TYPE
    OBJECTS { 
              fr6-circuit, 
              fr6-ifcname 
            }
    STATUS current
    DESCRIPTION
        "Notification of Event FR.6

        Message: 'Circuit enters active state PVC = $1, on interface $2'

        Parameters list:
              $1: fr6-circuit
              $2: fr6-ifcname

        The circuit enters the active state."
    ::= { frNotificationsPrefix 6 }

frNotification7 NOTIFICATION-TYPE
    OBJECTS { 
              fr7-circuit, 
              fr7-ifcname 
            }
    STATUS current
    DESCRIPTION
        "Notification of Event FR.7

        Message: 'An orphan circuit not statically configured has joined the network PVC = $1, on interface $2'

        Parameters list:
              $1: fr7-circuit
              $2: fr7-ifcname

        The LMI signalled present and active a circuit which had not been
        statically configured."
    ::= { frNotificationsPrefix 7 }

frNotification8 NOTIFICATION-TYPE
    OBJECTS { 
              fr8-circuit, 
              fr8-ifcname 
            }
    STATUS current
    DESCRIPTION
        "Notification of Event FR.8

        Message: 'Circuit enters inactive state PVC = $1, on interface $2'

        Parameters list:
              $1: fr8-circuit
              $2: fr8-ifcname

        The circuit enters the inactive state."
    ::= { frNotificationsPrefix 8 }

frNotification9 NOTIFICATION-TYPE
    OBJECTS { 
              fr9-circuit, 
              fr9-ifcname 
            }
    STATUS current
    DESCRIPTION
        "Notification of Event FR.9

        Message: 'Circuit is unavailable PVC = $1, on interface $2'

        Parameters list:
              $1: fr9-circuit
              $2: fr9-ifcname

        The circuit is no longer available on the network."
    ::= { frNotificationsPrefix 9 }

frNotification10 NOTIFICATION-TYPE
    OBJECTS { 
              fr10-circuit, 
              fr10-ifcname 
            }
    STATUS current
    DESCRIPTION
        "Notification of Event FR.10

        Message: 'Circuit is available PVC = $1, on interface $2'

        Parameters list:
              $1: fr10-circuit
              $2: fr10-ifcname

        The circuit is now available on the network."
    ::= { frNotificationsPrefix 10 }

frNotification11 NOTIFICATION-TYPE
    OBJECTS { 
              fr11-rcvseq, 
              fr11-xmtseq,
              fr11-ifcname 
            }
    STATUS current
    DESCRIPTION
        "Notification of Event FR.11

        Message: 'LMI sequence number exchange requested, last received sequence = $1, current transmit sequence = $2, on interface $3'

        Parameters list:
              $1: fr11-rcvseq
              $2: fr11-xmtseq
              $3: fr11-ifcname

        A LMI sequence number exchange has been requested."
    ::= { frNotificationsPrefix 11 }

frNotification12 NOTIFICATION-TYPE
    OBJECTS { 
              fr12-ifcname 
            }
    STATUS current
    DESCRIPTION
        "Notification of Event FR.12

        Message: 'LMI Status Enquiry requested on interface $1'

        Parameters list:
              $1: fr12-ifcname

        A LMI full Status Enquiry has been requested."
    ::= { frNotificationsPrefix 12 }

frNotification13 NOTIFICATION-TYPE
    OBJECTS { 
              fr13-ifcname 
            }
    STATUS current
    DESCRIPTION
        "Notification of Event FR.13

        Message: 'LMI solicited Status Enquiry response had been received on interface $1'

        Parameters list:
              $1: fr13-ifcname

        A solicited LMI Status Enquiry response has been received."
    ::= { frNotificationsPrefix 13 }

frNotification14 NOTIFICATION-TYPE
    OBJECTS { 
              fr14-ifcname 
            }
    STATUS current
    DESCRIPTION
        "Notification of Event FR.14

        Message: 'LMI Full Status Enquiry response had been received on interface $1'

        Parameters list:
              $1: fr14-ifcname

        A LMI full Status Enquiry response has been received."
    ::= { frNotificationsPrefix 14 }

frNotification15 NOTIFICATION-TYPE
    OBJECTS { 
              fr15-dcd, 
              fr15-cts,
              fr15-ifcname 
            }
    STATUS current
    DESCRIPTION
        "Notification of Event FR.15

        Message: 'Modem status changed DCD = $1 CTS = $2 on interface $3'

        Parameters list:
              $1: fr15-dcd
              $2: fr15-cts
              $3: fr15-ifcname

        A modem status change has occurred. The present state is described."
    ::= { frNotificationsPrefix 15 }

frNotification16 NOTIFICATION-TYPE
    OBJECTS { 
              fr16-circuit, 
              fr16-protocol,
              fr16-ifcname 
            }
    STATUS current
    DESCRIPTION
        "Notification of Event FR.16

        Message: 'Multicast frame transmitted PVC = $1 protocol type = $2, on interface $3'

        Parameters list:
              $1: fr16-circuit
              $2: fr16-protocol
              $3: fr16-ifcname

        A multicast frame had been transmitted on the FR interface."
    ::= { frNotificationsPrefix 16 }

frNotification17 NOTIFICATION-TYPE
    OBJECTS { 
              fr17-circuit, 
              fr17-ifcname 
            }
    STATUS current
    DESCRIPTION
        "Notification of Event FR.17

        Message: 'Circuit remains congested in the outbound direction PVC = $1, on interface $2'

        Parameters list:
              $1: fr17-circuit
              $2: fr17-ifcname

        The circuit is remaining in the outbound congested state toward
        the network."
    ::= { frNotificationsPrefix 17 }

frNotification18 NOTIFICATION-TYPE
    OBJECTS { 
              fr18-circuit, 
              fr18-protocol,
              fr18-ifcname 
            }
    STATUS current
    DESCRIPTION
        "Notification of Event FR.18

        Message: 'CIR exceeded, transmit frame discarded PVC = $1 protocol type = $2, on interface $3'

        Parameters list:
              $1: fr18-circuit
              $2: fr18-protocol
              $3: fr18-ifcname

        A protocol frame had been discarded due to the PVC exceeding the CIR on
        the circuit."
    ::= { frNotificationsPrefix 18 }

frNotification19 NOTIFICATION-TYPE
    OBJECTS { 
              fr19-circuit, 
              fr19-ifcname 
            }
    STATUS current
    DESCRIPTION
        "Notification of Event FR.19

        Message: 'A disallowed orphan circuit not statically configured has been ignored PVC = $1, on interface $2'

        Parameters list:
              $1: fr19-circuit
              $2: fr19-ifcname

        The LMI signalled present and active a circuit which had not been
        statically configured or allowed."
    ::= { frNotificationsPrefix 19 }

frNotification20 NOTIFICATION-TYPE
    OBJECTS { 
              fr20-circuit, 
              fr20-ifcname 
            }
    STATUS current
    DESCRIPTION
        "Notification of Event FR.20

        Message: 'The total circuits allowed has been exceeded, an orphan circuit has been ignored PVC = $1, on interface $2'

        Parameters list:
              $1: fr20-circuit
              $2: fr20-ifcname

        The LMI signalled present and active a circuit which cannot join
        the interface, maximum circuits have been exceeded."
    ::= { frNotificationsPrefix 20 }

frNotification21 NOTIFICATION-TYPE
    OBJECTS { 
              fr21-circuit, 
              fr21-ifcname 
            }
    STATUS current
    DESCRIPTION
        "Notification of Event FR.21

        Message: 'No available memory for orphan circuit, the circuit has been ignored PVC = $1, on interface $2'

        Parameters list:
              $1: fr21-circuit
              $2: fr21-ifcname

        The LMI signalled present and active a circuit which cannot join
        the interface, memory is unavailable."
    ::= { frNotificationsPrefix 21 }

frNotification22 NOTIFICATION-TYPE
    OBJECTS { 
              fr22-type, 
              fr22-ifcname 
            }
    STATUS current
    DESCRIPTION
        "Notification of Event FR.22

        Message: 'Unsupported LMI information element, type = $1 on interface $2'

        Parameters list:
              $1: fr22-type
              $2: fr22-ifcname

        An unsupported management information element has been encountered."
    ::= { frNotificationsPrefix 22 }

frNotification23 NOTIFICATION-TYPE
    OBJECTS { 
              fr23-type, 
              fr23-ifcname 
            }
    STATUS current
    DESCRIPTION
        "Notification of Event FR.23

        Message: 'Unsupported LMI message type, type encountered = $1, on interface $2'

        Parameters list:
              $1: fr23-type
              $2: fr23-ifcname

        An unsupported management message has been encountered."
    ::= { frNotificationsPrefix 23 }

frNotification24 NOTIFICATION-TYPE
    OBJECTS { 
              fr24-circuit, 
              fr24-group,
              fr24-ifcname 
            }
    STATUS current
    DESCRIPTION
        "Notification of Event FR.24

        Message: 'A multicast circuit has joined the network PVC = $1, in multicast group = $2 on interface $3'

        Parameters list:
              $1: fr24-circuit
              $2: fr24-group
              $3: fr24-ifcname

        The LMI signalled present and active a multicast circuit."
    ::= { frNotificationsPrefix 24 }

frNotification25 NOTIFICATION-TYPE
    OBJECTS { 
              fr25-circuit, 
              fr25-group,
              fr25-ifcname 
            }
    STATUS current
    DESCRIPTION
        "Notification of Event FR.25

        Message: 'An multicast circuit has left the network PVC = $1, from multicast group = $2 on interface $3'

        Parameters list:
              $1: fr25-circuit
              $2: fr25-group
              $3: fr25-ifcname

        The LMI signalled present and active a multicast circuit."
    ::= { frNotificationsPrefix 25 }

frNotification26 NOTIFICATION-TYPE
    OBJECTS { 
              fr26-type, 
              fr26-circuit,
              fr26-size,
              fr26-ifcname 
            }
    STATUS current
    DESCRIPTION
        "Notification of Event FR.26

        Message: 'Unsupported Network Layer Protocol ID, type = $1 from PVC = $2 size $3 bytes on interface $4'

        Parameters list:
              $1: fr26-type
              $2: fr26-circuit
              $3: fr26-size
              $4: fr26-ifcname

        An unsupported network layer protocol NLPID has been encountered."
    ::= { frNotificationsPrefix 26 }

frNotification27 NOTIFICATION-TYPE
    OBJECTS { 
              fr27-type, 
              fr27-circuit,
              fr27-size,
              fr27-ifcname 
            }
    STATUS current
    DESCRIPTION
        "Notification of Event FR.27

        Message: 'Unsupported ethernet type, type = $1 from PVC = $2 size $3 bytes on interface $4'

        Parameters list:
              $1: fr27-type
              $2: fr27-circuit
              $3: fr27-size
              $4: fr27-ifcname

        An unsupported Ethernet type has been encountered."
    ::= { frNotificationsPrefix 27 }

frNotification28 NOTIFICATION-TYPE
    OBJECTS { 
              fr28-circuit, 
              fr28-group,
              fr28-ifcname 
            }
    STATUS current
    DESCRIPTION
        "Notification of Event FR.28

        Message: 'An unsupported multicast circuit has been ignored, PVC = $1, in multicast group = $2 on interface $3'

        Parameters list:
              $1: fr28-circuit
              $2: fr28-group
              $3: fr28-ifcname

        The LMI signalled present and active a multicast circuit that is not
        supported on the interface."
    ::= { frNotificationsPrefix 28 }

frNotification29 NOTIFICATION-TYPE
    OBJECTS { 
              fr29-circuit, 
              fr29-ifcname 
            }
    STATUS current
    DESCRIPTION
        "Notification of Event FR.29

        Message: 'Data received on invalid or nonconfigured circuit, PVC = $1 on interface $2'

        Parameters list:
              $1: fr29-circuit
              $2: fr29-ifcname

        Data has been received on a circuit not configured or learned
        dynamically but not yet active on network."
    ::= { frNotificationsPrefix 29 }

frNotification30 NOTIFICATION-TYPE
    OBJECTS { 
              fr30-rcvseq, 
              fr30-xmtseq,
              fr30-ifcname 
            }
    STATUS current
    DESCRIPTION
        "Notification of Event FR.30

        Message: 'LMI sequence number exchange received, last received sequence = $1 current transmit sequence = $2, on interface $3'

        Parameters list:
              $1: fr30-rcvseq
              $2: fr30-xmtseq
              $3: fr30-ifcname

        A LMI sequence number exchange has been received."
    ::= { frNotificationsPrefix 30 }

frNotification31 NOTIFICATION-TYPE
    OBJECTS { 
              fr31-ifcname 
            }
    STATUS current
    DESCRIPTION
        "Notification of Event FR.31

        Message: 'LMI unsolicited single Status Update had been received on interface $1'

        Parameters list:
              $1: fr31-ifcname

        An LMI unsolicited single status update message has been received."
    ::= { frNotificationsPrefix 31 }

frNotification32 NOTIFICATION-TYPE
    OBJECTS { 
              fr32-ifcname 
            }
    STATUS current
    DESCRIPTION
        "Notification of Event FR.32

        Message: 'Circuit address length less than the 2 octet minimum received on interface $1'

        Parameters list:
              $1: fr32-ifcname

        A frame containing less than the 2 octet minimum address length
        had been encountered."
    ::= { frNotificationsPrefix 32 }

frNotification33 NOTIFICATION-TYPE
    OBJECTS { 
              fr33-ifcname 
            }
    STATUS current
    DESCRIPTION
        "Notification of Event FR.33

        Message: 'Circuit address length greater than the 2 octet maximum received on interface $1'

        Parameters list:
              $1: fr33-ifcname

        A frame containing greater than the 2 octet maximum address length
        supported had been encountered.
        Currently, only 2 octet addressing is supported."
    ::= { frNotificationsPrefix 33 }

frNotification34 NOTIFICATION-TYPE
    OBJECTS { 
              fr34-circuit, 
              fr34-ifcname 
            }
    STATUS current
    DESCRIPTION
        "Notification of Event FR.34

        Message: 'Circuit status update message contained a reserved management channel address, PVC = $1, on interface $2'

        Parameters list:
              $1: fr34-circuit
              $2: fr34-ifcname

        The LMI status message contained a reserved management channel address."
    ::= { frNotificationsPrefix 34 }

frNotification35 NOTIFICATION-TYPE
    OBJECTS { 
              fr35-type, 
              fr35-circuit,
              fr35-ifcname 
            }
    STATUS current
    DESCRIPTION
        "Notification of Event FR.35

        Message: 'Unsupported Link Layer Control frame encountered, type = $1 from PVC = $2 on interface $3'

        Parameters list:
              $1: fr35-type
              $2: fr35-circuit
              $3: fr35-ifcname

        An unsupported link layer control frame encountered."
    ::= { frNotificationsPrefix 35 }

frNotification36 NOTIFICATION-TYPE
    OBJECTS { 
              fr36-type, 
              fr36-ifcname 
            }
    STATUS current
    DESCRIPTION
        "Notification of Event FR.36

        Message: 'Unsupported layer management protocol descriptor encountered, type = $1 on interface $2'

        Parameters list:
              $1: fr36-type
              $2: fr36-ifcname

        An unsupported network layer protocol descriptor has been encountered."
    ::= { frNotificationsPrefix 36 }

frNotification37 NOTIFICATION-TYPE
    OBJECTS { 
              fr37-ifcname 
            }
    STATUS current
    DESCRIPTION
        "Notification of Event FR.37

        Message: 'Unsupported layer management call reference encountered on interface $1'

        Parameters list:
              $1: fr37-ifcname

        An unsupported network layer call reference field has been encountered."
    ::= { frNotificationsPrefix 37 }

frNotification38 NOTIFICATION-TYPE
    OBJECTS { 
              fr38-ifcname 
            }
    STATUS current
    DESCRIPTION
        "Notification of Event FR.38

        Message: 'No lock shift encountered in received ANSI LMI message on interface $1'

        Parameters list:
              $1: fr38-ifcname

        The received ANSI management frame did not include required
        locking shift information element."
    ::= { frNotificationsPrefix 38 }

frNotification39 NOTIFICATION-TYPE
    OBJECTS { 
              fr39-ifcname 
            }
    STATUS current
    DESCRIPTION
        "Notification of Event FR.39

        Message: 'Incorrect formated information element encountered on interface $1'

        Parameters list:
              $1: fr39-ifcname

        The received management frame information element was incorrectly
        formated."
    ::= { frNotificationsPrefix 39 }

frNotification40 NOTIFICATION-TYPE
    OBJECTS { 
              fr40-rcvseq, 
              fr40-xmtseq,
              fr40-ifcname 
            }
    STATUS current
    DESCRIPTION
        "Notification of Event FR.40

        Message: 'LMI receive sequence number in error, receive sequence = $1 expected sequence = $2, on interface $3'

        Parameters list:
              $1: fr40-rcvseq
              $2: fr40-xmtseq
              $3: fr40-ifcname

        An incorrect LMI receive sequence number has been received."
    ::= { frNotificationsPrefix 40 }

frNotification41 NOTIFICATION-TYPE
    OBJECTS { 
              fr41-circuit, 
              fr41-ifcname 
            }
    STATUS current
    DESCRIPTION
        "Notification of Event FR.41

        Message: 'An circuit has been removed from the network PVC = $1, on interface $2'

        Parameters list:
              $1: fr41-circuit
              $2: fr41-ifcname

        The LMI failed to signal the mentioned circuit is last network status
        update message.
        Circuit assumed removed from network."
    ::= { frNotificationsPrefix 41 }

frNotification42 NOTIFICATION-TYPE
    OBJECTS { 
              fr42-circuit, 
              fr42-ifcname 
            }
    STATUS current
    DESCRIPTION
        "Notification of Event FR.42

        Message: 'Circuit inbound congestion PVC = $1, on interface $2'

        Parameters list:
              $1: fr42-circuit
              $2: fr42-ifcname

        The circuit is now experiencing congestion in the inbound direction."
    ::= { frNotificationsPrefix 42 }

frNotification43 NOTIFICATION-TYPE
    OBJECTS { 
              fr43-ifcname 
            }
    STATUS current
    DESCRIPTION
        "Notification of Event FR.43

        Message: 'Incorrect formatted address header for LMI packet encountered on interface $1'

        Parameters list:
              $1: fr43-ifcname

        The address header on received management frame had BECN, FECN,
        DE or CR bits set."
    ::= { frNotificationsPrefix 43 }

frNotification44 NOTIFICATION-TYPE
    OBJECTS { 
              fr44-ifcname 
            }
    STATUS current
    DESCRIPTION
        "Notification of Event FR.44

        Message: 'Unsolicited LMI Link Integrity Verification received on interface $1'

        Parameters list:
              $1: fr44-ifcname

        LMI Link Integrity Verification message was received from the network
        without the router polling for it."
    ::= { frNotificationsPrefix 44 }

frNotification45 NOTIFICATION-TYPE
    OBJECTS { 
              fr45-ifcname 
            }
    STATUS current
    DESCRIPTION
        "Notification of Event FR.45

        Message: 'Unsolicited LMI FULL STATUS response received on interface $1'

        Parameters list:
              $1: fr45-ifcname

        LMI Full Status message was received from the network without the
        router polling for it."
    ::= { frNotificationsPrefix 45 }

frNotification46 NOTIFICATION-TYPE
    OBJECTS { 
              fr46-circuit, 
              fr46-ifcname 
            }
    STATUS current
    DESCRIPTION
        "Notification of Event FR.46

        Message: 'DROP: Bridging not enabled on PVC=$1, on interface $2'

        Parameters list:
              $1: fr46-circuit
              $2: fr46-ifcname

        A frame was received of a bridge type defined in RFC 1490.
        However, since bridging has not been enabled on this circuit, frame
        is being discarded."
    ::= { frNotificationsPrefix 46 }

frNotification47 NOTIFICATION-TYPE
    OBJECTS { 
              fr47-circuit, 
              fr47-ifcname 
            }
    STATUS current
    DESCRIPTION
        "Notification of Event FR.47

        Message: 'DROP: Bridge port not forwarding on PVC=$1, on interface $2'

        Parameters list:
              $1: fr47-circuit
              $2: fr47-ifcname

        A bridge frame is being discarded as a bridge port is not in
        forwarding state."
    ::= { frNotificationsPrefix 47 }

frNotification48 NOTIFICATION-TYPE
    OBJECTS { 
              fr48-source-mac, 
              fr48-dest-mac,
              fr48-circuit,
              fr48-ifcname 
            }
    STATUS current
    DESCRIPTION
        "Notification of Event FR.48

        Message: 'DROP: $1->$2, Frame to bridge port behavior mismatch on PVC=$3, on interface $4'

        Parameters list:
              $1: fr48-source-mac
              $2: fr48-dest-mac
              $3: fr48-circuit
              $4: fr48-ifcname

        A bridged frame has been received and is being discarded due to mismatch
        in the frame type versus the bridge port behavior."
    ::= { frNotificationsPrefix 48 }

frNotification49 NOTIFICATION-TYPE
    OBJECTS { 
              fr49-type, 
              fr49-circuit,
              fr49-ifcname 
            }
    STATUS current
    DESCRIPTION
        "Notification of Event FR.49

        Message: 'Unsupported bridge frame type = $1 from PVC = $2 on interface $3'

        Parameters list:
              $1: fr49-type
              $2: fr49-circuit
              $3: fr49-ifcname

        An unsupported bridge frame type has been encountered."
    ::= { frNotificationsPrefix 49 }

frNotification50 NOTIFICATION-TYPE
    OBJECTS { 
              fr50-type, 
              fr50-circuit,
              fr50-ifcname 
            }
    STATUS current
    DESCRIPTION
        "Notification of Event FR.50

        Message: 'Unrecognized outgoing bridge frame type = $1 on PVC = $2 on interface $3'

        Parameters list:
              $1: fr50-type
              $2: fr50-circuit
              $3: fr50-ifcname

        An unrecognized outgoing bridge frame type. Bridge has asked the
        Frame Relay interface to send out a frame whose type cannot be
        translated into encapsulation defined in RFC 1490."
    ::= { frNotificationsPrefix 50 }

frNotification51 NOTIFICATION-TYPE
    OBJECTS { 
              fr51-circuit, 
              fr51-protocol,
              fr51-ifcname 
            }
    STATUS current
    DESCRIPTION
        "Notification of Event FR.51

        Message: 'Transmit frame discarded PVC = $1 protocol type = $2, on interface $3'

        Parameters list:
              $1: fr51-circuit
              $2: fr51-protocol
              $3: fr51-ifcname

        A protocol frame has been discarded because it could not be queued
        for transmission."
    ::= { frNotificationsPrefix 51 }

frNotification52 NOTIFICATION-TYPE
    OBJECTS { 
              fr52-sndseq, 
              fr52-ifcname 
            }
    STATUS current
    DESCRIPTION
        "Notification of Event FR.52

        Message: 'LMI send sequence number in error, sequence = $1, on interface $2'

        Parameters list:
              $1: fr52-sndseq
              $2: fr52-ifcname

        An LMI send sequence number of 0 has been received."
    ::= { frNotificationsPrefix 52 }

frNotification53 NOTIFICATION-TYPE
    OBJECTS { 
              fr53-message, 
              fr53-header,
              fr53-circuit,
              fr53-size,
              fr53-ifcname 
            }
    STATUS current
    DESCRIPTION
        "Notification of Event FR.53

        Message: 'FRF.12 $1 header $2 on PVC = $3 size $4 bytes, on interface $5'

        Parameters list:
              $1: fr53-message
              $2: fr53-header
              $3: fr53-circuit
              $4: fr53-size
              $5: fr53-ifcname

        A FRF.12 fragment is processed and a event is reported."
    ::= { frNotificationsPrefix 53 }


END
