PEM-STANDARD-TC DEFINITIONS ::= BEGIN

IMPORTS
	diaxMIB
		FROM DXD-SMI

    MODULE-IDENTITY, OBJECT-TYPE, Counter32
        FROM SNMPv2-SMI
 
	TEXTUAL-CONVENTION
		FROM SNMPv2-TC; 
 
pemStandardObjectsTC MODULE-IDENTITY
    LAST-UPDATED
         "200204101235Z"
    ORGANIZATION
		 "Ericsson Diax A/S - Denmark"
    CONTACT-INFO
		 "
		 Ericsson Diax A/S
		 Faelledvej 17
		 DK-7600 Struer
		 Denmark
		 Phone : +45 97 86 90 22

		 Contact : Peder Joergensen
		 E-mail: peder.jorgensen@dxd.ericsson.se
		 "
   DESCRIPTION
		 "
		 The MIB module defines the Alarm textual convention for 
         the standard alarm objects.    
         
         See IANA-ITU-ALARM-TC and ITU-ALARM-MIB
		 "
   REVISION
   		 "200204101600Z"
   DESCRIPTION
		 "
		 REVISION HISTORY:-

		 REV	DATE		NAME		DESCRIPTION
		 A		020410		DXDPJN		File created
		 "
    ::= { diaxMIB 501 }

-- TEXTUAL-CONVENTION

   ItuPerceivedSeverity ::= TEXTUAL-CONVENTION
       STATUS current
       DESCRIPTION
               "ITU perceived severity values as per M.3100
               and X.733"
       SYNTAX         INTEGER 			{
              cleared (1),
              indeterminate (2),
              critical (3),
              major (4),
              minor (5),
              warning (6)
              } 	


   IANAItuProbableCause ::= TEXTUAL-CONVENTION
       STATUS current
       DESCRIPTION
               "ITU probable cause values for the alarms as per M.3100,
               X.733 and X.736."
       SYNTAX         INTEGER
               {
                aIS  (1),
                callSetUpFailure  (2),
                degradedSignal  (3),
                farEndReceiverFailure  (4),
                framingError  (5),
                lossOfFrame (6),
                lossOfPointer  (7),
                lossOfSignal  (8),
                payloadTypeMismatch (9),
                transmissionError (10),
                remoteAlarmInterface (11),
                excessiveBER  (12),
                pathTraceMismatch  (13),
                unavailable  (14),
                signalLabelMismatch (15),
                lossOfMultiFrame (16),
                receiveFailure (17),
                transmitFailure (18),
                modulationFailure (19),
                demodulationFailure (20),
                broadcastChannelFailure (21),
                connectionEstablishmentError (22),
                invalidMessageReceived (23),
                localNodeTransmissionError (24),
                remoteNodeTransmissionError (25),
                routingFailure (26),

    --Values 27-50 are reserved for communications alarm related
    --probable causes
    -- The following are used with equipment alarm.

                backplaneFailure (51),
                dataSetProblem  (52),
                equipmentIdentifierDuplication  (53),
                externalIFDeviceProblem  (54),
                lineCardProblem (55),
                multiplexerProblem  (56),
                nEIdentifierDuplication  (57),
                powerProblem  (58),
                processorProblem  (59),
                protectionPathFailure  (60),
                receiverFailure  (61),
                replaceableUnitMissing  (62),
                replaceableUnitTypeMismatch (63),
                synchronizationSourceMismatch  (64),
                terminalProblem   (65),
                timingProblem   (66),
                transmitterFailure  (67),
                trunkCardProblem  (68),
                replaceableUnitProblem  (69),
                realTimeClockFailure (70),
    --An equipment alarm to be issued if the system detects that the
    --real time clock has failed
                antennaFailure (71),
                batteryChargingFailure (72),
                diskFailure (73),
                frequencyHoppingFailure (74),
                iODeviceError (75),
                lossOfSynchronisation (76),
                lossOfRedundancy (77),
                powerSupplyFailure (78),
                signalQualityEvaluationFailure (79),
                tranceiverFailure (80),
                protectionMechanismFailure (81),
                protectingResourceFailure (82),
    -- Values 83-100 are reserved for equipment alarm related probable
    -- causes
    -- The following are used with environmental alarm.
                airCompressorFailure  (101),
                airConditioningFailure  (102),
                airDryerFailure   (103),
                batteryDischarging  (104),
                batteryFailure   (105),
                commercialPowerFailure  (106),
                coolingFanFailure  (107),
                engineFailure  (108),
                fireDetectorFailure  (109),
                fuseFailure  (110),
                generatorFailure  (111),
                lowBatteryThreshold (112),
                pumpFailure  (113),
                rectifierFailure  (114),
                rectifierHighVoltage  (115),
                rectifierLowFVoltage  (116),
                ventilationsSystemFailure  (117),
                enclosureDoorOpen  (118),
                explosiveGas  (119),
                fire (120),
                flood   (121),
                highHumidity  (122),
                highTemperature  (123),
                highWind  (124),
                iceBuildUp  (125),
                intrusionDetection  (126),
                lowFuel  (127),
                lowHumidity  (128),
                lowCablePressure  (129),
                lowTemperatue  (130),
                lowWater  (131),
                smoke  (132),
                toxicGas  (133),
                coolingSystemFailure (134),
                externalEquipmentFailure (135),
                externalPointFailure (136),
    -- Values 137-150 are reserved for environmental alarm related
    -- probable causes
    -- The following are used with Processing error alarm.
                storageCapacityProblem (151),
                memoryMismatch  (152),
                corruptData  (153),
                outOfCPUCycles   (154),
                sfwrEnvironmentProblem  (155),
                sfwrDownloadFailure  (156),
                lossOfRealTimel (157),
    --A processing error alarm to be issued after the system has
    --reinitialised. This will indicate
    --to the management systems that the view they have of the managed
    --system may no longer
    --be valid. Usage example: The managed
    --system issues this alarm after a reinitialization with severity
    --warning to inform the
    --management system about the event. No clearing notification will
    --be sent.
                applicationSubsystemFailure (159),
                configurationOrCustomisationError (160),
                databaseInconsistency (161),
                fileError (162),
                outOfMemory (163),
                softwareError (164),
                timeoutExpired (165),
                underlayingResourceUnavailable (166),
                versionMismatch (167),
    --Values 168-200 are reserved for processing error alarm related
    -- probable causes.
                bandwidthReduced (201),
                congestion (202),
                excessiveErrorRate (203),
                excessiveResponseTime (204),
                excessiveRetransmissionRate (205),
                reducedLoggingCapability (206),
                systemResourcesOverload (207 ),

   			  other (255),
                adapterError (256),
                callEstablishmentError (257),
                communicationsProtocolError (258),
                communicationsSubsystemFailure (259),
                configurationOrCustomizationError (260),
                cpuCyclesLimitExceeded (261),
                dataSetOrModemError (262),
                dteDceInterfaceError (263),
                equipmentMalfunction (264),
                excessiveVibration (265),
                fireDetected (266),
                floodDetected (267),
                heatingVentCoolingSystemProblem (268),
                humidityUnacceptable (269),
                inputOutputDeviceError (270),
                inputDeviceError (271),
                lanError (272),
                leakDetected (273),
                materialSupplyExhausted (274),
                ouputDeviceError (275),
                performanceDegraded (276),
                pressureUnacceptable (277),
                queueSizeExceeded (278),
                resourceAtOrNearingCapacity (279),
                responseTimeExecessive (280),
                retransmissionRateExcessive (281),
                softwareProgramAbnormallyTerminated (282),
                softwareProgramError (283),
                temperatureUnacceptable (284),
                thresholdCrossed (285),
                toxicLeakDetected (286),
                underlyingResourceUnavailable (287),
                authenticationFailure (288),
                breachOfConfidentiality (289),
                cableTamper (290),
                delayedInformation (291),
                denialOfService (292),
                duplicateInformation (293),
                informationMissing (294),
                informationModificationDetected (295),
                informationOutOfSequence (296),
                keyExpired (297),
                nonRepudiationFailure (298),
                outOfHoursActivity (299),
                outOfService (300),
                proceduralError (301),
                unauthorizedAccessAttempt (302),
                unexpectedInformation (303)
                }

   IANAItuEventType ::= TEXTUAL-CONVENTION
       STATUS current
       DESCRIPTION
               "The ITU event Type values as per M.3100"
       SYNTAX         INTEGER
              {
              other (1),
              communicationsAlarm (2),
              qualityOfServiceAlarm (3),
              processingErrorAlarm (4),
              equipmentAlarm (5),
              environmentalAlarm (6),
              integrityViolation (7),
              operationalViolation (8),
              physicalViolation (9),
              securityServiceOrMechanismViolation (10),
              timeDomainViolation (11)
              } 	



END
