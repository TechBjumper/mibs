-- This file is corresponding to Release 6.1.2.100 from 2001/09/26 00:00:00
-- (C)opyright 1991-1999 BinTec Communications AG, All Rights Reserved
--  $RCSfile: mibipsrv,v $ 
-- $Revision: 1.5 $ 

BIANCA-BRICK-IP-SERVICE-MIB DEFINITIONS ::= BEGIN
        IMPORTS
            IpAddress, Counter, TimeTicks
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    biboip	OBJECT IDENTIFIER ::= { bibo 5 }
    biboipsrv	OBJECT IDENTIFIER
	::= { biboip 14 }

    localTcpAllowTable OBJECT-TYPE
	SYNTAX SEQUENCE OF LocalTcpAllowEntry
	ACCESS not-accessible
	STATUS mandatory
	DESCRIPTION
	    "Filter rule table for incoming TCP packets for local services.
	     This table is used to restrict access to TCP services provided
	     by the system.

	     o  active rules have at least one of 'localTcpAllowAddrMode'
		and 'localTcpAllowIfMode' set to 'verify'

	     o  if there are active rules for a certain service,
		incoming connections of this service type (port) must
		match at least one of them.

	     o  incoming connections to a service (port) without
		an active rule are always allowed.

	     o  connections originating from 127.0.0.1 are always
		allowed
	    "
    ::= { biboipsrv 1 }

    localTcpAllowEntry OBJECT-TYPE
	SYNTAX LocalTcpAllowEntry
	ACCESS not-accessible
	STATUS mandatory
	DESCRIPTION
	    ""
--	INDEX { localTcpAllowAddr, Service }
    ::= { localTcpAllowTable 1 }

    LocalTcpAllowEntry ::=
	SEQUENCE {
	    localTcpAllowAddrMode INTEGER,
	    localTcpAllowAddr IpAddress,
	    localTcpAllowMask IpAddress,
	    localTcpAllowIfMode INTEGER,
	    localTcpAllowIfIndex INTEGER,
	    localTcpAllowService INTEGER
	}

    localTcpAllowAddrMode OBJECT-TYPE
	SYNTAX INTEGER {
	    dont-verify(1),
	    verify(2),
	    delete(3)
	}
	ACCESS read-write
	STATUS mandatory
	DESCRIPTION
	    "Specifies wether or not the IP source address of incoming
	    TCP packets should checked"
    ::= { localTcpAllowEntry 1 }

    localTcpAllowAddr OBJECT-TYPE
	SYNTAX IpAddress
	ACCESS read-write
	STATUS mandatory
	DESCRIPTION
	    "source IP address"
    ::= { localTcpAllowEntry 2 }

    localTcpAllowMask OBJECT-TYPE
	SYNTAX IpAddress
	ACCESS read-write
	STATUS mandatory
	DESCRIPTION
	    "source IP address mask"
    ::= { localTcpAllowEntry 3 }

    localTcpAllowIfMode OBJECT-TYPE
	SYNTAX INTEGER {
	    dont-verify(1),
	    verify(2)
	}
	ACCESS read-write
	STATUS mandatory
	DESCRIPTION
	    "Specifies wether or not the source interface of incoming
	    TCP packets should checked"
    ::= { localTcpAllowEntry 4 }

    localTcpAllowIfIndex OBJECT-TYPE
	SYNTAX INTEGER
	ACCESS read-write
	STATUS mandatory
	DESCRIPTION
	    "source interface index"
    ::= { localTcpAllowEntry 5 }

    localTcpAllowService OBJECT-TYPE
	SYNTAX INTEGER {
	    telnet(1),
	    trace(2),
	    snmp(3),
	    capi(4),
	    tapi(5),
	    rfc1086(6),
	    http(7)
	}
	ACCESS read-write
	STATUS mandatory
	DESCRIPTION
	    "TCP service"
    ::= { localTcpAllowEntry 6 }




    localUdpAllowTable OBJECT-TYPE
	SYNTAX SEQUENCE OF LocalUdpAllowEntry
	ACCESS not-accessible
	STATUS mandatory
	DESCRIPTION
	    "Filter rule table for incoming UDP packets for local services.
	     This table is used to restrict access to UDP services provided
	     by the system.

	     o  active rules have at least one of 'localUdpAllowAddrMode'
		and 'localUdpAllowIfMode' set to 'verify'

	     o  if there are active rules for a certain service,
		incoming packets of this service type must
		match at least one of them.

	     o  incoming packets to a service (port) without
		an active rule are always allowed.

	     o  packets originating from 127.0.0.1 are always
		allowed
	    "
    ::= { biboipsrv 2 }

    localUdpAllowEntry OBJECT-TYPE
	SYNTAX LocalUdpAllowEntry
	ACCESS not-accessible
	STATUS mandatory
	DESCRIPTION
	    ""
--	INDEX { localUdpAllowAddr, Service }
    ::= { localUdpAllowTable 1 }

    LocalUdpAllowEntry ::=
	SEQUENCE {
	    localUdpAllowAddrMode INTEGER,
	    localUdpAllowAddr IpAddress,
	    localUdpAllowMask IpAddress,
	    localUdpAllowIfMode INTEGER,
	    localUdpAllowIfIndex INTEGER,
	    localUdpAllowService INTEGER
	}

    localUdpAllowAddrMode OBJECT-TYPE
	SYNTAX INTEGER {
	    dont-verify(1),
	    verify(2),
	    delete(3)
	}
	ACCESS read-write
	STATUS mandatory
	DESCRIPTION
	    "Specifies wether or not the IP source address of incoming
	    UDP packets should checked"
    ::= { localUdpAllowEntry 1 }

    localUdpAllowAddr OBJECT-TYPE
	SYNTAX IpAddress
	ACCESS read-write
	STATUS mandatory
	DESCRIPTION
	    "source IP address"
    ::= { localUdpAllowEntry 2 }

    localUdpAllowMask OBJECT-TYPE
	SYNTAX IpAddress
	ACCESS read-write
	STATUS mandatory
	DESCRIPTION
	    "source IP address mask"
    ::= { localUdpAllowEntry 3 }

    localUdpAllowIfMode OBJECT-TYPE
	SYNTAX INTEGER {
	    dont-verify(1),
	    verify(2)
	}
	ACCESS read-write
	STATUS mandatory
	DESCRIPTION
	    "Specifies wether or not the source interface of incoming
	    UDP packets should checked"
    ::= { localUdpAllowEntry 4 }

    localUdpAllowIfIndex OBJECT-TYPE
	SYNTAX INTEGER
	ACCESS read-write
	STATUS mandatory
	DESCRIPTION
	    "source interface index"
    ::= { localUdpAllowEntry 5 }

    localUdpAllowService OBJECT-TYPE
	SYNTAX INTEGER {
	    snmp(1),
	    rip(2),
	    bootps(3),
	    dns(4),
	    nbns(5),
	    statmon(6)
	}
	ACCESS read-write
	STATUS mandatory
	DESCRIPTION
	    "service"
    ::= { localUdpAllowEntry 6 }

END
