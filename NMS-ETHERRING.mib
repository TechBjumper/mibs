-- *****************************************************************
-- NMS-ETHERRING.my: NMS ETHERRING MIB
--
-- September 2008
-- Edit by LIUQIANG
-- Copyright (c) 2008 by NMS, Inc.
-- All rights reserved.
-- *****************************************************************

NMS-ETHERRING DEFINITIONS ::= BEGIN




IMPORTS
    MODULE-IDENTITY, OBJECT-TYPE, NOTIFICATION-TYPE,
    Integer32, Unsigned32                       FROM SNMPv2-SMI
    MODULE-COMPLIANCE, OBJECT-GROUP,
    NOTIFICATION-GROUP                          FROM SNMPv2-CONF
    nmslocal                              		FROM NMS-SMI
    IpAddress, TimeTicks                                   FROM RFC1155-SMI
    PhysAddress				                FROM RFC1213-MIB;

--definition of the etherring table content

               nmsetherring         OBJECT IDENTIFIER ::= { nmslocal 224 }
               
               TypeOfType ::= INTEGER
                	{ master(0),
                           transit(1)
                         }
                         
               TypeOfStatus ::= INTEGER
                         {
                           up(0),
                           down(1)
                          }

               
               
               
               nmsEtherRingTable OBJECT-TYPE
                   SYNTAX  SEQUENCE OF NMSEtherRingEntry
                   ACCESS  not-accessible
                   STATUS  mandatory
                   DESCRIPTION
                            " ."
                   ::= { nmsetherring 1 }

               nmsEtherRingEntry OBJECT-TYPE
                   SYNTAX  NMSEtherRingEntry
                   ACCESS  not-accessible
                   STATUS  mandatory
                   DESCRIPTION
                            "."
                   INDEX { index }
               ::= { nmsEtherRingTable 1 }

               NMSEtherRingEntry ::=
                   SEQUENCE {
                       index
                           INTEGER (0..32),
                       type
                           TypeOfType,
                       status
                           TypeOfStatus,
                       time
                           TimeTicks
                  }
              
		
               index OBJECT-TYPE
                   SYNTAX  INTEGER (0..32)
                   ACCESS  read-only
                   STATUS  mandatory
                   DESCRIPTION
                           "index of the etherring table."
                   ::= { nmsEtherRingEntry 1 }
		

              type OBJECT-TYPE
                   SYNTAX  TypeOfType
              	   ACCESS  read-only
              	   STATUS  mandatory
              	   DESCRIPTION
                   	   "type of ."
              	   ::= { nmsEtherRingEntry 2 }
              	   
              	   
              status OBJECT-TYPE
                   SYNTAX  TypeOfStatus
              	   ACCESS  read-only
              	   STATUS  mandatory
              	   DESCRIPTION
                   	   "type of 2 ."
              	   ::= { nmsEtherRingEntry 3 }



              time OBJECT-TYPE
                   SYNTAX  TimeTicks
              	   ACCESS  read-only
              	   STATUS  mandatory
              	   DESCRIPTION
                   	   "Hold time of blocking."
              	   ::= { nmsEtherRingEntry 4 }

                   

-- Notifications
	nmsEtherRingMIBNotifications OBJECT IDENTIFIER
                                ::= { nmsetherring 2 }


	nmsEtherRingNotification NOTIFICATION-TYPE
    		OBJECTS {
                       index,
                       type,
                       status,
                       time
    		}
    		STATUS      current
    		DESCRIPTION
        	"The agent generates this notification when certain defined types of packages have been blocked or unblocked."
    		::= { nmsEtherRingMIBNotifications 1 }

              

END
