-- ============================================================================
-- Copyright (C) 2004 by  HUAWEI TECHNOLOGIES. All rights reserved.
-- 
-- Description:IASV300R001 IPDSLAM 
-- Reference:  RFC2320 RFC2225
-- Version:    V1.00
-- History:
-- yuedongsheng created.   2004-07-05 
-- ============================================================================

HUAWEI-DSLAM-IPOA-MIB DEFINITIONS ::= BEGIN

IMPORTS
	OBJECT-TYPE, MODULE-IDENTITY	, IpAddress
		FROM SNMPv2-SMI	       		
	TruthValue 
 		FROM SNMPv2-TC
	huaweiUtility
		FROM HUAWEI-MIB;       
				
hwIpDslamPvcIpoa MODULE-IDENTITY
	LAST-UPDATED "200407210900Z"
	ORGANIZATION "Fix-Net Dept, Huawei Technologies Co.,Ltd."
	CONTACT-INFO 
		"Floor 5 ,Block 4, R&D Building,
		Huawei Longgang Production Base,
		Shenzhen,   P.R.C.
		http://www.huawei.com
		Zip:518057
		"
	DESCRIPTION 
		"huawei IPDSLAM IPOA mib "
    ::= { huaweiUtility 46}
    
		

	-- ++++++++++++++++++++++++++++++++++++++++++++++++++++++++++++++++++++++++
	-- 
	-- ++++++++++++++++++++++++++++++++++++++++++++++++++++++++++++++++++++++++

	hwIpDslamPvcIpoaEnable OBJECT-TYPE
		SYNTAX      TruthValue
		MAX-ACCESS   read-write
		STATUS       current
		DESCRIPTION
			     "
			     IPOA Setting enable,
			     "
		     DEFVAL { false}
		::= { hwIpDslamPvcIpoa 1 }
		

	-- ++++++++++++++++++++++++++++++++++++++++++++++++++++++++++++++++++++++++
	-- 
	-- ++++++++++++++++++++++++++++++++++++++++++++++++++++++++++++++++++++++++

	hwIpDslamPvcIpoaDefaultGatewayIp OBJECT-TYPE
		SYNTAX       IpAddress 
		MAX-ACCESS   read-write
		STATUS       current
		DESCRIPTION
			     " 
			     default gateway IP Address 
			     "
			     
		::= { hwIpDslamPvcIpoa 2 }
		
	-- ++++++++++++++++++++++++++++++++++++++++++++++++++++++++++++++++++++++++
	-- 
	-- ++++++++++++++++++++++++++++++++++++++++++++++++++++++++++++++++++++++++


	hwIpDslamPvcIpoaAgeTimeout OBJECT-TYPE
		SYNTAX       INTEGER(180..1200) 
		UNITS 	     "minute"
		MAX-ACCESS   read-write
		STATUS       current
		DESCRIPTION
			     " 
			     ipoa age time out setting 
			     "
		     DEFVAL { 1200 }
		::= { hwIpDslamPvcIpoa 3 }	
		
	-- ++++++++++++++++++++++++++++++++++++++++++++++++++++++++++++++++++++++++
	-- 
	-- ++++++++++++++++++++++++++++++++++++++++++++++++++++++++++++++++++++++++


	hwIpDslamPvcIpoaTagMode OBJECT-TYPE
		SYNTAX INTEGER
		  {
		    single(1),
		    double(2),
		    unconcern(3)
		  }
		MAX-ACCESS   read-write
		STATUS       current
		DESCRIPTION
			     "
			     Indicates the VLAN tag-mode of IPoA.
			     Options:
			     1. single(1)  -Set IPoA single tag-mode
			     2. double(2)  -Set IPoA double tag-mode   
			     3. unconcern(3) -Set IPoA unconcern tag-mode  
			     Default: unconcern(3)
			     "
		::= { hwIpDslamPvcIpoa 6 }
		
END
