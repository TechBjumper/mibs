-- file automatically created


TELDAT-TRAP-ICMP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


icmpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ICMP event subsystem."
    REVISION "201401200930Z"
    DESCRIPTION "Initial implementation"
        ::= { telEventTraps 11 }


icmpEventsGroup	OBJECT IDENTIFIER	::= { icmpTrapsMIB 1 }

icmpNotifications	OBJECT IDENTIFIER	::= { icmpTrapsMIB 2 }
icmpNotificationsPrefix	OBJECT IDENTIFIER	::= { icmpNotifications 0 }

icmpEventObjects1 OBJECT-IDENTITY
    STATUS current
    DESCRIPTION
        "Event ICMP.1
        A bad ICMP checksum was detected in an incoming ICMP message. The
        received checksum is displayed, together with the value that the checkum
        should have had. The received packet is discarded."
    ::= { icmpEventsGroup 1 }

icmp1-received-checksum OBJECT-TYPE
    SYNTAX Integer32
    MAX-ACCESS accessible-for-notify
    STATUS current
    DESCRIPTION
        "Parameter 'received-checksum' in event ICMP.1"
    ::= { icmpEventObjects1 1 }

icmp1-good-checksum OBJECT-TYPE
    SYNTAX Integer32
    MAX-ACCESS accessible-for-notify
    STATUS current
    DESCRIPTION
        "Parameter 'good-checksum' in event ICMP.1"
    ::= { icmpEventObjects1 2 }

icmp1-source-IP-address OBJECT-TYPE
    SYNTAX IpAddress
    MAX-ACCESS accessible-for-notify
    STATUS current
    DESCRIPTION
        "Parameter 'source-IP-address' in event ICMP.1"
    ::= { icmpEventObjects1 3 }

icmp1-destination-IP-address OBJECT-TYPE
    SYNTAX IpAddress
    MAX-ACCESS accessible-for-notify
    STATUS current
    DESCRIPTION
        "Parameter 'destination-IP-address' in event ICMP.1"
    ::= { icmpEventObjects1 4 }

icmpEventObjects2 OBJECT-IDENTITY
    STATUS current
    DESCRIPTION
        "Event ICMP.2
        An ICMP Echo Request was received from the source host by the router.
        Note that an ICMP Echo Request is only recognized when it comes in
        over the interface with the address the packet is addressed to."
    ::= { icmpEventsGroup 2 }

icmp2-source-IP-address OBJECT-TYPE
    SYNTAX IpAddress
    MAX-ACCESS accessible-for-notify
    STATUS current
    DESCRIPTION
        "Parameter 'source-IP-address' in event ICMP.2"
    ::= { icmpEventObjects2 1 }

icmp2-destination-IP-address OBJECT-TYPE
    SYNTAX IpAddress
    MAX-ACCESS accessible-for-notify
    STATUS current
    DESCRIPTION
        "Parameter 'destination-IP-address' in event ICMP.2"
    ::= { icmpEventObjects2 2 }

icmpEventObjects3 OBJECT-IDENTITY
    STATUS current
    DESCRIPTION
        "Event ICMP.3
        An ICMP Echo Reply was received from the source host by the router.
        This is a slightly suspicious event, since the router does not
        normally send ICMP Echo Requests."
    ::= { icmpEventsGroup 3 }

icmp3-source-IP-address OBJECT-TYPE
    SYNTAX IpAddress
    MAX-ACCESS accessible-for-notify
    STATUS current
    DESCRIPTION
        "Parameter 'source-IP-address' in event ICMP.3"
    ::= { icmpEventObjects3 1 }

icmp3-destination-IP-address OBJECT-TYPE
    SYNTAX IpAddress
    MAX-ACCESS accessible-for-notify
    STATUS current
    DESCRIPTION
        "Parameter 'destination-IP-address' in event ICMP.3"
    ::= { icmpEventObjects3 2 }

icmpEventObjects4 OBJECT-IDENTITY
    STATUS current
    DESCRIPTION
        "Event ICMP.4
        An ICMP message came in with a type that the router software does
        not handle."
    ::= { icmpEventsGroup 4 }

icmp4-ICMP-type OBJECT-TYPE
    SYNTAX Integer32
    MAX-ACCESS accessible-for-notify
    STATUS current
    DESCRIPTION
        "Parameter 'ICMP-type' in event ICMP.4"
    ::= { icmpEventObjects4 1 }

icmp4-ICMP-code OBJECT-TYPE
    SYNTAX Integer32
    MAX-ACCESS accessible-for-notify
    STATUS current
    DESCRIPTION
        "Parameter 'ICMP-code' in event ICMP.4"
    ::= { icmpEventObjects4 2 }

icmp4-source-IP-address OBJECT-TYPE
    SYNTAX IpAddress
    MAX-ACCESS accessible-for-notify
    STATUS current
    DESCRIPTION
        "Parameter 'source-IP-address' in event ICMP.4"
    ::= { icmpEventObjects4 3 }

icmp4-destination-IP-address OBJECT-TYPE
    SYNTAX IpAddress
    MAX-ACCESS accessible-for-notify
    STATUS current
    DESCRIPTION
        "Parameter 'destination-IP-address' in event ICMP.4"
    ::= { icmpEventObjects4 4 }

icmpEventObjects5 OBJECT-IDENTITY
    STATUS current
    DESCRIPTION
        "Event ICMP.5
        A broadcast ICMP message came in with a type that the router software
        does not handle."
    ::= { icmpEventsGroup 5 }

icmp5-ICMP-type OBJECT-TYPE
    SYNTAX Integer32
    MAX-ACCESS accessible-for-notify
    STATUS current
    DESCRIPTION
        "Parameter 'ICMP-type' in event ICMP.5"
    ::= { icmpEventObjects5 1 }

icmp5-ICMP-code OBJECT-TYPE
    SYNTAX Integer32
    MAX-ACCESS accessible-for-notify
    STATUS current
    DESCRIPTION
        "Parameter 'ICMP-code' in event ICMP.5"
    ::= { icmpEventObjects5 2 }

icmp5-source-IP-address OBJECT-TYPE
    SYNTAX IpAddress
    MAX-ACCESS accessible-for-notify
    STATUS current
    DESCRIPTION
        "Parameter 'source-IP-address' in event ICMP.5"
    ::= { icmpEventObjects5 3 }

icmp5-destination-IP-address OBJECT-TYPE
    SYNTAX IpAddress
    MAX-ACCESS accessible-for-notify
    STATUS current
    DESCRIPTION
        "Parameter 'destination-IP-address' in event ICMP.5"
    ::= { icmpEventObjects5 4 }

icmpEventObjects6 OBJECT-IDENTITY
    STATUS current
    DESCRIPTION
        "Event ICMP.6
        An ICMP message came in with a type that is not legal."
    ::= { icmpEventsGroup 6 }

icmp6-ICMP-type OBJECT-TYPE
    SYNTAX Integer32
    MAX-ACCESS accessible-for-notify
    STATUS current
    DESCRIPTION
        "Parameter 'ICMP-type' in event ICMP.6"
    ::= { icmpEventObjects6 1 }

icmp6-ICMP-code OBJECT-TYPE
    SYNTAX Integer32
    MAX-ACCESS accessible-for-notify
    STATUS current
    DESCRIPTION
        "Parameter 'ICMP-code' in event ICMP.6"
    ::= { icmpEventObjects6 2 }

icmp6-source-IP-address OBJECT-TYPE
    SYNTAX IpAddress
    MAX-ACCESS accessible-for-notify
    STATUS current
    DESCRIPTION
        "Parameter 'source-IP-address' in event ICMP.6"
    ::= { icmpEventObjects6 3 }

icmp6-destination-IP-address OBJECT-TYPE
    SYNTAX IpAddress
    MAX-ACCESS accessible-for-notify
    STATUS current
    DESCRIPTION
        "Parameter 'destination-IP-address' in event ICMP.6"
    ::= { icmpEventObjects6 4 }

icmpEventObjects7 OBJECT-IDENTITY
    STATUS current
    DESCRIPTION
        "Event ICMP.7
        An ICMP Address Mask Request was received from the source host by
        the router."
    ::= { icmpEventsGroup 7 }

icmp7-source-IP-address OBJECT-TYPE
    SYNTAX IpAddress
    MAX-ACCESS accessible-for-notify
    STATUS current
    DESCRIPTION
        "Parameter 'source-IP-address' in event ICMP.7"
    ::= { icmpEventObjects7 1 }

icmp7-destination-IP-address OBJECT-TYPE
    SYNTAX IpAddress
    MAX-ACCESS accessible-for-notify
    STATUS current
    DESCRIPTION
        "Parameter 'destination-IP-address' in event ICMP.7"
    ::= { icmpEventObjects7 2 }

icmpEventObjects8 OBJECT-IDENTITY
    STATUS current
    DESCRIPTION
        "Event ICMP.8
        An ICMP Address Mask Reply was received from the source host by
        the router."
    ::= { icmpEventsGroup 8 }

icmp8-source-IP-address OBJECT-TYPE
    SYNTAX IpAddress
    MAX-ACCESS accessible-for-notify
    STATUS current
    DESCRIPTION
        "Parameter 'source-IP-address' in event ICMP.8"
    ::= { icmpEventObjects8 1 }

icmp8-destination-IP-address OBJECT-TYPE
    SYNTAX IpAddress
    MAX-ACCESS accessible-for-notify
    STATUS current
    DESCRIPTION
        "Parameter 'destination-IP-address' in event ICMP.8"
    ::= { icmpEventObjects8 2 }

icmpEventObjects10 OBJECT-IDENTITY
    STATUS current
    DESCRIPTION
        "Event ICMP.10
        An incoming address mask request on an interface which contained more
        than one IP source address contained a destination address which could
        not be localized to one of the addresses, so no reply could be
        generated."
    ::= { icmpEventsGroup 10 }

icmp10-source-IP-address OBJECT-TYPE
    SYNTAX IpAddress
    MAX-ACCESS accessible-for-notify
    STATUS current
    DESCRIPTION
        "Parameter 'source-IP-address' in event ICMP.10"
    ::= { icmpEventObjects10 1 }

icmp10-destination-IP-address OBJECT-TYPE
    SYNTAX IpAddress
    MAX-ACCESS accessible-for-notify
    STATUS current
    DESCRIPTION
        "Parameter 'destination-IP-address' in event ICMP.10"
    ::= { icmpEventObjects10 2 }

icmpEventObjects11 OBJECT-IDENTITY
    STATUS current
    DESCRIPTION
        "Event ICMP.11
        An outgoing reply packet was dropped as the result of some
        problem in the router."
    ::= { icmpEventsGroup 11 }

icmp11-code OBJECT-TYPE
    SYNTAX Integer32
    MAX-ACCESS accessible-for-notify
    STATUS current
    DESCRIPTION
        "Parameter 'code' in event ICMP.11"
    ::= { icmpEventObjects11 1 }

icmp11-interface OBJECT-TYPE
    SYNTAX DisplayString
    MAX-ACCESS accessible-for-notify
    STATUS current
    DESCRIPTION
        "Parameter 'interface' in event ICMP.11"
    ::= { icmpEventObjects11 2 }

icmpEventObjects12 OBJECT-IDENTITY
    STATUS current
    DESCRIPTION
        "Event ICMP.12
        The router is sending an ICMP Redirect, advising a source host on
        a directly connected network that there is a better first hop router
        for this traffic."
    ::= { icmpEventsGroup 12 }

icmp12-source-IP-address OBJECT-TYPE
    SYNTAX IpAddress
    MAX-ACCESS accessible-for-notify
    STATUS current
    DESCRIPTION
        "Parameter 'source-IP-address' in event ICMP.12"
    ::= { icmpEventObjects12 1 }

icmp12-destination-IP-address OBJECT-TYPE
    SYNTAX IpAddress
    MAX-ACCESS accessible-for-notify
    STATUS current
    DESCRIPTION
        "Parameter 'destination-IP-address' in event ICMP.12"
    ::= { icmpEventObjects12 2 }

icmp12-new-next-hop-IP-address OBJECT-TYPE
    SYNTAX IpAddress
    MAX-ACCESS accessible-for-notify
    STATUS current
    DESCRIPTION
        "Parameter 'new-next-hop-IP-address' in event ICMP.12"
    ::= { icmpEventObjects12 3 }

icmpEventObjects13 OBJECT-IDENTITY
    STATUS current
    DESCRIPTION
        "Event ICMP.13
        The router is sending an ICMP Parameter Problem message, for an
        unspecified problem at the given offset."
    ::= { icmpEventsGroup 13 }

icmp13-problem-offset OBJECT-TYPE
    SYNTAX Integer32
    MAX-ACCESS accessible-for-notify
    STATUS current
    DESCRIPTION
        "Parameter 'problem-offset' in event ICMP.13"
    ::= { icmpEventObjects13 1 }

icmp13-source-IP-address OBJECT-TYPE
    SYNTAX IpAddress
    MAX-ACCESS accessible-for-notify
    STATUS current
    DESCRIPTION
        "Parameter 'source-IP-address' in event ICMP.13"
    ::= { icmpEventObjects13 2 }

icmp13-destination-IP-address OBJECT-TYPE
    SYNTAX IpAddress
    MAX-ACCESS accessible-for-notify
    STATUS current
    DESCRIPTION
        "Parameter 'destination-IP-address' in event ICMP.13"
    ::= { icmpEventObjects13 3 }

icmpEventObjects14 OBJECT-IDENTITY
    STATUS current
    DESCRIPTION
        "Event ICMP.14
        The router is sending an ICMP packet of the specified type about
        a packet from the source host to the destination."
    ::= { icmpEventsGroup 14 }

icmp14-ICMP-type OBJECT-TYPE
    SYNTAX Integer32
    MAX-ACCESS accessible-for-notify
    STATUS current
    DESCRIPTION
        "Parameter 'ICMP-type' in event ICMP.14"
    ::= { icmpEventObjects14 1 }

icmp14-ICMP-code OBJECT-TYPE
    SYNTAX Integer32
    MAX-ACCESS accessible-for-notify
    STATUS current
    DESCRIPTION
        "Parameter 'ICMP-code' in event ICMP.14"
    ::= { icmpEventObjects14 2 }

icmp14-source-IP-address OBJECT-TYPE
    SYNTAX IpAddress
    MAX-ACCESS accessible-for-notify
    STATUS current
    DESCRIPTION
        "Parameter 'source-IP-address' in event ICMP.14"
    ::= { icmpEventObjects14 3 }

icmp14-destination-IP-address OBJECT-TYPE
    SYNTAX IpAddress
    MAX-ACCESS accessible-for-notify
    STATUS current
    DESCRIPTION
        "Parameter 'destination-IP-address' in event ICMP.14"
    ::= { icmpEventObjects14 4 }

icmpEventObjects15 OBJECT-IDENTITY
    STATUS current
    DESCRIPTION
        "Event ICMP.15
        This message is generated when an ICMP packet's indicated header length
        is below the minimum possible length for an ICMP packet."
    ::= { icmpEventsGroup 15 }

icmp15-header-length OBJECT-TYPE
    SYNTAX Integer32
    MAX-ACCESS accessible-for-notify
    STATUS current
    DESCRIPTION
        "Parameter 'header-length' in event ICMP.15"
    ::= { icmpEventObjects15 1 }

icmp15-source-ip-address OBJECT-TYPE
    SYNTAX IpAddress
    MAX-ACCESS accessible-for-notify
    STATUS current
    DESCRIPTION
        "Parameter 'source-ip-address' in event ICMP.15"
    ::= { icmpEventObjects15 2 }

icmpEventObjects16 OBJECT-IDENTITY
    STATUS current
    DESCRIPTION
        "Event ICMP.16
        A redirect has been received, changing the next hop for the given
        destination. Redirects are only processed when running in host mode."
    ::= { icmpEventsGroup 16 }

icmp16-current-next-hop OBJECT-TYPE
    SYNTAX IpAddress
    MAX-ACCESS accessible-for-notify
    STATUS current
    DESCRIPTION
        "Parameter 'current-next-hop' in event ICMP.16"
    ::= { icmpEventObjects16 1 }

icmp16-IP-destination OBJECT-TYPE
    SYNTAX IpAddress
    MAX-ACCESS accessible-for-notify
    STATUS current
    DESCRIPTION
        "Parameter 'IP-destination' in event ICMP.16"
    ::= { icmpEventObjects16 2 }

icmp16-better-next-hop OBJECT-TYPE
    SYNTAX IpAddress
    MAX-ACCESS accessible-for-notify
    STATUS current
    DESCRIPTION
        "Parameter 'better-next-hop' in event ICMP.16"
    ::= { icmpEventObjects16 3 }

icmpEventObjects17 OBJECT-IDENTITY
    STATUS current
    DESCRIPTION
        "Event ICMP.17
        A redirect was received from a router, but rejected for the
        specified reason."
    ::= { icmpEventsGroup 17 }

icmp17-gateway-address OBJECT-TYPE
    SYNTAX IpAddress
    MAX-ACCESS accessible-for-notify
    STATUS current
    DESCRIPTION
        "Parameter 'gateway-address' in event ICMP.17"
    ::= { icmpEventObjects17 1 }

icmp17-reason OBJECT-TYPE
    SYNTAX DisplayString
    MAX-ACCESS accessible-for-notify
    STATUS current
    DESCRIPTION
        "Parameter 'reason' in event ICMP.17"
    ::= { icmpEventObjects17 2 }

icmpEventObjects18 OBJECT-IDENTITY
    STATUS current
    DESCRIPTION
        "Event ICMP.18
        An ICMP Router Advertisement (Gateway Discovery) message has
        been received from the specified router."
    ::= { icmpEventsGroup 18 }

icmp18-router-address OBJECT-TYPE
    SYNTAX IpAddress
    MAX-ACCESS accessible-for-notify
    STATUS current
    DESCRIPTION
        "Parameter 'router-address' in event ICMP.18"
    ::= { icmpEventObjects18 1 }

icmpEventObjects19 OBJECT-IDENTITY
    STATUS current
    DESCRIPTION
        "Event ICMP.19
        An ICMP Router Advertisement (Gateway Discovery) message has been
        received from the specified router, but was rejected for
        the specified reason."
    ::= { icmpEventsGroup 19 }

icmp19-gateway-address OBJECT-TYPE
    SYNTAX IpAddress
    MAX-ACCESS accessible-for-notify
    STATUS current
    DESCRIPTION
        "Parameter 'gateway-address' in event ICMP.19"
    ::= { icmpEventObjects19 1 }

icmp19-reason OBJECT-TYPE
    SYNTAX DisplayString
    MAX-ACCESS accessible-for-notify
    STATUS current
    DESCRIPTION
        "Parameter 'reason' in event ICMP.19"
    ::= { icmpEventObjects19 2 }

icmpEventObjects20 OBJECT-IDENTITY
    STATUS current
    DESCRIPTION
        "Event ICMP.20
        The router has received an ICMP message of the specified type from
        the source host."
    ::= { icmpEventsGroup 20 }

icmp20-ICMP-type OBJECT-TYPE
    SYNTAX Integer32
    MAX-ACCESS accessible-for-notify
    STATUS current
    DESCRIPTION
        "Parameter 'ICMP-type' in event ICMP.20"
    ::= { icmpEventObjects20 1 }

icmp20-ICMP-code OBJECT-TYPE
    SYNTAX Integer32
    MAX-ACCESS accessible-for-notify
    STATUS current
    DESCRIPTION
        "Parameter 'ICMP-code' in event ICMP.20"
    ::= { icmpEventObjects20 2 }

icmp20-source-IP-address OBJECT-TYPE
    SYNTAX IpAddress
    MAX-ACCESS accessible-for-notify
    STATUS current
    DESCRIPTION
        "Parameter 'source-IP-address' in event ICMP.20"
    ::= { icmpEventObjects20 3 }

icmp20-destination-IP-address OBJECT-TYPE
    SYNTAX IpAddress
    MAX-ACCESS accessible-for-notify
    STATUS current
    DESCRIPTION
        "Parameter 'destination-IP-address' in event ICMP.20"
    ::= { icmpEventObjects20 4 }

icmpEventObjects21 OBJECT-IDENTITY
    STATUS current
    DESCRIPTION
        "Event ICMP.21
        A redirect message has been filtered at specified interface."
    ::= { icmpEventsGroup 21 }

icmp21-interface OBJECT-TYPE
    SYNTAX DisplayString
    MAX-ACCESS accessible-for-notify
    STATUS current
    DESCRIPTION
        "Parameter 'interface' in event ICMP.21"
    ::= { icmpEventObjects21 1 }

icmpEventObjects22 OBJECT-IDENTITY
    STATUS current
    DESCRIPTION
        "Event ICMP.22
        An unreachable message has been filtered at specified interface."
    ::= { icmpEventsGroup 22 }

icmp22-interface OBJECT-TYPE
    SYNTAX DisplayString
    MAX-ACCESS accessible-for-notify
    STATUS current
    DESCRIPTION
        "Parameter 'interface' in event ICMP.22"
    ::= { icmpEventObjects22 1 }


icmpNotification1 NOTIFICATION-TYPE
    OBJECTS { 
              icmp1-received-checksum, 
              icmp1-good-checksum,
              icmp1-source-IP-address,
              icmp1-destination-IP-address 
            }
    STATUS current
    DESCRIPTION
        "Notification of Event ICMP.1

        Message: 'bad ICMP checksum 0x$1 received (expected 0x$2) in packet from $3 to $4'

        Parameters list:
              $1: icmp1-received-checksum
              $2: icmp1-good-checksum
              $3: icmp1-source-IP-address
              $4: icmp1-destination-IP-address

        A bad ICMP checksum was detected in an incoming ICMP message. The
        received checksum is displayed, together with the value that the checkum
        should have had. The received packet is discarded."
    ::= { icmpNotificationsPrefix 1 }

icmpNotification2 NOTIFICATION-TYPE
    OBJECTS { 
              icmp2-source-IP-address, 
              icmp2-destination-IP-address 
            }
    STATUS current
    DESCRIPTION
        "Notification of Event ICMP.2

        Message: 'echo request packet received from $1 to $2'

        Parameters list:
              $1: icmp2-source-IP-address
              $2: icmp2-destination-IP-address

        An ICMP Echo Request was received from the source host by the router.
        Note that an ICMP Echo Request is only recognized when it comes in
        over the interface with the address the packet is addressed to."
    ::= { icmpNotificationsPrefix 2 }

icmpNotification3 NOTIFICATION-TYPE
    OBJECTS { 
              icmp3-source-IP-address, 
              icmp3-destination-IP-address 
            }
    STATUS current
    DESCRIPTION
        "Notification of Event ICMP.3

        Message: 'echo reply packet received from $1 to $2'

        Parameters list:
              $1: icmp3-source-IP-address
              $2: icmp3-destination-IP-address

        An ICMP Echo Reply was received from the source host by the router.
        This is a slightly suspicious event, since the router does not
        normally send ICMP Echo Requests."
    ::= { icmpNotificationsPrefix 3 }

icmpNotification4 NOTIFICATION-TYPE
    OBJECTS { 
              icmp4-ICMP-type, 
              icmp4-ICMP-code,
              icmp4-source-IP-address,
              icmp4-destination-IP-address 
            }
    STATUS current
    DESCRIPTION
        "Notification of Event ICMP.4

        Message: 'unhandled message type $1 $2 from $3 to $4'

        Parameters list:
              $1: icmp4-ICMP-type
              $2: icmp4-ICMP-code
              $3: icmp4-source-IP-address
              $4: icmp4-destination-IP-address

        An ICMP message came in with a type that the router software does
        not handle."
    ::= { icmpNotificationsPrefix 4 }

icmpNotification5 NOTIFICATION-TYPE
    OBJECTS { 
              icmp5-ICMP-type, 
              icmp5-ICMP-code,
              icmp5-source-IP-address,
              icmp5-destination-IP-address 
            }
    STATUS current
    DESCRIPTION
        "Notification of Event ICMP.5

        Message: 'unhandled broadcast message type $1 $2 from $3 to $4'

        Parameters list:
              $1: icmp5-ICMP-type
              $2: icmp5-ICMP-code
              $3: icmp5-source-IP-address
              $4: icmp5-destination-IP-address

        A broadcast ICMP message came in with a type that the router software
        does not handle."
    ::= { icmpNotificationsPrefix 5 }

icmpNotification6 NOTIFICATION-TYPE
    OBJECTS { 
              icmp6-ICMP-type, 
              icmp6-ICMP-code,
              icmp6-source-IP-address,
              icmp6-destination-IP-address 
            }
    STATUS current
    DESCRIPTION
        "Notification of Event ICMP.6

        Message: 'bad message type $1 $2 from $3 to $4'

        Parameters list:
              $1: icmp6-ICMP-type
              $2: icmp6-ICMP-code
              $3: icmp6-source-IP-address
              $4: icmp6-destination-IP-address

        An ICMP message came in with a type that is not legal."
    ::= { icmpNotificationsPrefix 6 }

icmpNotification7 NOTIFICATION-TYPE
    OBJECTS { 
              icmp7-source-IP-address, 
              icmp7-destination-IP-address 
            }
    STATUS current
    DESCRIPTION
        "Notification of Event ICMP.7

        Message: 'address mask request received from $1 to $2'

        Parameters list:
              $1: icmp7-source-IP-address
              $2: icmp7-destination-IP-address

        An ICMP Address Mask Request was received from the source host by
        the router."
    ::= { icmpNotificationsPrefix 7 }

icmpNotification8 NOTIFICATION-TYPE
    OBJECTS { 
              icmp8-source-IP-address, 
              icmp8-destination-IP-address 
            }
    STATUS current
    DESCRIPTION
        "Notification of Event ICMP.8

        Message: 'address mask reply received from $1 to $2'

        Parameters list:
              $1: icmp8-source-IP-address
              $2: icmp8-destination-IP-address

        An ICMP Address Mask Reply was received from the source host by
        the router."
    ::= { icmpNotificationsPrefix 8 }

icmpNotification9 NOTIFICATION-TYPE
    STATUS current
    DESCRIPTION
        "Notification of Event ICMP.9

        Message: 'heap memory or packet buffer not available'

        Internal resources in the router necessary to reply to the incoming
        message were unavailable."
    ::= { icmpNotificationsPrefix 9 }

icmpNotification10 NOTIFICATION-TYPE
    OBJECTS { 
              icmp10-source-IP-address, 
              icmp10-destination-IP-address 
            }
    STATUS current
    DESCRIPTION
        "Notification of Event ICMP.10

        Message: 'ambiguous address mask request received from $1 to $2'

        Parameters list:
              $1: icmp10-source-IP-address
              $2: icmp10-destination-IP-address

        An incoming address mask request on an interface which contained more
        than one IP source address contained a destination address which could
        not be localized to one of the addresses, so no reply could be
        generated."
    ::= { icmpNotificationsPrefix 10 }

icmpNotification11 NOTIFICATION-TYPE
    OBJECTS { 
              icmp11-code, 
              icmp11-interface 
            }
    STATUS current
    DESCRIPTION
        "Notification of Event ICMP.11

        Message: 'error $1 sending packet to interface $2'

        Parameters list:
              $1: icmp11-code
              $2: icmp11-interface

        An outgoing reply packet was dropped as the result of some
        problem in the router."
    ::= { icmpNotificationsPrefix 11 }

icmpNotification12 NOTIFICATION-TYPE
    OBJECTS { 
              icmp12-source-IP-address, 
              icmp12-destination-IP-address,
              icmp12-new-next-hop-IP-address 
            }
    STATUS current
    DESCRIPTION
        "Notification of Event ICMP.12

        Message: 'sending redirect for packet from $1 to $2 to use router $3'

        Parameters list:
              $1: icmp12-source-IP-address
              $2: icmp12-destination-IP-address
              $3: icmp12-new-next-hop-IP-address

        The router is sending an ICMP Redirect, advising a source host on
        a directly connected network that there is a better first hop router
        for this traffic."
    ::= { icmpNotificationsPrefix 12 }

icmpNotification13 NOTIFICATION-TYPE
    OBJECTS { 
              icmp13-problem-offset, 
              icmp13-source-IP-address,
              icmp13-destination-IP-address 
            }
    STATUS current
    DESCRIPTION
        "Notification of Event ICMP.13

        Message: 'sending parameter problem message problem offset $1 for packet from $2 to $3'

        Parameters list:
              $1: icmp13-problem-offset
              $2: icmp13-source-IP-address
              $3: icmp13-destination-IP-address

        The router is sending an ICMP Parameter Problem message, for an
        unspecified problem at the given offset."
    ::= { icmpNotificationsPrefix 13 }

icmpNotification14 NOTIFICATION-TYPE
    OBJECTS { 
              icmp14-ICMP-type, 
              icmp14-ICMP-code,
              icmp14-source-IP-address,
              icmp14-destination-IP-address 
            }
    STATUS current
    DESCRIPTION
        "Notification of Event ICMP.14

        Message: 'sending packet type $1 code $2 for packet from $3 to $4'

        Parameters list:
              $1: icmp14-ICMP-type
              $2: icmp14-ICMP-code
              $3: icmp14-source-IP-address
              $4: icmp14-destination-IP-address

        The router is sending an ICMP packet of the specified type about
        a packet from the source host to the destination."
    ::= { icmpNotificationsPrefix 14 }

icmpNotification15 NOTIFICATION-TYPE
    OBJECTS { 
              icmp15-header-length, 
              icmp15-source-ip-address 
            }
    STATUS current
    DESCRIPTION
        "Notification of Event ICMP.15

        Message: 'short ICMP packet $1 received in packet from $2'

        Parameters list:
              $1: icmp15-header-length
              $2: icmp15-source-ip-address

        This message is generated when an ICMP packet's indicated header length
        is below the minimum possible length for an ICMP packet."
    ::= { icmpNotificationsPrefix 15 }

icmpNotification16 NOTIFICATION-TYPE
    OBJECTS { 
              icmp16-current-next-hop, 
              icmp16-IP-destination,
              icmp16-better-next-hop 
            }
    STATUS current
    DESCRIPTION
        "Notification of Event ICMP.16

        Message: '$1 has redirected traffic for $2 to $3'

        Parameters list:
              $1: icmp16-current-next-hop
              $2: icmp16-IP-destination
              $3: icmp16-better-next-hop

        A redirect has been received, changing the next hop for the given
        destination. Redirects are only processed when running in host mode."
    ::= { icmpNotificationsPrefix 16 }

icmpNotification17 NOTIFICATION-TYPE
    OBJECTS { 
              icmp17-gateway-address, 
              icmp17-reason 
            }
    STATUS current
    DESCRIPTION
        "Notification of Event ICMP.17

        Message: 'Redirect received from $1 was bad for the reason: $2'

        Parameters list:
              $1: icmp17-gateway-address
              $2: icmp17-reason

        A redirect was received from a router, but rejected for the
        specified reason."
    ::= { icmpNotificationsPrefix 17 }

icmpNotification18 NOTIFICATION-TYPE
    OBJECTS { 
              icmp18-router-address 
            }
    STATUS current
    DESCRIPTION
        "Notification of Event ICMP.18

        Message: 'Router advertisement received from $1'

        Parameters list:
              $1: icmp18-router-address

        An ICMP Router Advertisement (Gateway Discovery) message has
        been received from the specified router."
    ::= { icmpNotificationsPrefix 18 }

icmpNotification19 NOTIFICATION-TYPE
    OBJECTS { 
              icmp19-gateway-address, 
              icmp19-reason 
            }
    STATUS current
    DESCRIPTION
        "Notification of Event ICMP.19

        Message: 'Router advertisement received from $1 was bad for the reason: $2'

        Parameters list:
              $1: icmp19-gateway-address
              $2: icmp19-reason

        An ICMP Router Advertisement (Gateway Discovery) message has been
        received from the specified router, but was rejected for
        the specified reason."
    ::= { icmpNotificationsPrefix 19 }

icmpNotification20 NOTIFICATION-TYPE
    OBJECTS { 
              icmp20-ICMP-type, 
              icmp20-ICMP-code,
              icmp20-source-IP-address,
              icmp20-destination-IP-address 
            }
    STATUS current
    DESCRIPTION
        "Notification of Event ICMP.20

        Message: 'received message type $1 $2 from $3 to $4'

        Parameters list:
              $1: icmp20-ICMP-type
              $2: icmp20-ICMP-code
              $3: icmp20-source-IP-address
              $4: icmp20-destination-IP-address

        The router has received an ICMP message of the specified type from
        the source host."
    ::= { icmpNotificationsPrefix 20 }

icmpNotification21 NOTIFICATION-TYPE
    OBJECTS { 
              icmp21-interface 
            }
    STATUS current
    DESCRIPTION
        "Notification of Event ICMP.21

        Message: 'redirect message filtered at interface $1'

        Parameters list:
              $1: icmp21-interface

        A redirect message has been filtered at specified interface."
    ::= { icmpNotificationsPrefix 21 }

icmpNotification22 NOTIFICATION-TYPE
    OBJECTS { 
              icmp22-interface 
            }
    STATUS current
    DESCRIPTION
        "Notification of Event ICMP.22

        Message: 'unreachable message filtered at interface $1'

        Parameters list:
              $1: icmp22-interface

        An unreachable message has been filtered at specified interface."
    ::= { icmpNotificationsPrefix 22 }


END
