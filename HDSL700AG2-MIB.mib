-- Copyright 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     27-Jan-98  C. Amorossi     Initial Revision

HDSL700AG2-MIB DEFINITIONS ::= BEGIN

IMPORTS
	OBJECT-TYPE			FROM RFC-1212
	DisplayString			FROM RFC1213-MIB
	hdsl700AG2                      FROM GDCHDSL-MIB;

hdsl700AG2System          OBJECT IDENTIFIER ::= { hdsl700AG2 1 }
hdsl700AG2Version         OBJECT IDENTIFIER ::= { hdsl700AG2System 1 }

-- This mib is a subset of the HDSL mib for the 700AG2 product.

-- ***************************************************************************
-- The interfaces are defined as follows:
--	Unit	0
--	E1	1
--	Loop1	2
--	Loop2	3
-- ***************************************************************************

gdc700AG2SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl700AG2Version 1 }

--
-- ********************************************************************
-- GDC Hdsl Alarm Object Identifier Definitions
-- ********************************************************************
hdsl700AG2Alarms                OBJECT IDENTIFIER ::= { hdsl700AG2 2 }

hdsl700AG2NoResponseAlm		OBJECT IDENTIFIER ::= { hdsl700AG2Alarms 1  }
hdsl700AG2DiagRxErrAlm		OBJECT IDENTIFIER ::= { hdsl700AG2Alarms 2  }
hdsl700AG2PowerUpAlm		OBJECT IDENTIFIER ::= { hdsl700AG2Alarms 3  }
hdsl700AG2UnitFailure           OBJECT IDENTIFIER ::= { hdsl700AG2Alarms 4  }
hdsl700AG2ChecksumCorrupt       OBJECT IDENTIFIER ::= { hdsl700AG2Alarms 5  }
hdsl700AG2LossofSignal		OBJECT IDENTIFIER ::= { hdsl700AG2Alarms 6  }
hdsl700AG2UnavailableSec	OBJECT IDENTIFIER ::= { hdsl700AG2Alarms 7  }
hdsl700AG2ErrorSec		OBJECT IDENTIFIER ::= { hdsl700AG2Alarms 8  }
hdsl700AG2LossofSyncWord	OBJECT IDENTIFIER ::= { hdsl700AG2Alarms 9  }
hdsl700AG2LossofFrameAlign	OBJECT IDENTIFIER ::= { hdsl700AG2Alarms 10 }
hdsl700AG2AllOnes		OBJECT IDENTIFIER ::= { hdsl700AG2Alarms 11 }
hdsl700AG2RemoteLossofSig	OBJECT IDENTIFIER ::= { hdsl700AG2Alarms 12 }
hdsl700AG2RemoteAlarmInd	OBJECT IDENTIFIER ::= { hdsl700AG2Alarms 13 }
hdsl700AG2MajorBER      	OBJECT IDENTIFIER ::= { hdsl700AG2Alarms 14 }
hdsl700AG2MinorBER		OBJECT IDENTIFIER ::= { hdsl700AG2Alarms 15 }
 
 
-- ALARM			Maskable	Valid Interfaces  Thres
--======================================================================
--hdsl700AG2NoResponseAlm	No		Unit		   No
--hdsl700AG2DiagRxErrAlm        No              Unit		   No
--hdsl700AG2PowerUpAlm		No		Unit		   No
--hdsl700AG2UnitFailure         No              Unit		   No
--hdsl700AG2ChecksumCorrupt     No              Unit		   No
--hdsl700AG2LossofSignal	Yes		E1, L1, L2 	   No
--hdsl700AG2UnavailableSec	Yes		E1, L1, L2	   No
--hdsl700AG2ErrorSec		Yes		E1, L1, L2	   No
--hdsl700AG2LossofSyncWord	Yes		L1, L2		   No
--hdsl700AG2LossofFrameAlign	Yes		E1		   No
--hdsl700AG2AllOnes		Yes		E1		   No
--hdsl700AG2RemoteLossofSig	Yes		E1		   No
--hdsl700AG2RemoteAlarmInd	Yes		E1 		   No
--hdsl700AG2MajorBER		Yes		L1, L2		   Yes
--hdsl700AG2MinorBER		Yes		L1, L2		   Yes


END
