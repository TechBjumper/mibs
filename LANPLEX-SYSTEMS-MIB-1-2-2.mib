--	LANplex Systems Management Information Base
		--	Version 1.2.2
		--	November 15, 1995

		--	3Com Corporation
		--	80 Central Street
		--	Boxborough, MA 01719 
		--	(508) 264-1400

 		----------
		--	Change History:
                --              11/20/95	bbm		Incremented the version number to 1-2-2,
		--						and fixed the LpsTokenRingPortEntry that
		--						where incorretly defined as INTEGER instead
		--						of Counter.
		--		11/15/95	bbm		Changed version, and added the
		--						Token Ring Group.
		--		11/02/95	kgd		Changed version, address.
		--		10/03/95	ctm		Added lps6012TRSM & lps6004TRSM
	  	--               9/29/95        kgd             Added lpsSlotTokenRingPortCount,
		--							trsmBoard, tokenringPort,
		--							SR & SRTBridgeModes
		--		 5/15/95	eah		Added modularCard to
		--							lpsSmtFddiPortLocationType.
		--		 5/12/95	eah		Added lss2200.
		--		 3/13/95	eah		Added modularCard to
		--							lpsInterfaceLocationType.  Added
		--							lpsNetworkMonitor group.
		--		 3/ 1/95	eah		Added efsmBoard to lpsSlotBoardType.
		--							Deprecated lpsSnmpProxyInternalRequests,
		--							lpsSnmpProxyInternalTraps, and
		--							lpsAgentProxyRemoteSmtRequests.
		--							Changed lps6012FESM to lps6012EFSM and
		--							lps6004FESM to lps6004EFSM.
		--		 1/19/95	eah		Corrected lps2016 object identifier and
		--							added lps6012FESM and lps6004FESM.
		--		12/ 2/94	eah		Revised system object id paths, changed
		--							lpsChassis to lpsSlot, and converted
		--							lpsBridgePortForwardedToTable to the
		--							lpsBridgePortPairTable.  Re-organized the
		--							physical to logical mappings.  Add the
		--							lpsInterface group and removed the
		--							lpsBridgePortFilteredToTable.  Changed/
		--							added several other bridge port statistics.
		--		10/28/94	eah		Added lpsSystemOvertemperature,
		--							lpsSystemFanFailure,
		--							lpsChassisSlotOvertemperature, and
		--							lpsPowerSupplyStatusSupported objects.
		--							Added lpsSystemFanFailure event.
		--		 7/13/94	eah		Originated.
		----------
		LANPLEX-SYSTEMS-MIB-1-2-2 DEFINITIONS ::= BEGIN

		IMPORTS
			enterprises, Counter, Gauge			FROM RFC1155-SMI
			DisplayString						FROM RFC1213-MIB
			OBJECT-TYPE							FROM RFC-1212
			TRAP-TYPE							FROM RFC-1215;

		synernetics				OBJECT IDENTIFIER ::= { enterprises 114 }
		lanplex					OBJECT IDENTIFIER ::= { synernetics 1 }

		-- LANplex products.

		lpsProducts				OBJECT IDENTIFIER ::= { lanplex 3 }

		lps6000					OBJECT IDENTIFIER ::= { lpsProducts 2 }
		lps2000					OBJECT IDENTIFIER ::= { lpsProducts 3 }

		-- Product types.

		lps6012					OBJECT IDENTIFIER ::= { lps6000 1 }
		lps6004					OBJECT IDENTIFIER ::= { lps6000 2 }

		lps2500					OBJECT IDENTIFIER ::= { lps2000 1 }
		lss2200					OBJECT IDENTIFIER ::= { lps2000 2 }
		lps2016					OBJECT IDENTIFIER ::= { lps2000 3 }

		-- Independently managed product device types.

		lps6012System			OBJECT IDENTIFIER ::= { lps6012 1 }
		lps6012Chassis			OBJECT IDENTIFIER ::= { lps6012 2 }
		lps6012ESM				OBJECT IDENTIFIER ::= { lps6012 3 }
		lps6012EFSM				OBJECT IDENTIFIER ::= { lps6012 4 }
		lps6012TRSM				OBJECT IDENTIFIER ::= { lps6012 5 }

		lps6004System			OBJECT IDENTIFIER ::= { lps6004 1 }
		lps6004Chassis			OBJECT IDENTIFIER ::= { lps6004 2 }
		lps6004ESM				OBJECT IDENTIFIER ::= { lps6004 3 }
		lps6004EFSM				OBJECT IDENTIFIER ::= { lps6004 4 }
 		lps6004TRSM				OBJECT IDENTIFIER ::= { lps6004 5 }

		-- This is the LANplex Systems MIB module.

		lanplexSystemsMib		OBJECT IDENTIFIER ::= { lanplex 4 }

		-- LANplex Systems MIB groups.

		lpsSystem				OBJECT IDENTIFIER ::= { lanplexSystemsMib 1 }
		lpsSlot					OBJECT IDENTIFIER ::= { lanplexSystemsMib 2 }
		lpsControlPanel			OBJECT IDENTIFIER ::= { lanplexSystemsMib 3 }
		lpsPowerSupply			OBJECT IDENTIFIER ::= { lanplexSystemsMib 4 }
		lpsSnmp					OBJECT IDENTIFIER ::= { lanplexSystemsMib 5 }
		lpsAgent				OBJECT IDENTIFIER ::= { lanplexSystemsMib 6 }
		lpsInterface			OBJECT IDENTIFIER ::= { lanplexSystemsMib 7 }
		lpsEthernetPort			OBJECT IDENTIFIER ::= { lanplexSystemsMib 8 }
		lpsSmt					OBJECT IDENTIFIER ::= { lanplexSystemsMib 9 }
		lpsBridge				OBJECT IDENTIFIER ::= { lanplexSystemsMib 10 }
		lpsIpRouter				OBJECT IDENTIFIER ::= { lanplexSystemsMib 11 }
		lpsNetworkMonitor		OBJECT IDENTIFIER ::= { lanplexSystemsMib 12 }
		lpsTokenRingPort		OBJECT IDENTIFIER ::= { lanplexSystemsMib 13 }

		-- The LANplex Systems MIB system group.  Implementation of this
		-- group is mandatory for agents which manage system resources.

		lpsSystemId OBJECT-TYPE
			SYNTAX	INTEGER 
			ACCESS	read-only
			STATUS	mandatory
			DESCRIPTION
					"The unique identifier assigned to this system during
					manufacturing."
			::= { lpsSystem 1 }

		lpsSystemType OBJECT-TYPE
			SYNTAX	INTEGER {
						other(1),
						lanplex6000(2),
						lanplex2000(3)
					}
			ACCESS	read-only
			STATUS	mandatory
			DESCRIPTION
					"The type of system."
			::= { lpsSystem 2 }

		lpsSystemName OBJECT-TYPE
			SYNTAX	DisplayString (SIZE (0..31))
			ACCESS	read-write
			STATUS	mandatory
			DESCRIPTION
					"The text string describing this system."
			::= { lpsSystem 3 }

		lpsSystemManufacturer OBJECT-TYPE
			SYNTAX	DisplayString (SIZE (0..127))
			ACCESS	read-only
			STATUS	mandatory
			DESCRIPTION
					"The text string describing the manufacturer of this
					system."
			::= { lpsSystem 4 }

		lpsSystemHardwareRevision OBJECT-TYPE
			SYNTAX	OCTET STRING (SIZE (2)) 
			ACCESS	read-only
			STATUS	mandatory
			DESCRIPTION
					"The revision level of the system, contained in two
					octets.  The first octet indicates the artwork revision,
					and the second octet indicates the rework level."
			::= { lpsSystem 5 }

		lpsSystemMemorySize OBJECT-TYPE
			SYNTAX	INTEGER 
			ACCESS	read-only
			STATUS	mandatory
			DESCRIPTION
					"The amount of memory (RAM), in bytes, present on the
					system processor board." 
			::= { lpsSystem 6 }

		lpsSystemFlashMemorySize OBJECT-TYPE
			SYNTAX	INTEGER 
			ACCESS	read-only
			STATUS	mandatory
			DESCRIPTION
					"The amount of flash memory, in bytes, present on the
					system processor board."
			::= { lpsSystem 7 }

		lpsSystemNvMemorySize OBJECT-TYPE
			SYNTAX	INTEGER 
			ACCESS	read-only
			STATUS	mandatory
			DESCRIPTION
					"The amount of non-volatile memory, in bytes, present
					on the system processor board." 
			::= { lpsSystem 8 }

		lpsSystemSoftwareRevision OBJECT-TYPE
			SYNTAX	OCTET STRING (SIZE (4)) 
			ACCESS	read-only
			STATUS	mandatory
			DESCRIPTION
					"The revision number of the LANplex system software.
					Each byte indicates the following:
						byte 0: major release number.
						byte 1: minor release number.
						byte 2: update number.
						byte 3:
							bits 7-6: release type.
							bits 5-0: supplemental identifier."
			::= { lpsSystem 9 }

		lpsSystemBuildTime OBJECT-TYPE
			SYNTAX	DisplayString (SIZE (0..127))
			ACCESS	read-only
			STATUS	mandatory
			DESCRIPTION
					"The build time of the system software."
			::= { lpsSystem 10 }

		lpsSystemSnmpRevision OBJECT-TYPE
			SYNTAX	INTEGER
			ACCESS	read-only
			STATUS	mandatory
			DESCRIPTION
					"The revision number of the SNMP agent implementation."
			::= { lpsSystem 11 }

		lpsSystemRequestedSnmpMode OBJECT-TYPE
			SYNTAX	INTEGER {
						singleAgentMode(1),
						multiAgentMode(2)
					}
			ACCESS	read-write
			STATUS	mandatory
			DESCRIPTION
					"This object describes the requested SNMP mode for the
					system.  The value of this object indicates the mode that
					will become effective following a reboot of the system.
					Note that only a subset of the above values may be valid
					for some systems."
			::= { lpsSystem 12 }

		lpsSystemCurrentSnmpMode OBJECT-TYPE
			SYNTAX	INTEGER {
						singleAgentMode(1),
						multiAgentMode(2)
					}
			ACCESS	read-only
			STATUS	mandatory
			DESCRIPTION
					"This object describes the currently active SNMP mode for
					the system.  Note that only a subset of the above values
					may be valid for some systems."
			::= { lpsSystem 13 }

		lpsSystemAction OBJECT-TYPE
			SYNTAX	INTEGER {
						other(1),
						reset(2)
					}
			ACCESS	read-write
			STATUS	mandatory
			DESCRIPTION
					"This object, when read, always returns the value
					other(1).  Setting this object to the value reset(2) causes
					a reset of the system.  The value other(1) is not a vaild
					value for set operations."
			::= { lpsSystem 14 }

		lpsSystemOvertemperature OBJECT-TYPE
			SYNTAX	INTEGER {
						true(1),
						false(2),
						notSupported(3)
					}
			ACCESS	read-only
			STATUS	mandatory
			DESCRIPTION
					"This object indicates the current overtemperature
					status for the system.  If the system does not support
					overtemperature detection, this object returns
					notSupported."
			::= { lpsSystem 15 }

		lpsSystemFanFailure OBJECT-TYPE
			SYNTAX	INTEGER {
						true(1),
						false(2),
						notSupported(3)
					}
			ACCESS	read-only
			STATUS	mandatory
			DESCRIPTION
					"This object indicates the current fan status for the
					system.  If the system does not support fan failure
					detection, this object returns notSupported."
			::= { lpsSystem 16 }

		-- The LANplex Systems MIB slot group.  Implementation of this
		-- group is mandatory for agents which manage system resources
		-- for modular systems with independently manageable slots.

		lpsSlotCount OBJECT-TYPE
			SYNTAX	INTEGER
			ACCESS	read-only
			STATUS	mandatory
			DESCRIPTION
					"The count of slots in the chassis."
			::= { lpsSlot 1 }

		-- The LANplex Systems MIB slot table.

		lpsSlotTable OBJECT-TYPE
			SYNTAX	SEQUENCE OF LpsSlotEntry
			ACCESS	not-accessible
			STATUS	mandatory
			DESCRIPTION
					"A list of slot entries.  A single entry exists in this 
					list for each slot in the chassis."
			::= { lpsSlot 2 }

		lpsSlotEntry OBJECT-TYPE
			SYNTAX	LpsSlotEntry
			ACCESS	not-accessible
			STATUS	mandatory
			DESCRIPTION
					"A slot entry contains information about a particular
					slot."
			INDEX	{ lpsSlotIndex }
			::= { lpsSlotTable 1 }

		LpsSlotEntry ::=
			SEQUENCE {
				lpsSlotIndex
					INTEGER,
				lpsSlotBoardType
					INTEGER,
				lpsSlotBoardRevision
					OCTET STRING,
				lpsSlotBoardStatus
					INTEGER,
				lpsSlotBoardName
					DisplayString,
				lpsSlotBoardNameAbbrev
					DisplayString,
				lpsSlotEthernetPortCount
					INTEGER,
				lpsSlotFddiMacCount
					INTEGER,
				lpsSlotFddiPortCount
					INTEGER,
				lpsSlotOvertemperature
					INTEGER,
				lpsSlotTokenRingPortCount
					INTEGER
			}

		lpsSlotIndex OBJECT-TYPE
			SYNTAX	INTEGER
			ACCESS	read-only
			STATUS	mandatory
			DESCRIPTION
					"The index of the slot identified by this entry."
			::= { lpsSlotEntry 1 }

		lpsSlotBoardType OBJECT-TYPE
			SYNTAX	INTEGER {
						other(1),
						emptyLocation(2),
						esmBoard(7),
						fcmBoard(8),
						lmmBoard(9),
						efsmBoard(10),
						trsmBoard(11)
					}
			ACCESS	read-only
			STATUS	mandatory
			DESCRIPTION
					"The type of board residing in the slot identified by
					this entry."
			::= { lpsSlotEntry 2 }

		lpsSlotBoardRevision OBJECT-TYPE
			SYNTAX	OCTET STRING (SIZE (0..1))
			ACCESS	read-only
			STATUS	mandatory
			DESCRIPTION
					"The revision number of the board in the slot identified
					by this entry.  If the slot is empty, or the revision is
					unknown this object returns a zero length string."
			::= { lpsSlotEntry 3 }

		lpsSlotBoardStatus OBJECT-TYPE
			SYNTAX	INTEGER {
						notPresent(1),
						testing(2),
						offline(3),
						online(4)
					}
			ACCESS	read-only
			STATUS	mandatory
			DESCRIPTION
					"The status of the board in the slot identified by this
					entry."
			::= { lpsSlotEntry 4 }

		lpsSlotBoardName OBJECT-TYPE
			SYNTAX	DisplayString (SIZE (0..255))
			ACCESS	read-only
			STATUS	mandatory
			DESCRIPTION
					"The text string describing the board in the slot
					identified by this entry."
			::= { lpsSlotEntry 5 }

		lpsSlotBoardNameAbbrev OBJECT-TYPE
			SYNTAX	DisplayString (SIZE (0..31))
			ACCESS	read-only
			STATUS	mandatory
			DESCRIPTION
					"The abbreviation used to describe the board in the slot
					identified by this entry." 
			::= { lpsSlotEntry 6 }

		lpsSlotEthernetPortCount OBJECT-TYPE
			SYNTAX	INTEGER
			ACCESS	read-only
			STATUS	mandatory
			DESCRIPTION
					"The count of ethernet ports in the slot identified by
					this entry."
			::= { lpsSlotEntry 7 }

		lpsSlotFddiMacCount OBJECT-TYPE
			SYNTAX	INTEGER
			ACCESS	read-only
			STATUS	mandatory
			DESCRIPTION
					"The count of FDDI MACs in the slot identified by this
					entry."
			::= { lpsSlotEntry 8 }

		lpsSlotFddiPortCount OBJECT-TYPE
			SYNTAX	INTEGER
			ACCESS	read-only
			STATUS	mandatory
			DESCRIPTION
					"The count of FDDI ports in the slot identified by this
					entry."
			::= { lpsSlotEntry 9 }

		lpsSlotOvertemperature OBJECT-TYPE
			SYNTAX	INTEGER {
						true(1),
						false(2),
						notSupported(3)
					}
			ACCESS	read-only
			STATUS	mandatory
			DESCRIPTION
					"This object indicates the current overtemperature status
					for the slot.  If the slot does not support overtemperature
					detection, this object returns notSupported."
			::= { lpsSlotEntry 10 }

		lpsSlotTokenRingPortCount OBJECT-TYPE
			SYNTAX	INTEGER
			ACCESS	read-only
			STATUS	mandatory
			DESCRIPTION
					"The count of TokenRing ports in the slot identified by this
					entry."
			::= { lpsSlotEntry 11 }

		-- The LANplex Systems MIB control panel group.  Implementation of
		-- this group is mandatory for agents which manage system resources
		-- for systems which are equipped with manageable control panels.

		lpsControlPanelHardwareRevision OBJECT-TYPE
			SYNTAX	OCTET STRING (SIZE (1)) 
			ACCESS	read-only
			STATUS	mandatory
			DESCRIPTION
					"An 8-bit value specifying the revision level of the
					control panel hardware."
			::= { lpsControlPanel 1 }

		lpsControlPanelSoftwareRevision OBJECT-TYPE
			SYNTAX	OCTET STRING (SIZE (1)) 
			ACCESS	read-only
			STATUS	mandatory
			DESCRIPTION
					"An 8-bit value specifying the revision level of the
					control panel software."
			::= { lpsControlPanel 2 }

		lpsControlPanelLines OBJECT-TYPE
			SYNTAX	INTEGER 
			ACCESS	read-only
			STATUS	mandatory
			DESCRIPTION
					"The number of lines in the control panel display."
			::= { lpsControlPanel 3 }

		lpsControlPanelColumns OBJECT-TYPE
			SYNTAX	INTEGER 
			ACCESS	read-only
			STATUS	mandatory
			DESCRIPTION
					"The number of columns in the control panel display."
			::= { lpsControlPanel 4 }

		lpsControlPanelText OBJECT-TYPE
			SYNTAX	OCTET STRING (SIZE (0..127))
			ACCESS	read-only
			STATUS	mandatory
			DESCRIPTION
					"The currently displayed text in the control panel
					display."
			::= { lpsControlPanel 5 }

		-- The LANplex Systems MIB power supply group.  Implementation of this
		-- group is mandatory for agents which manage system resources for
		-- systems which are equipped with managable power supplies.

		lpsPowerSupplyCount OBJECT-TYPE
			SYNTAX	INTEGER
			ACCESS	read-only
			STATUS	mandatory
			DESCRIPTION
					"The count of power supplies in the system."
			::= { lpsPowerSupply 1 }

		-- The LANplex Systems MIB power supply status table.

		lpsPowerSupplyStatusTable OBJECT-TYPE
			SYNTAX	SEQUENCE OF LpsPowerSupplyStatusEntry
			ACCESS	not-accessible
			STATUS	mandatory
			DESCRIPTION
					"A list of power supply status entries."
			::= { lpsPowerSupply 2 }

		lpsPowerSupplyStatusEntry OBJECT-TYPE
			SYNTAX	LpsPowerSupplyStatusEntry
			ACCESS	not-accessible
			STATUS	mandatory
			DESCRIPTION
					"A power supply status entry contains information about a 
					particular power supply."
			INDEX	{ lpsPowerSupplyStatusIndex }
			::= { lpsPowerSupplyStatusTable 1 }

		LpsPowerSupplyStatusEntry ::=
			SEQUENCE {
				lpsPowerSupplyStatusIndex
					INTEGER,
				lpsPowerSupplyStatus
					INTEGER,
				lpsPowerSupplyStatusSupported
					INTEGER
			}

		lpsPowerSupplyStatusIndex OBJECT-TYPE
			SYNTAX	INTEGER
			ACCESS	read-only
			STATUS	mandatory
			DESCRIPTION
					"The unique index of the power supply identified by this
					entry."
			::= { lpsPowerSupplyStatusEntry 1 }

		lpsPowerSupplyStatus OBJECT-TYPE
			SYNTAX	INTEGER
			ACCESS	read-only
			STATUS	mandatory
			DESCRIPTION
					"This object represents the power supply status.  The
					value is a sum. It initially takes on the value 0, then
					for each failure type which is active, 2 raised to a power
					is added to the sum.  The powers are according to the
					following table:

						Failure Type			Power
						AC Failure				  0
						Plus 5 Failure			  1
						Plus 12 Failure			  2
						Over Temperature Failure  3"
			::= { lpsPowerSupplyStatusEntry 2 }

		lpsPowerSupplyStatusSupported OBJECT-TYPE
			SYNTAX	INTEGER
			ACCESS	read-only
			STATUS	mandatory
			DESCRIPTION
					"This object represents the various power supply failure
					types which are supported.  The value is a sum.  It
					initially takes on the value 0, then for each failure type
					which is supported, 2 raised to a power is added to the
					sum.  The powers are according to the following table:

						Failure Type			Power
						AC Failure				  0
						Plus 5 Failure			  1
						Plus 12 Failure			  2
						Over Temperature Failure  3

					This object used in conjunction with the
					lpsPowerSupplyStatus object for a given power supply
					provide a complete picture of the status of the power
					supply."
			::= { lpsPowerSupplyStatusEntry 3 }

		-- The LANplex Systems MIB SNMP group.  Implementation of this group
		-- is mandatory for agents in systems which contain multiple
		-- independently manageable devices and which support a multiple agent
		-- mode.  Note that this group is only available in the multiple agent
		-- mode for those systems that support it.

		lpsSnmpAgentId OBJECT-TYPE
			SYNTAX	INTEGER
			ACCESS	read-only
			STATUS	mandatory
			DESCRIPTION
					"The unique id for this SNMP agent within the system."
			::= { lpsSnmp 1 }

		lpsSnmpInternalAgentTrapMask OBJECT-TYPE
			SYNTAX	OCTET STRING (SIZE (8))
			ACCESS	read-write
			STATUS	mandatory
			DESCRIPTION
					"This value is a bit string that indicates which traps
					are enabled for transmit to other agents in the system.
					The octet string value is treated as a 64-bit integer
					value.  The value is a sum.  It initially takes on the
					value 0, then for each trap which is enabled, 2 raised
					to the value of (lpsAgentTrapDescriptionIndex - 1) for
					that trap is added to the sum."
			::= { lpsSnmp 2 }

		lpsSnmpInternalAgentTrapDestinationMask OBJECT-TYPE
			SYNTAX	INTEGER
			ACCESS	read-write
			STATUS	mandatory
			DESCRIPTION
					"A value which indicates to which other agents in the
					system traps should be sent.  The value is a sum.  It
					initially takes on the value 0, then for each agent which
					is to receive traps, 2 raised to the value of
					(lpsSnmpAgentId - 1) for that agent is added to the sum.
					Note that only traps which are enabled according to the
					value of the lpsSnmpInternalAgentTrapMask object will be
					forwarded, and that each trap which is forwarded will
					be transmitted to each agent identified by this mask."
			::= { lpsSnmp 3 }

		lpsSnmpProxyInternalRequests OBJECT-TYPE
			SYNTAX	INTEGER {
						true(1),
						false(2)
					}
			ACCESS	read-write
			STATUS	deprecated
			DESCRIPTION
					"This object determines if this agent will proxy requests
					to other agents in the system.  If the value of this
					object is true(1), this agent will proxy requests to other
					agents in the chassis."
			::= { lpsSnmp 4 }

		lpsSnmpInternalProxyRequestMaxAge OBJECT-TYPE
			SYNTAX	INTEGER (1..255)
			ACCESS	read-write
			STATUS	mandatory
			DESCRIPTION
					"The maximum time, in seconds, an internal proxy request
					will remain queued waiting for a response before being
					discarded.  Note that when the value of
					lpsSnmpProxyInternalRequests is false(2), the value of
					this object is ignored."
			::= { lpsSnmp 5 }

		lpsSnmpProxyInternalTraps OBJECT-TYPE
			SYNTAX	INTEGER {
						true(1),
						false(2)
					}
			ACCESS	read-write
			STATUS	deprecated
			DESCRIPTION
					"This object determines if this agent will generate proxy
					traps for those traps received from other agents in the
					system.  If the value of this object is true(1), this
					agent will generate proxy traps for those received from
					other agents in the chassis.  Note that agents will not
					proxy traps to other agents within the system to prevent
					looping of traps."
			::= { lpsSnmp 6 }

		-- The LANplex Systems MIB SNMP internal proxy table.

		lpsSnmpInternalProxyTable OBJECT-TYPE
			SYNTAX	SEQUENCE OF LpsSnmpInternalProxyEntry
			ACCESS	not-accessible
			STATUS	mandatory
			DESCRIPTION
					"A list of SNMP internal agent proxy entries.  An entry in
					this table exists for each agent in the system that can be
					reached by this agent via the internal proxy mechanism."
			::= { lpsSnmp 7 }

		lpsSnmpInternalProxyEntry OBJECT-TYPE
			SYNTAX	LpsSnmpInternalProxyEntry
			ACCESS	not-accessible
			STATUS	mandatory
			DESCRIPTION
					"An entry identifies the communities available for
					communicating with another agent in the system via the
					internal proxy mechanism."
			INDEX	{ lpsSnmpInternalProxyAgentId,
					lpsSnmpInternalProxyAccessClass }
			::= { lpsSnmpInternalProxyTable 1 }

		LpsSnmpInternalProxyEntry ::=
			SEQUENCE {
				lpsSnmpInternalProxyAgentId
					INTEGER,
				lpsSnmpInternalProxyAccessClass
					INTEGER,
				lpsSnmpInternalProxyCommunity
					OCTET STRING
			}

		lpsSnmpInternalProxyAgentId OBJECT-TYPE
			SYNTAX	INTEGER
			ACCESS	read-only
			STATUS	mandatory
			DESCRIPTION
					"The id of the agent identified by this entry."
			::= { lpsSnmpInternalProxyEntry 1 }

		lpsSnmpInternalProxyAccessClass OBJECT-TYPE
			SYNTAX	INTEGER {
						readOnly(1),
						readWrite(2)
					}
			ACCESS	read-only
			STATUS	mandatory
			DESCRIPTION
					"The access to MIB objects supported by the agent
					identified by this entry provided by this agent, when
					using the community string identified by the corresponding
					value of lpsSnmpInternalProxyCommunity."
			::= { lpsSnmpInternalProxyEntry 2 }

		lpsSnmpInternalProxyCommunity OBJECT-TYPE
			SYNTAX	OCTET STRING
			ACCESS	read-only
			STATUS	mandatory
			DESCRIPTION
					"A community which allows access to MIB objects supported
					by the agent identified by this entry."
			::= { lpsSnmpInternalProxyEntry 3 }

		-- The LANplex Systems MIB agent group.  Implementation of this group
		-- is mandatory for all agents.

		lpsAgentRequestMaxAge OBJECT-TYPE
			SYNTAX	INTEGER (1..255)
			ACCESS	read-write
			STATUS	mandatory
			DESCRIPTION
					"The maximum time, in seconds, a local SNMP request will
					remain queued waiting for a response before being
					discarded."
			::= { lpsAgent 1 }

		lpsAgentProxyRemoteSmtRequests OBJECT-TYPE
			SYNTAX	INTEGER {
						true(1),
						false(2)
					}
			ACCESS	read-write
			STATUS	deprecated
			DESCRIPTION
					"This object determines if this agent will proxy SMT
					requests to other FDDI stations.  If the value of this
					object is true(1), this agent will proxy SMT requests to
					other stations.  Note that only a subset of the above
					values may be valid for some systems."
			::= { lpsAgent 2 }

		lpsAgentRemoteSmtProxyRequestMaxAge OBJECT-TYPE
			SYNTAX	INTEGER (1..255)
			ACCESS	read-write
			STATUS	mandatory
			DESCRIPTION
					"The maximum time, in seconds, an SMT proxy request will
					remain queued waiting for a response before being
					discarded.  Note that when the value of
					lpsAgentProxyRemoteSmtRequests is false(2), the value of
					this object is ignored."
			::= { lpsAgent 3 }

		lpsAgentProxyRemoteSmtEvents OBJECT-TYPE
			SYNTAX	INTEGER {
						true(1),
						false(2)
					}
			ACCESS	read-write
			STATUS	mandatory
			DESCRIPTION
					"This object determines if this agent will generate traps
					for SMT events occuring at other stations.  If the value
					of this object is true(1), this agent will generate traps
					for all SMT events, those which occur locally, and those
					which occur at other stations.  If the value of this
					object is false(2), this agent will only generate traps
					for events which occur locally.  Note that only a subset
					of the above values may be valid for some systems."
			::= { lpsAgent 4 }

		-- The LANplex Systems MIB agent trap description table.

		lpsAgentTrapDescriptionTable OBJECT-TYPE
			SYNTAX	SEQUENCE OF LpsAgentTrapDescriptionTableEntry
			ACCESS	not-accessible
			STATUS	mandatory
			DESCRIPTION
					"This table contains a listing of trap descriptions for
					each trap supported by this agent.  This 
					provides a relationship between a trap index, and the trap
					enterprise oid and trap number for a given trap.  In all
					cases except for the MIB-2 generic traps, the enterprise
					under which a trap is defined is the same as that
					appearing in the ENTERPRISE portion of the trap."
			::= { lpsAgent 5 }

		lpsAgentTrapDescriptionTableEntry OBJECT-TYPE
			SYNTAX	LpsAgentTrapDescriptionTableEntry
			ACCESS	not-accessible
			STATUS	mandatory
			DESCRIPTION
					"Information relating a trap index to a specific trap
					enterprise oid and trap number."
			INDEX	{ lpsAgentTrapDescriptionIndex }
			::= { lpsAgentTrapDescriptionTable 1 }

		LpsAgentTrapDescriptionTableEntry ::=
			SEQUENCE {
				lpsAgentTrapDescriptionIndex
					INTEGER,
				lpsAgentTrapEnterprise
					OBJECT IDENTIFIER,
				lpsAgentTrapNumber
					INTEGER
			}

		lpsAgentTrapDescriptionIndex OBJECT-TYPE
			SYNTAX	INTEGER
			ACCESS	read-only
			STATUS	mandatory
			DESCRIPTION
					"A unique index corresponding to the trap described by
					this entry.  This value of this object corresponding to
					a particular trap will remain constant accross system
					resets."
			::= { lpsAgentTrapDescriptionTableEntry 1 }

		lpsAgentTrapEnterprise OBJECT-TYPE
			SYNTAX	OBJECT IDENTIFIER
			ACCESS	read-only
			STATUS	mandatory
			DESCRIPTION
					"The enterpise under which the trap identified by this
					entry is defined."
			::= { lpsAgentTrapDescriptionTableEntry 2 }

		lpsAgentTrapNumber OBJECT-TYPE
			SYNTAX	INTEGER
			ACCESS	read-only
			STATUS	mandatory
			DESCRIPTION
					"The number of the trap identified by this entry, within
					the enterprise where it is defined."
			::= { lpsAgentTrapDescriptionTableEntry 3 }

		-- The LANplex Systems MIB agent trap destination table.

		lpsAgentTrapDestinationTable OBJECT-TYPE
			SYNTAX	SEQUENCE OF LpsAgentTrapDestinationTableEntry
			ACCESS	not-accessible
			STATUS	mandatory
			DESCRIPTION
					"This table contains information specifying which traps
					will be transmitted to a given destination address.  The
					table is indexed by the destination address type and
					destination address.  Each entry in the table with a
					status of valid identifies a set of traps which, when
					generated, will be transmitted to the corresponding
					destination address listed in that entry."
			::= { lpsAgent 6 }

		lpsAgentTrapDestinationTableEntry OBJECT-TYPE
			SYNTAX	LpsAgentTrapDestinationTableEntry
			ACCESS	not-accessible
			STATUS	mandatory
			DESCRIPTION
					"Information relating a set of traps and a destination
					address to which each trap in ths set will be transmitted
					when it is generated.  To create a new entry, set a
					non-existent instance of lpsAgentTrapDestinationTrapMask
					to a valid value.  To remove an entry, set the instance of
					lpsAgentTrapDestinationEntryStatus for the entry to
					invalid(2)."
			INDEX	{ lpsAgentTrapDestinationAddressType,
					lpsAgentTrapDestinationAddress }
			::= { lpsAgentTrapDestinationTable 1 }

		LpsAgentTrapDestinationTableEntry ::=
			SEQUENCE {
				lpsAgentTrapDestinationAddressType
					INTEGER,
				lpsAgentTrapDestinationAddress
					OCTET STRING,
				lpsAgentTrapDestinationTrapMask
					OCTET STRING,
				lpsAgentTrapDestinationEntryStatus
					INTEGER
			}

		lpsAgentTrapDestinationAddressType OBJECT-TYPE
			SYNTAX	INTEGER {
						ip(1)
					}
			ACCESS	read-only
			STATUS	mandatory
			DESCRIPTION
					"The type of address identified by this entry."
			::= { lpsAgentTrapDestinationTableEntry 1 }

		lpsAgentTrapDestinationAddress OBJECT-TYPE
			SYNTAX	OCTET STRING
			ACCESS	read-only
			STATUS	mandatory
			DESCRIPTION
					"The address, of the type specified by the corresponding
					value of lpsAgentTrapDestinationAddressType, to which the
					set of traps identified by this entry are to be
					transmitted."
			::= { lpsAgentTrapDestinationTableEntry 2 }

		lpsAgentTrapDestinationTrapMask OBJECT-TYPE
			SYNTAX	OCTET STRING (SIZE (8))
			ACCESS	read-write
			STATUS	mandatory
			DESCRIPTION
					"This value is a bit string that indicates which traps
					are enabled for the address identified by this entry.
					The octet string value is treated as a 64-bit value.  The
					value is a sum.  It initially takes on the value 0, then
					for each trap which is enabled, 2 raised to the value of
					(lpsAgentTrapDescriptionIndex - 1) for that trap is
					added to the sum.  A new entry in the table is created by
					setting the value of this object for a new destination
					address type and destination address.  Note that an octet
					string of all zeros is not a valid value for this object."
			::= { lpsAgentTrapDestinationTableEntry 3 }

		lpsAgentTrapDestinationEntryStatus OBJECT-TYPE
			SYNTAX	INTEGER {
						valid(1),
						invalid(2)
					}
			ACCESS	read-write
			STATUS	mandatory
			DESCRIPTION
					"The status of the trap destination table entry.  Setting
					this object to invalid(1) has the effect of removing the
					corresponding entry from the table."
			::= { lpsAgentTrapDestinationTableEntry 4 }

		-- The LANplex Systems MIB interface group.  Implementation of this
		-- group is mandatory for all agents.

		-- The LANplex Systems MIB interface location table.

		lpsInterfaceLocationTable OBJECT-TYPE
			SYNTAX	SEQUENCE OF LpsInterfaceLocationEntry
			ACCESS	not-accessible
			STATUS	mandatory
			DESCRIPTION
					"A list of interface location entries.  A single entry
					exists in this list for each interface managed by this
					agent."
			::= { lpsInterface 1 }

		lpsInterfaceLocationEntry OBJECT-TYPE
			SYNTAX	LpsInterfaceLocationEntry
			ACCESS	not-accessible
			STATUS	mandatory
			DESCRIPTION
					"An interface location entry describes the location of
					a particular interface managed by this agent."
			INDEX	{ lpsInterfaceLocationIfIndex }
			::= { lpsInterfaceLocationTable 1 }

		LpsInterfaceLocationEntry ::=
			SEQUENCE {
				lpsInterfaceLocationIfIndex
					INTEGER,
				lpsInterfaceLocationInterfaceType
					INTEGER,
				lpsInterfaceLocationType
					INTEGER,
				lpsInterfaceLocationTypeIndex
					INTEGER,
				lpsInterfaceLocationLocalIndex
					INTEGER
			}

		lpsInterfaceLocationIfIndex OBJECT-TYPE
			SYNTAX	INTEGER
			ACCESS	read-only
			STATUS	mandatory
			DESCRIPTION
					"The value of the MIB-II ifIndex corresponding to the
					interface identified by this entry."
			::= { lpsInterfaceLocationEntry 1 }

		lpsInterfaceLocationInterfaceType OBJECT-TYPE
			SYNTAX	INTEGER {
						other(1),
						ethernetPort(2),
						fddiMac(3),
						tokenringPort(4)
					}
			ACCESS	read-only
			STATUS	mandatory
			DESCRIPTION
					"The type of the physical implementation of the interface
					identified by this entry."
			::= { lpsInterfaceLocationEntry 2 }

		lpsInterfaceLocationType OBJECT-TYPE
			SYNTAX	INTEGER {
						other(1),
						modularSlot(2),
						chassis(3),
						modularCard(4)
					}
			ACCESS	read-only
			STATUS	mandatory
			DESCRIPTION
					"The type of location where the interface identified
					by this entry is physically located."
			::= { lpsInterfaceLocationEntry 3 }

		lpsInterfaceLocationTypeIndex OBJECT-TYPE
			SYNTAX	INTEGER
			ACCESS	read-only
			STATUS	mandatory
			DESCRIPTION
					"The index of the location identified by the corresponding
					instance of lpsInterfaceLocationType where the interface
					identified by this entry is physically located."
			::= { lpsInterfaceLocationEntry 4 }

		lpsInterfaceLocationLocalIndex OBJECT-TYPE
			SYNTAX	INTEGER
			ACCESS	read-only
			STATUS	mandatory
			DESCRIPTION
					"The local index of the interface identified by
					this entry relative to its type specified by the
					corresponding value of lpsInterfaceLocationInterfaceType,
					and the location specified by the corresponding values
					of lpsInterfaceLocationType and lpsInterfaceLocationTypeIndex."
			::= { lpsInterfaceLocationEntry 5 }

		-- The LANplex Systems MIB ethernet port group.  Implementation of
		-- this group is mandatory for agents which manage ethernet port
		-- resources.

		lpsEthernetPortCount OBJECT-TYPE
			SYNTAX	INTEGER
			ACCESS	read-only
			STATUS	mandatory
			DESCRIPTION
					"The count of ethernet ports managed by this agent."
			::= { lpsEthernetPort 1 }

		-- The LANplex Systems MIB ethernet port table.

		lpsEthernetPortTable OBJECT-TYPE
			SYNTAX	SEQUENCE OF LpsEthernetPortEntry
			ACCESS	not-accessible
			STATUS	mandatory
			DESCRIPTION
					"A list of ethernet port entries.  A single entry exists
					in this list for each ethernet port managed by this agent."
			::= { lpsEthernetPort 2 }

		lpsEthernetPortEntry OBJECT-TYPE
			SYNTAX	LpsEthernetPortEntry
			ACCESS	not-accessible
			STATUS	mandatory
			DESCRIPTION
					"An ethernet port entry contains information about a
					particular ethernet port managed by this agent."
			INDEX	{ lpsEthernetPortIndex }
			::= { lpsEthernetPortTable 1 }

		LpsEthernetPortEntry ::=
			SEQUENCE {
				lpsEthernetPortIndex
					INTEGER,
				lpsEthernetPortIfIndex
					INTEGER,
				lpsEthernetPortLabel
					DisplayString,
				lpsEthernetPortLinkStatus
					INTEGER,
				lpsEthernetPortType
					INTEGER
			}

		lpsEthernetPortIndex OBJECT-TYPE
			SYNTAX	INTEGER
			ACCESS	read-only
			STATUS	mandatory
			DESCRIPTION
					"The index of the ethernet port identified by this entry,
					relative to this agent."
			::= { lpsEthernetPortEntry 1 }

		lpsEthernetPortIfIndex OBJECT-TYPE
			SYNTAX	INTEGER
			ACCESS	read-only
			STATUS	mandatory
			DESCRIPTION
					"The value of the MIB-II ifIndex corresponding to the
					ethernet port identified by this entry."
			::= { lpsEthernetPortEntry 2 }

		lpsEthernetPortLabel OBJECT-TYPE
			SYNTAX	DisplayString (SIZE (0..31))
			ACCESS	read-write
			STATUS	mandatory
			DESCRIPTION
					"An ASCII text string describing the ethernet port
					identified by this entry."
			::= { lpsEthernetPortEntry 3 }

		lpsEthernetPortLinkStatus OBJECT-TYPE
			SYNTAX	INTEGER {
						active(1),
						inActive(2)
					}
			ACCESS	read-only
			STATUS	mandatory
			DESCRIPTION
					"The current value of the link status for the ethernet port
					identified by this entry."
			::= { lpsEthernetPortEntry 4 }

		lpsEthernetPortType OBJECT-TYPE
			SYNTAX	INTEGER {
						rj2110BaseT(1),
						rj4510BaseT(2),
						st10BaseFL(3),
						aui(4),
						bnc10Base2(5),
						other(6),
						rj45100BaseT(7)
					}
			ACCESS	read-only
			STATUS	mandatory
			DESCRIPTION
					"Specific port type description for the ethernet port
					identified by this entry."
			::= { lpsEthernetPortEntry 5 }

		-- The LANplex Systems MIB ethernet port rate table.

		lpsEthernetPortRateTable OBJECT-TYPE
			SYNTAX	SEQUENCE OF LpsEthernetPortRateEntry
			ACCESS	not-accessible
			STATUS	mandatory
			DESCRIPTION
					"A list of ethernet port rate entries.  A single entry
					exists in this list for each ethernet port, managed by
					this agent, which supports rate information."
			::= { lpsEthernetPort 3 }

		lpsEthernetPortRateEntry OBJECT-TYPE
			SYNTAX	LpsEthernetPortRateEntry
			ACCESS	not-accessible
			STATUS	mandatory
			DESCRIPTION
					"An ethernet port rate entry contains rate statistics for a
					particular ethernet port managed by this agent.  Rate
					statistics are calculated based on a one second sampling
					interval."
			INDEX	{ lpsEthernetPortRateIndex }
			::= { lpsEthernetPortRateTable 1 }

		LpsEthernetPortRateEntry ::=
			SEQUENCE {
				lpsEthernetPortRateIndex
					INTEGER,
				lpsEthernetPortRateByteReceiveRate
					INTEGER,
				lpsEthernetPortRatePeakByteReceiveRate
					INTEGER,
				lpsEthernetPortRateFrameReceiveRate
					INTEGER,
				lpsEthernetPortRatePeakFrameReceiveRate
					INTEGER,
				lpsEthernetPortRateByteTransmitRate
					INTEGER,
				lpsEthernetPortRatePeakByteTransmitRate
					INTEGER,
				lpsEthernetPortRateFrameTransmitRate
					INTEGER,
				lpsEthernetPortRatePeakFrameTransmitRate
					INTEGER
			}

		lpsEthernetPortRateIndex OBJECT-TYPE
			SYNTAX	INTEGER
			ACCESS	read-only
			STATUS	mandatory
			DESCRIPTION
					"The index of the ethernet port identified by this entry,
					relative to this agent."
			::= { lpsEthernetPortRateEntry 1 }

		lpsEthernetPortRateByteReceiveRate OBJECT-TYPE
			SYNTAX	INTEGER
			ACCESS	read-only
			STATUS	mandatory
			DESCRIPTION
					"The average number of bytes received per second by the
					ethernet port identified by this entry during the most
					recent sampling period."
			::= { lpsEthernetPortRateEntry 2 }

		lpsEthernetPortRatePeakByteReceiveRate OBJECT-TYPE
			SYNTAX	INTEGER
			ACCESS	read-only
			STATUS	mandatory
			DESCRIPTION
					"The peak value of lpsEthernetPortRateByteReceiveRate
					since the system was last initialized for the ethernet
					port identified by this entry."
			::= { lpsEthernetPortRateEntry 3 }

		lpsEthernetPortRateFrameReceiveRate OBJECT-TYPE
			SYNTAX	INTEGER
			ACCESS	read-only
			STATUS	mandatory
			DESCRIPTION
					"The average number of frames received per second by the
					ethernet port identified by this entry during the most
					recent sampling period."
			::= { lpsEthernetPortRateEntry 4 }

		lpsEthernetPortRatePeakFrameReceiveRate OBJECT-TYPE
			SYNTAX	INTEGER
			ACCESS	read-only
			STATUS	mandatory
			DESCRIPTION
					"The peak value of lpsEthernetPortRateFrameReceiveRate
					since the system was last initialized for the ethernet
					port identified by this entry."
			::= { lpsEthernetPortRateEntry 5 }

		lpsEthernetPortRateByteTransmitRate OBJECT-TYPE
			SYNTAX	INTEGER
			ACCESS	read-only
			STATUS	mandatory
			DESCRIPTION
					"The average number of bytes transmitted per second by the
					ethernet port identified by this entry during the most
					recent sampling period."
			::= { lpsEthernetPortRateEntry 6 }

		lpsEthernetPortRatePeakByteTransmitRate OBJECT-TYPE
			SYNTAX	INTEGER
			ACCESS	read-only
			STATUS	mandatory
			DESCRIPTION
					"The peak value of lpsEthernetPortRateByteTransmitRate
					since the system was last initialized for the ethernet
					port identified by this entry."
			::= { lpsEthernetPortRateEntry 7 }

		lpsEthernetPortRateFrameTransmitRate OBJECT-TYPE
			SYNTAX	INTEGER
			ACCESS	read-only
			STATUS	mandatory
			DESCRIPTION
					"The average number of frames transmitted per second by the
					ethernet port identified by this entry during the most
					recent sampling period."
			::= { lpsEthernetPortRateEntry 8 }

		lpsEthernetPortRatePeakFrameTransmitRate OBJECT-TYPE
			SYNTAX	INTEGER
			ACCESS	read-only
			STATUS	mandatory
			DESCRIPTION
					"The peak value of lpsEthernetPortRateFrameTransmitRate
					since the system was last initialized for the ethernet
					port identified by this entry."
			::= { lpsEthernetPortRateEntry 9 }

		-- The LANplex Systems MIB SMT group.  Implementation of this group is
		-- mandatory for agents which manage SMT resources.

		lpsSmtCount OBJECT-TYPE
			SYNTAX	INTEGER
			ACCESS	read-only
			STATUS	mandatory
			DESCRIPTION
					"The count of SMTs managed by this agent."
			::= { lpsSmt 1 }

		-- The LANplex Systems MIB SMT table.
		-- This table is currently unused and is reserved for future use.
		-- { lpsSmt 2 }

		-- The LANplex Systems MIB SMT FDDI MAC table.
		-- This table is currently unused and is reserved for future use.
		-- { lpsSmt 3 }

		-- The LANplex Systems MIB SMT FDDI MAC beacon table.

		lpsSmtFddiMacBeaconTable OBJECT-TYPE
			SYNTAX	SEQUENCE OF LpsSmtFddiMacBeaconEntry
			ACCESS	not-accessible
			STATUS	mandatory
			DESCRIPTION
					"A list of FDDI MAC beacon entries.  A single entry exists
					in this list for each FDDI MAC, managed by this agent,
					which supports MAC beacon history."
			::= { lpsSmt 4 }

		lpsSmtFddiMacBeaconEntry OBJECT-TYPE
			SYNTAX	LpsSmtFddiMacBeaconEntry
			ACCESS	not-accessible
			STATUS	mandatory
			DESCRIPTION
					"An FDDI MAC beacon entry contains information about a
					particular FDDI MAC's beacon history."
			INDEX	{ lpsSmtFddiMacBeaconSmtIndex,
					lpsSmtFddiMacBeaconIndex }
			::= { lpsSmtFddiMacBeaconTable 1 }

		LpsSmtFddiMacBeaconEntry ::=
			SEQUENCE {
				lpsSmtFddiMacBeaconSmtIndex
					INTEGER,
				lpsSmtFddiMacBeaconIndex
					INTEGER,
				lpsSmtFddiMacBeaconHistory
					OCTET STRING
			}

		lpsSmtFddiMacBeaconSmtIndex OBJECT-TYPE
			SYNTAX	INTEGER
			ACCESS	read-only
			STATUS	mandatory
			DESCRIPTION
					"The index of the SMT instance identified by this entry,
					relative to this agent."
			::= { lpsSmtFddiMacBeaconEntry 1 }

		lpsSmtFddiMacBeaconIndex OBJECT-TYPE
			SYNTAX	INTEGER
			ACCESS	read-only
			STATUS	mandatory
			DESCRIPTION
					"The index of the FDDI MAC identified by this entry,
					within the SMT identified by this entry."
			::= { lpsSmtFddiMacBeaconEntry 2 }

		lpsSmtFddiMacBeaconHistory OBJECT-TYPE
			SYNTAX	OCTET STRING (SIZE (0..256))
			ACCESS	read-only
			STATUS	mandatory
			DESCRIPTION
					"This object gives a history of the most recent beacon
					information received on the FDDI MAC identified by this
					entry.  It can contain up to a maximum of eight records.
					Each record is of the form:
						source MAC:				6 bytes
						beacon data length:		2 bytes.
						beacon data:			0-16 bytes."
			::= { lpsSmtFddiMacBeaconEntry 3 }

		-- The LANplex Systems MIB SMT FDDI MAC rate table.

		lpsSmtFddiMacRateTable OBJECT-TYPE
			SYNTAX	SEQUENCE OF LpsSmtFddiMacRateEntry
			ACCESS	not-accessible
			STATUS	mandatory
			DESCRIPTION
					"A list of FDDI MAC rate entries.  A single entry exists
					in this list for each FDDI MAC, managed by this agent,
					which supports rate statistics."
			::= { lpsSmt 5 }

		lpsSmtFddiMacRateEntry OBJECT-TYPE
			SYNTAX	LpsSmtFddiMacRateEntry
			ACCESS	not-accessible
			STATUS	mandatory
			DESCRIPTION
					"An FDDI MAC rate entry contains rate statistics for a
					particular FDDI MAC managed by this agent.  Rate statistics
					are calculated based on a one second sampling interval."
			INDEX	{ lpsSmtFddiMacRateSmtIndex,
					lpsSmtFddiMacRateIndex }
			::= { lpsSmtFddiMacRateTable 1 }

		LpsSmtFddiMacRateEntry ::=
			SEQUENCE {
				lpsSmtFddiMacRateSmtIndex
					INTEGER,
				lpsSmtFddiMacRateIndex
					INTEGER,
				lpsSmtFddiMacRateByteReceiveRate
					INTEGER,
				lpsSmtFddiMacRatePeakByteReceiveRate
					INTEGER,
				lpsSmtFddiMacRateFrameReceiveRate
					INTEGER,
				lpsSmtFddiMacRatePeakFrameReceiveRate
					INTEGER,
				lpsSmtFddiMacRateByteTransmitRate
					INTEGER,
				lpsSmtFddiMacRatePeakByteTransmitRate
					INTEGER,
				lpsSmtFddiMacRateFrameTransmitRate
					INTEGER,
				lpsSmtFddiMacRatePeakFrameTransmitRate
					INTEGER
			}

		lpsSmtFddiMacRateSmtIndex OBJECT-TYPE
			SYNTAX	INTEGER
			ACCESS	read-only
			STATUS	mandatory
			DESCRIPTION
					"The index of the SMT instance identified by this entry,
					relative to this agent."
			::= { lpsSmtFddiMacRateEntry 1 }

		lpsSmtFddiMacRateIndex OBJECT-TYPE
			SYNTAX	INTEGER
			ACCESS	read-only
			STATUS	mandatory
			DESCRIPTION
					"The index of the FDDI MAC identified by this entry, within
					the SMT identified by this entry."
			::= { lpsSmtFddiMacRateEntry 2 }

		lpsSmtFddiMacRateByteReceiveRate OBJECT-TYPE
			SYNTAX	INTEGER
			ACCESS	read-only
			STATUS	mandatory
			DESCRIPTION
					"The average number of bytes received per second by the
					FDDI MAC identified by this entry during the most recent
					sampling period."
			::= { lpsSmtFddiMacRateEntry 3 }

		lpsSmtFddiMacRatePeakByteReceiveRate OBJECT-TYPE
			SYNTAX	INTEGER
			ACCESS	read-only
			STATUS	mandatory
			DESCRIPTION
					"The peak value of lpsSmtFddiMacByteReceiveRate since the
					system was last initialized for the FDDI MAC identified by
					this entry."
			::= { lpsSmtFddiMacRateEntry 4 }

		lpsSmtFddiMacRateFrameReceiveRate OBJECT-TYPE
			SYNTAX	INTEGER
			ACCESS	read-only
			STATUS	mandatory
			DESCRIPTION
					"The average number of frames received per second by the
					FDDI MAC identified by this entry during the most recent
					sampling period."
			::= { lpsSmtFddiMacRateEntry 5 }

		lpsSmtFddiMacRatePeakFrameReceiveRate OBJECT-TYPE
			SYNTAX	INTEGER
			ACCESS	read-only
			STATUS	mandatory
			DESCRIPTION
					"The peak value of lpsSmtFddiMacRateFrameReceiveRate since
					the system was last initialized for the FDDI MAC identified
					by this entry."
			::= { lpsSmtFddiMacRateEntry 6 }

		lpsSmtFddiMacRateByteTransmitRate OBJECT-TYPE
			SYNTAX	INTEGER
			ACCESS	read-only
			STATUS	mandatory
			DESCRIPTION
					"The average number of bytes transmitted per second by the
					FDDI MAC identified by this entry during the most recent
					sampling period."
			::= { lpsSmtFddiMacRateEntry 7 }

		lpsSmtFddiMacRatePeakByteTransmitRate OBJECT-TYPE
			SYNTAX	INTEGER
			ACCESS	read-only
			STATUS	mandatory
			DESCRIPTION
					"The peak value of lpsSmtFddiMacByteTransmitRate since the
					system was last initialized for the FDDI MAC identified by
					this entry."
			::= { lpsSmtFddiMacRateEntry 8 }

		lpsSmtFddiMacRateFrameTransmitRate OBJECT-TYPE
			SYNTAX	INTEGER
			ACCESS	read-only
			STATUS	mandatory
			DESCRIPTION
					"The average number of frames transmitted per second by
					the FDDI MAC identified by this entry during the most
					recent sampling period."
			::= { lpsSmtFddiMacRateEntry 9 }

		lpsSmtFddiMacRatePeakFrameTransmitRate OBJECT-TYPE
			SYNTAX	INTEGER
			ACCESS	read-only
			STATUS	mandatory
			DESCRIPTION
					"The peak value of lpsSmtFddiMacFrameTransmitRate since the
					system was last initialized for the FDDI MAC identified by
					this entry."
			::= { lpsSmtFddiMacRateEntry 10 }

		-- The LANplex Systems MIB SMT FDDI port table.

		lpsSmtFddiPortTable OBJECT-TYPE
			SYNTAX	SEQUENCE OF LpsSmtFddiPortEntry
			ACCESS	not-accessible
			STATUS	mandatory
			DESCRIPTION
					"A list of FDDI port entries.  A single entry exists in
					this list for each FDDI port managed by this agent."
			::= { lpsSmt 6 }

		lpsSmtFddiPortEntry OBJECT-TYPE
			SYNTAX	LpsSmtFddiPortEntry
			ACCESS	not-accessible
			STATUS	mandatory
			DESCRIPTION
					"An FDDI port entry contains information about a particular
					FDDI port managed by this agent."
			INDEX	{ lpsSmtFddiPortSmtIndex,
					lpsSmtFddiPortIndex }
			::= { lpsSmtFddiPortTable 1 }

		LpsSmtFddiPortEntry ::=
			SEQUENCE {
				lpsSmtFddiPortSmtIndex
					INTEGER,
				lpsSmtFddiPortIndex
					INTEGER,
				lpsSmtFddiPortLocationType
					INTEGER,
				lpsSmtFddiPortLocationTypeIndex
					INTEGER,
				lpsSmtFddiPortLocationLocalIndex
					INTEGER,
				lpsSmtFddiPortLabel
					DisplayString
			}

		lpsSmtFddiPortSmtIndex OBJECT-TYPE
			SYNTAX	INTEGER
			ACCESS	read-only
			STATUS	mandatory
			DESCRIPTION
					"The index of the SMT instance identified by this entry,
					relative to this agent."
			::= { lpsSmtFddiPortEntry 1 }

		lpsSmtFddiPortIndex OBJECT-TYPE
			SYNTAX	INTEGER
			ACCESS	read-only
			STATUS	mandatory
			DESCRIPTION
					"The index of the FDDI port identified by this entry,
					within the SMT identified by this entry."
			::= { lpsSmtFddiPortEntry 2 }

		lpsSmtFddiPortLocationType OBJECT-TYPE
			SYNTAX	INTEGER {
						other(1),
						modularSlot(2),
						chassis(3),
						modularCard(4)
					}
			ACCESS	read-only
			STATUS	mandatory
			DESCRIPTION
					"The type of location where the FDDI port identified by
					this entry is physically located."
			::= { lpsSmtFddiPortEntry 3 }

		lpsSmtFddiPortLocationTypeIndex OBJECT-TYPE
			SYNTAX	INTEGER
			ACCESS	read-only
			STATUS	mandatory
			DESCRIPTION
					"The index of the location identified by the corresponding
					instance of lpsSmtFddiPortLocationType where the FDDI port
					identified by this entry is physically located."
			::= { lpsSmtFddiPortEntry 4 }

		lpsSmtFddiPortLocationLocalIndex OBJECT-TYPE
			SYNTAX	INTEGER
			ACCESS	read-only
			STATUS	mandatory
			DESCRIPTION
					"The local index of the FDDI port identified by this
					entry relative to the location specified by the
					corresponding values of lpsSmtFddiPortLocationType and
					lpsSmtFddiPortLocationTypeIndex."
			::= { lpsSmtFddiPortEntry 5 }

		lpsSmtFddiPortLabel OBJECT-TYPE
			SYNTAX	DisplayString (SIZE (0..31))
			ACCESS	read-write
			STATUS	mandatory
			DESCRIPTION
					"An ASCII text string describing the FDDI port identified
					by this entry."
			::= { lpsSmtFddiPortEntry 6 }

		-- The LANplex Systems MIB bridge group.  Implementation of this group
		-- is mandatory for agents which manage bridge resources.

		lpsBridgeCount OBJECT-TYPE
			SYNTAX	INTEGER
			ACCESS	read-only
			STATUS	mandatory
			DESCRIPTION
					"The count of bridges managed by this agent."
			::= { lpsBridge 1 }

		-- The LANplex Systems MIB bridge table.

		lpsBridgeTable OBJECT-TYPE
			SYNTAX	SEQUENCE OF LpsBridgeEntry
			ACCESS	not-accessible
			STATUS	mandatory
			DESCRIPTION
					"A list of bridge entries.  A single entry exists in this
					list for each bridge managed by this agent."
			::= { lpsBridge 2 }

		lpsBridgeEntry OBJECT-TYPE
			SYNTAX	LpsBridgeEntry
			ACCESS	not-accessible
			STATUS	mandatory
			DESCRIPTION
					"A bridge entry contains information about a particular
					bridge managed by this agent."
			INDEX	{ lpsBridgeIndex }
			::= { lpsBridgeTable 1 }
								
		LpsBridgeEntry ::=
			SEQUENCE {
				lpsBridgeIndex
					INTEGER,
				lpsBridgePortCount
					INTEGER,
				lpsBridgeAddressTableSize
					INTEGER,
				lpsBridgeAddressTableCount
					INTEGER,
				lpsBridgeAddressTablePeakCount
					INTEGER,
				lpsBridgeAddressThreshold
					INTEGER,
				lpsBridgeMode
					INTEGER,
				lpsBridgeBackbonePort
					INTEGER,
				lpsBridgeIpFragmentationEnabled
					INTEGER,
				lpsBridgeTrFddiTranslationMode
					INTEGER
			}


		lpsBridgeIndex OBJECT-TYPE
			SYNTAX	INTEGER
			ACCESS	read-only
			STATUS	mandatory
			DESCRIPTION
					"The index of the bridge identified by this entry,
					relative to this agent."
			::= { lpsBridgeEntry 1 }

		lpsBridgePortCount OBJECT-TYPE
			SYNTAX	INTEGER
			ACCESS	read-only
			STATUS	mandatory
			DESCRIPTION
					"The number of bridge ports that the bridge identified by
					this entry controls."
			::= { lpsBridgeEntry 2 }

		lpsBridgeAddressTableSize OBJECT-TYPE
			SYNTAX	INTEGER 
			ACCESS	read-only
			STATUS	mandatory
			DESCRIPTION
					"The size of the address table for the bridge identified
					by this entry."
			::= { lpsBridgeEntry 3 }

		lpsBridgeAddressTableCount OBJECT-TYPE
			SYNTAX	INTEGER 
			ACCESS	read-only
			STATUS	mandatory
			DESCRIPTION
					"The current count of addresses in the address table for
					the bridge identified by this entry."
			::= { lpsBridgeEntry 4 }

		lpsBridgeAddressTablePeakCount OBJECT-TYPE
			SYNTAX	INTEGER 
			ACCESS	read-only
			STATUS	mandatory
			DESCRIPTION
					"The peak count of addresses in the address table for the
					bridge identified by this entry, since the system was last
					initialized."
			::= { lpsBridgeEntry 5 }

		lpsBridgeAddressThreshold OBJECT-TYPE
			SYNTAX	INTEGER 
			ACCESS	read-write
			STATUS	mandatory
			DESCRIPTION
					"A reporting threshold for the total number of addresses
					known for the bridge identified by this entry.  When this
					threshold is reached, the event
					lpsBridgeAddressThresholdEvent is generated.  The range of
					valid values for setting this object is between 1 and the
					corresponding value reported by lpsBridgeAddressTableSize
					+ 1 (Note that this range applies to values issued in set
					requests.  The current value may be outside this range,
					for example if the corresponding value of lpsBridgeMode is
					changed). Setting this object to one greater than the
					address table size disables the generation of
					lpsBridgeAddressThresholdEvents since the limit will never
					be reached."
			::= { lpsBridgeEntry 6 }

		lpsBridgeMode OBJECT-TYPE
			SYNTAX	INTEGER {
					expressMode(1),
					ieee8021dBridgeMode(2),
					notSupported(3),
					ieee8021dSRTBridgeMode(4),
					ieee8021dSRBridgeMode(5),
					ibmSRBridgeMode(6),
					srtBBridgeMode(7),
					srExpressBridgeMode(8)
					}
			ACCESS	read-write
			STATUS	mandatory
			DESCRIPTION
					"The operational mode of the bridge identified by this
					entry.  Note that bridges which report notSupported(3)
					will not support sets of this object, and that the value
					notSupported(3) is not a valid value for a set operation."
			::= { lpsBridgeEntry 7 }

		lpsBridgeBackbonePort OBJECT-TYPE
			SYNTAX	INTEGER
			ACCESS	read-write
			STATUS	mandatory
			DESCRIPTION
					"The number of the port selected as the backbone segment
					port when the corresponding value of lpsBridgeMode is
					is expressMode(1).  The value of this object can range
					from 1 to the corresponding value of lpsBridgePortCount,
					however, some bridges may support only a subset of ports
					as backbone ports.  If the corresponding value of
					lpsBridgeMode is not expressMode(1), the value of this
					object is ignored."
			::= { lpsBridgeEntry 8 }

		lpsBridgeIpFragmentationEnabled OBJECT-TYPE
			SYNTAX	INTEGER {
						true(1),
						false(2),
						notSupported(3)
					}
			ACCESS	read-write
			STATUS	mandatory
			DESCRIPTION
					"A flag indicating whether or not IP fragmentation is
					enabled on this bridge.  Note that bridges which report
					notSupported(3) will not support sets of this object, and
					that the value notSupported(3) is not a valid value for a
					set operation."
			::= { lpsBridgeEntry 9 }

		lpsBridgeTrFddiTranslationMode OBJECT-TYPE
			SYNTAX	INTEGER {
					native(1),
					backbone(2)
					}
			ACCESS	read-write
			STATUS	mandatory
			DESCRIPTION
					"The mode used to describe whether the embedded MAC
					addresses are byte-conjugated in order to convert them
					from Token Ring format to native FDDI format (and vice
					versa), or whether they are left alone (used for traffic
					flowing	across a FDDI backbone to/from Token Ring end
					stations)."
			::= { lpsBridgeEntry 10 }

		-- The LANplex Systems MIB bridge port table.

		lpsBridgePortTable OBJECT-TYPE
			SYNTAX	SEQUENCE OF LpsBridgePortEntry
			ACCESS	not-accessible
			STATUS	mandatory
			DESCRIPTION
					"A list of bridge port entries.  A single entry exists in
					this list for each bridge port managed by this agent."
			::= { lpsBridge 3 }

		lpsBridgePortEntry OBJECT-TYPE
			SYNTAX	LpsBridgePortEntry
			ACCESS	not-accessible
			STATUS	mandatory
			DESCRIPTION
					"A bridge port entry contains information about a
					particular bridge port managed by this agent."
			INDEX	{ lpsBridgePortBridgeIndex,
					lpsBridgePortIndex }
			::= { lpsBridgePortTable 1 }

		LpsBridgePortEntry ::=
			SEQUENCE {
				lpsBridgePortBridgeIndex
					INTEGER,
				lpsBridgePortIndex
					INTEGER,
				lpsBridgePortIfIndex
					INTEGER,
				lpsBridgePortReceiveMulticastLimit
					INTEGER,
				lpsBridgePortAddressAction
					INTEGER,
				lpsBridgePortSpanningTreeFrameReceivedCounts
					Counter,
				lpsBridgePortReceiveBlockedDiscards
					Counter,
				lpsBridgePortReceiveMulticastLimitExceededs
					Counter,
				lpsBridgePortReceiveMulticastLimitExceededDiscards
					Counter,
				lpsBridgePortReceiveSecurityDiscards
					Counter,
				lpsBridgePortReceiveUnknownDiscards
					Counter,
				lpsBridgePortReceiveOtherDiscards
					Counter,
				lpsBridgePortReceiveErrorDiscards
					Counter,
				lpsBridgePortSameSegmentDiscards
					Counter,
				lpsBridgePortTransmitBlockedDiscards
					Counter,
				lpsBridgePortReceiveAllPathFilteredFrames
					Counter,
				lpsBridgePortReceiveMulticastPathFilteredFrames
					Counter,
				lpsBridgePortTransmitAllPathFilteredFrames
					Counter,
				lpsBridgePortTransmitMulticastPathFilteredFrames
					Counter,
				lpsBridgePortForwardedUnicastFrames
					Counter,
				lpsBridgePortForwardedUnicastOctets
					Counter,
				lpsBridgePortForwardedMulticastFrames
					Counter,
				lpsBridgePortForwardedMulticastOctets
					Counter,
				lpsBridgePortFloodedUnicastFrames
					Counter,
				lpsBridgePortFloodedUnicastOctets
					Counter
			}

		lpsBridgePortBridgeIndex OBJECT-TYPE
			SYNTAX	INTEGER
			ACCESS	read-only
			STATUS	mandatory
			DESCRIPTION
					"The index of the bridge identified by this entry,
					relative to this agent."
			::= { lpsBridgePortEntry 1 }

		lpsBridgePortIndex OBJECT-TYPE
			SYNTAX	INTEGER
			ACCESS	read-only
			STATUS	mandatory
			DESCRIPTION
					"The index of the bridge port identified by this entry,
					within the bridge identified by this entry."
			::= { lpsBridgePortEntry 2 }

		lpsBridgePortIfIndex OBJECT-TYPE
			SYNTAX	INTEGER
			ACCESS	read-only
			STATUS	mandatory
			DESCRIPTION
					"The value of the MIB-II ifIndex corresponding to the
					bridge port identified by this entry."
			::= { lpsBridgePortEntry 3 }

		lpsBridgePortReceiveMulticastLimit OBJECT-TYPE
			SYNTAX	INTEGER (0..65535)
			ACCESS	read-write
			STATUS	mandatory
			DESCRIPTION
					"The maximum number of multicast frames per second that
					can be received in the sample interval.  The sample
					interval is one second.  The default value for this object
					is zero which implies an infinite rate."
			::= { lpsBridgePortEntry 4 }

		lpsBridgePortAddressAction OBJECT-TYPE
			SYNTAX	INTEGER {
						other(1),
						freezeAddress(2),
						flushAddress(3),
						flushDynamicAddress(4)
					}
			ACCESS	read-write
			STATUS	mandatory
			DESCRIPTION
					"This object, when read, always returns the value
					other(1).  The behavior of setting this object to each of
					the acceptable values is as follows:

						freezeAddress:	causes all the learned dynamic
										addresses to be converted into static
										addresses.

						flushAddress:   causes all the addresses to be flushed
										from the address list for the bridge
										port identified by this entry.

						flushDynamicAddress:
										causes all dynamic addresses to be
										flushed from the address list for the
										bridge port identified by this entry."
			::= { lpsBridgePortEntry 5 }

		lpsBridgePortSpanningTreeFrameReceivedCounts OBJECT-TYPE
			SYNTAX	Counter
			ACCESS	read-only
			STATUS	mandatory
			DESCRIPTION
					"The number of spanning tree frames received by the
					bridge port identified by this entry."
			::= { lpsBridgePortEntry 6 }

		lpsBridgePortReceiveBlockedDiscards OBJECT-TYPE
			SYNTAX	Counter
			ACCESS	read-only
			STATUS	mandatory
			DESCRIPTION
					"The number of frames discarded by the bridge port
					identified by this entry because the receiving bridge port
					was not in the 'forwarding' state."
			::= { lpsBridgePortEntry 7 }

		lpsBridgePortReceiveMulticastLimitExceededs OBJECT-TYPE
			SYNTAX	Counter
			ACCESS	read-only
			STATUS	mandatory
			DESCRIPTION
					"The number of times the value of
					lpsBridgePortReceiveMulticastLimit was exceeded for the
					port identified by this entry."
			::= { lpsBridgePortEntry 8 }

		lpsBridgePortReceiveMulticastLimitExceededDiscards OBJECT-TYPE
			SYNTAX	Counter
			ACCESS	read-only
			STATUS	mandatory
			DESCRIPTION
					"The number of multicast/broadcast frames discarded by the
					bridge port identified by this entry because the
					corresponding value of lpsBridgePortReceiveMulticastLimit
					was exceeded."
			::= { lpsBridgePortEntry 9 }

		lpsBridgePortReceiveSecurityDiscards OBJECT-TYPE
			SYNTAX	Counter
			ACCESS	read-only
			STATUS	mandatory
			DESCRIPTION
					"The number of frames discarded by the bridge port
					identified by this entry because they contained source
					addresses which were statically configured on another
					bridge port.  A statically configured address (station),
					which is not allowed to move, appears to have moved."
			::= { lpsBridgePortEntry 10 }

		lpsBridgePortReceiveUnknownDiscards OBJECT-TYPE
			SYNTAX	Counter
			ACCESS	read-only
			STATUS	mandatory
			DESCRIPTION
					"The number of frames discarded by the bridge port
					identified by this entry because the destination address
					was unknown.  Note that this counter is only valid for
					backbone ports, and only when the bridge is operating in
					express mode."
			::= { lpsBridgePortEntry 11 }

		lpsBridgePortReceiveOtherDiscards OBJECT-TYPE
			SYNTAX	Counter
			ACCESS	read-only
			STATUS	mandatory
			DESCRIPTION
					"The number of frames discarded by the bridge port
					identified by this entry because they contained either
					invalid (group) source addresses or source addresses
					belonging to this bridge (indicative of network loops)."
			::= { lpsBridgePortEntry 12 }

		lpsBridgePortReceiveErrorDiscards OBJECT-TYPE
			SYNTAX	Counter
			ACCESS	read-only
			STATUS	mandatory
			DESCRIPTION
					"The number of frames discarded by the bridge port
					identified by this entry because of internal bridge system
					errors (e.g., hardware and software address table
					discrepencies)."
			::= { lpsBridgePortEntry 13 }

		lpsBridgePortSameSegmentDiscards OBJECT-TYPE
			SYNTAX	Counter
			ACCESS	read-only
			STATUS	mandatory
			DESCRIPTION
					"The number of frames discarded by the bridge port
					identified by this entry because the destination address
					is known on the same network segment as the source address,
					i.e., the frame does not need to be bridged."
			::= { lpsBridgePortEntry 14 }

		lpsBridgePortTransmitBlockedDiscards OBJECT-TYPE
			SYNTAX	Counter
			ACCESS	read-only
			STATUS	mandatory
			DESCRIPTION
					"The number of frames discarded by the bridge port
					identified by this entry because the transmitting bridge
					port was not in the 'forwarding' state."
			::= { lpsBridgePortEntry 15 }

		lpsBridgePortReceiveAllPathFilteredFrames OBJECT-TYPE
			SYNTAX	Counter
			ACCESS	read-only
			STATUS	mandatory
			DESCRIPTION
					"The number of frames discarded by the bridge port
					identified by this entry due to user defined receive all
					path filters."
			::= { lpsBridgePortEntry 16 }

		lpsBridgePortReceiveMulticastPathFilteredFrames OBJECT-TYPE
			SYNTAX	Counter
			ACCESS	read-only
			STATUS	mandatory
			DESCRIPTION
					"The number of frames discarded by the bridge port
					identified by this entry due to user defined receive
					multicast path filters."
			::= { lpsBridgePortEntry 17 }

		lpsBridgePortTransmitAllPathFilteredFrames OBJECT-TYPE
			SYNTAX	Counter
			ACCESS	read-only
			STATUS	mandatory
			DESCRIPTION
					"The number of frames discarded by the bridge port
					identified by this entry due to user defined transmit all
					path filters."
			::= { lpsBridgePortEntry 18 }

		lpsBridgePortTransmitMulticastPathFilteredFrames OBJECT-TYPE
			SYNTAX	Counter
			ACCESS	read-only
			STATUS	mandatory
			DESCRIPTION
					"The number of frames discarded by the bridge port
					identified by this entry due to user defined transmit
					multicast path filters."
			::= { lpsBridgePortEntry 19 }

		lpsBridgePortForwardedUnicastFrames OBJECT-TYPE
			SYNTAX	Counter
			ACCESS	read-only
			STATUS	mandatory
			DESCRIPTION
					"The number of unicast frames which this port forwarded
					to a single destination port."
			::= { lpsBridgePortEntry 20 }

		lpsBridgePortForwardedUnicastOctets OBJECT-TYPE
			SYNTAX	Counter
			ACCESS	read-only
			STATUS	mandatory
			DESCRIPTION
					"The number of octets contained in unicast frames
					which this port forwarded to a single destination port."
			::= { lpsBridgePortEntry 21 }

		lpsBridgePortForwardedMulticastFrames OBJECT-TYPE
			SYNTAX	Counter
			ACCESS	read-only
			STATUS	mandatory
			DESCRIPTION
					"The number of multicast frames which this port forwarded."
			::= { lpsBridgePortEntry 22 }

		lpsBridgePortForwardedMulticastOctets OBJECT-TYPE
			SYNTAX	Counter
			ACCESS	read-only
			STATUS	mandatory
			DESCRIPTION
					"The number of octets contained in multicast frames which
					this port forwarded."
			::= { lpsBridgePortEntry 23 }

		lpsBridgePortFloodedUnicastFrames OBJECT-TYPE
			SYNTAX	Counter
			ACCESS	read-only
			STATUS	mandatory
			DESCRIPTION
					"The number of unicast frames which this port flooded to
					all other ports in the bridge."
			::= { lpsBridgePortEntry 24 }

		lpsBridgePortFloodedUnicastOctets OBJECT-TYPE
			SYNTAX	Counter
			ACCESS	read-only
			STATUS	mandatory
			DESCRIPTION
					"The number of octets contained in unicast frames which
					this port flooded to all other ports in the bridge."
			::= { lpsBridgePortEntry 25 }

		-- The LANplex Systems MIB bridge port pair table

		lpsBridgePortPairTable OBJECT-TYPE
			SYNTAX	SEQUENCE OF LpsBridgePortPairEntry
			ACCESS	not-accessible
			STATUS	mandatory
			DESCRIPTION
					"A list of bridge port pair statistics information.  A
					single entry exists in this list for each bridge port pair
					combination within each bridge managed by this agent."
			::= { lpsBridge 4 }

		lpsBridgePortPairEntry OBJECT-TYPE
			SYNTAX	LpsBridgePortPairEntry
			ACCESS	not-accessible
			STATUS	mandatory
			DESCRIPTION
					"A bridge port pair entry contains statistics information
					for a port pair within the same bridge.  The port paring
					consists of a receiving port indicated by the value of
					lpsBridgePortPairReceivePortIndex, and a destination port
					indicated by the corresponding value of
					lpsBridgePortPairDestinationPortIndex.  The corresponding
					value of lpsBridgePortPairBridgeIndex is the index of the
					bridge containing the port pair.  Note that no entries
					exist which are indexed with the same values for both
					lpsBridgePortPairReceivePortIndex and
					lpsBridgePortPairToDestinationPortIndex."
			INDEX	{ lpsBridgePortPairBridgeIndex,
					lpsBridgePortPairReceivePortIndex,
					lpsBridgePortPairDestinationPortIndex }
			::= { lpsBridgePortPairTable 1 }

		LpsBridgePortPairEntry ::=
			SEQUENCE {
				lpsBridgePortPairBridgeIndex
					INTEGER,
				lpsBridgePortPairReceivePortIndex
					INTEGER,
				lpsBridgePortPairDestinationPortIndex
					INTEGER,
				lpsBridgePortPairForwardedToUnicastFrames
					Counter,
				lpsBridgePortPairForwardedToUnicastOctets
					Counter
			}

		lpsBridgePortPairBridgeIndex OBJECT-TYPE
			SYNTAX	INTEGER
			ACCESS	read-only
			STATUS	mandatory
			DESCRIPTION
					"The index of the bridge identified by this entry,
					relative to this agent."
			::= { lpsBridgePortPairEntry 1 }

		lpsBridgePortPairReceivePortIndex OBJECT-TYPE
			SYNTAX	INTEGER
			ACCESS	read-only
			STATUS	mandatory
			DESCRIPTION
					"The index of the receiving bridge port identified by this
					entry, within the bridge identified by this entry."
			::= { lpsBridgePortPairEntry 2 }

		lpsBridgePortPairDestinationPortIndex OBJECT-TYPE
			SYNTAX	INTEGER
			ACCESS	read-only
			STATUS	mandatory
			DESCRIPTION
					"The index of the destination bridge port identified by
					this entry, within the bridge identified by this entry."
			::= { lpsBridgePortPairEntry 3 }

		lpsBridgePortPairForwardedToUnicastFrames OBJECT-TYPE
			SYNTAX	Counter
			ACCESS	read-only
			STATUS	mandatory
			DESCRIPTION
					"The number of unicast frames forwarded from the receiving
					bridge port identified by this entry to the destination
					bridge port identified by this entry.  Note that this count
					only includes frames which were uniquely forwarded to the
					destination port, frames which were flooded are not included."
			::= { lpsBridgePortPairEntry 4 }

		lpsBridgePortPairForwardedToUnicastOctets OBJECT-TYPE
			SYNTAX	Counter
			ACCESS	read-only
			STATUS	mandatory
			DESCRIPTION
					"The number of octets contained in unicast frames forwarded
					from the receiving bridge port identified by this entry to
					the destination bridge port identified by this entry.  Note
					that this count only includes frames which were uniquely
					forwarded to the destination port, frames which were flooded
					are not included."
			::= { lpsBridgePortPairEntry 5 }

		-- The LANplex Systems MIB bridge port address table

		lpsBridgePortAddressTable OBJECT-TYPE
			SYNTAX	SEQUENCE OF LpsBridgePortAddressEntry
			ACCESS	not-accessible
			STATUS	mandatory
			DESCRIPTION
					"A list of bridge port address information.  A single
					entry exists in this list for each learned address,
					accross all bridge ports and all bridges managed by this
					agent."
			::= { lpsBridge 5 }

		lpsBridgePortAddressEntry OBJECT-TYPE
			SYNTAX	LpsBridgePortAddressEntry
			ACCESS	not-accessible
			STATUS	mandatory
			DESCRIPTION
					"An bridge port address entry contains information about a
					particular bridge port address.  To create a new entry,
					set an instance of lpsBridgePortAddressRemoteAddress with
					the address index portion of the instance set to 0, to a
					valid value.  To remove an entry, set the instance of the
					lpsBridgePortAddressType for the entry to invalid(2)."
			INDEX	{ lpsBridgePortAddressBridgeIndex, 
					lpsBridgePortAddressPortIndex, 
					lpsBridgePortAddressIndex }
			::= { lpsBridgePortAddressTable 1 }

		LpsBridgePortAddressEntry ::=
			SEQUENCE {
				lpsBridgePortAddressBridgeIndex
					INTEGER,
				lpsBridgePortAddressPortIndex
					INTEGER,
				lpsBridgePortAddressIndex
					INTEGER,
				lpsBridgePortAddressRemoteAddress
					OCTET STRING,
				lpsBridgePortAddressType
					INTEGER,
				lpsBridgePortAddressIsStatic
					INTEGER,
				lpsBridgePortAddressStaticPort
					INTEGER,
				lpsBridgePortAddressAge
					INTEGER
			}

		lpsBridgePortAddressBridgeIndex OBJECT-TYPE
			SYNTAX	INTEGER
			ACCESS	read-only
			STATUS	mandatory
			DESCRIPTION
					"The index of the bridge identified by this entry,
					relative to this agent."
			::= { lpsBridgePortAddressEntry 1 }

		lpsBridgePortAddressPortIndex OBJECT-TYPE
			SYNTAX	INTEGER
			ACCESS	read-only
			STATUS	mandatory
			DESCRIPTION
					"The index of the bridge port identified by this entry,
					within the bridge identified by this entry."
			::= { lpsBridgePortAddressEntry 2 }

		lpsBridgePortAddressIndex OBJECT-TYPE
			SYNTAX	INTEGER
			ACCESS	read-only
			STATUS	mandatory
			DESCRIPTION
					"The index of this address entry within the bridge address
					table for the bridge identified by this entry.  This index
					ranges from 1 to the corresponding value of
					lpsBridgeAddressTableSize." 
			::= { lpsBridgePortAddressEntry 3 }

		lpsBridgePortAddressRemoteAddress OBJECT-TYPE
			SYNTAX	OCTET STRING (SIZE (6)) -- 6 octet address in "canonical" order
			ACCESS	read-write
			STATUS	mandatory
			DESCRIPTION
					"The remote MAC address detected on the bridge port
					identified by to this entry.  Setting this object results
					in an attempt to create a new entry in the table.  Since
					the value of lpsBridgePortAddressIndex is determined
					automatically internal to the bridge, a set is only
					successful if the index value specified for
					lpsBridgePortAddressIndex is zero.  A get-next
					using the values of lpsBridgePortAddressTypeIndex and
					lpsBridgePortAddressPortIndex can be used to determine the
					address index assigned to the newly added address entry."
			::= { lpsBridgePortAddressEntry 4 }

		lpsBridgePortAddressType OBJECT-TYPE
			SYNTAX INTEGER {
						valid(1),
						invalid(2)
					}
			ACCESS	read-write
			STATUS	mandatory
			DESCRIPTION
					"This object, when read, always returns the value valid(1).
					Setting this object to invalid(2) will remove the
					corresponding address entry from the table."
			::= { lpsBridgePortAddressEntry 5 }

		lpsBridgePortAddressIsStatic OBJECT-TYPE
			SYNTAX	INTEGER {
						isStatic(1),
						isDynamic(2)
					}
			ACCESS	read-write
			STATUS	mandatory
			DESCRIPTION
					"A value indicating whether this MAC address was
					statically configured or was dynamically learned.  Note
					that isStatic(1) it the only valid for set operations."
			::= { lpsBridgePortAddressEntry 6 }

		lpsBridgePortAddressStaticPort OBJECT-TYPE
			SYNTAX	INTEGER
			ACCESS	read-only
			STATUS	mandatory
			DESCRIPTION
					"If the corresponding value of the object 
					lpsBridgePortAddressIsStatic is isStatic(1), this object
					indicates the local bridge port index (as reported by
					lpsBridgePortLocalIndex) for which this address MAC was
					statically configured.  If the object
					lpsBridgePortAddressIsStatic has the value isDynamic(2),
					the value of this object is 0."
			::= { lpsBridgePortAddressEntry 7 }

		lpsBridgePortAddressAge OBJECT-TYPE
			SYNTAX	INTEGER
			ACCESS	read-only
			STATUS	mandatory
			DESCRIPTION
					"This object indicates the time, in seconds, elapsed since
					a packet containing this address as a source was last seen
					on the bridge port identified by this entry."
			::= { lpsBridgePortAddressEntry 8 }

		-- The LANplex Systems MIB IP router group.  Implementation of this
		-- group is mandatory for agents which manage IP router resources.
		-- This group is reserved for future use.

		-- The LANplex Systems MIB networking monitoring group.  Implementation
		-- of this group is manadatory for all agents which manage bridge
		-- resources that support network monitoring.

		-- The LANplex Systems MIB network analyzer table.

		lpsNetworkAnalyzerTable OBJECT-TYPE
			SYNTAX	SEQUENCE OF LpsNetworkAnalyzerTableEntry
			ACCESS	not-accessible
			STATUS	mandatory
			DESCRIPTION
					"A list of analyzer entries.  A single entry exists in this
					list for each bridge port configured for an analyzer."
			::= { lpsNetworkMonitor 1 }

		lpsNetworkAnalyzerTableEntry OBJECT-TYPE
			SYNTAX	LpsNetworkAnalyzerTableEntry
			ACCESS	not-accessible
			STATUS	mandatory
			DESCRIPTION
					"An analyzer table entry contains information relating an
					analyzer port address to the bridge and port index for that
					analyzer.

					The effect of creating an entry for a particular port is
					to configure that port for monitoring.  A port which is
					configured for monitoring is no longer available for
					switching.  To create an entry, set the value of the
					lpsNetworkAnalyzerStatus object for a non-existent instance
					to valid(1).  The value of the lpsNetworkAnalyzerPhysicalAddress
					object for the new entry is filled in as a result of the
					creation.

					The effect of removing an entry for a particular port is to
					disable the port for monitoring.  The port is then available
					for switching.  To remove an entry, set the value of the
					corresponding instance of the lpsNetworkAnalyzerStatus object
					to invalid(2)."
			INDEX	{ lpsNetworkAnalyzerBridgeIndex,
					lpsNetworkAnalyzerBridgePortIndex}
			::= { lpsNetworkAnalyzerTable 1 }

		LpsNetworkAnalyzerTableEntry ::=
			SEQUENCE {
				lpsNetworkAnalyzerBridgeIndex
					INTEGER,
				lpsNetworkAnalyzerBridgePortIndex
					INTEGER,
				lpsNetworkAnalyzerPhysicalAddress
					OCTET STRING,
				lpsNetworkAnalyzerStatus
					INTEGER
			}

		lpsNetworkAnalyzerBridgeIndex OBJECT-TYPE
			SYNTAX	INTEGER
			ACCESS	read-only
			STATUS	mandatory
			DESCRIPTION
					"The index of the bridge relative to this agent where the
					analyzer identified by this entry is configured."
			::= { lpsNetworkAnalyzerTableEntry 1 }

		lpsNetworkAnalyzerBridgePortIndex OBJECT-TYPE
			SYNTAX	INTEGER
			ACCESS	read-only
			STATUS	mandatory
			DESCRIPTION
					"The index of the port relative to the bridge identified by
					this entry where the analyzer identified by this entry is
					configured."
			::= { lpsNetworkAnalyzerTableEntry 2 }

		lpsNetworkAnalyzerPhysicalAddress OBJECT-TYPE
			SYNTAX	OCTET STRING (SIZE (6)) -- 6 octet address in "canonical" order
			ACCESS	read-only
			STATUS	mandatory
			DESCRIPTION
					"The physical address of the bridge port identified by the
					corresponding values of lpsNetworkAnalyzerBridgeIndex and
					lpsNetworkAnayzerBridgePortIndex."
			::= { lpsNetworkAnalyzerTableEntry 3 }

		lpsNetworkAnalyzerStatus OBJECT-TYPE
			SYNTAX	INTEGER {
						valid(1),
						invalid(2)
					}
			ACCESS	read-write
			STATUS	mandatory
			DESCRIPTION
					"The status of the entry.  Setting the value of a non-existent
					instance of this object to valid(1) attempts to add the
					corresponding entry to the table.  The effect of adding an
					entry to the table is to configure the port for monitoring and
					to disable it for switching.  Setting an existing instance of
					this object to invalid(2) attempts to remove the corresponding
					entry from the table.  The effect of removing an entry from
					the table is to disable the port for monitoring and to make
					available for switching."
			::= { lpsNetworkAnalyzerTableEntry 4 }

		-- The LANplex Systems MIB network port monitor table.

		lpsNetworkPortMonitorTable OBJECT-TYPE
			SYNTAX	SEQUENCE OF LpsNetworkPortMonitorTableEntry
			ACCESS	not-accessible
			STATUS	mandatory
			DESCRIPTION
					"A list of monitor port entries.  A single entry exists in
					this for each bridge port being monitored."
			::= { lpsNetworkMonitor 2 }

		lpsNetworkPortMonitorTableEntry OBJECT-TYPE
			SYNTAX	LpsNetworkPortMonitorTableEntry
			ACCESS	not-accessible
			STATUS	mandatory
			DESCRIPTION
					"A port monitor table entry contains information relating a
					bridge port being monitored with the address of the analyzer
					which is being used to monitor the port.

					The effect of creating an entry for a particular port is to
					enable monitoring of that port by the analyzer specified.  To
					create an entry, set the value of the
					lpsNetworkPortMonitorAnalyzerAddress object to the address of
					the network analyzer port.  This value should be the same as
					the value of the lpsNetworkAnalyzerPhysicalAddress object for
					the analyzer.

					The effect of removing an entry for a particular port is to
					disable monitoring of that port.  To remove an entry, set the
					value of the corresponding instance of the
					lpsNetworkPortMonitorStatus object to invalid(2)."
			INDEX	{ lpsNetworkPortMonitorBridgeIndex,
					lpsNetworkPortMonitorBridgePortIndex }
			::= { lpsNetworkPortMonitorTable 1 }

		LpsNetworkPortMonitorTableEntry ::=
			SEQUENCE {
				lpsNetworkPortMonitorBridgeIndex
					INTEGER,
				lpsNetworkPortMonitorBridgePortIndex
					INTEGER,
				lpsNetworkPortMonitorAnalyzerAddress
					OCTET STRING,
				lpsNetworkPortMonitorStatus
					INTEGER
			}

		lpsNetworkPortMonitorBridgeIndex OBJECT-TYPE
			SYNTAX	INTEGER
			ACCESS	read-only
			STATUS	mandatory
			DESCRIPTION
					"The index of the bridge relative to this agent where the
					monitored port identified by this entry is located."
			::= { lpsNetworkPortMonitorTableEntry 1 }

		lpsNetworkPortMonitorBridgePortIndex OBJECT-TYPE
			SYNTAX	INTEGER
			ACCESS	read-only
			STATUS	mandatory
			DESCRIPTION
					"The index of the port which is being monitored relative to
					the bridge identified by this entry."
			::= { lpsNetworkPortMonitorTableEntry 2 }

		lpsNetworkPortMonitorAnalyzerAddress OBJECT-TYPE
			SYNTAX	OCTET STRING (SIZE (6)) -- 6 octet address in "canonical" order
			ACCESS	read-write
			STATUS	mandatory
			DESCRIPTION
					"The physical address of the port where the analyzer,
					which is monitoring the port identified by this entry, is
					located.  Setting the value of a non-existent instance of
					this object attempts to add an entry to the table.  The effect
					of adding an entry to the table is to enable monitoring of the
					port by the analyzer specified.  Setting the value of an
					existing instance of this object will switch the monitored
					port to the new analyzer address."
			::= { lpsNetworkPortMonitorTableEntry 3 }

		lpsNetworkPortMonitorStatus OBJECT-TYPE
			SYNTAX	INTEGER {
						valid(1),
						invalid(2)
					}
			ACCESS	read-write
			STATUS	mandatory
			DESCRIPTION
					"The status of the entry.  Setting an existing instance
					of this object to invalid(2) attempts to remove the
					corresponding entry from the table.  The effect of removing
					an entry from the table is to disable monitoring of the
					port."
			::= { lpsNetworkPortMonitorTableEntry 4 }

		-- The LANplex Systems MIB token ring port group.  Implementation of
		-- this group is mandatory for agents which manage token ring port
		-- resources.

		lpsTokenRingPortCount OBJECT-TYPE
			SYNTAX	INTEGER
			ACCESS	read-only
			STATUS	mandatory
			DESCRIPTION
					"The count of token ring ports managed by this agent."
			::= { lpsTokenRingPort 1 }


		-- The LANplex Systems MIB token ring port table.

		lpsTokenRingPortTable OBJECT-TYPE
			SYNTAX	SEQUENCE OF LpsTokenRingPortEntry
			ACCESS	not-accessible
			STATUS	mandatory
			DESCRIPTION
					"A list of token ring port entries.  A single entry exists
					 in this list for each token ring port managed by this agent."
			::= { lpsTokenRingPort 2 }

		lpsTokenRingPortEntry OBJECT-TYPE
			SYNTAX	LpsTokenRingPortEntry
			ACCESS	not-accessible
			STATUS	mandatory
			DESCRIPTION
					"A token ring port entry contains information about a
					 particular token ring port managed by this agent."
			INDEX	{ lpsTokenRingPortIndex }
			::= { lpsTokenRingPortTable 1 }

 		LpsTokenRingPortEntry ::=
			SEQUENCE {
				lpsTokenRingPortIndex			INTEGER,
				lpsTokenRingPortIfIndex			INTEGER,
				lpsTokenRingPortLabel			DisplayString,
				lpsTokenRingPortInsertStatus		INTEGER,
				lpsTokenRingPortType			INTEGER,
				lpsTokenRingPortMode			INTEGER,
				lpsTokenRingPortSpeed			INTEGER,
				lpsTokenRingPortLineErrors		Counter,
				lpsTokenRingPortBurstErrors		Counter,
				lpsTokenRingPortACErrors		Counter,
				lpsTokenRingPortAbortTransErrors	Counter,
				lpsTokenRingPortInternalErrors		Counter,
				lpsTokenRingPortLostFrameErrors		Counter,
				lpsTokenRingPortReceiveCongestionErrors	Counter,
				lpsTokenRingPortFrameCopiedErrors	Counter,
				lpsTokenRingPortTokenErrors		Counter,
				lpsTokenRingPortSoftErrors		Counter,
				lpsTokenRingPortHardErrors		Counter,
				lpsTokenRingPortSignalLoss		Counter,
				lpsTokenRingPortTransmitBeacons		Counter,
				lpsTokenRingPortRecoveries		Counter,
				lpsTokenRingPortLobeWires		Counter,
				lpsTokenRingPortRemoves			Counter,
				lpsTokenRingPortSingles			Counter,
				lpsTokenRingPortFreqErrors		Counter
			}

		lpsTokenRingPortIndex OBJECT-TYPE
			SYNTAX	INTEGER
			ACCESS	read-only
			STATUS	mandatory
			DESCRIPTION
				"The index of the token ring port identified by this entry,
				 relative to this agent."
			::= { lpsTokenRingPortEntry 1 }

		lpsTokenRingPortIfIndex OBJECT-TYPE
			SYNTAX	INTEGER
			ACCESS	read-only
			STATUS	mandatory
			DESCRIPTION
					"The value of the MIB-II ifIndex corresponding to the
					 token ring port identified by this entry."
			::= { lpsTokenRingPortEntry 2 }

		lpsTokenRingPortLabel OBJECT-TYPE
			SYNTAX	DisplayString (SIZE (0..31))
			ACCESS	read-write
			STATUS	mandatory
			DESCRIPTION
					"An ASCII text string describing the token ring port
					 identified by this entry."
			::= { lpsTokenRingPortEntry 3 }

		lpsTokenRingPortInsertStatus OBJECT-TYPE
			SYNTAX	INTEGER {
					inserted(1),
					deinserted(2)
					}
			ACCESS	read-only
			STATUS	mandatory
			DESCRIPTION
				"The current value of the link status for the token ring port
				 identified by this entry."
			::= { lpsTokenRingPortEntry 4 }

		lpsTokenRingPortType OBJECT-TYPE
			SYNTAX	INTEGER {
					rj45(1),
					other(2)
					}
			ACCESS	read-only
			STATUS	mandatory
			DESCRIPTION
					"Specific port type description for the token ring port
					 identified by this entry."
			::= { lpsTokenRingPortEntry 5 }

		lpsTokenRingPortMode OBJECT-TYPE
			SYNTAX	INTEGER	{
					station(1),
					lobe(2)
					}
			ACCESS	read-write
			STATUS	mandatory
			DESCRIPTION
					"The current mode of the port. The default mode (station) is
					used to connect a hub to the port.  Lobe mode is used to direct
			 		connect a Token Ring station into the port.  This selection
			 		can only be made on ports 1 and 2 of the module."
			::= { lpsTokenRingPortEntry 6 }

		lpsTokenRingPortSpeed OBJECT-TYPE
			SYNTAX	INTEGER {
					fourMegabit(1),
					sixteenMegabit(2),
					sixteenMegabitETR(3)
					}
			ACCESS	read-write
			STATUS	mandatory
			DESCRIPTION
					"The current speed of the port. The default speed is
					 sixteenMegabit."
			::= { lpsTokenRingPortEntry 7 }

          	lpsTokenRingPortLineErrors OBJECT-TYPE
			SYNTAX  Counter
                	ACCESS  read-only
                	STATUS  mandatory
                	DESCRIPTION
                        		"This counter is incremented when a frame
                         		or token is copied or repeated by a
                         		station, the E bit is zero in the frame
                         		or token and one of the following
                         		conditions exists: 1) there is a
                         		non-data bit (J or K bit) between the SD
                         		and the ED of the frame or token, or
                         		2) there is an FCS error in the frame."
                	::= { lpsTokenRingPortEntry 8 }

          	lpsTokenRingPortBurstErrors OBJECT-TYPE
                	SYNTAX  Counter
                	ACCESS  read-only
                	STATUS  mandatory
                	DESCRIPTION
                        		"This counter is incremented when a station
                         		detects the absence of transitions for five
                         		half-bit timers (burst-five error)."
                	::= {  lpsTokenRingPortEntry 9 }

          	lpsTokenRingPortACErrors OBJECT-TYPE
                	SYNTAX  Counter
                	ACCESS  read-only
                	STATUS  mandatory
                	DESCRIPTION
                        		"This counter is incremented when a station
                         		receives an AMP or SMP frame in which A is
                         		equal to C is equal to 0, and then receives
                         		another SMP frame with A is equal to C is
                         		equal to 0 without first receiving an AMP
                         		frame. It denotes a station that cannot set
                         		the AC bits properly."
                	::= { lpsTokenRingPortEntry 10 }

          	lpsTokenRingPortAbortTransErrors OBJECT-TYPE
                	SYNTAX  Counter
                	ACCESS  read-only
                	STATUS  mandatory
                	DESCRIPTION
                        		"This counter is incremented when a station
                         		transmits an abort delimiter while
                         		transmitting."
                	::= { lpsTokenRingPortEntry 11 }

          	lpsTokenRingPortInternalErrors OBJECT-TYPE
                	SYNTAX  Counter
                	ACCESS  read-only
                	STATUS  mandatory
                	DESCRIPTION
                        		"This counter is incremented when a station
                         		recognizes an internal error."
                	::= { lpsTokenRingPortEntry 12 }

          	lpsTokenRingPortLostFrameErrors OBJECT-TYPE
                	SYNTAX  Counter
                	ACCESS  read-only
                	STATUS  mandatory
                	DESCRIPTION
                        		"This counter is incremented when a station
                         		is transmitting and its TRR timer expires.
                         		This condition denotes a condition where a
                         		transmitting station in strip mode does not
                         		receive the trailer of the frame before the
                         		TRR timer goes off."
                	::= { lpsTokenRingPortEntry 13 }

          	lpsTokenRingPortReceiveCongestionErrors OBJECT-TYPE
                	SYNTAX  Counter
                	ACCESS  read-only
                	STATUS  mandatory
                	DESCRIPTION
                        		"This counter is incremented when a station
                         		recognizes a frame addressed to its
                         		specific address, but has no available
                         		buffer space indicating that the station
                         		is congested."
                	::= { lpsTokenRingPortEntry 14 }

          	lpsTokenRingPortFrameCopiedErrors OBJECT-TYPE
                	SYNTAX  Counter
                	ACCESS  read-only
                	STATUS  mandatory
                	DESCRIPTION
                        		"This counter is incremented when a station
                         		recognizes a frame addressed to its
                         		specific address and detects that the FS
                         		field A bits are set to 1 indicating a
                         		possible line hit or duplicate address."
                	::= { lpsTokenRingPortEntry 15 }

          	lpsTokenRingPortTokenErrors OBJECT-TYPE
                	SYNTAX  Counter
                	ACCESS  read-only
                	STATUS  mandatory
                	DESCRIPTION
                        		"This counter is incremented when a station
                         		acting as the active monitor recognizes an
                         		error condition that needs a token
                         		transmitted."
                	::= { lpsTokenRingPortEntry 16 }

          	lpsTokenRingPortSoftErrors OBJECT-TYPE
                	SYNTAX  Counter
                	ACCESS  read-only
                	STATUS  mandatory
                	DESCRIPTION
                       			"The number of Soft Errors the interface
                         		has detected. It directly corresponds to
                         		the number of Report Error MAC frames
                         		that this interface has transmitted.
                         		Soft Errors are those which are
                         		recoverable by the MAC layer protocols."
                	::= { lpsTokenRingPortEntry 17 }

          	lpsTokenRingPortHardErrors OBJECT-TYPE
                	SYNTAX  Counter
                	ACCESS  read-only
                	STATUS  mandatory
                	DESCRIPTION
                        		"The number of times this interface has
                         		detected an immediately recoverable
                         		fatal error.  It denotes the number of
                         		times this interface is either
                         		transmitting or receiving beacon MAC
                         		frames."
                	::= { lpsTokenRingPortEntry 18 }

          	lpsTokenRingPortSignalLoss OBJECT-TYPE
                	SYNTAX  Counter
                	ACCESS  read-only
                	STATUS  mandatory
                	DESCRIPTION
                        		"The number of times this interface has
                         		detected the loss of signal condition from
                         		the ring."
                	::= { lpsTokenRingPortEntry 19 }

          	lpsTokenRingPortTransmitBeacons OBJECT-TYPE
                	SYNTAX  Counter
                	ACCESS  read-only
                	STATUS  mandatory
                	DESCRIPTION
                        		"The number of times this interface has
                         		transmitted a beacon frame."
                	::= { lpsTokenRingPortEntry 20 }

          	lpsTokenRingPortRecoveries OBJECT-TYPE
                	SYNTAX  Counter
                	ACCESS  read-only
                	STATUS  mandatory
                	DESCRIPTION
                        		"The number of Claim Token MAC frames
                         		received or transmitted after the interface
                         		has received a Ring Purge MAC frame.  This
                         		counter signifies the number of times the
                         		ring has been purged and is being recovered
                         		back into a normal operating state."
                	::= { lpsTokenRingPortEntry 21 }

          	lpsTokenRingPortLobeWires OBJECT-TYPE
                	SYNTAX  Counter
                	ACCESS  read-only
                	STATUS  mandatory
                	DESCRIPTION
                        		"The number of times the interface has
                         		detected an open or short circuit in the
                         		lobe data path.  The adapter will be closed
                         		when this condition occurs."
                	::= { lpsTokenRingPortEntry 22 }

          	lpsTokenRingPortRemoves OBJECT-TYPE
                	SYNTAX  Counter
                	ACCESS  read-only
                	STATUS  mandatory
                	DESCRIPTION
                        		"The number of times the interface has
                         		received a Remove Ring Station MAC frame
                         		request.  When this frame is received
                         		the interface will enter the close state."
                	::= { lpsTokenRingPortEntry 23 }

          	lpsTokenRingPortSingles OBJECT-TYPE
                	SYNTAX  Counter
                	ACCESS  read-only
                	STATUS  mandatory
                	DESCRIPTION
                        	"The number of times the interface has
                         	sensed that it is the only station on the
                         	ring.  This will happen if the interface
                         	is the first one up on a ring, or if
                         	there is a hardware problem."
                	::= { lpsTokenRingPortEntry 24 }


          	lpsTokenRingPortFreqErrors OBJECT-TYPE
                	SYNTAX  Counter
                	ACCESS  read-only
                	STATUS  optional
                	DESCRIPTION
                        		"The number of times the interface has
                         		detected that the frequency of the
                         		incoming signal differs from the expected
                         		frequency."
                	::= { lpsTokenRingPortEntry 25 }



		-- The LANplex Systems MIB traps.

		lpsSystemOverTemperatureEvent TRAP-TYPE
			ENTERPRISE	lanplexSystemsMib
			VARIABLES	{ lpsSystemOvertemperature }
			DESCRIPTION
					"The trap that is generated when the system temperature
					exceeds a certain threshold."
			::= 1

		lpsPowerSupplyFailureEvent TRAP-TYPE
			ENTERPRISE	lanplexSystemsMib
			VARIABLES	{ lpsPowerSupplyStatusIndex,
						lpsPowerSupplyStatus,
						lpsPowerSupplyStatusSupported }
			DESCRIPTION
					"The trap that is generated when a power supply unit
					fails."
			::= 2

		lpsChassisSlotOverTemperatureEvent TRAP-TYPE
			ENTERPRISE	lanplexSystemsMib
			VARIABLES	{ lpsSlotIndex,
						lpsSlotBoardType,
						lpsSlotBoardRevision,
						lpsSlotBoardStatus,
						lpsSlotOvertemperature }
			DESCRIPTION
					"The trap that is generated when the temperature of a
					board in a particular slot exceeds a certain threshold."
			::= 3

		lpsChassisSlotInsertEvent TRAP-TYPE
			ENTERPRISE	lanplexSystemsMib
			VARIABLES	{ lpsSlotIndex,
						lpsSlotBoardType,
						lpsSlotBoardRevision }
			DESCRIPTION
					"The trap that is generated when a board is inserted into a
					particular slot."
			::= 4

		lpsChassisSlotExtractEvent TRAP-TYPE
			ENTERPRISE	lanplexSystemsMib
			VARIABLES	{ lpsSlotIndex }
			DESCRIPTION
					"The trap that is generated when a board is extracted
					from a particular slot."
			::= 5

		lpsBridgeAddressThresholdEvent TRAP-TYPE
			ENTERPRISE	lanplexSystemsMib
			VARIABLES	{ lpsBridgeIndex }
			DESCRIPTION
					"The trap that is generated when the number of addresses
					stored in the bridge reaches lpsBridgeAddressThreshold."
			::= 6

		lpsSystemFanFailureEvent TRAP-TYPE
			ENTERPRISE	lanplexSystemsMib
			VARIABLES	{ lpsSystemFanFailure }
			DESCRIPTION
					"The trap that is generated when one of the system fans
					fails."
			::= 7

	END
