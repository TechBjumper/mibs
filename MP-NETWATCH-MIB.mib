-- ***************************************************************************************
-- FileName    :mpNetWatchVRMIB.my
-- Description :MultiMedia Platform private MIB
-- Revision History     :
--   Ver.     mark   date      
--   01.00    ****   12/26/2001
--
-- ***************************************************************************************
--



MP-NETWATCH-MIB DEFINITIONS ::= BEGIN
   IMPORTS
	
		TimeTicks, IpAddress FROM RFC1155-SMI

      OBJECT-TYPE
      FROM RFC-1212

      TRAP-TYPE
      FROM RFC-1215;

    org               OBJECT IDENTIFIER ::= { iso 3 }
    dod               OBJECT IDENTIFIER ::= { org 6 }
    internet          OBJECT IDENTIFIER ::= { dod 1 }
    private           OBJECT IDENTIFIER ::= { internet 4 }
    enterprises       OBJECT IDENTIFIER ::= { private 1 }
    nec               OBJECT IDENTIFIER ::= { enterprises 119}
    nec-mib           OBJECT IDENTIFIER ::= { nec 2 }
    necProductDepend  OBJECT IDENTIFIER ::= { nec-mib 3 }
    datax-mib         OBJECT IDENTIFIER ::= { necProductDepend 3 }
    mmpf-mib          OBJECT IDENTIFIER ::= { datax-mib 13 }

    mpInterface       OBJECT IDENTIFIER ::= { mmpf-mib 103 }
    mpNetwatch        OBJECT IDENTIFIER ::= { mmpf-mib 132 }
    mpNetping         OBJECT IDENTIFIER ::= { mmpf-mib 133 }
--
--  Net-Watch Private MIB
--

	mpNetWatchTable  OBJECT-TYPE
               SYNTAX  SEQUENCE OF MpNetWatchEntry
               ACCESS  not-accessible
               STATUS  mandatory
               DESCRIPTION 
			"This is the table type object of NetWatch infomation" 
               ::= { mpNetwatch 1 }

        mpNetWatchEntry OBJECT-TYPE
               SYNTAX  MpNetWatchEntry
               ACCESS  not-accessible
               STATUS  mandatory
               DESCRIPTION 
			"This is the table entry of mpNetWatchTable."
               INDEX   { mpNetWatchID }
               ::= { mpNetWatchTable 1 }

        MpNetWatchEntry ::=
               SEQUENCE {
                   mpNetWatchID
                       INTEGER,
                   mpNetWatchVPNID
                       INTEGER,
                   mpNetWatchEntryStatus
                       INTEGER,
                   mpNetWatchAction
                       INTEGER,
                   mpNetWatchNetworkAddr1
                       IpAddress,
                   mpNetWatchSubNetMask1
                       IpAddress,
                   mpNetWatchNetworkAddr2
                       IpAddress,
                   mpNetWatchSubNetMask2
                       IpAddress,
                   mpNetWatchNetworkAddr3
                       IpAddress,
                   mpNetWatchSubNetMask3
                       IpAddress,
                   mpNetWatchNetworkAddr4
                       IpAddress,
                   mpNetWatchSubNetMask4
                       IpAddress,
                   mpNetWatchNetworkAddr5
                       IpAddress,
                   mpNetWatchSubNetMask5
                       IpAddress,
                   mpNetWatchNetworkAddr6
                       IpAddress,
                   mpNetWatchSubNetMask6
                       IpAddress,
                   mpNetWatchNetworkAddr7
                       IpAddress,
                   mpNetWatchSubNetMask7
                       IpAddress,
                   mpNetWatchNetworkAddr8
                       IpAddress, 
                   mpNetWatchSubNetMask8
                       IpAddress,
		   mpNetWatchifIndex1
		       INTEGER,
		   mpNetWatchifIndex2
		       INTEGER,
		   mpNetWatchifIndex3
		       INTEGER,
		   mpNetWatchifIndex4
		       INTEGER,
		   mpNetWatchifIndex5
		       INTEGER,
		   mpNetWatchifIndex6
		       INTEGER,
		   mpNetWatchifIndex7
		       INTEGER,
		   mpNetWatchifIndex8
		       INTEGER,
		   mpNetWatchifIndex9
		       INTEGER,
		   mpNetWatchifIndex10
		       INTEGER,
		   mpNetWatchifIndex11
		       INTEGER,
		   mpNetWatchifIndex12
		       INTEGER,
		   mpNetWatchifIndex13
		       INTEGER,
		   mpNetWatchifIndex14
		       INTEGER,
		   mpNetWatchifIndex15
		       INTEGER,
		   mpNetWatchifIndex16
		       INTEGER
               }

--NetWatch ID
mpNetWatchID OBJECT-TYPE
	SYNTAX	INTEGER
	ACCESS	read-only
	STATUS	mandatory
	DESCRIPTION
		"A unique value to identify a net-watch(Net-watch ID)."
--
	::= { mpNetWatchEntry 1 }

-- VPN ID
mpNetWatchVPNID OBJECT-TYPE
	SYNTAX	INTEGER
	ACCESS	read-only
	STATUS	mandatory
	DESCRIPTION
		"A unique value to identify a VPN(VPN-ID)."
--
	::= { mpNetWatchEntry 2 }

--Netwatch Entry Status
mpNetWatchEntryStatus OBJECT-TYPE
        SYNTAX  INTEGER {
                        up(1),
                        down(2),
                        retry(3)
                        }
        ACCESS  read-only
        STATUS  mandatory
        DESCRIPTION
                "A unique value to identify a net-watch Status."
--
        ::= { mpNetWatchEntry 3 }

--Port Admin Contorol Action Type
mpNetWatchAction OBJECT-TYPE
        SYNTAX  INTEGER {
                        down(1),
                        up(2)
                        }
        ACCESS  read-only
        STATUS  mandatory
        DESCRIPTION
                "A unique value to identify a Port Admin Contorol Type,
                 when watched all network address is failured."
--
--
        ::= { mpNetWatchEntry 4 }


--
mpNetWatchNetworkAddr1 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 5 }

mpNetWatchSubNetMask1 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 6 }

mpNetWatchNetworkAddr2 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 7 }

mpNetWatchSubNetMask2 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 8 }

mpNetWatchNetworkAddr3 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 9 }

mpNetWatchSubNetMask3 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 10 }

mpNetWatchNetworkAddr4 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 11 }

mpNetWatchSubNetMask4 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 12 }

mpNetWatchNetworkAddr5 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 13 }

mpNetWatchSubNetMask5 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 14 }

mpNetWatchNetworkAddr6 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 15 }

mpNetWatchSubNetMask6 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 16 }

mpNetWatchNetworkAddr7 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 17 }

mpNetWatchSubNetMask7 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 18 }

mpNetWatchNetworkAddr8 OBJECT-TYPE
	SYNTAX	IpAddress
	ACCESS	read-only
	STATUS	mandatory
	DESCRIPTION
		"ipv4 Address of watched Network Address. Its value is
		 significant only when be indicated subject to watch,
		 otherwise it should return a value of 0."
	::= { mpNetWatchEntry 19 }

mpNetWatchSubNetMask8 OBJECT-TYPE
        SYNTAX  IpAddress
        ACCESS  read-only
        STATUS  mandatory
        DESCRIPTION
                "ipv4 Address of watched Subnet Mask. Its value is
                 significant only when be indicated subject to watch,
                 otherwise it should return a value of 0."
        ::= { mpNetWatchEntry 20 }

--Admin Change Port
mpNetWatchifIndex1 OBJECT-TYPE
	SYNTAX	INTEGER 
	ACCESS	read-only
	STATUS	mandatory
	DESCRIPTION
		"A unique value to identify a object of Port Admin change,
                 when watched all network address is failured."
--
	::= { mpNetWatchEntry 21 }

mpNetWatchifIndex2 OBJECT-TYPE
	SYNTAX	INTEGER 
	ACCESS	read-only
	STATUS	mandatory
	DESCRIPTION
		"A unique value to identify a object of Port Admin change,
                 when watched all network address is failured."
--
	::= { mpNetWatchEntry 22 }

mpNetWatchifIndex3 OBJECT-TYPE
	SYNTAX	INTEGER 
	ACCESS	read-only
	STATUS	mandatory
	DESCRIPTION
		"A unique value to identify a object of Port Admin change,
                 when watched all network address is failured."
--
	::= { mpNetWatchEntry 23 }

mpNetWatchifIndex4 OBJECT-TYPE
	SYNTAX	INTEGER 
	ACCESS	read-only
	STATUS	mandatory
	DESCRIPTION
		"A unique value to identify a object of Port Admin change,
                 when watched all network address is failured."
--
	::= { mpNetWatchEntry 24 }

mpNetWatchifIndex5 OBJECT-TYPE
	SYNTAX	INTEGER 
	ACCESS	read-only
	STATUS	mandatory
	DESCRIPTION
		"A unique value to identify a object of Port Admin change,
                 when watched all network address is failured."
--
	::= { mpNetWatchEntry 25 }

mpNetWatchifIndex6 OBJECT-TYPE
	SYNTAX	INTEGER 
	ACCESS	read-only
	STATUS	mandatory
	DESCRIPTION
		"A unique value to identify a object of Port Admin change,
                 when watched all network address is failured."
--
	::= { mpNetWatchEntry 26 }

mpNetWatchifIndex7 OBJECT-TYPE
	SYNTAX	INTEGER 
	ACCESS	read-only
	STATUS	mandatory
	DESCRIPTION
		"A unique value to identify a object of Port Admin change,
                 when watched all network address is failured."
--
	::= { mpNetWatchEntry 27 }

mpNetWatchifIndex8 OBJECT-TYPE
	SYNTAX	INTEGER 
	ACCESS	read-only
	STATUS	mandatory
	DESCRIPTION
		"A unique value to identify a object of Port Admin change,
                 when watched all network address is failured."
--
	::= { mpNetWatchEntry 28 }

mpNetWatchifIndex9 OBJECT-TYPE
	SYNTAX	INTEGER 
	ACCESS	read-only
	STATUS	mandatory
	DESCRIPTION
		"A unique value to identify a object of Port Admin change,
                 when watched all network address is failured."
--
	::= { mpNetWatchEntry 29 }

mpNetWatchifIndex10 OBJECT-TYPE
	SYNTAX	INTEGER 
	ACCESS	read-only
	STATUS	mandatory
	DESCRIPTION
		"A unique value to identify a object of Port Admin change,
                 when watched all network address is failured."
--
	::= { mpNetWatchEntry 30 }

mpNetWatchifIndex11 OBJECT-TYPE
	SYNTAX	INTEGER 
	ACCESS	read-only
	STATUS	mandatory
	DESCRIPTION
		"A unique value to identify a object of Port Admin change,
                 when watched all network address is failured."
--
	::= { mpNetWatchEntry 31 }

mpNetWatchifIndex12 OBJECT-TYPE
	SYNTAX	INTEGER 
	ACCESS	read-only
	STATUS	mandatory
	DESCRIPTION
		"A unique value to identify a object of Port Admin change,
                 when watched all network address is failured."
--
	::= { mpNetWatchEntry 32 }

mpNetWatchifIndex13 OBJECT-TYPE
	SYNTAX	INTEGER 
	ACCESS	read-only
	STATUS	mandatory
	DESCRIPTION
		"A unique value to identify a object of Port Admin change,
                 when watched all network address is failured."
--
	::= { mpNetWatchEntry 33 }

mpNetWatchifIndex14 OBJECT-TYPE
	SYNTAX	INTEGER 
	ACCESS	read-only
	STATUS	mandatory
	DESCRIPTION
		"A unique value to identify a object of Port Admin change,
                 when watched all network address is failured."
--
	::= { mpNetWatchEntry 34 }

mpNetWatchifIndex15 OBJECT-TYPE
	SYNTAX	INTEGER 
	ACCESS	read-only
	STATUS	mandatory
	DESCRIPTION
		"A unique value to identify a object of Port Admin change,
                 when watched all network address is failured."
--
	::= { mpNetWatchEntry 35 }

mpNetWatchifIndex16 OBJECT-TYPE
	SYNTAX	INTEGER 
	ACCESS	read-only
	STATUS	mandatory
	DESCRIPTION
		"A unique value to identify a object of Port Admin change,
		 when watched all network address is failured."
--
	::= { mpNetWatchEntry 36 }


--
--
--
mpNetWatchStatusTimeStamp  OBJECT IDENTIFIER ::= { mpNetwatch 2 }

mpNetWatchStatusLastChange    OBJECT-TYPE
     SYNTAX       TimeTicks
     ACCESS       read-only
     STATUS       mandatory
     DESCRIPTION   "This object indicates the the time which configuration of 
                    NetWatch ID status is changed."
--
--

 	::= { mpNetWatchStatusTimeStamp 1 }


--
--  Net-Ping Private MIB
--

	mpNetPingTable  OBJECT-TYPE
               SYNTAX  SEQUENCE OF MpNetPingEntry
               ACCESS  not-accessible
               STATUS  mandatory
               DESCRIPTION 
			"This is the table type object of NetPing infomation." 
               ::= { mpNetping 1 }

        mpNetPingEntry OBJECT-TYPE
               SYNTAX  MpNetPingEntry
               ACCESS  not-accessible
               STATUS  mandatory
               DESCRIPTION 
			"This is the table entry of mpNetPingTable."
               INDEX   { mpNetPingID }
               ::= { mpNetPingTable 1 }

       MpNetPingEntry ::=
               SEQUENCE {
                   mpNetPingID
                       INTEGER,
                   mpNetPingVPNID
                       INTEGER,
                   mpNetPingEntryStatus
                       INTEGER,
                   mpNetPingAction
                       INTEGER,
                   mpNetPingDestIPAddr1
                       IpAddress,
                   mpNetPingDestIPAddr2
                       IpAddress,
                   mpNetPingDestIPAddr3
                       IpAddress,
                   mpNetPingDestIPAddr4
                       IpAddress,
                   mpNetPingDestIPAddr5
                       IpAddress,
                   mpNetPingDestIPAddr6
                       IpAddress,
                   mpNetPingDestIPAddr7
                       IpAddress,
                   mpNetPingDestIPAddr8
                       IpAddress,
		   mpNetPingifIndex1
		       INTEGER,
		   mpNetPingifIndex2
		       INTEGER,
		   mpNetPingifIndex3
		       INTEGER,
		   mpNetPingifIndex4
		       INTEGER,
		   mpNetPingifIndex5
		       INTEGER,
		   mpNetPingifIndex6
		       INTEGER,
		   mpNetPingifIndex7
		       INTEGER,
		   mpNetPingifIndex8
		       INTEGER,
		   mpNetPingifIndex9
		       INTEGER,
		   mpNetPingifIndex10
		       INTEGER,
		   mpNetPingifIndex11
		       INTEGER,
		   mpNetPingifIndex12
		       INTEGER,
		   mpNetPingifIndex13
		       INTEGER,
		   mpNetPingifIndex14
		       INTEGER,
		   mpNetPingifIndex15
		       INTEGER,
		   mpNetPingifIndex16
		       INTEGER
              }

--NetPing ID
mpNetPingID OBJECT-TYPE
	SYNTAX	INTEGER
	ACCESS	read-only
	STATUS	mandatory
	DESCRIPTION
		"A unique value to identify a net-Ping(Net-Ping ID)."
--
	::= { mpNetPingEntry 1 }

-- VPN ID
mpNetPingVPNID OBJECT-TYPE
	SYNTAX	INTEGER
	ACCESS	read-only
	STATUS	mandatory
	DESCRIPTION
		"A unique value to identify a VPN(VPN-ID)."
--
	::= { mpNetPingEntry 2 }

--NetPing Entry Status
mpNetPingEntryStatus OBJECT-TYPE
        SYNTAX  INTEGER {
                        up(1),
                        down(2),
                        retry(3)
                        }
        ACCESS  read-only
        STATUS  mandatory
        DESCRIPTION
                "A unique value to identify a net-Ping Status."
--
        ::= { mpNetPingEntry 3 }

--Port Admin Contorol Action Type
mpNetPingAction OBJECT-TYPE
        SYNTAX  INTEGER {
                        down(1),
                        up(2)
                        }
        ACCESS  read-only
        STATUS  mandatory
        DESCRIPTION
                "A unique value to identify a Port Admin Contorol Type,
                 when it is failured in ping for all destination IP Address of ping Entry."
--
        ::= { mpNetPingEntry 4 }

--
mpNetPingDestIPAddr1 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 5 }

mpNetPingDestIPAddr2 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 6 }

mpNetPingDestIPAddr3 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 7 }

mpNetPingDestIPAddr4 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 8 }

mpNetPingDestIPAddr5 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 9 }

mpNetPingDestIPAddr6 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 10 }

mpNetPingDestIPAddr7 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 11 }

mpNetPingDestIPAddr8 OBJECT-TYPE
	SYNTAX	IpAddress
	ACCESS	read-only
	STATUS	mandatory
	DESCRIPTION
		"ipv4 Address of watched Destination IP Address by ping send. 
		 Its value is significant only when be indicated subject to watch,
		 otherwise it should return a value of 0."
	::= { mpNetPingEntry 12 }

--Admin Change Port
mpNetPingifIndex1 OBJECT-TYPE
	SYNTAX	INTEGER 
	ACCESS	read-only
	STATUS	mandatory
	DESCRIPTION
		"A unique value to identify a object of Port Admin change,
                 when it is failured in ping for all destination IP Address of ping Entry."
--
	::= { mpNetPingEntry 13 }

mpNetPingifIndex2 OBJECT-TYPE
	SYNTAX	INTEGER 
	ACCESS	read-only
	STATUS	mandatory
	DESCRIPTION
		"A unique value to identify a object of Port Admin change,
                 when it is failured in ping for all destination IP Address of ping Entry."
--
	::= { mpNetPingEntry 14 }

mpNetPingifIndex3 OBJECT-TYPE
	SYNTAX	INTEGER 
	ACCESS	read-only
	STATUS	mandatory
	DESCRIPTION
		"A unique value to identify a object of Port Admin change,
                 when it is failured in ping for all destination IP Address of ping Entry."
--
	::= { mpNetPingEntry 15 }

mpNetPingifIndex4 OBJECT-TYPE
	SYNTAX	INTEGER 
	ACCESS	read-only
	STATUS	mandatory
	DESCRIPTION
		"A unique value to identify a object of Port Admin change,
                 when it is failured in ping for all destination IP Address of ping Entry."
--
	::= { mpNetPingEntry 16 }

mpNetPingifIndex5 OBJECT-TYPE
	SYNTAX	INTEGER 
	ACCESS	read-only
	STATUS	mandatory
	DESCRIPTION
		"A unique value to identify a object of Port Admin change,
                 when it is failured in ping for all destination IP Address of ping Entry."
--
	::= { mpNetPingEntry 17 }

mpNetPingifIndex6 OBJECT-TYPE
	SYNTAX	INTEGER 
	ACCESS	read-only
	STATUS	mandatory
	DESCRIPTION
		"A unique value to identify a object of Port Admin change,
                 when it is failured in ping for all destination IP Address of ping Entry."
--
	::= { mpNetPingEntry 18 }

mpNetPingifIndex7 OBJECT-TYPE
	SYNTAX	INTEGER 
	ACCESS	read-only
	STATUS	mandatory
	DESCRIPTION
		"A unique value to identify a object of Port Admin change,
                 when it is failured in ping for all destination IP Address of ping Entry."
--
	::= { mpNetPingEntry 19 }

mpNetPingifIndex8 OBJECT-TYPE
	SYNTAX	INTEGER 
	ACCESS	read-only
	STATUS	mandatory
	DESCRIPTION
		"A unique value to identify a object of Port Admin change,
                 when it is failured in ping for all destination IP Address of ping Entry."
--
	::= { mpNetPingEntry 20 }

mpNetPingifIndex9 OBJECT-TYPE
	SYNTAX	INTEGER 
	ACCESS	read-only
	STATUS	mandatory
	DESCRIPTION
		"A unique value to identify a object of Port Admin change,
                 when it is failured in ping for all destination IP Address of ping Entry."
--
	::= { mpNetPingEntry 21 }

mpNetPingifIndex10 OBJECT-TYPE
	SYNTAX	INTEGER 
	ACCESS	read-only
	STATUS	mandatory
	DESCRIPTION
		"A unique value to identify a object of Port Admin change,
                 when it is failured in ping for all destination IP Address of ping Entry."
--
	::= { mpNetPingEntry 22 }

mpNetPingifIndex11 OBJECT-TYPE
	SYNTAX	INTEGER 
	ACCESS	read-only
	STATUS	mandatory
	DESCRIPTION
		"A unique value to identify a object of Port Admin change,
                 when it is failured in ping for all destination IP Address of ping Entry."
--
	::= { mpNetPingEntry 23 }

mpNetPingifIndex12 OBJECT-TYPE
	SYNTAX	INTEGER 
	ACCESS	read-only
	STATUS	mandatory
	DESCRIPTION
		"A unique value to identify a object of Port Admin change,
                 when it is failured in ping for all destination IP Address of ping Entry."
--
	::= { mpNetPingEntry 24 }

mpNetPingifIndex13 OBJECT-TYPE
	SYNTAX	INTEGER 
	ACCESS	read-only
	STATUS	mandatory
	DESCRIPTION
		"A unique value to identify a object of Port Admin change,
                 when it is failured in ping for all destination IP Address of ping Entry."
--
	::= { mpNetPingEntry 25 }

mpNetPingifIndex14 OBJECT-TYPE
	SYNTAX	INTEGER 
	ACCESS	read-only
	STATUS	mandatory
	DESCRIPTION
		"A unique value to identify a object of Port Admin change,
                 when it is failured in ping for all destination IP Address of ping Entry."
--
	::= { mpNetPingEntry 26 }

mpNetPingifIndex15 OBJECT-TYPE
	SYNTAX	INTEGER 
	ACCESS	read-only
	STATUS	mandatory
	DESCRIPTION
		"A unique value to identify a object of Port Admin change,
                 when it is failured in ping for all destination IP Address of ping Entry."
--
	::= { mpNetPingEntry 27 }

mpNetPingifIndex16 OBJECT-TYPE
	SYNTAX	INTEGER 
	ACCESS	read-only
	STATUS	mandatory
	DESCRIPTION
		"A unique value to identify a object of Port Admin change,
                 when it is failured in ping for all destination IP Address of ping Entry."
--
	::= { mpNetPingEntry 28 }




--
--
--
mpNetPingStatusTimeStamp  OBJECT IDENTIFIER ::= { mpNetping 2 }

mpNetPingStatusLastChange    OBJECT-TYPE
     SYNTAX       TimeTicks
     ACCESS       read-only
     STATUS       mandatory
     DESCRIPTION   "This object indicates the the time which configuration of 
                    NetPing ID status is changed."
--
--

 	::= { mpNetPingStatusTimeStamp 1 }


             
END
