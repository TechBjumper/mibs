-- file automatically created


TELDAT-TRAP-VRRP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


vrrpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the VRRP event subsystem."
    REVISION "201401200930Z"
    DESCRIPTION "Initial implementation"
        ::= { telEventTraps 179 }


vrrpEventsGroup	OBJECT IDENTIFIER	::= { vrrpTrapsMIB 1 }

vrrpNotifications	OBJECT IDENTIFIER	::= { vrrpTrapsMIB 2 }
vrrpNotificationsPrefix	OBJECT IDENTIFIER	::= { vrrpNotifications 0 }

vrrpEventObjects1 OBJECT-IDENTITY
    STATUS current
    DESCRIPTION
        "Event VRRP.1
        Generic info."
    ::= { vrrpEventsGroup 1 }

vrrp1-generic-info OBJECT-TYPE
    SYNTAX DisplayString
    MAX-ACCESS accessible-for-notify
    STATUS current
    DESCRIPTION
        "Parameter 'generic-info' in event VRRP.1"
    ::= { vrrpEventObjects1 1 }

vrrpEventObjects2 OBJECT-IDENTITY
    STATUS current
    DESCRIPTION
        "Event VRRP.2
        Virtual router event descriptor."
    ::= { vrrpEventsGroup 2 }

vrrp2-interface OBJECT-TYPE
    SYNTAX DisplayString
    MAX-ACCESS accessible-for-notify
    STATUS current
    DESCRIPTION
        "Parameter 'interface' in event VRRP.2"
    ::= { vrrpEventObjects2 1 }

vrrp2-vrid OBJECT-TYPE
    SYNTAX Integer32
    MAX-ACCESS accessible-for-notify
    STATUS current
    DESCRIPTION
        "Parameter 'vrid' in event VRRP.2"
    ::= { vrrpEventObjects2 2 }

vrrp2-state OBJECT-TYPE
    SYNTAX DisplayString
    MAX-ACCESS accessible-for-notify
    STATUS current
    DESCRIPTION
        "Parameter 'state' in event VRRP.2"
    ::= { vrrpEventObjects2 3 }

vrrp2-event OBJECT-TYPE
    SYNTAX DisplayString
    MAX-ACCESS accessible-for-notify
    STATUS current
    DESCRIPTION
        "Parameter 'event' in event VRRP.2"
    ::= { vrrpEventObjects2 4 }

vrrpEventObjects3 OBJECT-IDENTITY
    STATUS current
    DESCRIPTION
        "Event VRRP.3
        A virtual router has changed its state."
    ::= { vrrpEventsGroup 3 }

vrrp3-interface OBJECT-TYPE
    SYNTAX DisplayString
    MAX-ACCESS accessible-for-notify
    STATUS current
    DESCRIPTION
        "Parameter 'interface' in event VRRP.3"
    ::= { vrrpEventObjects3 1 }

vrrp3-vrid OBJECT-TYPE
    SYNTAX Integer32
    MAX-ACCESS accessible-for-notify
    STATUS current
    DESCRIPTION
        "Parameter 'vrid' in event VRRP.3"
    ::= { vrrpEventObjects3 2 }

vrrp3-new-state OBJECT-TYPE
    SYNTAX DisplayString
    MAX-ACCESS accessible-for-notify
    STATUS current
    DESCRIPTION
        "Parameter 'new-state' in event VRRP.3"
    ::= { vrrpEventObjects3 3 }

vrrpEventObjects4 OBJECT-IDENTITY
    STATUS current
    DESCRIPTION
        "Event VRRP.4
        An error has ocurred while receiving a VRRP Advertisement."
    ::= { vrrpEventsGroup 4 }

vrrp4-error-message OBJECT-TYPE
    SYNTAX DisplayString
    MAX-ACCESS accessible-for-notify
    STATUS current
    DESCRIPTION
        "Parameter 'error-message' in event VRRP.4"
    ::= { vrrpEventObjects4 1 }

vrrpEventObjects5 OBJECT-IDENTITY
    STATUS current
    DESCRIPTION
        "Event VRRP.5
        An error associated to a virtual router has ocurred while receiving a
        VRRP Advertisement."
    ::= { vrrpEventsGroup 5 }

vrrp5-interface OBJECT-TYPE
    SYNTAX DisplayString
    MAX-ACCESS accessible-for-notify
    STATUS current
    DESCRIPTION
        "Parameter 'interface' in event VRRP.5"
    ::= { vrrpEventObjects5 1 }

vrrp5-vrid OBJECT-TYPE
    SYNTAX Integer32
    MAX-ACCESS accessible-for-notify
    STATUS current
    DESCRIPTION
        "Parameter 'vrid' in event VRRP.5"
    ::= { vrrpEventObjects5 2 }

vrrp5-error-message OBJECT-TYPE
    SYNTAX DisplayString
    MAX-ACCESS accessible-for-notify
    STATUS current
    DESCRIPTION
        "Parameter 'error-message' in event VRRP.5"
    ::= { vrrpEventObjects5 3 }

vrrpEventObjects6 OBJECT-IDENTITY
    STATUS current
    DESCRIPTION
        "Event VRRP.6
        A VRRP Advertisement has been sent."
    ::= { vrrpEventsGroup 6 }

vrrp6-interface OBJECT-TYPE
    SYNTAX DisplayString
    MAX-ACCESS accessible-for-notify
    STATUS current
    DESCRIPTION
        "Parameter 'interface' in event VRRP.6"
    ::= { vrrpEventObjects6 1 }

vrrp6-vrid OBJECT-TYPE
    SYNTAX Integer32
    MAX-ACCESS accessible-for-notify
    STATUS current
    DESCRIPTION
        "Parameter 'vrid' in event VRRP.6"
    ::= { vrrpEventObjects6 2 }

vrrp6-priority OBJECT-TYPE
    SYNTAX Integer32
    MAX-ACCESS accessible-for-notify
    STATUS current
    DESCRIPTION
        "Parameter 'priority' in event VRRP.6"
    ::= { vrrpEventObjects6 3 }

vrrp6-checksum OBJECT-TYPE
    SYNTAX Integer32
    MAX-ACCESS accessible-for-notify
    STATUS current
    DESCRIPTION
        "Parameter 'checksum' in event VRRP.6"
    ::= { vrrpEventObjects6 4 }

vrrpEventObjects7 OBJECT-IDENTITY
    STATUS current
    DESCRIPTION
        "Event VRRP.7
        A gratuitous ARP-request has been sent."
    ::= { vrrpEventsGroup 7 }

vrrp7-virtual-ip-address OBJECT-TYPE
    SYNTAX IpAddress
    MAX-ACCESS accessible-for-notify
    STATUS current
    DESCRIPTION
        "Parameter 'virtual-ip-address' in event VRRP.7"
    ::= { vrrpEventObjects7 1 }

vrrp7-virtual-mac-address OBJECT-TYPE
    SYNTAX Integer32
    MAX-ACCESS accessible-for-notify
    STATUS current
    DESCRIPTION
        "Parameter 'virtual-mac-address' in event VRRP.7"
    ::= { vrrpEventObjects7 2 }

vrrpEventObjects8 OBJECT-IDENTITY
    STATUS current
    DESCRIPTION
        "Event VRRP.8
        An internal error has ocurred."
    ::= { vrrpEventsGroup 8 }

vrrp8-error-message OBJECT-TYPE
    SYNTAX DisplayString
    MAX-ACCESS accessible-for-notify
    STATUS current
    DESCRIPTION
        "Parameter 'error-message' in event VRRP.8"
    ::= { vrrpEventObjects8 1 }

vrrpEventObjects9 OBJECT-IDENTITY
    STATUS current
    DESCRIPTION
        "Event VRRP.9
        Waiting for preempt delay timeout."
    ::= { vrrpEventsGroup 9 }

vrrp9-interface OBJECT-TYPE
    SYNTAX DisplayString
    MAX-ACCESS accessible-for-notify
    STATUS current
    DESCRIPTION
        "Parameter 'interface' in event VRRP.9"
    ::= { vrrpEventObjects9 1 }

vrrp9-vrid OBJECT-TYPE
    SYNTAX Integer32
    MAX-ACCESS accessible-for-notify
    STATUS current
    DESCRIPTION
        "Parameter 'vrid' in event VRRP.9"
    ::= { vrrpEventObjects9 2 }

vrrp9-state OBJECT-TYPE
    SYNTAX DisplayString
    MAX-ACCESS accessible-for-notify
    STATUS current
    DESCRIPTION
        "Parameter 'state' in event VRRP.9"
    ::= { vrrpEventObjects9 3 }

vrrp9-timeout OBJECT-TYPE
    SYNTAX Integer32
    MAX-ACCESS accessible-for-notify
    STATUS current
    DESCRIPTION
        "Parameter 'timeout' in event VRRP.9"
    ::= { vrrpEventObjects9 4 }

vrrp9-sec OBJECT-TYPE
    SYNTAX DisplayString
    MAX-ACCESS accessible-for-notify
    STATUS current
    DESCRIPTION
        "Parameter 'sec' in event VRRP.9"
    ::= { vrrpEventObjects9 5 }

vrrpEventObjects10 OBJECT-IDENTITY
    STATUS current
    DESCRIPTION
        "Event VRRP.10
        Changing priority due to tracking."
    ::= { vrrpEventsGroup 10 }

vrrp10-interface OBJECT-TYPE
    SYNTAX DisplayString
    MAX-ACCESS accessible-for-notify
    STATUS current
    DESCRIPTION
        "Parameter 'interface' in event VRRP.10"
    ::= { vrrpEventObjects10 1 }

vrrp10-vrid OBJECT-TYPE
    SYNTAX Integer32
    MAX-ACCESS accessible-for-notify
    STATUS current
    DESCRIPTION
        "Parameter 'vrid' in event VRRP.10"
    ::= { vrrpEventObjects10 2 }

vrrp10-oldPriority OBJECT-TYPE
    SYNTAX Integer32
    MAX-ACCESS accessible-for-notify
    STATUS current
    DESCRIPTION
        "Parameter 'oldPriority' in event VRRP.10"
    ::= { vrrpEventObjects10 3 }

vrrp10-newPriority OBJECT-TYPE
    SYNTAX Integer32
    MAX-ACCESS accessible-for-notify
    STATUS current
    DESCRIPTION
        "Parameter 'newPriority' in event VRRP.10"
    ::= { vrrpEventObjects10 4 }

vrrpEventObjects11 OBJECT-IDENTITY
    STATUS current
    DESCRIPTION
        "Event VRRP.11
        Changing delay state."
    ::= { vrrpEventsGroup 11 }

vrrp11-interface OBJECT-TYPE
    SYNTAX DisplayString
    MAX-ACCESS accessible-for-notify
    STATUS current
    DESCRIPTION
        "Parameter 'interface' in event VRRP.11"
    ::= { vrrpEventObjects11 1 }

vrrp11-vrid OBJECT-TYPE
    SYNTAX Integer32
    MAX-ACCESS accessible-for-notify
    STATUS current
    DESCRIPTION
        "Parameter 'vrid' in event VRRP.11"
    ::= { vrrpEventObjects11 2 }

vrrp11-state OBJECT-TYPE
    SYNTAX DisplayString
    MAX-ACCESS accessible-for-notify
    STATUS current
    DESCRIPTION
        "Parameter 'state' in event VRRP.11"
    ::= { vrrpEventObjects11 3 }

vrrp11-reason OBJECT-TYPE
    SYNTAX DisplayString
    MAX-ACCESS accessible-for-notify
    STATUS current
    DESCRIPTION
        "Parameter 'reason' in event VRRP.11"
    ::= { vrrpEventObjects11 4 }

vrrpEventObjects12 OBJECT-IDENTITY
    STATUS current
    DESCRIPTION
        "Event VRRP.12
        Changing preemption exception state."
    ::= { vrrpEventsGroup 12 }

vrrp12-interface OBJECT-TYPE
    SYNTAX DisplayString
    MAX-ACCESS accessible-for-notify
    STATUS current
    DESCRIPTION
        "Parameter 'interface' in event VRRP.12"
    ::= { vrrpEventObjects12 1 }

vrrp12-vrid OBJECT-TYPE
    SYNTAX Integer32
    MAX-ACCESS accessible-for-notify
    STATUS current
    DESCRIPTION
        "Parameter 'vrid' in event VRRP.12"
    ::= { vrrpEventObjects12 2 }

vrrp12-state OBJECT-TYPE
    SYNTAX DisplayString
    MAX-ACCESS accessible-for-notify
    STATUS current
    DESCRIPTION
        "Parameter 'state' in event VRRP.12"
    ::= { vrrpEventObjects12 3 }

vrrp12-reason OBJECT-TYPE
    SYNTAX DisplayString
    MAX-ACCESS accessible-for-notify
    STATUS current
    DESCRIPTION
        "Parameter 'reason' in event VRRP.12"
    ::= { vrrpEventObjects12 4 }

vrrpEventObjects13 OBJECT-IDENTITY
    STATUS current
    DESCRIPTION
        "Event VRRP.13
        An advertisement timeout has occurred too fast."
    ::= { vrrpEventsGroup 13 }

vrrp13-interface OBJECT-TYPE
    SYNTAX DisplayString
    MAX-ACCESS accessible-for-notify
    STATUS current
    DESCRIPTION
        "Parameter 'interface' in event VRRP.13"
    ::= { vrrpEventObjects13 1 }

vrrp13-vrid OBJECT-TYPE
    SYNTAX Integer32
    MAX-ACCESS accessible-for-notify
    STATUS current
    DESCRIPTION
        "Parameter 'vrid' in event VRRP.13"
    ::= { vrrpEventObjects13 2 }

vrrpEventObjects14 OBJECT-IDENTITY
    STATUS current
    DESCRIPTION
        "Event VRRP.14
        The curernt key is not valid."
    ::= { vrrpEventsGroup 14 }

vrrp14-interface OBJECT-TYPE
    SYNTAX DisplayString
    MAX-ACCESS accessible-for-notify
    STATUS current
    DESCRIPTION
        "Parameter 'interface' in event VRRP.14"
    ::= { vrrpEventObjects14 1 }

vrrp14-vrid OBJECT-TYPE
    SYNTAX Integer32
    MAX-ACCESS accessible-for-notify
    STATUS current
    DESCRIPTION
        "Parameter 'vrid' in event VRRP.14"
    ::= { vrrpEventObjects14 2 }

vrrp14-reason OBJECT-TYPE
    SYNTAX DisplayString
    MAX-ACCESS accessible-for-notify
    STATUS current
    DESCRIPTION
        "Parameter 'reason' in event VRRP.14"
    ::= { vrrpEventObjects14 3 }

vrrpEventObjects15 OBJECT-IDENTITY
    STATUS current
    DESCRIPTION
        "Event VRRP.15
        Information about the authentication."
    ::= { vrrpEventsGroup 15 }

vrrp15-interface OBJECT-TYPE
    SYNTAX DisplayString
    MAX-ACCESS accessible-for-notify
    STATUS current
    DESCRIPTION
        "Parameter 'interface' in event VRRP.15"
    ::= { vrrpEventObjects15 1 }

vrrp15-vrid OBJECT-TYPE
    SYNTAX Integer32
    MAX-ACCESS accessible-for-notify
    STATUS current
    DESCRIPTION
        "Parameter 'vrid' in event VRRP.15"
    ::= { vrrpEventObjects15 2 }

vrrp15-info OBJECT-TYPE
    SYNTAX DisplayString
    MAX-ACCESS accessible-for-notify
    STATUS current
    DESCRIPTION
        "Parameter 'info' in event VRRP.15"
    ::= { vrrpEventObjects15 3 }


vrrpNotification1 NOTIFICATION-TYPE
    OBJECTS { 
              vrrp1-generic-info 
            }
    STATUS current
    DESCRIPTION
        "Notification of Event VRRP.1

        Message: '$1'

        Parameters list:
              $1: vrrp1-generic-info

        Generic info."
    ::= { vrrpNotificationsPrefix 1 }

vrrpNotification2 NOTIFICATION-TYPE
    OBJECTS { 
              vrrp2-interface, 
              vrrp2-vrid,
              vrrp2-state,
              vrrp2-event 
            }
    STATUS current
    DESCRIPTION
        "Notification of Event VRRP.2

        Message: 'VR[$1, vrId $2] State $3, Event $4'

        Parameters list:
              $1: vrrp2-interface
              $2: vrrp2-vrid
              $3: vrrp2-state
              $4: vrrp2-event

        Virtual router event descriptor."
    ::= { vrrpNotificationsPrefix 2 }

vrrpNotification3 NOTIFICATION-TYPE
    OBJECTS { 
              vrrp3-interface, 
              vrrp3-vrid,
              vrrp3-new-state 
            }
    STATUS current
    DESCRIPTION
        "Notification of Event VRRP.3

        Message: 'VR[$1, vrId $2] changing state to $3'

        Parameters list:
              $1: vrrp3-interface
              $2: vrrp3-vrid
              $3: vrrp3-new-state

        A virtual router has changed its state."
    ::= { vrrpNotificationsPrefix 3 }

vrrpNotification4 NOTIFICATION-TYPE
    OBJECTS { 
              vrrp4-error-message 
            }
    STATUS current
    DESCRIPTION
        "Notification of Event VRRP.4

        Message: 'I ERROR, $1'

        Parameters list:
              $1: vrrp4-error-message

        An error has ocurred while receiving a VRRP Advertisement."
    ::= { vrrpNotificationsPrefix 4 }

vrrpNotification5 NOTIFICATION-TYPE
    OBJECTS { 
              vrrp5-interface, 
              vrrp5-vrid,
              vrrp5-error-message 
            }
    STATUS current
    DESCRIPTION
        "Notification of Event VRRP.5

        Message: 'VR[$1, vrId $2] I ERROR, $3'

        Parameters list:
              $1: vrrp5-interface
              $2: vrrp5-vrid
              $3: vrrp5-error-message

        An error associated to a virtual router has ocurred while receiving a
        VRRP Advertisement."
    ::= { vrrpNotificationsPrefix 5 }

vrrpNotification6 NOTIFICATION-TYPE
    OBJECTS { 
              vrrp6-interface, 
              vrrp6-vrid,
              vrrp6-priority,
              vrrp6-checksum 
            }
    STATUS current
    DESCRIPTION
        "Notification of Event VRRP.6

        Message: 'VR[$1, vrId $2] O Advertisement prio $3, cksum $4'

        Parameters list:
              $1: vrrp6-interface
              $2: vrrp6-vrid
              $3: vrrp6-priority
              $4: vrrp6-checksum

        A VRRP Advertisement has been sent."
    ::= { vrrpNotificationsPrefix 6 }

vrrpNotification7 NOTIFICATION-TYPE
    OBJECTS { 
              vrrp7-virtual-ip-address, 
              vrrp7-virtual-mac-address 
            }
    STATUS current
    DESCRIPTION
        "Notification of Event VRRP.7

        Message: 'O Gratuitous ARP-req $1/00005e0001$2'

        Parameters list:
              $1: vrrp7-virtual-ip-address
              $2: vrrp7-virtual-mac-address

        A gratuitous ARP-request has been sent."
    ::= { vrrpNotificationsPrefix 7 }

vrrpNotification8 NOTIFICATION-TYPE
    OBJECTS { 
              vrrp8-error-message 
            }
    STATUS current
    DESCRIPTION
        "Notification of Event VRRP.8

        Message: 'Internal ERROR, $1'

        Parameters list:
              $1: vrrp8-error-message

        An internal error has ocurred."
    ::= { vrrpNotificationsPrefix 8 }

vrrpNotification9 NOTIFICATION-TYPE
    OBJECTS { 
              vrrp9-interface, 
              vrrp9-vrid,
              vrrp9-state,
              vrrp9-timeout,
              vrrp9-sec 
            }
    STATUS current
    DESCRIPTION
        "Notification of Event VRRP.9

        Message: 'VR[$1, vrId $2] State $3, Waiting for preempt delay timeout ($4 $5)'

        Parameters list:
              $1: vrrp9-interface
              $2: vrrp9-vrid
              $3: vrrp9-state
              $4: vrrp9-timeout
              $5: vrrp9-sec

        Waiting for preempt delay timeout."
    ::= { vrrpNotificationsPrefix 9 }

vrrpNotification10 NOTIFICATION-TYPE
    OBJECTS { 
              vrrp10-interface, 
              vrrp10-vrid,
              vrrp10-oldPriority,
              vrrp10-newPriority 
            }
    STATUS current
    DESCRIPTION
        "Notification of Event VRRP.10

        Message: 'VR[$1, vrId $2] Track: Changing priority from $3 to $4'

        Parameters list:
              $1: vrrp10-interface
              $2: vrrp10-vrid
              $3: vrrp10-oldPriority
              $4: vrrp10-newPriority

        Changing priority due to tracking."
    ::= { vrrpNotificationsPrefix 10 }

vrrpNotification11 NOTIFICATION-TYPE
    OBJECTS { 
              vrrp11-interface, 
              vrrp11-vrid,
              vrrp11-state,
              vrrp11-reason 
            }
    STATUS current
    DESCRIPTION
        "Notification of Event VRRP.11

        Message: 'VR[$1, vrId $2] Delay is $3, reason: $4'

        Parameters list:
              $1: vrrp11-interface
              $2: vrrp11-vrid
              $3: vrrp11-state
              $4: vrrp11-reason

        Changing delay state."
    ::= { vrrpNotificationsPrefix 11 }

vrrpNotification12 NOTIFICATION-TYPE
    OBJECTS { 
              vrrp12-interface, 
              vrrp12-vrid,
              vrrp12-state,
              vrrp12-reason 
            }
    STATUS current
    DESCRIPTION
        "Notification of Event VRRP.12

        Message: 'VR[$1, vrId $2] Preemption exception is $3, reason: $4'

        Parameters list:
              $1: vrrp12-interface
              $2: vrrp12-vrid
              $3: vrrp12-state
              $4: vrrp12-reason

        Changing preemption exception state."
    ::= { vrrpNotificationsPrefix 12 }

vrrpNotification13 NOTIFICATION-TYPE
    OBJECTS { 
              vrrp13-interface, 
              vrrp13-vrid 
            }
    STATUS current
    DESCRIPTION
        "Notification of Event VRRP.13

        Message: 'VR[$1, vrId $2] Advertisement timeout too fast. It will be ignored'

        Parameters list:
              $1: vrrp13-interface
              $2: vrrp13-vrid

        An advertisement timeout has occurred too fast."
    ::= { vrrpNotificationsPrefix 13 }

vrrpNotification14 NOTIFICATION-TYPE
    OBJECTS { 
              vrrp14-interface, 
              vrrp14-vrid,
              vrrp14-reason 
            }
    STATUS current
    DESCRIPTION
        "Notification of Event VRRP.14

        Message: 'VR[$1, vrId $2] Invalid authentication key: $3'

        Parameters list:
              $1: vrrp14-interface
              $2: vrrp14-vrid
              $3: vrrp14-reason

        The curernt key is not valid."
    ::= { vrrpNotificationsPrefix 14 }

vrrpNotification15 NOTIFICATION-TYPE
    OBJECTS { 
              vrrp15-interface, 
              vrrp15-vrid,
              vrrp15-info 
            }
    STATUS current
    DESCRIPTION
        "Notification of Event VRRP.15

        Message: 'VR[$1, vrId $2] Authentication info: $3'

        Parameters list:
              $1: vrrp15-interface
              $2: vrrp15-vrid
              $3: vrrp15-info

        Information about the authentication."
    ::= { vrrpNotificationsPrefix 15 }


END
