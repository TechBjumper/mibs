-- Title:         Fibronics' MIB  
-- MIB Module :   Private MIB for  NM349
-- Version    :   V1.0
-- Date       :   Jan 1, 1995
-- By         :   Gadi K.
-- Contact    :   Edna Ganon
-- Email:     :   edna@fibronics.co.il 
-- 
-- Description:   NM349 private system mib
-- Copyright (c) 1994 Fibronics International

        Fib-sys DEFINITIONS ::= BEGIN
		  
		  IMPORTS OBJECT-TYPE, internet, IpAddress FROM SNMPv2-SMI
		  DisplayString FROM SNMPv2-TC;

        private      OBJECT IDENTIFIER ::= { internet 4 }
        enterprises  OBJECT IDENTIFIER ::= { private 1 }
	fibronics    OBJECT IDENTIFIER ::= { enterprises 22 }
        trap            OBJECT IDENTIFIER ::= { fibronics 3 }
        fm800           OBJECT IDENTIFIER ::= { fibronics 51 }
        traprun         OBJECT IDENTIFIER ::= { trap 1 }
	traperm         OBJECT IDENTIFIER ::= { trap 2 }
        fmsystem        OBJECT IDENTIFIER ::= { fm800 1 }
        fmslot          OBJECT IDENTIFIER ::= { fm800 2 }
        fmlu            OBJECT IDENTIFIER ::= { fm800 3 }
        fmdiag          OBJECT IDENTIFIER ::= { fm800 5 }
        fmdebug         OBJECT IDENTIFIER ::= { fm800 6 }
        fmsystemrun     OBJECT IDENTIFIER ::= { fmsystem 1 }
        fmsystemperm    OBJECT IDENTIFIER ::= { fmsystem 2 }


--   Trap runtime objects

rTrapAddrTable	OBJECT-TYPE
	SYNTAX  SEQUENCE OF RTrapAddrEntry
	ACCESS  not-accessible
	STATUS  mandatory
	DESCRIPTION "Table of managers to which traps
  		     must be sent. Up to 10 
		     entries in table"
	::= { traprun 1 }

rTrapAddrEntry	OBJECT-TYPE
	SYNTAX  RTrapAddrEntry
	ACCESS  read-only
	STATUS  mandatory
		DESCRIPTION ""
	INDEX   { rTrapAddrAddr }
	::= { rTrapAddrTable 1 }

RTrapAddrEntry ::= SEQUENCE {
	rTrapAddrAddr
		IpAddress,
	rTrapAddrComm
	        OCTET STRING,
	rTrapAddrVer
		INTEGER,
	rTrapAddrType
		OCTET STRING,
	rTrapAddrState
		INTEGER,
	rTrapAddrFlag
		INTEGER,
	rTrapAddrAge
		INTEGER
	}

rTrapAddrAddr 	OBJECT-TYPE
	SYNTAX	IpAddress
        ACCESS  read-write
        STATUS  mandatory
	DESCRIPTION "IP address of entity
		     requesting event notification"
	::= { rTrapAddrEntry 1 }

rTrapAddrComm 	OBJECT-TYPE
        SYNTAX  OCTET STRING
        ACCESS  read-write
        STATUS  mandatory
	DESCRIPTION "Community name the receiving
 		     entity will expect.
                    When reading the instance of this
                    object the value has no meaning."
	::= { rTrapAddrEntry 2 }

rTrapAddrVer  	OBJECT-TYPE
	SYNTAX  INTEGER
        ACCESS  read-write
        STATUS  mandatory
	DESCRIPTION "Version number supported by
		     destination node"
	::= { rTrapAddrEntry 3 }

rTrapAddrType 	OBJECT-TYPE
	SYNTAX  OCTET STRING
        ACCESS  read-write
        STATUS  mandatory
	DESCRIPTION "Type of event that should be
		     reported to this address,
                     bit 0 - authentication trap
		     bit 1 - other SNMP traps
		     bit 2 - Error Traps
		     bit 3 - Diagnostic Traps
		     bit 4 - Debug Traps
		     bit 5 - Enterprise Traps other than fmDiagGenericTrap"
	::= { rTrapAddrEntry 4 }

rTrapAddrState	OBJECT-TYPE
	SYNTAX  INTEGER {
		active(1),
		inactive(2)
		}
        ACCESS  read-write
        STATUS  mandatory
	DESCRIPTION "Determines status of this entry"
	::= { rTrapAddrEntry 5 }

rTrapAddrFlag	OBJECT-TYPE
	SYNTAX	INTEGER {
		fixed(0),
		removable(1)
		}
	ACCESS	read-write
	STATUS	mandatory
	DESCRIPTION "If the entry is fixed, it can not
		be deleted because of aging"
	::= { rTrapAddrEntry 6 }

rTrapAddrAge	OBJECT-TYPE
	SYNTAX	INTEGER
	ACCESS	read-only
	STATUS	mandatory
	DESCRIPTION "Aging time of the entry (in sec)"
	::= { rTrapAddrEntry 7 }

rTrapLearning	OBJECT-TYPE
	SYNTAX	INTEGER {
		disable(0),
		enable(1)
		}
	ACCESS	read-only
	STATUS  mandatory
	DESCRIPTION "Learn the addresses of the managers
		automatically."
	::= { traprun 2 }

rTrapAging	OBJECT-TYPE
	SYNTAX	INTEGER 
	ACCESS	read-only
	STATUS	mandatory
	DESCRIPTION "Time in sec. until we erase a trap
		entry"
	::= { traprun 3 }


--   Trap permanents objects

pTrapAddrTable	OBJECT-TYPE
	SYNTAX  SEQUENCE OF PTrapAddrEntry
	ACCESS  not-accessible
	STATUS  mandatory
	DESCRIPTION "Table of managers to which traps
  		     must be sent. Up to 10 
		     entries in table"
	::= { traperm 1 }

pTrapAddrEntry	OBJECT-TYPE
	SYNTAX  PTrapAddrEntry
	ACCESS  read-write
	STATUS  mandatory
		DESCRIPTION ""
	INDEX   { pTrapAddrAddr }
	::= { pTrapAddrTable 1 }

PTrapAddrEntry ::= SEQUENCE {
	pTrapAddrAddr
		IpAddress,
	pTrapAddrComm
	        OCTET STRING,
	pTrapAddrVer
		INTEGER,
	pTrapAddrType
		OCTET STRING,
	pTrapAddrState
		INTEGER
	}

pTrapAddrAddr 	OBJECT-TYPE
	SYNTAX	IpAddress
        ACCESS  read-write
        STATUS  mandatory
	DESCRIPTION "IP address of entity
		     requesting event notification"
	::= { pTrapAddrEntry 1 }

pTrapAddrComm 	OBJECT-TYPE
        SYNTAX  OCTET STRING
        ACCESS  read-write
        STATUS  mandatory
	DESCRIPTION "Community name the receiving
 		     entity will expect.
                    When reading the instance of this
                    object the value has no meaning."
	::= { pTrapAddrEntry 2 }

pTrapAddrVer  	OBJECT-TYPE
	SYNTAX  INTEGER
        ACCESS  read-write
        STATUS  mandatory
	DESCRIPTION "Version number supported by
		     destination node"
	::= { pTrapAddrEntry 3 }

pTrapAddrType 	OBJECT-TYPE
	SYNTAX  OCTET STRING
        ACCESS  read-write
        STATUS  mandatory
	DESCRIPTION "Type of event that should be
		     reported to this address,
                     bit 0 - authentication trap
		     bit 1 - other SNMP traps
		     bit 2 - Error Traps
		     bit 3 - Diagnostic Traps
		     bit 4 - Debug Traps
		     bit 5 - all Enterprise Traps other than fmDiagGenericTrap"
	::= { pTrapAddrEntry 4 }

pTrapAddrState 	OBJECT-TYPE
	SYNTAX  INTEGER {
		active(1),
		inactive(2)
		}
        ACCESS  read-write
        STATUS  mandatory
	DESCRIPTION "Determines status of this entry"
	::= { pTrapAddrEntry 5 }
	
pTrapLearning	OBJECT-TYPE
	SYNTAX	INTEGER {
		disable(0),
		enable(1)
		}
	ACCESS	read-write
	STATUS  mandatory
	DESCRIPTION "Learn the addresses of the managers
		automatically."
	::= { traperm 2 }

pTrapAging	OBJECT-TYPE
	SYNTAX	INTEGER 
	ACCESS	read-write
	STATUS	mandatory
	DESCRIPTION "Time in sec. until we erase a trap
		entry"
	::= { traperm 3 }

------------------------------------------------

-- Fibronics System Group RunTime
------------------------------------------------

fmSystemReset	OBJECT-TYPE
	SYNTAX  INTEGER {
		cold-reset(0),
		warm-reset(1),
		power-up(2),
		meaning-less-value(127)
		}
	ACCESS  read-write
	STATUS  mandatory
	DESCRIPTION "Resetting the CARD.
                    When reading the instance of this
	            object the value has no meaning.
		    cold reset is performed with selftest ,
		    while warm start is performed without
		    selftest"

	::= { fmsystemrun 4 }

fmSystemSelfTestLevel	OBJECT-TYPE
	SYNTAX	INTEGER {
		none(0),
		partial(1),
		full(2),
		extended(3)
		}
	ACCESS	read-write
	STATUS	mandatory
	DESCRIPTION "Type of self test to be
		     executed upon cold-reset.
		     Note: upon write, executes,
			no difference between levels"
	::= { fmsystemrun 5 }

fmSystemIpAddr		OBJECT-TYPE
	SYNTAX	IpAddress
	ACCESS	read-only
	STATUS  mandatory
	DESCRIPTION "IP address of the agent"
	::= { fmsystemrun 7 }

fmSystemIPNetMask	OBJECT-TYPE
	SYNTAX	IpAddress
	ACCESS	read-only
	STATUS	mandatory
	DESCRIPTION "IP Network Mask"
	::= { fmsystemrun 8 }

fmSystemIPDefGway	OBJECT-TYPE
	SYNTAX	IpAddress
	ACCESS	read-only
	STATUS	mandatory
	DESCRIPTION "Default Gateway Address"
	::= { fmsystemrun 9 }

fmSystemFileServer     OBJECT-TYPE
        SYNTAX  IpAddress
        ACCESS  read-write
        STATUS  mandatory
        DESCRIPTION "IP address to which a TFTP for boot is sent."
        ::= { fmsystemrun 10 }

fmSystemBootFile       OBJECT-TYPE
        SYNTAX  OCTET STRING
        ACCESS  read-only
        STATUS  mandatory
        DESCRIPTION "Path and file name that is
                   sent as a TFTP request"
        ::= { fmsystemrun 11 }

fmSystemDownLoad   OBJECT-TYPE
        SYNTAX  INTEGER {
                download(1),
		meaning-less-value(127)
                }
        ACCESS  read-write
        STATUS  mandatory
        DESCRIPTION "Downloading the EDB.
                     When reading the instance of this
	             object the value has no meaning."
        ::= { fmsystemrun 13 }

fmSystemSlipIpAddr          OBJECT-TYPE
        SYNTAX  IpAddress
        ACCESS  read-only
        STATUS  mandatory
        DESCRIPTION "SLIP IP address.
	            This is object is available
		    only when slip interface exist "
        ::= { fmsystemrun 14 }

fmSystemSlipIPNetMask       OBJECT-TYPE
        SYNTAX  IpAddress
        ACCESS  read-only
        STATUS  mandatory
        DESCRIPTION "SLIP IP Network Mask
	            This is object is available
		    only when slip interface exist "
        ::= { fmsystemrun 15 }

fmSystemSlipBaudRate OBJECT-TYPE
        SYNTAX  INTEGER {
                baud1200(0),
                baud2400(1),
                baud4800(2),
                baud9600(3),
                baud19200(4),
                baud38400(5)
                }
	 
        ACCESS  read-only
        STATUS  mandatory
        DESCRIPTION "SLIP Baud rate
	             This is object is available
		     only when slip interface exist "
        ::= { fmsystemrun 16 }

fmSystemSlipParity   OBJECT-TYPE
        SYNTAX  INTEGER {
                none(0),
                odd(1),
                even(2)
                }
        ACCESS  read-only
        STATUS  mandatory
        DESCRIPTION "SLIP Parity
                     This is object is available
	             only when slip interface exist "
        ::= { fmsystemrun 17 }

fmSystemSlipStopBits	OBJECT-TYPE
        SYNTAX  INTEGER {
                one(0),
                two(1)
                }
        ACCESS  read-only
        STATUS  mandatory
        DESCRIPTION "SLIP Stop Bits 
                     This is object is available
	             only when slip interface exist "
        ::= { fmsystemrun 18 }

fmSystemLastSourceIpAddr    OBJECT-TYPE
        SYNTAX  IpAddress
        ACCESS  read-only
        STATUS  mandatory
        DESCRIPTION "The source IP address, extracted from the last 
                     IP message"
        ::= { fmsystemrun 20 }

fmSystemLastDestinationIpAddr  OBJECT-TYPE
        SYNTAX  IpAddress
        ACCESS  read-only
        STATUS  mandatory
        DESCRIPTION "The destination IP address in the the last 
                     IP message. It may be either fmSystemIpAddr or fmSystemSlipIpAddr"
        ::= { fmsystemrun 21 }


------------------------------------------------
--  System Group Permanent
------------------------------------------------


pfmSystemIpAddr		OBJECT-TYPE
	SYNTAX	IpAddress
	ACCESS	read-write
	STATUS  mandatory
	DESCRIPTION "IP address of the agent"
	::= { fmsystemperm 7 }

pfmSystemIPNetMask	OBJECT-TYPE
	SYNTAX	IpAddress
	ACCESS	read-write
	STATUS	mandatory
	DESCRIPTION "IP Network Mask"
	::= { fmsystemperm 8 }

pfmSystemIPDefGway	OBJECT-TYPE
	SYNTAX	IpAddress
	ACCESS	read-write
	STATUS	mandatory
	DESCRIPTION "Default Gateway Address"
	::= { fmsystemperm 9 }

pfmSystemFileServer	OBJECT-TYPE
	SYNTAX  IpAddress
	ACCESS  read-write
	STATUS  mandatory
	DESCRIPTION "IP address to which a TFTP for boot is sent."
	::= { fmsystemperm 10 }

pfmSystemBootFile	OBJECT-TYPE
	SYNTAX  OCTET STRING
	ACCESS  read-write
	STATUS  mandatory
	DESCRIPTION "Path and file name that is 
		   sent as a TFTP request"
	::= { fmsystemperm 11 }

pfmSystemReadCommunity	OBJECT-TYPE
	SYNTAX	OCTET STRING
	ACCESS	read-write
	STATUS  mandatory
	DESCRIPTION "Community string for reading
                    When reading the instance of this
                    object the value has no meaning."

	::= { fmsystemperm 13 }

pfmSystemWriteCommunity	OBJECT-TYPE
	SYNTAX	OCTET STRING
	ACCESS	read-write
	STATUS	mandatory
	DESCRIPTION "Community string for writing
                    When reading the instance of this
                    object the value has no meaning."
	::= { fmsystemperm 14 }
	
pfmSystemSlipIpAddr          OBJECT-TYPE
        SYNTAX  IpAddress
        ACCESS  read-write
        STATUS  mandatory
        DESCRIPTION "SLIP IP address 
                     This is object is available
	             only when slip interface exist "
        ::= { fmsystemperm 15 }

pfmSystemSlipIPNetMask       OBJECT-TYPE
        SYNTAX  IpAddress
        ACCESS  read-write
        STATUS  mandatory
        DESCRIPTION "SLIP IP Network Mask
                     This is object is available
	             only when slip interface exist "
        ::= { fmsystemperm 16 }

	
pfmSystemSlipBaudRate OBJECT-TYPE
        SYNTAX  INTEGER {
                baud1200(0),
                baud2400(1),
                baud4800(2),
                baud9600(3),
                baud19200(4),
                baud38400(5)
                }
        ACCESS  read-write
        STATUS  mandatory
        DESCRIPTION "SLIP Baud rate 
                     This is object is available
	             only when slip interface exist "
        ::= { fmsystemperm 17 }


pfmSystemSlipParity   OBJECT-TYPE
        SYNTAX  INTEGER {
                none(0),
                odd(1),
                even(2)
                }
        ACCESS  read-write
        STATUS  mandatory
        DESCRIPTION "SLIP Parity 
                     This is object is available
	             only when slip interface exist "
        ::= { fmsystemperm 18 }

pfmSystemSlipStopBits    OBJECT-TYPE
        SYNTAX  INTEGER {
                one(0),
                two(1)
                }
        ACCESS  read-write
        STATUS  mandatory
        DESCRIPTION "SLIP Stop Bits 
                     This is object is available
	             only when slip interface exist "
        ::= { fmsystemperm 19 }

-------------------------------------------------------
--  Diagnostic Group
-------------------------------------------------------

fmDiagTrapInfo  OBJECT-TYPE
        SYNTAX  DisplayString  (SIZE (0..255))
        ACCESS  read-only
        STATUS  mandatory
        DESCRIPTION "Used for generic traps. The first word
                is the trap code. The rest of the string is
                the extra information. Contains CR and LF char."
        ::= { fmdiag 2 }

	
fmDiagFaultTable  OBJECT-TYPE
        SYNTAX  SEQUENCE OF FmDiagFaultEntry 
        ACCESS  not-accessible
	STATUS  optional
  	 DESCRIPTION "Table of fault reports from the agent"
	 ::= { fmdiag 3 }


fmDiagFaultEntry  OBJECT-TYPE
        SYNTAX  FmDiagFaultEntry
	ACCESS  not-accessible
	STATUS  optional
		DESCRIPTION ""
  	INDEX   { fmDiagFaultIndex}
	::=     { fmDiagFaultTable 1 }


FmDiagFaultEntry ::= SEQUENCE {
        fmDiagFaultIndex
	        INTEGER,
        fmDiagFaultReport
	        DisplayString
	}


fmDiagFaultIndex OBJECT-TYPE
        SYNTAX  INTEGER
	ACCESS  read-only
	STATUS  optional
        DESCRIPTION "The fault index in the
  			      fault table"
        ::= { fmDiagFaultEntry 1 }			      		      
						
fmDiagFaultReport	OBJECT-TYPE
	SYNTAX	DisplayString  (SIZE (0..255))
	ACCESS	read-only
	STATUS	optional
  	DESCRIPTION "Get the faults detected by the agent"
        ::= { fmDiagFaultEntry 2 }			      		      

	

fmDiagDebug       OBJECT-TYPE
        SYNTAX  INTEGER {
                normal-mode(1),
                debug-mode(2)
                }
        ACCESS  read-write
        STATUS  mandatory
        DESCRIPTION "This object is for factory use only. Users must not
		     write into this variable or improper operation
		     can occur."
        ::= { fmdiag 4 }

fmDiagDeleteFaults       OBJECT-TYPE
        SYNTAX  INTEGER {
                no-delete(1),
                delete(2)
                }
        ACCESS  read-write
        STATUS  mandatory
        DESCRIPTION "setting this object to delete(2) causes the fault
	table in the e2 and it's ram image to be initialized, setting the
	object to no-delete(1) does not effect the fault table.
	when reading the object the value no-delete(1) will always be returned"
        ::= { fmdiag 5 }

	

-- fm800 system traps


fmDiagGenericTrap	TRAP-TYPE
	ENTERPRISE fm800
	VARIABLES { fmDiagTrapInfo }
	DESCRIPTION "Generic Trap information"
	::= 30

	END
