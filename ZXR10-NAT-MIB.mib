--  ************************************************
--  $Id: nat.mib  2012-11-26 12:17:08Z xiaoliujun $
--
--  nat.mib: ZXR10 NAT MIB file
--
--  Nov. 2012, xiaoliujun 
--
--  Copyright(c) 2008 by ZTE Corporaton
--  All rights reservered
--
--  ************************************************

   ZXR10-NAT-MIB DEFINITIONS ::= BEGIN

   IMPORTS
   MODULE-IDENTITY,OBJECT-TYPE, Integer32, Unsigned32,enterprises,Counter64,IpAddress
   FROM SNMPv2-SMI
    
   Ipv6Address   
   FROM IPV6-TC
      
   DisplayString, RowStatus,TEXTUAL-CONVENTION
   FROM SNMPv2-TC;   
   
   
   zxr10NatMIB MODULE-IDENTITY
       LAST-UPDATED "201704141058Z"
       ORGANIZATION "ZTE Corporation"
       CONTACT-INFO
           "       Yi Hong
           Tel:    +86-25-52870000
           E-Mail: yi.hong@zte.com.cn "
           DESCRIPTION
           "The MIB module to describe NAT."    
                
       REVISION "201704141058Z"  
       DESCRIPTION
           "modify:    zxr10NatUploadFtpUserName
                       zxr10NatUploadFtpUserPassword
                       zxr10NatUploadFtpFileName
                       zxr10NatUploadFtpVrfName
                       change minimum length from 1 to 0"    
       REVISION "201509070000Z"
       DESCRIPTION
           "modify:    zxr10NatCntSoftware
                       zxr10NatCntSoftwire"
       REVISION "201312100000Z"
       DESCRIPTION
           "add:       zxr10NatUploadFtpGroup
                       zxr10NatCntIpv4Address
                       zxr10NatCntSoftware"
       REVISION "201301170000Z"
       DESCRIPTION 
           "Initial version of this MIB module."     

    ::= { zxr10RosngMIB 600 }
       
   zte OBJECT IDENTIFIER ::= { enterprises 3902 }
   zxr10 OBJECT IDENTIFIER ::= { zte 3}
   zxr10RosngMIB OBJECT IDENTIFIER ::= { zxr10 6000}
  
   
   Zxr10NatUsage ::= TEXTUAL-CONVENTION
       DISPLAY-HINT    "d-2"
       STATUS          current
       DESCRIPTION     "suggests that a Hundredths value of 1234 be 
                       rendered as 12.34."                                 
       SYNTAX          Integer32 (0..10000)                            
                                 
       

   
   -------------------------------------------------------
   --zxr10NatObjects
   -------------------------------------------------------   
   zxr10NatObjects OBJECT IDENTIFIER ::= { zxr10NatMIB 2}  
   
    --zxr10NatCountersObjects     
    zxr10NatCountersObjects OBJECT IDENTIFIER ::= { zxr10NatObjects 1} 
    
        --zxr10NatGlobalCounters 
        zxr10NatGlobalCounters OBJECT IDENTIFIER ::= { zxr10NatCountersObjects 1}  
    
            zxr10NatCntTranslates OBJECT-TYPE
                   SYNTAX  Counter64
                   MAX-ACCESS  read-only
                   STATUS  current
                   DESCRIPTION
                           "The number of packets to which NAT has been applied."
                   ::= { zxr10NatGlobalCounters 1 }
        
            zxr10NatCntOOP OBJECT-TYPE
                   SYNTAX  Counter64
                   MAX-ACCESS  read-only
                   STATUS  current
                   DESCRIPTION
                           "The number of packets to which NAT could not be applied because no external port was available."
                   ::= { zxr10NatGlobalCounters 2 }
                                   
            zxr10NatCntQuota OBJECT-TYPE
                   SYNTAX  Counter64
                   MAX-ACCESS  read-only
                   STATUS  current
                   DESCRIPTION
                           "The number of packets to which NAT could not be applied because of exceeded quotas. 
                           Quotas include absolute limits as well as limits on rate of allocation."
                   ::= { zxr10NatGlobalCounters 5 }  
                      
            zxr10NatCntMappings OBJECT-TYPE
                   SYNTAX  Counter64
                   MAX-ACCESS  read-only
                   STATUS  current
                   DESCRIPTION
                           "The number of active mappings."
                   ::= { zxr10NatGlobalCounters 6 }  
                   
            zxr10NatCntIpv4Address OBJECT-TYPE
                   SYNTAX  Unsigned32
                   MAX-ACCESS  read-only
                   STATUS  current
                   DESCRIPTION
                           "The number of IPv4 address with NAT SR users."
                   ::= { zxr10NatGlobalCounters 10 }  
               
            zxr10NatCntSoftwire OBJECT-TYPE
                   SYNTAX  Unsigned32
                   MAX-ACCESS  read-only
                   STATUS  current
                   DESCRIPTION
                           "The number of IPv6 softwire ,include dislite users and nat64 users."
                   ::= { zxr10NatGlobalCounters 11 }                           
     -------------------------------------------------------
     --zxr10NatCntInstTable
     ------------------------------------------------------- 
     zxr10NatCntInstTable OBJECT-TYPE
              SYNTAX  SEQUENCE OF Zxr10NatCntInstEntry
              MAX-ACCESS  not-accessible
              STATUS  current
              DESCRIPTION
                      "Information of the NAT instance "
              ::= { zxr10NatCountersObjects 9}     
   
          -------------------------------------------------------
          --zxr10NatCntInstEntry 
          ------------------------------------------------------- 
          zxr10NatCntInstEntry OBJECT-TYPE
              SYNTAX  Zxr10NatCntInstEntry
              MAX-ACCESS  not-accessible
              STATUS  current
              DESCRIPTION
                      "Information of the NAT instance."
              INDEX   { 
                        zxr10NatCntInstName
                      }
              ::= { zxr10NatCntInstTable 1 }   
              
              Zxr10NatCntInstEntry ::=
                  SEQUENCE{ 
                            zxr10NatCntInstName
                            DisplayString,
                            zxr10NatCntInstIndex
                            Unsigned32,
                            zxr10NatCntInstTranslates
                            Counter64,
                            zxr10NatCntInstOOP 
                            Counter64,
                            zxr10NatCntInstQuota 
                            Counter64,
                            zxr10NatCntInstMappings 
                            Counter64 
                            
                          }
    
                zxr10NatCntInstName OBJECT-TYPE
                    SYNTAX  DisplayString (SIZE(1..31))
                    MAX-ACCESS  not-accessible
                    STATUS  current
                    DESCRIPTION
                            "The instance name of this instance."                     
                    ::= { zxr10NatCntInstEntry 1 } 
                    
                zxr10NatCntInstIndex OBJECT-TYPE
                     SYNTAX  Unsigned32
                     MAX-ACCESS read-only
                     STATUS     current
                     DESCRIPTION                
                               "The instance index of this instance."
                     ::= { zxr10NatCntInstEntry 2 }  
                   
                zxr10NatCntInstTranslates OBJECT-TYPE
                       SYNTAX  Counter64
                       MAX-ACCESS  read-only
                       STATUS  current
                       DESCRIPTION
                               "The number of packets to which NAT has been applied."
                       ::= { zxr10NatCntInstEntry 3 }
            
                zxr10NatCntInstOOP OBJECT-TYPE
                       SYNTAX  Counter64
                       MAX-ACCESS  read-only
                       STATUS  current
                       DESCRIPTION
                               "The number of packets to which NAT could not be applied because no external port was available."
                       ::= { zxr10NatCntInstEntry 4 }
                       
                zxr10NatCntInstQuota OBJECT-TYPE
                       SYNTAX  Counter64
                       MAX-ACCESS  read-only
                       STATUS  current
                       DESCRIPTION
                               "The number of packets to which NAT could not be applied because of exceeded quotas. 
                               Quotas include absolute limits as well as limits on rate of allocation."
                       ::= { zxr10NatCntInstEntry 7 }  
                          
                zxr10NatCntInstMappings OBJECT-TYPE
                       SYNTAX  Counter64
                       MAX-ACCESS  read-only
                       STATUS  current
                       DESCRIPTION
                               "The number of active mappings."
                       ::= { zxr10NatCntInstEntry 8 }  
                                                               
    --zxr10NatSubscribersObject     
    zxr10NatSubscribersObject OBJECT IDENTIFIER ::= { zxr10NatObjects 2} 

     -------------------------------------------------------
     --zxr10NatIPv4SubscribersTable
     ------------------------------------------------------- 
     zxr10NatIPv4SubscribersTable OBJECT-TYPE
              SYNTAX  SEQUENCE OF Zxr10NatIPv4SubscribersEntry
              MAX-ACCESS  not-accessible
              STATUS  current
              DESCRIPTION
                      "Information of the NAT IPv4 subscriber."
              ::= { zxr10NatSubscribersObject 1}     
   
          -------------------------------------------------------
          --zxr10NatIPv4SubscribersEntry 
          ------------------------------------------------------- 
          zxr10NatIPv4SubscribersEntry OBJECT-TYPE
              SYNTAX  Zxr10NatIPv4SubscribersEntry
              MAX-ACCESS  not-accessible
              STATUS  current
              DESCRIPTION
                      "Information of the NAT IPv4 subscriber."
              INDEX   { 
                        zxr10NatIPv4SubscribersType,  
                        zxr10NatIPv4SubscribersVrf,
                        zxr10NatIPv4SubscribersIPv4Address
                      }
              ::= { zxr10NatIPv4SubscribersTable 1 }   
              
              Zxr10NatIPv4SubscribersEntry ::=
                  SEQUENCE{ 
                            zxr10NatIPv4SubscribersType 
                            INTEGER,
                            zxr10NatIPv4SubscribersVrf
                            DisplayString,
                            zxr10NatIPv4SubscribersIPv4Address
                            IpAddress,
                            zxr10NatIPv4SubscribersInstName
                            DisplayString,
                            zxr10NatIPv4SubscribersPool
                            DisplayString,  
                            zxr10NatIPv4SubscribersCntTranslates
                            Counter64 ,
                            zxr10NatIPv4SubscribersCntMappings 
                            Unsigned32              
                          }

            zxr10NatIPv4SubscribersType OBJECT-TYPE
                   SYNTAX   INTEGER
                            {
                                unknown(0), 
                                sr-nat44(2), 
                                bras-nat44(3)
                            }

                   MAX-ACCESS  not-accessible
                   STATUS  current
                   DESCRIPTION
                           "The type of this IPv4 subscriber."                     
                   ::= { zxr10NatIPv4SubscribersEntry 1 }


            zxr10NatIPv4SubscribersVrf OBJECT-TYPE
                   SYNTAX  DisplayString(SIZE(0..35))
                   MAX-ACCESS  not-accessible
                   STATUS  current
                   DESCRIPTION
                           "The VRF name of this IPv4 subscriber."
                   ::= { zxr10NatIPv4SubscribersEntry 2 }
    
            zxr10NatIPv4SubscribersIPv4Address OBJECT-TYPE
                   SYNTAX  IpAddress
                   MAX-ACCESS  not-accessible
                   STATUS  current
                   DESCRIPTION
                           "The IPv4 address of this IPv4 subscriber."
                   ::= { zxr10NatIPv4SubscribersEntry 3 }
        
            zxr10NatIPv4SubscribersInstName OBJECT-TYPE
                   SYNTAX  DisplayString(SIZE(1..31)) 
                   MAX-ACCESS  read-only
                   STATUS  current
                   DESCRIPTION
                           "The instance name of this IPv4 subscriber."
                   ::= { zxr10NatIPv4SubscribersEntry 4 }
       
            zxr10NatIPv4SubscribersPool OBJECT-TYPE
                   SYNTAX  DisplayString(SIZE(1..31))
                   MAX-ACCESS  read-only
                   STATUS  current
                   DESCRIPTION
                           "The pool name of this IPv4 subscriber."
                   ::= { zxr10NatIPv4SubscribersEntry 5 }  
                   
            zxr10NatIPv4SubscribersCntTranslates OBJECT-TYPE
                   SYNTAX  Counter64
                   MAX-ACCESS  read-only
                   STATUS  current
                   DESCRIPTION
                           "The number of packets to which this IPv4 subscriber has been applied."
                   ::= { zxr10NatIPv4SubscribersEntry 6 } 
        
            zxr10NatIPv4SubscribersCntMappings OBJECT-TYPE
                   SYNTAX  Unsigned32
                   MAX-ACCESS  read-only
                   STATUS  current
                   DESCRIPTION
                           "The number of active mappings of this IPv4 subscriber."
                   ::= { zxr10NatIPv4SubscribersEntry 11 }
                   
                   
     -------------------------------------------------------
     --zxr10NatIPv6SubscribersTable
     ------------------------------------------------------- 
     zxr10NatIPv6SubscribersTable OBJECT-TYPE
              SYNTAX  SEQUENCE OF Zxr10NatIPv6SubscribersEntry
              MAX-ACCESS  not-accessible
              STATUS  current
              DESCRIPTION
                      "Information of the NAT IPv6 subscriber."
              ::= { zxr10NatSubscribersObject 2}     
   
          -------------------------------------------------------
          --zxr10NatIPv6SubscribersEntry 
          ------------------------------------------------------- 
          zxr10NatIPv6SubscribersEntry OBJECT-TYPE
              SYNTAX  Zxr10NatIPv6SubscribersEntry
              MAX-ACCESS  not-accessible
              STATUS  current
              DESCRIPTION
                      "Information of the NAT IPv6 subscriber."
              INDEX   { 
                        zxr10NatIPv6SubscribersType,
                        zxr10NatIPv6SubscribersVrf,
                        zxr10NatIPv6SubscribersAftrAddress,
                        zxr10NatIPv6SubscribersIPv6Address
                      }
              ::= { zxr10NatIPv6SubscribersTable 1 }   
              
              Zxr10NatIPv6SubscribersEntry ::=
                  SEQUENCE{ 
                            zxr10NatIPv6SubscribersType
                            INTEGER, 
                            zxr10NatIPv6SubscribersVrf
                            DisplayString,
                            zxr10NatIPv6SubscribersAftrAddress
                            Ipv6Address,
                            zxr10NatIPv6SubscribersIPv6Address 
                            Ipv6Address,
                            zxr10NatIPv6SubscribersInstName
                            DisplayString,
                            zxr10NatIPv6SubscribersPool
                            DisplayString,   
                            zxr10NatIPv6SubscribersCntTranslates
                            Counter64,
                            zxr10NatIPv6SubscribersCntMappings 
                            Unsigned32                          
                          }

            zxr10NatIPv6SubscribersType OBJECT-TYPE
                   SYNTAX   INTEGER
                            {
                                unknown(0), 
                                standalone(1)
                            }
                   MAX-ACCESS  not-accessible
                   STATUS  current
                   DESCRIPTION
                           "The type of this IPv6 subscriber."                    
                   ::= { zxr10NatIPv6SubscribersEntry 1 }


            zxr10NatIPv6SubscribersVrf OBJECT-TYPE
                   SYNTAX  DisplayString(SIZE(0..35))
                   MAX-ACCESS  not-accessible
                   STATUS  current
                   DESCRIPTION
                           "The VRF name of this IPv6 subscriber."
                   ::= { zxr10NatIPv6SubscribersEntry 2 }
    
            zxr10NatIPv6SubscribersAftrAddress OBJECT-TYPE
                   SYNTAX  Ipv6Address
                   MAX-ACCESS  not-accessible
                   STATUS  current
                   DESCRIPTION
                           "The AFTR address of this IPv6 subscriber."
                   ::= { zxr10NatIPv6SubscribersEntry 3 }

            zxr10NatIPv6SubscribersIPv6Address OBJECT-TYPE
                   SYNTAX  Ipv6Address
                   MAX-ACCESS  not-accessible
                   STATUS  current
                   DESCRIPTION
                           "The CPE address of this IPv6 subscriber."
                   ::= { zxr10NatIPv6SubscribersEntry 4 }
        
            zxr10NatIPv6SubscribersInstName OBJECT-TYPE
                   SYNTAX  DisplayString(SIZE(1..31)) 
                   MAX-ACCESS  read-only
                   STATUS  current
                   DESCRIPTION
                           "The instance name of this IPv6 subscriber."
                   ::= { zxr10NatIPv6SubscribersEntry 5 }
       
            zxr10NatIPv6SubscribersPool OBJECT-TYPE
                   SYNTAX  DisplayString(SIZE(1..31))
                   MAX-ACCESS  read-only
                   STATUS  current
                   DESCRIPTION
                           "The pool name of this IPv6 subscriber."
                   ::= { zxr10NatIPv6SubscribersEntry 6 }
                     
            zxr10NatIPv6SubscribersCntTranslates OBJECT-TYPE
                   SYNTAX  Counter64
                   MAX-ACCESS  read-only
                   STATUS  current
                   DESCRIPTION
                           "The number of packets to which this IPv6 subscriber has been applied."
                   ::= { zxr10NatIPv6SubscribersEntry 7 }
    
            zxr10NatIPv6SubscribersCntMappings OBJECT-TYPE
                   SYNTAX  Unsigned32
                   MAX-ACCESS  read-only
                   STATUS  current
                   DESCRIPTION
                           "The number of active mappings of this IPv6 subscriber."
                   ::= { zxr10NatIPv6SubscribersEntry 12 }
        
    --zxr10NatPoolObject     
    zxr10NatPoolObject OBJECT IDENTIFIER ::= { zxr10NatObjects 3} 

     -------------------------------------------------------
     --zxr10NatPoolTable
     ------------------------------------------------------- 
     zxr10NatPoolTable OBJECT-TYPE
              SYNTAX  SEQUENCE OF Zxr10NatPoolEntry
              MAX-ACCESS  not-accessible
              STATUS  current
              DESCRIPTION
                      "Information of the CGN pool."
              ::= { zxr10NatPoolObject 1}     
   
          -------------------------------------------------------
          --zxr10NatPoolEntry 
          ------------------------------------------------------- 
          zxr10NatPoolEntry OBJECT-TYPE
              SYNTAX  Zxr10NatPoolEntry
              MAX-ACCESS  not-accessible
              STATUS  current
              DESCRIPTION
                      "Information of the CGN pool."
              INDEX   { 
                        zxr10NatPoolName
                      }
              ::= { zxr10NatPoolTable 1 }   
              
              Zxr10NatPoolEntry ::=
                  SEQUENCE{ 
                            zxr10NatPoolName
                            DisplayString,
                            zxr10NatPoolIndex
                            Unsigned32,
                            zxr10NatPoolInstName
                            DisplayString ,
                            zxr10NatPoolUsage
                            Zxr10NatUsage,
                            zxr10NatPoolVrf
                            DisplayString,
                            zxr10NatPoolDescription
                            DisplayString,
                            zxr10NatPoolType 
                            INTEGER,
                            zxr10NatPoolMaxPortsPerIP
                            Unsigned32,
                            zxr10NatPoolShareCnt 
                            Unsigned32,
                            zxr10NatPoolAlarmShareRatio
                            Unsigned32,
                            zxr10NatPoolPortRangeSize
                            Unsigned32,
                            zxr10NatPoolPortRangeStart
                            Unsigned32,
                            zxr10NatPoolPortRangeEnd 
                            Unsigned32,
                            zxr10NatPoolPortRangeCount
                            Unsigned32,
                            zxr10NatPoolPortRangeUsedCount
                            Unsigned32,
                            zxr10NatPoolPortRangeAlarmRatio 
                            Unsigned32,
                            zxr10NatPoolPortRangePortAlarmRatio 
                            Unsigned32,
                            zxr10NatPoolIPUsedCnt 
                            Unsigned32,
                            zxr10NatPoolIPUsedUsage
                            Zxr10NatUsage                           
                          } 
                         
            zxr10NatPoolName OBJECT-TYPE
                   SYNTAX  DisplayString (SIZE(1..31))
                   MAX-ACCESS  not-accessible
                   STATUS  current
                   DESCRIPTION
                           "Name of an address pool."
                   ::= { zxr10NatPoolEntry 1 }
    
            zxr10NatPoolIndex OBJECT-TYPE
                   SYNTAX  Unsigned32
                   MAX-ACCESS read-only
                   STATUS  current
                   DESCRIPTION
                           "Index of an address pool."
                   ::= { zxr10NatPoolEntry 2 }

            zxr10NatPoolInstName OBJECT-TYPE
                   SYNTAX  DisplayString (SIZE(1..31))
                   MAX-ACCESS  read-only
                   STATUS  current
                   DESCRIPTION
                           "The instance number of an address pool"
                   ::= { zxr10NatPoolEntry 3 }
        
            zxr10NatPoolUsage OBJECT-TYPE
                   SYNTAX  Zxr10NatUsage 
                   MAX-ACCESS  read-only
                   STATUS  current
                   DESCRIPTION
                           "One ten-thousandth of the pool's total number of external ports currently mapped."
                   ::= { zxr10NatPoolEntry 4 }               
    
            zxr10NatPoolVrf OBJECT-TYPE
                   SYNTAX  DisplayString (SIZE(0..35))
                   MAX-ACCESS  read-only
                   STATUS  current
                   DESCRIPTION
                           "Bind VRF name."
                   ::= { zxr10NatPoolEntry 10 }
    
            zxr10NatPoolDescription OBJECT-TYPE
                   SYNTAX  DisplayString (SIZE(0..63))
                   MAX-ACCESS  read-only
                   STATUS  current
                   DESCRIPTION
                           "Describe the pool."
                   ::= { zxr10NatPoolEntry 11 }
        
            zxr10NatPoolType OBJECT-TYPE
                    SYNTAX  INTEGER
                           { 
                            nat(0) ,
                            pat(1) ,
                            inValid(3)                         
                           }
                   MAX-ACCESS  read-only
                   STATUS  current
                   DESCRIPTION
                           "NAT or PAT pool."
                   ::= { zxr10NatPoolEntry 12 }
     
            zxr10NatPoolMaxPortsPerIP OBJECT-TYPE
                   SYNTAX  Unsigned32
                   MAX-ACCESS  read-only
                   STATUS  current
                   DESCRIPTION
                           "Max ports of each protocol for per address."
                   ::= { zxr10NatPoolEntry 13 }           

            zxr10NatPoolShareCnt OBJECT-TYPE
                   SYNTAX  Unsigned32
                   MAX-ACCESS  read-only
                   STATUS  current
                   DESCRIPTION
                           "The number of users for each protocol per address."
                   ::= { zxr10NatPoolEntry 14 }
    
            zxr10NatPoolAlarmShareRatio OBJECT-TYPE
                   SYNTAX  Unsigned32
                   MAX-ACCESS  read-only
                   STATUS  current
                   DESCRIPTION
                           "Ratio alarm threshold (%) of pool sharing."
                   ::= { zxr10NatPoolEntry 15 }  
    
            zxr10NatPoolPortRangeSize OBJECT-TYPE
                   SYNTAX  Unsigned32
                   MAX-ACCESS  read-only
                   STATUS  current
                   DESCRIPTION
                           "Port range size."
                   ::= { zxr10NatPoolEntry 16 }  

            zxr10NatPoolPortRangeStart OBJECT-TYPE
                   SYNTAX  Unsigned32
                   MAX-ACCESS  read-only
                   STATUS  current
                   DESCRIPTION
                           "Port range start port."
                   ::= { zxr10NatPoolEntry 17 }  
    
            zxr10NatPoolPortRangeEnd OBJECT-TYPE
                   SYNTAX  Unsigned32
                   MAX-ACCESS  read-only
                   STATUS  current
                   DESCRIPTION
                           "Port range end port."
                   ::= { zxr10NatPoolEntry 18 }

            zxr10NatPoolPortRangeCount OBJECT-TYPE
                   SYNTAX  Unsigned32
                   MAX-ACCESS  read-only
                   STATUS  current
                   DESCRIPTION
                           "Port range count."
                   ::= { zxr10NatPoolEntry 19 }  
    
            zxr10NatPoolPortRangeUsedCount OBJECT-TYPE
                   SYNTAX  Unsigned32
                   MAX-ACCESS  read-only
                   STATUS  current
                   DESCRIPTION
                           "Used port range count."
                   ::= { zxr10NatPoolEntry 20 }

            zxr10NatPoolPortRangeAlarmRatio OBJECT-TYPE
                   SYNTAX  Unsigned32
                   MAX-ACCESS  read-only
                   STATUS  current
                   DESCRIPTION
                           "Ratio alarm threshold (%) of used port range count in a IP."
                   ::= { zxr10NatPoolEntry 21 }
        
            zxr10NatPoolPortRangePortAlarmRatio OBJECT-TYPE
                   SYNTAX  Unsigned32
                   MAX-ACCESS  read-only
                   STATUS  current
                   DESCRIPTION
                           "Ratio alarm threshold (%) of used port count in a range."
                   ::= { zxr10NatPoolEntry 22 }
    
            zxr10NatPoolIPUsedCnt OBJECT-TYPE
                   SYNTAX  Unsigned32
                   MAX-ACCESS  read-only
                   STATUS  current
                   DESCRIPTION
                           "Number of used IP in NAT pool."
                   ::= { zxr10NatPoolEntry 26 }  

            zxr10NatPoolIPUsedUsage OBJECT-TYPE
                   SYNTAX  Zxr10NatUsage
                   MAX-ACCESS  read-only
                   STATUS  current
                   DESCRIPTION
                           "Ratio(0.01%) of used IP in NAT pool."
                   ::= { zxr10NatPoolEntry 27 }        
                   
     -------------------------------------------------------
     --zxr10NatPoolIPTable
     ------------------------------------------------------- 
     zxr10NatPoolIPTable OBJECT-TYPE
              SYNTAX  SEQUENCE OF Zxr10NatPoolIPEntry
              MAX-ACCESS  not-accessible
              STATUS  current
              DESCRIPTION
                      "Information about an IP."
              ::= { zxr10NatPoolObject 3}     
   
          -------------------------------------------------------
          --zxr10NatPoolIPEntry 
          ------------------------------------------------------- 
          zxr10NatPoolIPEntry OBJECT-TYPE
              SYNTAX  Zxr10NatPoolIPEntry
              MAX-ACCESS  not-accessible
              STATUS  current
              DESCRIPTION
                      "Information about an IP."
              INDEX   { 
                            zxr10NatPoolIPPoolName,
                            zxr10NatPoolIPAddr
                      }
              ::= { zxr10NatPoolIPTable 1 }   
              
          Zxr10NatPoolIPEntry ::=
                  SEQUENCE{ 
                            zxr10NatPoolIPPoolName
                            DisplayString,
                            zxr10NatPoolIPAddr 
                            IpAddress,
                            zxr10NatPoolIPTcpPortCnt
                            Unsigned32,
                            zxr10NatPoolIPUdpPortCnt
                            Unsigned32,
                            zxr10NatPoolIPICMPortCnt
                            Unsigned32,
                            zxr10NatPoolIPTCPUsage
                            Zxr10NatUsage,
                            zxr10NatPoolIPUDPUsage
                            Zxr10NatUsage,
                            zxr10NatPoolIPICMPUsage
                            Zxr10NatUsage,
                            zxr10NatPoolIPShareRatio
                            Unsigned32,
                            zxr10NatPoolIPPortRangeCount
                            Unsigned32,
                            zxr10NatPoolIPPortRangeUsedCount
                            Unsigned32                          
                          } 
                         
            zxr10NatPoolIPPoolName OBJECT-TYPE
                   SYNTAX  DisplayString (SIZE(1..31))
                   MAX-ACCESS  not-accessible
                   STATUS  current
                   DESCRIPTION
                           "The pool name this IP belongs."
                   ::= { zxr10NatPoolIPEntry 1 }
                   
            zxr10NatPoolIPAddr OBJECT-TYPE
                   SYNTAX       IpAddress
                   MAX-ACCESS  not-accessible
                   STATUS  current
                   DESCRIPTION
                           "IP address."
                   ::= { zxr10NatPoolIPEntry 2 }

            zxr10NatPoolIPTcpPortCnt OBJECT-TYPE
                   SYNTAX  Unsigned32
                   MAX-ACCESS  read-only
                   STATUS  current
                   DESCRIPTION
                           "Number of used TCP resource."
                   ::= { zxr10NatPoolIPEntry 3 }
                   
            zxr10NatPoolIPUdpPortCnt OBJECT-TYPE
                   SYNTAX  Unsigned32
                   MAX-ACCESS  read-only
                   STATUS  current
                   DESCRIPTION
                           "Number of used UDP resource."
                   ::= { zxr10NatPoolIPEntry 4 }
                   
            zxr10NatPoolIPICMPortCnt OBJECT-TYPE
                   SYNTAX  Unsigned32
                   MAX-ACCESS  read-only
                   STATUS  current
                   DESCRIPTION
                           "Number of used ICMP resource."
                   ::= { zxr10NatPoolIPEntry 5 }    
            
            zxr10NatPoolIPTCPUsage OBJECT-TYPE
                   SYNTAX  Zxr10NatUsage
                   MAX-ACCESS  read-only
                   STATUS  current
                   DESCRIPTION
                           "Ratio(0.01%) of used TCP resource."
                   ::= { zxr10NatPoolIPEntry 6 }
                   
            zxr10NatPoolIPUDPUsage OBJECT-TYPE
                   SYNTAX  Zxr10NatUsage
                   MAX-ACCESS  read-only
                   STATUS  current
                   DESCRIPTION
                           "Ratio(0.01%) of used UDP resource."
                   ::= { zxr10NatPoolIPEntry 7 }
                   
            zxr10NatPoolIPICMPUsage OBJECT-TYPE
                   SYNTAX  Zxr10NatUsage
                   MAX-ACCESS  read-only
                   STATUS  current
                   DESCRIPTION
                           "Ratio(0.01%) of used ICMP resource."
                   ::= { zxr10NatPoolIPEntry 8 }                   

            zxr10NatPoolIPShareRatio OBJECT-TYPE
                   SYNTAX  Unsigned32
                   MAX-ACCESS  read-only
                   STATUS  current
                   DESCRIPTION
                           "Number of users using this address."
                   ::= { zxr10NatPoolIPEntry 9 }
                   
            zxr10NatPoolIPPortRangeCount OBJECT-TYPE
                   SYNTAX  Unsigned32
                   MAX-ACCESS  read-only
                   STATUS  current
                   DESCRIPTION
                           "Port range count."
                   ::= { zxr10NatPoolIPEntry 10 }
                   
            zxr10NatPoolIPPortRangeUsedCount OBJECT-TYPE
                   SYNTAX  Unsigned32
                   MAX-ACCESS  read-only
                   STATUS  current
                   DESCRIPTION
                           "Used port range count."
                   ::= { zxr10NatPoolIPEntry 11 }
                   
                   
    --zxr10NatLimitsObject     
    zxr10NatLimitsObject OBJECT IDENTIFIER ::= { zxr10NatObjects 4} 
    
     --zxr10NatGlobalLimitsObject     
     zxr10NatGlobalLimitsObject OBJECT IDENTIFIER ::= { zxr10NatLimitsObject 1} 
                   
            zxr10NatLimitMappings OBJECT-TYPE
                   SYNTAX  Unsigned32
                   MAX-ACCESS  read-only
                   STATUS  obsolete
                   DESCRIPTION
                           "Global limit on the total number of mappings."
                   ::= { zxr10NatGlobalLimitsObject 1 }
           
             zxr10NatLimitMappingsLicense OBJECT-TYPE
                   SYNTAX  Counter64
                   MAX-ACCESS  read-only
                   STATUS  current
                   DESCRIPTION
                           "Global limit on the total number of mappings."
                   ::= { zxr10NatGlobalLimitsObject 2 }       

            zxr10NatLimitSubscribers OBJECT-TYPE
                   SYNTAX  Unsigned32
                   MAX-ACCESS  read-only
                   STATUS  current
                   DESCRIPTION
                           "Global limit on the number of subscribers with active mappings."
                   ::= { zxr10NatGlobalLimitsObject 4 }       
                   
    --zxr10NatUploadFtpGroup     
    zxr10NatUploadFtpGroup OBJECT IDENTIFIER ::= { zxr10NatObjects 5} 
    
        zxr10NatUploadFtpType OBJECT-TYPE
              SYNTAX  INTEGER {
                            ipv4subscriber(1),
                            ipv6subscriber(2),
                            ip(3)
                          }                             
              MAX-ACCESS  read-write
              STATUS  current
              DESCRIPTION
                      "The type of this request."
              ::= { zxr10NatUploadFtpGroup 1 }
              
        zxr10NatUploadFtpAddr OBJECT-TYPE
              SYNTAX  IpAddress                         
              MAX-ACCESS  read-write
              STATUS  current
              DESCRIPTION
                      "The IP address for the FTP server used for uploading files."
              ::= { zxr10NatUploadFtpGroup 2 }
        
        zxr10NatUploadFtpUserName OBJECT-TYPE
              SYNTAX  DisplayString(SIZE(0..31))    
              MAX-ACCESS  read-write
              STATUS  current
              DESCRIPTION
                      "The FTP user name."
              ::= { zxr10NatUploadFtpGroup 3 }
        
        zxr10NatUploadFtpUserPassword OBJECT-TYPE
              SYNTAX  DisplayString(SIZE(0..31))                                
              MAX-ACCESS  read-write
              STATUS  current
              DESCRIPTION
                      "The FTP user password."
              ::= { zxr10NatUploadFtpGroup 4 }
        
        zxr10NatUploadFtpFileName OBJECT-TYPE
              SYNTAX  DisplayString(SIZE(0..31))                                
              MAX-ACCESS  read-write
              STATUS  current
              DESCRIPTION
                      "The FTP file path and name."
              ::= { zxr10NatUploadFtpGroup 5 }
        
        zxr10NatUploadFtpExecuteStatus OBJECT-TYPE
              SYNTAX  INTEGER {
                            notstarted(1),
                            inprogress(2),
                            success(3),
                            userorpasswordfailed(4),
                            requestbedenied(5),
                            datatransfailed(6)
                          }                             
              MAX-ACCESS  read-only
              STATUS  current
              DESCRIPTION
                      "Save flash operational status."
              ::= { zxr10NatUploadFtpGroup 6 }
        
        zxr10NatUploadFtpExecutePercent OBJECT-TYPE
              SYNTAX  DisplayString(SIZE(1..5))                             
              MAX-ACCESS  read-only
              STATUS  current
              DESCRIPTION
                      "Stored data percent."
              ::= { zxr10NatUploadFtpGroup 7 }     
              
        zxr10NatUploadFtpVrfName OBJECT-TYPE
              SYNTAX  DisplayString(SIZE(0..35))                                
              MAX-ACCESS  read-write
              STATUS  current
              DESCRIPTION
                      "The FTP vrf name."
              ::= { zxr10NatUploadFtpGroup 8 }

                                   
     END
