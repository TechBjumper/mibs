--
-- Title:         Fibronics' MIB  
-- MIB Module :   Private MIB for  fx8210B
-- Version    :   V1.0
-- Date       :   Nov 23, 1992
-- By         :   Adi Fischer
-- Contact    :   Edna Ganon
-- Email:     :   edna@fibronics.co.il 
-- 
-- Description:   SNMP Agent MIB Definitions - for the Fibronics
--                                             fx8210B private MIB
-- 

        FIBRONICS-PROPRIETARY-FX8210-B-MIB DEFINITIONS ::= BEGIN

            IMPORTS

                enterprises, NetworkAddress, IpAddress, Counter,
                        Gauge, TimeTicks        FROM RFC1155-SMI
                OBJECT-TYPE                     FROM RFC-1212;


                -- spartacus objects

                spartacus  OBJECT IDENTIFIER ::= { enterprises 22 }

                dec       OBJECT IDENTIFIER ::= { spartacus 2 }
                trap      OBJECT IDENTIFIER ::= { spartacus 3 }
                dec2      OBJECT IDENTIFIER ::= { spartacus 4 }
                propSys   OBJECT IDENTIFIER ::= { spartacus 5 }
                propIp    OBJECT IDENTIFIER ::= { spartacus 6 }
                propFddi  OBJECT IDENTIFIER ::= { spartacus 7 }

                decrun       OBJECT IDENTIFIER ::= { dec 1 }
                decperm      OBJECT IDENTIFIER ::= { dec 2 }
                traprun      OBJECT IDENTIFIER ::= { trap 1 }
                traperm      OBJECT IDENTIFIER ::= { trap 2 }
                dec2run      OBJECT IDENTIFIER ::= { dec2 1 }
                dec2perm     OBJECT IDENTIFIER ::= { dec2 2 }
                propSysRun   OBJECT IDENTIFIER ::= { propSys 1 }
                propSysPerm  OBJECT IDENTIFIER ::= { propSys 2 }
                propIpRun    OBJECT IDENTIFIER ::= { propIp 1 }
                propIpPerm   OBJECT IDENTIFIER ::= { propIp 2 }


                -- decnetIV runtime objects

                rcircs  OBJECT IDENTIFIER ::= { decrun 1 }
                rnodes  OBJECT IDENTIFIER ::= { decrun 2 }
                rareas  OBJECT IDENTIFIER ::= { decrun 3 }


                -- decnetIV permanent objects

                pcircs     OBJECT IDENTIFIER ::= { decperm 1 }
                pnodes     OBJECT IDENTIFIER ::= { decperm 2 }
                pnRtParms  OBJECT IDENTIFIER ::= { pnodes 1 }


                -- runtime proprietary IP objects

                rIpRipStats  OBJECT IDENTIFIER ::= { propIpRun 15 }
                rIpArpStats  OBJECT IDENTIFIER ::= { propIpRun 16 }
                rIpPArp      OBJECT IDENTIFIER ::= { propIpRun 17 }


                -- decnetIV runtime node objects

                rnNmParms  OBJECT IDENTIFIER ::= { rnodes 1 }
                rnRtParms  OBJECT IDENTIFIER ::= { rnodes 2 }
                rnRtCount  OBJECT IDENTIFIER ::= { rnodes 3 }


                -- decnetIV runtime objects

                rCircNum  OBJECT-TYPE
                        SYNTAX  INTEGER
                        ACCESS  read-only
                        STATUS  mandatory
                        DESCRIPTION
                            ""
                        ::= { rcircs 1 }


                -- common circuit parm parameters

                rccTable  OBJECT-TYPE
                        SYNTAX  SEQUENCE OF RccEntry
                        ACCESS  not-accessible
                        STATUS  mandatory
                        DESCRIPTION
                            ""
                        ::= { rcircs 2 }

                rccEntry  OBJECT-TYPE
                        SYNTAX  RccEntry
                        ACCESS  not-accessible
                        STATUS  mandatory
                        DESCRIPTION
                            ""
                        INDEX   { rccIndex }
                        ::= { rccTable 1 }

                RccEntry ::= SEQUENCE {
                        rccIndex
                            INTEGER,
                        rccState
                            INTEGER,
                        rccType
                            INTEGER,
                        rccCost
                            INTEGER,
                        rccBSize
                            INTEGER,
                        rccHTimer
                            INTEGER,
                        rccLine
                            INTEGER
                }

                rccIndex  OBJECT-TYPE
                        SYNTAX  INTEGER
                        ACCESS  read-only
                        STATUS  mandatory
                        DESCRIPTION
                            ""
                        ::= { rccEntry 1 }

                rccState  OBJECT-TYPE
                        SYNTAX  INTEGER
                        ACCESS  read-write
                        STATUS  mandatory
                        DESCRIPTION
                            ""
                        ::= { rccEntry 2 }

                rccType  OBJECT-TYPE
                        SYNTAX  INTEGER
                        ACCESS  read-only
                        STATUS  mandatory
                        DESCRIPTION
                            ""
                        ::= { rccEntry 3 }

                rccCost  OBJECT-TYPE
                        SYNTAX  INTEGER
                        ACCESS  read-write
                        STATUS  mandatory
                        DESCRIPTION
                            ""
                        ::= { rccEntry 4 }

                rccBSize  OBJECT-TYPE
                        SYNTAX  INTEGER
                        ACCESS  read-only
                        STATUS  mandatory
                        DESCRIPTION
                            ""
                        ::= { rccEntry 5 }

                rccHTimer  OBJECT-TYPE
                        SYNTAX  INTEGER
                        ACCESS  read-write
                        STATUS  mandatory
                        DESCRIPTION
                            ""
                        ::= { rccEntry 6 }

                rccLine  OBJECT-TYPE
                        SYNTAX  INTEGER
                        ACCESS  read-only
                        STATUS  mandatory
                        DESCRIPTION
                            ""
                        ::= { rccEntry 7 }


                -- bcast circuit parameters

                rbcTable  OBJECT-TYPE
                        SYNTAX  SEQUENCE OF RbcEntry
                        ACCESS  not-accessible
                        STATUS  mandatory
                        DESCRIPTION
                            ""
                        ::= { rcircs 3 }

                rbcEntry  OBJECT-TYPE
                        SYNTAX  RbcEntry
                        ACCESS  not-accessible
                        STATUS  mandatory
                        DESCRIPTION
                            "The INDEX value specified should correspond to
                            the index of the circuit of the desired entry."
--                        INDEX   { INTEGER }
                        ::= { rbcTable 1 }

                RbcEntry ::= SEQUENCE {
                        rbcDrout
                            OCTET STRING,
                        rbcMrout
                            INTEGER,
                        rbcRpri
                            INTEGER
                }

                rbcDrout  OBJECT-TYPE
                        SYNTAX  OCTET STRING
                        ACCESS  read-only
                        STATUS  mandatory
                        DESCRIPTION
                            ""
                        ::= { rbcEntry 1 }

                rbcMrout  OBJECT-TYPE
                        SYNTAX  INTEGER
                        ACCESS  read-write
                        STATUS  mandatory
                        DESCRIPTION
                            ""
                        ::= { rbcEntry 2 }

                rbcRpri  OBJECT-TYPE
                        SYNTAX  INTEGER
                        ACCESS  read-write
                        STATUS  mandatory
                        DESCRIPTION
                            ""
                        ::= { rbcEntry 3 }


                -- common circuit counters

                rCCntrs  OBJECT-TYPE
                        SYNTAX  SEQUENCE OF RCCntrEntry
                        ACCESS  not-accessible
                        STATUS  mandatory
                        DESCRIPTION
                            ""
                        ::= { rcircs 4 }

                rCCntrEntry  OBJECT-TYPE
                        SYNTAX  RCCntrEntry
                        ACCESS  not-accessible
                        STATUS  mandatory
                        DESCRIPTION
                            "The INDEX value specified should correspond to
                            the index of the circuit of the desired entry."
                        --INDEX   { INTEGER }
                        ::= { rCCntrs 1 }

                RCCntrEntry ::= SEQUENCE {
                        rCCntTePktsIn
                            Counter,
                        rCCntOPktsOut
                            Counter,
                        rCCntTrPktsIn
                            Counter,
                        rCCntTrPktsOut
                            Counter,
                        rCCntAdjDown
                            Counter
                }

                rCCntTePktsIn  OBJECT-TYPE
                        SYNTAX Counter
                        ACCESS  read-only
                        STATUS  mandatory
                        DESCRIPTION
                            ""
                        ::= { rCCntrEntry 1 }

                rCCntOPktsOut  OBJECT-TYPE
                        SYNTAX Counter
                        ACCESS  read-only
                        STATUS  mandatory
                        DESCRIPTION
                            ""
                        ::= { rCCntrEntry 2 }

                rCCntTrPktsIn  OBJECT-TYPE
                        SYNTAX Counter
                        ACCESS  read-only
                        STATUS  mandatory
                        DESCRIPTION
                            ""
                        ::= { rCCntrEntry 3 }

                rCCntTrPktsOut  OBJECT-TYPE
                        SYNTAX Counter
                        ACCESS  read-only
                        STATUS  mandatory
                        DESCRIPTION
                            ""
                        ::= { rCCntrEntry 4 }

                rCCntAdjDown  OBJECT-TYPE
                        SYNTAX Counter
                        ACCESS  read-only
                        STATUS  mandatory
                        DESCRIPTION
                            ""
                        ::= { rCCntrEntry 5 }


                -- node netmanagement parms

                rnNmId  OBJECT-TYPE
                        SYNTAX  OCTET STRING
                        ACCESS  read-only
                        STATUS  mandatory
                        DESCRIPTION
                            ""
                        ::= { rnNmParms 1 }

                rnNmPaddr  OBJECT-TYPE
                        SYNTAX  OCTET STRING
                        ACCESS  read-only
                        STATUS  mandatory
                        DESCRIPTION
                            ""
                        ::= { rnNmParms 2 }


                -- runtime node routing parms

                rnRpAMaxC  OBJECT-TYPE
                        SYNTAX  INTEGER
                        ACCESS  read-write
                        STATUS  mandatory
                        DESCRIPTION
                            ""
                        ::= { rnRtParms 1 }

                rnRpAMaxH OBJECT-TYPE
                        SYNTAX  INTEGER
                        ACCESS  read-write
                        STATUS  mandatory
                        DESCRIPTION
                            ""
                        ::= { rnRtParms 2 }

                rnRpBRtTmr  OBJECT-TYPE
                        SYNTAX  INTEGER
                        ACCESS  read-write
                        STATUS  mandatory
                        DESCRIPTION
                            ""
                        ::= { rnRtParms 3 }

                rnRpBSize  OBJECT-TYPE
                        SYNTAX  INTEGER
                        ACCESS  read-write
                        STATUS  mandatory
                        DESCRIPTION
                            ""
                        ::= { rnRtParms 4 }

                rnRpMAddr  OBJECT-TYPE
                        SYNTAX  INTEGER
                        ACCESS  read-write
                        STATUS  mandatory
                        DESCRIPTION
                            ""
                        ::= { rnRtParms 5 }

                rnRpMArea  OBJECT-TYPE
                        SYNTAX  INTEGER
                        ACCESS  read-write
                        STATUS  mandatory
                        DESCRIPTION
                            ""
                        ::= { rnRtParms 6 }

                rnRpMaxBNR  OBJECT-TYPE
                        SYNTAX  INTEGER
                        ACCESS  read-write
                        STATUS  mandatory
                        DESCRIPTION
                            ""
                        ::= { rnRtParms 7 }

                rnRpMaxBR  OBJECT-TYPE
                        SYNTAX  INTEGER
                        ACCESS  read-write
                        STATUS  mandatory
                        DESCRIPTION
                            ""
                        ::= { rnRtParms 8 }

                rnRpMaxCir   OBJECT-TYPE
                        SYNTAX  INTEGER
                        ACCESS  read-only
                        STATUS  mandatory
                        DESCRIPTION
                            ""
                        ::= { rnRtParms 9 }

                rnRpMaxCost  OBJECT-TYPE
                        SYNTAX  INTEGER
                        ACCESS  read-write
                        STATUS  mandatory
                        DESCRIPTION
                            ""
                        ::= { rnRtParms 10 }

                rnRpMaxHops  OBJECT-TYPE
                        SYNTAX  INTEGER
                        ACCESS  read-write
                        STATUS  mandatory
                        DESCRIPTION
                            ""
                        ::= { rnRtParms 11 }

                rnRpMaxV  OBJECT-TYPE
                        SYNTAX  INTEGER
                        ACCESS  read-write
                        STATUS  mandatory
                        DESCRIPTION
                            ""
                        ::= { rnRtParms 12 }

                rnRpVers  OBJECT-TYPE
                        SYNTAX  OCTET STRING
                        ACCESS  read-only
                        STATUS  mandatory
                        DESCRIPTION
                            ""
                        ::= { rnRtParms 13 }

                rnRpSegBuf  OBJECT-TYPE
                        SYNTAX  INTEGER
                        ACCESS  read-only
                        STATUS  mandatory
                        DESCRIPTION
                            ""
                        ::= { rnRtParms 14 }

                rnRpType  OBJECT-TYPE
                        SYNTAX  INTEGER
                        ACCESS  read-write
                        STATUS  mandatory
                        DESCRIPTION
                            ""
                        ::= { rnRtParms 15 }

                rnRpAddr  OBJECT-TYPE
                        SYNTAX  OCTET STRING
                        ACCESS  read-only
                        STATUS  mandatory
                        DESCRIPTION
                            ""
                        ::= { rnRtParms 16 }

                rnRpUseL2A  OBJECT-TYPE
                        SYNTAX  INTEGER
                        ACCESS  read-write
                        STATUS  mandatory
                        DESCRIPTION
                            ""
                        ::= { rnRtParms 17 }


                -- node routing counters

                rnRcAgedPkt  OBJECT-TYPE
                        SYNTAX Counter
                        ACCESS  read-only
                        STATUS  mandatory
                        DESCRIPTION
                            ""
                        ::= { rnRtCount 1 }

                rnRcUnReach  OBJECT-TYPE
                        SYNTAX Counter
                        ACCESS  read-only
                        STATUS  mandatory
                        DESCRIPTION
                            ""
                        ::= { rnRtCount 2 }

                rnRcBadRange  OBJECT-TYPE
                        SYNTAX Counter
                        ACCESS  read-only
                        STATUS  mandatory
                        DESCRIPTION
                            ""
                        ::= { rnRtCount 3 }

                rnRcOversize  OBJECT-TYPE
                        SYNTAX Counter
                        ACCESS  read-only
                        STATUS  mandatory
                        DESCRIPTION
                            ""
                        ::= { rnRtCount 4 }

                rnRcFormErr  OBJECT-TYPE
                        SYNTAX Counter
                        ACCESS  read-only
                        STATUS  mandatory
                        DESCRIPTION
                            ""
                        ::= { rnRtCount 5 }

                rnRcRtUpLoss  OBJECT-TYPE
                        SYNTAX Counter
                        ACCESS  read-only
                        STATUS  mandatory
                        DESCRIPTION
                            ""
                        ::= { rnRtCount 6 }


                -- adjacency table

                rnAdjTbl  OBJECT-TYPE
                        SYNTAX  SEQUENCE OF RnAdjEnt
                        ACCESS  not-accessible
                        STATUS  mandatory
                        DESCRIPTION
                            ""
                        ::= { rnodes 4 }

                rnAdjEnt  OBJECT-TYPE
                        SYNTAX  RnAdjEnt
                        ACCESS  not-accessible
                        STATUS  mandatory
                        DESCRIPTION
                            ""
                        INDEX   { rnAdjAddr }
                        ::= { rnAdjTbl 1 }

                RnAdjEnt ::= SEQUENCE {
                        rnAdjAddr
                            OCTET STRING,
                        rnAdjState
                            INTEGER,
                        rnAdjType
                            INTEGER,
                        rnAdjCIdx
                            INTEGER,
                        rnAdjBSize
                            INTEGER,
                        rnAdjLTmr
                            INTEGER,
                        rnAdjPri
                            INTEGER
                }

                rnAdjAddr  OBJECT-TYPE
                        SYNTAX  OCTET STRING
                        ACCESS  read-only
                        STATUS  mandatory
                        DESCRIPTION
                            ""
                        ::= { rnAdjEnt 1 }

                rnAdjState  OBJECT-TYPE
                        SYNTAX  INTEGER
                        ACCESS  read-only
                        STATUS  mandatory
                        DESCRIPTION
                            ""
                        ::= { rnAdjEnt 2 }

                rnAdjType  OBJECT-TYPE
                        SYNTAX  INTEGER
                        ACCESS  read-only
                        STATUS  mandatory
                        DESCRIPTION
                            ""
                        ::= { rnAdjEnt 3 }

                rnAdjCIdx  OBJECT-TYPE
                        SYNTAX  INTEGER
                        ACCESS  read-only
                        STATUS  mandatory
                        DESCRIPTION
                            ""
                        ::= { rnAdjEnt 4 }

                rnAdjBSize  OBJECT-TYPE
                        SYNTAX  INTEGER
                        ACCESS  read-only
                        STATUS  mandatory
                        DESCRIPTION
                            ""
                        ::= { rnAdjEnt 5 }

                rnAdjLTmr  OBJECT-TYPE
                        SYNTAX  INTEGER
                        ACCESS  read-only
                        STATUS  mandatory
                        DESCRIPTION
                            ""
                        ::= { rnAdjEnt 6 }

                rnAdjPri  OBJECT-TYPE
                        SYNTAX  INTEGER
                        ACCESS  read-only
                        STATUS  mandatory
                        DESCRIPTION
                            ""
                        ::= { rnAdjEnt 7 }


                -- level 1 routing table

                rnLvl1Tbl  OBJECT-TYPE
                        SYNTAX  SEQUENCE OF RnLvl1Ent
                        ACCESS  not-accessible
                        STATUS  mandatory
                        DESCRIPTION
                            ""
                        ::= { rnodes 5 }

                rnLvl1Ent  OBJECT-TYPE
                        SYNTAX  RnLvl1Ent
                        ACCESS  not-accessible
                        STATUS  mandatory
                        DESCRIPTION
                            ""
                        INDEX   { rnLvl1Addr }
                        ::= { rnLvl1Tbl 1 }

                RnLvl1Ent ::= SEQUENCE {
                        rnLvl1Addr
                            OCTET STRING,
                        rnLvl1Cidx
                            INTEGER,
                        rnLvl1Cost
                            INTEGER,
                        rnLvl1Hops
                            INTEGER,
                        rnLvl1Next
                            OCTET STRING
                }


                rnLvl1Addr  OBJECT-TYPE
                        SYNTAX  OCTET STRING
                        ACCESS  read-only
                        STATUS  mandatory
                        DESCRIPTION
                            ""
                        ::= { rnLvl1Ent 1 }

                rnLvl1Cidx  OBJECT-TYPE
                        SYNTAX  INTEGER
                        ACCESS  read-only
                        STATUS  mandatory
                        DESCRIPTION
                            ""
                        ::= { rnLvl1Ent 2 }

                rnLvl1Cost  OBJECT-TYPE
                        SYNTAX  INTEGER
                        ACCESS  read-only
                        STATUS  mandatory
                        DESCRIPTION
                            ""
                        ::= { rnLvl1Ent 3 }

                rnLvl1Hops  OBJECT-TYPE
                        SYNTAX  INTEGER
                        ACCESS  read-only
                        STATUS  mandatory
                        DESCRIPTION
                            ""
                        ::= { rnLvl1Ent 4 }

                rnLvl1Next  OBJECT-TYPE
                        SYNTAX  OCTET STRING
                        ACCESS  read-only
                        STATUS  mandatory
                        DESCRIPTION
                            ""
                        ::= { rnLvl1Ent 5 }


                -- area objects

                raParmTbl  OBJECT-TYPE
                        SYNTAX  SEQUENCE OF RaParmEntry
                        ACCESS  not-accessible
                        STATUS  mandatory
                        DESCRIPTION
                            ""
                        ::= { rareas 1 }

                raParmEntry  OBJECT-TYPE
                        SYNTAX  RaParmEntry
                        ACCESS  not-accessible
                        STATUS  mandatory
                        DESCRIPTION
                            ""
                        INDEX   { raNum }
                        ::= { raParmTbl 1 }

                RaParmEntry ::= SEQUENCE {
                        raNum
                            INTEGER,
                        raCIdx
                            INTEGER,
                        raCost
                            INTEGER,
                        raHops
                            INTEGER,
                        raNext
                            OCTET STRING
                }

                raNum  OBJECT-TYPE
                        SYNTAX  INTEGER
                        ACCESS  read-only
                        STATUS  mandatory
                        DESCRIPTION
                            ""
                        ::= { raParmEntry 1 }

                raCIdx  OBJECT-TYPE
                        SYNTAX  INTEGER
                        ACCESS  read-only
                        STATUS  mandatory
                        DESCRIPTION
                            ""
                        ::= { raParmEntry 2 }

                raCost  OBJECT-TYPE
                        SYNTAX  INTEGER
                        ACCESS  read-only
                        STATUS  mandatory
                        DESCRIPTION
                            ""
                        ::= { raParmEntry 3 }

                raHops  OBJECT-TYPE
                        SYNTAX  INTEGER
                        ACCESS  read-only
                        STATUS  mandatory
                        DESCRIPTION
                            ""
                        ::= { raParmEntry 4 }

                raNext  OBJECT-TYPE
                        SYNTAX  OCTET STRING
                        ACCESS  read-only
                        STATUS  mandatory
                        DESCRIPTION
                            ""
                        ::= { raParmEntry 5 }


                -- decnetIV permanent objects

                pccTable  OBJECT-TYPE
                        SYNTAX  SEQUENCE OF PccEntry
                        ACCESS  not-accessible
                        STATUS  mandatory
                        DESCRIPTION
                            ""
                        ::= { pcircs 1 }

                pccEntry OBJECT-TYPE
                        SYNTAX  PccEntry
                        ACCESS  not-accessible
                        STATUS  mandatory
                        DESCRIPTION
                            ""
                        INDEX   { pccIndex }
                        ::= { pccTable 1 }

                PccEntry ::= SEQUENCE {
                        pccIndex
                            INTEGER,
                        pccState
                            INTEGER,
                        pccCost
                            INTEGER,
                        pccHTimer
                            INTEGER
                }

                pccIndex  OBJECT-TYPE
                        SYNTAX  INTEGER
                        ACCESS  read-only
                        STATUS  mandatory
                        DESCRIPTION
                            ""
                        ::= { pccEntry 1 }

                pccState  OBJECT-TYPE
                        SYNTAX  INTEGER
                        ACCESS  read-write
                        STATUS  mandatory
                        DESCRIPTION
                            ""
                        ::= { pccEntry 2 }

                pccCost  OBJECT-TYPE
                        SYNTAX  INTEGER
                        ACCESS  read-write
                        STATUS  mandatory
                        DESCRIPTION
                            ""
                        ::= { pccEntry 3 }

                pccHTimer  OBJECT-TYPE
                        SYNTAX  INTEGER
                        ACCESS  read-write
                        STATUS  mandatory
                        DESCRIPTION
                            ""
                        ::= { pccEntry 4 }


                -- bdcast circuit parameters

                pbcTable  OBJECT-TYPE
                        SYNTAX  SEQUENCE OF PbcEntry
                        ACCESS  not-accessible
                        STATUS  mandatory
                        DESCRIPTION
                            ""
                        ::= { pcircs 2 }

                pbcEntry  OBJECT-TYPE
                        SYNTAX  PbcEntry
                        ACCESS  not-accessible
                        STATUS  mandatory
                        DESCRIPTION
                            "The INDEX value specified should correspond to
                            the index of the circuit of the desired entry."
                        --INDEX   { INTEGER }
                        ::= { pbcTable 1 }

                PbcEntry ::= SEQUENCE {
                        pbcMrout
                            INTEGER,
                        pbcRpri
                            INTEGER
                }

                pbcMrout  OBJECT-TYPE
                        SYNTAX  INTEGER
                        ACCESS  read-write
                        STATUS  mandatory
                        DESCRIPTION
                            ""
                        ::= { pbcEntry 1 }

                pbcRpri  OBJECT-TYPE
                        SYNTAX  INTEGER
                        ACCESS  read-write
                        STATUS  mandatory
                        DESCRIPTION
                            ""
                        ::= { pbcEntry 2 }


                -- permanent node routing parms

                pnRpAMaxC  OBJECT-TYPE
                        SYNTAX  INTEGER
                        ACCESS  read-write
                        STATUS  mandatory
                        DESCRIPTION
                            ""
                        ::= { pnRtParms 1 }

                pnRpAMaxH  OBJECT-TYPE
                        SYNTAX  INTEGER
                        ACCESS  read-write
                        STATUS  mandatory
                        DESCRIPTION
                            ""
                        ::= { pnRtParms 2 }

                pnRpBRtTmr  OBJECT-TYPE
                        SYNTAX  INTEGER
                        ACCESS  read-write
                        STATUS  mandatory
                        DESCRIPTION
                            ""
                        ::= { pnRtParms 3 }

                pnRpBSize  OBJECT-TYPE
                        SYNTAX  INTEGER
                        ACCESS  read-write
                        STATUS  mandatory
                        DESCRIPTION
                            ""
                        ::= { pnRtParms 4 }

                pnRpMAddr  OBJECT-TYPE
                        SYNTAX  INTEGER
                        ACCESS  read-write
                        STATUS  mandatory
                        DESCRIPTION
                            ""
                        ::= { pnRtParms 5 }

                pnRpMArea  OBJECT-TYPE
                        SYNTAX  INTEGER
                        ACCESS  read-write
                        STATUS  mandatory
                        DESCRIPTION
                            ""
                        ::= { pnRtParms 6 }

                pnRpMaxBNR  OBJECT-TYPE
                        SYNTAX  INTEGER
                        ACCESS  read-write
                        STATUS  mandatory
                        DESCRIPTION
                            ""
                        ::= { pnRtParms 7 }

                pnRpMaxBR  OBJECT-TYPE
                        SYNTAX  INTEGER
                        ACCESS  read-write
                        STATUS  mandatory
                        DESCRIPTION
                            ""
                        ::= { pnRtParms 8 }

                pnRpMaxCost  OBJECT-TYPE
                        SYNTAX  INTEGER
                        ACCESS  read-write
                        STATUS  mandatory
                        DESCRIPTION
                            ""
                        ::= { pnRtParms 9 }

                pnRpMaxHops  OBJECT-TYPE
                        SYNTAX  INTEGER
                        ACCESS  read-write
                        STATUS  mandatory
                        DESCRIPTION
                            ""
                        ::= { pnRtParms 10 }

                pnRpMaxV  OBJECT-TYPE
                        SYNTAX  INTEGER
                        ACCESS  read-write
                        STATUS  mandatory
                        DESCRIPTION
                            ""
                        ::= { pnRtParms 11 }

                pnRpType  OBJECT-TYPE
                        SYNTAX  INTEGER
                        ACCESS  read-write
                        STATUS  mandatory
                        DESCRIPTION
                            ""
                        ::= { pnRtParms 12 }

                pnRpAddr  OBJECT-TYPE
                        SYNTAX  OCTET STRING
                        ACCESS  read-write
                        STATUS  mandatory
                        DESCRIPTION
                            ""
                        ::= { pnRtParms 13 }

                pnRpUseL2A  OBJECT-TYPE
                        SYNTAX  INTEGER
                        ACCESS  read-write
                        STATUS  mandatory
                        DESCRIPTION
                            ""
                        ::= { pnRtParms 14 }

                pnRpRstDaddr  OBJECT-TYPE
                        SYNTAX  INTEGER
                        ACCESS  read-write
                        STATUS  mandatory
                        DESCRIPTION
                            ""
                        ::= { pnRtParms 15 }

                pDecDefaults  OBJECT-TYPE
                        SYNTAX  INTEGER {
                            reset-defaults(1)
                        }
                        ACCESS  read-write
                        STATUS  mandatory
                        DESCRIPTION
                            "When this object is set to 1, the side effect will
                            be to cause the unit to reset all the objects
                            defined under the subtree decperm to their default
                            values.  Reading this object has no meaning.  The
                            integer value 1 will be returned to a get or
                            get-next request."
                        ::= { decperm 3 }


                -- trap runtime objects

                rTrapAddrTbl  OBJECT-TYPE
                        SYNTAX  SEQUENCE OF RTrapAddrEntry
                        ACCESS  not-accessible
                        STATUS  mandatory
                        DESCRIPTION
                            "This table contains runtime information about
                            destinations to which traps should be directed.
                            Setting the rTrapAddrState to INACTIVE removes
                            an entry from the table."
                        ::= { traprun 1 }

                rTrapAddrEntry  OBJECT-TYPE
                        SYNTAX  RTrapAddrEntry
                        ACCESS  not-accessible
                        STATUS  mandatory
                        DESCRIPTION
                            "This object contains runtime information about
                            an individual trap destination."
                        INDEX   { rTrapAddrAddr }
                        ::= { rTrapAddrTbl 1 }

                RTrapAddrEntry ::= SEQUENCE {
                        rTrapAddrAddr
                            NetworkAddress,
                        rTrapAddrComm
                            OCTET STRING,
                        rTrapAddrVer
                            INTEGER,
                        rTrapAddrType
                            OCTET STRING,
                        rTrapAddrState
                            INTEGER
                }

                rTrapAddrAddr  OBJECT-TYPE
                        SYNTAX  NetworkAddress
                        ACCESS  read-write
                        STATUS  mandatory
                        DESCRIPTION
                            "The IP address of the network management entity
                            to which traps (of the type specified in this
                            table entry) should be sent."
                        ::= { rTrapAddrEntry 1 }

                rTrapAddrComm  OBJECT-TYPE
                        SYNTAX  OCTET STRING
                        ACCESS  read-write
                        STATUS  mandatory
                        DESCRIPTION
                            "Community string to be used in SNMP message
                            generated to the receiving SNMP protocol entity."
                        ::= { rTrapAddrEntry 2 }

                rTrapAddrVer  OBJECT-TYPE
                        SYNTAX  INTEGER
                        ACCESS  read-write
                        STATUS  mandatory
                        DESCRIPTION
                            "The trap address table version number.  The
                            current (and only valid) version number is 1."
                        ::= { rTrapAddrEntry 3 }

                rTrapAddrType  OBJECT-TYPE
                        SYNTAX  OCTET STRING
                        ACCESS  read-write
                        STATUS  mandatory
                        DESCRIPTION
                            "A bit-encoded string, 1 byte in length, which
                            contains information about which trap(s) should be
                            directed to the management entity described by
                            this table entry.  The following list identifies
                            the trap types and corresponding bit values.

                                TRAP-STANDARD-MIB       1000 0000
                                TRAP-DIAG               0100 0000
                                TRAP-GNRL-PROPRIETARY   0010 0000
                                TRAP-ROUT               0001 0000
                                TRAP-DEBUG              0000 1000
                                TRAP-PROP-DEC4          0000 0100"
                        ::= { rTrapAddrEntry 4 }

                rTrapAddrState  OBJECT-TYPE
                        SYNTAX  INTEGER {
                            active(1),
                            inactive(2)
                        }
                        ACCESS  read-write
                        STATUS  mandatory
                        DESCRIPTION
                            "The state of this entry in the trap address
                            table.  Setting this object to INACTIVE
                            removes the corresponding entry from the
                            table."
                        ::= { rTrapAddrEntry 5 }


                -- trap permanent objects

                pTrapAddrTbl  OBJECT-TYPE
                        SYNTAX  SEQUENCE OF PTrapAddrEntry
                        ACCESS  not-accessible
                        STATUS  mandatory
                        DESCRIPTION
                            "This table contains permanent information about
                            destinations to which traps should be directed.
                            Setting the pTrapAddrState to INACTIVE removes
                            an entry from the table.  This information is
                            used to initialize the rTrapAddrTbl on unit
                            startup."
                        ::= { traperm 1 }

                pTrapAddrEntry  OBJECT-TYPE
                        SYNTAX  PTrapAddrEntry
                        ACCESS  not-accessible
                        STATUS  mandatory
                        DESCRIPTION
                            "This object contains permanent information about
                            an individual trap destination."
                        INDEX   { pTrapAddrAddr }
                        ::= { pTrapAddrTbl 1 }

                PTrapAddrEntry ::= SEQUENCE {
                        pTrapAddrAddr
                            NetworkAddress,
                        pTrapAddrComm
                            OCTET STRING,
                        pTrapAddrVer
                            INTEGER,
                        pTrapAddrType
                            OCTET STRING,
                        pTrapAddrState
                            INTEGER
                }

                pTrapAddrAddr  OBJECT-TYPE
                        SYNTAX  NetworkAddress
                        ACCESS  read-write
                        STATUS  mandatory
                        DESCRIPTION
                            "The IP address of the network management entity
                            to which traps (of the type specified in this
                            table entry) should be sent."
                        ::= { pTrapAddrEntry 1 }

                pTrapAddrComm  OBJECT-TYPE
                        SYNTAX  OCTET STRING
                        ACCESS  read-write
                        STATUS  mandatory
                        DESCRIPTION
                            "Community string to be used in SNMP message
                            generated to the receiving SNMP protocol entity."
                        ::= { pTrapAddrEntry 2 }

                pTrapAddrVer  OBJECT-TYPE
                        SYNTAX  INTEGER
                        ACCESS  read-write
                        STATUS  mandatory
                        DESCRIPTION
                            "The trap address table version number.  The
                            current (and only valid) version number is 1."
                        ::= { pTrapAddrEntry 3 }

                pTrapAddrType  OBJECT-TYPE
                        SYNTAX OCTET STRING
                        ACCESS  read-write
                        STATUS  mandatory
                        DESCRIPTION
                            "A bit-encoded string, 1 byte in length, which
                            contains information about which trap(s) should be
                            directed to the management entity described by
                            this table entry.  The following list identifies
                            the trap types and corresponding bit values.

                                TRAP-STANDARD-MIB       1000 0000
                                TRAP-DIAG               0100 0000
                                TRAP-GNRL-PROPRIETARY   0010 0000
                                TRAP-ROUT               0001 0000
                                TRAP-DEBUG              0000 1000
                                TRAP-PROP-DEC4          0000 0100"
                        ::= { pTrapAddrEntry 4 }

                pTrapAddrState  OBJECT-TYPE
                        SYNTAX  INTEGER
                        ACCESS  read-write
                        STATUS  mandatory
                        DESCRIPTION
                            "The state of this entry in the trap address
                            table.  Setting this object to INACTIVE
                            removes the corresponding entry from the
                            table."
                        ::= { pTrapAddrEntry 5 }

                pTrapDefaults  OBJECT-TYPE
                        SYNTAX  INTEGER {
                            reset-defautls(1)
                        }
                        ACCESS  read-write
                        STATUS  mandatory
                        DESCRIPTION
                            "When this object is set to 1, the side effect will
                            be to cause the unit to reset all the objects
                            defined under the subtree traperm to their default
                            values.  Reading this object has no meaning.  The
                            integer value 1 will be returned to a get or
                            get-next request."
                        ::= { traperm 2 }


                -- runtime decnet level 2 variables

                rClParmTbl  OBJECT-TYPE
                        SYNTAX  SEQUENCE OF RClParmEntry
                        ACCESS  not-accessible
                        STATUS  mandatory
                        DESCRIPTION
                            ""
                        ::= { dec2run 1 }

                rClParmEntry  OBJECT-TYPE
                        SYNTAX  RClParmEntry
                        ACCESS  not-accessible
                        STATUS  mandatory
                        DESCRIPTION
                            "The INDEX value specified should correspond to
                            the index of the interface of the desired entry."
                        --INDEX   { INTEGER }
                        ::= { rClParmTbl 1 }

                RClParmEntry ::= SEQUENCE {
                        rClState
                            INTEGER,
                        rClSubSt
                            INTEGER
                }

                rClState  OBJECT-TYPE
                        SYNTAX  INTEGER
                        ACCESS  read-write
                        STATUS  mandatory
                        DESCRIPTION
                            ""
                        ::= { rClParmEntry 1 }

                rClSubSt  OBJECT-TYPE
                        SYNTAX  INTEGER
                        ACCESS  read-only
                        STATUS  mandatory
                        DESCRIPTION
                            ""
                        ::= { rClParmEntry 2 }

                rBlParmTbl  OBJECT-TYPE
                        SYNTAX  SEQUENCE OF RBlParmEntry
                        ACCESS  not-accessible
                        STATUS  mandatory
                        DESCRIPTION
                            ""
                        ::= { dec2run 2 }

                rBlParmEntry  OBJECT-TYPE
                        SYNTAX  RBlParmEntry
                        ACCESS  not-accessible
                        STATUS  mandatory
                        DESCRIPTION
                            "The INDEX value specified should correspond to
                            the index of the interface of the desired entry."
                        --INDEX   { INTEGER }
                        ::= { rBlParmTbl 1 }

                RBlParmEntry ::= SEQUENCE {
                        rBlHAddr
                            OCTET STRING
                }

                rBlHAddr  OBJECT-TYPE
                        SYNTAX  OCTET STRING
                        ACCESS  read-only
                        STATUS  mandatory
                        DESCRIPTION
                            ""
                        ::= { rBlParmEntry 1 }

                rElCountTbl  OBJECT-TYPE
                        SYNTAX SEQUENCE OF RElCountEntry
                        ACCESS  not-accessible
                        STATUS  mandatory
                        DESCRIPTION
                            ""
                        ::= { dec2run 3 }

                rElCountEntry  OBJECT-TYPE
                        SYNTAX  RElCountEntry
                        ACCESS  not-accessible
                        STATUS  mandatory
                        DESCRIPTION
                            "The INDEX value specified should correspond to
                            the index of the interface of the desired entry."
                        --INDEX   { INTEGER }
                        ::= { rElCountTbl 1 }

                RElCountEntry ::= SEQUENCE {
                        rElFrIn
                            Counter,
                        rElFrOut
                            Counter,
                        rElBcBin
                            Counter,
                        rElBcFIn
                            Counter,
                        rElMcBIn
                            Counter,
                        rElMcFIn
                            Counter,
                        rElFDef
                            Counter,
                        rElF1Col
                            Counter,
                        rElFMCol
                            Counter,
                        rElOutF
                            Counter,
                        rElCDetF
                            Counter,
                        rElInF
                            Counter,
                        rElBadD
                            Counter,
                        rElOvRun
                            Counter,
                        rElNoBuf
                            Counter
                }

                rElFrIn  OBJECT-TYPE
                        SYNTAX  Counter
                        ACCESS  read-only
                        STATUS  mandatory
                        DESCRIPTION
                            ""
                        ::= { rElCountEntry 1 }

                rElFrOut  OBJECT-TYPE
                        SYNTAX  Counter
                        ACCESS  read-only
                        STATUS  mandatory
                        DESCRIPTION
                            ""
                        ::= { rElCountEntry 2 }

                rElBcBIn  OBJECT-TYPE
                        SYNTAX  Counter
                        ACCESS  read-only
                        STATUS  mandatory
                        DESCRIPTION
                            ""
                        ::= { rElCountEntry 3 }

                rElBcFIn  OBJECT-TYPE
                        SYNTAX  Counter
                        ACCESS  read-only
                        STATUS  mandatory
                        DESCRIPTION
                            ""
                        ::= { rElCountEntry 4 }

                rElMcBIn  OBJECT-TYPE
                        SYNTAX  Counter
                        ACCESS  read-only
                        STATUS  mandatory
                        DESCRIPTION
                            ""
                        ::= { rElCountEntry 5 }

                rElMcFIn  OBJECT-TYPE
                        SYNTAX  Counter
                        ACCESS  read-only
                        STATUS  mandatory
                        DESCRIPTION
                            ""
                        ::= { rElCountEntry 6 }

                rElFDef  OBJECT-TYPE
                        SYNTAX  Counter
                        ACCESS  read-only
                        STATUS  mandatory
                        DESCRIPTION
                            ""
                        ::= { rElCountEntry 7 }

                rElF1Col  OBJECT-TYPE
                        SYNTAX  Counter
                        ACCESS  read-only
                        STATUS  mandatory
                        DESCRIPTION
                            ""
                        ::= { rElCountEntry 8 }

                rElFMCol  OBJECT-TYPE
                        SYNTAX  Counter
                        ACCESS  read-only
                        STATUS  mandatory
                        DESCRIPTION
                            ""
                        ::= { rElCountEntry 9 }

                rElOutF  OBJECT-TYPE
                        SYNTAX  Counter
                        ACCESS  read-only
                        STATUS  mandatory
                        DESCRIPTION
                            ""
                        ::= { rElCountEntry 10 }

                rElCDetF  OBJECT-TYPE
                        SYNTAX  Counter
                        ACCESS  read-only
                        STATUS  mandatory
                        DESCRIPTION
                            ""
                        ::= { rElCountEntry 11 }

                rElInF  OBJECT-TYPE
                        SYNTAX  Counter
                        ACCESS  read-only
                        STATUS  mandatory
                        DESCRIPTION
                            ""
                        ::= { rElCountEntry 12 }

                rElBadD  OBJECT-TYPE
                        SYNTAX  Counter
                        ACCESS  read-only
                        STATUS  mandatory
                        DESCRIPTION
                            ""
                        ::= { rElCountEntry 13 }

                rElOvRun  OBJECT-TYPE
                        SYNTAX  Counter
                        ACCESS  read-only
                        STATUS  mandatory
                        DESCRIPTION
                            ""
                        ::= { rElCountEntry 14 }

                rElNoBuf  OBJECT-TYPE
                        SYNTAX  Counter
                        ACCESS  read-only
                        STATUS  mandatory
                        DESCRIPTION
                            ""
                        ::= { rElCountEntry 15 }


                -- runtime proprietary system objects

                rTod  OBJECT-TYPE
                        SYNTAX  OCTET STRING
                        ACCESS  read-write
                        STATUS  mandatory
                        DESCRIPTION
                            "This is a 15 byte string containing the Greenwich
                            Mean Time formatted as: YYMMDDHHMMSSUUU,
                                where:

                                    YY = year
                                    DD = day
                                    HH = hours
                                    MM = minutes
                                    SS = seconds
                                    UUU = microseconds"
                        ::= { propSysRun 1 }


                 rFddiIfIndex  OBJECT-TYPE
                        SYNTAX  INTEGER
                        ACCESS  read-only
                        STATUS  mandatory
                        DESCRIPTION
                            "The snmp Fddi interface Number"
                        ::= { propSysRun 2 }




                rPingTable  OBJECT-TYPE
                        SYNTAX  SEQUENCE OF RPingEntry
                        ACCESS  not-accessible
                        STATUS  mandatory
                        DESCRIPTION
                            "A table of requests for ping via ICMP echo.  No
                            modification of existing table entries is allowed,
                            only addition of new entries."
                        ::= { propSysRun 3 }

                rPingEntry  OBJECT-TYPE
                        SYNTAX  RPingEntry
                        ACCESS  not-accessible
                        STATUS  mandatory
                        DESCRIPTION
                            "The list of parameters required to perform a
                            ping request"
                        INDEX   { rPProto, rPDest }
                        ::= { rPingTable 1 }

                RPingEntry ::= SEQUENCE {
                        rPProto
                            INTEGER,
                        rPDest
                            NetworkAddress,
                        rPTimeOut
                            INTEGER,
                        rPReply
                            INTEGER,
                        rPState
                            INTEGER
                }

                rPProto  OBJECT-TYPE
                        SYNTAX  INTEGER {
                            icmp-echo(1)
                        }
                        ACCESS  read-write
                        STATUS  mandatory
                        DESCRIPTION
                            "The protocol to be used for the ping request.
                            Future versions will also support Loopback Mirror
                            and Decnet Circuit Loopback."
                        ::= { rPingEntry 1 }

                rPDest  OBJECT-TYPE
                        SYNTAX  NetworkAddress
                        ACCESS  read-write
                        STATUS  mandatory
                        DESCRIPTION
                            "The network address of the node to ping."
                        ::= { rPingEntry 2 }

                rPTimeOut  OBJECT-TYPE
                        SYNTAX  INTEGER
                        ACCESS  read-write
                        STATUS  mandatory
                        DESCRIPTION
                            "Timeout in seconds to allow for the remote node
                            to respond."
                        ::= { rPingEntry 3 }

                rPReply  OBJECT-TYPE
                        SYNTAX  INTEGER {
                            alive(1),
                            no-response(2),
                            in-process(3)
                        }
                        ACCESS  read-write
                        STATUS  mandatory
                        DESCRIPTION
                            "Reply to ICMP echo received by agent.  NOTE:
                            Although this object is defined as read-write,
                            attempting to write any value results in an
                            error."
                        ::= { rPingEntry 4 }

                rPState  OBJECT-TYPE
                        SYNTAX  INTEGER {
                            active(1),
                            inactive(2)
                        }
                        ACCESS  read-write
                        STATUS  mandatory
                        DESCRIPTION
                            "The state of the entry.  When this state is
                            set to ACTIVE, the appropriate ping request
                            will be issued by Brouter.  A table entry
                            with a state of INACTIVE is an invalidated
                            entry and will not be returned to a get
                            request."
                        ::= { rPingEntry 5 }

                rDebugTable  OBJECT-TYPE
                        SYNTAX  SEQUENCE OF RDebugEntry
                        ACCESS  not-accessible
                        STATUS  mandatory
                        DESCRIPTION
                            "A table of entries used to manage debug reporting
                            from the Brouter."
                        ::= { propSysRun 4 }

                rDebugEntry  OBJECT-TYPE
                        SYNTAX  RDebugEntry
                        ACCESS  not-accessible
                        STATUS  mandatory
                        DESCRIPTION
                            "Variables needed to maintain the FPP debug
                            mechanisms."
                        INDEX   { rDTaskId }
                        ::= { rDebugTable 1 }

                RDebugEntry ::= SEQUENCE {
                        rDTaskId
                            INTEGER,
                        rDDevStat
                            INTEGER,
                        rDRunStat
                            INTEGER
                }

                rDTaskId  OBJECT-TYPE
                        SYNTAX  INTEGER
                        ACCESS  read-only
                        STATUS  mandatory
                        DESCRIPTION
                            "Task-id assigned to the task being debugged.
                            Task-id`s are assigned as follows:

                                IP-ID           2
                                ICMP-ID         3
                                RIP-ID          4
                                UDP-ID          6
                                ARP-ID          7
                                KSMAP-ID        8
                                FMAINP-ID       9
                                SYSTEM-ID       10
                                PROXY-ARP-ID    11"
                        ::= { rDebugEntry 1 }

                rDDevStat  OBJECT-TYPE
                        SYNTAX  INTEGER {
                            on(1),
                            off(2)
                        }
                        ACCESS  read-write
                        STATUS  mandatory
                        DESCRIPTION
                            "Indicates whether the development level debug
                            messages for this module should be reported to
                            the NMS."
                        ::= { rDebugEntry 2 }

                rDRunStat  OBJECT-TYPE
                        SYNTAX  INTEGER {
                            on(1),
                            off(2)
                        }
                        ACCESS  read-write
                        STATUS  mandatory
                        DESCRIPTION
                            "Indicates whether the runtime network diagnostic
                            messages for this module should be reported to
                            the NMS."
                        ::= { rDebugEntry 3 }

                rUDnld  OBJECT-TYPE
                        SYNTAX  INTEGER
                        ACCESS  read-write
                        STATUS  mandatory
                        DESCRIPTION
                            "Setting this object to 1 has the side effect of
                            causing the unit to perform a cold reset.
                            Reading this object has no meaning. The value 1
                            is returned in response to a get or get-next
                            request."
                        ::= { propSysRun 7 }

                rURset  OBJECT-TYPE
                        SYNTAX  INTEGER
                        ACCESS  read-write
                        STATUS  mandatory
                        DESCRIPTION
                            "Setting this object to 1 has the side effect of
                            causing the unit to perform a warm reset.
                            Reading this object has no meaning. The value 1
                            is returned in response to a get or get-next
                            request."
                        ::= { propSysRun 8 }

                rUIpSw  OBJECT-TYPE
                        SYNTAX  INTEGER {
                            on(1),
                            off(2)
                        }
                        ACCESS  read-write
                        STATUS  mandatory
                        DESCRIPTION
                            "Indicates the state of the IP routing feature.
                            If this switch is turned OFF, IP traffic will
                            not be routed through the brouter.  IP messages
                            destined for the brouter will be delivered to
                            the unit's upper layers.  This leaves the SNMP
                            agent accessible to its manager even when IP
                            routing is de-activated.  If bridging is
                            activated, the IP traffic will be bridged."
                        ::= { propSysRun 10 }

                rUDecSw  OBJECT-TYPE
                        SYNTAX  INTEGER {
                            on(1),
                            off(2)
                        }
                        ACCESS  read-write
                        STATUS  mandatory
                        DESCRIPTION
                            "Indicates the state of the Decnet feature.
                            If this switch is turned OFF, no Decnet traffic
                            will be routed through this unit.  If bridging is
                            activated, the Decnet trafic will be bridged."
                        ::= { propSysRun 11 }

                rUBrSw  OBJECT-TYPE
                        SYNTAX  INTEGER {
                            on(1),
                            off(2)
                        }
                        ACCESS  read-write
                        STATUS  mandatory
                        DESCRIPTION
                            "Indicates the state of the bridging feature.
                            If this switch is turned OFF, no traffic
                            will be bridged through this unit.  All traffic
                            will be required to be sent through one of the
                            active routing functions."
                        ::= { propSysRun 12 }

                rUIpCfg  OBJECT-TYPE
                        SYNTAX  INTEGER {
                            rt-cfg-host-only(1),
                            rt-cfg-br-ether(2),
                            rt-cfg-br-all(3),
                            rt-cfg-rte-all(4)
                        }
                        ACCESS  read-write
                        STATUS  mandatory
                        DESCRIPTION
                            "Indicates the state of IP routing based on its
                            (sub)net configuration.  RT-CFG-HOST-ONLY indicates
                            that there is only one IP address in the unit.
                            All IP packets received while in this state will
                            be bridged as an unknown protocol."
                        ::= { propSysRun 13 }

                rURunningVersion  OBJECT-TYPE
                        SYNTAX  OCTET STRING
                        ACCESS  read-only
                        STATUS  mandatory
                        DESCRIPTION
                            "Indicates the running version."
                        ::= { propSysRun 14 }

                rUDnldAllowed  OBJECT-TYPE
                        SYNTAX  INTEGER {
                            true(1),
                            false(2)
                        }
                        ACCESS  read-write
                        STATUS  mandatory
                        DESCRIPTION
                            "Indicates whether downloading to the brouter's
                            Flash memory will be permitted.  If this flag is
                            set to OFF the agent will refuse to download
                            into its flash memory.  At system start-up this
                            parameter will be initialized to OFF.  Once this
                            has been set to ON, it will remain ON until either
                            the user sets it to OFF or a download has been
                            performed at which time the agent will set it
                            to OFF."
                        ::= { propSysRun 15 }

                rUInitFlash  OBJECT-TYPE
                        SYNTAX  INTEGER {
                            true(1),
                            false(2)
                        }
                        ACCESS  read-write
                        STATUS  mandatory
                        DESCRIPTION
                            "Indicates if the flash bank states are being
                            initialized.  If this object is set to TRUE, the
                            side effect will be to cause the flash states
                            to be initialized.  If the flash is in the
                            process of being initialized, a get or getnext
                            operation performed on this object will return
                            1 (TRUE), otherwise it will return 2 (FALSE)."
                        ::= { propSysRun 16 }


                -- permanent proprietary objects

                pPMibVer  OBJECT-TYPE
                        SYNTAX  INTEGER
                        ACCESS  read-only
                        STATUS  mandatory
                        DESCRIPTION
                            "Proprietary mib version number."
                        ::= { propSysPerm 2 }

                pEepVer  OBJECT-TYPE
                        SYNTAX  INTEGER {
                            single-eth(1),
                            dual-eth(2),
                            brouter(3)
                        }
                        ACCESS  read-only
                        STATUS  mandatory
                        DESCRIPTION
                            "Version number supported in the EEPROM."
                        ::= { propSysPerm 4 }

                pUIpSw  OBJECT-TYPE
                        SYNTAX  INTEGER {
                            on(1),
                            off(2)
                        }
                        ACCESS  read-write
                        STATUS  mandatory
                        DESCRIPTION
                            "Permanently stored (EEPROM) value for IP
                            routing status.  See rUIpSw for a complete
                            description.  The default value for this object
                            is ON."
                        ::= { propSysPerm 6 }

                pUDecSw  OBJECT-TYPE
                        SYNTAX  INTEGER {
                            on(1),
                            off(2)
                        }
                        ACCESS  read-write
                        STATUS  mandatory
                        DESCRIPTION
                            "Permanently stored (EEPROM) value for DECnet
                            routing status.  See rUDecSw for a complete
                            description.  The default value for this object
                            is ON."
                        ::= { propSysPerm 7 }

                pUBrSw  OBJECT-TYPE
                        SYNTAX  INTEGER {
                            on(1),
                            off(2)
                        }
                        ACCESS  read-write
                        STATUS  mandatory
                        DESCRIPTION
                            "Permanently stored (EEPROM) value for
                            bridging status.  See rUBrSw for a complete
                            description.  The default value for this object
                            is ON."
                        ::= { propSysPerm 8 }

                pUIpCfg  OBJECT-TYPE
                        SYNTAX  INTEGER
                        ACCESS  read-only
                        STATUS  mandatory
                        DESCRIPTION
                            "Permanently stored (EEPROM) value for
                            IP configuration.  See rUIpCfg for a complete
                            description.  The default value for this object
                            is determined by the IP address stored in the
                            permanent database."
                        ::= { propSysPerm 9 }

                pULoadVersion  OBJECT-TYPE
                        SYNTAX  OCTET STRING
                        ACCESS  read-write
                        STATUS  mandatory
                        DESCRIPTION
                            "Permanently stored (EEPROM) value for the
                            desired load version.  This value of this object
                            indicates which flash-stored version is to be
                            initiated upon reset of this unit."
                        ::= { propSysPerm 10 }

                pUDefaults  OBJECT-TYPE
                        SYNTAX  INTEGER
                        ACCESS  read-write
                        STATUS  mandatory
                        DESCRIPTION
                            "When this object is set to 1, the side effect will
                            be to cause the unit to reset all the objects
                            defined under the subtree propSysPerm to their
                            default values.  Reading this object has no
                            meaning.  The integer value 1 will be returned
                            to a get or get-next request."
                        ::= { propSysPerm 11 }

                pUFlashTable  OBJECT-TYPE
                        SYNTAX  SEQUENCE OF PUFlashEntry
                        ACCESS  not-accessible
                        STATUS  mandatory
                        DESCRIPTION
                            "Contains the information needed for Flash memory
                            maintenance."
                        ::= { propSysPerm 12 }

                pUFlashEntry OBJECT-TYPE
                        SYNTAX  PUFlashEntry
                        ACCESS  not-accessible
                        STATUS  mandatory
                        DESCRIPTION
                            "Information about a particular bank of flash
                            memory."
                        --INDEX   { FlashIndex }
                        ::= { pUFlashTable 1 }

                PUFlashEntry ::= SEQUENCE {
                        flashIndex
                            INTEGER,
                        flashVersion
                            OCTET STRING,
                        flashState
                            INTEGER
                }

                flashIndex  OBJECT-TYPE
                        SYNTAX  INTEGER
                        ACCESS  read-only
                        STATUS  mandatory
                        DESCRIPTION
                            "A unique index value for each flash memory bank."
                        ::= { pUFlashEntry 1 }

                flashVersion  OBJECT-TYPE
                        SYNTAX  OCTET STRING
                        ACCESS  read-only
                        STATUS  mandatory
                        DESCRIPTION
                            "Indicates the version contained in this flash
                            memory bank.  If the flash memory bank is
                            uninitialized or invalid, this object will
                            contain a NULL string"
                        ::= { pUFlashEntry 2 }

                flashState  OBJECT-TYPE
                        SYNTAX  INTEGER {
                            valid(1),
                            invalid(2),
                            dnloading-in-process(3),
                            reset-in-progress(4),
                            reset-complete(5)
                        }
                        ACCESS  read-only
                        STATUS  mandatory
                        DESCRIPTION
                            ""
                        ::= { pUFlashEntry 3 }

                sysPermBridgeAvailable  OBJECT-TYPE
                        SYNTAX  INTEGER {
                            true(1),
                            false(2)
                        }
                        ACCESS  read-only
                        STATUS  mandatory
                        DESCRIPTION
                            "Indicates whether the unit supports bridging
                            functionality or not."
                        ::= { propSysPerm 13 }

                sysPermIpAvailable  OBJECT-TYPE
                        SYNTAX  INTEGER {
                            true(1),
                            false(2)
                        }
                        ACCESS  read-only
                        STATUS  mandatory
                        DESCRIPTION
                            "Indicates whether the unit supports IP
                            functionality or not.  IP host functionality is
                            always present."
                        ::= { propSysPerm 14 }

                sysPermDecAvailable   OBJECT-TYPE
                        SYNTAX  INTEGER {
                            true(1),
                            false(2)
                        }
                        ACCESS  read-only
                        STATUS  mandatory
                        DESCRIPTION
                            "Indicates whether the unit supports DECnet
                            functionality or not."
                        ::= { propSysPerm 15 }

                pUloadType  OBJECT-TYPE
                        SYNTAX  INTEGER
                        ACCESS  read-write
                        STATUS  mandatory
                        DESCRIPTION
                            "This object indicates the type of download to
                            be exercised the next time the unit is loaded.
                            It is a choice of:

                                USER        1
                                MFG         2
                                DEV         3"
                        ::= { propSysPerm 50 }


                -- runtime proprietary IP objects

                rIpMaskTable  OBJECT-TYPE
                        SYNTAX  SEQUENCE OF RIpMaskEntry
                        ACCESS  not-accessible
                        STATUS  mandatory
                        DESCRIPTION
                            "The list of address masks used by this router
                            for determining its subnets."
                        ::= { propIpRun 1 }

                rIpMaskEntry  OBJECT-TYPE
                        SYNTAX  RIpMaskEntry
                        ACCESS  not-accessible
                        STATUS  mandatory
                        DESCRIPTION
                            "Items contained in the runtime Address Mask
                            Table."
                        INDEX   { rMaskNet }
                        ::= { rIpMaskTable 1 }

                RIpMaskEntry ::= SEQUENCE {
                        rMaskNet
                            NetworkAddress,
                        rMask
                            NetworkAddress,
                        rMaskState
                            INTEGER
                }

                rMaskNet  OBJECT-TYPE
                        SYNTAX  NetworkAddress
                        ACCESS  read-write
                        STATUS  mandatory
                        DESCRIPTION
                            "The IP network this mask is defined for."
                        ::= { rIpMaskEntry 1 }

                rMask  OBJECT-TYPE
                        SYNTAX  NetworkAddress
                        ACCESS  read-write
                        STATUS  mandatory
                        DESCRIPTION
                            "The subnet mask associated with the IP address
                            of this entry.  The value of the mask is an IP
                            address with all the network bits set to 1
                            and all the hosts bits set to 0."
                        ::= { rIpMaskEntry 2 }

                rMaskState  OBJECT-TYPE
                        SYNTAX  INTEGER {
                            active(1),
                            inactive(2)
                        }
                        ACCESS  read-write
                        STATUS  mandatory
                        DESCRIPTION
                            "The state of this entry.  To remove an entry
                            from the table, simply set this field to
                            INACTIVE."
                        ::= { rIpMaskEntry 3 }

                rIpOurAddrTable  OBJECT-TYPE

                        SYNTAX  SEQUENCE OF RIpOurAddrEntry
                        ACCESS  not-accessible
                        STATUS  mandatory
                        DESCRIPTION
                            "Proprietary extensions for the rfc1156 defined
                            ipAddrTable."
                        ::= { propIpRun 2 }

                rIpOurAddrEntry  OBJECT-TYPE
                        SYNTAX  RIpOurAddrEntry
                        ACCESS  not-accessible
                        STATUS  mandatory
                        DESCRIPTION
                            "Proprietary extensions for the rfc1156 defined
                            ipAddrEntry.  A proprietary ipAddrTable entry
                            contains 4 standard objects and the 4 proprietary
                            objects listed below.  The standard objects
                            are: ipAdEntAddr, ipAdEntIfIndex, ipAdEntNetMask
                            and ipAdEntBcastAddr.  To add an ipAddrEntry to
                            the ipAddrTable, the rAddrState is the validating
                            item.  Therefore, rAddrState must be the last item
                            in the message when adding an entry.  The
                            ipAdEntNetMask is determined by the agent.  There
                            is a separate mechanism that allows the user to
                            define address masks for the unit.  See
                            rIpMaskTable and pIpMaskTable.  To add to the
                            ipAddrTable the agent requires the ipAdEntAddr,
                            ipAdEntIfIndex, ipAdEntBcastAddr, rAddrDBcast,
                            rAddrRipMetric and the rAddrRipState followed by
                            the rAddrState.  There are 4 default values
                            provided by the agent for this entry:
                            ipAdEntBcastAddr defaults to 'all ones',
                            rAddrDbcast defaults to 'no directed broadcast',
                            rAddrRipState defaults to ON and rAddrRipMetric
                            defaults to 1.  To remove an ipAddrEntry, the
                            rAddrState should be set to INACTIVE.  The INDEX
                            value specified should correspond to the IP
                            address of the desired entry."
                        --INDEX   { IpAddress }
                        ::= { rIpOurAddrTable 1 }

                RIpOurAddrEntry ::= SEQUENCE {
                        rAddrDbcast
                            INTEGER,
                        rAddrRipMetric
                            INTEGER,
                        rAddrRipState
                            INTEGER,
                        rAddrState
                            INTEGER
                }

                rAddrDbcast  OBJECT-TYPE
                        SYNTAX  INTEGER {
                            no-directed-bdcst(1),
                            bdcst-host(2),
                            bdcst-net(3)
                        }
                        ACCESS  read-write
                        STATUS  mandatory
                        DESCRIPTION
                            "Allows the user to set the directed broadcast
                            parameter of an IP network.  Default value
                            is 'no directed broadcast'."
                        ::= { rIpOurAddrEntry 1 }

                rAddrRipMetric  OBJECT-TYPE
                        SYNTAX  INTEGER
                        ACCESS  read-write
                        STATUS  mandatory
                        DESCRIPTION
                            "A number from 1 to 15 used to calculate the
                            metrics to given destinations, RIP will add
                            this metric to metrics received from other
                            RIP gateways on this (sub)network.  In effect,
                            this can be used to prioritize the (sub)network
                            used for a destination reachable via more than
                            one Brouter (sub)network.  Default value is 1."
                        ::= { rIpOurAddrEntry 2 }

                rAddrRipState  OBJECT-TYPE
                        SYNTAX  INTEGER {
                            on(1),
                            off(2),
                            quiet(3)
                        }
                        ACCESS  read-write
                        STATUS  mandatory
                        DESCRIPTION
                            "Defines the current state of the RIP protocol
                            for this IP network.  The default value is ON."
                        ::= { rIpOurAddrEntry 3 }

                rAddrState  OBJECT-TYPE
                        SYNTAX  INTEGER {
                            active(1),
                            inactive(2)
                        }
                        ACCESS  read-write
                        STATUS  mandatory
                        DESCRIPTION
                            "The state of this entry.  To remove an entry
                            from the table, simply set this field to INACTIVE."
                        ::= { rIpOurAddrEntry 4 }

                rIpIfTable  OBJECT-TYPE
                        SYNTAX  SEQUENCE OF RIpIfEntry
                        ACCESS  not-accessible
                        STATUS  mandatory
                        DESCRIPTION
                            "Proprietary extensions for the rfc1156 defined
                            ifTable."
                        ::= { propIpRun 3 }

                rIpIfEntry  OBJECT-TYPE
                        SYNTAX  RIpIfEntry
                        ACCESS  not-accessible
                        STATUS  mandatory
                        DESCRIPTION
                            "Proprietary extensions for the rfc1156 defined
                            ifEntry.  The INDEX value specified should
                            correspond to the index of the interface of
                            the desired entry."
                        --INDEX   { INTEGER }
                        ::= { rIpIfTable 1 }

                RIpIfEntry ::= SEQUENCE {
                        rIfArpStat
                            INTEGER,
                        rIfPArpStat
                            INTEGER,
                        rIfBcMask
                            INTEGER
                }

                rIfArpStat  OBJECT-TYPE
                        SYNTAX  INTEGER {
                            on(1),
                            off(2)
                        }
                        ACCESS  read-write
                        STATUS  mandatory
                        DESCRIPTION
                            "Allows the user to turn ARP on and off for the
                            interface."
                        ::= { rIpIfEntry 1 }

                rIfPArpStat  OBJECT-TYPE
                        SYNTAX  INTEGER {
                            on(1),
                            off(2)
                        }
                        ACCESS  read-write
                        STATUS  mandatory
                        DESCRIPTION
                            "Allows the user to turn proxy ARP on and off
                            for the interface."
                        ::= { rIpIfEntry 2 }

                rIfBcMask  OBJECT-TYPE
                        SYNTAX  INTEGER {
                            on(1),
                            off(2)
                        }
                        ACCESS  read-write
                        STATUS  mandatory
                        DESCRIPTION
                            "When set to ON, Brouter will broadcast its
                            address mask on start up.  When set to OFF,
                            the Brouter will not broadcast its address
                            mask on start up."
                        ::= { rIpIfEntry 3 }

                rDftGw  OBJECT-TYPE
                        SYNTAX  NetworkAddress
                        ACCESS  read-write
                        STATUS  mandatory
                        DESCRIPTION
                            "The IP address of the default gateway."
                        ::= { propIpRun 4 }

                rIpAtTable  OBJECT-TYPE
                        SYNTAX  SEQUENCE OF RIpAtEntry
                        ACCESS  not-accessible
                        STATUS  mandatory
                        DESCRIPTION
                            "Proprietary extensions for the rfc1156 defined
                            atTable."
                        ::= { propIpRun 5 }

                rIpAtEntry  OBJECT-TYPE
                        SYNTAX  RIpAtEntry
                        ACCESS  not-accessible
                        STATUS  mandatory
                        DESCRIPTION
                            "Proprietary extensions for the rfc1156 defined
                            atEntry.  A proprietary atTable entry contains
                            3 standard objects and the 2 proprietary objects
                            listed below.  The standard objects are:
                            atIfIndex, atPhysAddress and atNetAddress.  To
                            add an atEntry to the atTable, MIB-II defines
                            the atPhysAddress as the validating item.
                            Therefore, atPhysAddress must be the last item in
                            the message when adding an entry.  To add to the
                            atTable the user must provide the atNetAddress
                            followed by the atPhysAddress.  The 2 proprietary
                            objects associated with this entry are provided
                            by the agent.  The rAtAge is incremented as the
                            entry ages and the rAtStatic entry is set to
                            static.  All atEntries manually defined are
                            considered static and are not removed by the agent
                            until specifically requested by the manager.  To
                            remove an atEntry, the atPhysAddress should be
                            set to a NULL string.  The INDEX value is
                            constructed from the interface index of the
                            desired entry, the integer value 1, and the
                            network address of the desired entry."
                        --INDEX   { INTEGER, INTEGER, NetworkAddress }
                        ::= { rIpAtTable 1 }

                RIpAtEntry ::= SEQUENCE {
                        rAtStatic
                            INTEGER,
                        rAtAge
                            INTEGER
                }

                rAtStatic  OBJECT-TYPE
                        SYNTAX  INTEGER {
                            static(1),
                            dynamic(2)
                        }
                        ACCESS  read-only
                        STATUS  mandatory
                        DESCRIPTION
                            "Defines an entry as static or dynamic.  A static
                            entry is one that has been entered manually by
                            the network administrator and can be changed
                            only by the network administrator.  The routing
                            protocols never overwrite a static entry.  A
                            dynamic entry is one created by the routing
                            protocols and is updated by them as per standard
                            definitions."
                        ::= { rIpAtEntry 1 }

                rAtAge  OBJECT-TYPE
                        SYNTAX  INTEGER
                        ACCESS  read-only
                        STATUS  mandatory
                        DESCRIPTION
                            "The age of the entry in minutes."
                        ::= { rIpAtEntry 2 }

                rIpRtTable  OBJECT-TYPE
                        SYNTAX  SEQUENCE OF RIpRtEntry
                        ACCESS  not-accessible
                        STATUS  mandatory
                        DESCRIPTION
                            "Proprietary extensions for the rfc1156 defined
                            ipRoutingTable."
                        ::= { propIpRun 6 }

                rIpRtEntry  OBJECT-TYPE
                        SYNTAX  RIpRtEntry
                        ACCESS  not-accessible
                        STATUS  mandatory
                        DESCRIPTION
                            "Proprietary extensions for the rfc1156 defined
                            ipRoutingEntry.  A proprietary ipRouteEntry entry
                            contains 10 standard objects and the proprietary
                            object listed below.  The standard objects are:
                            ipRouteDest, ipRouteIfIndex, ipRouteMetric1,
                            ipRouteMetric2, ipRouteMetric3, ipRouteMetric4,
                            ipRouteNextHop, ipRouteType, ipRouteProto and
                            ipRouteAge.  To add an atEntry to the
                            ipRoutingTable,  MIB-II defines the ipRouteType
                            as the validating item.  Therefore, ipRouteType
                            must be the last item in the message when adding
                            an entry.  All items, both proprietary and
                            standard, except the ipRouteDest, ipRouteNextHop,
                            ipRouteMetric1, and ipRouteType are determined
                            by the agent.  To add to the ipRouteEntry the
                            agent requires the ipRouteDest, ipRouteNextHop,
                            and the ipRouteMetric1 followed by the
                            ipRouteType.  The ipRouteIfIndex is determined
                            by the agent based on the ipRouteDest.
                            The ipRouteMetric2, ipRouteMetric3 and
                            ipRouteMetric4 are not used by the router and
                            are set to zero.  The ipRouteProto is set to
                            local and rRtStatic is set to static.  All
                            ipRouteEntries manually defined are considered
                            static and are not removed by the agent until
                            specifically requested by the manager.  If the
                            ipRouteMetric1 is not provided, it's value
                            defaults to 1.  To remove an ipRouteEntry, the
                            ipRouteType should be set to invalid.  The INDEX
                            value specified should correspond to the
                            destination IP address of the desired entry."
                        --INDEX   { IpAddress }
                        ::= { rIpRtTable 1 }

                RIpRtEntry ::= SEQUENCE {
                        rRtStatic
                            INTEGER
                }

                rRtStatic  OBJECT-TYPE
                        SYNTAX  INTEGER {
                            static(1),
                            dynamic(2)
                        }
                        ACCESS  read-only
                        STATUS  mandatory
                        DESCRIPTION
                            "Defines an entry as static or dynamic.  A static
                            entry is one that has been entered manually by
                            the network administrator and can be changed only
                            by the network administrator.  The routing
                            protocols never overwrite a static entry.  A
                            dynamic entry is one created by the routing
                            protocols and is updated by them as per standard
                            definitions."
                        ::= { rIpRtEntry 1 }

                rRipTrInd  OBJECT-TYPE
                        SYNTAX  INTEGER {
                            off(2),
                            trusted(3),
                            not-trusted(4)
                        }
                        ACCESS  read-write
                        STATUS  mandatory
                        DESCRIPTION
                            "This flag indicates whether the rRipTrustTable
                            is used to list trusted or not-trusted gateways.
                            When the state is changed, all existing entries
                            in the table are cleared.  The default value is
                            OFF.  Setting this object to OFF causes the
                            trust list to be removed and the router is
                            returned to the default state of TRUST ALL."
                        ::= { propIpRun 7 }

                rRipTrustTable  OBJECT-TYPE
                        SYNTAX  SEQUENCE OF RRipTrustEntry
                        ACCESS  not-accessible
                        STATUS  mandatory
                        DESCRIPTION
                            "This table has 2 possible meanings depending on
                            the value of rRipTrInd.  These 2 configuration
                            options allow the network administrator to limit
                            RIP's scope for inbound processing.  Outbound
                            processing in not affected by this table.  If
                            rRipTrInd is set to TRUSTED, RIP listens only to
                            the indicated gateways and no others.  If
                            rRipTrInd is set to NOT-TRUSTED, RIP does not
                            listen to the indicated gateways but will accept
                            updates from all other gateways.  If the value
                            of rRipTrInd is changed, this table is cleared.
                            If the table is empty, it is assumed that all
                            gateways are to be trusted or not-trusted
                            depending on the value of rRipTrInd.  The default
                            for initialization is all gateways are trusted."
                        ::= { propIpRun 8 }

                rRipTrustEntry  OBJECT-TYPE
                        SYNTAX  RRipTrustEntry
                        ACCESS  not-accessible
                        STATUS  mandatory
                        DESCRIPTION
                            "The list of fields needed to support the
                            rRipTrustTable."
                        INDEX   { rTrRestGw }
                        ::= { rRipTrustTable 1 }

                RRipTrustEntry ::= SEQUENCE {
                        rTrRestGw
                            NetworkAddress,
                        rTrRestState
                            INTEGER
                }

                rTrRestGw  OBJECT-TYPE
                        SYNTAX  NetworkAddress
                        ACCESS  read-write
                        STATUS  mandatory
                        DESCRIPTION
                            "The IP address of the gateway being restricted."
                        ::= { rRipTrustEntry 1 }

                rTrRestState  OBJECT-TYPE
                        SYNTAX  INTEGER {
                            active(1),
                            inactive(2)
                        }
                        ACCESS  read-write
                        STATUS  mandatory
                        DESCRIPTION
                            "The state of this entry.  To add an entry to the
                            list, set this field to ACTIVE.  To remove an
                            entry from the table, simply set this field to
                            INACTIVE."
                        ::= { rRipTrustEntry 2 }

                rRipLsnIndTable  OBJECT-TYPE
                        SYNTAX  SEQUENCE OF RRipLsnIndEntry
                        ACCESS  not-accessible
                        STATUS  mandatory
                        DESCRIPTION
                            "The rRipLsnIndTable contains the flags that
                            indicate the type of listen restriction that
                            is active for a given destination address."
                        ::= { propIpRun 9 }

                rRipLsnIndEntry  OBJECT-TYPE
                        SYNTAX  RRipLsnIndEntry
                        ACCESS  not-accessible
                        STATUS  mandatory
                        DESCRIPTION
                            "The variables needed to maintain an entry in
                            the rRipLsnIndTable."
                        INDEX   { rRipLsnIndDest }
                        ::= { rRipLsnIndTable 1 }

                RRipLsnIndEntry ::= SEQUENCE {
                        rRipLsnIndDest
                            NetworkAddress,
                        rRipLsnType
                            INTEGER
                }

                rRipLsnIndDest  OBJECT-TYPE
                        SYNTAX  NetworkAddress
                        ACCESS  read-write
                        STATUS  mandatory
                        DESCRIPTION
                            "The restricted destination address.  For the
                            LISTEN list this address will be the address of
                            a gateway on a locally attached (sub)network.
                            For the DO-NOT-LISTEN list this address will
                            be a locally attached (sub)network."
                        ::= { rRipLsnIndEntry 1 }

                rRipLsnType  OBJECT-TYPE
                        SYNTAX  INTEGER {
                            off(2),
                            listen(3),
                            do-not-listen(4)
                        }
                        ACCESS  read-write
                        STATUS  mandatory
                        DESCRIPTION
                            "Indicates whether the restricted list for this
                            destination is a LISTEN list or a DO-NOT-LISTEN
                            list.  When the restriction indicator is changed,
                            the associated LISTEN/DO-NOT-LISTEN list is
                            removed.  This field is the validation field to
                            add/delete an entry in this table."
                        ::= { rRipLsnIndEntry 2 }

                rRipLsnTable  OBJECT-TYPE
                        SYNTAX  SEQUENCE OF RRipLsnEntry
                        ACCESS  not-accessible
                        STATUS  mandatory
                        DESCRIPTION
                            "Setting this table causes RIP to select inbound
                            update information about a specific network or
                            host.  This table allows the network administrator
                            to limit RIP's scope for inbound processing.
                            Outbound processing is not affected by this table.
                            If the rRipLsnType for this destination is set to
                            LISTEN, RIP will use updates received from the
                            specified gateways only.  If the rRipLsnType is
                            set to DO-NOT-LISTEN, RIP will discard updates
                            received from the specified gateways and process
                            all others.  If the value of rRipLsnType is
                            changed, this table is cleared.  This table is
                            maintained on a per destination basis.  If the
                            table is empty, it is assumed that all gateways
                            are LISTEN for all destination addresses.  This
                            is also the default setting.  To change the state
                            of an entry in this table from LISTEN to
                            DO-NOT-LISTEN or vice versa, change the rRipLsnType
                            for the destination address and then define the
                            new restriction list for that address."
                        ::= { propIpRun 10 }

                rRipLsnEntry  OBJECT-TYPE
                        SYNTAX  RRipLsnEntry
                        ACCESS  not-accessible
                        STATUS  mandatory
                        DESCRIPTION
                            "The list of fields needed to support the
                            rRipLsnTable."
                        INDEX   { rLsnAddr, rLsnRstAddr }
                        ::= { rRipLsnTable 1 }

                RRipLsnEntry ::= SEQUENCE {
                        rLsnAddr
                            NetworkAddress,
                        rLsnRstAddr
                            NetworkAddress,
                        rLsnRstState
                            INTEGER
                }

                rLsnAddr  OBJECT-TYPE
                        SYNTAX  NetworkAddress
                        ACCESS  read-write
                        STATUS  mandatory
                        DESCRIPTION
                            "The destination address being restricted by
                            this command."
                        ::= { rRipLsnEntry 1 }

                rLsnRstAddr  OBJECT-TYPE
                        SYNTAX  NetworkAddress
                        ACCESS  read-write
                        STATUS  mandatory
                        DESCRIPTION
                            "The IP address of the gateway/network being
                            restricted."
                        ::= { rRipLsnEntry 2 }

                rLsnRstState  OBJECT-TYPE
                        SYNTAX  INTEGER {
                            active(1),
                            inactive(2)
                        }
                        ACCESS  read-write
                        STATUS  mandatory
                        DESCRIPTION
                            "The state of this entry.  To remove an entry
                            from the table, set this field to INACTIVE.
                            To add an item to this table set the state to
                            ACTIVE.  However, please note that before entries
                            be added to this list it must have a corresponding
                            entry in the rRipLsnIndTable."
                        ::= { rRipLsnEntry 3 }

                rRipAnncIndTable  OBJECT-TYPE
                        SYNTAX  SEQUENCE OF RRipAnncIndEntry
                        ACCESS  not-accessible
                        STATUS  mandatory
                        DESCRIPTION
                            "The rRipAnncIndTable contains the flags that
                            indicate the type of announce restriction(s) that
                            are active for each (sub)network supported by the
                            unit.  Please note that before any entries can be
                            defined here or in the rRipAnncTable, the
                            (sub)network must be defined to the router via
                            an ipAddrEntry."
                        ::= { propIpRun 11 }

                rRipAnncIndEntry  OBJECT-TYPE
                        SYNTAX  RRipAnncIndEntry
                        ACCESS  not-accessible
                        STATUS  mandatory
                        DESCRIPTION
                            "The variables needed to maintain an entry in
                            the rRipAnncIndTable."
                        INDEX   { rRipAnncIndNet }
                        ::= { rRipAnncIndTable 1 }

                RRipAnncIndEntry ::= SEQUENCE {
                        rRipAnncIndNet
                            NetworkAddress,
                        rRipAnncType
                            INTEGER
                }

                rRipAnncIndNet  OBJECT-TYPE
                        SYNTAX  NetworkAddress
                        ACCESS  read-write
                        STATUS  mandatory
                        DESCRIPTION
                            "The IP address this unit recognizes on the
                            (sub)network being restricted."
                        ::= { rRipAnncIndEntry 1 }

                rRipAnncType  OBJECT-TYPE
                        SYNTAX  INTEGER {
                            off(2),
                            announce(3),
                            do-not-announce(4)
                        }
                        ACCESS  read-write
                        STATUS  mandatory
                        DESCRIPTION
                            "Indicates whether this (sub)network has an
                            ANNOUNCE list, a DO-NOT-ANNOUNCE list or if the
                            restriction is shut OFF.  When the restriction
                            indicator is changed, the associated
                            ANNOUNCE/DO-NOT-ANNOUNCE list is removed."
                        ::= { rRipAnncIndEntry 2 }

                rRipAnncTable  OBJECT-TYPE
                        SYNTAX  SEQUENCE OF RRipAnncEntry
                        ACCESS  not-accessible
                        STATUS  mandatory
                        DESCRIPTION
                            "Setting this table causes RIP to taylor its
                            update announcements.  This table allows the
                            network administrator to limit RIP's scope for
                            outbound processing.  Inbound processing is not
                            affected by this table.  If the rRipAnncType
                            is set to ANNOUNCE, RIP will adjust its outbound
                            announcments on the indicated (sub)network by
                            propogating announcements for those gateways
                            listed in the rRipAnncTable only.  All
                            announcements for gateways not on the ANNOUNCE
                            list will not be sent over the associated
                            (sub)network.  If the rRipAnncType is set to
                            DO-NOT-ANNOUNCE, RIP will adjust its outbound
                            announcements on the indicated (sub)network by
                            not propogating announcements for those gateways
                            listed in the rRipAnncTable.  All other
                            announcements will be propogated on the indicated
                            (sub)network.  If the value of ripAnncType is
                            changed, this table is cleared.  This table is
                            maintained on a per (sub)network basis.  If the
                            table is empty, it is assumed that all gateways
                            on all (sub)networks are ANNOUNCE.  This is also
                            the default state.  To change the state of an
                            entry from ANNOUNCE to DO-NOT-ANNOUNCE or vice
                            versa, change the rRipAnncType in the
                            ripAnncIndTable for the (sub)network and then
                            define the new restriction list for the
                            (sub)network.  Please note that before any
                            entries can be defined here or in the
                            rRipAnncIndTable, the (sub)network must be
                            defined to the router via an ipAddrEntry."
                        ::= { propIpRun 12 }

                rRipAnncEntry  OBJECT-TYPE
                        SYNTAX  RRipAnncEntry
                        ACCESS  not-accessible
                        STATUS  mandatory
                        DESCRIPTION
                            "The list of fields needed to support the
                            rRipAnncTable."
                        INDEX   { rAnncDestAddr, rAnncNet }
                        ::= { rRipAnncTable 1 }

                RRipAnncEntry ::= SEQUENCE {
                        rAnncNet
                            NetworkAddress,
                        rAnncDestAddr
                            NetworkAddress,
                        rAnncRstState
                            INTEGER
                }

                rAnncNet  OBJECT-TYPE
                        SYNTAX  NetworkAddress
                        ACCESS  read-write
                        STATUS  mandatory
                        DESCRIPTION
                            "The IP address this unit recognizes on the
                            (sub)network being restricted."
                        ::= { rRipAnncEntry 1 }

                rAnncDestAddr  OBJECT-TYPE
                        SYNTAX  NetworkAddress
                        ACCESS  read-write
                        STATUS  mandatory
                        DESCRIPTION
                            "The IP address of the gateway being restricted."
                        ::= { rRipAnncEntry 2 }

                rAnncRstState  OBJECT-TYPE
                        SYNTAX  INTEGER {
                            active(1),
                            inactive(2)
                        }
                        ACCESS  read-write
                        STATUS  mandatory
                        DESCRIPTION
                            "The state of this entry.  To remove an entry
                            from the table, simply set this field to
                            INACTIVE."
                        ::= { rRipAnncEntry 3 }

                rRipSrcTable  OBJECT-TYPE
                        SYNTAX  SEQUENCE OF RRipSrcEntry
                        ACCESS  not-accessible
                        STATUS  mandatory
                        DESCRIPTION
                            "Setting this table causes RIP broadcasting to be
                            shut off by indicating which gateways should
                            receive directed RIP information.  No broadcast
                            RIP update massages will be sent on the specified
                            network.  This table allows the network
                            administrator to limit RIP's scope for outbound
                            processing.  Inbound processing is not affected
                            by this table.  As stated above, this table is
                            maintained on a per (sub)network basis.  If the
                            table is empty, it is assumed that all gateways
                            are to receive updates, i.e. broadcast is turned
                            on.  The default is broadcast all updates on all
                            (sub)networks.  Please note that before any
                            entries can be defined here, the (sub)network
                            must be defined to the router via an ipAddrEntry."
                        ::= { propIpRun 13 }

                rRipSrcEntry  OBJECT-TYPE
                        SYNTAX  RRipSrcEntry
                        ACCESS  not-accessible
                        STATUS  mandatory
                        DESCRIPTION
                            "The list of fields needed to support the
                            rRipSrcTable."
                        INDEX   { rSrcAddr, rSrcRstGw }
                        ::= { rRipSrcTable 1 }

                RRipSrcEntry ::= SEQUENCE {
                        rSrcAddr
                            NetworkAddress,
                        rSrcRstGw
                            NetworkAddress,
                        rSrcRstState
                            INTEGER
                }

                rSrcAddr  OBJECT-TYPE
                        SYNTAX  NetworkAddress
                        ACCESS  read-write
                        STATUS  mandatory
                        DESCRIPTION
                            "The IP address this unit recognizes on the
                            (sub)network being restricted."
                        ::= { rRipSrcEntry 1 }

                rSrcRstGw  OBJECT-TYPE
                        SYNTAX  NetworkAddress
                        ACCESS  read-write
                        STATUS  mandatory
                        DESCRIPTION
                            "The IP address of the gateway being restricted."
                        ::= { rRipSrcEntry 2 }

                rSrcRstState  OBJECT-TYPE
                        SYNTAX  INTEGER {
                            active(1),
                            inactive(2)
                        }
                        ACCESS  read-write
                        STATUS  mandatory
                        DESCRIPTION
                            "The state of this entry.  To remove an entry
                            from the table, simply set this field to
                            INACTIVE."
                        ::= { rRipSrcEntry 3 }

                rIpRtEvTable  OBJECT-TYPE
                        SYNTAX  SEQUENCE OF RIpRtEvEntry
                        ACCESS  not-accessible
                        STATUS  mandatory
                        DESCRIPTION
                            "Table containing the status of each routing
                            event supported in the brouter."
                        ::= { propIpRun 14 }

                rIpRtEvEntry  OBJECT-TYPE
                        SYNTAX  RIpRtEvEntry
                        ACCESS  not-accessible
                        STATUS  mandatory
                        DESCRIPTION
                            "The entry containing the status of a specific
                            routing event."
                        INDEX   { rRtEvTskId, rRtEvCode }
                        ::= { rIpRtEvTable 1 }

                RIpRtEvEntry ::= SEQUENCE {
                        rRtEvTskId
                            INTEGER,
                        rRtEvCode
                            INTEGER,
                        rRtEvStatus
                            INTEGER
                }

                rRtEvTskId  OBJECT-TYPE
                        SYNTAX  INTEGER
                        ACCESS  read-only
                        STATUS  mandatory
                        DESCRIPTION
                            "The task id of the reporting entity."
                        ::= { rIpRtEvEntry 1 }

                rRtEvCode  OBJECT-TYPE
                        SYNTAX  INTEGER
                        ACCESS  read-only
                        STATUS  mandatory
                        DESCRIPTION
                            "The event id assigned to the specific routing
                            event."
                        ::= { rIpRtEvEntry 2 }

                rRtEvStatus  OBJECT-TYPE
                        SYNTAX  INTEGER {
                            on(1),
                            off(2)
                        }
                        ACCESS  read-write
                        STATUS  mandatory
                        DESCRIPTION
                            "Status of this routing event."
                        ::= { rIpRtEvEntry 3 }

                rRipTotRef  OBJECT-TYPE
                        SYNTAX  Counter
                        ACCESS  read-only
                        STATUS  mandatory
                        DESCRIPTION
                            "Total number of RIP lookups."
                        ::= { rIpRipStats 1 }

                rRipTotFnd  OBJECT-TYPE
                        SYNTAX  Counter
                        ACCESS  read-only
                        STATUS  mandatory
                        DESCRIPTION
                            "Number of times when routing destination was
                            found."
                        ::= { rIpRipStats 2 }

                rRipUdpRcv  OBJECT-TYPE
                        SYNTAX  Counter
                        ACCESS  read-only
                        STATUS  mandatory
                        DESCRIPTION
                            "Number of received RIP responses."
                        ::= { rIpRipStats 3 }

                rRipUdpXmt  OBJECT-TYPE
                        SYNTAX  Counter
                        ACCESS  read-only
                        STATUS  mandatory
                        DESCRIPTION
                            "Number of transmitted RIP responses."
                        ::= { rIpRipStats 4 }

                rRipUdpTrig  OBJECT-TYPE
                        SYNTAX  Counter
                        ACCESS  read-only
                        STATUS  mandatory
                        DESCRIPTION
                            "Total number of triggered RIP updates."
                        ::= { rIpRipStats 5 }

                rRipReqRcv  OBJECT-TYPE
                        SYNTAX  Counter
                        ACCESS  read-only
                        STATUS  mandatory
                        DESCRIPTION
                            "Number of received RIP requests."
                        ::= { rIpRipStats 6 }

                rRipReqXmt  OBJECT-TYPE
                        SYNTAX  Counter
                        ACCESS  read-only
                        STATUS  mandatory
                        DESCRIPTION
                            "Number of transmitted RIP requests."
                        ::= { rIpRipStats 7 }

                rRipInvRcv  OBJECT-TYPE
                        SYNTAX  Counter
                        ACCESS  read-only
                        STATUS  mandatory
                        DESCRIPTION
                            "Number of invalid RIP messages received."
                        ::= { rIpRipStats 8 }

                rArpInMsgs  OBJECT-TYPE
                        SYNTAX  Counter
                        ACCESS  read-only
                        STATUS  mandatory
                        DESCRIPTION
                            "The total number of ARP messages which the
                            entity received.  Note that this counter includes
                            all those counted by 'Inbound Errors'."
                        ::= { rIpArpStats 1 }

                rArpInErr  OBJECT-TYPE
                        SYNTAX  Counter
                        ACCESS  read-only
                        STATUS  mandatory
                        DESCRIPTION
                            "The number of ARP messages which the entity
                            received but determined as having errors (bad
                            ARP opcode, bad protocol, bad hardware type)."
                        ::= { rIpArpStats 2 }

                rArpInIll  OBJECT-TYPE
                        SYNTAX  Counter
                        ACCESS  read-only
                        STATUS  mandatory
                        DESCRIPTION
                            "The number of illegal ARP messages received:
                            Target Protocol Address (tpa) and Sender Protocol
                            Address (spa) belongs to different networks, tpa,
                            spa are illegal, tpa is broadcast etc."
                        ::= { rIpArpStats 3 }

                rArpInOpCd  OBJECT-TYPE
                        SYNTAX  Counter
                        ACCESS  read-only
                        STATUS  mandatory
                        DESCRIPTION
                            "The number of ARP messages received, with bad
                            opcode.  Neither request nor reply."
                        ::= { rIpArpStats 4 }

                rArpInReq  OBJECT-TYPE
                        SYNTAX  Counter
                        ACCESS  read-only
                        STATUS  mandatory
                        DESCRIPTION
                            "The number of ARP Request messages received."
                        ::= { rIpArpStats 5 }

                rArpInRep  OBJECT-TYPE
                        SYNTAX  Counter
                        ACCESS  read-only
                        STATUS  mandatory
                        DESCRIPTION
                            "The number of ARP Reply messages received."
                        ::= { rIpArpStats 6 }

                rArpInNotMe  OBJECT-TYPE
                        SYNTAX  Counter
                        ACCESS  read-only
                        STATUS  mandatory
                        DESCRIPTION
                            "The number of ARP Requests 'Not For Me messages'
                            received."
                        ::= { rIpArpStats 7 }

                rArpOutMsgs  OBJECT-TYPE
                        SYNTAX  Counter
                        ACCESS  read-only
                        STATUS  mandatory
                        DESCRIPTION
                            "The total number of ARP messages which this
                            entity attempted to send.  Note that this counter
                            includes all those counted by 'Outbound Errors'."
                        ::= { rIpArpStats 8 }

                rArpOutErr  OBJECT-TYPE
                        SYNTAX  Counter
                        ACCESS  read-only
                        STATUS  mandatory
                        DESCRIPTION
                            "The number of ARP messages which this entity did
                            not send due to problems discovered within ARP
                            such as a lack of buffers.  This value should not
                            include errors discovered outside the ARP layer
                            such as the inability of the data link layer to
                            send the message."
                        ::= { rIpArpStats 9 }

                rArpOutReq  OBJECT-TYPE
                        SYNTAX  Counter
                        ACCESS  read-only
                        STATUS  mandatory
                        DESCRIPTION
                            "The number of ARP Request messages sent."
                        ::= { rIpArpStats 10 }

                rArpOutRep  OBJECT-TYPE
                        SYNTAX  Counter
                        ACCESS  read-only
                        STATUS  mandatory
                        DESCRIPTION
                            "The number of ARP Reply messages sent."
                        ::= { rIpArpStats 11 }

                rArpResReq  OBJECT-TYPE
                        SYNTAX  Counter
                        ACCESS  read-only
                        STATUS  mandatory
                        DESCRIPTION
                            "The number of resolve requests to this entity
                            made by an upper level protocol."
                        ::= { rIpArpStats 12 }

                rPArpInRep  OBJECT-TYPE
                        SYNTAX  Counter
                        ACCESS  read-only
                        STATUS  mandatory
                        DESCRIPTION
                            "The number of ARP replies recognized as a reply
                            to a previous arp-request issued by proxy arp."
                        ::= { rIpPArp 1 }

                rPArpInReqSrch  OBJECT-TYPE
                        SYNTAX  Counter
                        ACCESS  read-only
                        STATUS  mandatory
                        DESCRIPTION
                            "The number of ARP requests recognized as 'naive
                            request' that were put on the Proxy Search List."
                        ::= { rIpPArp 2 }

                rPArpOutReq  OBJECT-TYPE
                        SYNTAX  Counter
                        ACCESS  read-only
                        STATUS  mandatory
                        DESCRIPTION
                            "The number of ARP request sent on behalf of
                            another host by proxy arp."
                        ::= { rIpPArp 3 }

                rPArpOutRep  OBJECT-TYPE
                        SYNTAX  Counter
                        ACCESS  read-only
                        STATUS  mandatory
                        DESCRIPTION
                            "The number of ARP replies sent by proxy arp,
                            back to a naive host, as a result of passive
                            proxy (the sought host was in the table)."
                        ::= { rIpPArp 4 }

                rPArpOutActRep  OBJECT-TYPE
                        SYNTAX  Counter
                        ACCESS  read-only
                        STATUS  mandatory
                        DESCRIPTION
                            "The number of ARP replies sent by proxy arp,
                            back to a naive host, as the result of an
                            active proxy search."
                        ::= { rIpPArp 5 }

                rPArpToutSrch  OBJECT-TYPE
                        SYNTAX  Counter
                        ACCESS  read-only
                        STATUS  mandatory
                        DESCRIPTION
                            "The number of entries that were timed out from
                            proxy arp search list (these entries got no reply
                            during the proxy life-time interval)."
                        ::= { rIpPArp 6 }

                rPArpNaiveReq  OBJECT-TYPE
                        SYNTAX  Counter
                        ACCESS  read-only
                        STATUS  mandatory
                        DESCRIPTION
                            "The number of ARP requests recognized as 'naive
                            request' and to be handled by proxy arp mechanism.
                            (A 'naive host' is a host with no subnetting
                            knowledge.)"
                        ::= { rIpPArp 7 }


                -- permanent proprietary IP objects

                pIpMaskTable  OBJECT-TYPE
                        SYNTAX  SEQUENCE OF PIpMaskEntry
                        ACCESS  not-accessible
                        STATUS  mandatory
                        DESCRIPTION
                            "The permanent list of address masks used by this
                            router to initialize it's rIpMaskTable."
                        ::= { propIpPerm 1 }

                pIpMaskEntry  OBJECT-TYPE
                        SYNTAX  PIpMaskEntry
                        ACCESS  not-accessible
                        STATUS  mandatory
                        DESCRIPTION
                            "Items contained in the permanent Address Mask
                            Table."
                        INDEX   { pMaskNet }
                        ::= { pIpMaskTable 1 }

                PIpMaskEntry ::= SEQUENCE {
                        pMaskNet
                            NetworkAddress,
                        pMask
                            NetworkAddress,
                        pMaskState
                            INTEGER
                }

                pMaskNet  OBJECT-TYPE
                        SYNTAX  NetworkAddress
                        ACCESS  read-write
                        STATUS  mandatory
                        DESCRIPTION
                            "The IP network this mask is defined for."
                        ::= { pIpMaskEntry 1 }

                pMask  OBJECT-TYPE
                        SYNTAX  NetworkAddress
                        ACCESS  read-write
                        STATUS  mandatory
                        DESCRIPTION
                            "The subnet mask associated with the IP address
                            of this entry.  The value of the mask is an IP
                            address with all the network bits set to 1 and
                            all the hosts bits set to 0."
                        ::= { pIpMaskEntry 2 }

                pMaskState  OBJECT-TYPE
                        SYNTAX  INTEGER {
                            active(1),
                            inactive(2)
                        }
                        ACCESS  read-write
                        STATUS  mandatory
                        DESCRIPTION
                            "The state of this entry.  To remove an entry
                            from the table, simply set this field to
                            INACTIVE."
                        ::= { pIpMaskEntry 3 }

                pIpOurAddrTable  OBJECT-TYPE
                        SYNTAX  SEQUENCE OF PIpOurAddrEntry
                        ACCESS  not-accessible
                        STATUS  mandatory
                        DESCRIPTION
                            "The permanent list of parameters used by this
                            router to initialize its ipAddrTable as well as
                            the extention table rIpOurAddrTable."
                        ::= { propIpPerm 2 }

                pIpOurAddrEntry  OBJECT-TYPE
                        SYNTAX  PIpOurAddrEntry
                        ACCESS  not-accessible
                        STATUS  mandatory
                        DESCRIPTION
                            "Objects required for a single entry in the
                            pIpOurAddrTable.  To add a pIpOurAddrEntry
                            to the pIpOurAddrTable, the pAddrState is the
                            validating item.  Therefore, pAddrState must
                            be the last item in the message when adding an
                            entry.  To add to the pIpOurAddrTable the agent
                            requires all 7 items listed below. There are 3
                            default values provided by the agent for this
                            entry: pAddrBcAddr defaults to -1, pAddrDbcast
                            defaults to 'no directed broadcast'  and
                            pAddrRipMetric defaults to 1. To remove an
                            pIpOurAddrEntry, the pAddrState should be set
                            to INACTIVE."
                        INDEX   { pAddrOurAddr }
                        ::= { pIpOurAddrTable 1 }

                PIpOurAddrEntry ::= SEQUENCE {
                        pAddrOurAddr
                            NetworkAddress,
                        pAddrIfIndex
                            INTEGER,
                        pAddrBcAddr
                            INTEGER,
                        pAddrDbcast
                            INTEGER,
                        pAddrRipMetric 
                            INTEGER,
                        pAddrState
                            INTEGER,
                        pAddrRipState
                            INTEGER
                }

                pAddrOurAddr  OBJECT-TYPE
                        SYNTAX  NetworkAddress
                        ACCESS  read-write
                        STATUS  mandatory
                        DESCRIPTION
                            "The IP Address being defined in this entry."
                        ::= { pIpOurAddrEntry 1 }

                pAddrIfIndex  OBJECT-TYPE
                        SYNTAX  INTEGER
                        ACCESS  read-write
                        STATUS  mandatory
                        DESCRIPTION
                            "The interface this IP Address being defined on."
                        ::= { pIpOurAddrEntry 2 }

                pAddrBcAddr  OBJECT-TYPE
                        SYNTAX  INTEGER
                        ACCESS  read-write
                        STATUS  mandatory
                        DESCRIPTION
                            "As defined in rfc1156.  'The value of the
                            least-significant bit in the IP broadcast address
                            used for sending datagrams on the (logical)
                            interface associated with the IP address of this
                            entry.  For example, when the Internet standard
                            all-ones broadcast address is used, the value
                            will be 1.'  The default value for this item is
                            all-ones."
                        ::= { pIpOurAddrEntry 3 }

                pAddrDbcast  OBJECT-TYPE
                        SYNTAX  INTEGER
                        ACCESS  read-write
                        STATUS  mandatory
                        DESCRIPTION
                            "Allows the user to set the directed broadcast
                            parameter of an IP network. The default is 'no
                            directed broadcast'."
                        ::= { pIpOurAddrEntry 4 }

                pAddrRipMetric  OBJECT-TYPE
                        SYNTAX  INTEGER
                        ACCESS  read-write
                        STATUS  mandatory
                        DESCRIPTION
                            "A number from 1 to 15 used to calculate the
                            metrics to given destinations, RIP will add
                            this metric to metrics received from other
                            RIP gateways on this (sub)network.  In effect,
                            this can be used to prioritize the (sub)network
                            used for a destination reachable via more than
                            one Brouter (sub)network.  Default value is 1."
                        ::= { pIpOurAddrEntry 5 }

                pAddrState  OBJECT-TYPE
                        SYNTAX  INTEGER {
                            active(1),
                            inactive(2)
                        }
                        ACCESS  read-write
                        STATUS  mandatory
                        DESCRIPTION
                            "The state of this entry.  To remove an entry
                            from the table, simply set this field to
                            INACTIVE."
                        ::= { pIpOurAddrEntry 6 }

                pAddrRipState  OBJECT-TYPE
                        SYNTAX  INTEGER {
                            on(1),
                            off(2),
                            quiet(3)
                        }
                        ACCESS  read-write
                        STATUS  mandatory
                        DESCRIPTION
                            "The state of RIP for this entry."
                        ::= { pIpOurAddrEntry 7 }

                pIpIfTable  OBJECT-TYPE
                        SYNTAX  SEQUENCE OF PIpIfEntry
                        ACCESS  not-accessible
                        STATUS  mandatory
                        DESCRIPTION
                            "The permanent list of parameters used by this
                            router to initialize its ifTable as well as the
                            extention table rIpIfTable."
                        ::= { propIpPerm 3 }

                pIpIfEntry  OBJECT-TYPE
                        SYNTAX  PIpIfEntry
                        ACCESS  not-accessible
                        STATUS  mandatory
                        DESCRIPTION
                            "Objects required for a single entry in the
                            pIpIfEntry."
                        INDEX   { pIfIndex }
                        ::= { pIpIfTable 1 }

                PIpIfEntry ::= SEQUENCE {
                        pIfIndex
                            INTEGER,
                        pIfType
                            INTEGER,
                        pIfMtu
                            INTEGER,
                        pIfArpStat
                            INTEGER,
                        pIfPArpStat
                            INTEGER,
                        pIfAdminStat
                            INTEGER,
                        pIfBcMask
                            INTEGER
                }

                pIfIndex  OBJECT-TYPE
                        SYNTAX  INTEGER
                        ACCESS  read-only
                        STATUS  mandatory
                        DESCRIPTION
                            "Interface ID that uniquely identifies this
                            interface among all other interfaces in this
                            brouter."
                        ::= { pIpIfEntry 1 }

                pIfType  OBJECT-TYPE
                        SYNTAX  INTEGER
                        ACCESS  read-write
                        STATUS  mandatory
                        DESCRIPTION
                            "Specifies the type of Physical and Data-Link
                            layers.  See rfc1156 for protocol codes."
                        ::= { pIpIfEntry 2 }

                pIfMtu  OBJECT-TYPE
                        SYNTAX  INTEGER
                        ACCESS  read-write
                        STATUS  mandatory
                        DESCRIPTION
                            "Maximum Transmission Unit size that is supported
                            on this network.  The largest value acceptable for
                            Ethernet is 1500 and for FDDI is 4500."
                        ::= { pIpIfEntry 3 }

                pIfArpStat  OBJECT-TYPE
                        SYNTAX  INTEGER {
                            on(1),
                            off(2)
                        }
                        ACCESS  read-write
                        STATUS  mandatory
                        DESCRIPTION
                            "Allows the user to turn ARP on and off for the
                            interface."
                        ::= { pIpIfEntry 4 }

                pIfPArpStat  OBJECT-TYPE
                        SYNTAX  INTEGER {
                            on(1),
                            off(2)
                        }
                        ACCESS  read-write
                        STATUS  mandatory
                        DESCRIPTION
                            "Allows the user to turn proxy ARP on and off
                            for the interface."
                        ::= { pIpIfEntry 5 }

                pIfAdminStat  OBJECT-TYPE
                        SYNTAX  INTEGER
                        ACCESS  read-write
                        STATUS  mandatory
                        DESCRIPTION
                            "Specifies the desired initial state of the
                            interface (i.e., should the interface be started
                            without direction from the operator).  See rfc1156
                            for state codes."
                        ::= { pIpIfEntry 6 }

                pIfBcMask  OBJECT-TYPE
                        SYNTAX  INTEGER {
                            on(1),
                            off(2)
                        }
                        ACCESS  read-write
                        STATUS  mandatory
                        DESCRIPTION
                            "When set to ON, the brouter will broadcast its
                            address mask on start  up.  When set to OFF, the
                            brouter will not broadcast its address mask on
                            start up."
                        ::= { pIpIfEntry 7 }

                pDftGw  OBJECT-TYPE
                        SYNTAX  NetworkAddress
                        ACCESS  read-write
                        STATUS  mandatory
                        DESCRIPTION
                            "The IP address of the permanent default gateway."
                        ::= { propIpPerm 4 }

                pIpDefaults  OBJECT-TYPE
                        SYNTAX  INTEGER {
                            reset-defaults(1)
                        }
                        ACCESS  read-write
                        STATUS  mandatory
                        DESCRIPTION
                            "When this object is set to 1, the side effect
                            will be to cause the unit to reset all the objects
                            defined under the subtree propIpPerm to their
                            default values.  Reading this object has no
                            meaning.  The integer value 1 will be returned to
                            a get or get-next request."
                        ::= { propIpPerm 5 }


                -- proprietary fddi vars

                fddiSmtChge  OBJECT-TYPE
                        SYNTAX  INTEGER {
                            true(1),
                            false(2)
                        }
                        ACCESS  read-only
                        STATUS  mandatory
                        DESCRIPTION
                            "At system startup, this object is set to FALSE.
                            The SNMP agent then sets this flag to TRUE when
                            any SMT object in the system is set by the
                            manager."
                        ::= { propFddi 1 }

                fddiMacChge   OBJECT-TYPE
                        SYNTAX  INTEGER {
                            true(1),
                            false(2)
                        }
                        ACCESS  read-only
                        STATUS  mandatory
                        DESCRIPTION
                            "At system startup, this object is set to FALSE.
                            The SNMP agent then sets this flag to TRUE when
                            any MAC object in the system is set by the
                            manager."
                        ::= { propFddi 2 }

                fddiPortChge  OBJECT-TYPE
                        SYNTAX  INTEGER {
                            true(1),
                            false(2)
                        }
                        ACCESS  read-only
                        STATUS  mandatory
                        DESCRIPTION
                            "At system startup, this object is set to FALSE.
                            The SNMP agent then sets this flag to TRUE when
                            any PORT object in the system is set by the
                            manager."
                        ::= { propFddi 3 }

                fddiAttachChge   OBJECT-TYPE
                        SYNTAX  INTEGER {
                            true(1),
                            false(2)
                        }
                        ACCESS  read-only
                        STATUS  mandatory
                        DESCRIPTION
                            "At system startup, this object is set to FALSE.
                            The SNMP agent then sets this flag to TRUE when
                            any ATTACHMENT object in the system is set by the
                            manager."
                        ::= { propFddi 4 }
        END
