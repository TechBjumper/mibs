-- ****************************************************************************
--
--                     Dialogic Hardware Information
--         Management Information Base for SNMP Network Management
--
--
--      Copyright 1997, Dialogic Corporation.
--      All Rights Reserved.
--
--      The information in this document is subject to change without notice.
--
--      The Dialogic Enterprise number is 3028.
--      The ASN.1 prefix to, and including the Dialogic Enterprise is:
--           1.3.6.1.4.1.3028
--
--	Mib Rev Major = 1
-- 	Mib Rev Minor = 2
--
-- ****************************************************************************

DLGHWINF-MIB DEFINITIONS ::= BEGIN

    IMPORTS
        Counter                 FROM RFC1155-SMI
        OBJECT-TYPE             FROM RFC1155-SMI
        TRAP-TYPE               FROM RFC1155-SMI
        DisplayString           FROM RFC1213-MIB
        sysName                 FROM RFC1213-MIB
        dialogic                FROM DLGC-GLOBAL-REG
        dlgHardwareInfo         FROM DLGC-GLOBAL-REG;


    dlgHiMibRev       OBJECT IDENTIFIER ::= { dlgHardwareInfo 1 }
    dlgHiComponent    OBJECT IDENTIFIER ::= { dlgHardwareInfo 2 }

    dlgHiInterface    OBJECT IDENTIFIER ::= { dlgHiComponent 1 }
    dlgHiIdent        OBJECT IDENTIFIER ::= { dlgHiComponent 2 }

    dlgHiOsCommon     OBJECT IDENTIFIER ::= { dlgHiInterface 1 }

-- ****************************************************************************
-- HardwareInfo MIB Revision
-- =========================
--
-- The dialogic enterprise             (1.3.6.1.4.1.3028)
--       dlgHardware Group             (1.3.6.1.4.1.3028.1)
--        dlgHardwareInfo Group        (1.3.6.1.4.1.3028.1.1)
--         dlgHiMibRev Group           (1.3.6.1.4.1.3028.1.1.1)
--
--
--     An Agent implementing this MIB will return a mibRevMajor
-- 	 of one (1) and a mibRevMinor of two (2).
--
--
-- ****************************************************************************

    dlgHiMibRevMajor OBJECT-TYPE
       SYNTAX  INTEGER (1..65535)
       ACCESS  read-only
       STATUS  mandatory
       DESCRIPTION
           "The Major Revision level.

            A change in the major revision level represents a major change
            in the architecture of the MIB.  A change in the major revision
            level may indicate a significant change in the information
            supported and/or the meaning of the supported information,
            correct interpretation of data may require a MIB document with
            the same major revision level."
       ::= { dlgHiMibRev 1 }

       dlgHiMibRevMinor OBJECT-TYPE
       SYNTAX  INTEGER (0..65535)
       ACCESS  read-only
       STATUS  mandatory
       DESCRIPTION
           "The Minor Revision level.

            A change in the minor revision level may represent some minor
            additional support. no changes to any pre-existing information
            has occurred."
       ::= { dlgHiMibRev 2 }

       dlgHiMibCondition OBJECT-TYPE
           SYNTAX  INTEGER {
               other(1),
               ok(2),           -- default
               degraded(3),
               failed(4)
               }
           ACCESS  read-only
           STATUS  mandatory
           DESCRIPTION
               "The overall condition.

                This object represents the overall status of the Dialogic
                Hardware Information system represented by this MIB.

			Other - The status of the MIB is Unknown
			OK 	- The status of the MIB is OK
			Degraded - Some statuses in the MIB are not OK
			Failed   - Most statuses in the MIB are not OK"
           ::= { dlgHiMibRev 3 }

-- ****************************************************************************
--    HardwareInfo OS Common
--    ======================
--
-- The dialogic enterprise             (1.3.6.1.4.1.3028)
--       dlgHardware Group             (1.3.6.1.4.1.3028.1)
--        dlgHardwareInfo Group        (1.3.6.1.4.1.3028.1.1)
--         dlgHiComponent Group        (1.3.6.1.4.1.3028.1.1.2)
--          dlgHiInterface Group       (1.3.6.1.4.1.3028.1.1.2.1)
--           dlgHiOsCommon Group       (1.3.6.1.4.1.3028.1.1.2.1.1)
--
--
-- ****************************************************************************

    dlgHiOsCommonPollFreq OBJECT-TYPE
        SYNTAX  INTEGER (0..65535)
        ACCESS  read-write
        STATUS  mandatory
        DESCRIPTION
            "The Agent's polling frequency in seconds.

             The frequency, in seconds, at which the Agent updates the
             operational status of the individual devices within the
             device table. A value of zero indicates that the Agent 
             will not check the status of the indivdual devices.

             The default value is 60 (60 seconds). In this case the Agent
             checks each individual device every 60 seconds to make sure
             it is still operational. Should a device fail, it's status
             will set to failed and a trap is sent to the management
             application.

             Setting the poll frequency to a value too low can impact 
             system performance."
           ::= { dlgHiOsCommon 1 }

    dlgHiOsCommonNumberOfModules OBJECT-TYPE
        SYNTAX  INTEGER
        ACCESS  read-only
        STATUS  mandatory
        DESCRIPTION
            "The number of modules in the OS Common Module table."
           ::= { dlgHiOsCommon 2 }
 
-- ****************************************************************************

    dlgHiOsLogEnable OBJECT-TYPE
	SYNTAX  INTEGER (0..1) 
	ACCESS  read-write
	STATUS	mandatory
	DESCRIPTION
	   "The Agent's log enable bit 
		0 - disabled Setting this variable to this value will disable the trap logging
		1 - enabled  Setting this variable to this value will enable the trap logging "
	    ::= { dlgHiOsCommon 4 }

    dlgHiOsTestTrapEnable OBJECT-TYPE
	SYNTAX  INTEGER {
        	enabled(1)          
		}
	ACCESS  read-write
	STATUS	mandatory
	DESCRIPTION
	   " Every time this bit is set, test trap is sent from the agent "
   	    ::= { dlgHiOsCommon 5 }

-- ****************************************************************************
-- ****************************************************************************
     
      dlgHiIdentSystemServicesNameForTrap OBJECT-TYPE
        SYNTAX  DisplayString (SIZE (0..256))
        ACCESS  read-only
        STATUS  mandatory
	DESCRIPTION ""
        ::= { dlgHiOsCommon 6 }
    
      dlgHiIdentSystemServicesStatusForTrap OBJECT-TYPE
       SYNTAX  INTEGER {
           other(1),
           started(2),
           stop-pending(3),
           stopped(4),
           start-pending(5)
           }
       ACCESS  read-only
       STATUS  mandatory
	DESCRIPTION ""
       ::= { dlgHiOsCommon 7 }
	
     dlgHiIdentIndexForTrap OBJECT-TYPE
        SYNTAX  INTEGER (0..65535)
        ACCESS  read-only
        STATUS  mandatory
        DESCRIPTION
            "An index that uniquely specifies each device. This value
             is not necessarily contiguous"
        ::= { dlgHiOsCommon 8 }

     dlgHiIdentModelForTrap OBJECT-TYPE
        SYNTAX  DisplayString (SIZE (0..32))
        ACCESS  read-only
        STATUS  mandatory
        DESCRIPTION
           "Dialogic board Model.

            This is the Dialogic board's model name and can be used for
            identification purposes."
        ::= { dlgHiOsCommon 9 }

      dlgHiIdentOperStatusForTrap OBJECT-TYPE
        SYNTAX  INTEGER {
            other(1),
            ok(2),
            degraded(3),
            failed(4)
            }
        ACCESS  read-only
        STATUS  mandatory
        DESCRIPTION
           "Dialogic board Operational Status.

            This is the overall condition of the Dialogic board.
            The following values are defined

            other(1)
              The board does not support board condition monitoring.

            ok(2)
              The board is operating normally.  No user action is required.

            degraded(3)
              The board is partially failed.  The board may need to be reset.

            failed(4)
              The board has failed.  The board should be reset

                NOTE: In the implmentation of this version of the MIB (Major 1, Minor 2), SpanCards do not
                        support the degraded state.
                "
        ::= { dlgHiOsCommon 10 }

	dlgHiIdentAdminStatusForTrap OBJECT-TYPE
        SYNTAX  INTEGER {
            other(1),
            started(2),
            stopped(3),
            disabled(4),
            diagnose(5),
            start-pending(6),
            stop-pending(7)
            }
        ACCESS  read-only
        STATUS  mandatory
        DESCRIPTION
           "Dialogic board Admin Status.

            This is the Administrative Status of the Dialogic board.
            The following values are defined

            other(1)
              The board's admin status in unavailable.

            started(2)
              The board has been started.

            stopped(3)
              The board is stopped.

            disabled(4)
              The board is disabled.

            diagnose(5)
             The board is being diagnosed.

            start-pending(6)
              The board is in the process of starting.

            stop-pending(7)
              The board is in the process of stopping.
                "

        ::= {dlgHiOsCommon  11 }

	dlgHiIdentSerNumForTrap OBJECT-TYPE
        SYNTAX  DisplayString (SIZE (0..12))
        ACCESS  read-only
        STATUS  mandatory
        DESCRIPTION
           "Dialogic board Serial Number.

            This is the Dialogic board serial number and can be used for
            identification purposes. On many boards the serial number
            appears on the back of the board."
        ::= { dlgHiOsCommon 12 }
 	
	dlgHiIdentErrorMessageForTrap OBJECT-TYPE
        SYNTAX  DisplayString (SIZE (0..96))
        ACCESS  read-only
        STATUS  mandatory
        DESCRIPTION
           "Dialogic board Error Message.

            This value represents the error message associated with
            a failing Dialogic board."
        ::= { dlgHiOsCommon  13 }

-- ****************************************************************************
--    HardwareInfo OS Common Module
--    =============================
--
-- The dialogic enterprise              (1.3.6.1.4.1.3028)
--      dlgHardware Group               (1.3.6.1.4.1.3028.1)
--        dlgHardwareInfo Group         (1.3.6.1.4.1.3028.1.1)
--         dlgHiComponent Group         (1.3.6.1.4.1.3028.1.1.2)
--          dlgHiInterface Group        (1.3.6.1.4.1.3028.1.1.2.1)
--           dlgHiOsCommon Group        (1.3.6.1.4.1.3028.1.1.2.1.1)
--            dlgHiOsCommonModuleTable  (1.3.6.1.4.1.3028.1.1.2.1.1.3)
--
-- The OSCommonModuleTable contains information about the software modules
-- which interface to the Dialogic boards in the system 
--
-- ****************************************************************************

    dlgHiOsCommonModuleTable OBJECT-TYPE
	SYNTAX	SEQUENCE OF DlgHiOsCommonModuleEntry
	ACCESS	not-accessible
	STATUS	mandatory
        DESCRIPTION
            "A table of software modules that provide an interface to the devicethis MIB describes."
        ::= { dlgHiOsCommon 3 }

    dlgHiOsCommonModuleEntry OBJECT-TYPE
        SYNTAX  DlgHiOsCommonModuleEntry
        ACCESS  not-accessible
        STATUS  mandatory
        DESCRIPTION
            "A description of a software module that provides an interface to the device this MIB describes."
        INDEX   { dlgHiOsCommonModuleIndex }
        ::= { dlgHiOsCommonModuleTable 1 }

        DlgHiOsCommonModuleEntry ::= SEQUENCE {
            dlgHiOsCommonModuleIndex       INTEGER,
            dlgHiOsCommonModuleName        DisplayString,
            dlgHiOsCommonModuleVersion     DisplayString,
            dlgHiOsCommonModuleDate        OCTET STRING,
            dlgHiOsCommonModulePurpose     DisplayString
        }

    dlgHiOsCommonModuleIndex OBJECT-TYPE
        SYNTAX  INTEGER (0..255)
        ACCESS  read-only
        STATUS  mandatory
        DESCRIPTION
            "A unique index for this module description."
        ::= { dlgHiOsCommonModuleEntry 1 }

    dlgHiOsCommonModuleName OBJECT-TYPE
        SYNTAX  DisplayString (SIZE (0..255))
        ACCESS  read-only
        STATUS  mandatory
        DESCRIPTION
            "The module name."
        ::= { dlgHiOsCommonModuleEntry 2 }

    dlgHiOsCommonModuleVersion OBJECT-TYPE
        SYNTAX  DisplayString (SIZE (0..5))
        ACCESS  read-only
        STATUS  mandatory
        DESCRIPTION
            "Version of the module."
        ::= { dlgHiOsCommonModuleEntry 3 }

    dlgHiOsCommonModuleDate OBJECT-TYPE
        SYNTAX  OCTET STRING (SIZE (7))
        ACCESS  read-only
        STATUS  mandatory
        DESCRIPTION
            "The module date.

             field  octets  contents                  range
             =====  ======  =======                   =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
        ::= { dlgHiOsCommonModuleEntry 4 }

    dlgHiOsCommonModulePurpose OBJECT-TYPE
        SYNTAX  DisplayString (SIZE (0..255))
        ACCESS  read-only
        STATUS  mandatory
        DESCRIPTION
            "The purpose of the module described in this entry."
        ::= { dlgHiOsCommonModuleEntry 5 }

-- ****************************************************************************
--    HardwareInfo Ident Group
--    ========================
--
-- The dialogic enterprise              (1.3.6.1.4.1.3028)
--      dlgHardware Group               (1.3.6.1.4.1.3028.1)
--        dlgHardwareInfo Group         (1.3.6.1.4.1.3028.1.1)
--         dlgHiComponent Group         (1.3.6.1.4.1.3028.1.1.2)
--          dlgHiIdent Group            (1.3.6.1.4.1.3028.1.1.2.2)
--
--
--  The Ident group contains basic indentification information about the
--  Dialogic boards in the system.
--
-- ****************************************************************************

    dlgHiIdentNumberOfDevices OBJECT-TYPE
       SYNTAX  INTEGER
       ACCESS  read-only
       STATUS  mandatory
       DESCRIPTION
           "Number of Dialogic device in the system.

            A device may be a physical board, a channel on a board 
            or an embedded component on a board"
       ::= { dlgHiIdent 2 }

    dlgHiIdentServiceStatus OBJECT-TYPE
       SYNTAX  INTEGER {
           other(1),
           started(2),
           stop-pending(3),
           stopped(4),
           start-pending(5)
           }
       ACCESS  read-write
       STATUS  mandatory
       DESCRIPTION
           "Dialogic Service Status

            This is the overall status of the Dialogic system service.
	    The following values are defined:

            other(1)
              The service status is unknown.

            started(2)
              The service status is running - boards are started. Setting the
              variable to this value will fail.

            stop-pending(3)
              The service is in the act of stopping. Setting the
              variable to this value when the current condition is started(2)
              will cause the service to begin stopping, otherwise it will
              fail.

            stopped(4)
              The service status is stopped - boards are stopped. Setting the
              variable to this value will fail.

            start-pending(5)
              The service is in the act of starting. Setting the
              variable to this value when the current condition is stopped(4)
              will cause the service to begin starting, othewise it will
              fail."
       ::= { dlgHiIdent 3 }

    dlgHiIdentServiceChangeDate OBJECT-TYPE
        SYNTAX  OCTET STRING (SIZE (7))
        ACCESS  read-only
        STATUS  mandatory
        DESCRIPTION
            "The date and time the service was last started or stopped.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
       ::= { dlgHiIdent 4 }

   dlgHiIdentTrapMask OBJECT-TYPE
       SYNTAX  INTEGER 
       ACCESS  read-write
       STATUS  mandatory
       DESCRIPTION
           "Trap Enable mask.

            This variable is a bit mask which can  be used to enable or 
            disable certain enterprise specific traps.

            A '1' is used to enable the trap, a '0' disables it.

            Bit 0 - (1) enables Traps upon Dialogic Service Status
                        transitions to the Stopped or Started State.
            Bit 1 - (1) enables Traps when a specific board Condition
                        transitions to the Failed State.
            Bit 2 - (1) enables the dlgDsx1Alarm trap from the DS1 MIB. This trap
				indicates the beginning and end of a new alarm condition.
            Bit 3 - (1) enables the dlgDsx1SwEvtMskTrap trap from the DS1 MIB. This trap
				indicates that the DS1 Event Mask has been changed.
            Bit 4 - (1) enables the dlgIsdnDChanged trap from the ISDN MIB. This trap
				indicates the current operational status of LAPD of a particular D
				channel has changed 
            Bit 5 - (1) enables the dlgIsdnBChanged trap from the DS1 MIB. This trap
				indicates the current operational status of LAPD of a particular B
				channel has changed 
		"
       ::= { dlgHiIdent 5 }

--  this description info has been removed temporarily until Tapi 
--  is implemented in Boardwatch
--
--            Bit 6 - (1) enables the dlgTapiStartStopTrap trap from the TAPI MIB. This trap is
--		generated everytime the Tapi Service Provider starts or stops.

    dlgHiIdentSystemServicesTable OBJECT-TYPE
        SYNTAX  SEQUENCE OF DlgHiIdentSystemServicesEntry
        ACCESS  not-accessible
        STATUS  mandatory
        DESCRIPTION
           "Dialogic-Related system services table."
        ::= { dlgHiIdent 6 }

    dlgHiIdentSystemServicesEntry OBJECT-TYPE
        SYNTAX  DlgHiIdentSystemServicesEntry
        ACCESS  not-accessible
        STATUS  mandatory
        DESCRIPTION
           "Dialogic-Related system services table entry."
        INDEX   { dlgHiIdentSystemServicesIndex }
        ::= { dlgHiIdentSystemServicesTable 1 }

	DlgHiIdentSystemServicesEntry ::= SEQUENCE
        {
              dlgHiIdentSystemServicesIndex        INTEGER,
              dlgHiIdentSystemServicesName         DisplayString,
              dlgHiIdentSystemServicesScmName      DisplayString,
              dlgHiIdentSystemServicesStatus       INTEGER,
              dlgHiIdentSystemServicesChangeDate   OCTET STRING
        }

    dlgHiIdentSystemServicesIndex OBJECT-TYPE
        SYNTAX  INTEGER (0..65535)
        ACCESS  read-only
        STATUS  mandatory
        DESCRIPTION
            "An index that uniquely specifies each system service. This value
             is not necessarily contiguous"
        ::= { dlgHiIdentSystemServicesEntry 1 }

    dlgHiIdentSystemServicesName OBJECT-TYPE
        SYNTAX  DisplayString (SIZE (0..256))
        ACCESS  read-only
        STATUS  mandatory
        DESCRIPTION
           "System Service Name.

            This is the name of the system service used for Identification Purposes."
        ::= { dlgHiIdentSystemServicesEntry 2 }

    dlgHiIdentSystemServicesScmName OBJECT-TYPE
        SYNTAX  DisplayString (SIZE (0..256))
        ACCESS  read-only
        STATUS  mandatory
        DESCRIPTION
           "SCM System Service Name.

            This is the name of the system service that is given to SCM (Service Control Manager) and
		is used by SCM to identify the service."
        ::= { dlgHiIdentSystemServicesEntry 3 }

    dlgHiIdentSystemServicesStatus OBJECT-TYPE
       SYNTAX  INTEGER {
           other(1),
           started(2),
           stop-pending(3),
           stopped(4),
           start-pending(5)
           }
       ACCESS  read-write
       STATUS  mandatory
       DESCRIPTION
           "Service Status

            This is the overall status of the Dialogic system service.
	      The following values are defined:

            other(1)
              The service status is unknown.

            started(2)
              The service status is running - boards are started. Setting the
              variable to this value will fail.

            stop-pending(3)
              The service is in the act of stopping. Setting the
              variable to this value when the current condition is started(2)
              will cause the service to begin stopping, otherwise it will
              fail.

            stopped(4)
              The service status is stopped - boards are stopped. Setting the
              variable to this value will fail.

            start-pending(5)
              The service is in the act of starting. Setting the
              variable to this value when the current condition is stopped(4)
              will cause the service to begin starting, othewise it will
              fail."

       ::= { dlgHiIdentSystemServicesEntry 4 }

    dlgHiIdentSystemServicesChangeDate OBJECT-TYPE
        SYNTAX  OCTET STRING (SIZE (7))
        ACCESS  read-only
        STATUS  mandatory
        DESCRIPTION
            "The date and time the service was last started or stopped.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
       ::= { dlgHiIdentSystemServicesEntry 5 }


-- ****************************************************************************
--    HardwareInfo Ident Table
--    ========================
--
-- The dialogic enterprise              (1.3.6.1.4.1.3028)
--      dlgHardware Group               (1.3.6.1.4.1.3028.1)
--        dlgHardwareInfo Group         (1.3.6.1.4.1.3028.1.1)
--         dlgHiComponent Group         (1.3.6.1.4.1.3028.1.1.2)
--          dlgHiIdent Group            (1.3.6.1.4.1.3028.1.1.2.2)
--           dlgHiIdentTable            (1.3.6.1.4.1.3028.1.1.2.2.1)
--
--
--  The Ident table contains basic indentification information about the
--  Dialogic boards in the system.
--
-- ****************************************************************************

    dlgHiIdentTable OBJECT-TYPE
        SYNTAX  SEQUENCE OF DlgHiIdentEntry
        ACCESS  not-accessible
        STATUS  mandatory
        DESCRIPTION
           "Dialogic board Identification Table."
        ::= { dlgHiIdent 1 }

    dlgHiIdentEntry OBJECT-TYPE
        SYNTAX  DlgHiIdentEntry
        ACCESS  not-accessible
        STATUS  mandatory
        DESCRIPTION
           "Dialogic board Identification Table Entry."
        INDEX   { dlgHiIdentIndex }
        ::= { dlgHiIdentTable 1 }

        DlgHiIdentEntry ::= SEQUENCE
        {
              dlgHiIdentIndex          INTEGER,
              dlgHiIdentModel          DisplayString,
              dlgHiIdentType           INTEGER,
              dlgHiIdentFuncDescr      DisplayString,
              dlgHiIdentSerNum         DisplayString,
              dlgHiIdentFWName         DisplayString,
              dlgHiIdentFWVers         DisplayString,
              dlgHiIdentMemBaseAddr    INTEGER,
              dlgHiIdentIOBaseAddr     INTEGER,
              dlgHiIdentIrq            INTEGER,
              dlgHiIdentBoardID        INTEGER,
              dlgHiIdentPCISlotID      INTEGER,
              dlgHiIdentOperStatus     INTEGER,
              dlgHiIdentAdminStatus    INTEGER,
              dlgHiIdentErrorMessage   DisplayString,
              dlgHiIdentDeviceChangeDate  OCTET STRING,
              dlgHiIdentSpecific       OBJECT IDENTIFIER,
              dlgHiIdentPCIBusID	   INTEGER              
        }

    dlgHiIdentIndex OBJECT-TYPE
        SYNTAX  INTEGER (0..65535)
        ACCESS  read-only
        STATUS  mandatory
        DESCRIPTION
            "An index that uniquely specifies each device. This value
             is not necessarily contiguous"
        ::= { dlgHiIdentEntry 1 }


    dlgHiIdentModel OBJECT-TYPE
        SYNTAX  DisplayString (SIZE (0..32))
        ACCESS  read-only
        STATUS  mandatory
        DESCRIPTION
           "Dialogic board Model.

            This is the Dialogic board's model name and can be used for 
            identification purposes."
        ::= { dlgHiIdentEntry 2 }

    dlgHiIdentType OBJECT-TYPE
        SYNTAX  INTEGER {
                     other(1),         -- none of the following
                     release4span(2),  -- Proline/2V up to D/600SC-2E1 boards
                     dm3(3),           -- DM3 based 
                     gammaCP(4)        -- Gamma CP/x series
                }
        ACCESS  read-only
        STATUS  mandatory
        DESCRIPTION
           "Dialogic board type.

            This indicates which family of boards this device belongs to.

            other(1)         -- none of the following

            release4span(2)  -- Proline/2V up to D/600SC-2E1 boards

            dm3(3)           -- DM3 based board

            gammaCP(4)       -- Gamma CP/x series

            antares(5)       -- Antares based board"

        ::= { dlgHiIdentEntry 3 }

    dlgHiIdentFuncDescr OBJECT-TYPE
        SYNTAX  DisplayString (SIZE(0..128))
        ACCESS  read-only
        STATUS  mandatory
        DESCRIPTION
           "Dialogic board Function Description.
 
            This provides a description of the functionality provided by the
            Dialogic board. If the functional description of the board is 
            unavailable, then this string will be of length zero (0)."
        ::= { dlgHiIdentEntry 4 }


    dlgHiIdentSerNum OBJECT-TYPE
        SYNTAX  DisplayString (SIZE (0..12))
        ACCESS  read-only
        STATUS  mandatory
        DESCRIPTION
           "Dialogic board Serial Number.

            This is the Dialogic board serial number and can be used for 
            identification purposes. On many boards the serial number 
            appears on the back of the board."
        ::= { dlgHiIdentEntry 5 }

    dlgHiIdentFWName OBJECT-TYPE
        SYNTAX  DisplayString (SIZE (0..128))
        ACCESS  read-only
        STATUS  mandatory
        DESCRIPTION
           "Dialogic Firmware Name.

            This is the name of the firmware downloaded to this
            Dialogic board. If multiple different firmwares are loaded
            the filenames will be separated by a '\'. 
			
            If the firmware name is unavailable, then this strng will
            be of length zero (0)."
        ::= { dlgHiIdentEntry 6 }

    dlgHiIdentFWVers OBJECT-TYPE
        SYNTAX  DisplayString (SIZE (0..64))
        ACCESS  read-only
        STATUS  mandatory
        DESCRIPTION
           "Dialogic Firmware Version.

            This is the version of the firmware downloaded to this
            Dialogic board. If multiple different firmwares are loaded
            then each firmware version will be separated by a '\'.
			
            If the Dialogic firmware version is unavailable, 
            then this string will be of length zero (0)."
        ::= { dlgHiIdentEntry 7 }


    dlgHiIdentMemBaseAddr OBJECT-TYPE
        SYNTAX  INTEGER
        ACCESS  read-only
        STATUS  mandatory
        DESCRIPTION
            "Dialogic board Base Memory Address.

             This is the Memory address where the Dialogic board has been 
             installed on the system. If the Dialogic board does not use
             system memory then a value of zero (0) is returned"
        ::= { dlgHiIdentEntry 8 }

    dlgHiIdentIOBaseAddr OBJECT-TYPE
        SYNTAX  INTEGER
        ACCESS  read-only
        STATUS  mandatory
        DESCRIPTION
            "Dialogic board Base I/O Port Address.

             This is the I/O Port address where the Dialogic board has been 
             installed on the system. If the Dialogic board does not use
             a system I/O Port then a value of zero (0) is returned"
        ::= { dlgHiIdentEntry 9 }

    dlgHiIdentIrq OBJECT-TYPE
        SYNTAX  INTEGER
        ACCESS  read-only
        STATUS  mandatory
        DESCRIPTION
            "Dialogic board IRQ (Interrupt) Level.

             This is the Interrupt Level used by the Dialogic board  
             installed on the system. If the Dialogic board does not use
             an Interrupt then a value of zero (0) is returned"
        ::= { dlgHiIdentEntry 10 }

    dlgHiIdentBoardID OBJECT-TYPE
        SYNTAX  INTEGER
        ACCESS  read-only
        STATUS  mandatory
        DESCRIPTION
            "Dialogic board Board Locator ID.

             This is the Unique Board Locator ID set by the thumbwheel 
             on certain Dialogic boards. This may be used for identification 
             purposes. If the Dialogic board does not have a Unique Board 
             Locator ID setting then a value of negative one (-1) is 
             returned"
        ::= { dlgHiIdentEntry 11 }

    dlgHiIdentPCISlotID OBJECT-TYPE
        SYNTAX  INTEGER
        ACCESS  read-only
        STATUS  mandatory
        DESCRIPTION
            "Dialogic board PCI Slot ID.

             This is a PCI slot identifier where the Dialogic board is 
             installed. This may be used for identification purposes.
             If the Dialogic board is not a PCI board or if this info is 
             not available then a value of zero (0) is returned"
        ::= { dlgHiIdentEntry 12 }

    dlgHiIdentOperStatus OBJECT-TYPE
        SYNTAX  INTEGER {
            other(1),
            ok(2),
            degraded(3),
            failed(4)
            }
        ACCESS  read-only
        STATUS  mandatory
        DESCRIPTION
           "Dialogic board Operational Status.

            This is the overall condition of the Dialogic board.
	    The following values are defined

            other(1)
              The board does not support board condition monitoring.

            ok(2)
              The board is operating normally.  No user action is required.

            degraded(3)
              The board is partially failed.  The board may need to be reset.

            failed(4)
              The board has failed.  The board should be reset

		NOTE: In the implmentation of this version of the MIB (Major 1, Minor 2), SpanCards do not
			support the degraded state.
		"
        ::= { dlgHiIdentEntry 13 }

    dlgHiIdentAdminStatus OBJECT-TYPE
        SYNTAX  INTEGER {
            other(1),
            started(2),
            stopped(3),
            disabled(4),
            diagnose(5),
            start-pending(6),
            stop-pending(7)
            }
        ACCESS  read-write
        STATUS  mandatory
        DESCRIPTION
           "Dialogic board Admin Status.

            This is the Administrative Status of the Dialogic board.
	    The following values are defined

            other(1)
              The board's admin status in unavailable.

            started(2)
              The board has been started.

            stopped(3)
              The board is stopped.

            disabled(4)
              The board is disabled.

            diagnose(5)
             The board is being diagnosed.

            start-pending(6)
              The board is in the process of starting.

            stop-pending(7)
              The board is in the process of stopping.
		"

        ::= { dlgHiIdentEntry 14 }

    dlgHiIdentErrorMessage OBJECT-TYPE
        SYNTAX  DisplayString (SIZE (0..96))
        ACCESS  read-only
        STATUS  mandatory
        DESCRIPTION
           "Dialogic board Error Message.

            This value represents the error message associated with 
            a failing Dialogic board."
        ::= { dlgHiIdentEntry 15 }

    dlgHiIdentDeviceChangeDate OBJECT-TYPE
        SYNTAX  OCTET STRING (SIZE (7))
        ACCESS  read-only
        STATUS  mandatory
        DESCRIPTION
            "The date and time the boards operational status last changed.

             field  octets  contents                  range
             =====  ======  =======                   =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
       ::= { dlgHiIdentEntry 16 }

    dlgHiIdentSpecific OBJECT-TYPE
        SYNTAX  OBJECT IDENTIFIER
        ACCESS  read-only
        STATUS  mandatory
        DESCRIPTION
                "A reference to MIB definitions specific to the
                 particular board type specified in the row of 
                 the table

                 If this information is not present, its value should 
                 be set to the OBJECT IDENTIFIER { 0 0 }, which is a 
                 syntatically valid object identifier, and any conformant
                 implementation of ASN.1 and BER must be able to
                 generate and recognize this value."
         ::= { dlgHiIdentEntry 17 }

    dlgHiIdentPCIBusID OBJECT-TYPE
        SYNTAX  INTEGER
        ACCESS  read-only
        STATUS  mandatory
        DESCRIPTION
            "Dialogic board PCI Bus ID.

             This is a PCI Bus identifier where the Dialogic board is 
             installed. This may be used for identification purposes.
             If the Dialogic board is not a PCI board or if this info is 
             not available then a value of zero (0) is returned"
        ::= { dlgHiIdentEntry 18 }

-- ****************************************************************************
--  HardwareInfo Trap Definitions
--  =============================
--
--  The user may disable these traps by setting dlgHiIdentTrapMask
--
-- **************************************************************************

    dlgHiServiceChanged TRAP-TYPE
        ENTERPRISE dialogic
        VARIABLES  { sysName,
		     dlgHiIdentServiceStatus}
        DESCRIPTION
            "The Dialogic service condition has been changed

             Description: 

              The dlgHiIdentServiceChanged trap indicates that the 
              Dialogic service has transitioned to either the 
              started or stopped state. This may occur by performing 
              a set on the dlgHiIdentServiceStatus variable or by
              controlling the service directly on the machine which
              generated the trap.

             Action:

              This trap is informational. A management console may
              want to update any current device table views since
              attributes of the device may change when the Dialogic
              service is started or stopped"


        ::= 1001

       dlgHiboardStatusChanged TRAP-TYPE
        ENTERPRISE dialogic
        VARIABLES  { sysName,
		     dlgHiIdentIndexForTrap,
		     dlgHiIdentOperStatusForTrap,
                     dlgHiIdentAdminStatusForTrap,
                     dlgHiIdentModelForTrap,
                     dlgHiIdentSerNumForTrap,
                     dlgHiIdentErrorMessageForTrap
                   }
        DESCRIPTION
            "The condition of a Dialogic board has changed to failed or ok

             Description:

              The dlgHiIdentboardStatusChanged trap indicates that
              a device in the device table has transitioned from
              the ok state to the failed state or vice versa.
              In general this indicates that on-board firmware has
              crashed and is no longer responding or that the board
              has gone bad.
              Should the board recover from the failed state, the
              state will be transitioned back to the ok state and
              a trap will be generated to indicate the board is okay
              again.


             Action:

              If the state has transitioned to the failed then
              shutdown any active applications and reset the
              Dialogic service. This will cause the on-board firmware
              to be re-downloaded. If the problem persists you should
              run the device diagnostics on the board to make sure
              it is okay."

        ::= 1002

    dlgHiNonDlgcServiceChanged TRAP-TYPE
        ENTERPRISE dialogic
        VARIABLES  { sysName,
		     dlgHiIdentSystemServicesNameForTrap,
		     dlgHiIdentSystemServicesStatusForTrap
                     }
        DESCRIPTION
            "A Dialogic-Related service condition has been changed

             Description:

              The dlgHiNonDlgcServiceChanged trap indicates that a
              Dialogic-Related service (any UNIX Service other than the Dialogic System Service that has dependencies on Dialogic products) has transitioned to either the 
              started or stopped state. This may occur by performing
              a set on the dlgHiIdentSystemServicesStatus variable or by
              controlling the service directly on the machine which
              generated the trap.

             Action:

              This trap is informational. A management console may
              want to update any current device table views since
              attributes of the device may change when the Dialogic-Related
              service is started or stopped"


        ::= 1003
   


    dlgHiTestTrap TRAP-TYPE
        ENTERPRISE dialogic
        VARIABLES  { sysName }
        DESCRIPTION
            "This trap is to test if the trap sending mechanism is acting properly

             Description: 
              A managed node will request from the hardware agent to send this trap
	      with the name of the node the agent resides on to the manager.	      	

             Action:
              
              This trap is informational to indicate that the hardware agent is
              capable of sending traps to the manager." 

        ::= 1004
END
