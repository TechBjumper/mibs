-- file automatically created


TELDAT-TRAP-ADSL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


adslTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ADSL event subsystem."
    REVISION "201401200930Z"
    DESCRIPTION "Initial implementation"
        ::= { telEventTraps 140 }


adslEventsGroup	OBJECT IDENTIFIER	::= { adslTrapsMIB 1 }

adslNotifications	OBJECT IDENTIFIER	::= { adslTrapsMIB 2 }
adslNotificationsPrefix	OBJECT IDENTIFIER	::= { adslNotifications 0 }

adslEventObjects1 OBJECT-IDENTITY
    STATUS current
    DESCRIPTION
        "Event ADSL.1
        Registration of the indicated ADSL device built on the specified chipset
        at the indicated address."
    ::= { adslEventsGroup 1 }

adsl1-MNEMONIC OBJECT-TYPE
    SYNTAX DisplayString
    MAX-ACCESS accessible-for-notify
    STATUS current
    DESCRIPTION
        "Parameter 'MNEMONIC' in event ADSL.1"
    ::= { adslEventObjects1 1 }

adsl1-CHIPSET-DESCRIPTION OBJECT-TYPE
    SYNTAX DisplayString
    MAX-ACCESS accessible-for-notify
    STATUS current
    DESCRIPTION
        "Parameter 'CHIPSET-DESCRIPTION' in event ADSL.1"
    ::= { adslEventObjects1 2 }

adsl1-ADDRESS OBJECT-TYPE
    SYNTAX Integer32
    MAX-ACCESS accessible-for-notify
    STATUS current
    DESCRIPTION
        "Parameter 'ADDRESS' in event ADSL.1"
    ::= { adslEventObjects1 3 }

adslEventObjects2 OBJECT-IDENTITY
    STATUS current
    DESCRIPTION
        "Event ADSL.2
        Command to the ADSL device."
    ::= { adslEventsGroup 2 }

adsl2-MNEMONIC OBJECT-TYPE
    SYNTAX DisplayString
    MAX-ACCESS accessible-for-notify
    STATUS current
    DESCRIPTION
        "Parameter 'MNEMONIC' in event ADSL.2"
    ::= { adslEventObjects2 1 }

adsl2-COMMAND-DESCRIPTION OBJECT-TYPE
    SYNTAX DisplayString
    MAX-ACCESS accessible-for-notify
    STATUS current
    DESCRIPTION
        "Parameter 'COMMAND-DESCRIPTION' in event ADSL.2"
    ::= { adslEventObjects2 2 }

adslEventObjects3 OBJECT-IDENTITY
    STATUS current
    DESCRIPTION
        "Event ADSL.3
        Notification of a line event: opening state, open failed and reason,
        opened, monitoring forces reneg, signal lost, orderly closed not granted,
        suicide request, closed..."
    ::= { adslEventsGroup 3 }

adsl3-MNEMONIC OBJECT-TYPE
    SYNTAX DisplayString
    MAX-ACCESS accessible-for-notify
    STATUS current
    DESCRIPTION
        "Parameter 'MNEMONIC' in event ADSL.3"
    ::= { adslEventObjects3 1 }

adsl3-LINE-INFORMATION OBJECT-TYPE
    SYNTAX DisplayString
    MAX-ACCESS accessible-for-notify
    STATUS current
    DESCRIPTION
        "Parameter 'LINE-INFORMATION' in event ADSL.3"
    ::= { adslEventObjects3 2 }

adslEventObjects4 OBJECT-IDENTITY
    STATUS current
    DESCRIPTION
        "Event ADSL.4
        ADSL state machine event (each chipset has a different state machine)."
    ::= { adslEventsGroup 4 }

adsl4-MNEMONIC OBJECT-TYPE
    SYNTAX DisplayString
    MAX-ACCESS accessible-for-notify
    STATUS current
    DESCRIPTION
        "Parameter 'MNEMONIC' in event ADSL.4"
    ::= { adslEventObjects4 1 }

adsl4-STATE-MACHINE-EVENT OBJECT-TYPE
    SYNTAX DisplayString
    MAX-ACCESS accessible-for-notify
    STATUS current
    DESCRIPTION
        "Parameter 'STATE-MACHINE-EVENT' in event ADSL.4"
    ::= { adslEventObjects4 2 }

adslEventObjects5 OBJECT-IDENTITY
    STATUS current
    DESCRIPTION
        "Event ADSL.5
        Chipset specific event."
    ::= { adslEventsGroup 5 }

adsl5-MNEMONIC OBJECT-TYPE
    SYNTAX DisplayString
    MAX-ACCESS accessible-for-notify
    STATUS current
    DESCRIPTION
        "Parameter 'MNEMONIC' in event ADSL.5"
    ::= { adslEventObjects5 1 }

adsl5-EVENT-DESCRIPTION OBJECT-TYPE
    SYNTAX DisplayString
    MAX-ACCESS accessible-for-notify
    STATUS current
    DESCRIPTION
        "Parameter 'EVENT-DESCRIPTION' in event ADSL.5"
    ::= { adslEventObjects5 2 }


adslNotification1 NOTIFICATION-TYPE
    OBJECTS { 
              adsl1-MNEMONIC, 
              adsl1-CHIPSET-DESCRIPTION,
              adsl1-ADDRESS 
            }
    STATUS current
    DESCRIPTION
        "Notification of Event ADSL.1

        Message: '$1 Device $2 registered address 0x$3'

        Parameters list:
              $1: adsl1-MNEMONIC
              $2: adsl1-CHIPSET-DESCRIPTION
              $3: adsl1-ADDRESS

        Registration of the indicated ADSL device built on the specified chipset
        at the indicated address."
    ::= { adslNotificationsPrefix 1 }

adslNotification2 NOTIFICATION-TYPE
    OBJECTS { 
              adsl2-MNEMONIC, 
              adsl2-COMMAND-DESCRIPTION 
            }
    STATUS current
    DESCRIPTION
        "Notification of Event ADSL.2

        Message: '$1 Device command $2'

        Parameters list:
              $1: adsl2-MNEMONIC
              $2: adsl2-COMMAND-DESCRIPTION

        Command to the ADSL device."
    ::= { adslNotificationsPrefix 2 }

adslNotification3 NOTIFICATION-TYPE
    OBJECTS { 
              adsl3-MNEMONIC, 
              adsl3-LINE-INFORMATION 
            }
    STATUS current
    DESCRIPTION
        "Notification of Event ADSL.3

        Message: '$1 Line $2'

        Parameters list:
              $1: adsl3-MNEMONIC
              $2: adsl3-LINE-INFORMATION

        Notification of a line event: opening state, open failed and reason,
        opened, monitoring forces reneg, signal lost, orderly closed not granted,
        suicide request, closed..."
    ::= { adslNotificationsPrefix 3 }

adslNotification4 NOTIFICATION-TYPE
    OBJECTS { 
              adsl4-MNEMONIC, 
              adsl4-STATE-MACHINE-EVENT 
            }
    STATUS current
    DESCRIPTION
        "Notification of Event ADSL.4

        Message: '$1 FSM $2'

        Parameters list:
              $1: adsl4-MNEMONIC
              $2: adsl4-STATE-MACHINE-EVENT

        ADSL state machine event (each chipset has a different state machine)."
    ::= { adslNotificationsPrefix 4 }

adslNotification5 NOTIFICATION-TYPE
    OBJECTS { 
              adsl5-MNEMONIC, 
              adsl5-EVENT-DESCRIPTION 
            }
    STATUS current
    DESCRIPTION
        "Notification of Event ADSL.5

        Message: '$1 $2'

        Parameters list:
              $1: adsl5-MNEMONIC
              $2: adsl5-EVENT-DESCRIPTION

        Chipset specific event."
    ::= { adslNotificationsPrefix 5 }

adslNotification6 NOTIFICATION-TYPE
    STATUS current
    DESCRIPTION
        "Notification of Event ADSL.6

        Message: '---'

        Reserved for possible future use."
    ::= { adslNotificationsPrefix 6 }

adslNotification7 NOTIFICATION-TYPE
    STATUS current
    DESCRIPTION
        "Notification of Event ADSL.7

        Message: '---'

        Reserved for possible future use."
    ::= { adslNotificationsPrefix 7 }

adslNotification8 NOTIFICATION-TYPE
    STATUS current
    DESCRIPTION
        "Notification of Event ADSL.8

        Message: '---'

        Reserved for possible future use."
    ::= { adslNotificationsPrefix 8 }


END
