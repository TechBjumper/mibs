GBNServiceMACAUTHEN-MIB DEFINITIONS ::= BEGIN

    IMPORTS
        Unsigned32, MODULE-IDENTITY, OBJECT-TYPE,
        Integer32, IpAddress,
        NOTIFICATION-TYPE                       FROM SNMPv2-SMI

        DisplayString, MacAddress,
        RowStatus, TruthValue                   FROM SNMPv2-TC

        MODULE-COMPLIANCE, OBJECT-GROUP         FROM SNMPv2-CONF

        gbnServiceAAA                           FROM GREENTECH-MASTER-MIB
        ;


    gbnMacAuthenMib MODULE-IDENTITY
        LAST-UPDATED    "0106010000Z"  -- Jun 01, 2010
        ORGANIZATION "Greentech"
        CONTACT-INFO "Adam Armstrong
                  E-mail: adama@observium.org"

        DESCRIPTION     "macauthen Enterprise MIB definition."

        REVISION        "0106010000Z"  -- Jun 01, 2010
        DESCRIPTION     "Initial MIB creation."

        ::= { gbnServiceAAA 4 }

 
------------------------------------------------------------------------------
--  Textual Conventions (i.e., these do not affect object encoding):
------------------------------------------------------------------------------
    --
    --  "DURABLE":
    --    Objects that are saved across a system reset and/or power cycle
    --    are noted as "DURABLE" for convenience in the DESCRIPTION
    --    section of the object definition.  Code must be explicitly
    --    written to implement these DURABLE objects.
    --

------------------------------------------------------------------------------
--  define groups in gbn-TACACS-MIB
        globalEnable OBJECT-TYPE
        SYNTAX TruthValue
        MAX-ACCESS read-write
        STATUS current
        DESCRIPTION
            "global config of mac-authentication.default is false."
        ::= { gbnMacAuthenMib 1 }

        radiusDomain OBJECT-TYPE
        SYNTAX DisplayString (SIZE (0..24))
        MAX-ACCESS read-write
        STATUS current
        DESCRIPTION
            "domain name of radius domain.use size 0 to delete.default is size 0,indicating none."
        ::= { gbnMacAuthenMib 2 }

        offlineTimer OBJECT-TYPE
        SYNTAX Integer32 (30..3600)
        MAX-ACCESS read-write
        STATUS current
        DESCRIPTION
            "offline time of mac.unit is second.default is 300 seconds."
        ::= { gbnMacAuthenMib 3 }

        quietTimer OBJECT-TYPE
        SYNTAX Integer32 (30..3600)
        MAX-ACCESS read-write
        STATUS current
        DESCRIPTION
            "quiet time of mac.unit is second.default is 60 secondsl"
        ::= { gbnMacAuthenMib 4 }

        userMode OBJECT-TYPE
              SYNTAX  INTEGER {
                          fixed(1),       -- use fixed name and password
                          macaddress(0)   -- use mac-address
                      }
        MAX-ACCESS read-write
        STATUS current
        DESCRIPTION
            "how to make username and password of radius.default is macaddress(0)."
        ::= { gbnMacAuthenMib 5 }

        userName OBJECT-TYPE
        SYNTAX DisplayString (SIZE (0..63))
        MAX-ACCESS read-write
        STATUS current
        DESCRIPTION
            "username when usermode is fiexed.use size 0 to delete.default is size 0,indicating none."
        ::= { gbnMacAuthenMib 6 }

        password OBJECT-TYPE
        SYNTAX DisplayString (SIZE (0..63))
        MAX-ACCESS read-write
        STATUS current
        DESCRIPTION
            "password when usermode is fiexed.use size 0 to delete.default is size 0,indicating none."
        ::= { gbnMacAuthenMib 7 }

    macAuthenPortTable OBJECT-TYPE
        SYNTAX      SEQUENCE OF MacAuthenPortEntry
        MAX-ACCESS  not-accessible
        STATUS      current
        DESCRIPTION
            "table of information of ports."
        REFERENCE
            "9.6.1"
        ::= { gbnMacAuthenMib 8 }

    macAuthenPortEntry OBJECT-TYPE
        SYNTAX      MacAuthenPortEntry
        MAX-ACCESS  not-accessible
        STATUS      current
        DESCRIPTION
            "table of information of ports."
        INDEX { macAuthenPortNumber }
        ::= { macAuthenPortTable 1 }

    MacAuthenPortEntry ::=
        SEQUENCE {
            macAuthenPortNumber
                Unsigned32,
            macAuthenEnable
                TruthValue
            }

    macAuthenPortNumber OBJECT-TYPE
        SYNTAX      Unsigned32
        MAX-ACCESS  read-only
        STATUS      current
        DESCRIPTION
            "The Port number associated with this Port."
        REFERENCE
            "9.6.1, Port number"
        ::= { macAuthenPortEntry 1 }


    macAuthenEnable OBJECT-TYPE
        SYNTAX      TruthValue
        MAX-ACCESS  read-write
        STATUS      current
        DESCRIPTION
            "Enable/disable mac-authentication of this Port.default is disabled."
        REFERENCE
            "9.6.1, Protocol version"
        ::= { macAuthenPortEntry 2 }

        encrptionMode OBJECT-TYPE
              SYNTAX  INTEGER {
                          chap(1),       -- use chap
                          pap(0)   -- use pap
                      }
        MAX-ACCESS read-write
        STATUS current
        DESCRIPTION
            "radius password encrption mode,default is pap."
        ::= { gbnMacAuthenMib 9 }

        macvlanEnable OBJECT-TYPE
        SYNTAX TruthValue
        MAX-ACCESS read-write
        STATUS current
        DESCRIPTION
            "whethe to use mac vlan function.default is false."
        ::= { gbnMacAuthenMib 10 }

--
-- END of gbn-MACAUTHEN-MIB
--

END
