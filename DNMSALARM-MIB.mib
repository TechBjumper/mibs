--    @(#)3604trap.mib	9.1 10/16/98 
	DNMSALARM-MIB DEFINITIONS ::= BEGIN



	IMPORTS

		dynaCommGeneral

	      		FROM DYNATECHCOMMUNICATIONS-MIB

		DisplayString, ifIndex

			FROM RFC1213-MIB

		OBJECT-TYPE

			FROM RFC-1212

		TRAP-TYPE

			FROM RFC-1215;





	-- This file defines the DN25-Style alarms as SNMP traps

	-- this is meant to be a way to introduce the alarm/trap

	-- conditions into an SNMP controlled environment more

	-- quickly than the entire MIB for a DynaTech CPX Product

	-- can be created.



	dnmsAlarm OBJECT IDENTIFIER ::= { dynaCommGeneral 1 }



	-- Since each alarm is meant tobe turned on/off individually 

	-- above and beyond the Dynatech Enable for alarms there is

	-- an individual on/off for each in addtition to the main

	-- enable disable.



	dnmsAlarmEnable OBJECT-TYPE

		SYNTAX	INTEGER {

			enabled(1),

			disabled(2)

		}

		ACCESS	read-write

		STATUS	mandatory

		DESCRIPTION

			"The on/off switch for the dnms style alarms

			as SNMP traps.  When enabled, any condition that

			would generate an alarm in the DynaTech proprietary

			management systems would instead generate a SNMP

			style trap."

		::= { dnmsAlarm 1 }



	dnmsAlarmTable	OBJECT-TYPE

		SYNTAX	SEQUENCE OF DnmsAlarmEntry

		ACCESS	not-accessible

		STATUS	mandatory

		DESCRIPTION

			"The table of Dynatech proprietary alarms."

		::= { dnmsAlarm 2 }



	dnmsAlarmEntry	OBJECT-TYPE

		SYNTAX	DnmsAlarmEntry



		ACCESS	not-accessible

		STATUS	mandatory

		DESCRIPTION

			"An entry for each of the Dynatech proprietary alarms

			supported by the product."

		::= { dnmsAlarmTable 1 }



	DnmsAlarmEntry ::=

		SEQUENCE {

			dnmsAlarmEntryIndex

				INTEGER,

			dnmsAlarmEntryEnable

				INTEGER,

			dnmsAlarmEntryDescr

				DisplayString

		}



	dnmsAlarmEntryIndex OBJECT-TYPE

		SYNTAX	INTEGER {

			x25-lev1-dn(1),

			x25-lev1-up(2),

			x25-lev2-dn(3),

			x25-lev2-up(4),

			x25-lev3-dn(5),

			x25-lev3-up(6),

			fcs-err(7),

			cdrlost(8),

			almlost(9),

			stalost(10),

			dev-up(11),

			dev-dn(12),

			psufail(13),

			card-primem(14),

			card-secmem(15),

			card-primstr(16),

			card-secmstr(17),

			card-linecrd(18),

			x28-portX28(19),

			x28-portPkt(20),

			x28-inact(21),

			dllinit(22),

			dllok(23),

			dllfail(24),

			fr-nt1time(25),

			fr-nt2imte(26),

			fr-nn4count(27),

			fr-invmsg(28),

			tpad-nak-ex(29),

			tpad-slowPoll(30),

			tpad-normPoll(31),

			tpad-CD-down(32),

			tpad-CD-up(33)

		}

		ACCESS	read-only

		STATUS	mandatory

		DESCRIPTION

			"Arbitrary number assigned to each alarm.  Not all

			CPX equipment will support all alarms."

		::= { dnmsAlarmEntry 1 }



	dnmsAlarmEntryEnable OBJECT-TYPE

		SYNTAX	INTEGER {

			enable(1),

			disable(2)

		}

		ACCESS	read-write

		STATUS	mandatory

		DESCRIPTION

			"Each alarm can be enabled/disabled individually.

			This is expected to matter more as equivalent SNMP

			style traps are implemented in MIBS for CPX boxes.

			The overlapping traps (e.g. rfc1215's linkDown and

			linkUp overlapping the X25 link down and ups) could

			result in superfluous trap messages. These can be 

			avoided by selectively disabling some of these

			traps."

		::= { dnmsAlarmEntry 2 }



	dnmsAlarmEntryDescr OBJECT-TYPE

		SYNTAX	DisplayString (SIZE(0..255))

		ACCESS	read-only

		STATUS	mandatory

		DESCRIPTION

			"Textual Description of the alarm condition."

		::= { dnmsAlarmEntry 3 }





	dnmsAlarmTrap	TRAP-TYPE

		ENTERPRISE dnmsAlarm

		VARIABLES {

			ifIndex ,

			dnmsAlarmEntryIndex,

			dnmsAlarmEntryDescr

		}



		DESCRIPTION

			"An SNMP Trap to encapsulate the Dynatech Communications

			DN25 style alarms into an SNMP managed environment."

		::= 1



	END
