T300-MIB2 DEFINITIONS ::= BEGIN

IMPORTS
    enterprises, MODULE-IDENTITY, Integer32
        FROM SNMPv2-SMI;

t300 MODULE-IDENTITY
    LAST-UPDATED "0609201255Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        ""
    ::= { modules 19 }
modules	OBJECT IDENTIFIER ::= { agent 2 }

agent	OBJECT IDENTIFIER ::= { sunsymon 2 }

sunsymon	OBJECT IDENTIFIER ::= { prod 12 }

prod	OBJECT IDENTIFIER ::= { sun 2 }

sun	OBJECT IDENTIFIER ::= { enterprises 42 }


system	OBJECT IDENTIFIER ::= { t300 1 }

RowStatus ::= TEXTUAL-CONVENTION
    STATUS       current
    DESCRIPTION
               "RowStatus"
    SYNTAX       INTEGER {
                     -- the following two values are states:
                     -- these values may be read or written
                     active(1),
                     notInService(2),

                     -- the following value is a state:
                     -- this value may be read, but not written
                     notReady(3),

                     -- the following three values are
                     -- actions: these values may be written,
                     --   but are never read
                     createAndGo(4),
                     createAndWait(5),
                     destroy(6)
                 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

sysbasictable OBJECT-TYPE
    SYNTAX      SEQUENCE OF Basicentry
    MAX-ACCESS  not-accessible
    STATUS      current
    DESCRIPTION
                "MIB tree branch"
    ::= { system 1 }

sysbasicentry OBJECT-TYPE
    SYNTAX      Basicentry
    MAX-ACCESS  not-accessible
    STATUS      current
    DESCRIPTION
                "MIB tree branch"
    INDEX  { sysbasicentryt300name }
    ::= { sysbasictable 1 }

Basicentry ::=
    SEQUENCE {
        sysbasicentryt300name
            DisplayString,
        sysbasicentrysunSmTreeProp
            DisplayString,
        sysbasicentrysunSmNodeName
            DisplayString,
        sysrowstatus
            RowStatus,
        sysId
            DisplayString,
        sysVendor
            DisplayString,
        sysModel
            DisplayString,
        sysRevision
            DisplayString,
        sysIpAddr
            DisplayString,
        sysSubNet
            DisplayString,
        sysGateway
            DisplayString,
        sysBootMode
            DisplayString,
        sysBootDelay
            DisplayString,
        sysMpSupport
            DisplayString,
        sysHasVolumes
            DisplayString,
        sysStatus
            DisplayString
    }

sysbasicentryt300name OBJECT-TYPE
    SYNTAX      DisplayString
    MAX-ACCESS  read-only
    STATUS      current
    DESCRIPTION
                "Character string value"
    ::= { sysbasicentry 1 }

sysbasicentrysunSmTreeProp OBJECT-TYPE
    SYNTAX      DisplayString
    MAX-ACCESS  read-only
    STATUS      current
    DESCRIPTION
                "Character string value"
    ::= { sysbasicentry 2 }

sysbasicentrysunSmNodeName OBJECT-TYPE
    SYNTAX      DisplayString
    MAX-ACCESS  read-only
    STATUS      current
    DESCRIPTION
                "Character string value"
    ::= { sysbasicentry 3 }

sysrowstatus OBJECT-TYPE
    SYNTAX      RowStatus
    MAX-ACCESS  read-write
    STATUS      current
    DESCRIPTION
                "Table row status"
    ::= { sysbasicentry 4 }

sysId OBJECT-TYPE
    SYNTAX      DisplayString
    MAX-ACCESS  read-write
    STATUS      current
    DESCRIPTION
                "Character string value"
    ::= { sysbasicentry 5 }

sysVendor OBJECT-TYPE
    SYNTAX      DisplayString
    MAX-ACCESS  read-only
    STATUS      current
    DESCRIPTION
                "Character string value"
    ::= { sysbasicentry 6 }

sysModel OBJECT-TYPE
    SYNTAX      DisplayString
    MAX-ACCESS  read-only
    STATUS      current
    DESCRIPTION
                "Character string value"
    ::= { sysbasicentry 7 }

sysRevision OBJECT-TYPE
    SYNTAX      DisplayString
    MAX-ACCESS  read-only
    STATUS      current
    DESCRIPTION
                "Character string value"
    ::= { sysbasicentry 8 }

sysIpAddr OBJECT-TYPE
    SYNTAX      DisplayString
    MAX-ACCESS  read-only
    STATUS      current
    DESCRIPTION
                "Character string value"
    ::= { sysbasicentry 9 }

sysSubNet OBJECT-TYPE
    SYNTAX      DisplayString
    MAX-ACCESS  read-write
    STATUS      current
    DESCRIPTION
                "Character string value"
    ::= { sysbasicentry 10 }

sysGateway OBJECT-TYPE
    SYNTAX      DisplayString
    MAX-ACCESS  read-write
    STATUS      current
    DESCRIPTION
                "Character string value"
    ::= { sysbasicentry 11 }

sysBootMode OBJECT-TYPE
    SYNTAX      DisplayString
    MAX-ACCESS  read-write
    STATUS      current
    DESCRIPTION
                "Character string value"
    ::= { sysbasicentry 12 }

sysBootDelay OBJECT-TYPE
    SYNTAX      DisplayString
    MAX-ACCESS  read-write
    STATUS      current
    DESCRIPTION
                "Character string value"
    ::= { sysbasicentry 13 }

sysMpSupport OBJECT-TYPE
    SYNTAX      DisplayString
    MAX-ACCESS  read-write
    STATUS      current
    DESCRIPTION
                "Character string value"
    ::= { sysbasicentry 14 }

sysHasVolumes OBJECT-TYPE
    SYNTAX      DisplayString
    MAX-ACCESS  read-only
    STATUS      current
    DESCRIPTION
                "Character string value"
    ::= { sysbasicentry 15 }

sysStatus OBJECT-TYPE
    SYNTAX      DisplayString
    MAX-ACCESS  read-only
    STATUS      current
    DESCRIPTION
                "Character string value"
    ::= { sysbasicentry 16 }

systemadvancedtable OBJECT-TYPE
    SYNTAX      SEQUENCE OF Advancedentry
    MAX-ACCESS  not-accessible
    STATUS      current
    DESCRIPTION
                "MIB tree branch"
    ::= { system 2 }

systemadvancedentry OBJECT-TYPE
    SYNTAX      Advancedentry
    MAX-ACCESS  not-accessible
    STATUS      current
    DESCRIPTION
                "MIB tree branch"
    INDEX  { systemadvancedentryt300name }
    ::= { systemadvancedtable 1 }

Advancedentry ::=
    SEQUENCE {
        systemadvancedentryt300name
            DisplayString,
        systemadvancedentryrowstatus
            RowStatus,
        sysStripeUnitSize
            DisplayString,
        sysCacheMode
            DisplayString,
        sysCacheMirror
            DisplayString,
        sysReadAhead
            DisplayString,
        sysReconRate
            DisplayString,
        sysOndgMode
            DisplayString,
        sysOndgTimeslice
            DisplayString,
        sysTftpHost
            DisplayString,
        sysTftpFile
            DisplayString,
        sysLastRestart
            DisplayString,
        sysDate
            DisplayString,
        sysTime
            DisplayString,
        sysTimezone
            DisplayString
    }

systemadvancedentryt300name OBJECT-TYPE
    SYNTAX      DisplayString
    MAX-ACCESS  read-only
    STATUS      current
    DESCRIPTION
                "Character string value"
    ::= { systemadvancedentry 1 }

systemadvancedentryrowstatus OBJECT-TYPE
    SYNTAX      RowStatus
    MAX-ACCESS  read-write
    STATUS      current
    DESCRIPTION
                "Table row status"
    ::= { systemadvancedentry 2 }

sysStripeUnitSize OBJECT-TYPE
    SYNTAX      DisplayString
    MAX-ACCESS  read-write
    STATUS      current
    DESCRIPTION
                "Character string value"
    ::= { systemadvancedentry 3 }

sysCacheMode OBJECT-TYPE
    SYNTAX      DisplayString
    MAX-ACCESS  read-write
    STATUS      current
    DESCRIPTION
                "Character string value"
    ::= { systemadvancedentry 4 }

sysCacheMirror OBJECT-TYPE
    SYNTAX      DisplayString
    MAX-ACCESS  read-write
    STATUS      current
    DESCRIPTION
                "Character string value"
    ::= { systemadvancedentry 5 }

sysReadAhead OBJECT-TYPE
    SYNTAX      DisplayString
    MAX-ACCESS  read-write
    STATUS      current
    DESCRIPTION
                "Character string value"
    ::= { systemadvancedentry 6 }

sysReconRate OBJECT-TYPE
    SYNTAX      DisplayString
    MAX-ACCESS  read-write
    STATUS      current
    DESCRIPTION
                "Character string value"
    ::= { systemadvancedentry 7 }

sysOndgMode OBJECT-TYPE
    SYNTAX      DisplayString
    MAX-ACCESS  read-write
    STATUS      current
    DESCRIPTION
                "Character string value"
    ::= { systemadvancedentry 8 }

sysOndgTimeslice OBJECT-TYPE
    SYNTAX      DisplayString
    MAX-ACCESS  read-write
    STATUS      current
    DESCRIPTION
                "Character string value"
    ::= { systemadvancedentry 9 }

sysTftpHost OBJECT-TYPE
    SYNTAX      DisplayString
    MAX-ACCESS  read-only
    STATUS      current
    DESCRIPTION
                "Character string value"
    ::= { systemadvancedentry 10 }

sysTftpFile OBJECT-TYPE
    SYNTAX      DisplayString
    MAX-ACCESS  read-only
    STATUS      current
    DESCRIPTION
                "Character string value"
    ::= { systemadvancedentry 11 }

sysLastRestart OBJECT-TYPE
    SYNTAX      DisplayString
    MAX-ACCESS  read-only
    STATUS      current
    DESCRIPTION
                "Character string value"
    ::= { systemadvancedentry 12 }

sysDate OBJECT-TYPE
    SYNTAX      DisplayString
    MAX-ACCESS  read-only
    STATUS      current
    DESCRIPTION
                "Character string value"
    ::= { systemadvancedentry 13 }

sysTime OBJECT-TYPE
    SYNTAX      DisplayString
    MAX-ACCESS  read-only
    STATUS      current
    DESCRIPTION
                "Character string value"
    ::= { systemadvancedentry 14 }

sysTimezone OBJECT-TYPE
    SYNTAX      DisplayString
    MAX-ACCESS  read-only
    STATUS      current
    DESCRIPTION
                "Character string value"
    ::= { systemadvancedentry 15 }

statisticaltable OBJECT-TYPE
    SYNTAX      SEQUENCE OF Statisticalentry
    MAX-ACCESS  not-accessible
    STATUS      current
    DESCRIPTION
                "MIB tree branch"
    ::= { system 3 }

statisticalentry OBJECT-TYPE
    SYNTAX      Statisticalentry
    MAX-ACCESS  not-accessible
    STATUS      current
    DESCRIPTION
                "MIB tree branch"
    INDEX  { statisticalentryt300name }
    ::= { statisticaltable 1 }

Statisticalentry ::=
    SEQUENCE {
        statisticalentryt300name
            DisplayString,
        sysTotalRequests
            DisplayString,
        sysWriteRequests
            DisplayString,
        sysReadRequests
            DisplayString,
        sysTotalBlocks
            DisplayString,
        sysBlocksWritten
            DisplayString,
        sysBlocksRead
            DisplayString,
        sysCacheWriteHits
            DisplayString,
        sysCacheWriteMisses
            DisplayString,
        sysCacheReadHits
            DisplayString,
        sysCacheReadMisses
            DisplayString,
        sysCacheRmwFlushes
            DisplayString,
        sysCacheReconFlushes
            DisplayString,
        sysCacheStripeFlushes
            DisplayString,
        sysClearflag
            Integer32
    }

statisticalentryt300name OBJECT-TYPE
    SYNTAX      DisplayString
    MAX-ACCESS  read-only
    STATUS      current
    DESCRIPTION
                "Character string value"
    ::= { statisticalentry 1 }

sysTotalRequests OBJECT-TYPE
    SYNTAX      DisplayString
    MAX-ACCESS  read-only
    STATUS      current
    DESCRIPTION
                "Character string value"
    ::= { statisticalentry 2 }

sysWriteRequests OBJECT-TYPE
    SYNTAX      DisplayString
    MAX-ACCESS  read-only
    STATUS      current
    DESCRIPTION
                "Character string value"
    ::= { statisticalentry 3 }

sysReadRequests OBJECT-TYPE
    SYNTAX      DisplayString
    MAX-ACCESS  read-only
    STATUS      current
    DESCRIPTION
                "Character string value"
    ::= { statisticalentry 4 }

sysTotalBlocks OBJECT-TYPE
    SYNTAX      DisplayString
    MAX-ACCESS  read-only
    STATUS      current
    DESCRIPTION
                "Character string value"
    ::= { statisticalentry 5 }

sysBlocksWritten OBJECT-TYPE
    SYNTAX      DisplayString
    MAX-ACCESS  read-only
    STATUS      current
    DESCRIPTION
                "Character string value"
    ::= { statisticalentry 6 }

sysBlocksRead OBJECT-TYPE
    SYNTAX      DisplayString
    MAX-ACCESS  read-only
    STATUS      current
    DESCRIPTION
                "Character string value"
    ::= { statisticalentry 7 }

sysCacheWriteHits OBJECT-TYPE
    SYNTAX      DisplayString
    MAX-ACCESS  read-only
    STATUS      current
    DESCRIPTION
                "Character string value"
    ::= { statisticalentry 8 }

sysCacheWriteMisses OBJECT-TYPE
    SYNTAX      DisplayString
    MAX-ACCESS  read-only
    STATUS      current
    DESCRIPTION
                "Character string value"
    ::= { statisticalentry 9 }

sysCacheReadHits OBJECT-TYPE
    SYNTAX      DisplayString
    MAX-ACCESS  read-only
    STATUS      current
    DESCRIPTION
                "Character string value"
    ::= { statisticalentry 10 }

sysCacheReadMisses OBJECT-TYPE
    SYNTAX      DisplayString
    MAX-ACCESS  read-only
    STATUS      current
    DESCRIPTION
                "Character string value"
    ::= { statisticalentry 11 }

sysCacheRmwFlushes OBJECT-TYPE
    SYNTAX      DisplayString
    MAX-ACCESS  read-only
    STATUS      current
    DESCRIPTION
                "Character string value"
    ::= { statisticalentry 12 }

sysCacheReconFlushes OBJECT-TYPE
    SYNTAX      DisplayString
    MAX-ACCESS  read-only
    STATUS      current
    DESCRIPTION
                "Character string value"
    ::= { statisticalentry 13 }

sysCacheStripeFlushes OBJECT-TYPE
    SYNTAX      DisplayString
    MAX-ACCESS  read-only
    STATUS      current
    DESCRIPTION
                "Character string value"
    ::= { statisticalentry 14 }

sysClearflag OBJECT-TYPE
    SYNTAX      Integer32 (-2147483648..2147483647)
    MAX-ACCESS  read-write
    STATUS      current
    DESCRIPTION
                "Integer value"
    ::= { statisticalentry 15 }

unit	OBJECT IDENTIFIER ::= { t300 2 }

unittable OBJECT-TYPE
    SYNTAX      SEQUENCE OF Unitentry
    MAX-ACCESS  not-accessible
    STATUS      current
    DESCRIPTION
                "MIB tree branch"
    ::= { unit 1 }

unitentry OBJECT-TYPE
    SYNTAX      Unitentry
    MAX-ACCESS  not-accessible
    STATUS      current
    DESCRIPTION
                "MIB tree branch"
    INDEX  { unitentryt300name,
              unitId }
    ::= { unittable 1 }

Unitentry ::=
    SEQUENCE {
        unitentryt300name
            DisplayString,
        unitId
            DisplayString,
        unitentrysunSmTreeProp
            DisplayString,
        unitentrysunSmNodeName
            DisplayString,
        unitType
            DisplayString,
        unitStandby
            DisplayString,
        unitIsControllerUnit
            DisplayString,
        machine
            DisplayString,
        platform
            DisplayString
    }

unitentryt300name OBJECT-TYPE
    SYNTAX      DisplayString
    MAX-ACCESS  read-only
    STATUS      current
    DESCRIPTION
                "Character string value"
    ::= { unitentry 1 }

unitId OBJECT-TYPE
    SYNTAX      DisplayString
    MAX-ACCESS  read-only
    STATUS      current
    DESCRIPTION
                "Character string value"
    ::= { unitentry 2 }

unitentrysunSmTreeProp OBJECT-TYPE
    SYNTAX      DisplayString
    MAX-ACCESS  read-only
    STATUS      current
    DESCRIPTION
                "Character string value"
    ::= { unitentry 3 }

unitentrysunSmNodeName OBJECT-TYPE
    SYNTAX      DisplayString
    MAX-ACCESS  read-only
    STATUS      current
    DESCRIPTION
                "Character string value"
    ::= { unitentry 4 }

unitType OBJECT-TYPE
    SYNTAX      DisplayString
    MAX-ACCESS  read-only
    STATUS      current
    DESCRIPTION
                "Character string value"
    ::= { unitentry 5 }

unitStandby OBJECT-TYPE
    SYNTAX      DisplayString
    MAX-ACCESS  read-only
    STATUS      current
    DESCRIPTION
                "Character string value"
    ::= { unitentry 6 }

unitIsControllerUnit OBJECT-TYPE
    SYNTAX      DisplayString
    MAX-ACCESS  read-only
    STATUS      current
    DESCRIPTION
                "Character string value"
    ::= { unitentry 7 }

machine OBJECT-TYPE
    SYNTAX      DisplayString
    MAX-ACCESS  read-only
    STATUS      current
    DESCRIPTION
                "Character string value"
    ::= { unitentry 8 }

platform OBJECT-TYPE
    SYNTAX      DisplayString
    MAX-ACCESS  read-only
    STATUS      current
    DESCRIPTION
                "Character string value"
    ::= { unitentry 9 }

disks	OBJECT IDENTIFIER ::= { t300 3 }

diskstable OBJECT-TYPE
    SYNTAX      SEQUENCE OF Disksentry
    MAX-ACCESS  not-accessible
    STATUS      current
    DESCRIPTION
                "MIB tree branch"
    ::= { disks 1 }

disksentry OBJECT-TYPE
    SYNTAX      Disksentry
    MAX-ACCESS  not-accessible
    STATUS      current
    DESCRIPTION
                "MIB tree branch"
    INDEX  { entryno }
    ::= { diskstable 1 }

Disksentry ::=
    SEQUENCE {
        entryno
            DisplayString,
        sunSmTreeProp
            DisplayString,
        sunSmNodeName
            DisplayString
    }

entryno OBJECT-TYPE
    SYNTAX      DisplayString
    MAX-ACCESS  read-only
    STATUS      current
    DESCRIPTION
                "Character string value"
    ::= { disksentry 1 }

disksentrysunSmTreeProp OBJECT-TYPE
    SYNTAX      DisplayString
    MAX-ACCESS  read-only
    STATUS      current
    DESCRIPTION
                "Character string value"
    ::= { disksentry 2 }

disksentrysunSmNodeName OBJECT-TYPE
    SYNTAX      DisplayString
    MAX-ACCESS  read-only
    STATUS      current
    DESCRIPTION
                "Character string value"
    ::= { disksentry 3 }

disk	OBJECT IDENTIFIER ::= { t300 4 }

diskbasictable OBJECT-TYPE
    SYNTAX      SEQUENCE OF Basicentry
    MAX-ACCESS  not-accessible
    STATUS      current
    DESCRIPTION
                "MIB tree branch"
    ::= { disk 1 }

diskbasicentry OBJECT-TYPE
    SYNTAX      Basicentry
    MAX-ACCESS  not-accessible
    STATUS      current
    DESCRIPTION
                "MIB tree branch"
    INDEX  { diskbasicentry1t300name,
              unitId,
              diskfruId }
    ::= { diskbasictable 1 }

Basicentry ::=
    SEQUENCE {
        diskbasicentry1t300name
            DisplayString,
        diskunitId
            DisplayString,
        diskfruId
            DisplayString,
        disksunSmTreeProp
            DisplayString,
        disksunSmNodeName
            DisplayString,
        diskfruStatus
            DisplayString,
        diskfruState
            DisplayString,
        diskfruVendor
            DisplayString,
        diskfruModel
            DisplayString,
        diskfruRevision
            DisplayString,
        diskfruSerialNo
            DisplayString,
        diskfruErrors
            DisplayString,
        fruDiskRole
            DisplayString,
        fruDiskCapacity
            DisplayString,
        fruDiskTemp
            DisplayString
    }

diskbasicentry1t300name OBJECT-TYPE
    SYNTAX      DisplayString
    MAX-ACCESS  read-only
    STATUS      current
    DESCRIPTION
                "Character string value"
    ::= { diskbasicentry 1 }

diskunitId OBJECT-TYPE
    SYNTAX      DisplayString
    MAX-ACCESS  read-only
    STATUS      current
    DESCRIPTION
                "Character string value"
    ::= { diskbasicentry 2 }

diskfruId OBJECT-TYPE
    SYNTAX      DisplayString
    MAX-ACCESS  read-only
    STATUS      current
    DESCRIPTION
                "Character string value"
    ::= { diskbasicentry  3 }

disksunSmTreeProp OBJECT-TYPE
    SYNTAX      DisplayString
    MAX-ACCESS  read-only
    STATUS      current
    DESCRIPTION
                "Character string value"
    ::= { diskbasicentry 4 }

disksunSmNodeName OBJECT-TYPE
    SYNTAX      DisplayString
    MAX-ACCESS  read-only
    STATUS      current
    DESCRIPTION
                "Character string value"
    ::= { diskbasicentry 5 }

diskfruStatus OBJECT-TYPE
    SYNTAX      DisplayString
    MAX-ACCESS  read-only
    STATUS      current
    DESCRIPTION
                "Character string value"
    ::= { diskbasicentry 6 }

diskfruState OBJECT-TYPE
    SYNTAX      DisplayString
    MAX-ACCESS  read-only
    STATUS      current
    DESCRIPTION
                "Character string value"
    ::= { diskbasicentry 7 }

diskfruVendor OBJECT-TYPE
    SYNTAX      DisplayString
    MAX-ACCESS  read-only
    STATUS      current
    DESCRIPTION
                "Character string value"
    ::= { diskbasicentry 8 }

diskfruModel OBJECT-TYPE
    SYNTAX      DisplayString
    MAX-ACCESS  read-only
    STATUS      current
    DESCRIPTION
                "Character string value"
    ::= { diskbasicentry 9 }

diskfruRevision OBJECT-TYPE
    SYNTAX      DisplayString
    MAX-ACCESS  read-only
    STATUS      current
    DESCRIPTION
                "Character string value"
    ::= { diskbasicentry 10 }

diskfruSerialNo OBJECT-TYPE
    SYNTAX      DisplayString
    MAX-ACCESS  read-only
    STATUS      current
    DESCRIPTION
                "Character string value"
    ::= { diskbasicentry 11 }

diskfruErrors OBJECT-TYPE
    SYNTAX      DisplayString
    MAX-ACCESS  read-only
    STATUS      current
    DESCRIPTION
                "Character string value"
    ::= { diskbasicentry 12 }

fruDiskRole OBJECT-TYPE
    SYNTAX      DisplayString
    MAX-ACCESS  read-only
    STATUS      current
    DESCRIPTION
                "Character string value"
    ::= { diskbasicentry 13 }

fruDiskCapacity OBJECT-TYPE
    SYNTAX      DisplayString
    MAX-ACCESS  read-only
    STATUS      current
    DESCRIPTION
                "Character string value"
    ::= { diskbasicentry 14 }

fruDiskTemp OBJECT-TYPE
    SYNTAX      DisplayString
    MAX-ACCESS  read-only
    STATUS      current
    DESCRIPTION
                "Character string value"
    ::= { diskbasicentry 15 }

diskadvancedtable OBJECT-TYPE
    SYNTAX      SEQUENCE OF Advancedentry
    MAX-ACCESS  not-accessible
    STATUS      current
    DESCRIPTION
                "MIB tree branch"
    ::= { disk 2 }

diskadvancedentry OBJECT-TYPE
    SYNTAX      Advancedentry
    MAX-ACCESS  not-accessible
    STATUS      current
    DESCRIPTION
                "MIB tree branch"
    INDEX  { advancedentryt300name,
              unitId,
              diskadvancedentryfruId }
    ::= { diskadvancedtable 1 }

Advancedentry ::=
    SEQUENCE {
        advancedentryt300name
            DisplayString,
        diskadvancedentryunitId
            DisplayString,
        diskadvancedentryfruId
            DisplayString,
        fruDiskPort1State
            DisplayString,
        fruDiskPort2State
            DisplayString,
        fruDiskStatusCode
            DisplayString,
        fruDiskVolId
            DisplayString,
        fruDiskVolIndex
            DisplayString,
        fruDiskVolName
            DisplayString,
        fruDiskIsRoleData
            DisplayString,
        fruDiskIsRoleStandby
            DisplayString,
        fruDiskIsRoleUndefined
            DisplayString,
        fruDiskIsExpendable
            DisplayString,
        fruDiskIsRebuildable
            DisplayString
    }

advancedentryt300name OBJECT-TYPE
    SYNTAX      DisplayString
    MAX-ACCESS  read-only
    STATUS      current
    DESCRIPTION
                "Character string value"
    ::= { diskadvancedentry 1 }

diskadvancedentryunitId OBJECT-TYPE
    SYNTAX      DisplayString
    MAX-ACCESS  read-only
    STATUS      current
    DESCRIPTION
                "Character string value"
    ::= { diskadvancedentry 2 }

diskadvancedentryfruId OBJECT-TYPE
    SYNTAX      DisplayString
    MAX-ACCESS  read-only
    STATUS      current
    DESCRIPTION
                "Character string value"
    ::= { diskadvancedentry 3 }

fruDiskPort1State OBJECT-TYPE
    SYNTAX      DisplayString
    MAX-ACCESS  read-only
    STATUS      current
    DESCRIPTION
                "Character string value"
    ::= { diskadvancedentry 4 }

fruDiskPort2State OBJECT-TYPE
    SYNTAX      DisplayString
    MAX-ACCESS  read-only
    STATUS      current
    DESCRIPTION
                "Character string value"
    ::= { diskadvancedentry 5 }

fruDiskStatusCode OBJECT-TYPE
    SYNTAX      DisplayString
    MAX-ACCESS  read-only
    STATUS      current
    DESCRIPTION
                "Character string value"
    ::= { diskadvancedentry 6 }

fruDiskVolId OBJECT-TYPE
    SYNTAX      DisplayString
    MAX-ACCESS  read-only
    STATUS      current
    DESCRIPTION
                "Character string value"
    ::= { diskadvancedentry 7 }

fruDiskVolIndex OBJECT-TYPE
    SYNTAX      DisplayString
    MAX-ACCESS  read-only
    STATUS      current
    DESCRIPTION
                "Character string value"
    ::= { diskadvancedentry 8 }

fruDiskVolName OBJECT-TYPE
    SYNTAX      DisplayString
    MAX-ACCESS  read-only
    STATUS      current
    DESCRIPTION
                "Character string value"
    ::= { diskadvancedentry 9 }

fruDiskIsRoleData OBJECT-TYPE
    SYNTAX      DisplayString
    MAX-ACCESS  read-only
    STATUS      current
    DESCRIPTION
                "Character string value"
    ::= { diskadvancedentry 10 }

fruDiskIsRoleStandby OBJECT-TYPE
    SYNTAX      DisplayString
    MAX-ACCESS  read-only
    STATUS      current
    DESCRIPTION
                "Character string value"
    ::= { diskadvancedentry 11 }

fruDiskIsRoleUndefined OBJECT-TYPE
    SYNTAX      DisplayString
    MAX-ACCESS  read-only
    STATUS      current
    DESCRIPTION
                "Character string value"
    ::= { diskadvancedentry 12 }

fruDiskIsExpendable OBJECT-TYPE
    SYNTAX      DisplayString
    MAX-ACCESS  read-only
    STATUS      current
    DESCRIPTION
                "Character string value"
    ::= { diskadvancedentry 13 }

fruDiskIsRebuildable OBJECT-TYPE
    SYNTAX      DisplayString
    MAX-ACCESS  read-only
    STATUS      current
    DESCRIPTION
                "Character string value"
    ::= { diskadvancedentry 14 }

controllers	OBJECT IDENTIFIER ::= { t300 5 }

controllerstable OBJECT-TYPE
    SYNTAX      SEQUENCE OF Controllersentry
    MAX-ACCESS  not-accessible
    STATUS      current
    DESCRIPTION
                "MIB tree branch"
    ::= { controllers 1 }

controllersentry OBJECT-TYPE
    SYNTAX      Controllersentry
    MAX-ACCESS  not-accessible
    STATUS      current
    DESCRIPTION
                "MIB tree branch"
    INDEX  { entryno }
    ::= { controllerstable 1 }

Controllersentry ::=
    SEQUENCE {
        controllersentryentryno
            DisplayString,
        controllersentrysunSmTreeProp
            DisplayString,
        controllersentrysunSmNodeName
            DisplayString
    }

controllersentryentryno OBJECT-TYPE
    SYNTAX      DisplayString
    MAX-ACCESS  read-only
    STATUS      current
    DESCRIPTION
                "Character string value"
    ::= { controllersentry 1 }

controllersentrysunSmTreeProp OBJECT-TYPE
    SYNTAX      DisplayString
    MAX-ACCESS  read-only
    STATUS      current
    DESCRIPTION
                "Character string value"
    ::= { controllersentry 2 }

controllersentrysunSmNodeName OBJECT-TYPE
    SYNTAX      DisplayString
    MAX-ACCESS  read-only
    STATUS      current
    DESCRIPTION
                "Character string value"
    ::= { controllersentry 3 }

controller	OBJECT IDENTIFIER ::= { t300 6 }

controllertable OBJECT-TYPE
    SYNTAX      SEQUENCE OF Controllerentry
    MAX-ACCESS  not-accessible
    STATUS      current
    DESCRIPTION
                "MIB tree branch"
    ::= { controller 1 }

controllerentry OBJECT-TYPE
    SYNTAX      Controllerentry
    MAX-ACCESS  not-accessible
    STATUS      current
    DESCRIPTION
                "MIB tree branch"
    INDEX  { controllerentryt300name,
              unitId,
              controllerentryfruId }
    ::= { controllertable 1 }

Controllerentry ::=
    SEQUENCE {
        controllerentryt300name
            DisplayString,
        controllerentryunitId
            DisplayString,
        controllerentryfruId
            DisplayString,
        controllerentrysunSmTreeProp
            DisplayString,
        controllerentrysunSmNodeName
            DisplayString,
        controllerentryfruStatus
            DisplayString,
        controllerentryfruState
            DisplayString,
        controllerentryfruVendor
            DisplayString,
        controllerentryfruModel
            DisplayString,
        controllerentryfruRevision
            DisplayString,
        controllerentryfruSerialNo
            DisplayString,
        controllerentryfruErrors
            DisplayString,
        fruCtlrCpuDesc
            DisplayString,
        fruCtlrRole
            DisplayString,
        fruCtlrPartnerId
            DisplayString,
        fruCtlrCtState
            DisplayString,
        fruCtlrCacheSize
            DisplayString,
        fruCtlrTemp
            DisplayString,
        fruCtlrIsExpendable
            DisplayString
    }

controllerentryt300name OBJECT-TYPE
    SYNTAX      DisplayString
    MAX-ACCESS  read-only
    STATUS      current
    DESCRIPTION
                "Character string value"
    ::= { controllerentry 1 }

controllerentryunitId OBJECT-TYPE
    SYNTAX      DisplayString
    MAX-ACCESS  read-only
    STATUS      current
    DESCRIPTION
                "Character string value"
    ::= { controllerentry 2 }

controllerentryfruId OBJECT-TYPE
    SYNTAX      DisplayString
    MAX-ACCESS  read-only
    STATUS      current
    DESCRIPTION
                "Character string value"
    ::= { controllerentry 3 }

controllerentrysunSmTreeProp OBJECT-TYPE
    SYNTAX      DisplayString
    MAX-ACCESS  read-only
    STATUS      current
    DESCRIPTION
                "Character string value"
    ::= { controllerentry 4 }

controllerentrysunSmNodeName OBJECT-TYPE
    SYNTAX      DisplayString
    MAX-ACCESS  read-only
    STATUS      current
    DESCRIPTION
                "Character string value"
    ::= { controllerentry 5 }

controllerentryfruStatus OBJECT-TYPE
    SYNTAX      DisplayString
    MAX-ACCESS  read-only
    STATUS      current
    DESCRIPTION
                "Character string value"
    ::= { controllerentry 6 }

controllerentryfruState OBJECT-TYPE
    SYNTAX      DisplayString
    MAX-ACCESS  read-only
    STATUS      current
    DESCRIPTION
                "Character string value"
    ::= { controllerentry 7 }

controllerentryfruVendor OBJECT-TYPE
    SYNTAX      DisplayString
    MAX-ACCESS  read-only
    STATUS      current
    DESCRIPTION
                "Character string value"
    ::= { controllerentry 8 }

controllerentryfruModel OBJECT-TYPE
    SYNTAX      DisplayString
    MAX-ACCESS  read-only
    STATUS      current
    DESCRIPTION
                "Character string value"
    ::= { controllerentry 9 }

controllerentryfruRevision OBJECT-TYPE
    SYNTAX      DisplayString
    MAX-ACCESS  read-only
    STATUS      current
    DESCRIPTION
                "Character string value"
    ::= { controllerentry 10 }

controllerentryfruSerialNo OBJECT-TYPE
    SYNTAX      DisplayString
    MAX-ACCESS  read-only
    STATUS      current
    DESCRIPTION
                "Character string value"
    ::= { controllerentry 11 }

controllerentryfruErrors OBJECT-TYPE
    SYNTAX      DisplayString
    MAX-ACCESS  read-only
    STATUS      current
    DESCRIPTION
                "Character string value"
    ::= { controllerentry 12 }

fruCtlrCpuDesc OBJECT-TYPE
    SYNTAX      DisplayString
    MAX-ACCESS  read-only
    STATUS      current
    DESCRIPTION
                "Character string value"
    ::= { controllerentry 13 }

fruCtlrRole OBJECT-TYPE
    SYNTAX      DisplayString
    MAX-ACCESS  read-only
    STATUS      current
    DESCRIPTION
                "Character string value"
    ::= { controllerentry 14 }

fruCtlrPartnerId OBJECT-TYPE
    SYNTAX      DisplayString
    MAX-ACCESS  read-only
    STATUS      current
    DESCRIPTION
                "Character string value"
    ::= { controllerentry 15 }

fruCtlrCtState OBJECT-TYPE
    SYNTAX      DisplayString
    MAX-ACCESS  read-only
    STATUS      current
    DESCRIPTION
                "Character string value"
    ::= { controllerentry 16 }

fruCtlrCacheSize OBJECT-TYPE
    SYNTAX      DisplayString
    MAX-ACCESS  read-only
    STATUS      current
    DESCRIPTION
                "Character string value"
    ::= { controllerentry 17 }

fruCtlrTemp OBJECT-TYPE
    SYNTAX      DisplayString
    MAX-ACCESS  read-only
    STATUS      current
    DESCRIPTION
                "Character string value"
    ::= { controllerentry 18 }

fruCtlrIsExpendable OBJECT-TYPE
    SYNTAX      DisplayString
    MAX-ACCESS  read-only
    STATUS      current
    DESCRIPTION
                "Character string value"
    ::= { controllerentry 19 }

loopcards	OBJECT IDENTIFIER ::= { t300 7 }

loopcardstable OBJECT-TYPE
    SYNTAX      SEQUENCE OF Loopcardsentry
    MAX-ACCESS  not-accessible
    STATUS      current
    DESCRIPTION
                "MIB tree branch"
    ::= { loopcards 1 }

loopcardsentry OBJECT-TYPE
    SYNTAX      Loopcardsentry
    MAX-ACCESS  not-accessible
    STATUS      current
    DESCRIPTION
                "MIB tree branch"
    INDEX  { entryno }
    ::= { loopcardstable 1 }

Loopcardsentry ::=
    SEQUENCE {
        loopcardsentryentryno
            DisplayString,
        loopcardsentrysunSmTreeProp
            DisplayString,
        loopcardsentrysunSmNodeName
            DisplayString
    }

loopcardsentryentryno OBJECT-TYPE
    SYNTAX      DisplayString
    MAX-ACCESS  read-only
    STATUS      current
    DESCRIPTION
                "Character string value"
    ::= { loopcardsentry 1 }

loopcardsentrysunSmTreeProp OBJECT-TYPE
    SYNTAX      DisplayString
    MAX-ACCESS  read-only
    STATUS      current
    DESCRIPTION
                "Character string value"
    ::= { loopcardsentry 2 }

loopcardsentrysunSmNodeName OBJECT-TYPE
    SYNTAX      DisplayString
    MAX-ACCESS  read-only
    STATUS      current
    DESCRIPTION
                "Character string value"
    ::= { loopcardsentry 3 }

loopcard	OBJECT IDENTIFIER ::= { t300 8 }

loopcardtable OBJECT-TYPE
    SYNTAX      SEQUENCE OF Loopcardentry
    MAX-ACCESS  not-accessible
    STATUS      current
    DESCRIPTION
                "MIB tree branch"
    ::= { loopcard 1 }

loopcardentry OBJECT-TYPE
    SYNTAX      Loopcardentry
    MAX-ACCESS  not-accessible
    STATUS      current
    DESCRIPTION
                "MIB tree branch"
    INDEX  { loopcardentryt300name,
              loopcardentryunitId,
              loopcardentryfruId }
    ::= { loopcardtable 1 }

Loopcardentry ::=
    SEQUENCE {
        loopcardentryt300name
            DisplayString,
        loopcardentryunitId
            DisplayString,
        loopcardentryfruId
            DisplayString,
        loopcardentrysunSmTreeProp
            DisplayString,
        loopcardentrysunSmNodeName
            DisplayString,
        loopcardentryfruStatus
            DisplayString,
        loopcardentryfruState
            DisplayString,
        loopcardentryfruVendor
            DisplayString,
        loopcardentryfruModel
            DisplayString,
        loopcardentryfruRevision
            DisplayString,
        loopcardentryfruSerialNo
            DisplayString,
        loopcardentryfruErrors
            DisplayString,
        fruLoopMode
            DisplayString,
        fruLoopCable1State
            DisplayString,
        fruLoopCable2State
            DisplayString,
        fruLoopTemp
            DisplayString
    }

loopcardentryt300name OBJECT-TYPE
    SYNTAX      DisplayString
    MAX-ACCESS  read-only
    STATUS      current
    DESCRIPTION
                "Character string value"
    ::= { loopcardentry 1 }

loopcardentryunitId OBJECT-TYPE
    SYNTAX      DisplayString
    MAX-ACCESS  read-only
    STATUS      current
    DESCRIPTION
                "Character string value"
    ::= { loopcardentry 2 }

loopcardentryfruId OBJECT-TYPE
    SYNTAX      DisplayString
    MAX-ACCESS  read-only
    STATUS      current
    DESCRIPTION
                "Character string value"
    ::= { loopcardentry 3 }

loopcardentrysunSmTreeProp OBJECT-TYPE
    SYNTAX      DisplayString
    MAX-ACCESS  read-only
    STATUS      current
    DESCRIPTION
                "Character string value"
    ::= { loopcardentry 4 }

loopcardentrysunSmNodeName OBJECT-TYPE
    SYNTAX      DisplayString
    MAX-ACCESS  read-only
    STATUS      current
    DESCRIPTION
                "Character string value"
    ::= { loopcardentry 5 }

loopcardentryfruStatus OBJECT-TYPE
    SYNTAX      DisplayString
    MAX-ACCESS  read-only
    STATUS      current
    DESCRIPTION
                "Character string value"
    ::= { loopcardentry 6 }

loopcardentryfruState OBJECT-TYPE
    SYNTAX      DisplayString
    MAX-ACCESS  read-only
    STATUS      current
    DESCRIPTION
                "Character string value"
    ::= { loopcardentry 7 }

loopcardentryfruVendor OBJECT-TYPE
    SYNTAX      DisplayString
    MAX-ACCESS  read-only
    STATUS      current
    DESCRIPTION
                "Character string value"
    ::= { loopcardentry 8 }

loopcardentryfruModel OBJECT-TYPE
    SYNTAX      DisplayString
    MAX-ACCESS  read-only
    STATUS      current
    DESCRIPTION
                "Character string value"
    ::= { loopcardentry 9 }

loopcardentryfruRevision OBJECT-TYPE
    SYNTAX      DisplayString
    MAX-ACCESS  read-only
    STATUS      current
    DESCRIPTION
                "Character string value"
    ::= { loopcardentry 10 }

loopcardentryfruSerialNo OBJECT-TYPE
    SYNTAX      DisplayString
    MAX-ACCESS  read-only
    STATUS      current
    DESCRIPTION
                "Character string value"
    ::= { loopcardentry 11 }

loopcardentryfruErrors OBJECT-TYPE
    SYNTAX      DisplayString
    MAX-ACCESS  read-only
    STATUS      current
    DESCRIPTION
                "Character string value"
    ::= { loopcardentry 12 }

fruLoopMode OBJECT-TYPE
    SYNTAX      DisplayString
    MAX-ACCESS  read-only
    STATUS      current
    DESCRIPTION
                "Character string value"
    ::= { loopcardentry 13 }

fruLoopCable1State OBJECT-TYPE
    SYNTAX      DisplayString
    MAX-ACCESS  read-only
    STATUS      current
    DESCRIPTION
                "Character string value"
    ::= { loopcardentry 14 }

fruLoopCable2State OBJECT-TYPE
    SYNTAX      DisplayString
    MAX-ACCESS  read-only
    STATUS      current
    DESCRIPTION
                "Character string value"
    ::= { loopcardentry 15 }

fruLoopTemp OBJECT-TYPE
    SYNTAX      DisplayString
    MAX-ACCESS  read-only
    STATUS      current
    DESCRIPTION
                "Character string value"
    ::= { loopcardentry 16 }

powerunits	OBJECT IDENTIFIER ::= { t300 9 }

powerunitstable OBJECT-TYPE
    SYNTAX      SEQUENCE OF Powerunitsentry
    MAX-ACCESS  not-accessible
    STATUS      current
    DESCRIPTION
                "MIB tree branch"
    ::= { powerunits 1 }

powerunitsentry OBJECT-TYPE
    SYNTAX      Powerunitsentry
    MAX-ACCESS  not-accessible
    STATUS      current
    DESCRIPTION
                "MIB tree branch"
    INDEX  { powerunitentryno }
    ::= { powerunitstable 1 }

Powerunitsentry ::=
    SEQUENCE {
        powerunitentryno
            DisplayString,
        powerunitsunSmTreeProp
            DisplayString,
        powerunitsunSmNodeName
            DisplayString
    }

powerunitentryno OBJECT-TYPE
    SYNTAX      DisplayString
    MAX-ACCESS  read-only
    STATUS      current
    DESCRIPTION
                "Character string value"
    ::= { powerunitsentry 1 }

powerunitsunSmTreeProp OBJECT-TYPE
    SYNTAX      DisplayString
    MAX-ACCESS  read-only
    STATUS      current
    DESCRIPTION
                "Character string value"
    ::= { powerunitsentry 2 }

powerunitsunSmNodeName OBJECT-TYPE
    SYNTAX      DisplayString
    MAX-ACCESS  read-only
    STATUS      current
    DESCRIPTION
                "Character string value"
    ::= { powerunitsentry 3 }

powercoolingunit	OBJECT IDENTIFIER ::= { t300 10 }

powercoolingunittable OBJECT-TYPE
    SYNTAX      SEQUENCE OF Powercoolingunitentry
    MAX-ACCESS  not-accessible
    STATUS      current
    DESCRIPTION
                "MIB tree branch"
    ::= { powercoolingunit 1 }

powercoolingunitentry OBJECT-TYPE
    SYNTAX      Powercoolingunitentry
    MAX-ACCESS  not-accessible
    STATUS      current
    DESCRIPTION
                "MIB tree branch"
    INDEX  { powercoolingunitentryt300name,
              powercoolingunitentryunitId,
              powercoolingunitentryfruId }
    ::= { powercoolingunittable 1 }

Powercoolingunitentry ::=
    SEQUENCE {
        powercoolingunitentryt300name
            DisplayString,
        powercoolingunitentryunitId
            DisplayString,
        powercoolingunitentryfruId
            DisplayString,
        powercoolingunitentrysunSmTreeProp
            DisplayString,
        powercoolingunitentrysunSmNodeName
            DisplayString,
        powercoolingunitentryfruStatus
            DisplayString,
        powercoolingunitentryfruState
            DisplayString,
        powercoolingunitentryfruVendor
            DisplayString,
        powercoolingunitentryfruModel
            DisplayString,
        powercoolingunitentryfruRevision
            DisplayString,
        powercoolingunitentryfruSerialNo
            DisplayString,
        powercoolingunitentryfruErrors
            DisplayString,
        fruPowerPowOutput
            DisplayString,
        fruPowerPowSource
            DisplayString,
        fruPowerPowTemp
            DisplayString,
        fruPowerFan1State
            DisplayString,
        fruPowerFan2State
            DisplayString,
        fruPowerBatState
            DisplayString,
        fruPowerBatLife
            DisplayString,
        fruPowerBatUsed
            DisplayString
    }

powercoolingunitentryt300name OBJECT-TYPE
    SYNTAX      DisplayString
    MAX-ACCESS  read-only
    STATUS      current
    DESCRIPTION
                "Character string value"
    ::= { powercoolingunitentry 1 }

powercoolingunitentryunitId OBJECT-TYPE
    SYNTAX      DisplayString
    MAX-ACCESS  read-only
    STATUS      current
    DESCRIPTION
                "Character string value"
    ::= { powercoolingunitentry 2 }

powercoolingunitentryfruId OBJECT-TYPE
    SYNTAX      DisplayString
    MAX-ACCESS  read-only
    STATUS      current
    DESCRIPTION
                "Character string value"
    ::= { powercoolingunitentry 3 }

powercoolingunitentrysunSmTreeProp OBJECT-TYPE
    SYNTAX      DisplayString
    MAX-ACCESS  read-only
    STATUS      current
    DESCRIPTION
                "Character string value"
    ::= { powercoolingunitentry 4 }

powercoolingunitentrysunSmNodeName OBJECT-TYPE
    SYNTAX      DisplayString
    MAX-ACCESS  read-only
    STATUS      current
    DESCRIPTION
                "Character string value"
    ::= { powercoolingunitentry 5 }

powercoolingunitentryfruStatus OBJECT-TYPE
    SYNTAX      DisplayString
    MAX-ACCESS  read-only
    STATUS      current
    DESCRIPTION
                "Character string value"
    ::= { powercoolingunitentry 6 }

powercoolingunitentryfruState OBJECT-TYPE
    SYNTAX      DisplayString
    MAX-ACCESS  read-only
    STATUS      current
    DESCRIPTION
                "Character string value"
    ::= { powercoolingunitentry 7 }

powercoolingunitentryfruVendor OBJECT-TYPE
    SYNTAX      DisplayString
    MAX-ACCESS  read-only
    STATUS      current
    DESCRIPTION
                "Character string value"
    ::= { powercoolingunitentry 8 }

powercoolingunitentryfruModel OBJECT-TYPE
    SYNTAX      DisplayString
    MAX-ACCESS  read-only
    STATUS      current
    DESCRIPTION
                "Character string value"
    ::= { powercoolingunitentry 9 }

powercoolingunitentryfruRevision OBJECT-TYPE
    SYNTAX      DisplayString
    MAX-ACCESS  read-only
    STATUS      current
    DESCRIPTION
                "Character string value"
    ::= { powercoolingunitentry 10 }

powercoolingunitentryfruSerialNo OBJECT-TYPE
    SYNTAX      DisplayString
    MAX-ACCESS  read-only
    STATUS      current
    DESCRIPTION
                "Character string value"
    ::= { powercoolingunitentry 11 }

powercoolingunitentryfruErrors OBJECT-TYPE
    SYNTAX      DisplayString
    MAX-ACCESS  read-only
    STATUS      current
    DESCRIPTION
                "Character string value"
    ::= { powercoolingunitentry 12 }

fruPowerPowOutput OBJECT-TYPE
    SYNTAX      DisplayString
    MAX-ACCESS  read-only
    STATUS      current
    DESCRIPTION
                "Character string value"
    ::= { powercoolingunitentry 13 }

fruPowerPowSource OBJECT-TYPE
    SYNTAX      DisplayString
    MAX-ACCESS  read-only
    STATUS      current
    DESCRIPTION
                "Character string value"
    ::= { powercoolingunitentry 14 }

fruPowerPowTemp OBJECT-TYPE
    SYNTAX      DisplayString
    MAX-ACCESS  read-only
    STATUS      current
    DESCRIPTION
                "Character string value"
    ::= { powercoolingunitentry 15 }

fruPowerFan1State OBJECT-TYPE
    SYNTAX      DisplayString
    MAX-ACCESS  read-only
    STATUS      current
    DESCRIPTION
                "Character string value"
    ::= { powercoolingunitentry 16 }

fruPowerFan2State OBJECT-TYPE
    SYNTAX      DisplayString
    MAX-ACCESS  read-only
    STATUS      current
    DESCRIPTION
                "Character string value"
    ::= { powercoolingunitentry 17 }

fruPowerBatState OBJECT-TYPE
    SYNTAX      DisplayString
    MAX-ACCESS  read-only
    STATUS      current
    DESCRIPTION
                "Character string value"
    ::= { powercoolingunitentry 18 }

fruPowerBatLife OBJECT-TYPE
    SYNTAX      DisplayString
    MAX-ACCESS  read-only
    STATUS      current
    DESCRIPTION
                "Character string value"
    ::= { powercoolingunitentry 19 }

fruPowerBatUsed OBJECT-TYPE
    SYNTAX      DisplayString
    MAX-ACCESS  read-only
    STATUS      current
    DESCRIPTION
                "Character string value"
    ::= { powercoolingunitentry 20 }

midplanes	OBJECT IDENTIFIER ::= { t300 11 }

midplanestable OBJECT-TYPE
    SYNTAX      SEQUENCE OF Midplanesentry
    MAX-ACCESS  not-accessible
    STATUS      current
    DESCRIPTION
                "MIB tree branch"
    ::= { midplanes 1 }

midplanesentry OBJECT-TYPE
    SYNTAX      Midplanesentry
    MAX-ACCESS  not-accessible
    STATUS      current
    DESCRIPTION
                "MIB tree branch"
    INDEX  { entryno }
    ::= { midplanestable 1 }

Midplanesentry ::=
    SEQUENCE {
        midplanesentryentryno
            DisplayString,
        midplanesentrysunSmTreeProp
            DisplayString,
        midplanesentrysunSmNodeName
            DisplayString
    }

midplanesentryentryno OBJECT-TYPE
    SYNTAX      DisplayString
    MAX-ACCESS  read-only
    STATUS      current
    DESCRIPTION
                "Character string value"
    ::= { midplanesentry 1 }

midplanesentrysunSmTreeProp OBJECT-TYPE
    SYNTAX      DisplayString
    MAX-ACCESS  read-only
    STATUS      current
    DESCRIPTION
                "Character string value"
    ::= { midplanesentry 2 }

midplanesentrysunSmNodeName OBJECT-TYPE
    SYNTAX      DisplayString
    MAX-ACCESS  read-only
    STATUS      current
    DESCRIPTION
                "Character string value"
    ::= { midplanesentry 3 }

midplane	OBJECT IDENTIFIER ::= { t300 12 }

midplanetable OBJECT-TYPE
    SYNTAX      SEQUENCE OF Midplaneentry
    MAX-ACCESS  not-accessible
    STATUS      current
    DESCRIPTION
                "MIB tree branch"
    ::= { midplane 1 }

midplaneentry OBJECT-TYPE
    SYNTAX      Midplaneentry
    MAX-ACCESS  not-accessible
    STATUS      current
    DESCRIPTION
                "MIB tree branch"
    INDEX  { midplaneentryt300name,
              unitId,
              midplaneentryfruId }
    ::= { midplanetable 1 }

Midplaneentry ::=
    SEQUENCE {
        midplaneentryt300name
            DisplayString,
        midplaneentryunitId
            DisplayString,
        midplaneentryfruId
            DisplayString,
        midplaneentrysunSmTreeProp
            DisplayString,
        midplaneentrysunSmNodeName
            DisplayString,
        midplaneentryfruStatus
            DisplayString,
        midplaneentryfruState
            DisplayString,
        midplaneentryfruVendor
            DisplayString,
        midplaneentryfruModel
            DisplayString,
        midplaneentryfruRevision
            DisplayString,
        midplaneentryfruSerialNo
            DisplayString,
        midplaneentryfruErrors
            DisplayString
    }

midplaneentryt300name OBJECT-TYPE
    SYNTAX      DisplayString
    MAX-ACCESS  read-only
    STATUS      current
    DESCRIPTION
                "Character string value"
    ::= { midplaneentry 1 }

midplaneentryunitId OBJECT-TYPE
    SYNTAX      DisplayString
    MAX-ACCESS  read-only
    STATUS      current
    DESCRIPTION
                "Character string value"
    ::= { midplaneentry 2 }

midplaneentryfruId OBJECT-TYPE
    SYNTAX      DisplayString
    MAX-ACCESS  read-only
    STATUS      current
    DESCRIPTION
                "Character string value"
    ::= { midplaneentry 3 }

midplaneentrysunSmTreeProp OBJECT-TYPE
    SYNTAX      DisplayString
    MAX-ACCESS  read-only
    STATUS      current
    DESCRIPTION
                "Character string value"
    ::= { midplaneentry 4 }

midplaneentrysunSmNodeName OBJECT-TYPE
    SYNTAX      DisplayString
    MAX-ACCESS  read-only
    STATUS      current
    DESCRIPTION
                "Character string value"
    ::= { midplaneentry 5 }

midplaneentryfruStatus OBJECT-TYPE
    SYNTAX      DisplayString
    MAX-ACCESS  read-only
    STATUS      current
    DESCRIPTION
                "Character string value"
    ::= { midplaneentry 6 }

midplaneentryfruState OBJECT-TYPE
    SYNTAX      DisplayString
    MAX-ACCESS  read-only
    STATUS      current
    DESCRIPTION
                "Character string value"
    ::= { midplaneentry 7 }

midplaneentryfruVendor OBJECT-TYPE
    SYNTAX      DisplayString
    MAX-ACCESS  read-only
    STATUS      current
    DESCRIPTION
                "Character string value"
    ::= { midplaneentry 8 }

midplaneentryfruModel OBJECT-TYPE
    SYNTAX      DisplayString
    MAX-ACCESS  read-only
    STATUS      current
    DESCRIPTION
                "Character string value"
    ::= { midplaneentry 9 }

midplaneentryfruRevision OBJECT-TYPE
    SYNTAX      DisplayString
    MAX-ACCESS  read-only
    STATUS      current
    DESCRIPTION
                "Character string value"
    ::= { midplaneentry 10 }

midplaneentryfruSerialNo OBJECT-TYPE
    SYNTAX      DisplayString
    MAX-ACCESS  read-only
    STATUS      current
    DESCRIPTION
                "Character string value"
    ::= { midplaneentry 11 }

midplaneentryfruErrors OBJECT-TYPE
    SYNTAX      DisplayString
    MAX-ACCESS  read-only
    STATUS      current
    DESCRIPTION
                "Character string value"
    ::= { midplaneentry 12 }

volumes	OBJECT IDENTIFIER ::= { t300 13 }

volumestable OBJECT-TYPE
    SYNTAX      SEQUENCE OF Volumesentry
    MAX-ACCESS  not-accessible
    STATUS      current
    DESCRIPTION
                "MIB tree branch"
    ::= { volumes 1 }

volumesentry OBJECT-TYPE
    SYNTAX      Volumesentry
    MAX-ACCESS  not-accessible
    STATUS      current
    DESCRIPTION
                "MIB tree branch"
    INDEX  { entryno }
    ::= { volumestable 1 }

Volumesentry ::=
    SEQUENCE {
        volumesentryentryno
            DisplayString,
        volumesentrysunSmTreeProp
            DisplayString,
        volumesentrysunSmNodeName
            DisplayString
    }

volumesentryentryno OBJECT-TYPE
    SYNTAX      DisplayString
    MAX-ACCESS  read-only
    STATUS      current
    DESCRIPTION
                "Character string value"
    ::= { volumesentry 1 }

volumesentrysunSmTreeProp OBJECT-TYPE
    SYNTAX      DisplayString
    MAX-ACCESS  read-only
    STATUS      current
    DESCRIPTION
                "Character string value"
    ::= { volumesentry 2 }

volumesentrysunSmNodeName OBJECT-TYPE
    SYNTAX      DisplayString
    MAX-ACCESS  read-only
    STATUS      current
    DESCRIPTION
                "Character string value"
    ::= { volumesentry 3 }

volume	OBJECT IDENTIFIER ::= { t300 14 }

volumebasictable OBJECT-TYPE
    SYNTAX      SEQUENCE OF Basicentry
    MAX-ACCESS  not-accessible
    STATUS      current
    DESCRIPTION
                "MIB tree branch"
    ::= { volume 1 }

volumebasicentry OBJECT-TYPE
    SYNTAX      Basicentry
    MAX-ACCESS  not-accessible
    STATUS      current
    DESCRIPTION
                "MIB tree branch"
    INDEX  { volumebasicentryt300name,
              volumebasicentryunitId,
              volumebasicentryvolId }
    ::= { volumebasictable 1 }

Basicentry ::=
    SEQUENCE {
        volumebasicentryt300name
            DisplayString,
        volumebasicentryunitId
            DisplayString,
        volumebasicentryvolId
            DisplayString,
        volumebasicentrysunSmTreeProp
            DisplayString,
        volumebasicentrysunSmNodeName
            DisplayString,
        volName
            DisplayString,
        volWWN
            DisplayString,
        volStatus
            DisplayString,
        volCacheMode
            DisplayString,
        volCacheMirror
            DisplayString,
        volCapacity
            DisplayString,
        volArrayWidth
            DisplayString,
        volRaidLevel
            DisplayString,
        volDisabledDisk
            DisplayString,
        volSubstitutedDisk
            DisplayString,
        volInitRate
            DisplayString,
        volVerifyRate
            DisplayString
    }

volumebasicentryt300name OBJECT-TYPE
    SYNTAX      DisplayString
    MAX-ACCESS  read-only
    STATUS      current
    DESCRIPTION
                "Character string value"
    ::= { volumebasicentry 1 }

volumebasicentryunitId OBJECT-TYPE
    SYNTAX      DisplayString
    MAX-ACCESS  read-only
    STATUS      current
    DESCRIPTION
                "Character string value"
    ::= { volumebasicentry 2 }

volumebasicentryvolId OBJECT-TYPE
    SYNTAX      DisplayString
    MAX-ACCESS  read-only
    STATUS      current
    DESCRIPTION
                "Character string value"
    ::= { volumebasicentry 3 }

volumebasicentrysunSmTreeProp OBJECT-TYPE
    SYNTAX      DisplayString
    MAX-ACCESS  read-only
    STATUS      current
    DESCRIPTION
                "Character string value"
    ::= { volumebasicentry 4 }

volumebasicentrysunSmNodeName OBJECT-TYPE
    SYNTAX      DisplayString
    MAX-ACCESS  read-only
    STATUS      current
    DESCRIPTION
                "Character string value"
    ::= { volumebasicentry 5 }

volName OBJECT-TYPE
    SYNTAX      DisplayString
    MAX-ACCESS  read-only
    STATUS      current
    DESCRIPTION
                "Character string value"
    ::= { volumebasicentry 6 }

volWWN OBJECT-TYPE
    SYNTAX      DisplayString
    MAX-ACCESS  read-only
    STATUS      current
    DESCRIPTION
                "Character string value"
    ::= { volumebasicentry 7 }

volStatus OBJECT-TYPE
    SYNTAX      DisplayString
    MAX-ACCESS  read-only
    STATUS      current
    DESCRIPTION
                "Character string value"
    ::= { volumebasicentry 8 }

volCacheMode OBJECT-TYPE
    SYNTAX      DisplayString
    MAX-ACCESS  read-only
    STATUS      current
    DESCRIPTION
                "Character string value"
    ::= { volumebasicentry 9 }

volCacheMirror OBJECT-TYPE
    SYNTAX      DisplayString
    MAX-ACCESS  read-only
    STATUS      current
    DESCRIPTION
                "Character string value"
    ::= { volumebasicentry 10 }

volCapacity OBJECT-TYPE
    SYNTAX      DisplayString
    MAX-ACCESS  read-only
    STATUS      current
    DESCRIPTION
                "Character string value"
    ::= { volumebasicentry 11 }

volArrayWidth OBJECT-TYPE
    SYNTAX      DisplayString
    MAX-ACCESS  read-only
    STATUS      current
    DESCRIPTION
                "Character string value"
    ::= { volumebasicentry 12 }

volRaidLevel OBJECT-TYPE
    SYNTAX      DisplayString
    MAX-ACCESS  read-only
    STATUS      current
    DESCRIPTION
                "Character string value"
    ::= { volumebasicentry 13 }

volDisabledDisk OBJECT-TYPE
    SYNTAX      DisplayString
    MAX-ACCESS  read-only
    STATUS      current
    DESCRIPTION
                "Character string value"
    ::= { volumebasicentry 14 }

volSubstitutedDisk OBJECT-TYPE
    SYNTAX      DisplayString
    MAX-ACCESS  read-only
    STATUS      current
    DESCRIPTION
                "Character string value"
    ::= { volumebasicentry 15 }

volInitRate OBJECT-TYPE
    SYNTAX      DisplayString
    MAX-ACCESS  read-only
    STATUS      current
    DESCRIPTION
                "Character string value"
    ::= { volumebasicentry 16 }

volVerifyRate OBJECT-TYPE
    SYNTAX      DisplayString
    MAX-ACCESS  read-only
    STATUS      current
    DESCRIPTION
                "Character string value"
    ::= { volumebasicentry 17 }

volumestatisticaltable OBJECT-TYPE
    SYNTAX      SEQUENCE OF Statisticalentry
    MAX-ACCESS  not-accessible
    STATUS      current
    DESCRIPTION
                "MIB tree branch"
    ::= { volume 2 }

volumestatisticalentry OBJECT-TYPE
    SYNTAX      Statisticalentry
    MAX-ACCESS  not-accessible
    STATUS      current
    DESCRIPTION
                "MIB tree branch"
    INDEX  { volumestatisticalentryt300name,
              volumestatisticalentryunitId,
              volumestatisticalentryvolId }
    ::= { volumestatisticaltable 1 }

Statisticalentry ::=
    SEQUENCE {
        volumestatisticalentryt300name
            DisplayString,
        volumestatisticalentryunitId
            DisplayString,
        volumestatisticalentryvolId
            DisplayString,
        volTotalRequests
            DisplayString,
        volWriteRequests
            DisplayString,
        volReadRequests
            DisplayString,
        volTotalBlocks
            DisplayString,
        volBlocksWritten
            DisplayString,
        volBlocksRead
            DisplayString,
        volSoftErrors
            DisplayString,
        volFirmErrors
            DisplayString,
        volHardErrors
            DisplayString,
        volCacheWriteHits
            DisplayString,
        volCacheWriteMisses
            DisplayString,
        volCacheReadHits
            DisplayString,
        volCacheReadMisses
            DisplayString,
        volCacheRmwFlushes
            DisplayString,
        volCacheReconFlushes
            DisplayString,
        volCacheStripeFlushes
            DisplayString,
        clearflag
            Integer32
    }

volumestatisticalentryt300name OBJECT-TYPE
    SYNTAX      DisplayString
    MAX-ACCESS  read-only
    STATUS      current
    DESCRIPTION
                "Character string value"
    ::= { volumestatisticalentry 1 }

volumestatisticalentryunitId OBJECT-TYPE
    SYNTAX      DisplayString
    MAX-ACCESS  read-only
    STATUS      current
    DESCRIPTION
                "Character string value"
    ::= { volumestatisticalentry 2 }

volumestatisticalentryvolId OBJECT-TYPE
    SYNTAX      DisplayString
    MAX-ACCESS  read-only
    STATUS      current
    DESCRIPTION
                "Character string value"
    ::= { volumestatisticalentry 3 }

volTotalRequests OBJECT-TYPE
    SYNTAX      DisplayString
    MAX-ACCESS  read-only
    STATUS      current
    DESCRIPTION
                "Character string value"
    ::= { volumestatisticalentry 4 }

volWriteRequests OBJECT-TYPE
    SYNTAX      DisplayString
    MAX-ACCESS  read-only
    STATUS      current
    DESCRIPTION
                "Character string value"
    ::= { volumestatisticalentry 5 }

volReadRequests OBJECT-TYPE
    SYNTAX      DisplayString
    MAX-ACCESS  read-only
    STATUS      current
    DESCRIPTION
                "Character string value"
    ::= { volumestatisticalentry 6 }

volTotalBlocks OBJECT-TYPE
    SYNTAX      DisplayString
    MAX-ACCESS  read-only
    STATUS      current
    DESCRIPTION
                "Character string value"
    ::= { volumestatisticalentry 7 }

volBlocksWritten OBJECT-TYPE
    SYNTAX      DisplayString
    MAX-ACCESS  read-only
    STATUS      current
    DESCRIPTION
                "Character string value"
    ::= { volumestatisticalentry 8 }

volBlocksRead OBJECT-TYPE
    SYNTAX      DisplayString
    MAX-ACCESS  read-only
    STATUS      current
    DESCRIPTION
                "Character string value"
    ::= { volumestatisticalentry 9 }

volSoftErrors OBJECT-TYPE
    SYNTAX      DisplayString
    MAX-ACCESS  read-only
    STATUS      current
    DESCRIPTION
                "Character string value"
    ::= { volumestatisticalentry 10 }

volFirmErrors OBJECT-TYPE
    SYNTAX      DisplayString
    MAX-ACCESS  read-only
    STATUS      current
    DESCRIPTION
                "Character string value"
    ::= { volumestatisticalentry 11 }

volHardErrors OBJECT-TYPE
    SYNTAX      DisplayString
    MAX-ACCESS  read-only
    STATUS      current
    DESCRIPTION
                "Character string value"
    ::= { volumestatisticalentry 12 }

volCacheWriteHits OBJECT-TYPE
    SYNTAX      DisplayString
    MAX-ACCESS  read-only
    STATUS      current
    DESCRIPTION
                "Character string value"
    ::= { volumestatisticalentry 13 }

volCacheWriteMisses OBJECT-TYPE
    SYNTAX      DisplayString
    MAX-ACCESS  read-only
    STATUS      current
    DESCRIPTION
                "Character string value"
    ::= { volumestatisticalentry 14 }

volCacheReadHits OBJECT-TYPE
    SYNTAX      DisplayString
    MAX-ACCESS  read-only
    STATUS      current
    DESCRIPTION
                "Character string value"
    ::= { volumestatisticalentry 15 }

volCacheReadMisses OBJECT-TYPE
    SYNTAX      DisplayString
    MAX-ACCESS  read-only
    STATUS      current
    DESCRIPTION
                "Character string value"
    ::= { volumestatisticalentry 16 }

volCacheRmwFlushes OBJECT-TYPE
    SYNTAX      DisplayString
    MAX-ACCESS  read-only
    STATUS      current
    DESCRIPTION
                "Character string value"
    ::= { volumestatisticalentry 17 }

volCacheReconFlushes OBJECT-TYPE
    SYNTAX      DisplayString
    MAX-ACCESS  read-only
    STATUS      current
    DESCRIPTION
                "Character string value"
    ::= { volumestatisticalentry 18 }

volCacheStripeFlushes OBJECT-TYPE
    SYNTAX      DisplayString
    MAX-ACCESS  read-only
    STATUS      current
    DESCRIPTION
                "Character string value"
    ::= { volumestatisticalentry 19 }

clearflag OBJECT-TYPE
    SYNTAX      Integer32 (-2147483648..2147483647)
    MAX-ACCESS  read-write
    STATUS      current
    DESCRIPTION
                "Integer value"
    ::= { volumestatisticalentry 20 }

ports	OBJECT IDENTIFIER ::= { t300 15 }

portstable OBJECT-TYPE
    SYNTAX      SEQUENCE OF Portsentry
    MAX-ACCESS  not-accessible
    STATUS      current
    DESCRIPTION
                "MIB tree branch"
    ::= { ports 1 }

portsentry OBJECT-TYPE
    SYNTAX      Portsentry
    MAX-ACCESS  not-accessible
    STATUS      current
    DESCRIPTION
                "MIB tree branch"
    INDEX  { portsentryno }
    ::= { portstable 1 }

Portsentry ::=
    SEQUENCE {
        portsentryno
            DisplayString,
        portsentrysunSmTreeProp
            DisplayString,
        portsentrysunSmNodeName
            DisplayString
    }

portsentryno OBJECT-TYPE
    SYNTAX      DisplayString
    MAX-ACCESS  read-only
    STATUS      current
    DESCRIPTION
                "Character string value"
    ::= { portsentry 1 }

portsentrysunSmTreeProp OBJECT-TYPE
    SYNTAX      DisplayString
    MAX-ACCESS  read-only
    STATUS      current
    DESCRIPTION
                "Character string value"
    ::= { portsentry 2 }

portsentrysunSmNodeName OBJECT-TYPE
    SYNTAX      DisplayString
    MAX-ACCESS  read-only
    STATUS      current
    DESCRIPTION
                "Character string value"
    ::= { portsentry 3 }

port	OBJECT IDENTIFIER ::= { t300 16 }

portbasictable OBJECT-TYPE
    SYNTAX      SEQUENCE OF Basicentry
    MAX-ACCESS  not-accessible
    STATUS      current
    DESCRIPTION
                "MIB tree branch"
    ::= { port 1 }

portbasicentry OBJECT-TYPE
    SYNTAX      Basicentry
    MAX-ACCESS  not-accessible
    STATUS      current
    DESCRIPTION
                "MIB tree branch"
    INDEX  { portbasicentryt300name,
              portbasicentryunitId,
              portbasicentryportId }
    ::= { portbasictable 1 }

Basicentry ::=
    SEQUENCE {
        portbasicentryt300name
            DisplayString,
        portbasicentryunitId
            DisplayString,
        portbasicentryportId
            DisplayString,
        portbasicentrysunSmTreeProp
            DisplayString,
        portbasicentrysunSmNodeName
            DisplayString,
        portWWN
            DisplayString,
        portStatus
            DisplayString,
        portType
            DisplayString,
        portFruId
            DisplayString,
        portSunHost
            DisplayString,
        portFibreCount
            DisplayString,
        portFibreAlpaMode
            DisplayString,
        portFibreAlpa
            DisplayString
    }

portbasicentryt300name OBJECT-TYPE
    SYNTAX      DisplayString
    MAX-ACCESS  read-only
    STATUS      current
    DESCRIPTION
                "Character string value"
    ::= { portbasicentry 1 }

portbasicentryunitId OBJECT-TYPE
    SYNTAX      DisplayString
    MAX-ACCESS  read-only
    STATUS      current
    DESCRIPTION
                "Character string value"
    ::= { portbasicentry 2 }

portbasicentryportId OBJECT-TYPE
    SYNTAX      DisplayString
    MAX-ACCESS  read-only
    STATUS      current
    DESCRIPTION
                "Character string value"
    ::= { portbasicentry 3 }

sunSmTreeProp OBJECT-TYPE
    SYNTAX      DisplayString
    MAX-ACCESS  read-only
    STATUS      current
    DESCRIPTION
                "Character string value"
    ::= { portbasicentry 4 }

sunSmNodeName OBJECT-TYPE
    SYNTAX      DisplayString
    MAX-ACCESS  read-only
    STATUS      current
    DESCRIPTION
                "Character string value"
    ::= { portbasicentry 5 }

portWWN OBJECT-TYPE
    SYNTAX      DisplayString
    MAX-ACCESS  read-only
    STATUS      current
    DESCRIPTION
                "Character string value"
    ::= { portbasicentry 6 }

portStatus OBJECT-TYPE
    SYNTAX      DisplayString
    MAX-ACCESS  read-only
    STATUS      current
    DESCRIPTION
                "Character string value"
    ::= { portbasicentry 7 }

portType OBJECT-TYPE
    SYNTAX      DisplayString
    MAX-ACCESS  read-only
    STATUS      current
    DESCRIPTION
                "Character string value"
    ::= { portbasicentry 8 }

portFruId OBJECT-TYPE
    SYNTAX      DisplayString
    MAX-ACCESS  read-only
    STATUS      current
    DESCRIPTION
                "Character string value"
    ::= { portbasicentry 9 }

portSunHost OBJECT-TYPE
    SYNTAX      DisplayString
    MAX-ACCESS  read-only
    STATUS      current
    DESCRIPTION
                "Character string value"
    ::= { portbasicentry 10 }

portFibreCount OBJECT-TYPE
    SYNTAX      DisplayString
    MAX-ACCESS  read-only
    STATUS      current
    DESCRIPTION
                "Character string value"
    ::= { portbasicentry 11 }

portFibreAlpaMode OBJECT-TYPE
    SYNTAX      DisplayString
    MAX-ACCESS  read-only
    STATUS      current
    DESCRIPTION
                "Character string value"
    ::= { portbasicentry 12 }

portFibreAlpa OBJECT-TYPE
    SYNTAX      DisplayString
    MAX-ACCESS  read-only
    STATUS      current
    DESCRIPTION
                "Character string value"
    ::= { portbasicentry 13 }

portstatisticaltable OBJECT-TYPE
    SYNTAX      SEQUENCE OF Statisticalentry
    MAX-ACCESS  not-accessible
    STATUS      current
    DESCRIPTION
                "MIB tree branch"
    ::= { port 2 }

portstatisticalentry OBJECT-TYPE
    SYNTAX      Statisticalentry
    MAX-ACCESS  not-accessible
    STATUS      current
    DESCRIPTION
                "MIB tree branch"
    INDEX  { portstatisticalentryt300name,
              portstatisticalentryunitId,
              portstatisticalentryportId }
    ::= { portstatisticaltable 1 }

Statisticalentry ::=
    SEQUENCE {
        portstatisticalentryt300name
            DisplayString,
        portstatisticalentryunitId
            DisplayString,
        portstatisticalentryportId
            DisplayString,
        portTotalRequests
            DisplayString,
        portWriteRequests
            DisplayString,
        portReadRequests
            DisplayString,
        portTotalBlocks
            DisplayString,
        portBlocksWritten
            DisplayString,
        portBlocksRead
            DisplayString
    }

portstatisticalentryt300name OBJECT-TYPE
    SYNTAX      DisplayString
    MAX-ACCESS  read-only
    STATUS      current
    DESCRIPTION
                "Character string value"
    ::= { portstatisticalentry 1 }

portstatisticalentryunitId OBJECT-TYPE
    SYNTAX      DisplayString
    MAX-ACCESS  read-only
    STATUS      current
    DESCRIPTION
                "Character string value"
    ::= { portstatisticalentry 2 }

portstatisticalentryportId OBJECT-TYPE
    SYNTAX      DisplayString
    MAX-ACCESS  read-only
    STATUS      current
    DESCRIPTION
                "Character string value"
    ::= { portstatisticalentry 3 }

portTotalRequests OBJECT-TYPE
    SYNTAX      DisplayString
    MAX-ACCESS  read-only
    STATUS      current
    DESCRIPTION
                "Character string value"
    ::= { portstatisticalentry 4 }

portWriteRequests OBJECT-TYPE
    SYNTAX      DisplayString
    MAX-ACCESS  read-only
    STATUS      current
    DESCRIPTION
                "Character string value"
    ::= { portstatisticalentry 5 }

portReadRequests OBJECT-TYPE
    SYNTAX      DisplayString
    MAX-ACCESS  read-only
    STATUS      current
    DESCRIPTION
                "Character string value"
    ::= { portstatisticalentry 6 }

portTotalBlocks OBJECT-TYPE
    SYNTAX      DisplayString
    MAX-ACCESS  read-only
    STATUS      current
    DESCRIPTION
                "Character string value"
    ::= { portstatisticalentry 7 }

portBlocksWritten OBJECT-TYPE
    SYNTAX      DisplayString
    MAX-ACCESS  read-only
    STATUS      current
    DESCRIPTION
                "Character string value"
    ::= { portstatisticalentry 8 }

portBlocksRead OBJECT-TYPE
    SYNTAX      DisplayString
    MAX-ACCESS  read-only
    STATUS      current
    DESCRIPTION
                "Character string value"
    ::= { portstatisticalentry 9 }

attachments	OBJECT IDENTIFIER ::= { t300 17 }

attachmentstable OBJECT-TYPE
    SYNTAX      SEQUENCE OF Attachmentsentry
    MAX-ACCESS  not-accessible
    STATUS      current
    DESCRIPTION
                "MIB tree branch"
    ::= { attachments 1 }

attachmentsentry OBJECT-TYPE
    SYNTAX      Attachmentsentry
    MAX-ACCESS  not-accessible
    STATUS      current
    DESCRIPTION
                "MIB tree branch"
    INDEX  { attachmentsentryentryno }
    ::= { attachmentstable 1 }

Attachmentsentry ::=
    SEQUENCE {
        attachmentsentryentryno
            DisplayString,
        attachmentsentrysunSmTreeProp
            DisplayString,
        attachmentsentrysunSmNodeName
            DisplayString
    }

attachmentsentryentryno OBJECT-TYPE
    SYNTAX      DisplayString
    MAX-ACCESS  read-only
    STATUS      current
    DESCRIPTION
                "Character string value"
    ::= { attachmentsentry 1 }

attachmentsentrysunSmTreeProp OBJECT-TYPE
    SYNTAX      DisplayString
    MAX-ACCESS  read-only
    STATUS      current
    DESCRIPTION
                "Character string value"
    ::= { attachmentsentry 2 }

attachmentsentrysunSmNodeName OBJECT-TYPE
    SYNTAX      DisplayString
    MAX-ACCESS  read-only
    STATUS      current
    DESCRIPTION
                "Character string value"
    ::= { attachmentsentry 3 }

attachment	OBJECT IDENTIFIER ::= { t300 18 }

attachmenttable OBJECT-TYPE
    SYNTAX      SEQUENCE OF Attachmententry
    MAX-ACCESS  not-accessible
    STATUS      current
    DESCRIPTION
                "MIB tree branch"
    ::= { attachment 1 }

attachmententry OBJECT-TYPE
    SYNTAX      Attachmententry
    MAX-ACCESS  not-accessible
    STATUS      current
    DESCRIPTION
                "MIB tree branch"
    INDEX  { attachmententryt300name,
              attachmententryunitId,
              attachmententryportId,
              attachId }
    ::= { attachmenttable 1 }

Attachmententry ::=
    SEQUENCE {
        attachmententryt300name
            DisplayString,
        attachmententryunitId
            DisplayString,
        attachmententryportId
            DisplayString,
        attachId
            DisplayString,
        attachmententrysunSmTreeProp
            DisplayString,
        attachmententrysunSmNodeName
            DisplayString,
        attachLun
            DisplayString,
        attachMode
            DisplayString,
        attachVolId
            DisplayString,
        attachVolName
            DisplayString
    }

attachmententryt300name OBJECT-TYPE
    SYNTAX      DisplayString
    MAX-ACCESS  read-only
    STATUS      current
    DESCRIPTION
                "Character string value"
    ::= { attachmententry 1 }

attachmententryunitId OBJECT-TYPE
    SYNTAX      DisplayString
    MAX-ACCESS  read-only
    STATUS      current
    DESCRIPTION
                "Character string value"
    ::= { attachmententry 2 }

attachmententryportId OBJECT-TYPE
    SYNTAX      DisplayString
    MAX-ACCESS  read-only
    STATUS      current
    DESCRIPTION
                "Character string value"
    ::= { attachmententry 3 }

attachId OBJECT-TYPE
    SYNTAX      DisplayString
    MAX-ACCESS  read-only
    STATUS      current
    DESCRIPTION
                "Character string value"
    ::= { attachmententry 4 }

attachmententrysunSmTreeProp OBJECT-TYPE
    SYNTAX      DisplayString
    MAX-ACCESS  read-only
    STATUS      current
    DESCRIPTION
                "Character string value"
    ::= { attachmententry 5 }

attachmententrysunSmNodeName OBJECT-TYPE
    SYNTAX      DisplayString
    MAX-ACCESS  read-only
    STATUS      current
    DESCRIPTION
                "Character string value"
    ::= { attachmententry 6 }

attachLun OBJECT-TYPE
    SYNTAX      DisplayString
    MAX-ACCESS  read-only
    STATUS      current
    DESCRIPTION
                "Character string value"
    ::= { attachmententry 7 }

attachMode OBJECT-TYPE
    SYNTAX      DisplayString
    MAX-ACCESS  read-only
    STATUS      current
    DESCRIPTION
                "Character string value"
    ::= { attachmententry 8 }

attachVolId OBJECT-TYPE
    SYNTAX      DisplayString
    MAX-ACCESS  read-only
    STATUS      current
    DESCRIPTION
                "Character string value"
    ::= { attachmententry 9 }

attachVolName OBJECT-TYPE
    SYNTAX      DisplayString
    MAX-ACCESS  read-only
    STATUS      current
    DESCRIPTION
                "Character string value"
    ::= { attachmententry 10 }

loops	OBJECT IDENTIFIER ::= { t300 19 }

loopstable OBJECT-TYPE
    SYNTAX      SEQUENCE OF Loopsentry
    MAX-ACCESS  not-accessible
    STATUS      current
    DESCRIPTION
                "MIB tree branch"
    ::= { loops 1 }

loopsentry OBJECT-TYPE
    SYNTAX      Loopsentry
    MAX-ACCESS  not-accessible
    STATUS      current
    DESCRIPTION
                "MIB tree branch"
    INDEX  { loopsentryentryno }
    ::= { loopstable 1 }

Loopsentry ::=
    SEQUENCE {
        loopsentryentryno
            DisplayString,
        loopsentrysunSmTreeProp
            DisplayString,
        loopsentrysunSmNodeName
            DisplayString
    }

loopsentryentryno OBJECT-TYPE
    SYNTAX      DisplayString
    MAX-ACCESS  read-only
    STATUS      current
    DESCRIPTION
                "Character string value"
    ::= { loopsentry 1 }

loopsentrysunSmTreeProp OBJECT-TYPE
    SYNTAX      DisplayString
    MAX-ACCESS  read-only
    STATUS      current
    DESCRIPTION
                "Character string value"
    ::= { loopsentry 2 }

loopsentrysunSmNodeName OBJECT-TYPE
    SYNTAX      DisplayString
    MAX-ACCESS  read-only
    STATUS      current
    DESCRIPTION
                "Character string value"
    ::= { loopsentry 3 }

loop	OBJECT IDENTIFIER ::= { t300 20 }

looptable OBJECT-TYPE
    SYNTAX      SEQUENCE OF Loopentry
    MAX-ACCESS  not-accessible
    STATUS      current
    DESCRIPTION
                "MIB tree branch"
    ::= { loop 1 }

loopentry OBJECT-TYPE
    SYNTAX      Loopentry
    MAX-ACCESS  not-accessible
    STATUS      current
    DESCRIPTION
                "MIB tree branch"
    INDEX  { loopentryt300name,
              unitId,
              loopentryunitId }
    ::= { looptable 1 }

Loopentry ::=
    SEQUENCE {
        loopentryt300name
            DisplayString,
        loopentryunitId
            DisplayString,
        loopentryloopId
            DisplayString,
        loopentrysunSmTreeProp
            DisplayString,
        loopentrysunSmNodeName
            DisplayString,
        loopStatus
            DisplayString,
        loopMux
            DisplayString,
        loopIsAvailable
            DisplayString,
        loopIsReserved
            DisplayString,
        loopIsIsolated
            DisplayString,
        loopIsTop
            DisplayString,
        loopIsBottom
            DisplayString,
        loopIsMiddle
            DisplayString
    }

loopentryt300name OBJECT-TYPE
    SYNTAX      DisplayString
    MAX-ACCESS  read-only
    STATUS      current
    DESCRIPTION
                "Character string value"
    ::= { loopentry 1 }

loopentryunitId OBJECT-TYPE
    SYNTAX      DisplayString
    MAX-ACCESS  read-only
    STATUS      current
    DESCRIPTION
                "Character string value"
    ::= { loopentry 2 }

loopentryloopId OBJECT-TYPE
    SYNTAX      DisplayString
    MAX-ACCESS  read-only
    STATUS      current
    DESCRIPTION
                "Character string value"
    ::= { loopentry 3 }

loopentrysunSmTreeProp OBJECT-TYPE
    SYNTAX      DisplayString
    MAX-ACCESS  read-only
    STATUS      current
    DESCRIPTION
                "Character string value"
    ::= { loopentry 4 }

loopentrysunSmNodeName OBJECT-TYPE
    SYNTAX      DisplayString
    MAX-ACCESS  read-only
    STATUS      current
    DESCRIPTION
                "Character string value"
    ::= { loopentry 5 }

loopStatus OBJECT-TYPE
    SYNTAX      DisplayString
    MAX-ACCESS  read-only
    STATUS      current
    DESCRIPTION
                "Character string value"
    ::= { loopentry 6 }

loopMux OBJECT-TYPE
    SYNTAX      DisplayString
    MAX-ACCESS  read-only
    STATUS      current
    DESCRIPTION
                "Character string value"
    ::= { loopentry 7 }

loopIsAvailable OBJECT-TYPE
    SYNTAX      DisplayString
    MAX-ACCESS  read-only
    STATUS      current
    DESCRIPTION
                "Character string value"
    ::= { loopentry 8 }

loopIsReserved OBJECT-TYPE
    SYNTAX      DisplayString
    MAX-ACCESS  read-only
    STATUS      current
    DESCRIPTION
                "Character string value"
    ::= { loopentry 9 }

loopIsIsolated OBJECT-TYPE
    SYNTAX      DisplayString
    MAX-ACCESS  read-only
    STATUS      current
    DESCRIPTION
                "Character string value"
    ::= { loopentry 10 }

loopIsTop OBJECT-TYPE
    SYNTAX      DisplayString
    MAX-ACCESS  read-only
    STATUS      current
    DESCRIPTION
                "Character string value"
    ::= { loopentry 11 }

loopIsBottom OBJECT-TYPE
    SYNTAX      DisplayString
    MAX-ACCESS  read-only
    STATUS      current
    DESCRIPTION
                "Character string value"
    ::= { loopentry 12 }

loopIsMiddle OBJECT-TYPE
    SYNTAX      DisplayString
    MAX-ACCESS  read-only
    STATUS      current
    DESCRIPTION
                "Character string value"
    ::= { loopentry 13 }

logging	OBJECT IDENTIFIER ::= { t300 21 }

loggingtable OBJECT-TYPE
    SYNTAX      SEQUENCE OF Loggingentry
    MAX-ACCESS  not-accessible
    STATUS      current
    DESCRIPTION
                "MIB tree branch"
    ::= { logging 1 }

loggingentry OBJECT-TYPE
    SYNTAX      Loggingentry
    MAX-ACCESS  not-accessible
    STATUS      current
    DESCRIPTION
                "MIB tree branch"
    INDEX  { loggingentryt300name }
    ::= { loggingtable 1 }

Loggingentry ::=
    SEQUENCE {
        loggingentryt300name
            DisplayString,
        loggingentrysunSmTreeProp
            DisplayString,
        loggingentrysunSmNodeName
            DisplayString,
        loggingentryrowstatus
            RowStatus,
        logStatus
            DisplayString,
        logPort
            DisplayString,
        logTo
            DisplayString,
        logLevel
            DisplayString
    }

loggingentryt300name OBJECT-TYPE
    SYNTAX      DisplayString
    MAX-ACCESS  read-only
    STATUS      current
    DESCRIPTION
                "Character string value"
    ::= { loggingentry 1 }

loggingentrysunSmTreeProp OBJECT-TYPE
    SYNTAX      DisplayString
    MAX-ACCESS  read-only
    STATUS      current
    DESCRIPTION
                "Character string value"
    ::= { loggingentry 2 }

loggingentrysunSmNodeName OBJECT-TYPE
    SYNTAX      DisplayString
    MAX-ACCESS  read-only
    STATUS      current
    DESCRIPTION
                "Character string value"
    ::= { loggingentry 3 }

loggingentryrowstatus OBJECT-TYPE
    SYNTAX      RowStatus
    MAX-ACCESS  read-write
    STATUS      current
    DESCRIPTION
                "Table row status"
    ::= { loggingentry 4 }

logStatus OBJECT-TYPE
    SYNTAX      DisplayString
    MAX-ACCESS  read-only
    STATUS      current
    DESCRIPTION
                "Character string value"
    ::= { loggingentry 5 }

logPort OBJECT-TYPE
    SYNTAX      DisplayString
    MAX-ACCESS  read-write
    STATUS      current
    DESCRIPTION
                "Character string value"
    ::= { loggingentry 6 }

logTo OBJECT-TYPE
    SYNTAX      DisplayString
    MAX-ACCESS  read-write
    STATUS      current
    DESCRIPTION
                "Character string value"
    ::= { loggingentry 7 }

logLevel OBJECT-TYPE
    SYNTAX      DisplayString
    MAX-ACCESS  read-write
    STATUS      current
    DESCRIPTION
                "Character string value"
    ::= { loggingentry 8 }

t300rules	OBJECT IDENTIFIER ::= { t300 22 }

rple201 OBJECT-TYPE
    SYNTAX      DisplayString
    MAX-ACCESS  read-only
    STATUS      current
    DESCRIPTION
                "No Data Value"
    ::= { t300rules 1 }

rple202 OBJECT-TYPE
    SYNTAX      DisplayString
    MAX-ACCESS  read-only
    STATUS      current
    DESCRIPTION
                "No Data Value"
    ::= { t300rules 2 }

rple203 OBJECT-TYPE
    SYNTAX      DisplayString
    MAX-ACCESS  read-only
    STATUS      current
    DESCRIPTION
                "No Data Value"
    ::= { t300rules 3 }

rple204 OBJECT-TYPE
    SYNTAX      DisplayString
    MAX-ACCESS  read-only
    STATUS      current
    DESCRIPTION
                "No Data Value"
    ::= { t300rules 4 }

rple205 OBJECT-TYPE
    SYNTAX      DisplayString
    MAX-ACCESS  read-only
    STATUS      current
    DESCRIPTION
                "No Data Value"
    ::= { t300rules 5 }

rple206 OBJECT-TYPE
    SYNTAX      DisplayString
    MAX-ACCESS  read-only
    STATUS      current
    DESCRIPTION
                "No Data Value"
    ::= { t300rules 6 }

rple207 OBJECT-TYPE
    SYNTAX      DisplayString
    MAX-ACCESS  read-only
    STATUS      current
    DESCRIPTION
                "No Data Value"
    ::= { t300rules 7 }

rple208 OBJECT-TYPE
    SYNTAX      DisplayString
    MAX-ACCESS  read-only
    STATUS      current
    DESCRIPTION
                "No Data Value"
    ::= { t300rules 8 }

rple220 OBJECT-TYPE
    SYNTAX      DisplayString
    MAX-ACCESS  read-only
    STATUS      current
    DESCRIPTION
                "No Data Value"
    ::= { t300rules 9 }

rple221 OBJECT-TYPE
    SYNTAX      DisplayString
    MAX-ACCESS  read-only
    STATUS      current
    DESCRIPTION
                "No Data Value"
    ::= { t300rules 10 }

rple222 OBJECT-TYPE
    SYNTAX      DisplayString
    MAX-ACCESS  read-only
    STATUS      current
    DESCRIPTION
                "No Data Value"
    ::= { t300rules 11 }

rple223 OBJECT-TYPE
    SYNTAX      DisplayString
    MAX-ACCESS  read-only
    STATUS      current
    DESCRIPTION
                "No Data Value"
    ::= { t300rules 12 }

rple224 OBJECT-TYPE
    SYNTAX      DisplayString
    MAX-ACCESS  read-only
    STATUS      current
    DESCRIPTION
                "No Data Value"
    ::= { t300rules 13 }

rple225 OBJECT-TYPE
    SYNTAX      DisplayString
    MAX-ACCESS  read-only
    STATUS      current
    DESCRIPTION
                "No Data Value"
    ::= { t300rules 14 }

rple226 OBJECT-TYPE
    SYNTAX      DisplayString
    MAX-ACCESS  read-only
    STATUS      current
    DESCRIPTION
                "No Data Value"
    ::= { t300rules 15 }

rple227 OBJECT-TYPE
    SYNTAX      DisplayString
    MAX-ACCESS  read-only
    STATUS      current
    DESCRIPTION
                "No Data Value"
    ::= { t300rules 16 }
END
