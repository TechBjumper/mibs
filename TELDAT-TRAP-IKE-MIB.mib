-- file automatically created


TELDAT-TRAP-IKE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ikeTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IKE event subsystem."
    REVISION "201401200930Z"
    DESCRIPTION "Initial implementation"
        ::= { telEventTraps 176 }


ikeEventsGroup	OBJECT IDENTIFIER	::= { ikeTrapsMIB 1 }

ikeNotifications	OBJECT IDENTIFIER	::= { ikeTrapsMIB 2 }
ikeNotificationsPrefix	OBJECT IDENTIFIER	::= { ikeNotifications 0 }

ikeEventObjects1 OBJECT-IDENTITY
    STATUS current
    DESCRIPTION
        "Event IKE.1
        Matching template."
    ::= { ikeEventsGroup 1 }

ike1-remote-addr OBJECT-TYPE
    SYNTAX IpAddress
    MAX-ACCESS accessible-for-notify
    STATUS current
    DESCRIPTION
        "Parameter 'remote-addr' in event IKE.1"
    ::= { ikeEventObjects1 1 }

ike1-template-number OBJECT-TYPE
    SYNTAX Integer32
    MAX-ACCESS accessible-for-notify
    STATUS current
    DESCRIPTION
        "Parameter 'template-number' in event IKE.1"
    ::= { ikeEventObjects1 2 }

ikeEventObjects2 OBJECT-IDENTITY
    STATUS current
    DESCRIPTION
        "Event IKE.2
        Matching SA for negotiation."
    ::= { ikeEventsGroup 2 }

ike2-remote-addr OBJECT-TYPE
    SYNTAX IpAddress
    MAX-ACCESS accessible-for-notify
    STATUS current
    DESCRIPTION
        "Parameter 'remote-addr' in event IKE.2"
    ::= { ikeEventObjects2 1 }

ike2-connection OBJECT-TYPE
    SYNTAX Integer32
    MAX-ACCESS accessible-for-notify
    STATUS current
    DESCRIPTION
        "Parameter 'connection' in event IKE.2"
    ::= { ikeEventObjects2 2 }

ikeEventObjects3 OBJECT-IDENTITY
    STATUS current
    DESCRIPTION
        "Event IKE.3
        There was an error decrypting the message."
    ::= { ikeEventsGroup 3 }

ike3-remote-addr OBJECT-TYPE
    SYNTAX IpAddress
    MAX-ACCESS accessible-for-notify
    STATUS current
    DESCRIPTION
        "Parameter 'remote-addr' in event IKE.3"
    ::= { ikeEventObjects3 1 }

ikeEventObjects4 OBJECT-IDENTITY
    STATUS current
    DESCRIPTION
        "Event IKE.4
        Received message is a retransmission."
    ::= { ikeEventsGroup 4 }

ike4-remote-addr OBJECT-TYPE
    SYNTAX IpAddress
    MAX-ACCESS accessible-for-notify
    STATUS current
    DESCRIPTION
        "Parameter 'remote-addr' in event IKE.4"
    ::= { ikeEventObjects4 1 }

ikeEventObjects5 OBJECT-IDENTITY
    STATUS current
    DESCRIPTION
        "Event IKE.5
        Could not initiate IKE negotiation: unknown destination."
    ::= { ikeEventsGroup 5 }

ike5-remote-addr OBJECT-TYPE
    SYNTAX IpAddress
    MAX-ACCESS accessible-for-notify
    STATUS current
    DESCRIPTION
        "Parameter 'remote-addr' in event IKE.5"
    ::= { ikeEventObjects5 1 }

ikeEventObjects6 OBJECT-IDENTITY
    STATUS current
    DESCRIPTION
        "Event IKE.6
        Creating ISAKMP negotiation SA."
    ::= { ikeEventsGroup 6 }

ike6-remote-addr OBJECT-TYPE
    SYNTAX IpAddress
    MAX-ACCESS accessible-for-notify
    STATUS current
    DESCRIPTION
        "Parameter 'remote-addr' in event IKE.6"
    ::= { ikeEventObjects6 1 }

ike6-connection OBJECT-TYPE
    SYNTAX Integer32
    MAX-ACCESS accessible-for-notify
    STATUS current
    DESCRIPTION
        "Parameter 'connection' in event IKE.6"
    ::= { ikeEventObjects6 2 }

ikeEventObjects7 OBJECT-IDENTITY
    STATUS current
    DESCRIPTION
        "Event IKE.7
        Deleting ISAKMP negotiation SA."
    ::= { ikeEventsGroup 7 }

ike7-remote-addr OBJECT-TYPE
    SYNTAX IpAddress
    MAX-ACCESS accessible-for-notify
    STATUS current
    DESCRIPTION
        "Parameter 'remote-addr' in event IKE.7"
    ::= { ikeEventObjects7 1 }

ikeEventObjects8 OBJECT-IDENTITY
    STATUS current
    DESCRIPTION
        "Event IKE.8
        Creating ISAKMP SA."
    ::= { ikeEventsGroup 8 }

ike8-remote-addr OBJECT-TYPE
    SYNTAX IpAddress
    MAX-ACCESS accessible-for-notify
    STATUS current
    DESCRIPTION
        "Parameter 'remote-addr' in event IKE.8"
    ::= { ikeEventObjects8 1 }

ikeEventObjects9 OBJECT-IDENTITY
    STATUS current
    DESCRIPTION
        "Event IKE.9
        Creating ISAKMP SA id."
    ::= { ikeEventsGroup 9 }

ike9-remote-addr OBJECT-TYPE
    SYNTAX IpAddress
    MAX-ACCESS accessible-for-notify
    STATUS current
    DESCRIPTION
        "Parameter 'remote-addr' in event IKE.9"
    ::= { ikeEventObjects9 1 }

ike9-message-id OBJECT-TYPE
    SYNTAX Integer32
    MAX-ACCESS accessible-for-notify
    STATUS current
    DESCRIPTION
        "Parameter 'message-id' in event IKE.9"
    ::= { ikeEventObjects9 2 }

ikeEventObjects10 OBJECT-IDENTITY
    STATUS current
    DESCRIPTION
        "Event IKE.10
        Unable to create ISAKMP SA."
    ::= { ikeEventsGroup 10 }

ike10-remote-addr OBJECT-TYPE
    SYNTAX IpAddress
    MAX-ACCESS accessible-for-notify
    STATUS current
    DESCRIPTION
        "Parameter 'remote-addr' in event IKE.10"
    ::= { ikeEventObjects10 1 }

ike10-ini-cookie-lo OBJECT-TYPE
    SYNTAX Integer32
    MAX-ACCESS accessible-for-notify
    STATUS current
    DESCRIPTION
        "Parameter 'ini-cookie-lo' in event IKE.10"
    ::= { ikeEventObjects10 2 }

ike10-ini-cookie-hi OBJECT-TYPE
    SYNTAX Integer32
    MAX-ACCESS accessible-for-notify
    STATUS current
    DESCRIPTION
        "Parameter 'ini-cookie-hi' in event IKE.10"
    ::= { ikeEventObjects10 3 }

ike10-res-cookie-lo OBJECT-TYPE
    SYNTAX Integer32
    MAX-ACCESS accessible-for-notify
    STATUS current
    DESCRIPTION
        "Parameter 'res-cookie-lo' in event IKE.10"
    ::= { ikeEventObjects10 4 }

ike10-res-cookie-hi OBJECT-TYPE
    SYNTAX Integer32
    MAX-ACCESS accessible-for-notify
    STATUS current
    DESCRIPTION
        "Parameter 'res-cookie-hi' in event IKE.10"
    ::= { ikeEventObjects10 5 }

ikeEventObjects11 OBJECT-IDENTITY
    STATUS current
    DESCRIPTION
        "Event IKE.11
        Creating SA for incoming packets."
    ::= { ikeEventsGroup 11 }

ike11-remote-addr OBJECT-TYPE
    SYNTAX IpAddress
    MAX-ACCESS accessible-for-notify
    STATUS current
    DESCRIPTION
        "Parameter 'remote-addr' in event IKE.11"
    ::= { ikeEventObjects11 1 }

ike11-spi OBJECT-TYPE
    SYNTAX Integer32
    MAX-ACCESS accessible-for-notify
    STATUS current
    DESCRIPTION
        "Parameter 'spi' in event IKE.11"
    ::= { ikeEventObjects11 2 }

ikeEventObjects12 OBJECT-IDENTITY
    STATUS current
    DESCRIPTION
        "Event IKE.12
        Creating SA for outgoing packets."
    ::= { ikeEventsGroup 12 }

ike12-remote-addr OBJECT-TYPE
    SYNTAX IpAddress
    MAX-ACCESS accessible-for-notify
    STATUS current
    DESCRIPTION
        "Parameter 'remote-addr' in event IKE.12"
    ::= { ikeEventObjects12 1 }

ike12-spi OBJECT-TYPE
    SYNTAX Integer32
    MAX-ACCESS accessible-for-notify
    STATUS current
    DESCRIPTION
        "Parameter 'spi' in event IKE.12"
    ::= { ikeEventObjects12 2 }

ikeEventObjects13 OBJECT-IDENTITY
    STATUS current
    DESCRIPTION
        "Event IKE.13
        Deleting access list entry."
    ::= { ikeEventsGroup 13 }

ike13-remote-addr OBJECT-TYPE
    SYNTAX IpAddress
    MAX-ACCESS accessible-for-notify
    STATUS current
    DESCRIPTION
        "Parameter 'remote-addr' in event IKE.13"
    ::= { ikeEventObjects13 1 }

ikeEventObjects14 OBJECT-IDENTITY
    STATUS current
    DESCRIPTION
        "Event IKE.14
        Deleting SA for incoming packets."
    ::= { ikeEventsGroup 14 }

ike14-remote-addr OBJECT-TYPE
    SYNTAX IpAddress
    MAX-ACCESS accessible-for-notify
    STATUS current
    DESCRIPTION
        "Parameter 'remote-addr' in event IKE.14"
    ::= { ikeEventObjects14 1 }

ike14-spi OBJECT-TYPE
    SYNTAX Integer32
    MAX-ACCESS accessible-for-notify
    STATUS current
    DESCRIPTION
        "Parameter 'spi' in event IKE.14"
    ::= { ikeEventObjects14 2 }

ikeEventObjects15 OBJECT-IDENTITY
    STATUS current
    DESCRIPTION
        "Event IKE.15
        Deleting SA for outgoing packets."
    ::= { ikeEventsGroup 15 }

ike15-remote-addr OBJECT-TYPE
    SYNTAX IpAddress
    MAX-ACCESS accessible-for-notify
    STATUS current
    DESCRIPTION
        "Parameter 'remote-addr' in event IKE.15"
    ::= { ikeEventObjects15 1 }

ike15-spi OBJECT-TYPE
    SYNTAX Integer32
    MAX-ACCESS accessible-for-notify
    STATUS current
    DESCRIPTION
        "Parameter 'spi' in event IKE.15"
    ::= { ikeEventObjects15 2 }

ikeEventObjects16 OBJECT-IDENTITY
    STATUS current
    DESCRIPTION
        "Event IKE.16
        Keepalive expired: deleting SA."
    ::= { ikeEventsGroup 16 }

ike16-remote-addr OBJECT-TYPE
    SYNTAX IpAddress
    MAX-ACCESS accessible-for-notify
    STATUS current
    DESCRIPTION
        "Parameter 'remote-addr' in event IKE.16"
    ::= { ikeEventObjects16 1 }

ike16-spi OBJECT-TYPE
    SYNTAX Integer32
    MAX-ACCESS accessible-for-notify
    STATUS current
    DESCRIPTION
        "Parameter 'spi' in event IKE.16"
    ::= { ikeEventObjects16 2 }

ikeEventObjects17 OBJECT-IDENTITY
    STATUS current
    DESCRIPTION
        "Event IKE.17
        Purgetime expired for negotiation SA."
    ::= { ikeEventsGroup 17 }

ike17-remote-addr OBJECT-TYPE
    SYNTAX IpAddress
    MAX-ACCESS accessible-for-notify
    STATUS current
    DESCRIPTION
        "Parameter 'remote-addr' in event IKE.17"
    ::= { ikeEventObjects17 1 }

ikeEventObjects18 OBJECT-IDENTITY
    STATUS current
    DESCRIPTION
        "Event IKE.18
        Purgetime expired for phase II negotiation SA."
    ::= { ikeEventsGroup 18 }

ike18-remote-addr OBJECT-TYPE
    SYNTAX IpAddress
    MAX-ACCESS accessible-for-notify
    STATUS current
    DESCRIPTION
        "Parameter 'remote-addr' in event IKE.18"
    ::= { ikeEventObjects18 1 }

ike18-id OBJECT-TYPE
    SYNTAX Integer32
    MAX-ACCESS accessible-for-notify
    STATUS current
    DESCRIPTION
        "Parameter 'id' in event IKE.18"
    ::= { ikeEventObjects18 2 }

ike18-source OBJECT-TYPE
    SYNTAX IpAddress
    MAX-ACCESS accessible-for-notify
    STATUS current
    DESCRIPTION
        "Parameter 'source' in event IKE.18"
    ::= { ikeEventObjects18 3 }

ike18-destination OBJECT-TYPE
    SYNTAX IpAddress
    MAX-ACCESS accessible-for-notify
    STATUS current
    DESCRIPTION
        "Parameter 'destination' in event IKE.18"
    ::= { ikeEventObjects18 4 }

ikeEventObjects19 OBJECT-IDENTITY
    STATUS current
    DESCRIPTION
        "Event IKE.19
        ISAKMP SA commencing phase I negotiation."
    ::= { ikeEventsGroup 19 }

ike19-remote-addr OBJECT-TYPE
    SYNTAX IpAddress
    MAX-ACCESS accessible-for-notify
    STATUS current
    DESCRIPTION
        "Parameter 'remote-addr' in event IKE.19"
    ::= { ikeEventObjects19 1 }

ikeEventObjects20 OBJECT-IDENTITY
    STATUS current
    DESCRIPTION
        "Event IKE.20
        Negotiation on phase I: phase II not allowed."
    ::= { ikeEventsGroup 20 }

ike20-remote-addr OBJECT-TYPE
    SYNTAX IpAddress
    MAX-ACCESS accessible-for-notify
    STATUS current
    DESCRIPTION
        "Parameter 'remote-addr' in event IKE.20"
    ::= { ikeEventObjects20 1 }

ikeEventObjects21 OBJECT-IDENTITY
    STATUS current
    DESCRIPTION
        "Event IKE.21
        Either ISAKMP SA or phase II negotiation information is invalid."
    ::= { ikeEventsGroup 21 }

ike21-remote-addr OBJECT-TYPE
    SYNTAX IpAddress
    MAX-ACCESS accessible-for-notify
    STATUS current
    DESCRIPTION
        "Parameter 'remote-addr' in event IKE.21"
    ::= { ikeEventObjects21 1 }

ikeEventObjects22 OBJECT-IDENTITY
    STATUS current
    DESCRIPTION
        "Event IKE.22
        Renegotiation timer for outgoing packets SA initiated."
    ::= { ikeEventsGroup 22 }

ike22-remote-addr OBJECT-TYPE
    SYNTAX IpAddress
    MAX-ACCESS accessible-for-notify
    STATUS current
    DESCRIPTION
        "Parameter 'remote-addr' in event IKE.22"
    ::= { ikeEventObjects22 1 }

ike22-spi OBJECT-TYPE
    SYNTAX Integer32
    MAX-ACCESS accessible-for-notify
    STATUS current
    DESCRIPTION
        "Parameter 'spi' in event IKE.22"
    ::= { ikeEventObjects22 2 }

ikeEventObjects23 OBJECT-IDENTITY
    STATUS current
    DESCRIPTION
        "Event IKE.23
        Renegotiation timer for outgoing packets SA expired."
    ::= { ikeEventsGroup 23 }

ike23-remote-addr OBJECT-TYPE
    SYNTAX IpAddress
    MAX-ACCESS accessible-for-notify
    STATUS current
    DESCRIPTION
        "Parameter 'remote-addr' in event IKE.23"
    ::= { ikeEventObjects23 1 }

ike23-spi OBJECT-TYPE
    SYNTAX Integer32
    MAX-ACCESS accessible-for-notify
    STATUS current
    DESCRIPTION
        "Parameter 'spi' in event IKE.23"
    ::= { ikeEventObjects23 2 }

ikeEventObjects24 OBJECT-IDENTITY
    STATUS current
    DESCRIPTION
        "Event IKE.24
        Attempt to renegotiate delayed."
    ::= { ikeEventsGroup 24 }

ike24-remote-addr OBJECT-TYPE
    SYNTAX IpAddress
    MAX-ACCESS accessible-for-notify
    STATUS current
    DESCRIPTION
        "Parameter 'remote-addr' in event IKE.24"
    ::= { ikeEventObjects24 1 }

ikeEventObjects25 OBJECT-IDENTITY
    STATUS current
    DESCRIPTION
        "Event IKE.25
        Matching CRL (Certificate Revocation List)."
    ::= { ikeEventsGroup 25 }

ike25-remote-addr OBJECT-TYPE
    SYNTAX IpAddress
    MAX-ACCESS accessible-for-notify
    STATUS current
    DESCRIPTION
        "Parameter 'remote-addr' in event IKE.25"
    ::= { ikeEventObjects25 1 }

ikeEventObjects26 OBJECT-IDENTITY
    STATUS current
    DESCRIPTION
        "Event IKE.26
        Invalid ID information."
    ::= { ikeEventsGroup 26 }

ike26-remote-addr OBJECT-TYPE
    SYNTAX IpAddress
    MAX-ACCESS accessible-for-notify
    STATUS current
    DESCRIPTION
        "Parameter 'remote-addr' in event IKE.26"
    ::= { ikeEventObjects26 1 }

ikeEventObjects27 OBJECT-IDENTITY
    STATUS current
    DESCRIPTION
        "Event IKE.27
        No address information found in SA."
    ::= { ikeEventsGroup 27 }

ike27-remote-addr OBJECT-TYPE
    SYNTAX IpAddress
    MAX-ACCESS accessible-for-notify
    STATUS current
    DESCRIPTION
        "Parameter 'remote-addr' in event IKE.27"
    ::= { ikeEventObjects27 1 }

ikeEventObjects28 OBJECT-IDENTITY
    STATUS current
    DESCRIPTION
        "Event IKE.28
        ISAKMP SA commencing phase II negotiation."
    ::= { ikeEventsGroup 28 }

ike28-remote-addr OBJECT-TYPE
    SYNTAX IpAddress
    MAX-ACCESS accessible-for-notify
    STATUS current
    DESCRIPTION
        "Parameter 'remote-addr' in event IKE.28"
    ::= { ikeEventObjects28 1 }

ike28-last-id OBJECT-TYPE
    SYNTAX Integer32
    MAX-ACCESS accessible-for-notify
    STATUS current
    DESCRIPTION
        "Parameter 'last-id' in event IKE.28"
    ::= { ikeEventObjects28 2 }

ikeEventObjects29 OBJECT-IDENTITY
    STATUS current
    DESCRIPTION
        "Event IKE.29
        Negotiation from banned host stopped."
    ::= { ikeEventsGroup 29 }

ike29-remote-addr OBJECT-TYPE
    SYNTAX IpAddress
    MAX-ACCESS accessible-for-notify
    STATUS current
    DESCRIPTION
        "Parameter 'remote-addr' in event IKE.29"
    ::= { ikeEventObjects29 1 }

ikeEventObjects30 OBJECT-IDENTITY
    STATUS current
    DESCRIPTION
        "Event IKE.30
        DPD (Dead Peer Detection) system found a lost connection: deleting SAs."
    ::= { ikeEventsGroup 30 }

ike30-remote-addr OBJECT-TYPE
    SYNTAX IpAddress
    MAX-ACCESS accessible-for-notify
    STATUS current
    DESCRIPTION
        "Parameter 'remote-addr' in event IKE.30"
    ::= { ikeEventObjects30 1 }

ikeEventObjects31 OBJECT-IDENTITY
    STATUS current
    DESCRIPTION
        "Event IKE.31
        Maximum number of simultaneous tunnels reached."
    ::= { ikeEventsGroup 31 }

ike31-remote-addr OBJECT-TYPE
    SYNTAX IpAddress
    MAX-ACCESS accessible-for-notify
    STATUS current
    DESCRIPTION
        "Parameter 'remote-addr' in event IKE.31"
    ::= { ikeEventObjects31 1 }

ikeEventObjects32 OBJECT-IDENTITY
    STATUS current
    DESCRIPTION
        "Event IKE.32
        Renegotiation using DNAT started."
    ::= { ikeEventsGroup 32 }

ike32-remote-addr OBJECT-TYPE
    SYNTAX IpAddress
    MAX-ACCESS accessible-for-notify
    STATUS current
    DESCRIPTION
        "Parameter 'remote-addr' in event IKE.32"
    ::= { ikeEventObjects32 1 }

ikeEventObjects33 OBJECT-IDENTITY
    STATUS current
    DESCRIPTION
        "Event IKE.33
        SA lifetime counter changed."
    ::= { ikeEventsGroup 33 }

ike33-remote-addr OBJECT-TYPE
    SYNTAX IpAddress
    MAX-ACCESS accessible-for-notify
    STATUS current
    DESCRIPTION
        "Parameter 'remote-addr' in event IKE.33"
    ::= { ikeEventObjects33 1 }

ikeEventObjects34 OBJECT-IDENTITY
    STATUS current
    DESCRIPTION
        "Event IKE.34
        Searching Backup peer."
    ::= { ikeEventsGroup 34 }

ike34-remote-addr OBJECT-TYPE
    SYNTAX IpAddress
    MAX-ACCESS accessible-for-notify
    STATUS current
    DESCRIPTION
        "Parameter 'remote-addr' in event IKE.34"
    ::= { ikeEventObjects34 1 }

ikeEventObjects35 OBJECT-IDENTITY
    STATUS current
    DESCRIPTION
        "Event IKE.35
        Renegotiation Timer for negotiation SA expired."
    ::= { ikeEventsGroup 35 }

ike35-remote-addr OBJECT-TYPE
    SYNTAX IpAddress
    MAX-ACCESS accessible-for-notify
    STATUS current
    DESCRIPTION
        "Parameter 'remote-addr' in event IKE.35"
    ::= { ikeEventObjects35 1 }

ike35-connection OBJECT-TYPE
    SYNTAX Integer32
    MAX-ACCESS accessible-for-notify
    STATUS current
    DESCRIPTION
        "Parameter 'connection' in event IKE.35"
    ::= { ikeEventObjects35 2 }

ikeEventObjects36 OBJECT-IDENTITY
    STATUS current
    DESCRIPTION
        "Event IKE.36
        Local side starting negotiation."
    ::= { ikeEventsGroup 36 }

ike36-remote-addr OBJECT-TYPE
    SYNTAX IpAddress
    MAX-ACCESS accessible-for-notify
    STATUS current
    DESCRIPTION
        "Parameter 'remote-addr' in event IKE.36"
    ::= { ikeEventObjects36 1 }

ikeEventObjects37 OBJECT-IDENTITY
    STATUS current
    DESCRIPTION
        "Event IKE.37
        Remote side starting negotiation."
    ::= { ikeEventsGroup 37 }

ike37-remote-addr OBJECT-TYPE
    SYNTAX IpAddress
    MAX-ACCESS accessible-for-notify
    STATUS current
    DESCRIPTION
        "Parameter 'remote-addr' in event IKE.37"
    ::= { ikeEventObjects37 1 }

ikeEventObjects38 OBJECT-IDENTITY
    STATUS current
    DESCRIPTION
        "Event IKE.38
        Local side starting Backup negotiation."
    ::= { ikeEventsGroup 38 }

ike38-remote-addr OBJECT-TYPE
    SYNTAX IpAddress
    MAX-ACCESS accessible-for-notify
    STATUS current
    DESCRIPTION
        "Parameter 'remote-addr' in event IKE.38"
    ::= { ikeEventObjects38 1 }

ikeEventObjects39 OBJECT-IDENTITY
    STATUS current
    DESCRIPTION
        "Event IKE.39
        Remote side starting Backup negotiation."
    ::= { ikeEventsGroup 39 }

ike39-remote-addr OBJECT-TYPE
    SYNTAX IpAddress
    MAX-ACCESS accessible-for-notify
    STATUS current
    DESCRIPTION
        "Parameter 'remote-addr' in event IKE.39"
    ::= { ikeEventObjects39 1 }

ikeEventObjects40 OBJECT-IDENTITY
    STATUS current
    DESCRIPTION
        "Event IKE.40
        Tunnel correctly established."
    ::= { ikeEventsGroup 40 }

ike40-remote-addr OBJECT-TYPE
    SYNTAX IpAddress
    MAX-ACCESS accessible-for-notify
    STATUS current
    DESCRIPTION
        "Parameter 'remote-addr' in event IKE.40"
    ::= { ikeEventObjects40 1 }

ike40-spi OBJECT-TYPE
    SYNTAX Integer32
    MAX-ACCESS accessible-for-notify
    STATUS current
    DESCRIPTION
        "Parameter 'spi' in event IKE.40"
    ::= { ikeEventObjects40 2 }

ikeEventObjects41 OBJECT-IDENTITY
    STATUS current
    DESCRIPTION
        "Event IKE.41
        Tunnel disconnected."
    ::= { ikeEventsGroup 41 }

ike41-remote-addr OBJECT-TYPE
    SYNTAX IpAddress
    MAX-ACCESS accessible-for-notify
    STATUS current
    DESCRIPTION
        "Parameter 'remote-addr' in event IKE.41"
    ::= { ikeEventObjects41 1 }

ike41-spi OBJECT-TYPE
    SYNTAX Integer32
    MAX-ACCESS accessible-for-notify
    STATUS current
    DESCRIPTION
        "Parameter 'spi' in event IKE.41"
    ::= { ikeEventObjects41 2 }

ikeEventObjects42 OBJECT-IDENTITY
    STATUS current
    DESCRIPTION
        "Event IKE.42
        Unexpected notification from remote side received."
    ::= { ikeEventsGroup 42 }

ike42-remote-addr OBJECT-TYPE
    SYNTAX IpAddress
    MAX-ACCESS accessible-for-notify
    STATUS current
    DESCRIPTION
        "Parameter 'remote-addr' in event IKE.42"
    ::= { ikeEventObjects42 1 }

ike42-message OBJECT-TYPE
    SYNTAX DisplayString
    MAX-ACCESS accessible-for-notify
    STATUS current
    DESCRIPTION
        "Parameter 'message' in event IKE.42"
    ::= { ikeEventObjects42 2 }

ikeEventObjects43 OBJECT-IDENTITY
    STATUS current
    DESCRIPTION
        "Event IKE.43
        Notification from remote side received."
    ::= { ikeEventsGroup 43 }

ike43-remote-addr OBJECT-TYPE
    SYNTAX IpAddress
    MAX-ACCESS accessible-for-notify
    STATUS current
    DESCRIPTION
        "Parameter 'remote-addr' in event IKE.43"
    ::= { ikeEventObjects43 1 }

ike43-message OBJECT-TYPE
    SYNTAX DisplayString
    MAX-ACCESS accessible-for-notify
    STATUS current
    DESCRIPTION
        "Parameter 'message' in event IKE.43"
    ::= { ikeEventObjects43 2 }

ikeEventObjects44 OBJECT-IDENTITY
    STATUS current
    DESCRIPTION
        "Event IKE.44
        A new tunnel has opened and the router has established a new static
        route so it can be back-propagated via RIP or OSPF (RRI or Remote
        Route Injection)."
    ::= { ikeEventsGroup 44 }

ike44-spi OBJECT-TYPE
    SYNTAX Integer32
    MAX-ACCESS accessible-for-notify
    STATUS current
    DESCRIPTION
        "Parameter 'spi' in event IKE.44"
    ::= { ikeEventObjects44 1 }

ike44-dst-addr OBJECT-TYPE
    SYNTAX IpAddress
    MAX-ACCESS accessible-for-notify
    STATUS current
    DESCRIPTION
        "Parameter 'dst-addr' in event IKE.44"
    ::= { ikeEventObjects44 2 }

ike44-dest-mask OBJECT-TYPE
    SYNTAX Integer32
    MAX-ACCESS accessible-for-notify
    STATUS current
    DESCRIPTION
        "Parameter 'dest-mask' in event IKE.44"
    ::= { ikeEventObjects44 3 }

ike44-via-gw OBJECT-TYPE
    SYNTAX IpAddress
    MAX-ACCESS accessible-for-notify
    STATUS current
    DESCRIPTION
        "Parameter 'via-gw' in event IKE.44"
    ::= { ikeEventObjects44 4 }

ikeEventObjects45 OBJECT-IDENTITY
    STATUS current
    DESCRIPTION
        "Event IKE.45
        There was a problem establishing a static route for RRI."
    ::= { ikeEventsGroup 45 }

ike45-spi OBJECT-TYPE
    SYNTAX Integer32
    MAX-ACCESS accessible-for-notify
    STATUS current
    DESCRIPTION
        "Parameter 'spi' in event IKE.45"
    ::= { ikeEventObjects45 1 }

ike45-dst-addr OBJECT-TYPE
    SYNTAX IpAddress
    MAX-ACCESS accessible-for-notify
    STATUS current
    DESCRIPTION
        "Parameter 'dst-addr' in event IKE.45"
    ::= { ikeEventObjects45 2 }

ike45-dest-mask OBJECT-TYPE
    SYNTAX Integer32
    MAX-ACCESS accessible-for-notify
    STATUS current
    DESCRIPTION
        "Parameter 'dest-mask' in event IKE.45"
    ::= { ikeEventObjects45 3 }

ike45-via-gw OBJECT-TYPE
    SYNTAX IpAddress
    MAX-ACCESS accessible-for-notify
    STATUS current
    DESCRIPTION
        "Parameter 'via-gw' in event IKE.45"
    ::= { ikeEventObjects45 4 }

ikeEventObjects46 OBJECT-IDENTITY
    STATUS current
    DESCRIPTION
        "Event IKE.46
        RRI has cleared a static route."
    ::= { ikeEventsGroup 46 }

ike46-spi OBJECT-TYPE
    SYNTAX Integer32
    MAX-ACCESS accessible-for-notify
    STATUS current
    DESCRIPTION
        "Parameter 'spi' in event IKE.46"
    ::= { ikeEventObjects46 1 }

ike46-dst-addr OBJECT-TYPE
    SYNTAX IpAddress
    MAX-ACCESS accessible-for-notify
    STATUS current
    DESCRIPTION
        "Parameter 'dst-addr' in event IKE.46"
    ::= { ikeEventObjects46 2 }

ike46-dest-mask OBJECT-TYPE
    SYNTAX Integer32
    MAX-ACCESS accessible-for-notify
    STATUS current
    DESCRIPTION
        "Parameter 'dest-mask' in event IKE.46"
    ::= { ikeEventObjects46 3 }

ike46-via-gw OBJECT-TYPE
    SYNTAX IpAddress
    MAX-ACCESS accessible-for-notify
    STATUS current
    DESCRIPTION
        "Parameter 'via-gw' in event IKE.46"
    ::= { ikeEventObjects46 4 }

ikeEventObjects47 OBJECT-IDENTITY
    STATUS current
    DESCRIPTION
        "Event IKE.47
        User is trying authentication."
    ::= { ikeEventsGroup 47 }

ike47-user-addr OBJECT-TYPE
    SYNTAX IpAddress
    MAX-ACCESS accessible-for-notify
    STATUS current
    DESCRIPTION
        "Parameter 'user-addr' in event IKE.47"
    ::= { ikeEventObjects47 1 }

ike47-user-string OBJECT-TYPE
    SYNTAX DisplayString
    MAX-ACCESS accessible-for-notify
    STATUS current
    DESCRIPTION
        "Parameter 'user-string' in event IKE.47"
    ::= { ikeEventObjects47 2 }

ikeEventObjects48 OBJECT-IDENTITY
    STATUS current
    DESCRIPTION
        "Event IKE.48
        Tunnel ready to be established."
    ::= { ikeEventsGroup 48 }

ike48-remote-addr OBJECT-TYPE
    SYNTAX IpAddress
    MAX-ACCESS accessible-for-notify
    STATUS current
    DESCRIPTION
        "Parameter 'remote-addr' in event IKE.48"
    ::= { ikeEventObjects48 1 }

ike48-iniciator OBJECT-TYPE
    SYNTAX DisplayString
    MAX-ACCESS accessible-for-notify
    STATUS current
    DESCRIPTION
        "Parameter 'iniciator' in event IKE.48"
    ::= { ikeEventObjects48 2 }

ike48-responder OBJECT-TYPE
    SYNTAX DisplayString
    MAX-ACCESS accessible-for-notify
    STATUS current
    DESCRIPTION
        "Parameter 'responder' in event IKE.48"
    ::= { ikeEventObjects48 3 }

ike48-spi OBJECT-TYPE
    SYNTAX Integer32
    MAX-ACCESS accessible-for-notify
    STATUS current
    DESCRIPTION
        "Parameter 'spi' in event IKE.48"
    ::= { ikeEventObjects48 4 }

ikeEventObjects49 OBJECT-IDENTITY
    STATUS current
    DESCRIPTION
        "Event IKE.49
        Tunnel ready to be disconneted."
    ::= { ikeEventsGroup 49 }

ike49-remote-addr OBJECT-TYPE
    SYNTAX IpAddress
    MAX-ACCESS accessible-for-notify
    STATUS current
    DESCRIPTION
        "Parameter 'remote-addr' in event IKE.49"
    ::= { ikeEventObjects49 1 }

ike49-iniciator OBJECT-TYPE
    SYNTAX DisplayString
    MAX-ACCESS accessible-for-notify
    STATUS current
    DESCRIPTION
        "Parameter 'iniciator' in event IKE.49"
    ::= { ikeEventObjects49 2 }

ike49-responder OBJECT-TYPE
    SYNTAX DisplayString
    MAX-ACCESS accessible-for-notify
    STATUS current
    DESCRIPTION
        "Parameter 'responder' in event IKE.49"
    ::= { ikeEventObjects49 3 }

ike49-spi OBJECT-TYPE
    SYNTAX Integer32
    MAX-ACCESS accessible-for-notify
    STATUS current
    DESCRIPTION
        "Parameter 'spi' in event IKE.49"
    ::= { ikeEventObjects49 4 }

ikeEventObjects50 OBJECT-IDENTITY
    STATUS current
    DESCRIPTION
        "Event IKE.50
        Text Identification Payload registered."
    ::= { ikeEventsGroup 50 }

ike50-address OBJECT-TYPE
    SYNTAX IpAddress
    MAX-ACCESS accessible-for-notify
    STATUS current
    DESCRIPTION
        "Parameter 'address' in event IKE.50"
    ::= { ikeEventObjects50 1 }

ike50-idname OBJECT-TYPE
    SYNTAX DisplayString
    MAX-ACCESS accessible-for-notify
    STATUS current
    DESCRIPTION
        "Parameter 'idname' in event IKE.50"
    ::= { ikeEventObjects50 2 }

ike50-protocolnumber OBJECT-TYPE
    SYNTAX Integer32
    MAX-ACCESS accessible-for-notify
    STATUS current
    DESCRIPTION
        "Parameter 'protocolnumber' in event IKE.50"
    ::= { ikeEventObjects50 3 }

ike50-portnumber OBJECT-TYPE
    SYNTAX Integer32
    MAX-ACCESS accessible-for-notify
    STATUS current
    DESCRIPTION
        "Parameter 'portnumber' in event IKE.50"
    ::= { ikeEventObjects50 4 }

ike50-idtype OBJECT-TYPE
    SYNTAX DisplayString
    MAX-ACCESS accessible-for-notify
    STATUS current
    DESCRIPTION
        "Parameter 'idtype' in event IKE.50"
    ::= { ikeEventObjects50 5 }

ikeEventObjects51 OBJECT-IDENTITY
    STATUS current
    DESCRIPTION
        "Event IKE.51
        IP Identification Payload registered."
    ::= { ikeEventsGroup 51 }

ike51-address OBJECT-TYPE
    SYNTAX IpAddress
    MAX-ACCESS accessible-for-notify
    STATUS current
    DESCRIPTION
        "Parameter 'address' in event IKE.51"
    ::= { ikeEventObjects51 1 }

ike51-idaddress OBJECT-TYPE
    SYNTAX IpAddress
    MAX-ACCESS accessible-for-notify
    STATUS current
    DESCRIPTION
        "Parameter 'idaddress' in event IKE.51"
    ::= { ikeEventObjects51 2 }

ike51-protocolnumber OBJECT-TYPE
    SYNTAX Integer32
    MAX-ACCESS accessible-for-notify
    STATUS current
    DESCRIPTION
        "Parameter 'protocolnumber' in event IKE.51"
    ::= { ikeEventObjects51 3 }

ike51-portnumber OBJECT-TYPE
    SYNTAX Integer32
    MAX-ACCESS accessible-for-notify
    STATUS current
    DESCRIPTION
        "Parameter 'portnumber' in event IKE.51"
    ::= { ikeEventObjects51 4 }

ike51-idtype OBJECT-TYPE
    SYNTAX DisplayString
    MAX-ACCESS accessible-for-notify
    STATUS current
    DESCRIPTION
        "Parameter 'idtype' in event IKE.51"
    ::= { ikeEventObjects51 5 }

ikeEventObjects52 OBJECT-IDENTITY
    STATUS current
    DESCRIPTION
        "Event IKE.52
        Periodic information of the established tunnel."
    ::= { ikeEventsGroup 52 }

ike52-remote-addr OBJECT-TYPE
    SYNTAX IpAddress
    MAX-ACCESS accessible-for-notify
    STATUS current
    DESCRIPTION
        "Parameter 'remote-addr' in event IKE.52"
    ::= { ikeEventObjects52 1 }

ike52-spi OBJECT-TYPE
    SYNTAX Integer32
    MAX-ACCESS accessible-for-notify
    STATUS current
    DESCRIPTION
        "Parameter 'spi' in event IKE.52"
    ::= { ikeEventObjects52 2 }

ike52-remote-client OBJECT-TYPE
    SYNTAX IpAddress
    MAX-ACCESS accessible-for-notify
    STATUS current
    DESCRIPTION
        "Parameter 'remote-client' in event IKE.52"
    ::= { ikeEventObjects52 3 }

ikeEventObjects53 OBJECT-IDENTITY
    STATUS current
    DESCRIPTION
        "Event IKE.53
        Attribute string registered"
    ::= { ikeEventsGroup 53 }

ike53-remote-addr OBJECT-TYPE
    SYNTAX IpAddress
    MAX-ACCESS accessible-for-notify
    STATUS current
    DESCRIPTION
        "Parameter 'remote-addr' in event IKE.53"
    ::= { ikeEventObjects53 1 }

ike53-attribute-string OBJECT-TYPE
    SYNTAX DisplayString
    MAX-ACCESS accessible-for-notify
    STATUS current
    DESCRIPTION
        "Parameter 'attribute-string' in event IKE.53"
    ::= { ikeEventObjects53 2 }

ikeEventObjects54 OBJECT-IDENTITY
    STATUS current
    DESCRIPTION
        "Event IKE.54
        Information string registered"
    ::= { ikeEventsGroup 54 }

ike54-remote-addr OBJECT-TYPE
    SYNTAX IpAddress
    MAX-ACCESS accessible-for-notify
    STATUS current
    DESCRIPTION
        "Parameter 'remote-addr' in event IKE.54"
    ::= { ikeEventObjects54 1 }

ike54-info-string OBJECT-TYPE
    SYNTAX DisplayString
    MAX-ACCESS accessible-for-notify
    STATUS current
    DESCRIPTION
        "Parameter 'info-string' in event IKE.54"
    ::= { ikeEventObjects54 2 }

ikeEventObjects55 OBJECT-IDENTITY
    STATUS current
    DESCRIPTION
        "Event IKE.55
        There is been a change on the source or destination port for this SA"
    ::= { ikeEventsGroup 55 }

ike55-sa-conn-id OBJECT-TYPE
    SYNTAX Integer32
    MAX-ACCESS accessible-for-notify
    STATUS current
    DESCRIPTION
        "Parameter 'sa-conn-id' in event IKE.55"
    ::= { ikeEventObjects55 1 }

ike55-old-src-port OBJECT-TYPE
    SYNTAX Integer32
    MAX-ACCESS accessible-for-notify
    STATUS current
    DESCRIPTION
        "Parameter 'old-src-port' in event IKE.55"
    ::= { ikeEventObjects55 2 }

ike55-old-dst-port OBJECT-TYPE
    SYNTAX Integer32
    MAX-ACCESS accessible-for-notify
    STATUS current
    DESCRIPTION
        "Parameter 'old-dst-port' in event IKE.55"
    ::= { ikeEventObjects55 3 }

ike55-new-src-port OBJECT-TYPE
    SYNTAX Integer32
    MAX-ACCESS accessible-for-notify
    STATUS current
    DESCRIPTION
        "Parameter 'new-src-port' in event IKE.55"
    ::= { ikeEventObjects55 4 }

ike55-new-dst-port OBJECT-TYPE
    SYNTAX Integer32
    MAX-ACCESS accessible-for-notify
    STATUS current
    DESCRIPTION
        "Parameter 'new-dst-port' in event IKE.55"
    ::= { ikeEventObjects55 5 }

ikeEventObjects56 OBJECT-IDENTITY
    STATUS current
    DESCRIPTION
        "Event IKE.56
        A GDOI client message has been sent"
    ::= { ikeEventsGroup 56 }

ike56-message OBJECT-TYPE
    SYNTAX DisplayString
    MAX-ACCESS accessible-for-notify
    STATUS current
    DESCRIPTION
        "Parameter 'message' in event IKE.56"
    ::= { ikeEventObjects56 1 }

ike56-dst-ip OBJECT-TYPE
    SYNTAX IpAddress
    MAX-ACCESS accessible-for-notify
    STATUS current
    DESCRIPTION
        "Parameter 'dst-ip' in event IKE.56"
    ::= { ikeEventObjects56 2 }

ike56-group OBJECT-TYPE
    SYNTAX Integer32
    MAX-ACCESS accessible-for-notify
    STATUS current
    DESCRIPTION
        "Parameter 'group' in event IKE.56"
    ::= { ikeEventObjects56 3 }

ikeEventObjects57 OBJECT-IDENTITY
    STATUS current
    DESCRIPTION
        "Event IKE.57
        A GDOI client message has been received"
    ::= { ikeEventsGroup 57 }

ike57-message OBJECT-TYPE
    SYNTAX DisplayString
    MAX-ACCESS accessible-for-notify
    STATUS current
    DESCRIPTION
        "Parameter 'message' in event IKE.57"
    ::= { ikeEventObjects57 1 }

ike57-src-ip OBJECT-TYPE
    SYNTAX IpAddress
    MAX-ACCESS accessible-for-notify
    STATUS current
    DESCRIPTION
        "Parameter 'src-ip' in event IKE.57"
    ::= { ikeEventObjects57 2 }

ike57-group OBJECT-TYPE
    SYNTAX Integer32
    MAX-ACCESS accessible-for-notify
    STATUS current
    DESCRIPTION
        "Parameter 'group' in event IKE.57"
    ::= { ikeEventObjects57 3 }

ikeEventObjects58 OBJECT-IDENTITY
    STATUS current
    DESCRIPTION
        "Event IKE.58
        A GDOI server message has been sent"
    ::= { ikeEventsGroup 58 }

ike58-message OBJECT-TYPE
    SYNTAX DisplayString
    MAX-ACCESS accessible-for-notify
    STATUS current
    DESCRIPTION
        "Parameter 'message' in event IKE.58"
    ::= { ikeEventObjects58 1 }

ike58-dst-ip OBJECT-TYPE
    SYNTAX IpAddress
    MAX-ACCESS accessible-for-notify
    STATUS current
    DESCRIPTION
        "Parameter 'dst-ip' in event IKE.58"
    ::= { ikeEventObjects58 2 }

ike58-group OBJECT-TYPE
    SYNTAX Integer32
    MAX-ACCESS accessible-for-notify
    STATUS current
    DESCRIPTION
        "Parameter 'group' in event IKE.58"
    ::= { ikeEventObjects58 3 }

ikeEventObjects59 OBJECT-IDENTITY
    STATUS current
    DESCRIPTION
        "Event IKE.59
        A GDOI server message has been sent"
    ::= { ikeEventsGroup 59 }

ike59-message OBJECT-TYPE
    SYNTAX DisplayString
    MAX-ACCESS accessible-for-notify
    STATUS current
    DESCRIPTION
        "Parameter 'message' in event IKE.59"
    ::= { ikeEventObjects59 1 }

ike59-src-ip OBJECT-TYPE
    SYNTAX IpAddress
    MAX-ACCESS accessible-for-notify
    STATUS current
    DESCRIPTION
        "Parameter 'src-ip' in event IKE.59"
    ::= { ikeEventObjects59 2 }

ike59-group OBJECT-TYPE
    SYNTAX Integer32
    MAX-ACCESS accessible-for-notify
    STATUS current
    DESCRIPTION
        "Parameter 'group' in event IKE.59"
    ::= { ikeEventObjects59 3 }

ikeEventObjects60 OBJECT-IDENTITY
    STATUS current
    DESCRIPTION
        "Event IKE.60
        A GDOI client error"
    ::= { ikeEventsGroup 60 }

ike60-error OBJECT-TYPE
    SYNTAX DisplayString
    MAX-ACCESS accessible-for-notify
    STATUS current
    DESCRIPTION
        "Parameter 'error' in event IKE.60"
    ::= { ikeEventObjects60 1 }

ikeEventObjects61 OBJECT-IDENTITY
    STATUS current
    DESCRIPTION
        "Event IKE.61
        A GDOI server error"
    ::= { ikeEventsGroup 61 }

ike61-error OBJECT-TYPE
    SYNTAX DisplayString
    MAX-ACCESS accessible-for-notify
    STATUS current
    DESCRIPTION
        "Parameter 'error' in event IKE.61"
    ::= { ikeEventObjects61 1 }

ikeEventObjects62 OBJECT-IDENTITY
    STATUS current
    DESCRIPTION
        "Event IKE.62
        A GDOI client has added a new acl"
    ::= { ikeEventsGroup 62 }

ike62-spi OBJECT-TYPE
    SYNTAX Integer32
    MAX-ACCESS accessible-for-notify
    STATUS current
    DESCRIPTION
        "Parameter 'spi' in event IKE.62"
    ::= { ikeEventObjects62 1 }

ike62-srIP OBJECT-TYPE
    SYNTAX IpAddress
    MAX-ACCESS accessible-for-notify
    STATUS current
    DESCRIPTION
        "Parameter 'srIP' in event IKE.62"
    ::= { ikeEventObjects62 2 }

ike62-dstIP OBJECT-TYPE
    SYNTAX IpAddress
    MAX-ACCESS accessible-for-notify
    STATUS current
    DESCRIPTION
        "Parameter 'dstIP' in event IKE.62"
    ::= { ikeEventObjects62 3 }

ike62-prot OBJECT-TYPE
    SYNTAX Integer32
    MAX-ACCESS accessible-for-notify
    STATUS current
    DESCRIPTION
        "Parameter 'prot' in event IKE.62"
    ::= { ikeEventObjects62 4 }

ike62-sport OBJECT-TYPE
    SYNTAX Integer32
    MAX-ACCESS accessible-for-notify
    STATUS current
    DESCRIPTION
        "Parameter 'sport' in event IKE.62"
    ::= { ikeEventObjects62 5 }

ike62-dport OBJECT-TYPE
    SYNTAX Integer32
    MAX-ACCESS accessible-for-notify
    STATUS current
    DESCRIPTION
        "Parameter 'dport' in event IKE.62"
    ::= { ikeEventObjects62 6 }

ikeEventObjects63 OBJECT-IDENTITY
    STATUS current
    DESCRIPTION
        "Event IKE.63
        A GDOI client has created new in out sas"
    ::= { ikeEventsGroup 63 }

ike63-spi OBJECT-TYPE
    SYNTAX Integer32
    MAX-ACCESS accessible-for-notify
    STATUS current
    DESCRIPTION
        "Parameter 'spi' in event IKE.63"
    ::= { ikeEventObjects63 1 }

ike63-lifetime OBJECT-TYPE
    SYNTAX Integer32
    MAX-ACCESS accessible-for-notify
    STATUS current
    DESCRIPTION
        "Parameter 'lifetime' in event IKE.63"
    ::= { ikeEventObjects63 2 }

ikeEventObjects64 OBJECT-IDENTITY
    STATUS current
    DESCRIPTION
        "Event IKE.64
        A client rekey"
    ::= { ikeEventsGroup 64 }

ike64-ic-lo OBJECT-TYPE
    SYNTAX Integer32
    MAX-ACCESS accessible-for-notify
    STATUS current
    DESCRIPTION
        "Parameter 'ic-lo' in event IKE.64"
    ::= { ikeEventObjects64 1 }

ike64-ic-hi OBJECT-TYPE
    SYNTAX Integer32
    MAX-ACCESS accessible-for-notify
    STATUS current
    DESCRIPTION
        "Parameter 'ic-hi' in event IKE.64"
    ::= { ikeEventObjects64 2 }

ike64-rc-lo OBJECT-TYPE
    SYNTAX Integer32
    MAX-ACCESS accessible-for-notify
    STATUS current
    DESCRIPTION
        "Parameter 'rc-lo' in event IKE.64"
    ::= { ikeEventObjects64 3 }

ike64-rc-hi OBJECT-TYPE
    SYNTAX Integer32
    MAX-ACCESS accessible-for-notify
    STATUS current
    DESCRIPTION
        "Parameter 'rc-hi' in event IKE.64"
    ::= { ikeEventObjects64 4 }

ike64-nic-lo OBJECT-TYPE
    SYNTAX Integer32
    MAX-ACCESS accessible-for-notify
    STATUS current
    DESCRIPTION
        "Parameter 'nic-lo' in event IKE.64"
    ::= { ikeEventObjects64 5 }

ike64-nic-hi OBJECT-TYPE
    SYNTAX Integer32
    MAX-ACCESS accessible-for-notify
    STATUS current
    DESCRIPTION
        "Parameter 'nic-hi' in event IKE.64"
    ::= { ikeEventObjects64 6 }

ike64-nr-lo OBJECT-TYPE
    SYNTAX Integer32
    MAX-ACCESS accessible-for-notify
    STATUS current
    DESCRIPTION
        "Parameter 'nr-lo' in event IKE.64"
    ::= { ikeEventObjects64 7 }

ike64-nr-hi OBJECT-TYPE
    SYNTAX Integer32
    MAX-ACCESS accessible-for-notify
    STATUS current
    DESCRIPTION
        "Parameter 'nr-hi' in event IKE.64"
    ::= { ikeEventObjects64 8 }

ikeEventObjects65 OBJECT-IDENTITY
    STATUS current
    DESCRIPTION
        "Event IKE.65
        A server rekey"
    ::= { ikeEventsGroup 65 }

ike65-ic-lo OBJECT-TYPE
    SYNTAX Integer32
    MAX-ACCESS accessible-for-notify
    STATUS current
    DESCRIPTION
        "Parameter 'ic-lo' in event IKE.65"
    ::= { ikeEventObjects65 1 }

ike65-ic-hi OBJECT-TYPE
    SYNTAX Integer32
    MAX-ACCESS accessible-for-notify
    STATUS current
    DESCRIPTION
        "Parameter 'ic-hi' in event IKE.65"
    ::= { ikeEventObjects65 2 }

ike65-rc-lo OBJECT-TYPE
    SYNTAX Integer32
    MAX-ACCESS accessible-for-notify
    STATUS current
    DESCRIPTION
        "Parameter 'rc-lo' in event IKE.65"
    ::= { ikeEventObjects65 3 }

ike65-rc-hi OBJECT-TYPE
    SYNTAX Integer32
    MAX-ACCESS accessible-for-notify
    STATUS current
    DESCRIPTION
        "Parameter 'rc-hi' in event IKE.65"
    ::= { ikeEventObjects65 4 }

ike65-nic-lo OBJECT-TYPE
    SYNTAX Integer32
    MAX-ACCESS accessible-for-notify
    STATUS current
    DESCRIPTION
        "Parameter 'nic-lo' in event IKE.65"
    ::= { ikeEventObjects65 5 }

ike65-nic-hi OBJECT-TYPE
    SYNTAX Integer32
    MAX-ACCESS accessible-for-notify
    STATUS current
    DESCRIPTION
        "Parameter 'nic-hi' in event IKE.65"
    ::= { ikeEventObjects65 6 }

ike65-nr-lo OBJECT-TYPE
    SYNTAX Integer32
    MAX-ACCESS accessible-for-notify
    STATUS current
    DESCRIPTION
        "Parameter 'nr-lo' in event IKE.65"
    ::= { ikeEventObjects65 7 }

ike65-nr-hi OBJECT-TYPE
    SYNTAX Integer32
    MAX-ACCESS accessible-for-notify
    STATUS current
    DESCRIPTION
        "Parameter 'nr-hi' in event IKE.65"
    ::= { ikeEventObjects65 8 }

ikeEventObjects66 OBJECT-IDENTITY
    STATUS current
    DESCRIPTION
        "Event IKE.66
        Server has generated new ids"
    ::= { ikeEventsGroup 66 }

ike66-ic-lo OBJECT-TYPE
    SYNTAX Integer32
    MAX-ACCESS accessible-for-notify
    STATUS current
    DESCRIPTION
        "Parameter 'ic-lo' in event IKE.66"
    ::= { ikeEventObjects66 1 }

ike66-ic-hi OBJECT-TYPE
    SYNTAX Integer32
    MAX-ACCESS accessible-for-notify
    STATUS current
    DESCRIPTION
        "Parameter 'ic-hi' in event IKE.66"
    ::= { ikeEventObjects66 2 }

ike66-rc-lo OBJECT-TYPE
    SYNTAX Integer32
    MAX-ACCESS accessible-for-notify
    STATUS current
    DESCRIPTION
        "Parameter 'rc-lo' in event IKE.66"
    ::= { ikeEventObjects66 3 }

ike66-rc-hi OBJECT-TYPE
    SYNTAX Integer32
    MAX-ACCESS accessible-for-notify
    STATUS current
    DESCRIPTION
        "Parameter 'rc-hi' in event IKE.66"
    ::= { ikeEventObjects66 4 }

ike66-nic-lo OBJECT-TYPE
    SYNTAX Integer32
    MAX-ACCESS accessible-for-notify
    STATUS current
    DESCRIPTION
        "Parameter 'nic-lo' in event IKE.66"
    ::= { ikeEventObjects66 5 }

ike66-nic-hi OBJECT-TYPE
    SYNTAX Integer32
    MAX-ACCESS accessible-for-notify
    STATUS current
    DESCRIPTION
        "Parameter 'nic-hi' in event IKE.66"
    ::= { ikeEventObjects66 6 }

ike66-nr-lo OBJECT-TYPE
    SYNTAX Integer32
    MAX-ACCESS accessible-for-notify
    STATUS current
    DESCRIPTION
        "Parameter 'nr-lo' in event IKE.66"
    ::= { ikeEventObjects66 7 }

ike66-nr-hi OBJECT-TYPE
    SYNTAX Integer32
    MAX-ACCESS accessible-for-notify
    STATUS current
    DESCRIPTION
        "Parameter 'nr-hi' in event IKE.66"
    ::= { ikeEventObjects66 8 }

ikeEventObjects67 OBJECT-IDENTITY
    STATUS current
    DESCRIPTION
        "Event IKE.67
        client is processing a tek payload"
    ::= { ikeEventsGroup 67 }

ike67-spi OBJECT-TYPE
    SYNTAX Integer32
    MAX-ACCESS accessible-for-notify
    STATUS current
    DESCRIPTION
        "Parameter 'spi' in event IKE.67"
    ::= { ikeEventObjects67 1 }

ike67-size OBJECT-TYPE
    SYNTAX Integer32
    MAX-ACCESS accessible-for-notify
    STATUS current
    DESCRIPTION
        "Parameter 'size' in event IKE.67"
    ::= { ikeEventObjects67 2 }

ikeEventObjects68 OBJECT-IDENTITY
    STATUS current
    DESCRIPTION
        "Event IKE.68
        client is deleting and old sa"
    ::= { ikeEventsGroup 68 }

ike68-spi OBJECT-TYPE
    SYNTAX Integer32
    MAX-ACCESS accessible-for-notify
    STATUS current
    DESCRIPTION
        "Parameter 'spi' in event IKE.68"
    ::= { ikeEventObjects68 1 }

ike68-reason OBJECT-TYPE
    SYNTAX DisplayString
    MAX-ACCESS accessible-for-notify
    STATUS current
    DESCRIPTION
        "Parameter 'reason' in event IKE.68"
    ::= { ikeEventObjects68 2 }

ikeEventObjects69 OBJECT-IDENTITY
    STATUS current
    DESCRIPTION
        "Event IKE.69
        timestamp rcvd or sent"
    ::= { ikeEventsGroup 69 }

ike69-rcvd-or-sent OBJECT-TYPE
    SYNTAX DisplayString
    MAX-ACCESS accessible-for-notify
    STATUS current
    DESCRIPTION
        "Parameter 'rcvd-or-sent' in event IKE.69"
    ::= { ikeEventObjects69 1 }

ike69-timestam OBJECT-TYPE
    SYNTAX Integer32
    MAX-ACCESS accessible-for-notify
    STATUS current
    DESCRIPTION
        "Parameter 'timestam' in event IKE.69"
    ::= { ikeEventObjects69 2 }

ike69-diff OBJECT-TYPE
    SYNTAX Integer32
    MAX-ACCESS accessible-for-notify
    STATUS current
    DESCRIPTION
        "Parameter 'diff' in event IKE.69"
    ::= { ikeEventObjects69 3 }

ikeEventObjects70 OBJECT-IDENTITY
    STATUS current
    DESCRIPTION
        "Event IKE.70
        Doing a DNS request"
    ::= { ikeEventsGroup 70 }

ike70-host-addr OBJECT-TYPE
    SYNTAX DisplayString
    MAX-ACCESS accessible-for-notify
    STATUS current
    DESCRIPTION
        "Parameter 'host-addr' in event IKE.70"
    ::= { ikeEventObjects70 1 }

ikeEventObjects71 OBJECT-IDENTITY
    STATUS current
    DESCRIPTION
        "Event IKE.71
        DNS reply"
    ::= { ikeEventsGroup 71 }

ike71-host-addr OBJECT-TYPE
    SYNTAX DisplayString
    MAX-ACCESS accessible-for-notify
    STATUS current
    DESCRIPTION
        "Parameter 'host-addr' in event IKE.71"
    ::= { ikeEventObjects71 1 }

ike71-IP-addr OBJECT-TYPE
    SYNTAX IpAddress
    MAX-ACCESS accessible-for-notify
    STATUS current
    DESCRIPTION
        "Parameter 'IP-addr' in event IKE.71"
    ::= { ikeEventObjects71 2 }

ikeEventObjects72 OBJECT-IDENTITY
    STATUS current
    DESCRIPTION
        "Event IKE.72
        DNS ERROR "
    ::= { ikeEventsGroup 72 }

ike72-host-addr OBJECT-TYPE
    SYNTAX DisplayString
    MAX-ACCESS accessible-for-notify
    STATUS current
    DESCRIPTION
        "Parameter 'host-addr' in event IKE.72"
    ::= { ikeEventObjects72 1 }

ike72-error-code OBJECT-TYPE
    SYNTAX Integer32
    MAX-ACCESS accessible-for-notify
    STATUS current
    DESCRIPTION
        "Parameter 'error-code' in event IKE.72"
    ::= { ikeEventObjects72 2 }

ikeEventObjects73 OBJECT-IDENTITY
    STATUS current
    DESCRIPTION
        "Event IKE.73
        There is an IP address for this domain in the domain list"
    ::= { ikeEventsGroup 73 }

ike73-IP-addr OBJECT-TYPE
    SYNTAX IpAddress
    MAX-ACCESS accessible-for-notify
    STATUS current
    DESCRIPTION
        "Parameter 'IP-addr' in event IKE.73"
    ::= { ikeEventObjects73 1 }

ike73-host-addr OBJECT-TYPE
    SYNTAX DisplayString
    MAX-ACCESS accessible-for-notify
    STATUS current
    DESCRIPTION
        "Parameter 'host-addr' in event IKE.73"
    ::= { ikeEventObjects73 2 }

ike73-ttr OBJECT-TYPE
    SYNTAX Integer32
    MAX-ACCESS accessible-for-notify
    STATUS current
    DESCRIPTION
        "Parameter 'ttr' in event IKE.73"
    ::= { ikeEventObjects73 3 }

ikeEventObjects74 OBJECT-IDENTITY
    STATUS current
    DESCRIPTION
        "Event IKE.74
        There is a new IP/domain in the domain list"
    ::= { ikeEventsGroup 74 }

ike74-IP-addr OBJECT-TYPE
    SYNTAX IpAddress
    MAX-ACCESS accessible-for-notify
    STATUS current
    DESCRIPTION
        "Parameter 'IP-addr' in event IKE.74"
    ::= { ikeEventObjects74 1 }

ike74-host-addr OBJECT-TYPE
    SYNTAX DisplayString
    MAX-ACCESS accessible-for-notify
    STATUS current
    DESCRIPTION
        "Parameter 'host-addr' in event IKE.74"
    ::= { ikeEventObjects74 2 }

ike74-ttr OBJECT-TYPE
    SYNTAX Integer32
    MAX-ACCESS accessible-for-notify
    STATUS current
    DESCRIPTION
        "Parameter 'ttr' in event IKE.74"
    ::= { ikeEventObjects74 3 }

ikeEventObjects75 OBJECT-IDENTITY
    STATUS current
    DESCRIPTION
        "Event IKE.75
        The entry DOMAIN/IP will be removed"
    ::= { ikeEventsGroup 75 }

ike75-host-addr OBJECT-TYPE
    SYNTAX DisplayString
    MAX-ACCESS accessible-for-notify
    STATUS current
    DESCRIPTION
        "Parameter 'host-addr' in event IKE.75"
    ::= { ikeEventObjects75 1 }

ike75-IP-addr OBJECT-TYPE
    SYNTAX IpAddress
    MAX-ACCESS accessible-for-notify
    STATUS current
    DESCRIPTION
        "Parameter 'IP-addr' in event IKE.75"
    ::= { ikeEventObjects75 2 }


ikeNotification1 NOTIFICATION-TYPE
    OBJECTS { 
              ike1-remote-addr, 
              ike1-template-number 
            }
    STATUS current
    DESCRIPTION
        "Notification of Event IKE.1

        Message: 'IKE($1)01:--------- Matching template (number $2) ---------'

        Parameters list:
              $1: ike1-remote-addr
              $2: ike1-template-number

        Matching template."
    ::= { ikeNotificationsPrefix 1 }

ikeNotification2 NOTIFICATION-TYPE
    OBJECTS { 
              ike2-remote-addr, 
              ike2-connection 
            }
    STATUS current
    DESCRIPTION
        "Notification of Event IKE.2

        Message: 'IKE($1)02:--------- Matching SA NEG (connection number $2) ---------'

        Parameters list:
              $1: ike2-remote-addr
              $2: ike2-connection

        Matching SA for negotiation."
    ::= { ikeNotificationsPrefix 2 }

ikeNotification3 NOTIFICATION-TYPE
    OBJECTS { 
              ike3-remote-addr 
            }
    STATUS current
    DESCRIPTION
        "Notification of Event IKE.3

        Message: 'IKE($1)03:--------- Decryption error ---------'

        Parameters list:
              $1: ike3-remote-addr

        There was an error decrypting the message."
    ::= { ikeNotificationsPrefix 3 }

ikeNotification4 NOTIFICATION-TYPE
    OBJECTS { 
              ike4-remote-addr 
            }
    STATUS current
    DESCRIPTION
        "Notification of Event IKE.4

        Message: 'IKE($1)04:--------- Retransmission ---------'

        Parameters list:
              $1: ike4-remote-addr

        Received message is a retransmission."
    ::= { ikeNotificationsPrefix 4 }

ikeNotification5 NOTIFICATION-TYPE
    OBJECTS { 
              ike5-remote-addr 
            }
    STATUS current
    DESCRIPTION
        "Notification of Event IKE.5

        Message: 'IKE($1)05:--------- Unable to initiate. Unknown destination ---------'

        Parameters list:
              $1: ike5-remote-addr

        Could not initiate IKE negotiation: unknown destination."
    ::= { ikeNotificationsPrefix 5 }

ikeNotification6 NOTIFICATION-TYPE
    OBJECTS { 
              ike6-remote-addr, 
              ike6-connection 
            }
    STATUS current
    DESCRIPTION
        "Notification of Event IKE.6

        Message: 'IKE($1)06:--------- Creating ISAKMP NEG (connection number $2) ---------'

        Parameters list:
              $1: ike6-remote-addr
              $2: ike6-connection

        Creating ISAKMP negotiation SA."
    ::= { ikeNotificationsPrefix 6 }

ikeNotification7 NOTIFICATION-TYPE
    OBJECTS { 
              ike7-remote-addr 
            }
    STATUS current
    DESCRIPTION
        "Notification of Event IKE.7

        Message: 'IKE($1)07:--------- Deleting ISAKMP NEG ---------'

        Parameters list:
              $1: ike7-remote-addr

        Deleting ISAKMP negotiation SA."
    ::= { ikeNotificationsPrefix 7 }

ikeNotification8 NOTIFICATION-TYPE
    OBJECTS { 
              ike8-remote-addr 
            }
    STATUS current
    DESCRIPTION
        "Notification of Event IKE.8

        Message: 'IKE($1)08:--------- Creating ISAKMP SA ---------'

        Parameters list:
              $1: ike8-remote-addr

        Creating ISAKMP SA."
    ::= { ikeNotificationsPrefix 8 }

ikeNotification9 NOTIFICATION-TYPE
    OBJECTS { 
              ike9-remote-addr, 
              ike9-message-id 
            }
    STATUS current
    DESCRIPTION
        "Notification of Event IKE.9

        Message: 'IKE($1)09:--------- Creating ISAKMP SA id (0x$2) ---------'

        Parameters list:
              $1: ike9-remote-addr
              $2: ike9-message-id

        Creating ISAKMP SA id."
    ::= { ikeNotificationsPrefix 9 }

ikeNotification10 NOTIFICATION-TYPE
    OBJECTS { 
              ike10-remote-addr, 
              ike10-ini-cookie-lo,
              ike10-ini-cookie-hi,
              ike10-res-cookie-lo,
              ike10-res-cookie-hi 
            }
    STATUS current
    DESCRIPTION
        "Notification of Event IKE.10

        Message: 'IKE($1)10:--------- Unable to make ISAKMP SA (cookies initiator:$2$3 responder:$4$5) ---------'

        Parameters list:
              $1: ike10-remote-addr
              $2: ike10-ini-cookie-lo
              $3: ike10-ini-cookie-hi
              $4: ike10-res-cookie-lo
              $5: ike10-res-cookie-hi

        Unable to create ISAKMP SA."
    ::= { ikeNotificationsPrefix 10 }

ikeNotification11 NOTIFICATION-TYPE
    OBJECTS { 
              ike11-remote-addr, 
              ike11-spi 
            }
    STATUS current
    DESCRIPTION
        "Notification of Event IKE.11

        Message: 'IKE($1)11:--------- Creating SA IN spi: 0x$2---------'

        Parameters list:
              $1: ike11-remote-addr
              $2: ike11-spi

        Creating SA for incoming packets."
    ::= { ikeNotificationsPrefix 11 }

ikeNotification12 NOTIFICATION-TYPE
    OBJECTS { 
              ike12-remote-addr, 
              ike12-spi 
            }
    STATUS current
    DESCRIPTION
        "Notification of Event IKE.12

        Message: 'IKE($1)12:--------- Creating SA OUT spi: 0x$2---------'

        Parameters list:
              $1: ike12-remote-addr
              $2: ike12-spi

        Creating SA for outgoing packets."
    ::= { ikeNotificationsPrefix 12 }

ikeNotification13 NOTIFICATION-TYPE
    OBJECTS { 
              ike13-remote-addr 
            }
    STATUS current
    DESCRIPTION
        "Notification of Event IKE.13

        Message: 'IKE($1)13:--------- Deleting AL ENTRY ---------'

        Parameters list:
              $1: ike13-remote-addr

        Deleting access list entry."
    ::= { ikeNotificationsPrefix 13 }

ikeNotification14 NOTIFICATION-TYPE
    OBJECTS { 
              ike14-remote-addr, 
              ike14-spi 
            }
    STATUS current
    DESCRIPTION
        "Notification of Event IKE.14

        Message: 'IKE($1)14:--------- Deleting SA IN spi: 0x$2 ---------'

        Parameters list:
              $1: ike14-remote-addr
              $2: ike14-spi

        Deleting SA for incoming packets."
    ::= { ikeNotificationsPrefix 14 }

ikeNotification15 NOTIFICATION-TYPE
    OBJECTS { 
              ike15-remote-addr, 
              ike15-spi 
            }
    STATUS current
    DESCRIPTION
        "Notification of Event IKE.15

        Message: 'IKE($1)15:--------- Deleting SA OUT spi: 0x$2 ---------'

        Parameters list:
              $1: ike15-remote-addr
              $2: ike15-spi

        Deleting SA for outgoing packets."
    ::= { ikeNotificationsPrefix 15 }

ikeNotification16 NOTIFICATION-TYPE
    OBJECTS { 
              ike16-remote-addr, 
              ike16-spi 
            }
    STATUS current
    DESCRIPTION
        "Notification of Event IKE.16

        Message: 'IKE($1)16:--------- KeepAlive Deleting SA (spi: 0x$2) ---------'

        Parameters list:
              $1: ike16-remote-addr
              $2: ike16-spi

        Keepalive expired: deleting SA."
    ::= { ikeNotificationsPrefix 16 }

ikeNotification17 NOTIFICATION-TYPE
    OBJECTS { 
              ike17-remote-addr 
            }
    STATUS current
    DESCRIPTION
        "Notification of Event IKE.17

        Message: 'IKE($1)17:--------- Purgetime SA NEG ---------'

        Parameters list:
              $1: ike17-remote-addr

        Purgetime expired for negotiation SA."
    ::= { ikeNotificationsPrefix 17 }

ikeNotification18 NOTIFICATION-TYPE
    OBJECTS { 
              ike18-remote-addr, 
              ike18-id,
              ike18-source,
              ike18-destination 
            }
    STATUS current
    DESCRIPTION
        "Notification of Event IKE.18

        Message: 'IKE($1)18:--------- Purgetime SA NEG II (id:0x$2 source:$3 destination:$4) ---------'

        Parameters list:
              $1: ike18-remote-addr
              $2: ike18-id
              $3: ike18-source
              $4: ike18-destination

        Purgetime expired for phase II negotiation SA."
    ::= { ikeNotificationsPrefix 18 }

ikeNotification19 NOTIFICATION-TYPE
    OBJECTS { 
              ike19-remote-addr 
            }
    STATUS current
    DESCRIPTION
        "Notification of Event IKE.19

        Message: 'IKE($1)19:--------- Isakmp SA negotiating I ---------'

        Parameters list:
              $1: ike19-remote-addr

        ISAKMP SA commencing phase I negotiation."
    ::= { ikeNotificationsPrefix 19 }

ikeNotification20 NOTIFICATION-TYPE
    OBJECTS { 
              ike20-remote-addr 
            }
    STATUS current
    DESCRIPTION
        "Notification of Event IKE.20

        Message: 'IKE($1)20:--------- Negotiation on Phase I. Phase II not allowed ---------'

        Parameters list:
              $1: ike20-remote-addr

        Negotiation on phase I: phase II not allowed."
    ::= { ikeNotificationsPrefix 20 }

ikeNotification21 NOTIFICATION-TYPE
    OBJECTS { 
              ike21-remote-addr 
            }
    STATUS current
    DESCRIPTION
        "Notification of Event IKE.21

        Message: 'IKE($1)21:--------- Invalid NegII or Isakmp SA ---------'

        Parameters list:
              $1: ike21-remote-addr

        Either ISAKMP SA or phase II negotiation information is invalid."
    ::= { ikeNotificationsPrefix 21 }

ikeNotification22 NOTIFICATION-TYPE
    OBJECTS { 
              ike22-remote-addr, 
              ike22-spi 
            }
    STATUS current
    DESCRIPTION
        "Notification of Event IKE.22

        Message: 'IKE($1)22:--------- Initiated Renegotiation Timer for SA OUT (spi: 0x$2) ---------'

        Parameters list:
              $1: ike22-remote-addr
              $2: ike22-spi

        Renegotiation timer for outgoing packets SA initiated."
    ::= { ikeNotificationsPrefix 22 }

ikeNotification23 NOTIFICATION-TYPE
    OBJECTS { 
              ike23-remote-addr, 
              ike23-spi 
            }
    STATUS current
    DESCRIPTION
        "Notification of Event IKE.23

        Message: 'IKE($1)23:--------- Renegotiation Timer for SA OUT expired (spi: 0x$2) ---------'

        Parameters list:
              $1: ike23-remote-addr
              $2: ike23-spi

        Renegotiation timer for outgoing packets SA expired."
    ::= { ikeNotificationsPrefix 23 }

ikeNotification24 NOTIFICATION-TYPE
    OBJECTS { 
              ike24-remote-addr 
            }
    STATUS current
    DESCRIPTION
        "Notification of Event IKE.24

        Message: 'IKE($1)24:--------- Attempt to renegotiate delayed ---------'

        Parameters list:
              $1: ike24-remote-addr

        Attempt to renegotiate delayed."
    ::= { ikeNotificationsPrefix 24 }

ikeNotification25 NOTIFICATION-TYPE
    OBJECTS { 
              ike25-remote-addr 
            }
    STATUS current
    DESCRIPTION
        "Notification of Event IKE.25

        Message: 'IKE($1)25:--------- Matching CRL ---------'

        Parameters list:
              $1: ike25-remote-addr

        Matching CRL (Certificate Revocation List)."
    ::= { ikeNotificationsPrefix 25 }

ikeNotification26 NOTIFICATION-TYPE
    OBJECTS { 
              ike26-remote-addr 
            }
    STATUS current
    DESCRIPTION
        "Notification of Event IKE.26

        Message: 'IKE($1)26:--------- Invalid ID information ---------'

        Parameters list:
              $1: ike26-remote-addr

        Invalid ID information."
    ::= { ikeNotificationsPrefix 26 }

ikeNotification27 NOTIFICATION-TYPE
    OBJECTS { 
              ike27-remote-addr 
            }
    STATUS current
    DESCRIPTION
        "Notification of Event IKE.27

        Message: 'IKE($1)27:--------- No Dir Info in SA ---------'

        Parameters list:
              $1: ike27-remote-addr

        No address information found in SA."
    ::= { ikeNotificationsPrefix 27 }

ikeNotification28 NOTIFICATION-TYPE
    OBJECTS { 
              ike28-remote-addr, 
              ike28-last-id 
            }
    STATUS current
    DESCRIPTION
        "Notification of Event IKE.28

        Message: 'IKE($1)28:--------- Isakmp SA negotiating II (last id 0x$2) ---------'

        Parameters list:
              $1: ike28-remote-addr
              $2: ike28-last-id

        ISAKMP SA commencing phase II negotiation."
    ::= { ikeNotificationsPrefix 28 }

ikeNotification29 NOTIFICATION-TYPE
    OBJECTS { 
              ike29-remote-addr 
            }
    STATUS current
    DESCRIPTION
        "Notification of Event IKE.29

        Message: 'IKE($1)29:--------- Negotiation from banned host stopped ---------'

        Parameters list:
              $1: ike29-remote-addr

        Negotiation from banned host stopped."
    ::= { ikeNotificationsPrefix 29 }

ikeNotification30 NOTIFICATION-TYPE
    OBJECTS { 
              ike30-remote-addr 
            }
    STATUS current
    DESCRIPTION
        "Notification of Event IKE.30

        Message: 'IKE($1)30:--------- DPD Deleting SAs ---------'

        Parameters list:
              $1: ike30-remote-addr

        DPD (Dead Peer Detection) system found a lost connection: deleting SAs."
    ::= { ikeNotificationsPrefix 30 }

ikeNotification31 NOTIFICATION-TYPE
    OBJECTS { 
              ike31-remote-addr 
            }
    STATUS current
    DESCRIPTION
        "Notification of Event IKE.31

        Message: 'IKE($1)31:--------- Max tunnel supported reached ---------'

        Parameters list:
              $1: ike31-remote-addr

        Maximum number of simultaneous tunnels reached."
    ::= { ikeNotificationsPrefix 31 }

ikeNotification32 NOTIFICATION-TYPE
    OBJECTS { 
              ike32-remote-addr 
            }
    STATUS current
    DESCRIPTION
        "Notification of Event IKE.32

        Message: 'IKE($1)32:--------- Renegotiation using DNAT ---------'

        Parameters list:
              $1: ike32-remote-addr

        Renegotiation using DNAT started."
    ::= { ikeNotificationsPrefix 32 }

ikeNotification33 NOTIFICATION-TYPE
    OBJECTS { 
              ike33-remote-addr 
            }
    STATUS current
    DESCRIPTION
        "Notification of Event IKE.33

        Message: 'IKE($1)33:--------- Lifetime changed ---------'

        Parameters list:
              $1: ike33-remote-addr

        SA lifetime counter changed."
    ::= { ikeNotificationsPrefix 33 }

ikeNotification34 NOTIFICATION-TYPE
    OBJECTS { 
              ike34-remote-addr 
            }
    STATUS current
    DESCRIPTION
        "Notification of Event IKE.34

        Message: 'IKE($1)34:--------- Searching Backup Peer ---------'

        Parameters list:
              $1: ike34-remote-addr

        Searching Backup peer."
    ::= { ikeNotificationsPrefix 34 }

ikeNotification35 NOTIFICATION-TYPE
    OBJECTS { 
              ike35-remote-addr, 
              ike35-connection 
            }
    STATUS current
    DESCRIPTION
        "Notification of Event IKE.35

        Message: 'IKE($1)35:--------- Renegotiation Timer for SA NEG expired (connection number $2) ---------'

        Parameters list:
              $1: ike35-remote-addr
              $2: ike35-connection

        Renegotiation Timer for negotiation SA expired."
    ::= { ikeNotificationsPrefix 35 }

ikeNotification36 NOTIFICATION-TYPE
    OBJECTS { 
              ike36-remote-addr 
            }
    STATUS current
    DESCRIPTION
        "Notification of Event IKE.36

        Message: 'IKE($1)36:--------- Local Starting Neg ---------'

        Parameters list:
              $1: ike36-remote-addr

        Local side starting negotiation."
    ::= { ikeNotificationsPrefix 36 }

ikeNotification37 NOTIFICATION-TYPE
    OBJECTS { 
              ike37-remote-addr 
            }
    STATUS current
    DESCRIPTION
        "Notification of Event IKE.37

        Message: 'IKE($1)37:--------- Remote Starting Neg ---------'

        Parameters list:
              $1: ike37-remote-addr

        Remote side starting negotiation."
    ::= { ikeNotificationsPrefix 37 }

ikeNotification38 NOTIFICATION-TYPE
    OBJECTS { 
              ike38-remote-addr 
            }
    STATUS current
    DESCRIPTION
        "Notification of Event IKE.38

        Message: 'IKE($1)38:--------- Local Starting BackUp Neg ---------'

        Parameters list:
              $1: ike38-remote-addr

        Local side starting Backup negotiation."
    ::= { ikeNotificationsPrefix 38 }

ikeNotification39 NOTIFICATION-TYPE
    OBJECTS { 
              ike39-remote-addr 
            }
    STATUS current
    DESCRIPTION
        "Notification of Event IKE.39

        Message: 'IKE($1)39:--------- Remote Starting BackUp Neg ---------'

        Parameters list:
              $1: ike39-remote-addr

        Remote side starting Backup negotiation."
    ::= { ikeNotificationsPrefix 39 }

ikeNotification40 NOTIFICATION-TYPE
    OBJECTS { 
              ike40-remote-addr, 
              ike40-spi 
            }
    STATUS current
    DESCRIPTION
        "Notification of Event IKE.40

        Message: 'IKE($1)40:------!!! CONNECTED spi 0x$2!!!------'

        Parameters list:
              $1: ike40-remote-addr
              $2: ike40-spi

        Tunnel correctly established."
    ::= { ikeNotificationsPrefix 40 }

ikeNotification41 NOTIFICATION-TYPE
    OBJECTS { 
              ike41-remote-addr, 
              ike41-spi 
            }
    STATUS current
    DESCRIPTION
        "Notification of Event IKE.41

        Message: 'IKE($1)41:------!!! DISCONNECTED spi 0x$2!!!------'

        Parameters list:
              $1: ike41-remote-addr
              $2: ike41-spi

        Tunnel disconnected."
    ::= { ikeNotificationsPrefix 41 }

ikeNotification42 NOTIFICATION-TYPE
    OBJECTS { 
              ike42-remote-addr, 
              ike42-message 
            }
    STATUS current
    DESCRIPTION
        "Notification of Event IKE.42

        Message: 'IKE($1): $2'

        Parameters list:
              $1: ike42-remote-addr
              $2: ike42-message

        Unexpected notification from remote side received."
    ::= { ikeNotificationsPrefix 42 }

ikeNotification43 NOTIFICATION-TYPE
    OBJECTS { 
              ike43-remote-addr, 
              ike43-message 
            }
    STATUS current
    DESCRIPTION
        "Notification of Event IKE.43

        Message: 'IKE($1): $2'

        Parameters list:
              $1: ike43-remote-addr
              $2: ike43-message

        Notification from remote side received."
    ::= { ikeNotificationsPrefix 43 }

ikeNotification44 NOTIFICATION-TYPE
    OBJECTS { 
              ike44-spi, 
              ike44-dst-addr,
              ike44-dest-mask,
              ike44-via-gw 
            }
    STATUS current
    DESCRIPTION
        "Notification of Event IKE.44

        Message: 'RRI. SPI 0x$1 dst $2/$3 via $4'

        Parameters list:
              $1: ike44-spi
              $2: ike44-dst-addr
              $3: ike44-dest-mask
              $4: ike44-via-gw

        A new tunnel has opened and the router has established a new static
        route so it can be back-propagated via RIP or OSPF (RRI or Remote
        Route Injection)."
    ::= { ikeNotificationsPrefix 44 }

ikeNotification45 NOTIFICATION-TYPE
    OBJECTS { 
              ike45-spi, 
              ike45-dst-addr,
              ike45-dest-mask,
              ike45-via-gw 
            }
    STATUS current
    DESCRIPTION
        "Notification of Event IKE.45

        Message: 'RRI Problem. SPI 0x$1 dst $2/$3 via $4'

        Parameters list:
              $1: ike45-spi
              $2: ike45-dst-addr
              $3: ike45-dest-mask
              $4: ike45-via-gw

        There was a problem establishing a static route for RRI."
    ::= { ikeNotificationsPrefix 45 }

ikeNotification46 NOTIFICATION-TYPE
    OBJECTS { 
              ike46-spi, 
              ike46-dst-addr,
              ike46-dest-mask,
              ike46-via-gw 
            }
    STATUS current
    DESCRIPTION
        "Notification of Event IKE.46

        Message: 'Clearing RRI. SPI 0x$1, dst $2/$3, via $4'

        Parameters list:
              $1: ike46-spi
              $2: ike46-dst-addr
              $3: ike46-dest-mask
              $4: ike46-via-gw

        RRI has cleared a static route."
    ::= { ikeNotificationsPrefix 46 }

ikeNotification47 NOTIFICATION-TYPE
    OBJECTS { 
              ike47-user-addr, 
              ike47-user-string 
            }
    STATUS current
    DESCRIPTION
        "Notification of Event IKE.47

        Message: 'IKE($1): User $2'

        Parameters list:
              $1: ike47-user-addr
              $2: ike47-user-string

        User is trying authentication."
    ::= { ikeNotificationsPrefix 47 }

ikeNotification48 NOTIFICATION-TYPE
    OBJECTS { 
              ike48-remote-addr, 
              ike48-iniciator,
              ike48-responder,
              ike48-spi 
            }
    STATUS current
    DESCRIPTION
        "Notification of Event IKE.48

        Message: '($1): Ready to open->(Inic=$2, Resp=$3) spi 0x$4'

        Parameters list:
              $1: ike48-remote-addr
              $2: ike48-iniciator
              $3: ike48-responder
              $4: ike48-spi

        Tunnel ready to be established."
    ::= { ikeNotificationsPrefix 48 }

ikeNotification49 NOTIFICATION-TYPE
    OBJECTS { 
              ike49-remote-addr, 
              ike49-iniciator,
              ike49-responder,
              ike49-spi 
            }
    STATUS current
    DESCRIPTION
        "Notification of Event IKE.49

        Message: '($1): Ready to close->(Inic=$2, Resp=$3) spi 0x$4'

        Parameters list:
              $1: ike49-remote-addr
              $2: ike49-iniciator
              $3: ike49-responder
              $4: ike49-spi

        Tunnel ready to be disconneted."
    ::= { ikeNotificationsPrefix 49 }

ikeNotification50 NOTIFICATION-TYPE
    OBJECTS { 
              ike50-address, 
              ike50-idname,
              ike50-protocolnumber,
              ike50-portnumber,
              ike50-idtype 
            }
    STATUS current
    DESCRIPTION
        "Notification of Event IKE.50

        Message: '($1): Text Identification Payload, id $2, protocol $3, port $4, type $5'

        Parameters list:
              $1: ike50-address
              $2: ike50-idname
              $3: ike50-protocolnumber
              $4: ike50-portnumber
              $5: ike50-idtype

        Text Identification Payload registered."
    ::= { ikeNotificationsPrefix 50 }

ikeNotification51 NOTIFICATION-TYPE
    OBJECTS { 
              ike51-address, 
              ike51-idaddress,
              ike51-protocolnumber,
              ike51-portnumber,
              ike51-idtype 
            }
    STATUS current
    DESCRIPTION
        "Notification of Event IKE.51

        Message: '($1): IP Identification Payload, id $2, protocol $3, port $4, type $5'

        Parameters list:
              $1: ike51-address
              $2: ike51-idaddress
              $3: ike51-protocolnumber
              $4: ike51-portnumber
              $5: ike51-idtype

        IP Identification Payload registered."
    ::= { ikeNotificationsPrefix 51 }

ikeNotification52 NOTIFICATION-TYPE
    OBJECTS { 
              ike52-remote-addr, 
              ike52-spi,
              ike52-remote-client 
            }
    STATUS current
    DESCRIPTION
        "Notification of Event IKE.52

        Message: 'IKE($1)52:---------  Connection Event spi 0x$2 remote-client $3 ---------'

        Parameters list:
              $1: ike52-remote-addr
              $2: ike52-spi
              $3: ike52-remote-client

        Periodic information of the established tunnel."
    ::= { ikeNotificationsPrefix 52 }

ikeNotification53 NOTIFICATION-TYPE
    OBJECTS { 
              ike53-remote-addr, 
              ike53-attribute-string 
            }
    STATUS current
    DESCRIPTION
        "Notification of Event IKE.53

        Message: 'IKE($1): $2'

        Parameters list:
              $1: ike53-remote-addr
              $2: ike53-attribute-string

        Attribute string registered"
    ::= { ikeNotificationsPrefix 53 }

ikeNotification54 NOTIFICATION-TYPE
    OBJECTS { 
              ike54-remote-addr, 
              ike54-info-string 
            }
    STATUS current
    DESCRIPTION
        "Notification of Event IKE.54

        Message: 'IKE($1): Info: $2'

        Parameters list:
              $1: ike54-remote-addr
              $2: ike54-info-string

        Information string registered"
    ::= { ikeNotificationsPrefix 54 }

ikeNotification55 NOTIFICATION-TYPE
    OBJECTS { 
              ike55-sa-conn-id, 
              ike55-old-src-port,
              ike55-old-dst-port,
              ike55-new-src-port,
              ike55-new-dst-port 
            }
    STATUS current
    DESCRIPTION
        "Notification of Event IKE.55

        Message: 'UDP Port changed for SA with connid:$1, ($2-$3)=>($4-$5)'

        Parameters list:
              $1: ike55-sa-conn-id
              $2: ike55-old-src-port
              $3: ike55-old-dst-port
              $4: ike55-new-src-port
              $5: ike55-new-dst-port

        There is been a change on the source or destination port for this SA"
    ::= { ikeNotificationsPrefix 55 }

ikeNotification56 NOTIFICATION-TYPE
    OBJECTS { 
              ike56-message, 
              ike56-dst-ip,
              ike56-group 
            }
    STATUS current
    DESCRIPTION
        "Notification of Event IKE.56

        Message: 'GDOI client messsage $1 sent to $2 group $3'

        Parameters list:
              $1: ike56-message
              $2: ike56-dst-ip
              $3: ike56-group

        A GDOI client message has been sent"
    ::= { ikeNotificationsPrefix 56 }

ikeNotification57 NOTIFICATION-TYPE
    OBJECTS { 
              ike57-message, 
              ike57-src-ip,
              ike57-group 
            }
    STATUS current
    DESCRIPTION
        "Notification of Event IKE.57

        Message: 'GDOI client messsage $1 received from $2 group $3'

        Parameters list:
              $1: ike57-message
              $2: ike57-src-ip
              $3: ike57-group

        A GDOI client message has been received"
    ::= { ikeNotificationsPrefix 57 }

ikeNotification58 NOTIFICATION-TYPE
    OBJECTS { 
              ike58-message, 
              ike58-dst-ip,
              ike58-group 
            }
    STATUS current
    DESCRIPTION
        "Notification of Event IKE.58

        Message: 'GDOI server messsage $1 sent to $2 group $3'

        Parameters list:
              $1: ike58-message
              $2: ike58-dst-ip
              $3: ike58-group

        A GDOI server message has been sent"
    ::= { ikeNotificationsPrefix 58 }

ikeNotification59 NOTIFICATION-TYPE
    OBJECTS { 
              ike59-message, 
              ike59-src-ip,
              ike59-group 
            }
    STATUS current
    DESCRIPTION
        "Notification of Event IKE.59

        Message: 'GDOI server messsage $1 rcvd from $2 group $3'

        Parameters list:
              $1: ike59-message
              $2: ike59-src-ip
              $3: ike59-group

        A GDOI server message has been sent"
    ::= { ikeNotificationsPrefix 59 }

ikeNotification60 NOTIFICATION-TYPE
    OBJECTS { 
              ike60-error 
            }
    STATUS current
    DESCRIPTION
        "Notification of Event IKE.60

        Message: 'GDOI client error: $1'

        Parameters list:
              $1: ike60-error

        A GDOI client error"
    ::= { ikeNotificationsPrefix 60 }

ikeNotification61 NOTIFICATION-TYPE
    OBJECTS { 
              ike61-error 
            }
    STATUS current
    DESCRIPTION
        "Notification of Event IKE.61

        Message: 'GDOI server error: $1'

        Parameters list:
              $1: ike61-error

        A GDOI server error"
    ::= { ikeNotificationsPrefix 61 }

ikeNotification62 NOTIFICATION-TYPE
    OBJECTS { 
              ike62-spi, 
              ike62-srIP,
              ike62-dstIP,
              ike62-prot,
              ike62-sport,
              ike62-dport 
            }
    STATUS current
    DESCRIPTION
        "Notification of Event IKE.62

        Message: 'GDOI client acl added spi $1 src $2 dst $3 prot $4 sport $5 dport $6'

        Parameters list:
              $1: ike62-spi
              $2: ike62-srIP
              $3: ike62-dstIP
              $4: ike62-prot
              $5: ike62-sport
              $6: ike62-dport

        A GDOI client has added a new acl"
    ::= { ikeNotificationsPrefix 62 }

ikeNotification63 NOTIFICATION-TYPE
    OBJECTS { 
              ike63-spi, 
              ike63-lifetime 
            }
    STATUS current
    DESCRIPTION
        "Notification of Event IKE.63

        Message: 'GDOI client SAs created spi $1 lifetime $2'

        Parameters list:
              $1: ike63-spi
              $2: ike63-lifetime

        A GDOI client has created new in out sas"
    ::= { ikeNotificationsPrefix 63 }

ikeNotification64 NOTIFICATION-TYPE
    OBJECTS { 
              ike64-ic-lo, 
              ike64-ic-hi,
              ike64-rc-lo,
              ike64-rc-hi,
              ike64-nic-lo,
              ike64-nic-hi,
              ike64-nr-lo,
              ike64-nr-hi 
            }
    STATUS current
    DESCRIPTION
        "Notification of Event IKE.64

        Message: 'GDOI rekey ini:0x$1$2 res:0x$3$4 to ini:0x$5$6 res:0x$7$8'

        Parameters list:
              $1: ike64-ic-lo
              $2: ike64-ic-hi
              $3: ike64-rc-lo
              $4: ike64-rc-hi
              $5: ike64-nic-lo
              $6: ike64-nic-hi
              $7: ike64-nr-lo
              $8: ike64-nr-hi

        A client rekey"
    ::= { ikeNotificationsPrefix 64 }

ikeNotification65 NOTIFICATION-TYPE
    OBJECTS { 
              ike65-ic-lo, 
              ike65-ic-hi,
              ike65-rc-lo,
              ike65-rc-hi,
              ike65-nic-lo,
              ike65-nic-hi,
              ike65-nr-lo,
              ike65-nr-hi 
            }
    STATUS current
    DESCRIPTION
        "Notification of Event IKE.65

        Message: 'GDOI server rekey ini:0x$1$2 res:0x$3$4 to ini:0x$5$6 res:0x$7$8'

        Parameters list:
              $1: ike65-ic-lo
              $2: ike65-ic-hi
              $3: ike65-rc-lo
              $4: ike65-rc-hi
              $5: ike65-nic-lo
              $6: ike65-nic-hi
              $7: ike65-nr-lo
              $8: ike65-nr-hi

        A server rekey"
    ::= { ikeNotificationsPrefix 65 }

ikeNotification66 NOTIFICATION-TYPE
    OBJECTS { 
              ike66-ic-lo, 
              ike66-ic-hi,
              ike66-rc-lo,
              ike66-rc-hi,
              ike66-nic-lo,
              ike66-nic-hi,
              ike66-nr-lo,
              ike66-nr-hi 
            }
    STATUS current
    DESCRIPTION
        "Notification of Event IKE.66

        Message: 'GDOI server new ids ini:0x$1$2 res:0x$3$4 to ini:0x$5$6 res:0x$7$8'

        Parameters list:
              $1: ike66-ic-lo
              $2: ike66-ic-hi
              $3: ike66-rc-lo
              $4: ike66-rc-hi
              $5: ike66-nic-lo
              $6: ike66-nic-hi
              $7: ike66-nr-lo
              $8: ike66-nr-hi

        Server has generated new ids"
    ::= { ikeNotificationsPrefix 66 }

ikeNotification67 NOTIFICATION-TYPE
    OBJECTS { 
              ike67-spi, 
              ike67-size 
            }
    STATUS current
    DESCRIPTION
        "Notification of Event IKE.67

        Message: 'GDOI client tek payload received spi $1 size $2'

        Parameters list:
              $1: ike67-spi
              $2: ike67-size

        client is processing a tek payload"
    ::= { ikeNotificationsPrefix 67 }

ikeNotification68 NOTIFICATION-TYPE
    OBJECTS { 
              ike68-spi, 
              ike68-reason 
            }
    STATUS current
    DESCRIPTION
        "Notification of Event IKE.68

        Message: 'GDOI client sa $1 deleted, reason $2'

        Parameters list:
              $1: ike68-spi
              $2: ike68-reason

        client is deleting and old sa"
    ::= { ikeNotificationsPrefix 68 }

ikeNotification69 NOTIFICATION-TYPE
    OBJECTS { 
              ike69-rcvd-or-sent, 
              ike69-timestam,
              ike69-diff 
            }
    STATUS current
    DESCRIPTION
        "Notification of Event IKE.69

        Message: 'GDOI timestamp $1: $2 server diff $3'

        Parameters list:
              $1: ike69-rcvd-or-sent
              $2: ike69-timestam
              $3: ike69-diff

        timestamp rcvd or sent"
    ::= { ikeNotificationsPrefix 69 }

ikeNotification70 NOTIFICATION-TYPE
    OBJECTS { 
              ike70-host-addr 
            }
    STATUS current
    DESCRIPTION
        "Notification of Event IKE.70

        Message: 'DNS request: $1'

        Parameters list:
              $1: ike70-host-addr

        Doing a DNS request"
    ::= { ikeNotificationsPrefix 70 }

ikeNotification71 NOTIFICATION-TYPE
    OBJECTS { 
              ike71-host-addr, 
              ike71-IP-addr 
            }
    STATUS current
    DESCRIPTION
        "Notification of Event IKE.71

        Message: 'DNS reply: $1 ($2)'

        Parameters list:
              $1: ike71-host-addr
              $2: ike71-IP-addr

        DNS reply"
    ::= { ikeNotificationsPrefix 71 }

ikeNotification72 NOTIFICATION-TYPE
    OBJECTS { 
              ike72-host-addr, 
              ike72-error-code 
            }
    STATUS current
    DESCRIPTION
        "Notification of Event IKE.72

        Message: 'DNS ERROR for $1 (CODE: $2)'

        Parameters list:
              $1: ike72-host-addr
              $2: ike72-error-code

        DNS ERROR "
    ::= { ikeNotificationsPrefix 72 }

ikeNotification73 NOTIFICATION-TYPE
    OBJECTS { 
              ike73-IP-addr, 
              ike73-host-addr,
              ike73-ttr 
            }
    STATUS current
    DESCRIPTION
        "Notification of Event IKE.73

        Message: 'DNS IKE cache: Using $1 for $2 (Time to renegotiation < $3)'

        Parameters list:
              $1: ike73-IP-addr
              $2: ike73-host-addr
              $3: ike73-ttr

        There is an IP address for this domain in the domain list"
    ::= { ikeNotificationsPrefix 73 }

ikeNotification74 NOTIFICATION-TYPE
    OBJECTS { 
              ike74-IP-addr, 
              ike74-host-addr,
              ike74-ttr 
            }
    STATUS current
    DESCRIPTION
        "Notification of Event IKE.74

        Message: 'DNS IKE cache: $1 assigned for $2 (Time to renegotiation $3)'

        Parameters list:
              $1: ike74-IP-addr
              $2: ike74-host-addr
              $3: ike74-ttr

        There is a new IP/domain in the domain list"
    ::= { ikeNotificationsPrefix 74 }

ikeNotification75 NOTIFICATION-TYPE
    OBJECTS { 
              ike75-host-addr, 
              ike75-IP-addr 
            }
    STATUS current
    DESCRIPTION
        "Notification of Event IKE.75

        Message: 'DNS IKE cache: Purgetime expired. $1 ($2) deleted'

        Parameters list:
              $1: ike75-host-addr
              $2: ike75-IP-addr

        The entry DOMAIN/IP will be removed"
    ::= { ikeNotificationsPrefix 75 }


END
