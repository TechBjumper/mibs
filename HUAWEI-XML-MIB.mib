--
-- HUAWEI-XML-MIB.mib
-- MIB generated by MG-SOFT Visual MIB Builder Version 3.0 Build 253
-- Friday, September 29, 2006 at 17:00:01
--

--  HUAWEI-XML-MIB.mib
-- MIB generated by MG-SOFT Visual MIB Builder Version 3.0 Build 253
-- Monday, September 25, 2006 at 18:30:34
-- 
--  ============================================================================
-- Copyright (C) 2003 by  HUAWEI TECHNOLOGIES. All rights reserved.
-- 
-- Description:  
-- Reference:  
-- Version: V3.00
-- History:
-- liu chenglong 2003-04-28 Added IPR Decriptions and updated all MIB version to V3.00
-- ============================================================================

	HUAWEI-XML-MIB DEFINITIONS ::= BEGIN
 
		IMPORTS
			enterprises			
				FROM RFC1155-SMI			
			IpAddress, Integer32, OBJECT-TYPE, MODULE-IDENTITY			
				FROM SNMPv2-SMI			
			DateAndTime			
				FROM SNMPv2-TC;
	
	
--  April 28, 2003 at 09:00 GMT
-- November 29, 2002 at 09:00 GMT
		huawei MODULE-IDENTITY 
			LAST-UPDATED "200304280900Z"		-- April 28, 2003 at 09:00 GMT
			ORGANIZATION 
				"Fix-Net Dept, Huawei Technologies Co.,Ltd."
			CONTACT-INFO 
				"Floor 5, Block 4, R&D Building,
				Huawei Longgang Production Base,
				Shenzhen,  P.R.C.
				http://www.huawei.com
				Zip:518057
				"
			DESCRIPTION 
				"huawei common oid   mib defintion.	"
			REVISION "200211290900Z"		-- November 29, 2002 at 09:00 GMT
			DESCRIPTION
				"
				V2.00	
				reunification version based on the  Fix-Net MIBs baseline by the MIB Standard community.
				"
			::= { enterprises 2011 }
		
	
	
--
-- Node definitions
--
	
--  Node definitions
-- 
-- 1.3.6.1.4.1.2011.5
		-- 1.3.6.1.4.1.2011.5
		huaweiMgmt OBJECT IDENTIFIER ::= { huawei 5 }
		
--  1.3.6.1.4.1.2011.5.103
		-- 1.3.6.1.4.1.2011.5.103
		hwNetconfItem OBJECT IDENTIFIER ::= { huaweiMgmt 103 }
		
--  1.3.6.1.4.1.2011.5.103.1
		-- 1.3.6.1.4.1.2011.5.103.1
		hwNetconfUserTable OBJECT-TYPE
			SYNTAX SEQUENCE OF HwNetconfUserEntry
			MAX-ACCESS not-accessible
			STATUS current
			DESCRIPTION
				"Description."
			::= { hwNetconfItem 1 }
		
--  1.3.6.1.4.1.2011.5.103.1.1
		-- 1.3.6.1.4.1.2011.5.103.1.1
		hwNetconfUserEntry OBJECT-TYPE
			SYNTAX HwNetconfUserEntry
			MAX-ACCESS not-accessible
			STATUS current
			DESCRIPTION
				"Description."
			INDEX { hwNetconfUserID }
			::= { hwNetconfUserTable 1 }
		
		HwNetconfUserEntry ::=
			SEQUENCE { 
				hwNetconfUserID
					Integer32,
				hwNetconfUserName
					OCTET STRING,
				hwNetconfUserType
					Integer32,
				hwNetconfUserIp
					IpAddress,
				hwNetconfUserLoginTime
					DateAndTime
			 }

--  1.3.6.1.4.1.2011.5.103.1.1.1
		-- 1.3.6.1.4.1.2011.5.103.1.1.1
		hwNetconfUserID OBJECT-TYPE
			SYNTAX Integer32 (1..65535)
			MAX-ACCESS not-accessible
			STATUS current
			DESCRIPTION
				"Client ID
				"
			::= { hwNetconfUserEntry 1 }
		
--  1.3.6.1.4.1.2011.5.103.1.1.2
		-- 1.3.6.1.4.1.2011.5.103.1.1.2
		hwNetconfUserName OBJECT-TYPE
			SYNTAX OCTET STRING (SIZE (1..16))
			MAX-ACCESS read-only
			STATUS current
			DESCRIPTION
				"User name 
				"
			::= { hwNetconfUserEntry 2 }
		
--  1.3.6.1.4.1.2011.5.103.1.1.3
		-- 1.3.6.1.4.1.2011.5.103.1.1.3
		hwNetconfUserType OBJECT-TYPE
			SYNTAX Integer32
			MAX-ACCESS read-only
			STATUS current
			DESCRIPTION
				"Type of user(web user xml user)."
			::= { hwNetconfUserEntry 3 }
		
--  1.3.6.1.4.1.2011.5.103.1.1.4
		-- 1.3.6.1.4.1.2011.5.103.1.1.4
		hwNetconfUserIp OBJECT-TYPE
			SYNTAX IpAddress
			MAX-ACCESS read-only
			STATUS current
			DESCRIPTION
				"The IP address of client."
			::= { hwNetconfUserEntry 4 }
		
--  1.3.6.1.4.1.2011.5.103.1.1.5
		-- 1.3.6.1.4.1.2011.5.103.1.1.5
		hwNetconfUserLoginTime OBJECT-TYPE
			SYNTAX DateAndTime
			MAX-ACCESS read-only
			STATUS current
			DESCRIPTION
				"Login time of Client."
			::= { hwNetconfUserEntry 5 }
		
--  1.3.6.1.4.1.2011.5.103.2
		-- 1.3.6.1.4.1.2011.5.103.2
		hwNetconfResultTable OBJECT-TYPE
			SYNTAX SEQUENCE OF HwNetconfResultEntry
			MAX-ACCESS not-accessible
			STATUS current
			DESCRIPTION
				"Description."
			::= { hwNetconfItem 2 }
		
--  1.3.6.1.4.1.2011.5.103.2.1
		-- 1.3.6.1.4.1.2011.5.103.2.1
		hwNetconfResultEntry OBJECT-TYPE
			SYNTAX HwNetconfResultEntry
			MAX-ACCESS not-accessible
			STATUS current
			DESCRIPTION
				"Description."
			INDEX { hwNetconfResultNo }
			::= { hwNetconfResultTable 1 }
		
		HwNetconfResultEntry ::=
			SEQUENCE { 
				hwNetconfResultNo
					Integer32,
				hwNetconfResultInfo
					Integer32,
				hwNetconfResultType
					Integer32,
				hwNetconfResultStartTime
					DateAndTime,
				hwNetconfResultEndTime
					DateAndTime
			 }

--  1.3.6.1.4.1.2011.5.103.2.1.1
		-- 1.3.6.1.4.1.2011.5.103.2.1.1
		hwNetconfResultNo OBJECT-TYPE
			SYNTAX Integer32
			MAX-ACCESS not-accessible
			STATUS current
			DESCRIPTION
				"Number of order"
			::= { hwNetconfResultEntry 1 }
		
--  1.3.6.1.4.1.2011.5.103.2.1.2
		-- 1.3.6.1.4.1.2011.5.103.2.1.2
		hwNetconfResultInfo OBJECT-TYPE
			SYNTAX Integer32
			MAX-ACCESS read-only
			STATUS current
			DESCRIPTION
				"Type of resultinformation"
			::= { hwNetconfResultEntry 2 }
		
--  1.3.6.1.4.1.2011.5.103.2.1.3
		-- 1.3.6.1.4.1.2011.5.103.2.1.3
		hwNetconfResultType OBJECT-TYPE
			SYNTAX Integer32
			MAX-ACCESS read-only
			STATUS current
			DESCRIPTION
				"command type: 1.save 2.load"
			::= { hwNetconfResultEntry 3 }
		
--  1.3.6.1.4.1.2011.5.103.2.1.4
		-- 1.3.6.1.4.1.2011.5.103.2.1.4
		hwNetconfResultStartTime OBJECT-TYPE
			SYNTAX DateAndTime
			MAX-ACCESS read-only
			STATUS current
			DESCRIPTION
				"the start time of a command."
			::= { hwNetconfResultEntry 4 }
		
--  1.3.6.1.4.1.2011.5.103.2.1.5
		-- 1.3.6.1.4.1.2011.5.103.2.1.5
		hwNetconfResultEndTime OBJECT-TYPE
			SYNTAX DateAndTime
			MAX-ACCESS read-only
			STATUS current
			DESCRIPTION
				"the end time of a command."
			::= { hwNetconfResultEntry 5 }
		
	
	END

--
-- HUAWEI-XML-MIB.mib
--
