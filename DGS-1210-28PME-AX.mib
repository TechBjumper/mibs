--------------------------------------------------------------------------------

--  Revision 
-- Date        Version   Author         Chanage Description
--
-- 2014/12/05  6.11.013   D-Link         1.Add sysPortCtrlCapability, sysDhcpAutoImage, 
--																			 	 sysBootupConfigID, sysBootupImage, 
--																				 cosBandwidthEffectiveRX and cosBandwidthEffectiveTX.
--
-- 2014/07/30  6.11.009   D-Link         1.sync release version with firmware.
--
-- 2014/07/11  6.11.R005  D-Link         1.Add MultiIPInterface.
--
-- 2014/06/26  6.11.R004B D-Link         1.Add  impbLogState
--                                       2.Modify aacAccounting description.
--
-- 2014/06/04  6.11.R001  D-Link         1.Add RADIUS and TACACS+ accounting.
--                                       2.Add sfpVendorInfoTable.
--                                       3.Add DdmCtrl and ddmInfo.
--
-- 2014/06/04  6.10.B023 D-Link         1.Added RADIUS & TACACS+ accounting
--
-- 2014/05/30  6.10.B022 D-Link         1.Add GreenSetting.
--                                      2.Add PortUpLinkTime.
--
-- 2014/03/18  6.10.005  D-Link         1.Support DNA tool
--                                      2.Add companydot3azEEE.
--
-- 2014/03/07  4.00.B012 D-Link         1.Add poePortForcePDDetect object for 59111 IOT issue with HIKVision Camera on DGS-1210-28P
--
-- 2014/03/06  6.10.004  D-Link         1.ACL rule support vlan based mode 
--                                      2.Modify sysPortCtrlMediumType value. 
--
-- 2014/02/19  6.10.003  D-Link         1.Changed the sysPortCtrlMediumType valuelist.
--                                      2.Changed the sysPortCtrlType  valuelist.
--
-- 2013/12/06  6.10.002  D-Link         1.Hardware version changed from C1 to A1
--
-- 2013/11/21  6.10.001  D-Link         1.Initial version.
-- 
--  Revision End 

--------------------------------------------------------------------------------

        DGS-1210-28PME-AX DEFINITIONS ::= BEGIN

IMPORTS 
   MODULE-IDENTITY, OBJECT-TYPE, 
   enterprises, IpAddress, Integer32, Unsigned32, TimeTicks, Counter32
                                                  FROM SNMPv2-SMI 
   InetAddress                                    FROM INET-ADDRESS-MIB                                                  
   InterfaceIndex,InterfaceIndexOrZero    
                                                  FROM IF-MIB
   SnmpAdminString,SnmpEngineID,SnmpSecurityLevel FROM SNMP-FRAMEWORK-MIB 
   dot1dBridge, dot1dBasePortEntry, dot1dBasePort FROM BRIDGE-MIB                                                  
   RowStatus, TruthValue, DisplayString, 
   TEXTUAL-CONVENTION, MacAddress                 FROM SNMPv2-TC
   VlanId                                         FROM Q-BRIDGE-MIB
   AddressFamilyNumbers                           FROM IANA-ADDRESS-FAMILY-NUMBERS-MIB;
   
        

    d-link						OBJECT IDENTIFIER ::= { enterprises 171 }  
    dlink-products				OBJECT IDENTIFIER ::= { d-link 10 }
    dlink-DGS12XXSeriesProd	    OBJECT IDENTIFIER ::= { dlink-products 76}
    dgs-1210-28pme			OBJECT IDENTIFIER ::= { dlink-DGS12XXSeriesProd 30 }  
    dgs-1210-28pmeax					OBJECT IDENTIFIER ::= { dgs-1210-28pme 1 }  
   
VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32

PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING


BridgeId ::= TEXTUAL-CONVENTION
     STATUS  current
     DESCRIPTION
           "The Bridge-Identifier as used in the
           Spanning Tree
           Protocol to uniquely identify a bridge.  Its first two
           octets (in network byte order) contain a priority
           value and its last 6 octets contain the MAC address
           used to refer to a bridge in a unique fashion
           (typically, the numerically smallest MAC address
           of all ports on the bridge).
           Several objects in this MIB module represent values of
           timers used by the Spanning Tree Protocol.  In this
           MIB, these timers have values in units of hundreths of
           a second (i.e. 1/100 secs).
           These timers, when stored in a Spanning Tree Protocol's
           BPDU, are in units of 1/256 seconds.  Note, however,
           that 802.1D-1990 specifies a settable granularity of
           no more than 1 second for these timers.  To avoid
           ambiguity, a data type is defined here as a textual
           convention and all representation of these timers
           in this MIB module are defined using this data type.  An
           algorithm is also defined for converting between the
           different units, to ensure a timer's value is not                                  distorted by multiple conversions."
     SYNTAX          OCTET STRING (SIZE (8))
     
Timeout ::= TEXTUAL-CONVENTION
     DISPLAY-HINT "d4"
     STATUS       current
     DESCRIPTION
           "A STP timer in units of 1/100 seconds
           
            To convert a Timeout value into a value in units of
            1/256 seconds, the following algorithm should be used:
           
                 b  = floor( (n * 256) / 100)
            
            where:
                 floor   =  quotient [ignore remainder]
                 n is the value in 1/100 second units
                 b is the value in 1/256 second units
                                                                                               To convert the value from 1/256 second units back to
            1/100 seconds, the following algorithm should be used:
            
                 n = ceiling( (b * 100) / 256)
            
            where:
                  ceiling =  quotient [if remainder is 0], or
                             quotient + 1 [if remainder is non-zero]
                  n is the value in 1/100 second units
                  b is the value in 1/256 second units
             
             Note: it is important that the arithmetic operations are
             done in the order specified (i.e., multiply first, divide
             second)."
     SYNTAX       INTEGER

 LldpManAddress ::= TEXTUAL-CONVENTION
    STATUS      current
    DESCRIPTION
            "The value of a management address associated with the LLDP
            agent that may be used to reach higher layer entities to
            assist discovery by network management.

            It should be noted that appropriate security credentials,
            such as SNMP engineId, may be required to access the LLDP
            agent using a management address.  These necessary credentials
            should be known by the network management and the objects
            associated with the credentials are not included in the
            LLDP agent."
    SYNTAX      OCTET STRING (SIZE (1..31))
         
 OwnerString ::= TEXTUAL-CONVENTION
     STATUS current
     DESCRIPTION
         "This data type is used to model an administratively
         assigned name of the owner of a resource. Implementations
         must accept values composed of well-formed NVT ASCII
         sequences. In addition, implementations should accept
         values composed of well-formed UTF-8 sequences.

         It is suggested that this name contain one or more of
         the following: IP address, management station name,
         network manager's name, location, or phone number.
         In some cases the agent itself will be the owner of
         an entry.  In these cases, this string shall be set
         to a string starting with 'monitor'.

         SNMP access control is articulated entirely in terms
         of the contents of MIB views; access to a particular
         SNMP object instance depends only upon its presence
         or absence in a particular MIB view and never upon
         its value or the value of related object instances.
         Thus, objects of this type afford resolution of
         resource contention only among cooperating
         managers; they realize no access control function
         with respect to uncooperative parties."
     SYNTAX OCTET STRING (SIZE (0..127))

 RmonStatus ::= TEXTUAL-CONVENTION
     STATUS current
     DESCRIPTION
         "The status of a table entry.

         Setting this object to the value invalid(4) has the
         effect of invalidating the corresponding entry.
         That is, it effectively disassociates the mapping
         identified with said entry.
         It is an implementation-specific matter as to whether
         the agent removes an invalidated entry from the table.
         Accordingly, management stations must be prepared to
         receive tabular information from agents that corresponds
         to entries currently not in use.  Proper
         interpretation of such entries requires examination
         of the relevant RmonStatus object.

         An existing instance of this object cannot be set to
         createRequest(2).  This object may only be set to
         createRequest(2) when this instance is created.  When
         this object is created, the agent may wish to create
         supplemental object instances with default values
         to complete a conceptual row in this table.  Because the

         creation of these default objects is entirely at the option
         of the agent, the manager must not assume that any will be
         created, but may make use of any that are created.
         Immediately after completing the create operation, the agent
         must set this object to underCreation(3).

         When in the underCreation(3) state, an entry is allowed to
         exist in a possibly incomplete, possibly inconsistent state,
         usually to allow it to be modified in multiple PDUs.  When in
         this state, an entry is not fully active.
         Entries shall exist in the underCreation(3) state until
         the management station is finished configuring the entry
         and sets this object to valid(1) or aborts, setting this
         object to invalid(4).  If the agent determines that an
         entry has been in the underCreation(3) state for an
         abnormally long time, it may decide that the management
         station has crashed.  If the agent makes this decision,
         it may set this object to invalid(4) to reclaim the
         entry.  A prudent agent will understand that the
         management station may need to wait for human input
         and will allow for that possibility in its
         determination of this abnormally long period.

         An entry in the valid(1) state is fully configured and
         consistent and fully represents the configuration or
         operation such a row is intended to represent.  For
         example, it could be a statistical function that is
         configured and active, or a filter that is available
         in the list of filters processed by the packet capture
         process.

         A manager is restricted to changing the state of an entry in
         the following ways:

              To:       valid  createRequest  underCreation  invalid
         From:
         valid             OK             NO             OK       OK
         createRequest    N/A            N/A            N/A      N/A
         underCreation     OK             NO             OK       OK
         invalid           NO             NO             NO       OK
         nonExistent       NO             OK             NO       OK

         In the table above, it is not applicable to move the state
         from the createRequest state to any other state because the
         manager will never find the variable in that state.  The
         nonExistent state is not a value of the enumeration, rather
         it means that the entryStatus variable does not exist at all.

         An agent may allow an entryStatus variable to change state in
         additional ways, so long as the semantics of the states are
         followed.  This allowance is made to ease the implementation of
         the agent and is made despite the fact that managers should
         never exercise these additional state transitions."
     SYNTAX INTEGER {
                valid(1),
                createRequest(2),
                underCreation(3),
                invalid(4)
            }
Ipv6Address ::= TEXTUAL-CONVENTION
    DISPLAY-HINT "2x:"
    STATUS       current
    DESCRIPTION
        "This data type is used to model IPv6 addresses.
        This is a binary string of 16 octets in network
        byte-order."
    SYNTAX       OCTET STRING (SIZE (16))            
 
-- ----------------------------------------------------------------- -- 
-- groups in the MIB  
-- ----------------------------------------------------------------- -- 


-- end DLINK-METRO-LIKE-FIRMWARE-INFO-DISPLAY
-- start DLINK-METRO-LIKE-FIRMWARE-INFO-DISPLAY
      companySystem           OBJECT IDENTIFIER ::= { dgs-1210-28pmeax 1 }
      companyIpifGroup            OBJECT IDENTIFIER ::= { dgs-1210-28pmeax 2 } 
      companyTftpGroup            OBJECT IDENTIFIER ::= { dgs-1210-28pmeax 3 } 
      companyMiscGroup            OBJECT IDENTIFIER ::= { dgs-1210-28pmeax 4 }
      companySNMPV3                 OBJECT IDENTIFIER ::= { dgs-1210-28pmeax 5 }
      companySTP                 OBJECT IDENTIFIER ::= { dgs-1210-28pmeax 6 }
      companyDot1qVlanGroup       OBJECT IDENTIFIER ::= { dgs-1210-28pmeax 7 }      
      companyLA                   OBJECT IDENTIFIER ::= { dgs-1210-28pmeax 8 }
      companyStaticMAC   	      OBJECT IDENTIFIER ::= { dgs-1210-28pmeax 9 }          
      companyIgsGroup             OBJECT IDENTIFIER ::= { dgs-1210-28pmeax 10 }
      companyGVRPGroup       OBJECT IDENTIFIER ::= { dgs-1210-28pmeax 11 }
      companyQoSGroup             OBJECT IDENTIFIER ::= { dgs-1210-28pmeax 12 }
      companyTrafficMgmt          OBJECT IDENTIFIER ::= { dgs-1210-28pmeax 13 }
      companySecurity             OBJECT IDENTIFIER ::= { dgs-1210-28pmeax 14 }
      companyACLGroup             OBJECT IDENTIFIER ::= { dgs-1210-28pmeax 15 }
      companySyslog               OBJECT IDENTIFIER ::= { dgs-1210-28pmeax 16 } 
	  companyLBD                  OBJECT IDENTIFIER ::= { dgs-1210-28pmeax 17 }        
      companyMirror             OBJECT IDENTIFIER ::= { dgs-1210-28pmeax 18 }
      companyStaticMcast           OBJECT IDENTIFIER ::= { dgs-1210-28pmeax 19 }
      companySNTPSetting          OBJECT IDENTIFIER ::= { dgs-1210-28pmeax 20 }
      companyPoEGroup            OBJECT IDENTIFIER ::= { dgs-1210-28pmeax 21 }
      companyRMON                 OBJECT IDENTIFIER ::= { dgs-1210-28pmeax 22 }
      companyAuthGroup           OBJECT IDENTIFIER ::= { dgs-1210-28pmeax 23 }
      companyGuestVlan                   OBJECT IDENTIFIER ::= { dgs-1210-28pmeax 24 }
      companyMacNotify                   OBJECT IDENTIFIER ::= { dgs-1210-28pmeax 25 }
      companyISMVLAN          OBJECT IDENTIFIER ::= { dgs-1210-28pmeax 27 }
    companyDHCPRelay                            OBJECT IDENTIFIER ::= { dgs-1210-28pmeax 28 }
    companyDHCPLocalRelay   OBJECT IDENTIFIER ::= { dgs-1210-28pmeax 29 }
      companyGreenSetting	        OBJECT IDENTIFIER ::= { dgs-1210-28pmeax 31 }
      sysFirmwareInfomation   OBJECT IDENTIFIER ::= { companySystem 31 }
      companyLLDPSetting	      OBJECT IDENTIFIER ::= { dgs-1210-28pmeax 32 }
      companyCPUInterfaceFilterGroup             OBJECT IDENTIFIER ::= { dgs-1210-28pmeax 33 }
      companyStaticARP   	      OBJECT IDENTIFIER ::= { dgs-1210-28pmeax 34 }          
      companyCableDiagnostic             OBJECT IDENTIFIER ::= { dgs-1210-28pmeax 35 }
      companyVLANTrunk                   OBJECT IDENTIFIER ::= { dgs-1210-28pmeax 36 }
      companyTimeRangeMgmt                   OBJECT IDENTIFIER ::= { dgs-1210-28pmeax 38 }
      companySMTP                   OBJECT IDENTIFIER ::= { dgs-1210-28pmeax 40 }
      companyMultiIPInterface                   OBJECT IDENTIFIER ::= { dgs-1210-28pmeax 41 }
      companyLimitIp             OBJECT IDENTIFIER ::= { dgs-1210-28pmeax 45 }
      companyGratuitousARP       OBJECT IDENTIFIER ::= { dgs-1210-28pmeax 48 }
      companyNeighbor   	      OBJECT IDENTIFIER ::= { dgs-1210-28pmeax 50 }          
      companyEoam                   OBJECT IDENTIFIER ::= { dgs-1210-28pmeax 51 }
      companyDuld                   OBJECT IDENTIFIER ::= { dgs-1210-28pmeax 52 }
      companydot3azEEE             OBJECT IDENTIFIER ::= { dgs-1210-28pmeax 53 }
      companyMacAuthGroup           OBJECT IDENTIFIER ::= { dgs-1210-28pmeax 54 }
      companyWACAuthGroup           OBJECT IDENTIFIER ::= { dgs-1210-28pmeax 55}
      companyMacBasedVlan       OBJECT IDENTIFIER ::= { dgs-1210-28pmeax 70 }      
	  companyBPDUAttack                  OBJECT IDENTIFIER ::= { dgs-1210-28pmeax 77 }
    companyDHCPv6Relay                            OBJECT IDENTIFIER ::= { dgs-1210-28pmeax 86 }
      companyMldsGroup             OBJECT IDENTIFIER ::= { dgs-1210-28pmeax 88 }
      companyPPPoE                      OBJECT IDENTIFIER ::= { dgs-1210-28pmeax 98 }
      companyDoSCtrl             OBJECT IDENTIFIER ::= { dgs-1210-28pmeax 99 }
      companyAgentBasicInfo        OBJECT IDENTIFIER ::= { dgs-1210-28pmeax 100 }
      companyProtocolVlan                   OBJECT IDENTIFIER ::= { dgs-1210-28pmeax 101 }
      companyL2PT            OBJECT IDENTIFIER ::= { dgs-1210-28pmeax 102 }
      companyQinQ                   OBJECT IDENTIFIER ::= { dgs-1210-28pmeax 103 }
    companySfpVendorInfo                            OBJECT IDENTIFIER ::= { dgs-1210-28pmeax 104 }
    companyDDM                                      OBJECT IDENTIFIER ::= { dgs-1210-28pmeax 105 }
      companyCpuProtect             OBJECT IDENTIFIER ::= { dgs-1210-28pmeax 106 }
      
-- ---------------------------------------------------------------- --

    -- ------------------------------------------------------------------
    -- companySystem
    -- ------------------------------------------------------------------

    sysSwitchName OBJECT-TYPE
       SYNTAX      DisplayString (SIZE(1..20))
       MAX-ACCESS  read-write
       STATUS      current
       DESCRIPTION
          "System name used for identification of the device.
          The following characters are allowed to input.
          0 ~ 9 / a ~ z / A ~ Z
          Special character: (  )   V  +  -  =  ."
       ::= { companySystem 1 }

    sysHardwareVersion OBJECT-TYPE
       SYNTAX      DisplayString (SIZE(1..15))
       MAX-ACCESS  read-only
       STATUS      current
       DESCRIPTION
          "Version number of the Hardware."
          DEFVAL { "" }
       ::= { companySystem 2 }

    sysFirmwareVersion OBJECT-TYPE
       SYNTAX      DisplayString (SIZE(1..15))
       MAX-ACCESS  read-only
       STATUS      current
       DESCRIPTION
          "Version number of the Firmware."
          DEFVAL { "" }
       ::= { companySystem 3 }

    sysLoginTimeoutInterval  OBJECT-TYPE
       SYNTAX      Integer32 (3..30)
       MAX-ACCESS  read-write
       STATUS      current
       DESCRIPTION
          "This time interval is used to count the time and
           logout web interface automatically."
           DEFVAL  { 5 }
       ::= { companySystem 4 }

    sysLocationName OBJECT-TYPE
        SYNTAX      DisplayString (SIZE(1..20))
        MAX-ACCESS  read-write
        STATUS      current
        DESCRIPTION
                "The location name of this node (e.g., `telephone closet,
                 3rd floor').  If the location is unknown, the value is
                 the zero-length string."
       ::= { companySystem 5 }


    sysGroupInterval OBJECT-TYPE
       SYNTAX      Integer32 (0 | 120..1225)
       MAX-ACCESS  read-write
       STATUS      current
       DESCRIPTION
          "Group Interval is used to send D-link Discover packet to D-link
           SmartConsole Utility frequency.

           The timer in units of seconds.

           Set value 0 to disable group Interval."
       ::= { companySystem 6 }


    sysSafeGuardEnable  OBJECT-TYPE
       SYNTAX      INTEGER {
                    enable(1),
                    disable(2)
                   }
       MAX-ACCESS  read-write
       STATUS      current
       DESCRIPTION
          "This object is used to set Safeguard Enable\Disable."
          DEFVAL { enable }
       ::= { companySystem 8 }


    sysRestart OBJECT-TYPE
       SYNTAX      TruthValue
       MAX-ACCESS  read-write
       STATUS      current
       DESCRIPTION
          "This object allows the user to restart the Switch
          (i.e)the entire switch will operationally go down and
           start again.  Setting  a value of 'true' causes the switch
           to be restarted.

           When  the switch operationally goes down, configuration
           save operation is initiated based on the configuration save
           option chosen.

           When the switch operationally come up, the saved configurations
           are restored based on the restore option chosen.

           Once the switch is restarted, the value of this object reverts
           to 'false'."
       DEFVAL  { false }
       ::= { companySystem 9 }

    sysSave OBJECT-TYPE
       SYNTAX      TruthValue
       MAX-ACCESS  read-write
       STATUS      current
       DESCRIPTION
          "This object is used to save Configuration."
       DEFVAL  { false }
       ::= { companySystem 10 }


    sysJumboFrameEnable  OBJECT-TYPE
       SYNTAX      INTEGER {
                    enable(1),
                    disable(2)
                   }
       MAX-ACCESS  read-write
       STATUS      current
       DESCRIPTION
          "Gigabit Web Smart Switches support jumbo frames (frames larger than
           the Ethernet frame size of 1522 bytes) of up to 10,000 bytes (tagged).
           Default jumbo frame is disabled."
          DEFVAL { disable }
       ::= { companySystem 12 }

    -- Port Control Table

        sysPortCtrlTable OBJECT-TYPE
           SYNTAX      SEQUENCE OF SysPortCtrlEntry
           MAX-ACCESS  not-accessible
           STATUS      current
           DESCRIPTION
               "A table to control the port specific parameters of the device like speed,
                duplex mode, etc."
           ::= { companySystem 13 }

        sysPortCtrlEntry OBJECT-TYPE
           SYNTAX      SysPortCtrlEntry
           MAX-ACCESS  not-accessible
           STATUS      current
           DESCRIPTION
               "An entry appears in this table for each interface in the system.

               Index to the table is the interface index of the port."

           INDEX { sysPortCtrlIndex , sysPortCtrlMediumType}
           ::= { sysPortCtrlTable 1 }

        SysPortCtrlEntry ::=
           SEQUENCE {
              sysPortCtrlIndex
                 Integer32,
              sysPortCtrlMediumType
                 INTEGER,
              sysPortCtrlSpeed
                 INTEGER,
              sysPortCtrlOperStatus
                 INTEGER,
              sysPortCtrlMDI
                 INTEGER,
              sysPortCtrlFlowControl
                 INTEGER,
              sysPortCtrlFlowControlOper
                 INTEGER,
              sysPortCtrlType
                 INTEGER,           
              sysPortCtrlCapability
              	 BITS
          }

        sysPortCtrlIndex OBJECT-TYPE
           SYNTAX      Integer32 (1..65535)
           MAX-ACCESS  read-only
           STATUS      current
           DESCRIPTION
              "Interface index of the port for the configuration
              in this entry applies."

           ::= { sysPortCtrlEntry 1 }

        sysPortCtrlMediumType OBJECT-TYPE
           SYNTAX      INTEGER {
             copper(1),
             fiber(2)
           }
           MAX-ACCESS  read-only
           STATUS      current
           DESCRIPTION
              "This object indicates the port type: fiber 1G/100M or copper."

           ::= { sysPortCtrlEntry 2 }

        sysPortCtrlSpeed OBJECT-TYPE
           SYNTAX      INTEGER {
                         rate1000M-Full  (1),
                         rate100M-Full   (2),
                         rate100M-Half   (3),
                         rate10M-Full    (4),
                         rate10M-Half    (5),
                         auto            (6),
                         disable         (7),
                         rate10G-Full	 (8)
                      }	 
           MAX-ACCESS  read-write
           STATUS      current
           DESCRIPTION
              "Configures interface speed."

           ::= { sysPortCtrlEntry 3 }

        sysPortCtrlOperStatus OBJECT-TYPE
           SYNTAX      INTEGER {
                         down            (1),
                         rate1000M-Full  (2),
                         rate100M-Full   (3),
                         rate100M-Half   (4),
                         rate10M-Full    (5),
                         rate10M-Half    (6),
                         rate10G-Full	 (7)
                         
                      }
           MAX-ACCESS  read-only
           STATUS      current
           DESCRIPTION
              "The port's operating speed state."

           ::= { sysPortCtrlEntry 4 }

        sysPortCtrlMDI OBJECT-TYPE
           SYNTAX      INTEGER {
                         auto    (1),
                         mdi     (2),
                         mdix    (3)
                      }
           MAX-ACCESS  read-write
           STATUS      current
           DESCRIPTION
              "Configures interface auto/mdi/mdix mode.
              The default setting is Auto."

           ::= { sysPortCtrlEntry 5 }

        sysPortCtrlFlowControl OBJECT-TYPE
           SYNTAX      INTEGER {
                         enable     (1),
                         disable    (2)
                      }
           MAX-ACCESS  read-write
           STATUS      current
           DESCRIPTION
              "Enables / disables flow control for the interface."

           ::= { sysPortCtrlEntry 6 }

        sysPortCtrlFlowControlOper OBJECT-TYPE
            SYNTAX INTEGER {
                   enabled(1),
                   disabled(2)
            }
            MAX-ACCESS  read-only
            STATUS      current
            DESCRIPTION
                "The link parner negotiate port's operating flow control state."
            ::= { sysPortCtrlEntry 7 }

        sysPortCtrlType OBJECT-TYPE
            SYNTAX INTEGER {
                   fastethernet(1),
                   gigabitethernet(2),
                   fiberwith100BaseSFPModule(3),
                   fiberwith1GBaseSFPModule(4),
                   fiberwith10GBaseSFPModule(5)
            }
            MAX-ACCESS  read-only
            STATUS      current
            DESCRIPTION
                "The port's media type."
            ::= { sysPortCtrlEntry 8 }                                    
            
    	sysPortCtrlCapability OBJECT-TYPE
      		SYNTAX  BITS {
            	rate10-half(0),
            	rate10-full(1),
            	rate100-half(2),
            	rate100-full(3),
            	reserve(4),
            	rate1000-full(5)     			
            }  		    
			MAX-ACCESS read-write
     		STATUS current
      		DESCRIPTION              
      			"The port's capability advertised."     
   			::= { sysPortCtrlEntry 9 }
            
-- start DLINK-METRO-LIKE-GENERAL       
        sysPortDescriptionTable OBJECT-TYPE
           SYNTAX      SEQUENCE OF SysPortDescriptionEntry
           MAX-ACCESS  not-accessible
           STATUS      current
           DESCRIPTION
               "The port description table."
           ::= { companySystem 14 }

        sysPortDescriptionEntry OBJECT-TYPE
           SYNTAX      SysPortDescriptionEntry
           MAX-ACCESS  not-accessible
           STATUS      current
           DESCRIPTION
               "The port description entry."
           INDEX { sysPortDescIndex, sysPortDescMediumType }
           ::= { sysPortDescriptionTable 1 }

        SysPortDescriptionEntry ::=
           SEQUENCE {
              sysPortDescIndex
                 INTEGER,
              sysPortDescMediumType
                 INTEGER,
              sysPortDescString
                 DisplayString,
              sysPortUpLinkTime
                 DisplayString
           }

        sysPortDescIndex OBJECT-TYPE
           SYNTAX      INTEGER (1..255)
           MAX-ACCESS  read-only
           STATUS      current
           DESCRIPTION
              "This object indicates the port index."
           ::= { sysPortDescriptionEntry 1 }
              
              
        sysPortDescMediumType OBJECT-TYPE
           SYNTAX      INTEGER {
             copper(1),
             fiber(2)
           }
           MAX-ACCESS  read-only
           STATUS      current
           DESCRIPTION
              "This object indicates the port type: fiber 1G/100M or copper."
           ::= { sysPortDescriptionEntry 2 }
           
        sysPortDescString OBJECT-TYPE
           SYNTAX       DisplayString(SIZE(0..32))
           MAX-ACCESS   read-write
           STATUS       current
           DESCRIPTION
               "This object indicates the port description."
           ::= { sysPortDescriptionEntry 3 }

        sysPortUpLinkTime OBJECT-TYPE
           SYNTAX       DisplayString(SIZE(0..32))
           MAX-ACCESS   read-only
           STATUS       current
           DESCRIPTION
               "This object indicates the port link up time."
           ::= { sysPortDescriptionEntry 4 }

-- end DLINK-METRO-LIKE-GENERAL

-- start DLINK-METRO-LIKE-GENERAL
		sysPortErrTable OBJECT-TYPE
		   SYNTAX       SEQUENCE OF SysPortErrEntry
		   MAX-ACCESS   not-accessible
		   STATUS       current
		   DESCRIPTION
		   	   "The port error table."
           ::= { companySystem 15 }

		sysPortErrEntry OBJECT-TYPE
		   SYNTAX       SysPortErrEntry
		   MAX-ACCESS   not-accessible
		   STATUS       current
		   DESCRIPTION
		        "A list of information for the err port of the device."
		   INDEX { sysPortErrPortIndex }
		    ::= { sysPortErrTable 1 }

		SysPortErrEntry ::= 
		   SEQUENCE {
		      sysPortErrPortIndex
		         INTEGER,
		      sysPortErrPortState
		         INTEGER,
		      sysPortErrPortStatus 
		         INTEGER,
		      sysPortErrPortReason
		         INTEGER
		}

		sysPortErrPortIndex OBJECT-TYPE
		   SYNTAX       INTEGER (1..255)
		   MAX-ACCESS   read-only
		   STATUS       current
		   DESCRIPTION
		        "This object indicates the module's port number.(1..Max port number in
		        the module)"
		   ::= { sysPortErrEntry 1 }
       
		sysPortErrPortState OBJECT-TYPE
		   SYNTAX       INTEGER {
		      disabled(1),
		      enabled(2)
		   }
		   MAX-ACCESS   read-only
		   STATUS       current
		   DESCRIPTION
		        "This object decides whether the port state is enabled or disabled."
		   ::= { sysPortErrEntry 2 }
		
		sysPortErrPortStatus OBJECT-TYPE
		   SYNTAX       INTEGER {
		      other(1),
		      err-disabled(2)
		   }
		   MAX-ACCESS   read-only
		   STATUS       current
		   DESCRIPTION
		        "This object decides whether the PortStatus is err-disabled."
		   ::= { sysPortErrEntry 3 }
		
		sysPortErrPortReason OBJECT-TYPE
		   SYNTAX       INTEGER {
		      lbd(1)
		   }
		   MAX-ACCESS   read-only
		   STATUS       current
		   DESCRIPTION
		        "This object decides whether the PortStatus is LBD."
		   ::= { sysPortErrEntry 4 }
-- end DLINK-METRO-LIKE-GENERAL

        sysDhcpAutoConfiguration  OBJECT-TYPE
            SYNTAX      INTEGER {
                    enable(1),
                    disable(2)
            }
            MAX-ACCESS  read-write
            STATUS      current
            DESCRIPTION
            "This object indicates auto config is enabled or disabled."
            DEFVAL { disable }
            ::= { companySystem 16 }

-- start DLINK-METRO-LIKE-GENERAL

		   sysWebState  OBJECT-TYPE
		   SYNTAX       INTEGER {
		                enabled(1),
		                disabled(2)
		               }
		   MAX-ACCESS  read-write
		   STATUS      current
		   DESCRIPTION
		      "This object is for Enabled(1) or Disabled(2) Web state in the system."
		   ::= { companySystem 17 }


		   sysWebPortNumber  OBJECT-TYPE
		   SYNTAX      Integer32 (1..65535)
		   MAX-ACCESS  read-write
		   STATUS      current
		   DESCRIPTION
		       "Web Server Port Number." 
		   DEFVAL  { 80 }		   
		   ::= { companySystem 18 }

           sysARPAgingTime  OBJECT-TYPE
		   SYNTAX      INTEGER (0..65535)
		   MAX-ACCESS  read-write
		   STATUS      current
		   DESCRIPTION
		       "This object is for ARP aging time."
		   ::= { companySystem 19 }


           sysMACAgingTime  OBJECT-TYPE
		   SYNTAX      INTEGER (10..600)
		   MAX-ACCESS  read-write
		   STATUS      current
		   DESCRIPTION
		       "This object is for MAC aging time."
		   ::= { companySystem 20 }

 			baudRateConfiguration  OBJECT-TYPE
            SYNTAX      INTEGER {
                    baudrate9600(9600),
                    baudrate19200(19200),
                    baudrate38400(38400),
                    baudrate115200(115200)
            }
            MAX-ACCESS  read-write
            STATUS      current
            DESCRIPTION
            "To set SerialPort baud-rate configuration."
            ::= { companySystem 21 }

        	autologoutConfiguration  OBJECT-TYPE
            SYNTAX      INTEGER {
                    logouttime2mins(120),
                    logouttime5mins(300),
                    logouttime10mins(600),
                    logouttime15mins(900),
                    logouttimenever(0)

            }
            MAX-ACCESS  read-write
            STATUS      current
            DESCRIPTION
            "To set SerialPort auto-logout-time configuration."
            ::= { companySystem 22 }

            telnetsettingManagementOnOff OBJECT-TYPE
            SYNTAX INTEGER {
                   enabled(1),
                   disabled(2)
            }
            MAX-ACCESS read-write
            STATUS current
            DESCRIPTION
                "Enable/Disable management Telnetsetting mechanism."
            ::= { companySystem 23 }

            telnetUDPPort OBJECT-TYPE
            SYNTAX  INTEGER (1..65535)
            MAX-ACCESS  read-write
            STATUS  current
            DESCRIPTION
                "The value is for setting telnet's UDP Port." 
            DEFVAL  { 23 }
            ::= { companySystem 24 } 

        autoRefreshConfiguration  OBJECT-TYPE
            SYNTAX      INTEGER {
                    refreshimenever(0),
                    refreshtime10secs(1),
                    refreshtime30secs(2),
                    refreshtime1min(3),
                    refreshtime5mins(4)
            }
            MAX-ACCESS  read-write
            STATUS      current
            DESCRIPTION
            "To set the WEB panel auto refresh timer."
            ::= { companySystem 25 }
            
        floodfdbOnOff  OBJECT-TYPE
            SYNTAX      INTEGER {
                   enabled(1),
                   disabled(2)
            }
            MAX-ACCESS  read-write
            STATUS      current
            DESCRIPTION
            "To set enable status for flood fdb."
            ::= { companySystem 26 }
            
        sysContactName  OBJECT-TYPE
            SYNTAX      DisplayString (SIZE(1..128))
            MAX-ACCESS  read-write
            STATUS      current
            DESCRIPTION
            "To set system contact name."
            ::= { companySystem 27 }
-- end DLINK-METRO-LIKE-GENERAL

        sysDhcpAutoConfigTimeout  OBJECT-TYPE
            SYNTAX      INTEGER (1..65535)
            MAX-ACCESS  read-write
            STATUS      current
            DESCRIPTION
            "To set dhcp auto config timeout."
            ::= { companySystem 28 }

        sysCommandLogging OBJECT-TYPE
           SYNTAX      INTEGER {
                    enable    (1),
                    disable   (2)
            }
           MAX-ACCESS  read-write
           STATUS      current
           DESCRIPTION
           "To set enable status for CommandLogging."

           ::= { companySystem 29 }
           
        sysSerialNumber OBJECT-TYPE
           SYNTAX      DisplayString (SIZE(1..13))
           MAX-ACCESS  read-only
           STATUS      current
           DESCRIPTION
           "To get the serial number."

           ::= { companySystem 30 }             
           
-- start DLINK-METRO-LIKE-FIRMWARE-INFO-DISPLAY   

    --FirmwareInfo
        sysVersion OBJECT-TYPE
           SYNTAX      DisplayString (SIZE(1..15))
           MAX-ACCESS  read-only
           STATUS      current
           DESCRIPTION
              "The version of firmware information."
                DEFVAL { "" }

           ::= { sysFirmwareInfomation 1 }

        sysSize OBJECT-TYPE
           SYNTAX      Integer32 
           MAX-ACCESS  read-only
           STATUS      current
           DESCRIPTION
              "The size of firmware information."

           ::= { sysFirmwareInfomation 2 }

        sysUpdateTime OBJECT-TYPE
           SYNTAX      DisplayString (SIZE(1..20))
           MAX-ACCESS  read-only
           STATUS      current
           DESCRIPTION
              "The Update Time of firmware information."

           ::= { sysFirmwareInfomation 3 }

        sysFromIP OBJECT-TYPE
           SYNTAX      IpAddress
           MAX-ACCESS  read-only
           STATUS      current
           DESCRIPTION
              "The IP address of firmware information."

           ::= { sysFirmwareInfomation 4 }

        sysUser OBJECT-TYPE
           SYNTAX      DisplayString (SIZE(1..9))
           MAX-ACCESS  read-only
           STATUS      current
           DESCRIPTION
              "The user of firmware infomation."

           ::= { sysFirmwareInfomation 5 }

          sysType OBJECT-TYPE
           SYNTAX      INTEGER{
                    console(1),
                    telnet(2),
                    ssh(3),
                    web(4),
                    unknown(-1)

           }
           MAX-ACCESS  read-only
           STATUS      current
           DESCRIPTION
              "The type of firmware infomation."

           ::= { sysFirmwareInfomation 6 }

-- end DLINK-METRO-LIKE-FIRMWARE-INFO-DISPLAY

        sysDdp  OBJECT IDENTIFIER ::= { companySystem 32 }
        sysDdpGlobalOnOff       OBJECT-TYPE 
            SYNTAX INTEGER  {
        		 enabled(1),
        		 disabled(2)
            }
            MAX-ACCESS    read-write 
            STATUS        current
            DESCRIPTION 
           "This object indicates D-Link discover protocol is enabled or disabled." 
            ::= { sysDdp 1 }                                           

        sysDdpGeneralReportOnOff       OBJECT-TYPE 
            SYNTAX INTEGER  {
        		 enabled(1),
        		 disabled(2)
            }
            MAX-ACCESS    read-write 
            STATUS        current
            DESCRIPTION 
           "This object indicates D-Link discover protocol report is enabled or disabled.
            This object only can be modified when D-Link discover protocol state is enabled." 
            ::= { sysDdp 2 } 

        sysDdpGeneralReportTimer      OBJECT-TYPE 
            SYNTAX INTEGER  {
        		 time30seconds(30),
        		 time60seconds(60),
        		 time90seconds(90),
        		 time120seconds(120)
            }
            MAX-ACCESS    read-write 
            STATUS        current
            DESCRIPTION 
           "This object indicates D-Link discover protocol report time period.
            This object only can be modified when both D-Link discover protocol state and
            D-Link discover protocol report state are enabled." 
            ::= { sysDdp 3 }

        sysDdpProtStatusTable OBJECT-TYPE 
           SYNTAX      SEQUENCE OF SysDdpProtStatusEntry
           MAX-ACCESS  not-accessible 
           STATUS      current 
           DESCRIPTION 
               "A table to control the port status of D-Link discover protocol."
           ::= { sysDdp 4 }
        
        sysDdpProtStatusEntry OBJECT-TYPE 
           SYNTAX      SysDdpProtStatusEntry
           MAX-ACCESS  not-accessible 
           STATUS      current 
           DESCRIPTION 
               "An entry appears in this table for each port D-Link discover protocol status."
        
           INDEX { sysDdpProtStatusIndex }
           ::= { sysDdpProtStatusTable 1 }
           
        SysDdpProtStatusEntry ::= 
           SEQUENCE { 
              sysDdpProtStatusIndex 
                 Integer32, 
              sysDdpProtStatusControl
                 INTEGER
          }
        
        sysDdpProtStatusIndex OBJECT-TYPE 
           SYNTAX      Integer32 (1..65535)
           MAX-ACCESS  read-only 
           STATUS      current 
           DESCRIPTION 
              "Interface index of the port for the configuration
              in this entry applies."
           
           ::= { sysDdpProtStatusEntry 1 }

        sysDdpProtStatusControl OBJECT-TYPE 
           SYNTAX      INTEGER {
               enabled  (1),
               disabled (2)
                      }
           MAX-ACCESS  read-write 
           STATUS      current 
           DESCRIPTION 
              "Configures the port status of D-Link discover protocol."
        
           ::= { sysDdpProtStatusEntry 2 }

         

        sysSmartFan  OBJECT IDENTIFIER ::= { companySystem 33 }
        sysSmartFanStatus OBJECT-TYPE
           SYNTAX   INTEGER { 
                        failure(0), 
                        normal(1)
                    }
           MAX-ACCESS  read-only
           STATUS      current
           DESCRIPTION
              "The Fan status for this device."
           ::= {sysSmartFan 1 }


        sysDhcpAutoImage  OBJECT-TYPE
            SYNTAX      INTEGER {
                    enable(1),
                    disable(2)
            }
            MAX-ACCESS  read-write
            STATUS      current
            DESCRIPTION
            "This object indicates auto image is enabled or disabled."
            DEFVAL { disable }
            ::= { companySystem 34 }
                    
        sysBootupConfigID OBJECT-TYPE
           SYNTAX      INTEGER (1..2)
           MAX-ACCESS  read-write
           STATUS      current
           DESCRIPTION
           "To get/set bootup config ID."
           ::= { companySystem 35 }

        sysBootupImage OBJECT-TYPE
           SYNTAX      INTEGER (1..2)
           MAX-ACCESS  read-write
           STATUS      current
           DESCRIPTION
           "To get/set bootup Image."

           ::= { companySystem 36 }

 -- ----------------------------------------------------------
 -- The company802Dot3az Groups
 -- ----------------------------------------------------------      	
    dot3azEEEset                  OBJECT IDENTIFIER ::= { companydot3azEEE 1 }
 -- 802Dot3azTable  Group --------------------------------------------- --
    
    dot3azTable     OBJECT-TYPE
        SYNTAX SEQUENCE OF Dot3azEntry
        MAX-ACCESS not-accessible
        STATUS current
        DESCRIPTION
            "A table to control IEEE802.3az EEE settings features of the device."
        ::= { dot3azEEEset 1 }
        
    dot3azEntry OBJECT-TYPE
        SYNTAX Dot3azEntry
        MAX-ACCESS not-accessible
        STATUS current
        DESCRIPTION
            "An entry appears in IEEE802.3az EEE table for each interface 
 	        in the system."
        INDEX { portD3Index }
        ::= { dot3azTable 1 }
  
    Dot3azEntry ::= 
           SEQUENCE { 
              portD3Index 
                 Integer32, 
              portD3State 
                 INTEGER             
          }
        
               
         portD3Index OBJECT-TYPE 
           SYNTAX      Integer32 
           MAX-ACCESS  read-only 
           STATUS      current 
           DESCRIPTION 
              "The interface index for which the configuration in this 
               entry applies."
           ::= { dot3azEntry 1 }
            
        
         portD3State OBJECT-TYPE
           SYNTAX INTEGER  {
        		  enabled (1), disabled (2), notsupported (3)
            }
           MAX-ACCESS  read-write
           STATUS      current
           DESCRIPTION
              "Enable / disable port IEEE802.3az EEE admin state for the interface.
              
              A given ports' dynamic MAC address learning will be stopped such
              that the current source MAC addresses entered into the MAC address
              forwarding table can not be changed once the port security admin 
              state is enabled."
        
           ::= { dot3azEntry 2 }
        
       

        -- -------------------------------------------------------------------------
        -- companyIpifGroup       
        -- -------------------------------------------------------------------------
       
       ipv4sysIpAddrCfgMode OBJECT-TYPE 
       SYNTAX      INTEGER {
                    manual(1),
                    dynamic(2)
                   }
       MAX-ACCESS  read-write 
       STATUS      current 
       DESCRIPTION 
          "Specifies the means by which the default interface in the device 

      gets the IP address.

      If 'manual' mode is selected, the default interface takes the 
      'sysDefaultIpAddr' configured in the system.

      If 'dynamic' mode is selected, the default interface gets the IP address
      through dynamic IP address configuration protocols such as RARP client, 
      BootP client, DHCP Client, etc.
      
      If the system fails to get the IP address dynamically through all the
      above protocols, the default interface uses the 'sysDefaultIpAddr' 
      configured in the system."  
       DEFVAL  { manual } 
       ::= { companyIpifGroup 1 }

    ipv4sysIpAddr  OBJECT-TYPE
       SYNTAX      IpAddress
       MAX-ACCESS  read-write
       STATUS      current
       DESCRIPTION 
          "Default IP Address of the system.
    
           This IP address, if modified, will take effect only when the 
           configuration is stored & restored."
       ::= { companyIpifGroup 2 }
    
    ipv4sysIpSubnetMask  OBJECT-TYPE
       SYNTAX      IpAddress
       MAX-ACCESS  read-write
       STATUS      current
       DESCRIPTION 
          "IP subnet mask for the default IP address.
    
           This subnet mask, if modified, will take effect only when the
           configuration is stored & restored."
       ::= { companyIpifGroup 3 }

    ipv4sysGateway  OBJECT-TYPE
       SYNTAX      IpAddress
       MAX-ACCESS  read-write
       STATUS      current
       DESCRIPTION 
          "Gateway"
       ::= { companyIpifGroup 4 }

    ipv4dhcpOption12Status  OBJECT-TYPE
       SYNTAX      INTEGER {
                    enable(1),
                    disable(2)
                   }
       MAX-ACCESS  read-write
       STATUS      current
       DESCRIPTION 
          "Status of DHCP Option12"
       ::= { companyIpifGroup 5 }
       
    ipv4dhcpOption12HostName  OBJECT-TYPE
       SYNTAX      OCTET STRING
       MAX-ACCESS  read-write
       STATUS      current
       DESCRIPTION 
          "Host name in DHCP option 12"
       ::= { companyIpifGroup 6 }

      -- ----------------------------------------------------------------
      -- The multiIFSupportV4V6Info group
      -- ----------------------------------------------------------------

      ipifSupportV4V6Info         OBJECT IDENTIFIER ::= { companyIpifGroup 7 }

       sysIpAddrCfgMode OBJECT-TYPE 
       SYNTAX      INTEGER {
                    manual(1),
                    dynamic(2)
                   }
       MAX-ACCESS  read-write 
       STATUS      current 
       DESCRIPTION 
          "Specifies the means by which the default interface in the device 

      gets the IP address.

      If 'manual' mode is selected, the default interface takes the 
      'sysDefaultIpAddr' configured in the system.

      If 'dynamic' mode is selected, the default interface gets the IP address
      through dynamic IP address configuration protocols such as RARP client, 
      BootP client, DHCP Client, etc.
      
      If the system fails to get the IP address dynamically through all the
      above protocols, the default interface uses the 'sysDefaultIpAddr' 
      configured in the system."  
       DEFVAL  { manual } 
       ::= { ipifSupportV4V6Info 1 }

    sysIpAddr  OBJECT-TYPE
       SYNTAX      IpAddress
       MAX-ACCESS  read-write
       STATUS      current
       DESCRIPTION 
          "Default IP Address of the system.
    
           This IP address, if modified, will take effect only when the 
           configuration is stored & restored."
       ::= { ipifSupportV4V6Info 2 }
    
    sysIpSubnetMask  OBJECT-TYPE
       SYNTAX      IpAddress
       MAX-ACCESS  read-write
       STATUS      current
       DESCRIPTION 
          "IP subnet mask for the default IP address.
    
           This subnet mask, if modified, will take effect only when the
           configuration is stored & restored."
       ::= { ipifSupportV4V6Info 3 }

    sysGateway  OBJECT-TYPE
       SYNTAX      IpAddress
       MAX-ACCESS  read-write
       STATUS      current
       DESCRIPTION 
          "Gateway"
       ::= { ipifSupportV4V6Info 4 }

    dhcpOption12Status  OBJECT-TYPE
       SYNTAX      INTEGER {
                    enable(1),
                    disable(2)
                   }
       MAX-ACCESS  read-write
       STATUS      current
       DESCRIPTION 
          "Status of DHCP Option12"
       ::= { ipifSupportV4V6Info 5 }
       
    dhcpOption12HostName  OBJECT-TYPE
       SYNTAX      OCTET STRING
       MAX-ACCESS  read-write
       STATUS      current
       DESCRIPTION 
          "Host name in DHCP option 12"
       ::= { ipifSupportV4V6Info 6 }

    ipifName           OBJECT-TYPE
         SYNTAX             OCTET STRING
         MAX-ACCESS         read-only
         STATUS             current
         DESCRIPTION
               "The Description for the interface."
         ::= { ipifSupportV4V6Info 7 }         
         
      ipifVLANname       OBJECT-TYPE
         SYNTAX             OCTET STRING
         MAX-ACCESS         read-only
         STATUS             current
         DESCRIPTION
               "The vlan name for the interface."
         ::= { ipifSupportV4V6Info 8 }    

      ipifv6GlobalStatus     OBJECT-TYPE
            SYNTAX              INTEGER   {
                                  enable(1),    
                                  disable(2)
                                }
            MAX-ACCESS          read-create
            STATUS              current
            DESCRIPTION
                "The ID of VLAN that you want this interface to be in. 
                It must be a exist vlan id."
            ::= { ipifSupportV4V6Info 9 }

      ipifv6DHCPStatus       OBJECT-TYPE
            SYNTAX              INTEGER   {
                                  enable(1),    
                                  disable(2)
                                }
            MAX-ACCESS          read-create
            STATUS              current
            DESCRIPTION
                "The state of DHCPv6 that you want this interface to be in. 
                It must be a exist vlan id."
            ::= { ipifSupportV4V6Info 10 }

      ipifv6AutolinkloStatus OBJECT-TYPE
            SYNTAX              INTEGER   {
                                  enable(1),    
                                  disable(2)
                                }
            MAX-ACCESS          read-create
            STATUS              current
            DESCRIPTION
                "The global state of link local that you want this interface to be in. 
                It must be a exist vlan id."
            ::= { ipifSupportV4V6Info 11 }

      ipifv6NSRetransmitTime OBJECT-TYPE
            SYNTAX              INTEGER
            MAX-ACCESS          read-create
            STATUS              current
            DESCRIPTION
                "The NS's retransmit time that you want this interface to be in. 
                It must be a exist vlan id (1~3600)."
            ::= { ipifSupportV4V6Info 12 }

      ipifv6DefaultGateway OBJECT-TYPE
            SYNTAX              Ipv6Address
            MAX-ACCESS          read-create
            STATUS              current
            DESCRIPTION
                "The ipv6 default gateway that you want this interface to be in. 
                It must be a exist vlan id."
            ::= { ipifSupportV4V6Info 13 }
 
    -- ---------------------------------------------------------------------    
    -- ---------------------------------------------------------------------   

      ipifV6AddressTable          OBJECT-TYPE
         SYNTAX            SEQUENCE OF IpifV6AddressEntry
         MAX-ACCESS        not-accessible
         STATUS            current
         DESCRIPTION
            "A list of interface entries."
         ::= { ipifSupportV4V6Info 14}

      ipifV6AddressEntry          OBJECT-TYPE
         SYNTAX            IpifV6AddressEntry
         MAX-ACCESS        not-accessible
         STATUS            current
         DESCRIPTION
            "An entry containing management information applicable
               to a particular interface."
         INDEX { ipifV6AddressMainIndex, ipifV6AddressIpAddr, ipifV6AddressIpPrefix }
         ::= { ipifV6AddressTable 1 }

      IpifV6AddressEntry ::=
         SEQUENCE {
                ipifV6AddressMainIndex              InterfaceIndex,
                ipifV6AddressIpAddr                 Ipv6Address,     -- IPv6 Address.
                ipifV6AddressIpPrefix               INTEGER,         -- IPv6 Address Prefix.
                ipifV6AddressIpType                 INTEGER,         -- IP type (Link-local, Global, anycast).
                ipifV6AddressRowStatus              RowStatus        -- IPv6 Address entries row status.
            }

      ipifV6AddressMainIndex    OBJECT-TYPE
         SYNTAX                 InterfaceIndex
         MAX-ACCESS             read-only 
         STATUS                 current
         DESCRIPTION
            "The index of this IPv6 entry." 
         ::= { ipifV6AddressEntry 1 }

      ipifV6AddressIpAddr       OBJECT-TYPE
         SYNTAX                 Ipv6Address
         MAX-ACCESS             read-only
         STATUS                 current
         DESCRIPTION
            "The ip address of this IPv6 entry."
         DEFVAL { '00000000'H } 
         ::= { ipifV6AddressEntry 2 }
              
      ipifV6AddressIpPrefix     OBJECT-TYPE
            SYNTAX              INTEGER
            MAX-ACCESS          read-only
            STATUS              current
            DESCRIPTION
            "The ip prefix of this IPv6 entry."
        ::= { ipifV6AddressEntry 3 } 

      ipifV6AddressIpType       OBJECT-TYPE
         SYNTAX                 INTEGER {
                                    unicast(1), 
                                    anycast(2),
                                    linklocal(3)
                                }
            MAX-ACCESS          read-only
            STATUS              current
            DESCRIPTION
            "The ip type of this IPv6 entry."
        ::= { ipifV6AddressEntry 4 }
        
      ipifV6AddressRowStatus    OBJECT-TYPE
         SYNTAX                 RowStatus
         MAX-ACCESS             read-create
         STATUS                 current
         DESCRIPTION
            "The status of an entry in the Multi Interface Table.  Only a subset
             of the rowstatus variables (active, createAndWait, destroy) are available." 
         ::= { ipifV6AddressEntry 5 }     
    -- ---------------------------------------------------------------------    
    -- ---------------------------------------------------------------------   

    ipv4sysIprouteGateway OBJECT-TYPE 
       SYNTAX      IpAddress
       MAX-ACCESS  read-write
       STATUS      current
       DESCRIPTION 
          "IProute Gateway of the system."
       ::= { companyIpifGroup 8 }

    ipv4sysIprouteHops  OBJECT-TYPE
       SYNTAX      INTEGER
       MAX-ACCESS  read-write
       STATUS      current
       DESCRIPTION 
          "IProute Hops of the system."
       ::= { companyIpifGroup 9 }


        -- -------------------------------------------------------------------------
        -- companyTftpGroup         
        -- -------------------------------------------------------------------------
        tftpFwServerIpAddress OBJECT-TYPE
              SYNTAX IpAddress
              MAX-ACCESS read-write
              STATUS obsolete
              DESCRIPTION
                  "The TFTP server's IP address is used to upload or
  		           download firmware."
              ::= { companyTftpGroup 1 }
 

        tftpFwImageFileName OBJECT-TYPE
             SYNTAX DisplayString (SIZE(1..64))
             MAX-ACCESS read-write
             STATUS obsolete
             DESCRIPTION
                 "Configure firmware filename to download."
             ::= { companyTftpGroup 2 }

        tftpFwTftpOperation OBJECT-TYPE
             SYNTAX INTEGER {
                    none(0),
                    download(1),
                    upload(2)
             }
             MAX-ACCESS read-write
             STATUS obsolete
             DESCRIPTION
                 "The tftp operates to perform downloading the firmware image
                 to the unit. This object is used in conjunction with
 		         configBootTftpServerIp and configBootImageFileName."
             ::= { companyTftpGroup 3 }

        tftpFwTftpOperationStatus OBJECT-TYPE
             SYNTAX INTEGER {
                    none(0),
                    success(1),
                    fail(2),
                    progressing(3),
                    transmit(4)
             }
             MAX-ACCESS read-only
             STATUS obsolete
             DESCRIPTION
                 "The tftp operation status represent firmware backup or upgrade status."
             ::= { companyTftpGroup 4 }
         
         tftpCfgServerIpAddress OBJECT-TYPE
              SYNTAX IpAddress
              MAX-ACCESS read-write
              STATUS obsolete
              DESCRIPTION
                  "The TFTP server's IP address is used to upload or
  		           download configuration file."
              ::= { companyTftpGroup 5 }
                
         tftpConfigFileName OBJECT-TYPE
              SYNTAX DisplayString (SIZE(1..64))
              MAX-ACCESS read-write
              STATUS obsolete
              DESCRIPTION
                  "The configuration filename is used to store or retrieve config 
                   from the tftp server."
              ::= { companyTftpGroup 6 }
  
         tftpConfigTftpOperation OBJECT-TYPE
              SYNTAX INTEGER {
                     download(1),
                     upload(2),
                     progressing(3)
              }
              MAX-ACCESS read-write
              STATUS obsolete
              DESCRIPTION
                  "The tftp operates to perform either downloading the 
  		           configuration file to the unit or uploading the current
  		           configuration file to the tftp server. This object is 
  		           used in conjunction with configTftpServerIpAddress
  		           and configTftpServerFileName."
              ::= { companyTftpGroup 7 }

        tftpConfigTftpOperationStatus OBJECT-TYPE
             SYNTAX INTEGER {
                    none(0),
                    success(1),
                    fail(2),
                    progressing(3)
             }
             MAX-ACCESS read-only
             STATUS obsolete
             DESCRIPTION
                 "The tftp operation status represent configuration file backup or restore status."
             ::= { companyTftpGroup 8 }
             
    	tftpFwTargetGroup OBJECT IDENTIFIER ::= { companyTftpGroup 9 }
    	             
        tftpFwTargetServerIpAddress OBJECT-TYPE
              SYNTAX Ipv6Address
              MAX-ACCESS read-write
              STATUS current
              DESCRIPTION
                  "The TFTP server's IP address is used to upload or
  		           download firmware."
              ::= { tftpFwTargetGroup 1 }
 
        tftpFwTargetServerIpType OBJECT-TYPE
               SYNTAX    INTEGER {
                      iPv4              (1),
                      iPv6	            (2)
                   }
               MAX-ACCESS  read-write
               STATUS      current
               DESCRIPTION
                   "Type of IP interface."
               ::= { tftpFwTargetGroup 2 }
               
        tftpFwTargetInterfaceName OBJECT-TYPE
               SYNTAX      OCTET STRING
               MAX-ACCESS  read-write
               STATUS      current
               DESCRIPTION
                   "Specifies the interface name when the tftpFwTargetServerIpAddress
                    is linklocal address."
               ::= { tftpFwTargetGroup 3 }
               
        tftpFwTargetImageFileName OBJECT-TYPE
             SYNTAX DisplayString (SIZE(1..64))
             MAX-ACCESS read-write
             STATUS current
             DESCRIPTION
                 "Configure firmware filename to download."
             ::= { tftpFwTargetGroup 4 }

        tftpFwTargetTftpOperation OBJECT-TYPE
             SYNTAX INTEGER {
                    none(0),
                    download(1),
                    upload(2)
             }
             MAX-ACCESS read-write
             STATUS current
             DESCRIPTION
                 "The tftp operates to perform downloading the firmware image
                 to the unit. This object is used in conjunction with
 		         configBootTftpServerIp and configBootImageFileName."
             ::= { tftpFwTargetGroup 5 }

        tftpFwTargetTftpOperationStatus OBJECT-TYPE
             SYNTAX INTEGER {
                    none(0),
                    success(1),
                    fail(2),
                    progressing(3),
                    transmit(4)
             }
             MAX-ACCESS read-only
             STATUS current
             DESCRIPTION
                 "The tftp operation status represent firmware backup or upgrade status."
             ::= { tftpFwTargetGroup 6 }    	
             
    	tftpCfgTargetGroup OBJECT IDENTIFIER ::= { companyTftpGroup 10 }
    	                 	
         tftpCfgTargetServerIpAddress OBJECT-TYPE
              SYNTAX Ipv6Address
              MAX-ACCESS read-write
              STATUS current
              DESCRIPTION
                  "The TFTP server's IP address is used to upload or
  		           download configuration file."
              ::= { tftpCfgTargetGroup 1 }

        tftpCfgTargetServerIpType OBJECT-TYPE
               SYNTAX    INTEGER {
                      iPv4              (1),
                      iPv6	            (2)
                   }
               MAX-ACCESS  read-write
               STATUS      current
               DESCRIPTION
                   "Type of IP interface."
               ::= { tftpCfgTargetGroup 2 }
                
        tftpCfgTargetInterfaceName OBJECT-TYPE
               SYNTAX      OCTET STRING
               MAX-ACCESS  read-write
               STATUS      current
               DESCRIPTION
                   "Specifies the interface name when the tftpCfgTargetServerIpAddress
                    is linklocal address."
               ::= { tftpCfgTargetGroup 3 }
                
         tftpCfgTargetImageFileName OBJECT-TYPE
              SYNTAX DisplayString (SIZE(1..64))
              MAX-ACCESS read-write
              STATUS current
              DESCRIPTION
                  "The configuration filename is used to store or retrieve config 
                   from the tftp server."
              ::= { tftpCfgTargetGroup 4 }
  
         tftpCfgTargetTftpOperation OBJECT-TYPE
              SYNTAX INTEGER {
                     download(1),
                     upload(2),
                     progressing(3)
              }
              MAX-ACCESS read-write
              STATUS current
              DESCRIPTION
                  "The tftp operates to perform either downloading the 
  		           configuration file to the unit or uploading the current
  		           configuration file to the tftp server. This object is 
  		           used in conjunction with configTftpServerIpAddress
  		           and configTftpServerFileName."
              ::= { tftpCfgTargetGroup 5 }

        tftpCfgTargetTftpOperationStatus OBJECT-TYPE
             SYNTAX INTEGER {
                    none(0),
                    success(1),
                    fail(2),
                    progressing(3)
             }
             MAX-ACCESS read-only
             STATUS current
             DESCRIPTION
                 "The tftp operation status represent configuration file backup or restore status."
             ::= { tftpCfgTargetGroup 6 }    
             
         tftpCfgTargetConfigID OBJECT-TYPE
              SYNTAX INTEGER {
                     config1(1),
                     config2(2)
              }
              MAX-ACCESS read-write
              STATUS current
              DESCRIPTION
                  "The tftp operates to perform either downloading the 
  		           configuration file to the unit or uploading the current
  		           configuration file to the tftp server. This object is 
  		           used in conjunction with configTftpServerIpAddress
  		           and configTftpServerFileName."
              ::= { tftpCfgTargetGroup 7 }
	

        -- -------------------------------------------------------------------------
        -- company Extension MIB, Miscellaneous Information         
        -- -------------------------------------------------------------------------

        miscReset OBJECT-TYPE
            SYNTAX INTEGER {
                   reset(1),
                   noop(2)
            }
            MAX-ACCESS read-write
            STATUS current
            DESCRIPTION
                "Physically resets the unit - use with care. A (1) resets 
                 the unit, a (2) does nothing."
            ::= { companyMiscGroup 2 }

        miscStatisticsReset OBJECT-TYPE
            SYNTAX INTEGER {
                   reset(1),
                   noop(2)
            }
            MAX-ACCESS read-write
            STATUS current
            DESCRIPTION
                "Resets the units statistics. A (1) resets 
                 the statistics count, a (2) does nothing."
            ::= { companyMiscGroup 3 }
 -- ----------------------------------------------------------
 -- The companySecurity Groups
 -- ----------------------------------------------------------      	
    securityIpMacPortBinding                     OBJECT IDENTIFIER ::= { companySecurity 10 }
 -- IpMacPortBinding Group --------------------------------------------- --
    
    impbSettingTable     OBJECT-TYPE
        SYNTAX SEQUENCE OF ImpbSettingEntry
        MAX-ACCESS not-accessible
        STATUS current
        DESCRIPTION
            "A table to control IP-MAC-Port Binding Setting features of the device."
        ::= { securityIpMacPortBinding 1 }
        
    impbSettingEntry OBJECT-TYPE
        SYNTAX ImpbSettingEntry
        MAX-ACCESS not-accessible
        STATUS current
        DESCRIPTION
            "An entry appears in IP-MAC-Port Binding Setting table for each interface 
 	        in the system."
        INDEX { impbPortIndex }
        ::= { impbSettingTable 1 }
  
    ImpbSettingEntry ::= 
           SEQUENCE { 
              impbPortIndex 
                 INTEGER, 
              impbPortState 
                 INTEGER,   
              impbPortDHCPSnoopingState
                 INTEGER,
              impbPortArpInspectionState 
                 INTEGER,
              impbPortIpInspectionState 
                 INTEGER,   
              impbPortAllowZeroIPState   
                 INTEGER,
              impbPortForwardDHCPPktState   
                 INTEGER,
              impbPortDHCPMaxEntryIPv4
                 Integer32,
              impbPortDHCPMaxEntryIPv6
                 Integer32,
              impbPortNDInspectionState 
                 INTEGER,
              impbPortProtocolState 
                 INTEGER                
         }
        
         impbPortIndex OBJECT-TYPE 
           SYNTAX      INTEGER 
           MAX-ACCESS  read-only 
           STATUS      current 
           DESCRIPTION 
              "Specifies the port numbers through which the authorized manager can
	        access the switch. 
	        By default the authorized manager is allowed to access the switch 
	        through all the ports.
	        If a set of ports are configured in the 'PortList', the manager can
	        access the switch only through the configured ports."
           ::= { impbSettingEntry 1 }
            
         impbPortState OBJECT-TYPE
           SYNTAX INTEGER  {
        		  disabled (0), enabled (1)
            }
           MAX-ACCESS  read-write
           STATUS      current
           DESCRIPTION
              "Disable / enable IP-MAC-Port Binding admin state for the interface."
        
           ::= { impbSettingEntry 2 }
             
         impbPortDHCPSnoopingState OBJECT-TYPE
           SYNTAX INTEGER  {
        		  disabled (0), enabled (1)
            }
           MAX-ACCESS  read-write
           STATUS      current
           DESCRIPTION
              "Disable / enable IP-MAC-Port Binding DHCP snooping state for the interface."
        
           ::= { impbSettingEntry 4 }
           
         impbPortArpInspectionState OBJECT-TYPE
           SYNTAX INTEGER  {
        		  disabled (0), strict (1), loose (2)
            }
           MAX-ACCESS  read-write
           STATUS      current
           DESCRIPTION
              "Set IP-MAC-Port Binding ARP Inspection state for the interface."
        
           ::= { impbSettingEntry 5 }                             

         impbPortIpInspectionState OBJECT-TYPE
           SYNTAX INTEGER  {
        		  disabled (0), enabled (1)
            }
           MAX-ACCESS  read-write
           STATUS      current
           DESCRIPTION
              "Set IP-MAC-Port Binding IP Inspection state for the interface."
        
           ::= { impbSettingEntry 6 }
           
         impbPortAllowZeroIPState OBJECT-TYPE
           SYNTAX INTEGER  {
        		  disabled (0), enabled (1)
            }
           MAX-ACCESS  read-write
           STATUS      current
           DESCRIPTION
              "Disable / enable IP-MAC-Port Binding Allow-Zero-IP state for the interface."
        
           ::= { impbSettingEntry 7 }
           
         impbPortForwardDHCPPktState OBJECT-TYPE
           SYNTAX INTEGER  {
        		  disabled (0), enabled (1)
            }
           MAX-ACCESS  read-write
           STATUS      current
           DESCRIPTION
              "Disable / enable IP-MAC-Port Binding Forward-DHCP-Packet state for the interface."
        
           ::= { impbSettingEntry 8 }  
           
           impbPortDHCPMaxEntryIPv4 OBJECT-TYPE
           SYNTAX      Integer32 (0..10)
           MAX-ACCESS  read-write
           STATUS      current
           DESCRIPTION
              "Set the maximum number of IPv4 entries that can be learned for the interface."
        
           ::= { impbSettingEntry 9 }    
           
           impbPortDHCPMaxEntryIPv6 OBJECT-TYPE
           SYNTAX      Integer32 (0..10)
           MAX-ACCESS  read-write
           STATUS      current
           DESCRIPTION
              "Set the maximum number of IPv6 entries that can be learned for the interface."
        
           ::= { impbSettingEntry 10 }

           impbPortNDInspectionState OBJECT-TYPE
           SYNTAX INTEGER  {
        		  disabled (0), enabled (1)
            }
           MAX-ACCESS  read-write
           STATUS      current
           DESCRIPTION
              "Set IP-MAC-Port Binding ND Inspection state for the interface."        

           ::= { impbSettingEntry 11 }

           impbPortProtocolState OBJECT-TYPE
           SYNTAX INTEGER  {
        		  ipv4 (0), ipv6 (1), all (2)
            }
           MAX-ACCESS  read-write
           STATUS      current
           DESCRIPTION
              "Set IP-MAC-Port Binding protocol state for the interface."
        
           ::= { impbSettingEntry 12 }
           
  
    impbAutoScanTable  OBJECT-TYPE
            SYNTAX SEQUENCE OF ImpbAutoScanEntry
            MAX-ACCESS not-accessible
            STATUS current
            DESCRIPTION
                "A table to control auto scan features of the device."
            ::= { securityIpMacPortBinding 2 }
        
    impbAutoScanEntry OBJECT-TYPE
        SYNTAX ImpbAutoScanEntry
        MAX-ACCESS not-accessible
        STATUS current
        DESCRIPTION
            "An entry appears in auto scan table for each interface 
          in the system."
        INDEX { impbAutoScanMacAddress, impbAutoScanPort, impbAutoScanIpAddress}
        ::= { impbAutoScanTable 1 }
  
    ImpbAutoScanEntry ::= 
           SEQUENCE { 
              impbAutoScanMacAddress 
                 MacAddress, 
              impbAutoScanPort   
                 Integer32,
              impbAutoScanIpAddress 
                 DisplayString,
              impbAutoScanVlanId 
                 Integer32, 
              impbAutoScanBinding   
                 INTEGER             
          }
           
         impbAutoScanMacAddress OBJECT-TYPE 
           SYNTAX      MacAddress 
           MAX-ACCESS  read-only 
           STATUS      current 
           DESCRIPTION 
              "The MAC address associated of the auto scan entry."
           ::= { impbAutoScanEntry 1 } 
         
         impbAutoScanPort OBJECT-TYPE 
           SYNTAX      Integer32 
           MAX-ACCESS  read-only 
           STATUS      current 
           DESCRIPTION 
              "The port number of the auto scan entry."
           ::= { impbAutoScanEntry 2 }
                      
         impbAutoScanIpAddress OBJECT-TYPE 
           SYNTAX      DisplayString 
           MAX-ACCESS  read-only 
           STATUS      current 
           DESCRIPTION 
              "The IP address associated of the auto scan entry."      
           DEFVAL { '00000000'H } 
           ::= { impbAutoScanEntry 3 } 
           
         impbAutoScanVlanId OBJECT-TYPE 
           SYNTAX      Integer32 
           MAX-ACCESS  read-only 
           STATUS      current 
           DESCRIPTION 
              "The VLAN ID of the auto scan entry."
           ::= { impbAutoScanEntry 4 }  
           
         impbAutoScanBinding OBJECT-TYPE 
           SYNTAX INTEGER  {
        		  disabled (0), enabled (1)
            } 
           MAX-ACCESS  read-write 
           STATUS      current 
           DESCRIPTION 
              "Disable / enable IP-MAC-Port Binding for the entry."
           ::= { impbAutoScanEntry 5 }

    impbBindingListTable     OBJECT-TYPE
        SYNTAX SEQUENCE OF ImpbBindingListEntry
        MAX-ACCESS not-accessible
        STATUS current
        DESCRIPTION
            "A table to control Manual IP-MAC-Port Binding white list features of the device."
        ::= { securityIpMacPortBinding 3 }
        
    impbBindingListEntry OBJECT-TYPE
        SYNTAX ImpbBindingListEntry
        MAX-ACCESS not-accessible
        STATUS current
        DESCRIPTION
            "An entry appears in Manual IP-MAC-Port Binding white list table for each interface 
 	        in the system."
        INDEX { impbBindingListIpAddress, impbBindingListMacAddress }
        ::= { impbBindingListTable 1 }
  
    ImpbBindingListEntry ::= 
           SEQUENCE { 
              impbBindingListIpAddress 
                 DisplayString,
              impbBindingListMacAddress 
                 MacAddress, 
              impbBindingListPort   
                 Integer32,
              impbBindingListRowStatus   
                 RowStatus             
          }       
          
         impbBindingListIpAddress OBJECT-TYPE 
           SYNTAX      DisplayString 
           MAX-ACCESS  read-only 
           STATUS      current 
           DESCRIPTION 
              "The IP address associated of the Manual IP-MAC-PORT Binding white list entry."
           DEFVAL { '00000000'H }
           ::= { impbBindingListEntry 1 } 
            
         impbBindingListMacAddress OBJECT-TYPE 
           SYNTAX      MacAddress 
           MAX-ACCESS  read-only 
           STATUS      current 
           DESCRIPTION 
              "The MAC address associated of the Manual IP-MAC-PORT Binding white list entry."
           ::= { impbBindingListEntry 2 } 
           
         impbBindingListPort OBJECT-TYPE 
           SYNTAX      Integer32 
           MAX-ACCESS  read-write 
           STATUS      current 
           DESCRIPTION 
              "The port number of the Manual IP-MAC-PORT Binding white list entry."
           ::= { impbBindingListEntry 3 } 
           
         impbBindingListRowStatus OBJECT-TYPE
            SYNTAX      RowStatus
            MAX-ACCESS  read-create
            STATUS      current
            DESCRIPTION
                "The status of a row in impbBindingListTable. By setting this object, new
                entries can be created in impbBindingListTable and existing entries can be
                removed from impbBindingListTable. It can be used as specified in the SNMP
                v2 standard."
            ::= { impbBindingListEntry 4 } 

    impbBlockListTable     OBJECT-TYPE
        SYNTAX SEQUENCE OF ImpbBlockListEntry
        MAX-ACCESS not-accessible
        STATUS current
        DESCRIPTION
            "A table to control IP-MAC-Port Binding black list of the device."
        ::= { securityIpMacPortBinding 4 }
        
    impbBlockListEntry OBJECT-TYPE
        SYNTAX ImpbBlockListEntry
        MAX-ACCESS not-accessible
        STATUS current
        DESCRIPTION
            "An entry appears in Manual IP-MAC-Port Binding black list table for each interface 
 	        in the system."
        INDEX { impbBlockListMacAddress, impbBlockListVlanId, impbBlockListPort }
        ::= { impbBlockListTable 1 }
  
    ImpbBlockListEntry ::= 
           SEQUENCE { 
              impbBlockListMacAddress 
                 MacAddress, 
              impbBlockListVlanId 
                 Integer32, 
              impbBlockListPort   
                 Integer32,
              impbBlockListIpAddress 
                 DisplayString,
              impbBlockListStatus   
                 INTEGER             
          }
          
        impbBlockListMacAddress OBJECT-TYPE 
           SYNTAX      MacAddress 
           MAX-ACCESS  read-only 
           STATUS      current 
           DESCRIPTION 
              "The MAC address associated of the IP-MAC-PORT Binding black list entry."
           ::= { impbBlockListEntry 1 } 
         
         impbBlockListVlanId OBJECT-TYPE 
           SYNTAX      Integer32 
           MAX-ACCESS  read-only 
           STATUS      current 
           DESCRIPTION 
              "The VLAN ID of the IP-MAC-PORT Binding black list entry."
           ::= { impbBlockListEntry 2 }
           
         impbBlockListPort OBJECT-TYPE 
           SYNTAX      Integer32 
           MAX-ACCESS  read-only
           STATUS      current 
           DESCRIPTION 
              "The port number of the IP-MAC-PORT Binding black list entry."
           ::= { impbBlockListEntry 3 } 
           
         impbBlockListIpAddress OBJECT-TYPE 
           SYNTAX      DisplayString 
           MAX-ACCESS  read-only 
           STATUS      current 
           DESCRIPTION 
              "The IP address associated of the IP-MAC-PORT Binding black list entry."  
           DEFVAL { '00000000'H }
           ::= { impbBlockListEntry 4 } 
           
         impbBlockListStatus OBJECT-TYPE
            SYNTAX      INTEGER {
        		  nothing (0), deleted (1)
            }
            MAX-ACCESS  read-write
            STATUS      current
            DESCRIPTION
                "nothing/delete IP-MAC-Port Binding for the interface."
            ::= { impbBlockListEntry 5 }    

    impbAutoScanIpAddressFrom OBJECT-TYPE 
        SYNTAX      Ipv6Address 
        MAX-ACCESS  read-write 
        STATUS      current 
        DESCRIPTION 
           "The begin for IP address associated of the IP-MAC-PORT Binding auto scan entry."
        DEFVAL { '00000000'H }
        ::= { securityIpMacPortBinding 5 }
            
    impbAutoScanIpAddressTo OBJECT-TYPE 
        SYNTAX      Ipv6Address 
        MAX-ACCESS  read-write 
        STATUS      current 
        DESCRIPTION 
           "The end for IP address associated of the IP-MAC-PORT Binding auto scan entry."
        DEFVAL { '00000000'H }
        ::= { securityIpMacPortBinding 6 }
           
    impbAutoScanStatus OBJECT-TYPE
        SYNTAX      INTEGER {
      		  nothing (0), scan (1)
        }
        MAX-ACCESS  read-write
        STATUS      current
        DESCRIPTION
            "Nothing / scan IP-MAC-Port Binding auto scan for the interface."
        ::= { securityIpMacPortBinding 7 }
                                                               
    impbDhcpSnoopingTable     OBJECT-TYPE
        SYNTAX SEQUENCE OF ImpbDhcpSnoopingEntry
        MAX-ACCESS not-accessible
        STATUS current
        DESCRIPTION
            "A table to display DHCP snooping entries of the device."
        ::= { securityIpMacPortBinding 8 }
        
    impbDhcpSnoopingEntry OBJECT-TYPE
        SYNTAX ImpbDhcpSnoopingEntry
        MAX-ACCESS not-accessible
        STATUS current
        DESCRIPTION
            "An entry appears in DHCP snooping table for each interface 
 	        in the system."
        INDEX { impbDhcpSnoopingMacAddress, impbDhcpSnoopingIpAddress }
        ::= { impbDhcpSnoopingTable 1 }
  
    ImpbDhcpSnoopingEntry ::= 
           SEQUENCE {   
              impbDhcpSnoopingMacAddress 
                 MacAddress,
              impbDhcpSnoopingIpAddress 
                 Ipv6Address,
              impbDhcpSnoopingLeaseTime
                 Integer32,
              impbDhcpSnoopingPort   
                 Integer32
          }       
                  
         impbDhcpSnoopingMacAddress OBJECT-TYPE 
           SYNTAX      MacAddress 
           MAX-ACCESS  read-only 
           STATUS      current 
           DESCRIPTION 
              "The MAC address associated of the DHCP snooping entry."
           ::= { impbDhcpSnoopingEntry 1 } 
           
         impbDhcpSnoopingIpAddress OBJECT-TYPE 
           SYNTAX      Ipv6Address 
           MAX-ACCESS  read-only 
           STATUS      current 
           DESCRIPTION 
              "The IP address associated of the DHCP snooping entry."
           DEFVAL { '00000000'H }
           ::= { impbDhcpSnoopingEntry 2 } 
         
         impbDhcpSnoopingLeaseTime OBJECT-TYPE 
           SYNTAX      Integer32 
           MAX-ACCESS  read-only 
           STATUS      current 
           DESCRIPTION 
              "The lease time associated of the DHCP snooping entry."
           ::= { impbDhcpSnoopingEntry 3 }
           
         impbDhcpSnoopingPort OBJECT-TYPE 
           SYNTAX      Integer32 
           MAX-ACCESS  read-only 
           STATUS      current 
           DESCRIPTION 
              "The port number associated of the DHCP snooping entry."
           ::= { impbDhcpSnoopingEntry 4 } 
        
    impbRoamingState OBJECT-TYPE
           SYNTAX INTEGER  {
                  disabled (0), enabled (1)
            }
           MAX-ACCESS  read-write
           STATUS      current
           DESCRIPTION
              "Disable / enable IP-MAC-Port Binding roaming state."
           ::= { securityIpMacPortBinding 9 }

    impbVlanModeState OBJECT-TYPE
           SYNTAX INTEGER  {
                  disabled (0), enabled (1)
            }
           MAX-ACCESS  read-write
           STATUS      current
           DESCRIPTION
              "Disable / enable IP-MAC-Port Binding vlan mode state."
           ::= { securityIpMacPortBinding 10 }

    impbVlanModeVlanList OBJECT-TYPE
           SYNTAX      PortList
           MAX-ACCESS  read-write
           STATUS      current
           DESCRIPTION
              "IP-MAC-Port Binding vlan mode VID list."
           ::= { securityIpMacPortBinding 11 }

    impbLogState OBJECT-TYPE
           SYNTAX INTEGER  {
                  disabled (0), ipv4 (1), ipv6 (2), all (3)
            }
           MAX-ACCESS  read-write
           STATUS      current
           DESCRIPTION
              "Configure IP-MAC-Port Binding log state."
           ::= { securityIpMacPortBinding 12 }
    
    impbDHCPv6PrefixDelegationSnoopState OBJECT-TYPE
           SYNTAX INTEGER  {
                  disabled (0), enabled (1)
            }
           MAX-ACCESS  read-write
           STATUS      current
           DESCRIPTION
              "Configure DHCPv6 PD snooping state."
           ::= { securityIpMacPortBinding 13 }  
           
    impbBindingtraplog OBJECT-TYPE
           SYNTAX INTEGER  {
                  disabled (2), enabled (1)
            }
           MAX-ACCESS  read-write
           STATUS      current
           DESCRIPTION
              "This object is for enabling or disabling topology change event trap in the system."
           ::= { securityIpMacPortBinding 14 }       
 
    impbBindingtrap  OBJECT IDENTIFIER ::= { securityIpMacPortBinding 15 }
        
    impbBindingtrapsign  NOTIFICATION-TYPE
           STATUS  current
           DESCRIPTION
              "The object is for IMPB trap sign in the system."
              ::= {impbBindingtrap 1 }
         
    impbAutoScanCurrentStatus OBJECT-TYPE 
           SYNTAX INTEGER  {
        		  stop (0), scanning (1) 
            } 
           MAX-ACCESS  read-only 
           STATUS      current 
           DESCRIPTION 
              "Show Auto scan status"
           ::= { securityIpMacPortBinding 16 }
         
          
        -- ----------------------------------------------------------------
        -- The STP Bridge Global
        -- ----------------------------------------------------------------
        stpBridgeGlobal  OBJECT IDENTIFIER ::= { companySTP 1 }
        
        stpModuleStatus OBJECT-TYPE
           SYNTAX   INTEGER { 
                        enabled(1), 
                        disabled(2) 
                    }
           MAX-ACCESS  read-write
           STATUS      current
           DESCRIPTION
              "The administrative status requested by management for the MST  
              feature. The value enabled(1) indicates that Mst should be enabled  
              in the device on all ports. The value disabled(2) indicates that 
              Mst should be disabled in the device on all ports. The object can 
              be set to enabled(1) if and only if, fsMIMstSystemControl set to start."
           ::= { stpBridgeGlobal 1 }
           
        stpProtocolVersion OBJECT-TYPE
           SYNTAX      INTEGER {
                          stp(1),
                          rstp(2),
                          mstp(3)
                       }
           MAX-ACCESS  read-write 
           STATUS      current
           DESCRIPTION
              "The version of Spanning Tree Protocol the bridge is
        	   currently running.  The value 'stpCompatible(0)'
        	   indicates the Spanning Tree Protocol specified in
        	   IEEE 802.1D and 'rstp(2)' indicates the Rapid Spanning
        	   Tree Protocol specified in IEEE 802.1w and 'mstp(3)'
        	   indicates the Multiple Spanning Tree Protocol Specified
        	   in IEEE 802.1s." 
           DEFVAL { rstp }
           ::= { stpBridgeGlobal 2 }
           
        stpBridgePriority OBJECT-TYPE
           SYNTAX      Integer32 (0..61440) 
           MAX-ACCESS  read-write
           STATUS      current
           DESCRIPTION
              "The Value of the writable portion of the Bridge
               Identifier comprising of the first two octets.
               The values that are set for Bridge Priority must be 
               in steps of 4096."
           DEFVAL {32768}
           ::= { stpBridgeGlobal 3 }          

        stpTxHoldCount OBJECT-TYPE
            SYNTAX      Integer32 (1..10)
            MAX-ACCESS  read-write
            STATUS      current
            DESCRIPTION
               "The value used by the Port Transmit state machine to limit
                the maximum transmission rate."
            DEFVAL  { 3 }
            ::= { stpBridgeGlobal 4 }

        stpBridgeMaxAge OBJECT-TYPE
            SYNTAX      Timeout (600..4000)  
            MAX-ACCESS  read-write
            STATUS      current
            DESCRIPTION
               "The value that all bridges use for MaxAge when
                this bridge is acting as the root. The granularity 
                of this timer is specified to be 1 second.
                An agent may return a badValue error if a set is
                attempted to a value which is not a whole number
                of seconds."
            DEFVAL {2000}
            ::= { stpBridgeGlobal 5 }
        
        stpBridgeHelloTime OBJECT-TYPE
           SYNTAX      Timeout (100..1000)  
           MAX-ACCESS  read-write  
           STATUS      current
           DESCRIPTION
               "The amount of time between the transmission of
               Configuration bridge PDUs by this node in units 
               of hundredths of a second."
           ::= { stpBridgeGlobal 6 }

        stpBridgeForwardDelay OBJECT-TYPE
           SYNTAX      Timeout (400..3000)  
           MAX-ACCESS  read-write
           STATUS      current
           DESCRIPTION
                "The value that all bridges use for ForwardDelay
                 when this bridge is acting as the root.  Note that
                 802.1D specifies that the range for this
                 parameter is related to the value of
                 BridgeMaxAge.  The granularity of this
                 timer is specified to be 1 second.
                 An agent may return a badValue error if a set is
                 attempted to a value which is not a whole number
                 of seconds."
           DEFVAL {1500}
           ::= { stpBridgeGlobal 7 }
        stpFowardBPDU OBJECT-TYPE
           SYNTAX   INTEGER { 
                        enabled(1), 
                        disabled(2) 
                    }
           MAX-ACCESS  read-write
           STATUS      current
           DESCRIPTION
              "This object is for enabling or disabling forward BPDU."
           ::= {stpBridgeGlobal 8 }   

        stpRootBridge  OBJECT-TYPE
           SYNTAX      BridgeId  
           MAX-ACCESS  read-only
           STATUS      current
           DESCRIPTION
                "The bridge identifier of the Root of the common spanning
                 tree as determined by the Spanning Tree Protocol
                 as executed by this node.  This value is used as
                 the CIST Root Identifier parameter in all Configuration
                 Bridge PDUs originated by this node."
           ::= { stpBridgeGlobal 9 }
           
        stpRootCost OBJECT-TYPE
           SYNTAX      Integer32 
           MAX-ACCESS  read-only
           STATUS      current
           DESCRIPTION
                "The Cost of the path to the CIST Root as seen 
                from this bridge."
           ::= { stpBridgeGlobal 10 }
           
        stpMaxAge OBJECT-TYPE
           SYNTAX      Timeout
           MAX-ACCESS  read-only  
           STATUS      current
           DESCRIPTION
                 "The maximum age of Spanning Tree Protocol
                  information learned from the network on any port
                  before it is discarded, in units of hundredths of
                  a second.  This is the actual value that this
                  bridge is currently using."
           ::= { stpBridgeGlobal 11 }
           
        stpForwardDelay OBJECT-TYPE
           SYNTAX      Timeout
           MAX-ACCESS  read-only  
           STATUS      current
           DESCRIPTION
           	  "This time value, measured in units of hundredths
        	   of a second, controls how fast a port changes its
        	   spanning state when moving towards the Forwarding
        	   state.  The value determines how long the port
        	   stays in a particular state before moving to the
        	   next state."
           ::= { stpBridgeGlobal 12 }
           
        stpRootPort OBJECT-TYPE
           SYNTAX      Integer32  
           MAX-ACCESS  read-only      
           STATUS      current 
           DESCRIPTION 
              "The Port Number of the Port which offers the lowest    
               path cost from this bridge to the CIST Root Bridge."
           ::= { stpBridgeGlobal 13 }      
           
        stpTopologyChangeTrapStatus OBJECT-TYPE
           SYNTAX      INTEGER  {
        		 enabled(1),
        		 disabled(2)
            }  
           MAX-ACCESS  read-write     
           STATUS      current 
           DESCRIPTION 
              "This object is for enabling or disabling topology change event
               trap in the system."
           DEFVAL  { disabled }
           ::= { stpBridgeGlobal 14 }  
           
        stpNewRootTrapStatus OBJECT-TYPE
           SYNTAX      INTEGER  {
        		 enabled(1),
        		 disabled(2)
            }  
           MAX-ACCESS  read-write     
           STATUS      current 
           DESCRIPTION 
              "This object is for enabling or disabling new root event
               trap in the system."
           DEFVAL  { disabled }
           ::= { stpBridgeGlobal 15 }  		   

        stpNewRootTraps  OBJECT IDENTIFIER ::= { stpBridgeGlobal 16 }
         
        brgAddress NOTIFICATION-TYPE
           STATUS  current
           DESCRIPTION
              "The MAC address used by this bridge when it must
               be referred to in a unique fashion."
              ::= { stpNewRootTraps 1 }

        oldDesignatedRoot NOTIFICATION-TYPE
           STATUS  current
           DESCRIPTION
              "The bridge identifier of the old root of the spanning
 	       tree instance as determined by the Spanning Tree Protocol
 	       as executed by this node."

              ::= { stpNewRootTraps 2 }

        mstiBridgeRegionalRoot NOTIFICATION-TYPE
           STATUS  current
           DESCRIPTION
              "MSTI Regional Root Identifier value for the Instance."
              ::= { stpNewRootTraps 3 }
           
           
     -- -------------------------------------
     -- The Spanning Tree Port Table   
     -- -------------------------------------
             
        stpPortTable OBJECT-TYPE
           SYNTAX  SEQUENCE OF StpPortEntry
           MAX-ACCESS  not-accessible
           STATUS  current
           DESCRIPTION
             "A table that contains port-specific information
             for the Spanning Tree Protocol."
           ::= { companySTP 2 }
        
        stpPortEntry OBJECT-TYPE
           SYNTAX  StpPortEntry
           MAX-ACCESS  not-accessible
           STATUS  current
           DESCRIPTION
             "A list of information maintained by every port
             about the Spanning Tree Protocol state for that
             port."
           INDEX   { stpPort }
           ::= { stpPortTable 1 }

        StpPortEntry ::=
           SEQUENCE {
                  stpPort
                     INTEGER,
                  stpPortStatus
                     INTEGER,                     
                  stpPortPriority
                     INTEGER,
                  stpAdminPortPathCost
                     INTEGER,
                  stpPortPathCost
                     INTEGER,
                  stpPortProtocolMigration
                     TruthValue,
                  stpPortEdge
                     INTEGER,
                  stpPortAdminP2P
                     INTEGER,
                  stpPortRestrictedRole 
                     TruthValue, 
                  stpPortRestrictedTCN
                     TruthValue,
                  stpPortHelloTime
                     Timeout,
                  stpPortState
                     INTEGER,
                  stpPortFowardBPDU
                     INTEGER
        }

        stpPort OBJECT-TYPE
           SYNTAX      INTEGER (1..65535)
           MAX-ACCESS  read-only
           STATUS      current
           DESCRIPTION
              "The Port number of the port for which this entry contains   
               spanning tree information."                                      
           ::= { stpPortEntry 1 }
           
        stpPortStatus OBJECT-TYPE
          SYNTAX      INTEGER {
                       enabled(1),
                       disabled(0)
                      }
          MAX-ACCESS  read-write           
          STATUS      current
          DESCRIPTION
              "Current state of the Port which can be changed to either 
               Disabled or Enabled for ALL spanning tree   
               instances. Setting this object will override the port's
               status in any of the MSTI contexts"                                        
          ::= { stpPortEntry 2 }
          
        stpPortPriority OBJECT-TYPE
           SYNTAX      INTEGER (0..240)
           MAX-ACCESS  read-write           
           STATUS      current
           DESCRIPTION
              "The four most significant bits of the Port Identifier 
              of the Spanning Tree instance can be modified by setting 
              the CistPortPriority value. The values that are set for Port 
              Priority must be in steps of 16."
           DEFVAL {128}
           ::= { stpPortEntry 3 }

        stpAdminPortPathCost OBJECT-TYPE
           SYNTAX  INTEGER (0..200000000)
           MAX-ACCESS  read-write
           STATUS  current
           DESCRIPTION
             "The contribution of this port to the path cost of
             paths towards the spanning tree root which include
             this port.  Writing a value of '0' assigns the 
             automatically calculated default Path Cost value to 
             the ohter object stpPortPathCost. If the default 
             Path Cost is being used,this object returns '0' when 
             read."
           REFERENCE
             "IEEE 802.1D-2004"
           ::= { stpPortEntry 4 }
           
        stpPortPathCost OBJECT-TYPE
           SYNTAX      INTEGER (1..200000000)
           MAX-ACCESS  read-only           
           STATUS      current
           DESCRIPTION
                "The contribution of this port to the path cost of
                 paths towards the CIST Root which include this port."
           ::= { stpPortEntry 5 }
           
        stpPortProtocolMigration OBJECT-TYPE
           SYNTAX      TruthValue                
           MAX-ACCESS  read-write           
           STATUS      current
           DESCRIPTION
              "Indicates the Protocol migration state of this Port.         
               When operating in RSTP/MSTP (version >= 2) mode, writing 
               TRUE(1) to this object forces this port to transmit MSTP 
               BPDUs without instance information.
               Any other operation on this object has no effect and
               it always returns FALSE(2) when read."
           ::= { stpPortEntry 6 }
        
        stpPortEdge OBJECT-TYPE
            SYNTAX      INTEGER {
                           true(1),
                           false(0),
                           auto(2)
                       }
            MAX-ACCESS  read-write
            STATUS      current
            DESCRIPTION
                " This parameter when TRUE(1) indicates that detection of a port 
                 as Edge Port happens automatically and FALSE(2) 
                 indicates that this feature is disabled."
           ::= { stpPortEntry 7 }
        
        stpPortAdminP2P OBJECT-TYPE
           SYNTAX      INTEGER {               
                         forceTrue(0),
                         forceFalse(1),
                         auto(2)
                       }
           MAX-ACCESS  read-write           
           STATUS      current
           DESCRIPTION
              "The administrative point-to-point status of the LAN segment
               attached to this port.  A value of forceTrue(0) indicates that
               this port should always be treated as if it is connected to
               a point-to-point link.  A value of forceFalse(1) indicates
               that this port should be treated as having a shared media
               connection.  A value of auto(2) indicates that this port is
               considered to have a point-to-point link if it is an Aggregator
               and all of its members are aggregatable, or if the MAC entity
               is configured for full duplex operation, either through
               auto-negotiation or by management means."
           ::= { stpPortEntry 8 }
        
        stpPortRestrictedRole OBJECT-TYPE 
            SYNTAX      TruthValue 
            MAX-ACCESS  read-write 
            STATUS      current 
            DESCRIPTION 
                "A Boolean value set by management. If TRUE causes the Port not 
                 to be selected as Root Port for the CIST or any MSTI, even it has 
                 the best spanning tree priority vector. Such a Port will be selected 
                 as an Alternate Port after the Root Port has been selected. This 
                 parameter should be FALSE by default. If set it can cause lack of 
                 spanning tree connectivity. It is set by a network administrator to 
                 prevent bridges external to a core region of the network influencing 
                 the spanning tree active topology, possibly because those bridges are 
                 not under the full control of the administrator.
                 This administrator configuration is also known as 'Root Guard'."
            ::= {stpPortEntry 9}
  
        stpPortRestrictedTCN OBJECT-TYPE 
            SYNTAX      TruthValue 
            MAX-ACCESS  read-write 
            STATUS      current 
            DESCRIPTION 
                "A Boolean value set by management. If TRUE causes the Port not 
                 to propagate received topology change notifications and topology 
                 changes to other Ports. This parameter should be FALSE by default. 
                 If set it can cause temporary loss of connectivity after changes in 
                 a spanning trees active topology as a result of persistent 
                 incorrectly learnt station location information. It is set by a 
                 network administrator to prevent bridges external to a core region of 
                 the network causing address flushing in that region, possibly because 
                 those bridges are not under the full control of the administrator or 
                 MAC-Operational for the attached LANs transitions frequently." 
            ::= {stpPortEntry 10}
           
        stpPortHelloTime OBJECT-TYPE
           SYNTAX      Timeout (100..1000)  
           MAX-ACCESS  read-write  
           STATUS      current
           DESCRIPTION
               "The amount of time between the transmission of
               Configuration bridge PDUs by this node in units 
               of hundredths of a second."
           ::= { stpPortEntry 11 }
            
        stpPortState OBJECT-TYPE
             SYNTAX    INTEGER {              
                         disabled (1),
                         discarding (2),
                         learning (4),
                         forwarding (5)
                       }
             MAX-ACCESS  read-only            
             STATUS      current
             DESCRIPTION
                 "Current state of the Port as defined by the Common    
                  spanning tree protocol." 
           ::= { stpPortEntry 12 }
            
        stpPortFowardBPDU OBJECT-TYPE
           SYNTAX  INTEGER {
                       enabled(1),
                       disabled(2)
                   }
           MAX-ACCESS  read-write
           STATUS  current
           DESCRIPTION
             "This object is for enabling or disabling forward BPDU."
           REFERENCE
             "IEEE 802.1D-2004"
           ::= { stpPortEntry 13 }

        -- ----------------------------------------------------------------
        -- The MST Configuration Identification
        -- ----------------------------------------------------------------
        mstConfigurationIdentification  OBJECT IDENTIFIER ::= { companySTP 3 }
        
        mstiConfigurationName OBJECT-TYPE
           SYNTAX      OCTET STRING (SIZE (0..32))
           MAX-ACCESS  read-write 
           STATUS      current
           DESCRIPTION
              "The Name for the Region's configuration. By Default 
               Region Name will be equal to the Bridge Mac Address."
           ::= { mstConfigurationIdentification 1 } 
        
        mstiRevisionLevel OBJECT-TYPE
           SYNTAX      Integer32 (0..65535)
           MAX-ACCESS  read-write 
           STATUS      current
           DESCRIPTION
              "Version of the MST Region."
           ::= { mstConfigurationIdentification 2 }
           
        -- -----------------------------------------------------------------
        -- Future Mst VlanId to Instance Mapping Table : CIST             
        -- -----------------------------------------------------------------
        mstCistVlanMapped OBJECT-TYPE
            SYNTAX     OCTET STRING (SIZE (0..128))
            MAX-ACCESS read-only
            STATUS     current
            DESCRIPTION
                    "A string of octets containing one bit per VLAN. The
                    first octet corresponds to VLANs with VlanIndex values
                    1 through 8; the second octet to VLANs 9 through
                    16 etc.  The most significant bit of each octet
                    corresponds to the lowest VlanIndex value in that octet.
        
                    For each VLAN that is mapped to this MSTP instance,
                    the bit corresponding to that VLAN is set to '1'."
            ::= { mstConfigurationIdentification 3 }
        
        mstCistVlanMapped2k OBJECT-TYPE
            SYNTAX     OCTET STRING (SIZE (0..128))
            MAX-ACCESS read-only
            STATUS     current
            DESCRIPTION
                    "A string of octets containing one bit per VLAN for
                    VLANS with VlanIndex values 1024 through 2047. The
                    first octet corresponds to VLANs with VlanIndex values
                    1024 through 1031; the second octet to VLANs 1032
                    through 1039 etc.  The most significant bit of each
                    octet corresponds to the lowest VlanIndex value in that
                    octet.
        
                    For each VLAN that is mapped to this MSTP instance,
                    the bit corresponding to that VLAN is set to '1'.
                    
                    This object is only instantiated on devices with 
                    support for VlanIndex values up to 4095."
            ::= { mstConfigurationIdentification 4 }
        
        mstCistVlanMapped3k OBJECT-TYPE
            SYNTAX     OCTET STRING (SIZE (0..128))
            MAX-ACCESS read-only
            STATUS     current
            DESCRIPTION
                    "A string of octets containing one bit per VLAN for
                    VLANS with VlanIndex values 2048 through 3071. The
                    first octet corresponds to VLANs with VlanIndex values
                    of 2048 through 2055; the second octet to VLANs 2056
                    through 2063 etc.  The most significant bit of each
                    octet corresponds to the lowest VlanIndex value in that
                    octet.
        
                    For each VLAN that is mapped to this MSTP instance,
                    the bit corresponding to that VLAN is set to '1'.
        
                    This object is only instantiated on devices with 
                    support for VlanIndex values up to 4095."
            ::= { mstConfigurationIdentification 5 }
        
        mstCistVlanMapped4k OBJECT-TYPE
            SYNTAX     OCTET STRING (SIZE (0..128))
            MAX-ACCESS read-only
            STATUS     current
            DESCRIPTION
                    "A string of octets containing one bit per VLAN for
                    VLANS with VlanIndex values 3072 through 4095. The
                    first octet corresponds to VLANs with VlanIndex values
                    3072 through 3079; the second octet to VLANs 3080
                    through 3087 etc.  The most significant bit of each
                    octet corresponds to the lowest VlanIndex value in that
                    octet.
        
                    For each VLAN that is mapped to this MSTP instance,
                    the bit corresponding to that VLAN is set to '1'.
        
                    This object is only instantiated on devices with 
                    support for VlanIndex values up to 4095."
            ::= { mstConfigurationIdentification 6 }
        
        -- -----------------------------------------------------------------
        -- Future Mst VlanId to Instance Mapping Table : MSTI             
        -- -----------------------------------------------------------------        
        mstVlanMstiMappingTable OBJECT-TYPE
            SYNTAX      SEQUENCE OF MstVlanMstiMappingEntry
            MAX-ACCESS  not-accessible
            STATUS      current
            DESCRIPTION
                  "This table contains one entry for each instance of MSTP. 
        	       This table maintains context ID as one more index to 
        	       support Multiple Instances." 
            ::= { mstConfigurationIdentification 7 }
        
        mstVlanMstiMappingEntry OBJECT-TYPE
             SYNTAX      MstVlanMstiMappingEntry
             MAX-ACCESS  not-accessible
             STATUS      current
             DESCRIPTION
                 "A conceptual row containing the status of the MSTP instance."
                  INDEX  { mstInstanceIndex }
             ::= { mstVlanMstiMappingTable 1 }
        
        MstVlanMstiMappingEntry ::= 
           SEQUENCE {
               mstInstanceIndex  
                    Integer32,
               mstSetVlanList 
                    OCTET STRING,
               mstResetVlanList 
                    OCTET STRING,
               mstInstanceVlanMapped 
                    OCTET STRING,
               mstInstanceVlanMapped2k 
                    OCTET STRING,
               mstInstanceVlanMapped3k 
                    OCTET STRING,
               mstInstanceVlanMapped4k 
                    OCTET STRING
           }
        
        mstInstanceIndex OBJECT-TYPE
              SYNTAX      Integer32 (1..15)
              MAX-ACCESS  read-only
              STATUS      current
              DESCRIPTION
                  "An arbitrary integer within the range from 1 to the value of
                   Max Instance Number that uniquely identifies an instance."
              ::= { mstVlanMstiMappingEntry 1 }
        
        mstSetVlanList OBJECT-TYPE
            SYNTAX     OCTET STRING (SIZE (0..512))
            MAX-ACCESS read-write
            STATUS     current
            DESCRIPTION
           	 "A string of octets containing one bit per VLAN. The
        	  first octet corresponds to VLANs with VlanIndex values
        	  1 through 8; the second octet to VLANs 9 through
        	  16 etc.  The most significant bit of each octet
        	  corresponds to the lowest VlanIndex value in that octet.
        	  The set of vlans configured by management to map for this 
        	  Instance.  If the VlanId to Instance Mapping has to be known
              then any one of the VlanMapped object should be used.If a 
              vlan is already mapped to this Instance, it may not be mapped 
              again. This object is used only for SET operation.
              GET Operation returns null values."
            ::= { mstVlanMstiMappingEntry 2 }
        
        mstResetVlanList OBJECT-TYPE
            SYNTAX     OCTET STRING (SIZE (0..512))
            MAX-ACCESS read-write
            STATUS     current
            DESCRIPTION
           	 "A string of octets containing one bit per VLAN. The
        	  first octet corresponds to VLANs with VlanIndex values
        	  1 through 8; the second octet to VLANs 9 through
        	  16 etc.  The most significant bit of each octet
        	  corresponds to the lowest VlanIndex value in that octet.
        	  The set of vlans configured by management to unmap from this 
        	  Instance. A vlan may not be unmapped from this instance if 
        	  it is not already mapped to this Instance. This object is
              used only for SET operation.GET Operation returns null values."
            ::= { mstVlanMstiMappingEntry 3 }
        
        mstInstanceVlanMapped OBJECT-TYPE
            SYNTAX     OCTET STRING (SIZE (0..128))
            MAX-ACCESS read-only
            STATUS     current
            DESCRIPTION
                    "A string of octets containing one bit per VLAN. The
                    first octet corresponds to VLANs with VlanIndex values
                    1 through 8; the second octet to VLANs 9 through
                    16 etc.  The most significant bit of each octet
                    corresponds to the lowest VlanIndex value in that octet.
        
                    For each VLAN that is mapped to this MSTP instance,
                    the bit corresponding to that VLAN is set to '1'."
            ::= { mstVlanMstiMappingEntry 4 }
        
        mstInstanceVlanMapped2k OBJECT-TYPE
            SYNTAX     OCTET STRING (SIZE (0..128))
            MAX-ACCESS read-only
            STATUS     current
            DESCRIPTION
                    "A string of octets containing one bit per VLAN for
                    VLANS with VlanIndex values 1024 through 2047. The
                    first octet corresponds to VLANs with VlanIndex values
                    1024 through 1031; the second octet to VLANs 1032
                    through 1039 etc.  The most significant bit of each
                    octet corresponds to the lowest VlanIndex value in that
                    octet.
        
                    For each VLAN that is mapped to this MSTP instance,
                    the bit corresponding to that VLAN is set to '1'.
                    
                    This object is only instantiated on devices with 
                    support for VlanIndex values up to 4095."
            ::= { mstVlanMstiMappingEntry 5 }
        
        mstInstanceVlanMapped3k OBJECT-TYPE
            SYNTAX     OCTET STRING (SIZE (0..128))
            MAX-ACCESS read-only
            STATUS     current
            DESCRIPTION
                    "A string of octets containing one bit per VLAN for
                    VLANS with VlanIndex values 2048 through 3071. The
                    first octet corresponds to VLANs with VlanIndex values
                    of 2048 through 2055; the second octet to VLANs 2056
                    through 2063 etc.  The most significant bit of each
                    octet corresponds to the lowest VlanIndex value in that
                    octet.
        
                    For each VLAN that is mapped to this MSTP instance,
                    the bit corresponding to that VLAN is set to '1'.
        
                    This object is only instantiated on devices with 
                    support for VlanIndex values up to 4095."
            ::= { mstVlanMstiMappingEntry 6 }
        
        mstInstanceVlanMapped4k OBJECT-TYPE
            SYNTAX     OCTET STRING (SIZE (0..128))
            MAX-ACCESS read-only
            STATUS     current
            DESCRIPTION
                    "A string of octets containing one bit per VLAN for
                    VLANS with VlanIndex values 3072 through 4095. The
                    first octet corresponds to VLANs with VlanIndex values
                    3072 through 3079; the second octet to VLANs 3080
                    through 3087 etc.  The most significant bit of each
                    octet corresponds to the lowest VlanIndex value in that
                    octet.
        
                    For each VLAN that is mapped to this MSTP instance,
                    the bit corresponding to that VLAN is set to '1'.
        
                    This object is only instantiated on devices with 
                    support for VlanIndex values up to 4095."
            ::= { mstVlanMstiMappingEntry 7 }
            
        -- -----------------------------------------------------------------
        -- Mst Multiple Spanning Tree Instance Bridge Table
        -- -----------------------------------------------------------------
        stpInstance  OBJECT IDENTIFIER ::= { companySTP 4 }
        
        -- -----------------------------------------------------------------
        -- Mst Multiple Spanning Tree Instance Bridge Table : CIST
        -- -----------------------------------------------------------------
        mstCistBridgePriority OBJECT-TYPE
           SYNTAX      Integer32 (0..61440) 
           MAX-ACCESS  read-write     
           STATUS      current 
           DESCRIPTION 
              "The writable portion of the MSTI Bridge Identifier.
               comprising of the first two octets.
               The values that are set for Bridge Priority must be 
               in steps of 4096."
           DEFVAL {32768}
           ::= { stpInstance 1 }
           
        mstCistStatus OBJECT-TYPE
           SYNTAX   INTEGER { 
                        enabled(1), 
                        disabled(2) 
                    }
           MAX-ACCESS  read-only
           STATUS      current
           DESCRIPTION
              "The administrative status requested by management for the MST  
              feature. The value enabled(1) indicates that Mst should be enabled  
              in the device on all ports. The value disabled(2) indicates that 
              Mst should be disabled in the device on all ports. The object can 
              be set to enabled(1) if and only if, fsMIMstSystemControl set to start."
           ::= { stpInstance 2 }
           
        -- -----------------------------------------------------------------
        -- Mst Multiple Spanning Tree Instance Bridge Table : MSTI
        -- -----------------------------------------------------------------        
        mstMstiBridgeTable OBJECT-TYPE
           SYNTAX      SEQUENCE OF MstMstiBridgeEntry      
           MAX-ACCESS  not-accessible 
           STATUS      current 
           DESCRIPTION
              "Table containing Bridge Information specific to Spanning 
               Tree Instance. This table maintains context ID as one 
               more index to support Multiple Instances."
           ::= { stpInstance 3 } 
         
        mstMstiBridgeEntry OBJECT-TYPE
           SYNTAX      MstMstiBridgeEntry       
           MAX-ACCESS  not-accessible
           STATUS      current
           DESCRIPTION
              "Entry indicating the Bridge Information."
           INDEX { mstMstiInstanceIndex }
           ::= { mstMstiBridgeTable 1 }
        
        MstMstiBridgeEntry ::=
           SEQUENCE {
              mstMstiInstanceIndex 
                    Integer32,
              mstMstiBridgePriority 
                    Integer32,
              mstMstiStatus
                    INTEGER
           }
        
        mstMstiInstanceIndex OBJECT-TYPE
           SYNTAX      Integer32 (1..15)
           MAX-ACCESS  read-only 
           STATUS      current 
           DESCRIPTION 
              "Spanning Tree Instance to which the information belongs."
           ::= { mstMstiBridgeEntry 1 }
        
        mstMstiBridgePriority OBJECT-TYPE
           SYNTAX      Integer32 (0..61440) 
           MAX-ACCESS  read-write     
           STATUS      current 
           DESCRIPTION 
              "The writable portion of the MSTI Bridge Identifier.
               comprising of the first two octets.
               The values that are set for Bridge Priority must be 
               in steps of 4096."
           DEFVAL {32768}
           ::= { mstMstiBridgeEntry 2 }
       
        mstMstiStatus OBJECT-TYPE
           SYNTAX   INTEGER { 
                        enabled(1), 
                        disabled(2) 
                    }
           MAX-ACCESS  read-only
           STATUS      current
           DESCRIPTION
              "The administrative status requested by management for the MST  
              feature. The value enabled(1) indicates that Mst should be enabled  
              in the device on all ports. The value disabled(2) indicates that 
              Mst should be disabled in the device on all ports. The object can 
              be set to enabled(1) if and only if, fsMIMstSystemControl set to start."
           ::= { mstMstiBridgeEntry 3 }
        
        -- -----------------------------------------------------------------
        -- Mst Multiple Spanning Tree Instance Bridge Table
        -- -----------------------------------------------------------------
        stpInstancePortTable  OBJECT IDENTIFIER ::= { companySTP 5 }
        
        -- -----------------------------------------------------------------
        -- Mst Multiple Spanning Tree Instance Port Table : CIST
        -- -----------------------------------------------------------------
        mstCistPortTable OBJECT-TYPE
            SYNTAX      SEQUENCE OF MstCistPortEntry              
            MAX-ACCESS  not-accessible
            STATUS      current
            DESCRIPTION
                  "This table contains Common Spanning Tree Port
                   Information."
             ::= { stpInstancePortTable 1 }
        
        mstCistPortEntry OBJECT-TYPE
              SYNTAX      MstCistPortEntry               
              MAX-ACCESS  not-accessible
              STATUS      current
              DESCRIPTION
                  "A list of information maintained by every port for 
                  Common Spanning tree."
              INDEX  { mstCistPort }
              ::= { mstCistPortTable 1 }
        
        MstCistPortEntry ::= 
           SEQUENCE {
               mstCistPort  
                    Integer32,
               mstCistPortDesignatedBridge 
                    BridgeId,
               mstCistPortAdminPathCost 
                    Integer32,
               mstCistPortPathCost 
                    Integer32,
               mstCistPortPriority 
                    Integer32,
               mstCistForcePortState 
                    INTEGER,
               mstCistCurrentPortRole  
                    INTEGER
        }
        
        mstCistPort OBJECT-TYPE
              SYNTAX      Integer32 (1..65535)
              MAX-ACCESS  not-accessible
              STATUS      current
              DESCRIPTION
                  "The Port number of the port for which this entry contains   
                   spanning tree information."                                      
              ::= { mstCistPortEntry 1 }
        
        mstCistPortDesignatedBridge OBJECT-TYPE
              SYNTAX      BridgeId                 
              MAX-ACCESS  read-only            
              STATUS      current
              DESCRIPTION
                  "The unique Bridge Identifier of the bridge which this port  
                   considers to be the Designated Bridge for the port's segment."   
              ::= { mstCistPortEntry 2 }
        
        mstCistPortAdminPathCost OBJECT-TYPE
              SYNTAX      Integer32 (0..200000000)
              MAX-ACCESS  read-write           
              STATUS      current
              DESCRIPTION
                  "The contribution of this port to the path cost of
                   paths towards the MSTI Root which include this port."
              ::= { mstCistPortEntry 3 }
        
        mstCistPortPathCost OBJECT-TYPE
              SYNTAX      Integer32 (1..200000000)
              MAX-ACCESS  read-write           
              STATUS      current
              DESCRIPTION
                  "The contribution of this port to the path cost of
                   paths towards the MSTI Root which include this port."
              ::= { mstCistPortEntry 4 }
        
        mstCistPortPriority OBJECT-TYPE
              SYNTAX      Integer32 (0..240)
              MAX-ACCESS  read-write           
              STATUS      current
              DESCRIPTION
                  "The four most significant bits of the Port Identifier 
                  for a given Spanning Tree instance can be modified 
                  independently for each Spanning Tree instance 
                  supported by the Bridge. The values that are set for Port 
                  Priority must be in steps of 16."
            DEFVAL {128}
              ::= { mstCistPortEntry 5 }
        
        mstCistForcePortState OBJECT-TYPE
              SYNTAX      INTEGER {
                           disabled(0),
                           enabled(1)
                          }
              MAX-ACCESS  read-only           
              STATUS      current
              DESCRIPTION
                  "Current state of the Port which can be changed to either 
                   Disabled or Enabled for the specific spanning tree   
                   instance. This object can be set to enabled only if the 
                   'fsMIMstCistForcePortState' is set to 'enabled' for this port"                                            
              ::= { mstCistPortEntry 6 }
        
        mstCistCurrentPortRole OBJECT-TYPE
              SYNTAX      INTEGER {              
                           disabled(0),
                           alternate(1),
                           backup(2),
                           root(3),
                           designated(4),
                           master(5)
                          }
              MAX-ACCESS  read-only        
              STATUS      current
              DESCRIPTION
                  "Current Port Role of the port for this spanning 
                  tree instance."                                      
              ::= { mstCistPortEntry 7 }
          
        -- -----------------------------------------------------------------
        -- Mst Multiple Spanning Tree Instance Port Table : MSTI
        -- -----------------------------------------------------------------
        mstMstiPortTable OBJECT-TYPE
            SYNTAX      SEQUENCE OF MstMstiPortEntry              
            MAX-ACCESS  not-accessible
            STATUS      current
            DESCRIPTION
                  "This table contains Spanning Tree Instance Specific Port
                   Information."
             ::= { stpInstancePortTable 2 }
        
        mstMstiPortEntry OBJECT-TYPE
              SYNTAX      MstMstiPortEntry               
              MAX-ACCESS  not-accessible
              STATUS      current
              DESCRIPTION
                  "A list of information maintained by every port for each 
                   and every spanning tree instance."
              INDEX  { mstMstiPort, mstInstanceIndex }
              ::= { mstMstiPortTable 1 }
        
        MstMstiPortEntry ::= 
           SEQUENCE {
               mstMstiPort  
                    Integer32,
               mstMstiPortDesignatedBridge 
                    BridgeId,
               mstMstiPortAdminPathCost 
                    Integer32,
               mstMstiPortPathCost 
                    Integer32,
               mstMstiPortPriority 
                    Integer32,
               mstMstiForcePortState 
                    INTEGER,
               mstMstiCurrentPortRole  
                    INTEGER
        }
        
        mstMstiPort OBJECT-TYPE
              SYNTAX      Integer32 (1..65535)
              MAX-ACCESS  not-accessible
              STATUS      current
              DESCRIPTION
                  "The Port number of the port for which this entry contains   
                   spanning tree information."                                      
              ::= { mstMstiPortEntry 1 }
              
        mstMstiPortDesignatedBridge OBJECT-TYPE
              SYNTAX      BridgeId                 
              MAX-ACCESS  read-only            
              STATUS      current
              DESCRIPTION
                  "The unique Bridge Identifier of the bridge which this port  
                   considers to be the Designated Bridge for the port's segment."   
              ::= { mstMstiPortEntry 2 }
        
        mstMstiPortAdminPathCost OBJECT-TYPE
              SYNTAX      Integer32 (0..200000000)
              MAX-ACCESS  read-write           
              STATUS      current
              DESCRIPTION
                  "The contribution of this port to the path cost of
                   paths towards the MSTI Root which include this port."
              ::= { mstMstiPortEntry 3 }
        
        mstMstiPortPathCost OBJECT-TYPE
              SYNTAX      Integer32 (1..200000000)
              MAX-ACCESS  read-write           
              STATUS      current
              DESCRIPTION
                  "The contribution of this port to the path cost of
                   paths towards the MSTI Root which include this port."
              ::= { mstMstiPortEntry 4 }
        
        mstMstiPortPriority OBJECT-TYPE
              SYNTAX      Integer32 (0..240)
              MAX-ACCESS  read-write           
              STATUS      current
              DESCRIPTION
                  "The four most significant bits of the Port Identifier 
                  for a given Spanning Tree instance can be modified 
                  independently for each Spanning Tree instance 
                  supported by the Bridge. The values that are set for Port 
                  Priority must be in steps of 16."
            DEFVAL {128}
              ::= { mstMstiPortEntry 5 }
        
        mstMstiForcePortState OBJECT-TYPE
              SYNTAX      INTEGER {
                           disabled(0),
                           enabled(1)
                          }
              MAX-ACCESS  read-only           
              STATUS      current
              DESCRIPTION
                  "Current state of the Port which can be changed to either 
                   Disabled or Enabled for the specific spanning tree   
                   instance. This object can be set to enabled only if the 
                   'fsMIMstCistForcePortState' is set to 'enabled' for this port"                                            
              ::= { mstMstiPortEntry 6 }
        
        mstMstiCurrentPortRole OBJECT-TYPE
              SYNTAX      INTEGER {              
                           disabled(0),
                           alternate(1),
                           backup(2),
                           root(3),
                           designated(4),
                           master(5)
                          }
              MAX-ACCESS  read-only        
              STATUS      current
              DESCRIPTION
                  "Current Port Role of the port for this spanning 
                  tree instance."                                      
              ::= { mstMstiPortEntry 7 }
        

    -- ------------------------------------------------------------------
    -- The Static Multicast Group
    -- ------------------------------------------------------------------

      staticMcastTable OBJECT-TYPE
            SYNTAX SEQUENCE OF StaticMcastEntry
            MAX-ACCESS not-accessible
            STATUS current
            DESCRIPTION
                "A list of the Static MACs"
            ::= { companyStaticMcast 1 }

        staticMcastEntry OBJECT-TYPE
            SYNTAX StaticMcastEntry
            MAX-ACCESS not-accessible
            STATUS current
            DESCRIPTION
                "A Static MAC entry containing the mac and forwarding port."
            INDEX { staticMcastVlanID, staticMcastMac, staticMcastEgressPorts, staticMcastIpAddr}
            ::= { staticMcastTable 1 }

        StaticMcastEntry ::= SEQUENCE {
            staticMcastVlanID     	 INTEGER,
            staticMcastMac           MacAddress,
            staticMcastEgressPorts   PortList,
            staticMcastIpAddr        IpAddress,
            staticMcastStatus        RowStatus
        }

        staticMcastVlanID OBJECT-TYPE
            SYNTAX INTEGER
            MAX-ACCESS read-only
            STATUS current
            DESCRIPTION
                "The VLAN ID of the static MAC entry."
            ::= { staticMcastEntry 1 }

        staticMcastMac OBJECT-TYPE
           SYNTAX MacAddress
           MAX-ACCESS read-only
           STATUS current
           DESCRIPTION
               "The MAC address associated of the static MAC entry."
           ::= { staticMcastEntry 2 }

        staticMcastEgressPorts OBJECT-TYPE
            SYNTAX      PortList
            MAX-ACCESS  read-only
            STATUS      current
            DESCRIPTION
                "The set of ports to which frames received from a
                specific port and destined for a specific Multicast or
                Broadcast MAC address must be forwarded, regardless of
                any dynamic information e.g. from GMRP.  A port may not
                be added in this set if it is already a member of the
                set of ports in dot1qStaticMulticastForbiddenEgressPorts.
                The default value of this object is a string of ones of
                appropriate length."
            REFERENCE
                "IEEE 802.1Q/D11 Section 12.7.7.3, 11.2.3.2.3"
            ::= { staticMcastEntry 3 }

        staticMcastIpAddr  OBJECT-TYPE
           SYNTAX      IpAddress
           MAX-ACCESS  read-only
           STATUS      current
           DESCRIPTION 
              "Static Multicast IP Address."
           ::= { staticMcastEntry 4 }

        staticMcastStatus OBJECT-TYPE
            SYNTAX     RowStatus
            MAX-ACCESS read-write
            STATUS     current
            DESCRIPTION
                "The status of an entry in the Static Mcast Table.  Only a subset
                 of the rowstatus variables (active, createAndGo, destroy) 
                 are available."
            ::= { staticMcastEntry 5 }


  		-- ----------------------------------------------------------
		-- The 802.1Q VLAN Groups
		-- ----------------------------------------------------------      		

        dot1qVlanManagementOnOff OBJECT-TYPE
            SYNTAX INTEGER {
                   enabled(1),
                   disabled(2)
            }
            MAX-ACCESS read-write
            STATUS current
            DESCRIPTION
                "Enable/Disable management VLAN mechanism."
            ::= { companyDot1qVlanGroup 2 }

        dot1qVlanManagementid OBJECT-TYPE
            SYNTAX INTEGER
            MAX-ACCESS read-write
            STATUS current
            DESCRIPTION
                "The management VLAN ID, which will allow to forward packets of that VLAN to CPU."
            DEFVAL { 1 }
            ::= { companyDot1qVlanGroup 3 }

        dot1qVlanAsyOnOff OBJECT-TYPE
            SYNTAX INTEGER {
                   enabled(1),
                   disabled(2)
            }
            MAX-ACCESS read-write
            STATUS current
            DESCRIPTION
                "Enable/Disable IEEE 802.1Q Asymmetric VLAN"
            ::= { companyDot1qVlanGroup  5 }
            
        -- -------------------------------------------------------------
        -- The VLAN Database
        -- -------------------------------------------------------------
        
        dot1qVlanTable OBJECT-TYPE
            SYNTAX      SEQUENCE OF Dot1qVlanEntry
            MAX-ACCESS  not-accessible
            STATUS      current
            DESCRIPTION
                "A table containing static configuration information for
                each VLAN configured into the device by (local or
                network) management.  All entries are permanent and will
                be restored after the device is reset."
            ::= { companyDot1qVlanGroup 6 }
        
        dot1qVlanEntry OBJECT-TYPE
            SYNTAX      Dot1qVlanEntry
            MAX-ACCESS  not-accessible
            STATUS      current
            DESCRIPTION
                "Information for a VLAN configured into the
                device by (local or network) management."
            INDEX   { dot1qVlanName }
            ::= { dot1qVlanTable 1 }
        
        Dot1qVlanEntry ::=
            SEQUENCE {
                dot1qVlanName
                    SnmpAdminString,
                dot1qVlanEgressPorts
                    PortList,                  
                dot1qVlanForbiddenPorts
                    PortList,                                       
                dot1qVlanUntaggedPorts
                    PortList, 
                dot1qVlanAdvertisementStatus
                    INTEGER,
                dot1qVlanRowStatus
                    RowStatus
            }
        
        dot1qVlanName OBJECT-TYPE
            SYNTAX      SnmpAdminString (SIZE (0..20))
            MAX-ACCESS  read-create
            STATUS      current
            DESCRIPTION
                "An administratively assigned string, which may be used
                to identify the VLAN."
            REFERENCE
                "IEEE 802.1Q/D11 Section 12.10.2.1"
            ::= { dot1qVlanEntry 1 }
        
        dot1qVlanEgressPorts OBJECT-TYPE
            SYNTAX      PortList
            MAX-ACCESS  read-create
            STATUS      current
            DESCRIPTION
                "The set of ports which are permanently assigned to the
                egress list for this VLAN by management.  Changes to a
                bit in this object affect the per-port per-VLAN
                Registrar control for Registration Fixed for the
                relevant GVRP state machine on each port.  A port may
                not be added in this set if it is already a member of
                the set of ports in dot1qVlanForbiddenEgressPorts.  The
                default value of this object is a string of zeros of
                appropriate length, indicating not fixed."
            REFERENCE
                "IEEE 802.1Q/D11 Section 12.7.7.3, 11.2.3.2.3"
            ::= { dot1qVlanEntry 2 } 
                    
        dot1qVlanForbiddenPorts OBJECT-TYPE
            SYNTAX      PortList
            MAX-ACCESS  read-write
            STATUS      current
            DESCRIPTION
                "The set of ports which are prohibited by management
                from being included in the egress list for this VLAN.
                Changes to this object that cause a port to be included
                or excluded affect the per-port per-VLAN Registrar
                control for Registration Forbidden for the relevant GVRP
                state machine on each port.  A port may not be added in
                this set if it is already a member of the set of ports
                in dot1qVlanEgressPorts.  The default value of
                this object is a string of zeros of appropriate length,
                excluding all ports from the forbidden set."
            REFERENCE
                "IEEE 802.1Q/D11 Section 12.7.7.3, 11.2.3.2.3"
            ::= { dot1qVlanEntry 3 }      
        
        dot1qVlanUntaggedPorts OBJECT-TYPE
            SYNTAX      PortList
            MAX-ACCESS  read-create
            STATUS      current
            DESCRIPTION
                "The set of ports which should transmit egress packets
                for this VLAN as untagged.  The default value of this
                object for the default VLAN (dot1qVlanIndex = 1) is a string
                of appropriate length including all ports.  There is no
                specified default for other VLANs.  If a device agent cannot
                support the set of ports being set then it will reject the
                set operation with an error. An example might be if a
                manager attempts to set more than one VLAN to be untagged
                on egress where the device does not support this IEEE 802.1Q
                option."
            REFERENCE
                "IEEE 802.1Q/D11 Section 12.10.2.1"
            ::= { dot1qVlanEntry 4 }
 
        dot1qVlanAdvertisementStatus OBJECT-TYPE
            SYNTAX      INTEGER {
                   enabled(1),
                   disabled(2)
            }
            MAX-ACCESS  read-create
            STATUS      current
            DESCRIPTION
                "Enable/Disable Advertisement Status of the IEEE 802.1Q VLAN."
            ::= { dot1qVlanEntry 5 }
 
        dot1qVlanRowStatus OBJECT-TYPE
            SYNTAX      RowStatus
            MAX-ACCESS  read-create
            STATUS      current
            DESCRIPTION
                "The status of a row in dot1qVlanTable. By setting this object, new
                entries can be created in dot1qVlanTable and existing entries can be
                removed from dot1qVlanTable. It can be used as specified in the SNMP
                v2 standard."
            ::= { dot1qVlanEntry 6 }
    
        -- -------------------------------------------------------------
        -- The VLAN Ungister Multicast Filter Table
        -- -------------------------------------------------------------
      dot1qVlanUngisterMCFilterTable OBJECT-TYPE 
          SYNTAX      SEQUENCE OF Dot1qVlanUngisterMCFilterEntry 
          MAX-ACCESS  not-accessible 
          STATUS      current 
          DESCRIPTION 
             "This table contains the list of ports through which 
              a router, in a particular VLAN is reachable." 
          ::= { companyDot1qVlanGroup 8 } 
 
      dot1qVlanUngisterMCFilterEntry OBJECT-TYPE 
          SYNTAX      Dot1qVlanUngisterMCFilterEntry 
          MAX-ACCESS  not-accessible 
          STATUS      current 
          DESCRIPTION 
             "A list of multicast filter mode information for each VLAN ID." 
          INDEX { dot1qVlanUngisterMCFilterVlanId } 
          ::= { dot1qVlanUngisterMCFilterTable 1 } 
 
      Dot1qVlanUngisterMCFilterEntry ::= SEQUENCE { 
          dot1qVlanUngisterMCFilterVlanId             Integer32,
          dot1qVlanUngisterMCFiltermode               INTEGER
      }
           
      dot1qVlanUngisterMCFilterVlanId OBJECT-TYPE 
           SYNTAX      Integer32 (1..4094) 
           MAX-ACCESS  read-only
           STATUS      current 
           DESCRIPTION 
              "Per Vlan to configure multicast filtering function." 
           ::= { dot1qVlanUngisterMCFilterEntry 1 } 
 
      dot1qVlanUngisterMCFiltermode OBJECT-TYPE 
           SYNTAX      INTEGER {forwardall(2), filter(1), forward(0) } 
           MAX-ACCESS  read-write
           STATUS      current 
           DESCRIPTION 
               "Filter unknown multicast frames or normal operation(i.e. forwarding)"
           ::= { dot1qVlanUngisterMCFilterEntry 2 } 
                                              

      dot1qVlanPVIDAutoAssignOnOff OBJECT-TYPE
            SYNTAX INTEGER {
                   enabled(1),
                   disabled(2)
            }
            MAX-ACCESS read-write
            STATUS current
            DESCRIPTION
                "Enable/Disable VLAN PVID auto assignment"
            ::= { companyDot1qVlanGroup  9 }
            

  		-- ----------------------------------------------------------
		-- The GVRP Groups
		-- ----------------------------------------------------------

        gvrpGVRPGlobalSettingsOnOff OBJECT-TYPE
            SYNTAX      INTEGER { enabled(1), disabled(2) }
            MAX-ACCESS read-write
            STATUS current
            DESCRIPTION
                "Enable/Disable GVRP mechanism."
            ::= { companyGVRPGroup 1 }

        gvrpSettingsJoinTime OBJECT-TYPE
            SYNTAX       INTEGER (100..100000)
            MAX-ACCESS read-write
            STATUS current
            DESCRIPTION
            "The Join Time value assigned to this Join Time field.
            This 16-bit value is read-write."
            ::= { companyGVRPGroup 2 }

        gvrpSettingsLeaveTime OBJECT-TYPE
            SYNTAX       INTEGER (100..100000)
            MAX-ACCESS read-write
            STATUS current
            DESCRIPTION
            "The Leave Time value assigned to this Leave Time field.
            This 16-bit value is read-write."
            ::= { companyGVRPGroup 3 }

        gvrpSettingsLeaveAllTime OBJECT-TYPE
            SYNTAX       INTEGER (100..100000)
            MAX-ACCESS read-write
            STATUS current
            DESCRIPTION
            "The Leave-All Time value assigned to this Leave-All Time field.
            This 16-bit value is read-write."
            ::= { companyGVRPGroup 4 }



        -- GRVP Port Setting Table
        --

        gvrpSettingsTable OBJECT-TYPE
            SYNTAX      SEQUENCE OF GvrpSettingsEntry
            MAX-ACCESS  not-accessible
            STATUS      current
            DESCRIPTION
                "A table containing static configuration information for
                each GVRP configured into the device by (local or
                network) management.  All entries are permanent and will
                be restored after the device is reset."
            ::= { companyGVRPGroup 5 }

        gvrpSettingsEntry OBJECT-TYPE
            SYNTAX      GvrpSettingsEntry
            MAX-ACCESS  not-accessible
            STATUS      current
            DESCRIPTION
                "Information for a GVRP configured into the
                device by (local or network) management."
            INDEX   { gvrpSettingsPortControlIndex }
            ::= { gvrpSettingsTable 1 }

        GvrpSettingsEntry ::=
          SEQUENCE {
            gvrpSettingsPortControlIndex
                InterfaceIndex,
            gvrpSettingsPVID
                INTEGER,
            gvrpSettingsGVRPState
                INTEGER,
            gvrpSettingsIngressChecking
                INTEGER,
            gvrpSettingsAcceptableFrameType
                INTEGER
        }

        gvrpSettingsPortControlIndex OBJECT-TYPE
          SYNTAX       InterfaceIndex
          MAX-ACCESS   read-only
                STATUS       current
                DESCRIPTION
              "The index of the port."
          ::= { gvrpSettingsEntry 1 }

        gvrpSettingsPVID OBJECT-TYPE
          SYNTAX       INTEGER (1..4094)
          MAX-ACCESS   read-write
          STATUS       current
          DESCRIPTION
            "The PVID value assigned to this Aggregation Port.
            This 16-bit value is read-write."
          ::= { gvrpSettingsEntry 2 }

        gvrpSettingsGVRPState OBJECT-TYPE
            SYNTAX      INTEGER { enabled(1), disabled(2) }

          MAX-ACCESS   read-write
          STATUS       current
          DESCRIPTION
            "Enable/Disable GVRP State to this Aggregation Port."
          ::= { gvrpSettingsEntry 3 }

        gvrpSettingsIngressChecking OBJECT-TYPE
            SYNTAX      INTEGER { enabled(1), disabled(2) }

          MAX-ACCESS   read-write
          STATUS       current
          DESCRIPTION
            "Enable/Disable Ingress Checking mechanism of GVRP to this Aggregation Port."
          ::= { gvrpSettingsEntry 4 }

        gvrpSettingsAcceptableFrameType OBJECT-TYPE
          SYNTAX       INTEGER {
                   allFrames(1),
                   taggedOnly(2)
            }
          MAX-ACCESS   read-write
          STATUS       current
          DESCRIPTION
            "Chose types All Frames/Tagged to this Aggregation Port."
          ::= { gvrpSettingsEntry 5 }

        -- ----------------------------------------------------------
		-- The DHCP/BOOTP Relay
		-- ----------------------------------------------------------
  dhcpBOOTPRelayControl                   OBJECT IDENTIFIER ::= { companyDHCPRelay 1 }
  dhcpBOOTPRelayManagement                OBJECT IDENTIFIER ::= { companyDHCPRelay 2 }
  dhcpBOOTPRelayManagementOption82        OBJECT IDENTIFIER ::= { dhcpBOOTPRelayManagement 2 }
        
		-- The DHCP/BOOTP Relay Control
        
            
            dhcpBOOTPRelayState OBJECT-TYPE
                SYNTAX  INTEGER {
                    enabled(1),
                    disabled(2)
                }
                MAX-ACCESS  read-write
                STATUS  current
                DESCRIPTION
                    "This object indicates DHCP relay function is enabled or disabled."
            ::= { dhcpBOOTPRelayControl 1 }

            dhcpBOOTPRelayHopCount OBJECT-TYPE
                SYNTAX  INTEGER (1..16)
                MAX-ACCESS  read-write
                STATUS  current
                DESCRIPTION
                    "This object indicates the maximum number of router hops that the BOOTP packets can cross."
            ::= { dhcpBOOTPRelayControl 2 }

            dhcpBOOTPRelayTimeThreshold OBJECT-TYPE
                SYNTAX  INTEGER (0..65535)
                MAX-ACCESS  read-write
                STATUS  current
                DESCRIPTION
                    "This object indicates the minimum time in seconds within which the switch must relay the DHCP request.
                    If this time is exceeded, the switch will drop the DHCP packet."
            ::= { dhcpBOOTPRelayControl 3 }

            dhcpBOOTPRelayEnablePortlist OBJECT-TYPE 
               SYNTAX      PortList
               MAX-ACCESS  read-write 
               STATUS      current 
               DESCRIPTION 
                   "This object indicates DHCP relay function is enabled or disabled by portlist."
               ::= { dhcpBOOTPRelayControl 4 }

            dhcpRelayVlanTable OBJECT-TYPE
                SYNTAX  SEQUENCE OF DHCPRelayVlanSettings
                MAX-ACCESS  not-accessible
                STATUS  current
                DESCRIPTION
                    "This table indicates the IP address as a destination to forward (relay) DHCP packets to."
            ::= { dhcpBOOTPRelayControl 5 }

            dhcpRelayVlanTableEntry OBJECT-TYPE
                SYNTAX  DHCPRelayVlanSettings
                MAX-ACCESS  not-accessible
                STATUS  current
                DESCRIPTION
                    "A list of information indicates the IP address as a destination to forward (relay) DHCP packets to."
                INDEX  { dhcpRelayVlanSettingsVLANID }
            ::= { dhcpRelayVlanTable 1 }

            DHCPRelayVlanSettings ::=
                SEQUENCE {
                    dhcpRelayVlanSettingsVLANID
                        INTEGER,
                    dhcpRelayVlanSettingsState
                        INTEGER
                }

	        dhcpRelayVlanSettingsVLANID OBJECT-TYPE
                SYNTAX  INTEGER (1..4094)
                MAX-ACCESS  read-only
                STATUS  current
                DESCRIPTION
                    "This object displays the current VLAN ID of the device."
            ::= { dhcpRelayVlanTableEntry 1 }

            dhcpRelayVlanSettingsState OBJECT-TYPE
                SYNTAX  INTEGER {
                    enabled(1),
                    disabled(2)
                }
                MAX-ACCESS  read-write
                STATUS  current
                DESCRIPTION
                    "This object indicates DHCP relay function of VLAN is enabled or disabled."
            ::= { dhcpRelayVlanTableEntry 2 }

		-- The DHCP/BOOTP Relay Management
		-- The DHCP/BOOTP Relay Interface Settings Table

            dhcpBOOTPRelayInterfaceSettingsTable OBJECT-TYPE
                SYNTAX  SEQUENCE OF DHCPBOOTPRelayInterfaceSettings
                MAX-ACCESS  not-accessible
                STATUS  current
                DESCRIPTION
                    "This table indicates the IP address as a destination to forward (relay) DHCP packets to."
            ::= { dhcpBOOTPRelayManagement 1 }

            dhcpBOOTPRelayInterfaceSettingsEntry OBJECT-TYPE
                SYNTAX  DHCPBOOTPRelayInterfaceSettings
                MAX-ACCESS  not-accessible
                STATUS  current
                DESCRIPTION
                    "A list of information indicates the IP address as a destination to forward (relay) DHCP packets to."
                INDEX  { dhcpBOOTPRelayInterface,  dhcpBOOTPRelayServerIP}
            ::= { dhcpBOOTPRelayInterfaceSettingsTable 1 }

            DHCPBOOTPRelayInterfaceSettings ::=
                SEQUENCE {
                    dhcpBOOTPRelayInterface
                        DisplayString,
                    dhcpBOOTPRelayServerIP
                        IpAddress,
                    dhcpBOOTPRelayInterfaceSettingsRowStatus
                        RowStatus
                }

            dhcpBOOTPRelayInterface OBJECT-TYPE
                SYNTAX  DisplayString (SIZE(0..12))
                MAX-ACCESS  read-only
                STATUS  current
                DESCRIPTION
                    "This object indicates the name of the IP interface."
            ::= { dhcpBOOTPRelayInterfaceSettingsEntry 1 }

            dhcpBOOTPRelayServerIP OBJECT-TYPE
                SYNTAX IpAddress
                MAX-ACCESS  read-only
                STATUS current
                DESCRIPTION
                    "This object indicates the DHCP server IP address."
            ::= { dhcpBOOTPRelayInterfaceSettingsEntry 2 }

            dhcpBOOTPRelayInterfaceSettingsRowStatus OBJECT-TYPE
                SYNTAX  RowStatus
                MAX-ACCESS  read-create
                STATUS  current
                DESCRIPTION
                    "This object indicates the status of this entry."
            ::= { dhcpBOOTPRelayInterfaceSettingsEntry 3 }

		-- The DHCP/BOOTP Relay Management
		-- The DHCP/BOOTP Relay Option82

            dhcpBOOTPRelayOption82State OBJECT-TYPE
                SYNTAX  INTEGER {
                    enabled(1),
                    disabled(2)
                }
                MAX-ACCESS  read-write
                STATUS  current
                DESCRIPTION
                    "This object indicates DHCP relay option 82 function is enabled or disabled."
            ::= { dhcpBOOTPRelayManagementOption82 1 }

            dhcpBOOTPRelayOption82CheckState OBJECT-TYPE
                SYNTAX  INTEGER {
                    enabled(1),
                    disabled(2)
                }
                MAX-ACCESS  read-write
                STATUS  current
                DESCRIPTION
                    "This object indicates DHCP relay option 82 Check function is enabled or disabled."
            ::= { dhcpBOOTPRelayManagementOption82 2 }

            dhcpBOOTPRelayOption82Policy OBJECT-TYPE
                SYNTAX  INTEGER {
                    replace(1),
                    drop(2),
                    keep(3)
                }
                MAX-ACCESS  read-write
                STATUS  current
                DESCRIPTION
                    "This object indicates DHCP relay option 82 policy."
            ::= { dhcpBOOTPRelayManagementOption82 3 }

	        dhcpBOOTPRelayOption82RemoteIDType OBJECT-TYPE
                SYNTAX  INTEGER {
                    default(1),
                    userdefined(2),
                    userdefinedhex(3)
                }
                MAX-ACCESS  read-write
                STATUS  current
                DESCRIPTION
                    "This object indicates the type of remote ID.
                    If the type is default, the remote ID will be the MAC address of the device, otherwise,
                    the remote ID can be defined by writing to the swDHCPRelayOption82RemoteID object."
            ::= { dhcpBOOTPRelayManagementOption82 4 }

	        dhcpBOOTPRelayOption82RemoteID OBJECT-TYPE
                SYNTAX  DisplayString
                MAX-ACCESS  read-write
                STATUS  current
                DESCRIPTION
                    "This object displays the current remote ID of the device.
                    If swDHCPRelayOption82RemoteIDType is set to default, the value will be the MAC address of the device,
                    and this object cannot be modified.
                    If swDHCPRelayOption82RemoteIDType is set to user-defined or user-defined-hex, a new value can be written to this object."
            ::= { dhcpBOOTPRelayManagementOption82 5 }

            
            
	        dhcpBOOTPRelayOption82CircuitIDType OBJECT-TYPE
                SYNTAX  INTEGER {
                    default(1),
                    userdefined(2),
                    userdefinedhex(3)
                }
                MAX-ACCESS  read-write
                STATUS  current
                DESCRIPTION
                    "This object indicates the type of remote ID.
                    If the type is default, the circuit ID will be blank, otherwise,
                    the circuit ID can be defined by writing to the dhcpBOOTPRelayOption82CircuitID object."
            ::= { dhcpBOOTPRelayManagementOption82 7 }

	        dhcpBOOTPRelayOption82CircuitID OBJECT-TYPE
                SYNTAX  DisplayString
                MAX-ACCESS  read-write
                STATUS  current
                DESCRIPTION
                    "This object displays the current remote ID of the device.
                    If dhcpBOOTPRelayOption82CircuitIDType is set to default, the value will be the MAC address of the device,
                    and this object cannot be modified.
                    If dhcpBOOTPRelayOption82CircuitIDType is set to user-defined or user-defined-hex, a new value can be written to this object."
            ::= { dhcpBOOTPRelayManagementOption82 8 }
  		-- ----------------------------------------------------------
		-- The DHCP LocalRelay
		-- ----------------------------------------------------------
		-- The DHCP Local Relay Table
            dhcpLocalRelayGlobalState OBJECT-TYPE
                SYNTAX  INTEGER {
                    enabled(1),
                    disabled(2)
                }
                MAX-ACCESS  read-write
                STATUS  current
                DESCRIPTION
                    "This object indicates DHCP local relay function of VLAN is enabled or disabled."
            ::= { companyDHCPLocalRelay 1 }

            dhcpLocalRelayTable OBJECT-TYPE
                SYNTAX  SEQUENCE OF DHCPLocalRelaySettings
                MAX-ACCESS  not-accessible
                STATUS  current
                DESCRIPTION
                    "This table indicates the IP address as a destination to forward (local relay) DHCP packets to."
            ::= { companyDHCPLocalRelay 2 }

            dhcpLocalRelayTableEntry OBJECT-TYPE
                SYNTAX  DHCPLocalRelaySettings
                MAX-ACCESS  not-accessible
                STATUS  current
                DESCRIPTION
                    "A list of information indicates the IP address as a destination to forward (local relay) DHCP packets to."
                INDEX  { dhcpLocalRelaySettingsVLANID }
            ::= { dhcpLocalRelayTable 1 }

            DHCPLocalRelaySettings ::=
                SEQUENCE {
                    dhcpLocalRelaySettingsVLANID
                        INTEGER,
                    dhcpLocalRelaySettingsState
                        INTEGER
                }

	        dhcpLocalRelaySettingsVLANID OBJECT-TYPE
                SYNTAX  INTEGER (1..4094)
                MAX-ACCESS  read-only
                STATUS  current
                DESCRIPTION
                    "This object displays the current VLAN ID of the device."
            ::= { dhcpLocalRelayTableEntry 1 }

            dhcpLocalRelaySettingsState OBJECT-TYPE
                SYNTAX  INTEGER {
                    enabled(1),
                    disabled(2)
                }
                MAX-ACCESS  read-write
                STATUS  current
                DESCRIPTION
                    "This object indicates DHCP local relay function of VLAN is enabled or disabled."
            ::= { dhcpLocalRelayTableEntry 2 }
            
            dhcpLocalRelayEnablePortlist OBJECT-TYPE 
               SYNTAX      PortList
               MAX-ACCESS  read-write 
               STATUS      current 
               DESCRIPTION 
                   "This object indicates DHCP local relay function is enabled or disabled by portlist."
               ::= { companyDHCPLocalRelay 3 }
    -- ---------------------------------------------------------------------
    -- LA Function
    -- ---------------------------------------------------------------------
          
      laSystem                OBJECT IDENTIFIER ::= { companyLA 1 }
      laPortControl           OBJECT IDENTIFIER ::= { companyLA 2 }

    -- -------------------------------------------------------------
    -- Textual Conventions
    -- -------------------------------------------------------------
    
     PortLaMode ::= TEXTUAL-CONVENTION
         STATUS         current
         DESCRIPTION    
           "Defines how a Port Channel does channeling.
           lacp(1)      - place the port into passive 
                           negotiation state, in which the
                           port waits for its peer to 
                           initiate negotiation.
           static(2)    - force the port to enable 
                           channeling.
           disable(3)   - channeling is disabled."
                     
     SYNTAX INTEGER {
                       lacp(1),
                       static(2),
                       disable(3)
                    }

     LacpKey ::= TEXTUAL-CONVENTION
         STATUS    current
         DESCRIPTION
                "The Actor or Partner Key value (0..65535)."
         SYNTAX Integer32 (0..65535)
 

    -- ------------------------------------------------------------------
    -- The La System Group
    -- ------------------------------------------------------------------

      laStatus OBJECT-TYPE
           SYNTAX      INTEGER { enabled(1), disabled(2) }
           MAX-ACCESS  read-write
           STATUS      current
           DESCRIPTION
               "Sets the Link Aggregation Module administrative status as 
                enabled or disabled."
           ::= { laSystem 2 }

        --
    -- Port Channel Table
    --
    
    laPortChannelTable  OBJECT-TYPE
        SYNTAX     SEQUENCE OF LaPortChannelEntry 
        MAX-ACCESS not-accessible
        STATUS     current
        DESCRIPTION
           "A Port-channel is created through ifMain table.
           After the creation of the port-channel, corresponding logical
           interface will be created in the ifMain table. 
           This Port-channel table is indexed through Key values and allows to 
           configure link selection policy and the Mac address for 
           the port-channel. All other objects in this table displays 
           the details of the port-channel."

        ::= { laSystem 3 }

    laPortChannelEntry OBJECT-TYPE
        SYNTAX     LaPortChannelEntry 
        MAX-ACCESS not-accessible
        STATUS     current
        DESCRIPTION
              "There is one entry in this table for each created
               port-channel port."

        INDEX { laPortChannelIfIndex }
        ::= { laPortChannelTable 1 }

    LaPortChannelEntry ::= 
            SEQUENCE {
              laPortChannelIfIndex                InterfaceIndex,
              laPortChannelMemberList             PortList,
              laPortChannelMode                   PortLaMode              
	      -- start CAMEO-LA-MASTER-PORT-WANTED
	      ,
              laPortChannelMasterPort             InterfaceIndex
	      -- end CAMEO-LA-MASTER-PORT-WANTED
              }

    laPortChannelIfIndex OBJECT-TYPE
        SYNTAX      InterfaceIndex
        MAX-ACCESS  read-only
        STATUS      current
        DESCRIPTION
              "The index of the port-channel(Aggregator's 
               interface index). "
        ::= { laPortChannelEntry 1 }

  	laPortChannelMemberList OBJECT-TYPE
	   SYNTAX       PortList
	   MAX-ACCESS   read-write
	   STATUS       current
	   DESCRIPTION
	       "Member Port list of the port channel. Add the ports as a 
	        aggregation member associated of a port-channel."
	   ::= { laPortChannelEntry 2 }

        
    laPortChannelMode OBJECT-TYPE
       SYNTAX       PortLaMode
       MAX-ACCESS   read-write
       STATUS       current
       DESCRIPTION
         "Current Operating Channel Mode of the port channel
                     Lacp(1)    - forcing the port to negotiate with the
                                  partner.
                     manual(2)  - force the port to enable channeling (Manual).
                     disable(3) - channeling is disabled."
        ::= { laPortChannelEntry 3 }
        
-- start CAMEO-LA-MASTER-PORT-WANTED
    laPortChannelMasterPort OBJECT-TYPE
        SYNTAX      InterfaceIndex
        MAX-ACCESS  read-write
        STATUS      current
        DESCRIPTION
              "The master port of the port-channel. "
        ::= { laPortChannelEntry 4 }
-- end CAMEO-LA-MASTER-PORT-WANTED

    -- ------------------------------------------------------------------
    -- The La Algorithm Group
    -- ------------------------------------------------------------------

      laAlgorithm OBJECT-TYPE
           SYNTAX      INTEGER { 
				sourceMAC(1), 
				destMAC(2), 
				sourceAndDestMAC(3), 
				sourceIP(4), 
				destIP(5), 
				sourceAndDestIP(6)
				}
           MAX-ACCESS  read-write
           STATUS      current
           DESCRIPTION
               "Sets the Link Aggregation load balance algorithm."
           ::= { laSystem 4 }

    --
        -- LA Port Control Table
        --          

        laPortControlTable OBJECT-TYPE
          SYNTAX      SEQUENCE OF LaPortControlEntry
          MAX-ACCESS  not-accessible
           STATUS      current
           DESCRIPTION
                      "A table that contains Link Aggregation Control
                       configuration information about every
                       Aggregation Port associated with this device.
                       A row appears in this table for each physical port."
          ::= { laPortControl 1 }


        laPortControlEntry OBJECT-TYPE
          SYNTAX      LaPortControlEntry
          MAX-ACCESS  not-accessible
          STATUS      current
          DESCRIPTION
                      "A list of Link Aggregation Control configuration
                       parameters for each Aggregation Port on this device."
          INDEX      { laPortControlIndex }
          ::= { laPortControlTable 1 }  

        LaPortControlEntry ::=
          SEQUENCE {
            laPortControlIndex
                InterfaceIndex,
            laPortActorPortPriority
                INTEGER,
            laPortActorActivity
                INTEGER,
            laPortActorTimeout
                INTEGER        
        }
        
        laPortControlIndex OBJECT-TYPE
          SYNTAX       InterfaceIndex
          MAX-ACCESS   read-only
                STATUS       current
                DESCRIPTION
              "The index of the port."
          ::= { laPortControlEntry 1 }    
        
        laPortActorPortPriority OBJECT-TYPE
          SYNTAX       INTEGER (0..65535)
          MAX-ACCESS   read-write
          STATUS       current
          DESCRIPTION
            "The priority value assigned to this Aggregation Port.
            This 16-bit value is read-write."
          ::= { laPortControlEntry 2 }  
       
        laPortActorActivity      OBJECT-TYPE 
            SYNTAX INTEGER  {
        		 active(1),
        		 passive(2)
            }
           MAX-ACCESS  read-write 
           STATUS      current 
           DESCRIPTION 
                "This object indicates LACP-Activity to this Aggregation Port. 
                LACP can be configured in one of two modes: active or passive. 
                In active mode it will always send frames along the configured links. 
                If the actor and partner are both in passive mode, they do not 
                exchange LACP packets." 
           ::= { laPortControlEntry 3 }    

        laPortActorTimeout      OBJECT-TYPE 
            SYNTAX INTEGER  {
        		 short(1),
        		 long(2)
            }
           MAX-ACCESS  read-write 
           STATUS      current 
           DESCRIPTION 
                "This object indicates LACP-Timeout to this Aggregation Port.
                short(1) - LACP Timeout 3 seconds.
                long (2) - LACP Timeout 90 seconds." 
           ::= { laPortControlEntry 4 }  

        -- ----------------------------------------------------------------
        -- The STATIC MAC group
        -- ----------------------------------------------------------------
        
        staticDisableAutoLearn OBJECT-TYPE
            SYNTAX INTEGER {
                   on(1),
                   off(2)
            }
            MAX-ACCESS read-write
            STATUS current
            DESCRIPTION
                "Set on to disable Auto Learning Excluding Uplink Port and
                 set off to enable Auto Learning."
            ::= { companyStaticMAC 1 }

        staticAutoLearningList OBJECT-TYPE
            SYNTAX PortList
            MAX-ACCESS read-write
            STATUS current
            DESCRIPTION
                "The set of the device's member ports that belong
 	            to the Static MAC auto learning enable/disable.
 	            
 	            For example, when Disable Auto Learning is enable,
 	            the octet value set up as '# 0x0F 0xFF 0xFF 0xFF' means 
 	            from port 1 to port 4 are not in auto learning state, 
 	            the other ports are in auto learning state. It can be 
 	            set up when Disable Auto Learning is enable."
            ::= { companyStaticMAC 2 }

        staticTable OBJECT-TYPE
            SYNTAX SEQUENCE OF StaticEntry
            MAX-ACCESS not-accessible
            STATUS current
            DESCRIPTION
                "A list of the Static MACs"
            ::= { companyStaticMAC 3 }

        staticEntry OBJECT-TYPE
            SYNTAX StaticEntry
            MAX-ACCESS not-accessible
            STATUS current
            DESCRIPTION
                "A Static MAC entry containing the mac and forwarding port."
            INDEX { staticVlanID, staticMac,staticPort}
            ::= { staticTable 1 }

        StaticEntry ::= SEQUENCE {
            staticVlanID     	INTEGER,
            staticMac           MacAddress,
            staticPort          INTEGER,
            staticStatus        RowStatus
        }

        staticVlanID OBJECT-TYPE
            SYNTAX INTEGER
            MAX-ACCESS read-only
            STATUS current
            DESCRIPTION
                "The VLAN ID of the static MAC entry."
            ::= { staticEntry 1 }

         staticMac OBJECT-TYPE
           SYNTAX MacAddress
           MAX-ACCESS read-only
           STATUS current
           DESCRIPTION
               "The MAC address associated of the static MAC entry."
           ::= { staticEntry 2 }

        staticPort OBJECT-TYPE
            SYNTAX INTEGER
            MAX-ACCESS read-only
            STATUS current
            DESCRIPTION
                "The forwarding port of the static MAC entry."
            ::= { staticEntry 3 }
        
        staticStatus OBJECT-TYPE
            SYNTAX     RowStatus
            MAX-ACCESS read-write
            STATUS     current
            DESCRIPTION
                "The status of an entry in the Static MAC Table.  Only a subset
                 of the rowstatus variables (active, createAndGo, destroy) 
                 are available. The trunk member port can not set up static MAC."
            ::= { staticEntry 4 }
    -- ---------------------------------------------------------------------
    -- IGMP Snooping Function
    -- ---------------------------------------------------------------------
	igsSystem       OBJECT IDENTIFIER ::= { companyIgsGroup 1 }
	igsVlan         OBJECT IDENTIFIER ::= { companyIgsGroup 3 }
    igsAccessAuth   OBJECT IDENTIFIER ::= { companyIgsGroup 5 }
-- start IGMP-SNOOPING-HOST-BASED-FAST-LEAVE
    igsHost         OBJECT IDENTIFIER ::= { companyIgsGroup 6 }
-- end IGMP-SNOOPING-HOST-BASED-FAST-LEAVE

    igsStatus OBJECT-TYPE 
          SYNTAX      INTEGER  { enabled(1), disabled(2) } 
          MAX-ACCESS  read-write 
          STATUS      current 
          DESCRIPTION 
             "Enables or disables IGMP snooping in the system.
              When set to 'enabled', the IGS module starts 
              protocol operations.
              When set to 'disabled', the IGS module stops performing 
              protocol operations."
          DEFVAL  { 2 } 
          ::= { igsSystem 1 } 
 
      igsRouterPortPurgeInterval OBJECT-TYPE 
          SYNTAX      Integer32 (60..600) 
          MAX-ACCESS  read-write 
          STATUS      current 
          DESCRIPTION 
             "This is the interval (in seconds) after which a learnt  
              router port entry will be purged. For each router port learnt, 
              this timer runs for 'RouterPortPurgeInterval' seconds.When the 
              timer expires, the learnt router port entry is purged. However 
              if control messages are received from the router before the 
              timer expiry, then the timer is restarted."
          DEFVAL  { 260 } 
          ::= { igsSystem 2 } 
 
      igsHostPortPurgeInterval OBJECT-TYPE 
          SYNTAX      Integer32 (130..153025) 
          MAX-ACCESS  read-write 
          STATUS      current 
          DESCRIPTION 
             "This is the interval (in seconds) after which a learnt  
              port entry will be purged. For each port on which report
              has been received this timer runs for 'PortPurgeInterval'
              seconds. This timer will be restarted whenever a report 
              message is received from a host on the specific port. If 
              the timer expires, then , the learnt port entry  will 
              be purged from the multicast group." 
          DEFVAL  {260} 
          ::= { igsSystem 3 } 
    igsDataDrivenLearningMaxLearnedEntryVlaue OBJECT-TYPE
        SYNTAX      INTEGER (1..1024)
		MAX-ACCESS  read-write
		STATUS      current
		DESCRIPTION 
            "The maximum data driven learning entry value."
        DEFVAL     { 64 }
        ::= { igsSystem 8 }

    igsReportToAllPort OBJECT-TYPE 
        SYNTAX      INTEGER  { enabled(1), disabled(2) } 
        MAX-ACCESS  read-write 
        STATUS      current 
        DESCRIPTION 
           "Enables or disables IGMP snooping in the system.
            When set to 'enabled', the IGS module forwards packets 
            to report to all port.
            When set to 'disabled', the IGS module forwards packets 
            to router port only."
        DEFVAL  { 2 } 
        ::= { igsSystem 9 } 
-- VLAN Based MAC Multicast Forwarding Table 
-- 
--      igsVlanMcastMacFwdTable OBJECT-TYPE 
--          SYNTAX      SEQUENCE OF IgsVlanMcastMacFwdEntry 
--          MAX-ACCESS  not-accessible 
--          STATUS      current 
--          DESCRIPTION 
--            "This table contains MAC based multicast forwarding 
--             information. This information is applicable only if
--             the 'igsVlanMcastForwardingMode' is set to 'macbased' " 
--          ::= { igsVlan 1 } 
-- 
--      igsVlanMcastMacFwdEntry OBJECT-TYPE 
--          SYNTAX      IgsVlanMcastMacFwdEntry 
--          MAX-ACCESS  not-accessible 
--          STATUS      current 
--          DESCRIPTION 
--            "This table contains VLAN ID, multicast group MAC address and the  
--             list of ports onto which the multicast data packets for group
--             should be forwarded."  
--
--          INDEX { igsVlanMcastMacFwdVlanId,
--                  igsVlanMcastMacFwdGroupAddress } 
--          ::= { igsVlanMcastMacFwdTable 1 } 
-- 
--      IgsVlanMcastMacFwdEntry ::= SEQUENCE { 
--          igsVlanMcastMacFwdVlanId           Integer32,
--          igsVlanMcastMacFwdGroupAddress     MacAddress, 
--          igsVlanMcastMacFwdPortList         PortList 
--        } 
--
--      igsVlanMcastMacFwdVlanId OBJECT-TYPE 
--           SYNTAX      Integer32 (1..4094) 
--           MAX-ACCESS  not-accessible 
--           STATUS      current 
--           DESCRIPTION 
--              "VLAN ID pertaining to the Multicast forwarding entry"  
--           ::= { igsVlanMcastMacFwdEntry 1 } 
-- 
--      igsVlanMcastMacFwdGroupAddress OBJECT-TYPE 
--           SYNTAX      MacAddress 
--           MAX-ACCESS  not-accessible 
--           STATUS      current 
--           DESCRIPTION 
--               "Multicast group MAC address." 
--           ::= { igsVlanMcastMacFwdEntry 2 } 
-- 
-- 
--      igsVlanMcastMacFwdPortList OBJECT-TYPE 
--           SYNTAX      PortList 
--           MAX-ACCESS  read-only 
--           STATUS      current 
--           DESCRIPTION 
--               "List of ports onto which the multicast data
--                packets destined for this group will be forwarded."  
--           ::= { igsVlanMcastMacFwdEntry 3 } 

-- VLAN based router table.
 
      igsVlanRouterTable OBJECT-TYPE 
          SYNTAX      SEQUENCE OF IgsVlanRouterEntry 
          MAX-ACCESS  not-accessible 
          STATUS      current 
          DESCRIPTION 
             "This table contains the list of ports through which 
              a router, in a particular VLAN is reachable." 
          ::= { igsVlan 3 } 
 
      igsVlanRouterEntry OBJECT-TYPE 
          SYNTAX      IgsVlanRouterEntry 
          MAX-ACCESS  not-accessible 
          STATUS      current 
          DESCRIPTION 
             "Contains the VLAN ID and list of ports on which 
              routers are present in the VLAN." 
          INDEX { igsVlanRouterVlanId } 
          ::= { igsVlanRouterTable 1 } 
 
      IgsVlanRouterEntry ::= SEQUENCE { 
          igsVlanRouterVlanId             Integer32,
          igsVlanRouterPortList           PortList
      }
           
      igsVlanRouterVlanId OBJECT-TYPE 
           SYNTAX      Integer32 (1..4094) 
           MAX-ACCESS  read-only 
           STATUS      current 
           DESCRIPTION 
              "VLAN ID of the ports through which router is reachable." 
           ::= { igsVlanRouterEntry 1 } 
 
      igsVlanRouterPortList OBJECT-TYPE 
           SYNTAX      PortList 
           MAX-ACCESS  read-only
           STATUS      current 
           DESCRIPTION 
               "List of ports on which routers are present. 
                These router ports are learnt through control messages 
                received from routers, and can also be configured 
                statically." 
           ::= { igsVlanRouterEntry 2 } 
 
-- VLAN based filter table 
 
      igsVlanFilterTable OBJECT-TYPE 
          SYNTAX      SEQUENCE OF IgsVlanFilterEntry 
          MAX-ACCESS  not-accessible 
          STATUS      current 
          DESCRIPTION 
             "This table contains configuration of snooping
              on specific Vlans. This Table is valid only when VLAN is  
              enabled in the system." 
          ::= { igsVlan 4 } 
 
      igsVlanFilterEntry OBJECT-TYPE 
          SYNTAX      IgsVlanFilterEntry 
          MAX-ACCESS  not-accessible 
          STATUS      current 
          DESCRIPTION 
             "Contains snooping status , version and fast leave
              configuration for a specific VLAN." 
          INDEX { igsVlanFilterVlanId } 
          ::= { igsVlanFilterTable 1 } 
 
      IgsVlanFilterEntry ::= SEQUENCE { 
          igsVlanFilterVlanId           Integer32, 
          igsVlanSnoopStatus            INTEGER, 
          igsVlanQuerier                INTEGER, 
          igsVlanCfgQuerier             INTEGER, 
          igsVlanQueryInterval          Integer32, 
          igsVlanRtrPortList            PortList
          ,igsVlanFbdRtrPortList         PortList
          , igsVlanFastLeave            INTEGER
          , igsVlanDataDrivenLearningStatus INTEGER
          , igsVlanQuerierVersionStatus INTEGER
          , igsVlanDataDrivenLearningAgeOutStatus INTEGER
         ,  igsVlanReportSuppression  INTEGER
        ,   igsVlanRobustnessValue  Integer32
        ,   igsVlanGrpQueryInterval  Integer32
        ,   igsVlanQueryMaxResponseTime  INTEGER
          } 

      igsVlanFilterVlanId OBJECT-TYPE 
           SYNTAX      Integer32 (1..4094) 
           MAX-ACCESS  read-only 
           STATUS      current 
           DESCRIPTION 
            "Index of IgsVlanFilterEntry. This object indicates the VLAN ID for which 
            the snooping configurations in IgsVlanFilterEntry is to be done." 
           ::= { igsVlanFilterEntry 1 } 
 
      igsVlanSnoopStatus OBJECT-TYPE 
           SYNTAX      INTEGER { enabled(1), disabled(2) } 
           MAX-ACCESS  read-write 
           STATUS      current 
           DESCRIPTION 
               "This object allows you to enable/disable IGS function on a specific VLAN."  
           DEFVAL  { 1 }
           ::= { igsVlanFilterEntry 2 } 

      igsVlanQuerier OBJECT-TYPE 
          SYNTAX      INTEGER  { enabled(1), disabled(2) } 
          MAX-ACCESS  read-only 
          STATUS      current 
          DESCRIPTION 
             "Indicates whether the switch is configured as a querier in the VLAN"
          DEFVAL  { 2 } 
          ::= { igsVlanFilterEntry 3 } 

      igsVlanCfgQuerier OBJECT-TYPE 
          SYNTAX      INTEGER  { enabled(1), disabled(2) } 
          MAX-ACCESS  read-write 
          STATUS      current 
          DESCRIPTION 
             "The snooping switch can be configured as a querier via this object 
              to send out IGMP general queries when IGMP routers are not present in the VLAN. 
              When set to 'enabled', the switch will generate general queries."
          DEFVAL  { 2 } 
          ::= { igsVlanFilterEntry 4 } 
      igsVlanQueryInterval OBJECT-TYPE 
          SYNTAX      Integer32 (60..600) 
          MAX-ACCESS  read-write 
          STATUS      current 
          DESCRIPTION 
             "This is the interval (in seconds) for which the switch 
              sends general queries when it is configured as a querier for 
              the VLAN. A switch should be configured as a querier for a VLAN 
              only when there is no queriers in the network."   
          DEFVAL  { 125 } 
          ::= { igsVlanFilterEntry 5 } 
      igsVlanRtrPortList OBJECT-TYPE 
           SYNTAX      PortList 
           MAX-ACCESS  read-write
           STATUS      current 
           DESCRIPTION 
               "List of ports which are configured statically as router ports"
           ::= { igsVlanFilterEntry 6 } 

      igsVlanFbdRtrPortList OBJECT-TYPE 
           SYNTAX      PortList 
           MAX-ACCESS  read-write
           STATUS      current 
           DESCRIPTION 
               "List of ports which can be configured statically as forbidden router ports."
           ::= { igsVlanFilterEntry 7 }            

      igsVlanFastLeave OBJECT-TYPE 
           SYNTAX      INTEGER { enabled(1), disabled(2) } 
           MAX-ACCESS  read-write 
           STATUS      current 
           DESCRIPTION 
               "Enables or disables fast leave for the VLAN. When it is 
                'disabled',on reception of a leave message, the switch checks
                if they are any interested receivers for the group by sending 
                a group specific query before removing the port from the 
                forwarding table. If set to 'enabled', the switch does not 
                send a group specific query and immediately removes the port
                from the forwarding table."
           DEFVAL  { 2 }
           ::= { igsVlanFilterEntry 8 }

        igsVlanDataDrivenLearningStatus OBJECT-TYPE 
            SYNTAX      INTEGER { enabled(1), disabled(2) } 
            MAX-ACCESS  read-write 
            STATUS      current 
            DESCRIPTION
                "This object allows you to enable/disable
                Data Driven Learning function on a specific VLAN."
            ::= { igsVlanFilterEntry 9 }

        igsVlanQuerierVersionStatus OBJECT-TYPE 
            SYNTAX      INTEGER { igmp-v3(3), igmp-v2(2), igmp-v1(1) } 
            MAX-ACCESS  read-write 
            STATUS      current 
            DESCRIPTION
                "This object allows you to enable/disable
                Querier Version function on a specific VLAN."
            ::= { igsVlanFilterEntry 10 }

        igsVlanDataDrivenLearningAgeOutStatus OBJECT-TYPE 
            SYNTAX      INTEGER { enabled(1), disabled(2) } 
            MAX-ACCESS  read-write 
            STATUS      current 
            DESCRIPTION
                "This object allows you to enable/disable
                Data Driven Learning Age Out State on a specific VLAN."
            ::= { igsVlanFilterEntry 11 }
        igsVlanReportSuppression OBJECT-TYPE 
            SYNTAX      INTEGER  { enabled(1), disabled(2) } 
            MAX-ACCESS  read-write 
            STATUS      current 
            DESCRIPTION 
               "Enables or disables Report suppression in the system." 
            ::= { igsVlanFilterEntry 12 } 
      igsVlanRobustnessValue OBJECT-TYPE
          SYNTAX      Integer32 (2..255)
          MAX-ACCESS  read-write
          STATUS      current
          DESCRIPTION 
	     "When the switch receives leave message on a port, it
              sends group specific query to check if there are any other 
              interested receivers for the group. This attribute defines 
              the maximum number of queries sent by the switch before deleting 
              the port from the group membership information in the forwarding 
              database. If the maximum retry count exceeds 'igsRobustnessValue', 
              then the port will be deleted from the multicast group membership
              information in the forwarding database and received leave message
              will be forwarded onto the router ports if there are no 
              interested receivers for the group." 
          DEFVAL  { 2 } 
            ::= { igsVlanFilterEntry 13 } 

      igsVlanGrpQueryInterval OBJECT-TYPE 
          SYNTAX      Integer32 (1..25) 
          MAX-ACCESS  read-write 
          STATUS      current 
          DESCRIPTION 
             "The value of this attribute defines the time period with which 
              the switch will send group specific queries on a port to check 
              if there is any intersted receivers. The switch will send 
              'igsRobustnessValue' queries before removing the port from the 
              group membership information in the forwarding database."
          DEFVAL  { 1 }
            ::= { igsVlanFilterEntry 14 } 

    igsVlanQueryMaxResponseTime OBJECT-TYPE
        SYNTAX      INTEGER (10..25)
		MAX-ACCESS  read-write
		STATUS      current
		DESCRIPTION 
        	"The maximum query response time advertised in IGMPv2 general
        	queries on this interface."
        DEFVAL     { 10 }
            ::= { igsVlanFilterEntry 15 } 
    -- VLAN Based IGMP Snooping Group 
 
      igsVlanMulticastGroupTable OBJECT-TYPE 
          SYNTAX      SEQUENCE OF IgsVlanMulticastGroupEntry 
          MAX-ACCESS  not-accessible 
          STATUS      current 
          DESCRIPTION 
            "This table contains MAC based multicast forwarding 
             information." 
          ::= { igsVlan 5 } 
 
      igsVlanMulticastGroupEntry OBJECT-TYPE 
          SYNTAX      IgsVlanMulticastGroupEntry 
          MAX-ACCESS  not-accessible 
          STATUS      current 
          DESCRIPTION 
            "This table contains VLAN ID, multicast group MAC address and the  
             list of ports onto which the multicast data packets for group
             should be forwarded."  

          INDEX { igsVlanMulticastGroupVlanId,
                  igsVlanMulticastGroupIpAddress } 
          ::= { igsVlanMulticastGroupTable 1 } 
 
      IgsVlanMulticastGroupEntry ::= SEQUENCE { 
          igsVlanMulticastGroupVlanId           Integer32,
          igsVlanMulticastGroupIpAddress        InetAddress, 
          igsVlanMulticastGroupMacAddress       MacAddress,
          igsVlanMulticastGroupPortList         PortList
        } 

      igsVlanMulticastGroupVlanId OBJECT-TYPE 
           SYNTAX      Integer32 (1..4094) 
           MAX-ACCESS  read-only 
           STATUS      current 
           DESCRIPTION 
              "VLAN ID pertaining to the Multicast forwarding entry"  
           ::= { igsVlanMulticastGroupEntry 1 } 
 
      igsVlanMulticastGroupIpAddress OBJECT-TYPE 
           SYNTAX      InetAddress
           MAX-ACCESS  read-only 
           STATUS      current 
           DESCRIPTION 
               "Multicast group IP address. This object indicates that a
                multicast group address was learned in the switch and be represented 
                as IP address format." 
           ::= { igsVlanMulticastGroupEntry 2 } 
 
 
      igsVlanMulticastGroupMacAddress OBJECT-TYPE 
           SYNTAX      MacAddress 
           MAX-ACCESS  read-only 
           STATUS      current 
           DESCRIPTION 
               "Multicast group MAC address. This object indicates that a
                multicast group address was learned in the switch and be represented 
                as MAC address format." 
           ::= { igsVlanMulticastGroupEntry 3 } 

      igsVlanMulticastGroupPortList OBJECT-TYPE 
           SYNTAX      PortList 
           MAX-ACCESS  read-only 
           STATUS      current 
           DESCRIPTION 
               "List of ports onto which the multicast data
                packets destined for this group will be forwarded."  
           ::= { igsVlanMulticastGroupEntry 4 } 

      igsAccessAuthTable OBJECT-TYPE 
          SYNTAX      SEQUENCE OF IgsAccessAuthEntry 
          MAX-ACCESS  not-accessible 
          STATUS      current 
          DESCRIPTION 
             "This table is used to manage the IGMP Authentication
              function of the switch." 
          ::= { igsAccessAuth 1 } 
 
      igsAccessAuthEntry OBJECT-TYPE 
          SYNTAX      IgsAccessAuthEntry 
          MAX-ACCESS  not-accessible 
          STATUS      current 
          DESCRIPTION 
             "Contains management entities for IGMP Authentication
              function." 
          INDEX { igsAccessAuthPortIndex } 
          ::= { igsAccessAuthTable 1 } 
 
      IgsAccessAuthEntry ::= SEQUENCE { 
          igsAccessAuthPortIndex             Integer32,
          igsAccessAuthState                 INTEGER
      }
           
      igsAccessAuthPortIndex OBJECT-TYPE 
           SYNTAX      Integer32 
           MAX-ACCESS  read-only 
           STATUS      current 
           DESCRIPTION 
              "The port index of igsAccessAuthTable which 
               indicates the port to be configured." 
           ::= { igsAccessAuthEntry 1 } 
 
      igsAccessAuthState OBJECT-TYPE 
           SYNTAX      INTEGER  { enabled(1), disabled(2) } 
           MAX-ACCESS  read-write
           STATUS      current 
           DESCRIPTION 
               "This object can be configured to set IGMP Authentication
                state to enabled/disabled on each port." 
           ::= { igsAccessAuthEntry 2 }

-- start IGMP-SNOOPING-HOST-BASED-FAST-LEAVE
    igsHostTable OBJECT-TYPE
        SYNTAX      SEQUENCE OF IgsHostEntry
        MAX-ACCESS  not-accessible
        STATUS      current
        DESCRIPTION
            "This table is used to manage
            the IGMP Host based Fast Leave function of the switch."
        ::= { igsHost 1 }
 
    igsHostEntry OBJECT-TYPE
        SYNTAX      IgsHostEntry
        MAX-ACCESS  not-accessible
        STATUS      current
        DESCRIPTION
            "Contains management entities for
            IGMP Host based fast leave function."
        INDEX {igsHostTableVLANID,
               igsHostTableGroupAddress,
               igsHostTablePort,
               igsHostTableHostIPAddress}
        ::= { igsHostTable 1 }
 
    IgsHostEntry ::= SEQUENCE {
        igsHostTableVLANID          Integer32,
        igsHostTableGroupAddress    InetAddress,
        igsHostTablePort            Integer32,
        igsHostTableHostIPAddress   InetAddress
    }

    igsHostTableVLANID OBJECT-TYPE
        SYNTAX      Integer32 (1..4094)
        MAX-ACCESS  read-only
        STATUS      current
        DESCRIPTION
            "VLAN ID of Host table entry."
        ::= { igsHostEntry 1 }
 
    igsHostTableGroupAddress OBJECT-TYPE
        SYNTAX      InetAddress
        MAX-ACCESS  read-only
        STATUS      current
        DESCRIPTION
            "Group address of Host table entry."
        ::= { igsHostEntry 2 } 
 
    igsHostTablePort OBJECT-TYPE 
        SYNTAX      Integer32 
        MAX-ACCESS  read-only 
        STATUS      current 
        DESCRIPTION 
            "Port number of Host table entry."
        ::= { igsHostEntry 3 }

    igsHostTableHostIPAddress OBJECT-TYPE 
        SYNTAX      InetAddress 
        MAX-ACCESS  read-only 
        STATUS      current 
        DESCRIPTION 
            "Host IP address of Group in Host table entry."
        ::= { igsHostEntry 4 }
-- end IGMP-SNOOPING-HOST-BASED-FAST-LEAVE
    -- ---------------------------------------------------------------------
    -- MLD Snooping Function
    -- ---------------------------------------------------------------------
	mldsSystem       OBJECT IDENTIFIER ::= { companyMldsGroup 1 }
	mldsVlan         OBJECT IDENTIFIER ::= { companyMldsGroup 3 }
	mldsHost         OBJECT IDENTIFIER ::= { companyMldsGroup 4 }

    mldsStatus OBJECT-TYPE 
          SYNTAX      INTEGER  { enabled(1), disabled(2) } 
          MAX-ACCESS  read-write 
          STATUS      current 
          DESCRIPTION 
             "Enables or disables MLD snooping in the system.
              When set to 'enabled', the MLDS module starts 
              protocol operations.
              When set to 'disabled', the MLDS module stops performing 
              protocol operations."
          DEFVAL  { 2 } 
          ::= { mldsSystem 1 } 
 
     mldsRouterPortPurgeInterval OBJECT-TYPE 
          SYNTAX      Integer32 (60..600) 
          MAX-ACCESS  read-write 
          STATUS      current 
          DESCRIPTION 
             "This is the interval (in seconds) after which a learnt  
              router port entry will be purged. For each router port learnt, 
              this timer runs for 'RouterPortPurgeInterval' seconds.When the 
              timer expires, the learnt router port entry is purged. However 
              if control messages are received from the router before the 
              timer expiry, then the timer is restarted."
          DEFVAL  { 260 } 
          ::= { mldsSystem 2 } 
 
      mldsHostPortPurgeInterval OBJECT-TYPE 
          SYNTAX      Integer32 (130..153025) 
          MAX-ACCESS  read-write 
          STATUS      current 
          DESCRIPTION 
             "This is the interval (in seconds) after which a learnt  
              port entry will be purged. For each port on which report
              has been received this timer runs for 'PortPurgeInterval'
              seconds. This timer will be restarted whenever a report 
              message is received from a host on the specific port. If 
              the timer expires, then , the learnt port entry  will 
              be purged from the multicast group." 
          DEFVAL  {260} 
          ::= { mldsSystem 3 } 
    mldsDataDrivenLearningMaxLearnedEntryVlaue OBJECT-TYPE
        SYNTAX      INTEGER (1..1024)
		MAX-ACCESS  read-write
		STATUS      current
		DESCRIPTION 
            "The maximum data driven learning entry value."
        DEFVAL     { 64 }
        ::= { mldsSystem 8 }

-- VLAN based router table.
 
      mldsVlanRouterTable OBJECT-TYPE 
          SYNTAX      SEQUENCE OF MldsVlanRouterEntry 
          MAX-ACCESS  not-accessible 
          STATUS      current 
          DESCRIPTION 
             "This table contains the list of ports through which 
              a router, in a particular VLAN is reachable." 
          ::= { mldsVlan 3 } 
 
      mldsVlanRouterEntry OBJECT-TYPE 
          SYNTAX      MldsVlanRouterEntry 
          MAX-ACCESS  not-accessible 
          STATUS      current 
          DESCRIPTION 
             "Contains the VLAN ID and list of ports on which 
              routers are present in the VLAN." 
          INDEX { mldsVlanRouterVlanId } 
          ::= { mldsVlanRouterTable 1 } 
 
      MldsVlanRouterEntry ::= SEQUENCE { 
          mldsVlanRouterVlanId             Integer32,
          mldsVlanRouterPortList           PortList
      }
           
      mldsVlanRouterVlanId OBJECT-TYPE 
           SYNTAX      Integer32 (1..4094) 
           MAX-ACCESS  read-only 
           STATUS      current 
           DESCRIPTION 
              "VLAN ID of the ports through which router is reachable." 
           ::= { mldsVlanRouterEntry 1 } 
 
      mldsVlanRouterPortList OBJECT-TYPE 
           SYNTAX      PortList 
           MAX-ACCESS  read-only
           STATUS      current 
           DESCRIPTION 
               "List of ports on which routers are present. 
                These router ports are learnt through control messages 
                received from routers, and can also be configured 
                statically." 
           ::= { mldsVlanRouterEntry 2 } 
 
-- VLAN based filter table 
 
      mldsVlanFilterTable OBJECT-TYPE 
          SYNTAX      SEQUENCE OF MldsVlanFilterEntry 
          MAX-ACCESS  not-accessible 
          STATUS      current 
          DESCRIPTION 
             "This table contains configuration of snooping
              on specific Vlans. This Table is valid only when VLAN is  
              enabled in the system." 
          ::= { mldsVlan 4 } 
 
      mldsVlanFilterEntry OBJECT-TYPE 
          SYNTAX      MldsVlanFilterEntry 
          MAX-ACCESS  not-accessible 
          STATUS      current 
          DESCRIPTION 
             "Contains snooping status , version and fast leave
              configuration for a specific VLAN." 
          INDEX { mldsVlanFilterVlanId } 
          ::= { mldsVlanFilterTable 1 } 
 
      MldsVlanFilterEntry ::= SEQUENCE { 
          mldsVlanFilterVlanId           Integer32, 
          mldsVlanSnoopStatus            INTEGER, 
          mldsVlanQuerier                INTEGER, 
          mldsVlanCfgQuerier             INTEGER, 
          mldsVlanQueryInterval          Integer32, 
          mldsVlanRtrPortList            PortList
          , mldsVlanFbdRtrPortList         PortList
          , mldsVlanFastLeave            INTEGER
          , mldsVlanDataDrivenLearningStatus INTEGER
          , mldsVlanReportSuppression INTEGER
        ,   mldsVlanRobustnessValue  Integer32
        ,   mldsVlanGrpQueryInterval  Integer32
        ,   mldsVlanQueryMaxResponseTime  INTEGER
          } 

      mldsVlanFilterVlanId OBJECT-TYPE 
           SYNTAX      Integer32 (1..4094) 
           MAX-ACCESS  read-only 
           STATUS      current 
           DESCRIPTION 
            "Index of MldsVlanFilterEntry. This object indicates the VLAN ID for which 
            the snooping configurations in MldsVlanFilterEntry is to be done." 
           ::= { mldsVlanFilterEntry 1 } 
 
      mldsVlanSnoopStatus OBJECT-TYPE 
           SYNTAX      INTEGER { enabled(1), disabled(2) } 
           MAX-ACCESS  read-write 
           STATUS      current 
           DESCRIPTION 
               "This object allows you to enable/disable MLDS function on a specific VLAN."  
           DEFVAL  { 1 }
           ::= { mldsVlanFilterEntry 2 } 

      mldsVlanQuerier OBJECT-TYPE 
          SYNTAX      INTEGER  { enabled(1), disabled(2) } 
          MAX-ACCESS  read-only 
          STATUS      current 
          DESCRIPTION 
             "Indicates whether the switch is configured as a querier in the VLAN"
          DEFVAL  { 2 } 
          ::= { mldsVlanFilterEntry 3 } 

      mldsVlanCfgQuerier OBJECT-TYPE 
          SYNTAX      INTEGER  { enabled(1), disabled(2) } 
          MAX-ACCESS  read-write 
          STATUS      current 
          DESCRIPTION 
             "The snooping switch can be configured as a querier via this object 
              to send out MLD general queries when IGMP routers are not present in the VLAN. 
              When set to 'enabled', the switch will generate general queries."
          DEFVAL  { 2 } 
          ::= { mldsVlanFilterEntry 4 } 
      mldsVlanQueryInterval OBJECT-TYPE 
          SYNTAX      Integer32 (60..600) 
          MAX-ACCESS  read-write 
          STATUS      current 
          DESCRIPTION 
             "This is the interval (in seconds) for which the switch 
              sends general queries when it is configured as a querier for 
              the VLAN. A switch should be configured as a querier for a VLAN 
              only when there is no queriers in the network."   
          DEFVAL  { 125 } 
          ::= { mldsVlanFilterEntry 5 } 
      mldsVlanRtrPortList OBJECT-TYPE 
           SYNTAX      PortList 
           MAX-ACCESS  read-write
           STATUS      current 
           DESCRIPTION 
               "List of ports which are configured statically as router ports"
           ::= { mldsVlanFilterEntry 6 } 

      mldsVlanFbdRtrPortList OBJECT-TYPE 
           SYNTAX      PortList 
           MAX-ACCESS  read-write
           STATUS      current 
           DESCRIPTION 
               "List of ports which can be configured statically as forbidden router ports."
           ::= { mldsVlanFilterEntry 7 }            

      mldsVlanFastLeave OBJECT-TYPE 
           SYNTAX      INTEGER { enabled(1), disabled(2) } 
           MAX-ACCESS  read-write 
           STATUS      current 
           DESCRIPTION 
               "Enables or disables fast leave for the VLAN. When it is 
                'disabled',on reception of a leave message, the switch checks
                if they are any interested receivers for the group by sending 
                a group specific query before removing the port from the 
                forwarding table. If set to 'enabled', the switch does not 
                send a group specific query and immediately removes the port
                from the forwarding table."
           DEFVAL  { 2 }
           ::= { mldsVlanFilterEntry 8 }

        mldsVlanDataDrivenLearningStatus OBJECT-TYPE 
            SYNTAX      INTEGER { enabled(1), disabled(2) } 
            MAX-ACCESS  read-write 
            STATUS      current 
            DESCRIPTION
                "This object allows you to enable/disable
                Data Driven Learning function on a specific VLAN."
            ::= { mldsVlanFilterEntry 9 }

        mldsVlanReportSuppression OBJECT-TYPE 
            SYNTAX      INTEGER  { enabled(1), disabled(2) } 
            MAX-ACCESS  read-write 
            STATUS      current 
            DESCRIPTION 
               "Enables or disables Report suppression in the system."
            ::= { mldsVlanFilterEntry 10 } 
      mldsVlanRobustnessValue OBJECT-TYPE
          SYNTAX      Integer32 (2..255)
          MAX-ACCESS  read-write
          STATUS      current
          DESCRIPTION 
	     "When the switch receives leave message on a port, it
              sends group specific query to check if there are any other 
              interested receivers for the group. This attribute defines 
              the maximum number of queries sent by the switch before deleting 
              the port from the group membership information in the forwarding 
              database. If the maximum retry count exceeds 'mldsRobustnessValue', 
              then the port will be deleted from the multicast group membership
              information in the forwarding database and received leave message
              will be forwarded onto the router ports if there are no 
              interested receivers for the group." 
          DEFVAL  { 2 } 
            ::= { mldsVlanFilterEntry 11 } 

      mldsVlanGrpQueryInterval OBJECT-TYPE 
          SYNTAX      Integer32 (1..25) 
          MAX-ACCESS  read-write 
          STATUS      current 
          DESCRIPTION 
             "The value of this attribute defines the time period with which 
              the switch will send group specific queries on a port to check 
              if there is any intersted receivers. The switch will send 
              'mldsRobustnessValue' queries before removing the port from the 
              group membership information in the forwarding database."
          DEFVAL  { 1 }
            ::= { mldsVlanFilterEntry 12 } 

    mldsVlanQueryMaxResponseTime OBJECT-TYPE
        SYNTAX      INTEGER (10..25)
		MAX-ACCESS  read-write
		STATUS      current
		DESCRIPTION 
        	"The maximum query response time advertised in MLDv1 general
        	queries on this interface."
        DEFVAL     { 10 }
            ::= { mldsVlanFilterEntry 13 } 
    -- VLAN Based MLD Snooping Group 
 
      mldsVlanMulticastGroupTable OBJECT-TYPE 
          SYNTAX      SEQUENCE OF MldsVlanMulticastGroupEntry 
          MAX-ACCESS  not-accessible 
          STATUS      current 
          DESCRIPTION 
            "This table contains MAC based multicast forwarding 
             information." 
          ::= { mldsVlan 5 } 
 
      mldsVlanMulticastGroupEntry OBJECT-TYPE 
          SYNTAX      MldsVlanMulticastGroupEntry 
          MAX-ACCESS  not-accessible 
          STATUS      current 
          DESCRIPTION 
            "This table contains VLAN ID, multicast group MAC address and the  
             list of ports onto which the multicast data packets for group
             should be forwarded."  

          INDEX { mldsVlanMulticastGroupVlanId,
                  mldsVlanMulticastGroupIpAddress } 
          ::= { mldsVlanMulticastGroupTable 1 } 
 
      MldsVlanMulticastGroupEntry ::= SEQUENCE { 
          mldsVlanMulticastGroupVlanId           Integer32,
          mldsVlanMulticastGroupIpAddress        InetAddress, 
          mldsVlanMulticastGroupMacAddress       MacAddress,
          mldsVlanMulticastGroupPortList         PortList
        } 

      mldsVlanMulticastGroupVlanId OBJECT-TYPE 
           SYNTAX      Integer32 (1..4094) 
           MAX-ACCESS  read-only 
           STATUS      current 
           DESCRIPTION 
              "VLAN ID pertaining to the Multicast forwarding entry"  
           ::= { mldsVlanMulticastGroupEntry 1 } 
 
      mldsVlanMulticastGroupIpAddress OBJECT-TYPE 
           SYNTAX      InetAddress
           MAX-ACCESS  read-only 
           STATUS      current 
           DESCRIPTION 
               "Multicast group IP address. This object indicates that a
                multicast group address was learned in the switch and be represented 
                as IP address format." 
           ::= { mldsVlanMulticastGroupEntry 2 } 
 
 
      mldsVlanMulticastGroupMacAddress OBJECT-TYPE 
           SYNTAX      MacAddress 
           MAX-ACCESS  read-only 
           STATUS      current 
           DESCRIPTION 
               "Multicast group MAC address. This object indicates that a
                multicast group address was learned in the switch and be represented 
                as MAC address format." 
           ::= { mldsVlanMulticastGroupEntry 3 } 

      mldsVlanMulticastGroupPortList OBJECT-TYPE 
           SYNTAX      PortList 
           MAX-ACCESS  read-only 
           STATUS      current 
           DESCRIPTION 
               "List of ports onto which the multicast data
                packets destined for this group will be forwarded."  
           ::= { mldsVlanMulticastGroupEntry 4 } 

-- Host Table

    mldsHostTable OBJECT-TYPE
        SYNTAX      SEQUENCE OF MldsHostEntry
        MAX-ACCESS  not-accessible
        STATUS      current
        DESCRIPTION
            "This table is used to manage
            the IGMP Host based Fast Leave function of the switch."
        ::= { mldsHost 1 }
 
    mldsHostEntry OBJECT-TYPE
        SYNTAX      MldsHostEntry
        MAX-ACCESS  not-accessible
        STATUS      current
        DESCRIPTION
            "Contains management entities for
            IGMP Host based fast leave function."
        INDEX {mldsHostTableVLANID,
               mldsHostTableGroupAddress,
               mldsHostTablePort,
               mldsHostTableHostIPAddress}
        ::= { mldsHostTable 1 }
 
    MldsHostEntry ::= SEQUENCE {
        mldsHostTableVLANID          Integer32,
        mldsHostTableGroupAddress    Ipv6Address,
        mldsHostTablePort            Integer32,
        mldsHostTableHostIPAddress   Ipv6Address
    }

    mldsHostTableVLANID OBJECT-TYPE
        SYNTAX      Integer32 (1..4094)
        MAX-ACCESS  read-only
        STATUS      current
        DESCRIPTION
            "VLAN ID of IPv6 Host table entry."
        ::= { mldsHostEntry 1 }
 
    mldsHostTableGroupAddress OBJECT-TYPE
        SYNTAX      Ipv6Address
        MAX-ACCESS  read-only
        STATUS      current
        DESCRIPTION
            "Group address of IPv6 Host table entry."
        ::= { mldsHostEntry 2 } 
 
    mldsHostTablePort OBJECT-TYPE 
        SYNTAX      Integer32 
        MAX-ACCESS  read-only 
        STATUS      current 
        DESCRIPTION 
            "Port number of IPv6 Host table entry."
        ::= { mldsHostEntry 3 }

    mldsHostTableHostIPAddress OBJECT-TYPE 
        SYNTAX      Ipv6Address 
        MAX-ACCESS  read-only 
        STATUS      current 
        DESCRIPTION 
            "Host IP address of Group in IPv6 Host table entry."
        ::= { mldsHostEntry 4 }

-- -------------------------------------------------------------
-- groups in the Auth MIB
-- -------------------------------------------------------------
    swAuthenCtrl  OBJECT IDENTIFIER ::= { companyAuthGroup 1 }
-- -----------------------------------------------------------------------------
-- swAuthenCtrl
-- -----------------------------------------------------------------------------

    swAuthStatus OBJECT-TYPE
        SYNTAX INTEGER {
                   enabled(1),
                   disabled(2)
        }
        MAX-ACCESS          read-write
        STATUS              current
        DESCRIPTION
        "Enable/Disable Static 802.1x."
        ::= { swAuthenCtrl 1 }

    swAuthMode OBJECT-TYPE
        SYNTAX  INTEGER {
                    portBase(1),
                    macBase(2)
                }
        MAX-ACCESS  read-write
        STATUS  current
        DESCRIPTION
            "This object indicates the authentication mode of the device."
        ::= { swAuthenCtrl 2 }

    authProtocol OBJECT-TYPE
        SYNTAX INTEGER {
            authProtocolRadiusEap(1),
            authProtocolLocal(2)
        }
        MAX-ACCESS read-write
        STATUS current
        DESCRIPTION
            "The authentication method used to authenticate users."
        DEFVAL { authProtocolRadiusEap }
            ::= { swAuthenCtrl 3 }

-- start CAMEO-EAP-TRANSPARENT-FILTERING
    swAuthCtrlPktFwdMode OBJECT-TYPE
        SYNTAX INTEGER {
            authForwardEap(1),
            authDropEap(2)
        }
        MAX-ACCESS read-write
        STATUS current
        DESCRIPTION
            "When 802.1x disable, this item can decided eap packet be forward or drop."
        DEFVAL { authForwardEap }
            ::= { swAuthenCtrl 4 }
-- end CAMEO-EAP-TRANSPARENT-FILTERING

-- -------------------------------------------------------------
-- groups in the Port Access Control MIB
-- -------------------------------------------------------------
    swAuthPortAccessCtrl  OBJECT IDENTIFIER ::= { companyAuthGroup 2 }
-- -----------------------------------------------------------------------------
-- swAuthPortAccessCtrl
-- -----------------------------------------------------------------------------
    swAuthPortAccessControlTable OBJECT-TYPE
        SYNTAX SEQUENCE OF SwAuthPortAccessControlEntry
        MAX-ACCESS          not-accessible
        STATUS              current
        DESCRIPTION
        "A table that contains the configuration objects for the
         Authenticator PAE associated with each port.
         An entry appears in this table for each port that may
         authenticate access to itself."
        ::= { swAuthPortAccessCtrl 1 }

    swAuthPortAccessControlEntry OBJECT-TYPE
        SYNTAX              SwAuthPortAccessControlEntry
        MAX-ACCESS          not-accessible
        STATUS              current
        DESCRIPTION
        "The configuration information for an Authenticator Port."
        INDEX { swAuthAuthConfigPortNumber }
        ::= { swAuthPortAccessControlTable 1 }

    SwAuthPortAccessControlEntry ::= SEQUENCE {
        swAuthAuthConfigPortNumber          INTEGER,
        swAuthAuthQuietPeriod               INTEGER,
        swAuthAuthSuppTimeout               INTEGER,
        swAuthAuthServerTimeout             INTEGER,
        swAuthAuthMaxReq                    INTEGER,
        swAuthAuthTxPeriod                  INTEGER,
        swAuthAuthReAuthPeriod              INTEGER,
        swAuthAuthReAuthentication          INTEGER,
        swAuthAuthConfigPortControl         INTEGER,
        swAuthAuthCapability                INTEGER,
        swAuthAuthDirection                 INTEGER
    }

    swAuthAuthConfigPortNumber   OBJECT-TYPE
        SYNTAX              INTEGER
        MAX-ACCESS          read-only
        STATUS              current
        DESCRIPTION
        "A unique value for each port that correlates to port index.
         Its value ranges between 1 and the value of port number."
        ::= { swAuthPortAccessControlEntry 1 }

    swAuthAuthQuietPeriod        OBJECT-TYPE
        SYNTAX        INTEGER (0..65535)
        MAX-ACCESS    read-write
        STATUS        current
        DESCRIPTION
           "The value, in seconds, of the quietPeriod constant
           currently in use by the Authenticator PAE state
           machine."
        REFERENCE
           "9.4.1, quietPeriod."
        DEFVAL { 60 }
        ::= { swAuthPortAccessControlEntry 2 }

    swAuthAuthSuppTimeout        OBJECT-TYPE
        SYNTAX        INTEGER (1..65535)
        MAX-ACCESS    read-write
        STATUS        current
        DESCRIPTION
           "The value, in seconds, of the suppTimeout constant
           currently in use by the Backend Authentication state
           machine."
        REFERENCE
           "9.4.1, suppTimeout."
        DEFVAL { 12 }
        ::= { swAuthPortAccessControlEntry 3 }

    swAuthAuthServerTimeout      OBJECT-TYPE
        SYNTAX        INTEGER (1..65535)
        MAX-ACCESS    read-write
        STATUS        current
        DESCRIPTION
           "The value, in seconds, of the serverTimeout constant
           currently in use by the Backend Authentication state
           machine."
        REFERENCE
           "9.4.1, serverTimeout."
        DEFVAL { 16 }
        ::= { swAuthPortAccessControlEntry 4 }

    swAuthAuthMaxReq             OBJECT-TYPE
        SYNTAX        INTEGER (1..10)
        MAX-ACCESS    read-write
        STATUS        current
        DESCRIPTION
           "The value of the maxReq constant currently in use by
           the Backend Authentication state machine."
        REFERENCE
           "9.4.1, maxReq."
        DEFVAL { 2 }
        ::= { swAuthPortAccessControlEntry 5 }

    swAuthAuthTxPeriod           OBJECT-TYPE
        SYNTAX        INTEGER (1..65535)
        MAX-ACCESS    read-write
        STATUS        current
        DESCRIPTION
           "The value, in seconds, of the txPeriod constant
           currently in use by the Authenticator PAE state
           machine."
        REFERENCE
           "9.4.1, txPeriod."
        DEFVAL { 24 }
        ::= { swAuthPortAccessControlEntry 6 }

    swAuthAuthReAuthPeriod       OBJECT-TYPE
        SYNTAX        INTEGER (1..65535)
        MAX-ACCESS    read-write
        STATUS        current
        DESCRIPTION
           "The value, in seconds, of the reAuthPeriod constant
           currently in use by the Reauthentication Timer state
           machine."
        REFERENCE
           "9.4.1, reAuthPerio."
        DEFVAL { 3600 }
        ::= { swAuthPortAccessControlEntry 7 }

    swAuthAuthReAuthentication   OBJECT-TYPE
        SYNTAX        INTEGER { enabled(1), disabled(2) }
        MAX-ACCESS    read-write
        STATUS        current
        DESCRIPTION
           "The enable/disable control used by the Reauthentication
           Timer state machine (8.5.5.1)."
        REFERENCE
           "9.4.1, reAuthEnable."
        ::= { swAuthPortAccessControlEntry 8 }

    swAuthAuthConfigPortControl  OBJECT-TYPE
       SYNTAX       INTEGER {
                       forceUnauthorized(1),
                       auto(2),
                       forceAuthorized(3)
                   }
        MAX-ACCESS          read-write
        STATUS              current
        DESCRIPTION
           "The current value of the controlled Port
           control parameter for the Port."
        REFERENCE
           "9.4.1, AuthControlledPortControl."
        ::= { swAuthPortAccessControlEntry 9 }

    swAuthAuthCapability         OBJECT-TYPE
       SYNTAX       INTEGER {
                       authenticator(1),
                       none(2)
                   }
        MAX-ACCESS          read-write
        STATUS              current
        DESCRIPTION
           "The current value of the controlled Port
           control parameter for the Port."
        REFERENCE
           "AuthCapability."
        ::= { swAuthPortAccessControlEntry 10 }

    swAuthAuthDirection          OBJECT-TYPE
       SYNTAX       INTEGER {
                       both(0),
                       in(1)
                   }
        MAX-ACCESS          read-write
        STATUS              current
        DESCRIPTION
           "The current value of the controlled Port
           control parameter for the Port."
        REFERENCE
           "AuthDirection."
        ::= { swAuthPortAccessControlEntry 11 }

-- -------------------------------------------------------------
-- groups in the 802.1X Local user MIB
-- -------------------------------------------------------------
    swAuthUser  OBJECT IDENTIFIER ::= { companyAuthGroup 3 }
-- -----------------------------------------------------------------------------
-- swAuthUser
-- -----------------------------------------------------------------------------
    swAuthUserTable OBJECT-TYPE
        SYNTAX SEQUENCE OF SwAuthUserEntry
        MAX-ACCESS          not-accessible
        STATUS              current
        DESCRIPTION
        "A table that contains the configuration objects for the
         Authenticator PAE associated with each port.
         An entry appears in this table for each port that may
         authenticate access to itself."
        ::= { swAuthUser 1 }

    swAuthUserEntry OBJECT-TYPE
        SYNTAX              SwAuthUserEntry
        MAX-ACCESS          not-accessible
        STATUS              current
        DESCRIPTION
        "The configuration information for an Authenticator Port."
        INDEX { swAuthUserName }
        ::= { swAuthUserTable 1 }

    SwAuthUserEntry ::= SEQUENCE {
        swAuthUserName                      SnmpAdminString,
        swAuthUserPassword                  DisplayString,
        swAuthUserStatus                    RowStatus
    }

    swAuthUserName OBJECT-TYPE
        SYNTAX      SnmpAdminString (SIZE(1..15))
        MAX-ACCESS  read-only
        STATUS      current
        DESCRIPTION
            "The unique index value of a row in this table.

            This object is used to set 802.1X Local user name,
            The following characters are allowed to input:
            semicolon, question mark, space, and double quotation mark."
        ::= { swAuthUserEntry 1 }

    swAuthUserPassword  OBJECT-TYPE
       SYNTAX      DisplayString (SIZE(1..15))
       MAX-ACCESS  read-write
       STATUS      current
       DESCRIPTION
          "This object is used to set 802.1X Local user Password,
          The following characters are allowed to input:
          semicolon, question mark, space, and double quotation mark."
       ::= { swAuthUserEntry 2 }

    swAuthUserStatus OBJECT-TYPE
        SYNTAX       RowStatus
        MAX-ACCESS   read-create
        STATUS       current
        DESCRIPTION
            "The status of this conceptual row in the swAuthUserTable.

            An entry in this table is not qualified for activation
            until instances of all corresponding columns have been
            initialized, either through default values, or through
            Set operations.  The swAuthUserName objects must be
            explicitly set."
        ::= { swAuthUserEntry 3 }

-- -------------------------------------------------------------
-- groups in the Authentication RADIUS Server MIB
-- -------------------------------------------------------------
    swAuthRadiusServer  OBJECT IDENTIFIER ::= { companyAuthGroup 4 }
-- -----------------------------------------------------------------------------
-- swAuthRadiusServer
-- -----------------------------------------------------------------------------
    iPv4swAuthRadiusServerTable OBJECT-TYPE
        SYNTAX SEQUENCE OF IPv4SwAuthRadiusServerEntry
        MAX-ACCESS          not-accessible
        STATUS              obsolete
        DESCRIPTION
        "A table that contains the configuration objects for the
         Authenticator PAE associated with each port.
         An entry appears in this table for each port that may
         authenticate access to itself."
        ::= { swAuthRadiusServer 1 }

    iPv4swAuthRadiusServerEntry                 OBJECT-TYPE
        SYNTAX                              IPv4SwAuthRadiusServerEntry
        MAX-ACCESS                          not-accessible
        STATUS                              obsolete

        DESCRIPTION
        "The configuration information for an Authenticator Port."
        INDEX { iPv4swAuthRadiusServerIndex }
        ::= { iPv4swAuthRadiusServerTable 1 }

    IPv4SwAuthRadiusServerEntry ::= SEQUENCE {
        iPv4swAuthRadiusServerIndex                 INTEGER,
        iPv4swAuthRadiusServerAddress               IpAddress,
        iPv4swAuthRadiusServerAuthenticationPort    INTEGER,
        iPv4swAuthRadiusServerAccountingPort        INTEGER,
        iPv4swAuthRadiusServerTimeout               INTEGER,
        iPv4swAuthRadiusServerRetransmit            INTEGER,
        iPv4swAuthRadiusServerKey                   DisplayString,
        iPv4swAuthRadiusServerStatus                RowStatus
    }

    iPv4swAuthRadiusServerIndex                 OBJECT-TYPE
        SYNTAX                              INTEGER (1..3)
        MAX-ACCESS                          read-only
        STATUS                              obsolete

        DESCRIPTION
        "A unique value for Authentication RADIUS Server index.
         Its value ranges between 1 and 3."
        ::= { iPv4swAuthRadiusServerEntry 1 }

    iPv4swAuthRadiusServerAddress               OBJECT-TYPE
        SYNTAX                              IpAddress
        MAX-ACCESS                          read-write
        STATUS                              obsolete
        DESCRIPTION
            "The IP address of the RADIUS server
                     referred to in this table entry."
        ::=  { iPv4swAuthRadiusServerEntry 2 }

    iPv4swAuthRadiusServerAuthenticationPort    OBJECT-TYPE
        SYNTAX                              INTEGER (1..65535)
        MAX-ACCESS                          read-write
        STATUS                              obsolete
        DESCRIPTION
            "The value is for setting UDP Port."
        DEFVAL { 1812 }
       ::= { iPv4swAuthRadiusServerEntry 3 }

    iPv4swAuthRadiusServerAccountingPort        OBJECT-TYPE
        SYNTAX                              INTEGER (1..65535)
        MAX-ACCESS                          read-write
        STATUS                              obsolete
        DESCRIPTION
            "The value is for setting UDP Port."
        DEFVAL { 1813 }
       ::= { iPv4swAuthRadiusServerEntry 4 }

    iPv4swAuthRadiusServerTimeout               OBJECT-TYPE
        SYNTAX                              INTEGER (1..255)
        MAX-ACCESS                          read-write
        STATUS                              obsolete
        DESCRIPTION
            "The value is for setting UDP Port."
        DEFVAL { 5 }
       ::= { iPv4swAuthRadiusServerEntry 5 }

    iPv4swAuthRadiusServerRetransmit            OBJECT-TYPE
        SYNTAX                              INTEGER (1..255)
        MAX-ACCESS                          read-write
        STATUS                              obsolete
        DESCRIPTION
            "The value is for setting UDP Port."
        DEFVAL { 2 }
       ::= { iPv4swAuthRadiusServerEntry 6 }

    iPv4swAuthRadiusServerKey                   OBJECT-TYPE
       SYNTAX                               DisplayString (SIZE(1..15))
       MAX-ACCESS                           read-write
       STATUS                               obsolete
       DESCRIPTION
          "This object is used to set 802.1X Radius Server Key,
          The following characters are allowed to input:
          semicolon, question mark, space, and double quotation mark."
       ::= { iPv4swAuthRadiusServerEntry 7 }

    iPv4swAuthRadiusServerStatus OBJECT-TYPE
        SYNTAX       RowStatus
        MAX-ACCESS   read-create
        STATUS       obsolete
        DESCRIPTION
            "The status of this conceptual row in the
            swAuthRadiusServerTable.

            An entry in this table is not qualified for activation
            until instances of all corresponding columns have been
            initialized, either through default values, or through
            Set operations.  The swAuthRadiusServerIndex objects
            must be explicitly set."
        ::= { iPv4swAuthRadiusServerEntry 8 }
-- -----------------------------------------------------------------------------
-- swAuthRadiusServer for IPv6
-- -----------------------------------------------------------------------------
    swAuthRadiusServerTable OBJECT-TYPE
        SYNTAX SEQUENCE OF SwAuthRadiusServerEntry
        MAX-ACCESS          not-accessible
        STATUS              current
        DESCRIPTION
        "A table that contains the configuration objects for the
         Authenticator PAE associated with each port.
         An entry appears in this table for each port that may
         authenticate access to itself."
        ::= { swAuthRadiusServer 2 }

    swAuthRadiusServerEntry                 OBJECT-TYPE
        SYNTAX                              SwAuthRadiusServerEntry
        MAX-ACCESS                          not-accessible
        STATUS                              current
        DESCRIPTION
        "The configuration information for an Authenticator Port."
        INDEX { swAuthRadiusServerIndex }
        ::= { swAuthRadiusServerTable 1 }

    SwAuthRadiusServerEntry ::= SEQUENCE {
        swAuthRadiusServerIndex                 INTEGER,
        swAuthRadiusIPType                      INTEGER,
        swAuthRadiusServerAddress               Ipv6Address,
        swAuthRadiusServerInterfaceName         OCTET STRING,
        swAuthRadiusServerAuthenticationPort    INTEGER,
        swAuthRadiusServerAccountingPort        INTEGER,
        swAuthRadiusServerTimeout               INTEGER,
        swAuthRadiusServerRetransmit            INTEGER,
        swAuthRadiusServerKey                   DisplayString,
        swAuthRadiusServerStatus                RowStatus
    }

    swAuthRadiusServerIndex                 OBJECT-TYPE
        SYNTAX                              INTEGER (1..3)
        MAX-ACCESS                          read-only
        STATUS                              current
        DESCRIPTION
        "A unique value for Authentication RADIUS Server index.
         Its value ranges between 1 and 3."
        ::= { swAuthRadiusServerEntry 1 }

    swAuthRadiusIPType    OBJECT-TYPE
        SYNTAX                              INTEGER (1..2)
        MAX-ACCESS                          read-write
        STATUS                              current
        DESCRIPTION
            "The IP address of the RADIUS server IP type
                referred to in this table entry."
        DEFVAL { 1 }
       ::= { swAuthRadiusServerEntry 2 }

    swAuthRadiusServerAddress               OBJECT-TYPE
        SYNTAX                              Ipv6Address
        MAX-ACCESS                          read-write
        STATUS                              current
        DESCRIPTION
            "The IP address of the RADIUS server
                     referred to in this table entry."
        ::=  { swAuthRadiusServerEntry 3 }

    swAuthRadiusServerInterfaceName   OBJECT-TYPE
         SYNTAX      OCTET STRING
         MAX-ACCESS  read-create
         STATUS      current
         DESCRIPTION
               "Specifies the interface name when the swAuthRadiusServerAddress is linklocal address."
         ::= { swAuthRadiusServerEntry 4 } 

    swAuthRadiusServerAuthenticationPort    OBJECT-TYPE
        SYNTAX                              INTEGER (1..65535)
        MAX-ACCESS                          read-write
        STATUS                              current
        DESCRIPTION
            "The value is for setting UDP Port."
        DEFVAL { 1812 }
       ::= { swAuthRadiusServerEntry 5 }

    swAuthRadiusServerAccountingPort        OBJECT-TYPE
        SYNTAX                              INTEGER (1..65535)
        MAX-ACCESS                          read-write
        STATUS                              current
        DESCRIPTION
            "The value is for setting UDP Port."
        DEFVAL { 1813 }
       ::= { swAuthRadiusServerEntry 6 }

    swAuthRadiusServerTimeout               OBJECT-TYPE
        SYNTAX                              INTEGER (1..255)
        MAX-ACCESS                          read-write
        STATUS                              current
        DESCRIPTION
            "The value is for setting UDP Port."
        DEFVAL { 5 }
       ::= { swAuthRadiusServerEntry 7 }

    swAuthRadiusServerRetransmit            OBJECT-TYPE
        SYNTAX                              INTEGER (1..255)
        MAX-ACCESS                          read-write
        STATUS                              current
        DESCRIPTION
            "The value is for setting UDP Port."
        DEFVAL { 2 }
       ::= { swAuthRadiusServerEntry 8 }

    swAuthRadiusServerKey                   OBJECT-TYPE
       SYNTAX                               DisplayString (SIZE(1..15))
       MAX-ACCESS                           read-write
       STATUS                               current
       DESCRIPTION
          "This object is used to set 802.1X Radius Server Key,
          The following characters are allowed to input:
          semicolon, question mark, space, and double quotation mark."
       ::= { swAuthRadiusServerEntry 9 }

    swAuthRadiusServerStatus OBJECT-TYPE
        SYNTAX       RowStatus
        MAX-ACCESS   read-create
        STATUS       current
        DESCRIPTION
            "The status of this conceptual row in the
            swAuthRadiusServerTable.

            An entry in this table is not qualified for activation
            until instances of all corresponding columns have been
            initialized, either through default values, or through
            Set operations.  The swAuthRadiusServerIndex objects
            must be explicitly set."
        ::= { swAuthRadiusServerEntry 10 }
    -- ------------------------------------------------------------------ 
    -- QoS
    -- ------------------------------------------------------------------

--1--
    cosScheduleMechanism       OBJECT-TYPE 
        SYNTAX INTEGER {
            strictPriority(1),
            wrr(2)
        } 
        MAX-ACCESS    read-write 
        STATUS        current
        DESCRIPTION 
           "Queuing mechanism.
                 strictPriority(1) : Strict Priority
                 wrr(2)            : Weighted Round Robin    
            Strict-priority scheduling is implemented with a special strict-priority scheduler node that is stacked directly above the port. Queues stacked on top of the strict-priority scheduler node always get bandwidth before other queues.   
            Weighted round-robin scheduling is designed to better handle queues with different processing capacities. Each queue has a weight : Low is 1, Medium is 2, High is 4 and Highest is 8 for WS3 spec. Queues with higher weights get bandwidth before than other queues with less weights. 
           " 
        ::= { companyQoSGroup 1 } 

--2--
    cosOutputSchedule     OBJECT IDENTIFIER ::= { companyQoSGroup 2 }
    
    cosClassTable     OBJECT-TYPE
        SYNTAX SEQUENCE OF CosClassEntry
        MAX-ACCESS not-accessible
        STATUS current
        DESCRIPTION
            "A list of cosOutputSchedule."
        ::= { cosOutputSchedule 1 }
        
    cosClassEntry OBJECT-TYPE
        SYNTAX CosClassEntry
        MAX-ACCESS not-accessible
        STATUS current
        DESCRIPTION
            "A list of cosOutputClass Weight."
        INDEX { cosClassIndex }
        ::= { cosClassTable 1 }
        
    CosClassEntry ::= SEQUENCE {
        cosClassIndex                 INTEGER,
        cosWeight              INTEGER
    }
    
    cosClassIndex OBJECT-TYPE
        SYNTAX INTEGER (0..7)
        MAX-ACCESS read-only
        STATUS current
        DESCRIPTION
             "A index of class 0 ~ 7."
        ::= { cosClassEntry 1 }
        
    cosWeight OBJECT-TYPE 
        SYNTAX INTEGER (1..55)
        MAX-ACCESS read-write
        STATUS current
        DESCRIPTION
        "cos weight "
        ::= { cosClassEntry 2 }  

      cosBandwidthCtrlSettings     OBJECT IDENTIFIER ::= { companyQoSGroup 9 }
      
      cosBandwidthCtrlTable     OBJECT-TYPE
          SYNTAX SEQUENCE OF CosBandwidthCtrlEntry
          MAX-ACCESS not-accessible
          STATUS current
          DESCRIPTION
              "A list of cosBandwidthCtrlEntry default priority Entries."
          ::= { cosBandwidthCtrlSettings 1 }
          
      cosBandwidthCtrlEntry OBJECT-TYPE
          SYNTAX CosBandwidthCtrlEntry
          MAX-ACCESS not-accessible
          STATUS current
          DESCRIPTION
              "A list of cosBandwidthCtrlEntry default priority priorities."
          INDEX { cosBandwidthCtrlPortIndex, cosBandwidthCtrlClassIndex }
          ::= { cosBandwidthCtrlTable 1 }
          
      CosBandwidthCtrlEntry ::= SEQUENCE {
          cosBandwidthCtrlPortIndex      Integer32,
          cosBandwidthCtrlClassIndex     INTEGER,
          cosBandwidthValue              Integer32
      }
      
      cosBandwidthCtrlPortIndex OBJECT-TYPE
          SYNTAX Integer32 
          MAX-ACCESS read-only
          STATUS current
          DESCRIPTION
               "A port identifier that is in the range of 1 to ifNumber."
          ::= { cosBandwidthCtrlEntry 1 }
          
      cosBandwidthCtrlClassIndex OBJECT-TYPE
          SYNTAX INTEGER (0..3)
          MAX-ACCESS read-only
          STATUS current
          DESCRIPTION
           "A BandwidthCtrlClassIndex identifier that is in the range of 1 to ifNumber."
          ::= { cosBandwidthCtrlEntry 2 }   
          
          
      cosBandwidthValue OBJECT-TYPE
          SYNTAX Integer32 
          MAX-ACCESS read-write
          STATUS current
          DESCRIPTION
          "The BandwidthValue return value."
          ::= { cosBandwidthCtrlEntry 3 }  
    
    -- ------------------------------------------------------------------ 
    -- QoS
    -- ------------------------------------------------------------------ 
    
--4 default user priority--
    qosDefaultUserPri     OBJECT IDENTIFIER ::= { companyQoSGroup 4 }
    
    qosDefaultUserPriTable     OBJECT-TYPE
        SYNTAX SEQUENCE OF QosDefaultUserPriEntry
        MAX-ACCESS not-accessible
        STATUS current
        DESCRIPTION
            "A list of 802.1p port default priority Entries."
        ::= { qosDefaultUserPri 1 }
        
    qosDefaultUserPriEntry OBJECT-TYPE
        SYNTAX QosDefaultUserPriEntry
        MAX-ACCESS not-accessible
        STATUS current
        DESCRIPTION
            "A list of 802.1p port default priority priorities."
        INDEX { qosDefaultUserPriPortIndex }
        ::= { qosDefaultUserPriTable 1 }
        
    QosDefaultUserPriEntry ::= SEQUENCE {
        qosDefaultUserPriPortIndex      INTEGER,
        qosDefaultPriority              INTEGER,
        qosEffectiveDefaultPriority     INTEGER
    }
    
    qosDefaultUserPriPortIndex OBJECT-TYPE
        SYNTAX INTEGER 
        MAX-ACCESS read-only
        STATUS current
        DESCRIPTION
             "A port identifier that is in the range of 1 to ifNumber."
        ::= { qosDefaultUserPriEntry 1 }
        
    qosDefaultPriority OBJECT-TYPE
        SYNTAX INTEGER {
               priority0(0),
               priority1(1),    
               priority2(2),    
               priority3(3),
               priority4(4),
               priority5(5),    
               priority6(6),    
               priority7(7) 
    	}
        MAX-ACCESS read-write
        STATUS current
        DESCRIPTION
        "For ingress untagged packets, the per port 'Default Priority'
         setting will be applied to packets of each port to provide 
         port-based traffic prioritization when 802.1p is enabled."
        ::= { qosDefaultUserPriEntry 2 }   
        
        
    qosEffectiveDefaultPriority OBJECT-TYPE
        SYNTAX INTEGER {
               priority0(0),
               priority1(1),    
               priority2(2),    
               priority3(3),
               priority4(4),
               priority5(5),    
               priority6(6),    
               priority7(7) 
    	}
        MAX-ACCESS read-only
        STATUS current
        DESCRIPTION
        "For ingress untagged packets, the per port 'Effective Default 
         Priority' setting will be applied to packets of each port to 
         provide port-based traffic prioritization when 802.1p is enabled."
        ::= { qosDefaultUserPriEntry 3 }  

--5 vlan tag user priority --
    qosUserPriority     OBJECT IDENTIFIER ::= { companyQoSGroup 5 }
    qosUserPriorityTable OBJECT-TYPE
        SYNTAX      SEQUENCE OF QosUserPriEntry
        MAX-ACCESS  not-accessible
        STATUS      current
        DESCRIPTION
            "A table mapping evaluated User Priority to Traffic
             Class, for forwarding by the bridge.  Traffic class is a
             number in the range (0..3)."
        REFERENCE
            "ISO/IEC 15802-3 Table 7-2"
        ::= { qosUserPriority 1 }

    qosUserPriEntry OBJECT-TYPE
        SYNTAX      QosUserPriEntry
        MAX-ACCESS  not-accessible
        STATUS      current
        DESCRIPTION
        "User Priority to Traffic Class mapping."
        INDEX {qosUserPriIndex }
        ::= { qosUserPriorityTable 1 }

    QosUserPriEntry ::=
        SEQUENCE {
            qosUserPriIndex
                INTEGER,
            qosUserPriClass
                INTEGER
        }

    qosUserPriIndex OBJECT-TYPE
        SYNTAX      INTEGER (0..7)
        MAX-ACCESS  read-only
        STATUS      current
        DESCRIPTION
            "For ingress tagged packets, D-Link Smart Switches will refer
         to these information and prioritize them with 4 different priority queues. 
         If 802.1p is enabled."

        ::= { qosUserPriEntry 1 }

    qosUserPriClass OBJECT-TYPE
        SYNTAX      INTEGER (0..7)
        MAX-ACCESS  read-write
        STATUS      current
        DESCRIPTION
            "The User Class the received frame is mapped to."
        ::= { qosUserPriEntry 2 }

--7 priority setting on/off table --
    qosPriSettings     OBJECT IDENTIFIER ::= { companyQoSGroup 7 }
    qosPriSettingsTable OBJECT-TYPE
        SYNTAX      SEQUENCE OF QosPriSettingsEntry
        MAX-ACCESS  not-accessible
        STATUS      current
        DESCRIPTION
            "A list of port priority settings."
        REFERENCE
            "ISO/IEC 15802-3 Table 7-2"
        ::= { qosPriSettings 1 }

    qosPriSettingsEntry OBJECT-TYPE
        SYNTAX      QosPriSettingsEntry
        MAX-ACCESS  not-accessible
        STATUS      current
        DESCRIPTION
        "A list of port priority settings Entries."
        INDEX {qosPriSetPortIndex }
        ::= { qosPriSettingsTable 1 }

    QosPriSettingsEntry ::=
        SEQUENCE {
            qosPriSetPortIndex
                INTEGER,
            qosPriSetPortType
                INTEGER
        }

    qosPriSetPortIndex OBJECT-TYPE
        SYNTAX      INTEGER
        MAX-ACCESS  read-only
        STATUS      current
        DESCRIPTION
            "A port identifier that is in the range of 1 to ifNumber."
        ::= { qosPriSettingsEntry 1 }

    qosPriSetPortType OBJECT-TYPE
        SYNTAX      INTEGER
        {
               none(0),
               ieee8021P(2),
               dscp-tos(4),
               ieee8021P-dscp-tos(6)
    	}
        MAX-ACCESS  read-write
        STATUS      current
        DESCRIPTION
            "The port priority setting type. (ex. none = 0, 
             802.1p = 2, DSCP = 4. If you want enable 802.1p & DSCP, the value
             is 2 + 4 = 6. "
        ::= { qosPriSettingsEntry 2 }

    -- ------------------------------------------------------------------ 
    -- QoS
    -- ------------------------------------------------------------------
    qosDiffServTOS     OBJECT IDENTIFIER ::= { companyQoSGroup 6 }
    
	qosDSCPTOSMode  OBJECT-TYPE
        SYNTAX INTEGER {
           tos(1),
           dscp(2)
        } 
        MAX-ACCESS    read-write 
        STATUS        current
        DESCRIPTION 
           "Settings of Qos mode:
              DSCP QoS or TOS Qos.
            IEEE 802.1p : It specifies a priority(0~7) value to four queues in WS3 : Low(1,2), Medium(0,3), High(4,5) and Highest(6,7), inclusive that can be used by Quality of Service (QoS) disciplines to differentiate traffic.
            DSCP : Differentiated services enhancements to the Internet protocol are intended to enable scalable service discrimination in the Internet without the need for per-flow state and signaling at every hop. 
           " 
        ::= { qosDiffServTOS 1 }    

    -- ------------------------------------------------------------------ 
    -- DSCP-Mode
    -- ------------------------------------------------------------------
    
    qosDiffServTypeGroup OBJECT IDENTIFIER ::= { qosDiffServTOS 2 }
    
    qosDiffServType00 OBJECT-TYPE
        SYNTAX  INTEGER (0..7)
    	MAX-ACCESS   read-write
        STATUS       current
        DESCRIPTION
           "DiffServ Type 0 : IP ToS value = 0"  
        ::= { qosDiffServTypeGroup 1 }
    
    qosDiffServType01 OBJECT-TYPE
        SYNTAX  INTEGER (0..7)
    	MAX-ACCESS   read-write
        STATUS       current
        DESCRIPTION
           "DiffServ Type 01 : IP ToS value = 4"  
        ::= { qosDiffServTypeGroup 2 }
        
    qosDiffServType02 OBJECT-TYPE
        SYNTAX  INTEGER (0..7)
        MAX-ACCESS   read-write
        STATUS       current
        DESCRIPTION
           "DiffServ Type 02 : IP ToS value = 8"  
        ::= { qosDiffServTypeGroup 3 }
    
    qosDiffServType03 OBJECT-TYPE
        SYNTAX  INTEGER (0..7)
        MAX-ACCESS   read-write
        STATUS       current
        DESCRIPTION
           "DiffServ Type 03 : IP ToS value = 12"  
        ::= { qosDiffServTypeGroup 4 }
        
    qosDiffServType04 OBJECT-TYPE
        SYNTAX  INTEGER (0..7)
        MAX-ACCESS   read-write
        STATUS       current
        DESCRIPTION
           "DiffServ Type 04 : IP ToS value = 16"  
        ::= { qosDiffServTypeGroup 5 }
    
    qosDiffServType05 OBJECT-TYPE
        SYNTAX  INTEGER (0..7)
        MAX-ACCESS   read-write
        STATUS       current
        DESCRIPTION
           "DiffServ Type 05 : IP ToS value = 20"  
        ::= { qosDiffServTypeGroup 6 }
        
    qosDiffServType06 OBJECT-TYPE
        SYNTAX  INTEGER (0..7)
        MAX-ACCESS   read-write
        STATUS       current
        DESCRIPTION
           "DiffServ Type 06 : IP ToS value = 24"  
        ::= { qosDiffServTypeGroup 7 }
    
    qosDiffServType07 OBJECT-TYPE
        SYNTAX  INTEGER (0..7)
        MAX-ACCESS   read-write
        STATUS       current
        DESCRIPTION
           "DiffServ Type 07 : IP ToS value = 28"  
        ::= { qosDiffServTypeGroup 8 }
        
    qosDiffServType08 OBJECT-TYPE
        SYNTAX  INTEGER (0..7)
        MAX-ACCESS   read-write
        STATUS       current
        DESCRIPTION
           "DiffServ Type 08 : IP ToS value = 32"  
        ::= { qosDiffServTypeGroup 9 }
    
    qosDiffServType09 OBJECT-TYPE
        SYNTAX  INTEGER (0..7)
        MAX-ACCESS   read-write
        STATUS       current
        DESCRIPTION
           "DiffServ Type 09 : IP ToS value = 36"  
        ::= { qosDiffServTypeGroup 10 }
        
    qosDiffServType10 OBJECT-TYPE
        SYNTAX  INTEGER (0..7)
        MAX-ACCESS   read-write
        STATUS       current
        DESCRIPTION
           "DiffServ Type 10 : IP ToS value = 40"  
        ::= { qosDiffServTypeGroup 11 }
    
    qosDiffServType11 OBJECT-TYPE
        SYNTAX  INTEGER (0..7)
        MAX-ACCESS   read-write
        STATUS       current
        DESCRIPTION
           "DiffServ Type 11 : IP ToS value = 44"  
        ::= { qosDiffServTypeGroup 12 }
        
    qosDiffServType12 OBJECT-TYPE
        SYNTAX  INTEGER (0..7)
        MAX-ACCESS   read-write
        STATUS       current
        DESCRIPTION
           "DiffServ Type 12 : IP ToS value = 48"  
        ::= { qosDiffServTypeGroup 13 }
    
    qosDiffServType13 OBJECT-TYPE
        SYNTAX  INTEGER (0..7)
        MAX-ACCESS   read-write
        STATUS       current
        DESCRIPTION
           "DiffServ Type 13 : IP ToS value = 52"  
        ::= { qosDiffServTypeGroup 14 }
        
    qosDiffServType14 OBJECT-TYPE
        SYNTAX  INTEGER (0..7)
        MAX-ACCESS   read-write
        STATUS       current
        DESCRIPTION
           "DiffServ Type 14 : IP ToS value = 56"  
        ::= { qosDiffServTypeGroup 15 }
    
    qosDiffServType15 OBJECT-TYPE
        SYNTAX  INTEGER (0..7)
        MAX-ACCESS   read-write
        STATUS       current
        DESCRIPTION
           "DiffServ Type 15 : IP ToS value = 60"  
        ::= { qosDiffServTypeGroup 16 }
        
    qosDiffServType16 OBJECT-TYPE
        SYNTAX  INTEGER (0..7)
        MAX-ACCESS   read-write
        STATUS       current
        DESCRIPTION
           "DiffServ Type 16 : IP ToS value = 64"  
        ::= { qosDiffServTypeGroup 17 }
    
    qosDiffServType17 OBJECT-TYPE
        SYNTAX  INTEGER (0..7)
        MAX-ACCESS   read-write
        STATUS       current
        DESCRIPTION
           "DiffServ Type 17 : IP ToS value = 68"  
        ::= { qosDiffServTypeGroup 18 }
        
    qosDiffServType18 OBJECT-TYPE
        SYNTAX  INTEGER (0..7)
        MAX-ACCESS   read-write
        STATUS       current
        DESCRIPTION
           "DiffServ Type 18 : IP ToS value = 72"  
        ::= { qosDiffServTypeGroup 19 }
    
    qosDiffServType19 OBJECT-TYPE
        SYNTAX  INTEGER (0..7)
        MAX-ACCESS   read-write
        STATUS       current
        DESCRIPTION
           "DiffServ Type 19 : IP ToS value = 76"  
        ::= { qosDiffServTypeGroup 20 }
        
    qosDiffServType20 OBJECT-TYPE
        SYNTAX  INTEGER (0..7)
        MAX-ACCESS   read-write
        STATUS       current
        DESCRIPTION
           "DiffServ Type 20 : IP ToS value = 80"  
        ::= { qosDiffServTypeGroup 21 }
    
    qosDiffServType21 OBJECT-TYPE
        SYNTAX  INTEGER (0..7)
        MAX-ACCESS   read-write
        STATUS       current
        DESCRIPTION
           "DiffServ Type 21 : IP ToS value = 84"  
        ::= { qosDiffServTypeGroup 22 }                                            
        
    qosDiffServType22 OBJECT-TYPE
        SYNTAX  INTEGER (0..7)
        MAX-ACCESS   read-write
        STATUS       current
        DESCRIPTION
           "DiffServ Type 22 : IP ToS value = 88"  
        ::= { qosDiffServTypeGroup 23 }
    
    qosDiffServType23 OBJECT-TYPE
        SYNTAX  INTEGER (0..7)
        MAX-ACCESS   read-write
        STATUS       current
        DESCRIPTION
           "DiffServ Type 23 : IP ToS value = 92"  
        ::= { qosDiffServTypeGroup 24 }
        
    qosDiffServType24 OBJECT-TYPE
        SYNTAX  INTEGER (0..7)
        MAX-ACCESS   read-write
        STATUS       current
        DESCRIPTION
           "DiffServ Type 24 : IP ToS value = 96"  
        ::= { qosDiffServTypeGroup 25 }
    
    qosDiffServType25 OBJECT-TYPE
        SYNTAX  INTEGER (0..7)
        MAX-ACCESS   read-write
        STATUS       current
        DESCRIPTION
           "DiffServ Type 25 : IP ToS value = 100"  
        ::= { qosDiffServTypeGroup 26 }
        
    qosDiffServType26 OBJECT-TYPE
        SYNTAX  INTEGER (0..7)
        MAX-ACCESS   read-write
        STATUS       current
        DESCRIPTION
           "DiffServ Type 26 : IP ToS value = 104"  
        ::= { qosDiffServTypeGroup 27 }
    
    qosDiffServType27 OBJECT-TYPE
        SYNTAX  INTEGER (0..7)
        MAX-ACCESS   read-write
        STATUS       current
        DESCRIPTION
           "DiffServ Type 27 : IP ToS value = 108"  
        ::= { qosDiffServTypeGroup 28 }
        
    qosDiffServType28 OBJECT-TYPE
        SYNTAX  INTEGER (0..7)
        MAX-ACCESS   read-write
        STATUS       current
        DESCRIPTION
           "DiffServ Type 28 : IP ToS value = 112"  
        ::= { qosDiffServTypeGroup 29 }
    
    qosDiffServType29 OBJECT-TYPE
        SYNTAX  INTEGER (0..7)
        MAX-ACCESS   read-write
        STATUS       current
        DESCRIPTION
           "DiffServ Type 29 : IP ToS value = 116"  
        ::= { qosDiffServTypeGroup 30 }   
    
    qosDiffServType30 OBJECT-TYPE
        SYNTAX  INTEGER (0..7)
        MAX-ACCESS   read-write
        STATUS       current
        DESCRIPTION
           "DiffServ Type 30 : IP ToS value = 120"  
        ::= { qosDiffServTypeGroup 31 }
    
    qosDiffServType31 OBJECT-TYPE
        SYNTAX  INTEGER (0..7)
        MAX-ACCESS   read-write
        STATUS       current
        DESCRIPTION
           "DiffServ Type 31 : IP ToS value = 124"  
        ::= { qosDiffServTypeGroup 32 }
    
    qosDiffServType32 OBJECT-TYPE
        SYNTAX  INTEGER (0..7)
        MAX-ACCESS   read-write
        STATUS       current
        DESCRIPTION
           "DiffServ Type 32 : IP ToS value = 128"  
        ::= { qosDiffServTypeGroup 33 }
    
    qosDiffServType33 OBJECT-TYPE
        SYNTAX  INTEGER (0..7)
        MAX-ACCESS   read-write
        STATUS       current
        DESCRIPTION
           "DiffServ Type 33 : IP ToS value = 132"  
        ::= { qosDiffServTypeGroup 34 }
        
    qosDiffServType34 OBJECT-TYPE
        SYNTAX  INTEGER (0..7)
        MAX-ACCESS   read-write
        STATUS       current
        DESCRIPTION
           "DiffServ Type 34 : IP ToS value = 136"  
        ::= { qosDiffServTypeGroup 35 }
    
    qosDiffServType35 OBJECT-TYPE
        SYNTAX  INTEGER (0..7)
        MAX-ACCESS   read-write
        STATUS       current
        DESCRIPTION
           "DiffServ Type 35 : IP ToS value = 140"  
        ::= { qosDiffServTypeGroup 36 }
        
    qosDiffServType36 OBJECT-TYPE
        SYNTAX  INTEGER (0..7)
        MAX-ACCESS   read-write
        STATUS       current
        DESCRIPTION
           "DiffServ Type 36 : IP ToS value = 144"  
        ::= { qosDiffServTypeGroup 37 }
    
    qosDiffServType37 OBJECT-TYPE
        SYNTAX  INTEGER (0..7)
        MAX-ACCESS   read-write
        STATUS       current
        DESCRIPTION
           "DiffServ Type 37 : IP ToS value = 148"  
        ::= { qosDiffServTypeGroup 38 }
        
    qosDiffServType38 OBJECT-TYPE
        SYNTAX  INTEGER (0..7)
        MAX-ACCESS   read-write
        STATUS       current
        DESCRIPTION
           "DiffServ Type 38 : IP ToS value = 152"  
        ::= { qosDiffServTypeGroup 39 }
    
    qosDiffServType39 OBJECT-TYPE
        SYNTAX  INTEGER (0..7)
        MAX-ACCESS   read-write
        STATUS       current
        DESCRIPTION
           "DiffServ Type 39 : IP ToS value = 156"  
        ::= { qosDiffServTypeGroup 40 }
        
    qosDiffServType40 OBJECT-TYPE
        SYNTAX  INTEGER (0..7)
        MAX-ACCESS   read-write
        STATUS       current
        DESCRIPTION
           "DiffServ Type 40 : IP ToS value = 160"  
        ::= { qosDiffServTypeGroup 41 }
    
    qosDiffServType41 OBJECT-TYPE
        SYNTAX  INTEGER (0..7)
        MAX-ACCESS   read-write
        STATUS       current
        DESCRIPTION
           "DiffServ Type 41 : IP ToS value = 164"  
        ::= { qosDiffServTypeGroup 42 }
        
    qosDiffServType42 OBJECT-TYPE
        SYNTAX  INTEGER (0..7)
        MAX-ACCESS   read-write
        STATUS       current
        DESCRIPTION
           "DiffServ Type 42 : IP ToS value = 168"  
        ::= { qosDiffServTypeGroup 43 }
    
    qosDiffServType43 OBJECT-TYPE
        SYNTAX  INTEGER (0..7)
        MAX-ACCESS   read-write
        STATUS       current
        DESCRIPTION
           "DiffServ Type 43 : IP ToS value = 172"  
        ::= { qosDiffServTypeGroup 44 }
        
    qosDiffServType44 OBJECT-TYPE
        SYNTAX  INTEGER (0..7)
        MAX-ACCESS   read-write
        STATUS       current
        DESCRIPTION
           "DiffServ Type 44 : IP ToS value = 176"  
        ::= { qosDiffServTypeGroup 45 }
    
    qosDiffServType45 OBJECT-TYPE
        SYNTAX  INTEGER (0..7)
        MAX-ACCESS   read-write
        STATUS       current
        DESCRIPTION
           "DiffServ Type 45 : IP ToS value = 180"  
        ::= { qosDiffServTypeGroup 46 }
        
    qosDiffServType46 OBJECT-TYPE
        SYNTAX  INTEGER (0..7)
        MAX-ACCESS   read-write
        STATUS       current
        DESCRIPTION
           "DiffServ Type 46 : IP ToS value = 184"  
        ::= { qosDiffServTypeGroup 47 }
    
    qosDiffServType47 OBJECT-TYPE
        SYNTAX  INTEGER (0..7)
        MAX-ACCESS   read-write
        STATUS       current
        DESCRIPTION
           "DiffServ Type 47 : IP ToS value = 188"  
        ::= { qosDiffServTypeGroup 48 }
        
    qosDiffServType48 OBJECT-TYPE
        SYNTAX  INTEGER (0..7)
        MAX-ACCESS   read-write
        STATUS       current
        DESCRIPTION
           "DiffServ Type 48 : IP ToS value = 192"  
        ::= { qosDiffServTypeGroup 49 }
    
    qosDiffServType49 OBJECT-TYPE
        SYNTAX  INTEGER (0..7)
        MAX-ACCESS   read-write
        STATUS       current
        DESCRIPTION
           "DiffServ Type 49 : IP ToS value = 196"  
        ::= { qosDiffServTypeGroup 50 }
        
    qosDiffServType50 OBJECT-TYPE
        SYNTAX  INTEGER (0..7)
        MAX-ACCESS   read-write
        STATUS       current
        DESCRIPTION
           "DiffServ Type 50 : IP ToS value = 200"  
        ::= { qosDiffServTypeGroup 51 }
    
    qosDiffServType51 OBJECT-TYPE
        SYNTAX  INTEGER (0..7)
        MAX-ACCESS   read-write
        STATUS       current
        DESCRIPTION
           "DiffServ Type 51 : IP ToS value = 204"  
        ::= { qosDiffServTypeGroup 52 }
        
    qosDiffServType52 OBJECT-TYPE
        SYNTAX  INTEGER (0..7)
        MAX-ACCESS   read-write
        STATUS       current
        DESCRIPTION
           "DiffServ Type 52 : IP ToS value = 208"  
        ::= { qosDiffServTypeGroup 53 }
    
    qosDiffServType53 OBJECT-TYPE
        SYNTAX  INTEGER (0..7)
        MAX-ACCESS   read-write
        STATUS       current
        DESCRIPTION
           "DiffServ Type 53 : IP ToS value = 212"  
        ::= { qosDiffServTypeGroup 54 }                                            
        
    qosDiffServType54 OBJECT-TYPE
        SYNTAX  INTEGER (0..7)
        MAX-ACCESS   read-write
        STATUS       current
        DESCRIPTION
           "DiffServ Type 54 : IP ToS value = 216"  
        ::= { qosDiffServTypeGroup 55 }
    
    qosDiffServType55 OBJECT-TYPE
        SYNTAX  INTEGER (0..7)
        MAX-ACCESS   read-write
        STATUS       current
        DESCRIPTION
           "DiffServ Type 55 : IP ToS value = 220"  
        ::= { qosDiffServTypeGroup 56 }
        
    qosDiffServType56 OBJECT-TYPE
        SYNTAX  INTEGER (0..7)
        MAX-ACCESS   read-write
        STATUS       current
        DESCRIPTION
           "DiffServ Type 56 : IP ToS value = 224"  
        ::= { qosDiffServTypeGroup 57 }
    
    qosDiffServType57 OBJECT-TYPE
        SYNTAX  INTEGER (0..7)
        MAX-ACCESS   read-write
        STATUS       current
        DESCRIPTION
           "DiffServ Type 57 : IP ToS value = 228"  
        ::= { qosDiffServTypeGroup 58 }
        
    qosDiffServType58 OBJECT-TYPE
        SYNTAX  INTEGER (0..7)
        MAX-ACCESS   read-write
        STATUS       current
        DESCRIPTION
           "DiffServ Type 58 : IP ToS value = 232"  
        ::= { qosDiffServTypeGroup 59 }
    
    qosDiffServType59 OBJECT-TYPE
        SYNTAX  INTEGER (0..7)
        MAX-ACCESS   read-write
        STATUS       current
        DESCRIPTION
           "DiffServ Type 59 : IP ToS value = 236"  
        ::= { qosDiffServTypeGroup 60 }
        
    qosDiffServType60 OBJECT-TYPE
        SYNTAX  INTEGER (0..7)
        MAX-ACCESS   read-write
        STATUS       current
        DESCRIPTION
           "DiffServ Type 60 : IP ToS value = 240"  
        ::= { qosDiffServTypeGroup 61 }
    
    qosDiffServType61 OBJECT-TYPE
        SYNTAX  INTEGER (0..7)
        MAX-ACCESS   read-write
        STATUS       current
        DESCRIPTION
           "DiffServ Type 61 : IP ToS value = 244"  
        ::= { qosDiffServTypeGroup 62 }     
    
    qosDiffServType62 OBJECT-TYPE
        SYNTAX  INTEGER (0..7)
        MAX-ACCESS   read-write
        STATUS       current
        DESCRIPTION
           "DiffServ Type 62 : IP ToS value = 248"  
        ::= { qosDiffServTypeGroup 63 }                                 
    
    qosDiffServType63 OBJECT-TYPE
        SYNTAX  INTEGER (0..7)
        MAX-ACCESS   read-write
        STATUS       current
        DESCRIPTION
           "DiffServ Type 63 : IP ToS value = 252"  
        ::= { qosDiffServTypeGroup 64 }    
    
    -- ------------------------------------------------------------------ 
    -- TOS-Mode
    -- ------------------------------------------------------------------
        
    qosTOSGroup OBJECT IDENTIFIER ::= { qosDiffServTOS 3 }
    
    qosTOSType00 OBJECT-TYPE
        SYNTAX  INTEGER (0..7)
    	MAX-ACCESS   read-write
        STATUS       current
        DESCRIPTION
           "TOS 0"  
        ::= { qosTOSGroup 1 }
    
    qosTOSType01 OBJECT-TYPE
        SYNTAX  INTEGER (0..7)
    	MAX-ACCESS   read-write
        STATUS       current
        DESCRIPTION
           "TOS 01"  
        ::= { qosTOSGroup 2 }
        
    qosTOSType02 OBJECT-TYPE
        SYNTAX  INTEGER (0..7)
        MAX-ACCESS   read-write
        STATUS       current
        DESCRIPTION
           "TOS 02"  
        ::= { qosTOSGroup 3 }
    
    qosTOSType03 OBJECT-TYPE
        SYNTAX  INTEGER (0..7)
        MAX-ACCESS   read-write
        STATUS       current
        DESCRIPTION
           "TOS 03"  
        ::= { qosTOSGroup 4 }
        
    qosTOSType04 OBJECT-TYPE
        SYNTAX  INTEGER (0..7)
        MAX-ACCESS   read-write
        STATUS       current
        DESCRIPTION
           "TOS 04"  
        ::= { qosTOSGroup 5 }
    
    qosTOSType05 OBJECT-TYPE
        SYNTAX  INTEGER (0..7)
        MAX-ACCESS   read-write
        STATUS       current
        DESCRIPTION
           "TOS 05"  
        ::= { qosTOSGroup 6 }
        
    qosTOSType06 OBJECT-TYPE
        SYNTAX  INTEGER (0..7)
        MAX-ACCESS   read-write
        STATUS       current
        DESCRIPTION
           "TOS 06"  
        ::= { qosTOSGroup 7 }
    
    qosTOSType07 OBJECT-TYPE
        SYNTAX  INTEGER (0..7)
        MAX-ACCESS   read-write
        STATUS       current
        DESCRIPTION
           "TOS 07"  
        ::= { qosTOSGroup 8 }

    qosAclPrioritySettings     OBJECT IDENTIFIER ::= { companyQoSGroup 8 }

    -- ------------------------------------------------------------------
    -- ipv4aclQosTable
    -- ------------------------------------------------------------------

    ipv4aclQosTable  OBJECT-TYPE
        SYNTAX     SEQUENCE OF Ipv4AclQosEntry 
        MAX-ACCESS not-accessible
        STATUS     current
        DESCRIPTION
           "A list of priority by acl setting."

        ::= { qosAclPrioritySettings 1 }

    ipv4aclQosEntry OBJECT-TYPE
        SYNTAX     Ipv4AclQosEntry
        MAX-ACCESS not-accessible
        STATUS     current
        DESCRIPTION
              "A list of priority by acl setting entry."

        INDEX { ipv4aclQosIndex }
        ::= { ipv4aclQosTable 1 }

    Ipv4AclQosEntry  ::= 
            SEQUENCE {
              ipv4aclQosIndex          Integer32,
              ipv4aclQosType           INTEGER,
              ipv4aclQosMACAddr        MacAddress,
              ipv4aclQosIPAddr         IpAddress,
              ipv4aclQosTCPUDPPort     Integer32,
              ipv4aclQosVlanID         Integer32,
              ipv4aclQosProtocol       Integer32,
              ipv4aclQosAssignClass    INTEGER,
              ipv4aclQosStatus         RowStatus
              }
              
    ipv4aclQosIndex OBJECT-TYPE
       SYNTAX       Integer32 (1..65535)
       MAX-ACCESS   read-only
       STATUS       current
       DESCRIPTION
         "Index of priority by acl setting." 
        ::= { ipv4aclQosEntry  1 }
        
    ipv4aclQosType OBJECT-TYPE
       SYNTAX       INTEGER { mac(0), ip(1), tcp(2), udp(3), vlanid(4), protocol(5) }
       MAX-ACCESS   read-write
       STATUS       current
       DESCRIPTION
         "Type of priority by acl setting." 
        ::= { ipv4aclQosEntry  2 }

    ipv4aclQosMACAddr OBJECT-TYPE 
       SYNTAX      MacAddress 
       MAX-ACCESS  read-write
       STATUS      current 
       DESCRIPTION 
           "Dst MAC of priority by acl setting." 
        ::= { ipv4aclQosEntry  3 } 
        
        
    ipv4aclQosIPAddr OBJECT-TYPE 
       SYNTAX      IpAddress
       MAX-ACCESS  read-write
       STATUS      current 
       DESCRIPTION 
           "Dst IP of priority by acl setting" 
        ::= { ipv4aclQosEntry 4 } 
        
    ipv4aclQosTCPUDPPort OBJECT-TYPE
       SYNTAX       Integer32 (1..65535)
       MAX-ACCESS   read-write
       STATUS       current
       DESCRIPTION
         "Dst TCP/UDP port of priority by acl setting" 
        ::= { ipv4aclQosEntry  5 }
        
    ipv4aclQosVlanID OBJECT-TYPE
       SYNTAX       Integer32 (1..4094)
       MAX-ACCESS   read-write
       STATUS       current
       DESCRIPTION
         "VLAN ID of priority by acl setting" 
        ::= { ipv4aclQosEntry  6 }

    ipv4aclQosProtocol OBJECT-TYPE
       SYNTAX       Integer32 (1..255)
       MAX-ACCESS   read-write
       STATUS       current
       DESCRIPTION
         "Ip protocol number of priority by acl setting" 
        ::= { ipv4aclQosEntry  7 }
        
    ipv4aclQosAssignClass OBJECT-TYPE
       SYNTAX       INTEGER  { class0(0), class1(1), class2(2), class3(3) }
       MAX-ACCESS   read-write
       STATUS       current
       DESCRIPTION
         "Be mapped class of priority by acl setting." 
        ::= { ipv4aclQosEntry  8 }
        
    ipv4aclQosStatus OBJECT-TYPE
       SYNTAX RowStatus
       MAX-ACCESS read-write
       STATUS current
       DESCRIPTION
         "Status of priority by acl setting."
       ::= { ipv4aclQosEntry 9 }    


    -- ------------------------------------------------------------------
    -- aclQosTable
    -- ------------------------------------------------------------------       
       
    aclQosTable  OBJECT-TYPE
        SYNTAX     SEQUENCE OF AclQosEntry 
        MAX-ACCESS not-accessible
        STATUS     current
        DESCRIPTION
           "A list of priority by acl setting."

        ::= { qosAclPrioritySettings 2 }

    aclQosEntry OBJECT-TYPE
        SYNTAX     AclQosEntry
        MAX-ACCESS not-accessible
        STATUS     current
        DESCRIPTION
              "A list of priority by acl setting entry."

        INDEX { aclQosIndex }
        ::= { aclQosTable 1 }

    AclQosEntry  ::= 
            SEQUENCE {
              aclQosIndex          Integer32,
              aclQosType           INTEGER,
              aclQosMACAddr        MacAddress,
              aclQosIPAddr         IpAddress,
              aclQosIPv6Addr       Ipv6Address,
              aclQosTCPUDPPort     Integer32,
              aclQosVlanID         Integer32,
              aclQosProtocol       Integer32,
--start DLINK-METRO-LIKE-R25QOS-BY-IPV6-TC-ACL
              aclQosIP6TC          Integer32,
--end DLINK-METRO-LIKE-R25QOS-BY-IPV6-TC-ACL
              aclQosAssignClass    INTEGER,
              aclQosStatus         RowStatus
              }
              
    aclQosIndex OBJECT-TYPE
       SYNTAX       Integer32 (1..65535)
       MAX-ACCESS   read-only
       STATUS       current
       DESCRIPTION
         "Index of priority by acl setting." 
        ::= { aclQosEntry  1 }
        
    aclQosType OBJECT-TYPE
       SYNTAX       INTEGER { mac(0), ip(1), tcp(2), udp(3), vlanid(4), protocol(5), ipv6(6), ipv6traffic-class(7) }
       MAX-ACCESS   read-write
       STATUS       current
       DESCRIPTION
         "Type of priority by acl setting." 
        ::= { aclQosEntry  2 }

    aclQosMACAddr OBJECT-TYPE 
       SYNTAX      MacAddress 
       MAX-ACCESS  read-write
       STATUS      current 
       DESCRIPTION 
           "Dst MAC of priority by acl setting." 
        ::= { aclQosEntry  3 } 
        
        
    aclQosIPAddr OBJECT-TYPE 
       SYNTAX      IpAddress
       MAX-ACCESS  read-write
       STATUS      current 
       DESCRIPTION 
           "Dst IP of priority by acl setting" 
        ::= { aclQosEntry 4 } 
    
    aclQosIPv6Addr OBJECT-TYPE 
       SYNTAX      Ipv6Address
       MAX-ACCESS  read-write
       STATUS      current 
       DESCRIPTION 
           "Dst IP of priority by acl setting. " 
        ::= { aclQosEntry 5 }
        
    aclQosTCPUDPPort OBJECT-TYPE
       SYNTAX       Integer32 (1..65535)
       MAX-ACCESS   read-write
       STATUS       current
       DESCRIPTION
         "Dst TCP/UDP port of priority by acl setting" 
        ::= { aclQosEntry  6 }
        
    aclQosVlanID OBJECT-TYPE
       SYNTAX       Integer32 (1..4094)
       MAX-ACCESS   read-write
       STATUS       current
       DESCRIPTION
         "VLAN ID of priority by acl setting" 
        ::= { aclQosEntry  7 }

    aclQosProtocol OBJECT-TYPE
       SYNTAX       Integer32 (1..255)
       MAX-ACCESS   read-write
       STATUS       current
       DESCRIPTION
         "Ip protocol number of priority by acl setting" 
        ::= { aclQosEntry  8 }

--start DLINK-METRO-LIKE-R25QOS-BY-IPV6-TC-ACL
    aclQosIP6TC OBJECT-TYPE
       SYNTAX       Integer32 (0..255)
       MAX-ACCESS   read-write
       STATUS       current
       DESCRIPTION
         "Ipv6 Traffic Class number of priority by acl setting" 
        ::= { aclQosEntry  10 }
--end DLINK-METRO-LIKE-R25QOS-BY-IPV6-TC-ACL

    aclQosAssignClass OBJECT-TYPE
       SYNTAX       INTEGER  { class0(0), class1(1), class2(2), class3(3) }
       MAX-ACCESS   read-write
       STATUS       current
       DESCRIPTION
         "Be mapped class of priority by acl setting." 
        ::= { aclQosEntry  98 }
        
    aclQosStatus OBJECT-TYPE
       SYNTAX RowStatus
       MAX-ACCESS read-write
       STATUS current
       DESCRIPTION
         "Status of priority by acl setting."
       ::= { aclQosEntry 99 }         
 		-- ----------------------------------------------------------
		-- The companyTrafficMgmt Groups
		-- ----------------------------------------------------------      		

        -- Bandwidth Control Group --------------------------------------------- --
		bandwidthCtrlSettings  OBJECT IDENTIFIER ::= { companyTrafficMgmt 1 }
                
        bandwidthCtrlTable OBJECT-TYPE 
           SYNTAX      SEQUENCE OF BandwidthCtrlEntry 
           MAX-ACCESS  not-accessible 
           STATUS      current 
           DESCRIPTION 
              "A table to control the rate limiting parameters 
               either for the entire switch or for each interface in the switch."
           ::= { bandwidthCtrlSettings 2 }
        
        bandwidthCtrlEntry OBJECT-TYPE 
           SYNTAX      BandwidthCtrlEntry 
           MAX-ACCESS  not-accessible 
           STATUS      current 
           DESCRIPTION 
              "An entry appears in this table for each physical
               interface in the switch."
           INDEX { bandwidthCtrlIndex }
           ::= { bandwidthCtrlTable 1 }
           
        BandwidthCtrlEntry ::= 
           SEQUENCE { 
              bandwidthCtrlIndex 
                 Integer32, 
              bandwidthCtrlTxThreshold
                 Integer32,
              bandwidthCtrlRxThreshold
                 Integer32             
          }
        
        bandwidthCtrlIndex OBJECT-TYPE 
           SYNTAX      Integer32
           MAX-ACCESS  read-only 
           STATUS      current 
           DESCRIPTION 
              "The interface index for which the configuration in this 
               entry applies."
           ::= { bandwidthCtrlEntry 1 }
            
        
        bandwidthCtrlTxThreshold OBJECT-TYPE
           SYNTAX      Integer32 (0 | 64..1024000)
           MAX-ACCESS  read-write
           STATUS      current
           DESCRIPTION
              "Configures interface Rate Limit (Packet that can be transferred
              on a port at a particular second).
        
              This object's value will take effect on the interface speed. Based
              on the operating speed of the port, the rate limit will be applied.
              This value can also be affected by the metering. A value of zero(0)
              disable rate limiting i.e. sets the port to full speed. The value can 
              be set between 64~102400(Kbits per second) in FE port, 64~1024000
              (Kbits per second) in GE port."
        
           ::= { bandwidthCtrlEntry 2 }        
        
        bandwidthCtrlRxThreshold OBJECT-TYPE 
           SYNTAX      Integer32 (0 | 64..1024000)
           MAX-ACCESS  read-write 
           STATUS      current 
           DESCRIPTION 
              "Allows to configure the limiting value for the maximum number
               of receive packets that can be transmitted per second over this 
               interface. Setting this object to the value zero disables rate 
               limiting for receive packets on this interface. The value that
               can be set for this object is limited by the underlying hardware. 
               The value can be set between 64~102400(Kbits per second) in FE 
               port,  64~1024000(Kbits per second) in GE port."
        
           ::= { bandwidthCtrlEntry 3}               


       
       -- Traffic Control Group --------------------------------------------- --
       
       trafficCtrlSettings OBJECT IDENTIFIER ::= { companyTrafficMgmt 4 }
       
	   trafficCtrlTrap OBJECT-TYPE
          SYNTAX INTEGER {
          		none(0),
          		stormOccurred(1),
          		stormCleared(2),
           		both(3)
          }
          MAX-ACCESS   read-write
          STATUS       current
          DESCRIPTION
              "The trap setting of traffic control."
          ::= { trafficCtrlSettings 1 }

       
	   trafficCtrlTable OBJECT-TYPE 
          SYNTAX      SEQUENCE OF TrafficCtrlEntry
          MAX-ACCESS  not-accessible 
          STATUS      current 
          DESCRIPTION 
              "The traffic control table."
          ::= { trafficCtrlSettings 2 }

       trafficCtrlEntry OBJECT-TYPE 
          SYNTAX      TrafficCtrlEntry
          MAX-ACCESS  not-accessible 
          STATUS      current 
          DESCRIPTION 
              "The traffic control entry."
          INDEX { trafficCtrlIndex }
          ::= { trafficCtrlTable 1 }

       TrafficCtrlEntry ::= 
          SEQUENCE { 
             trafficCtrlIndex 
                Integer32, 
             trafficCtrlActionMode
                INTEGER, 
             trafficCtrlType
                INTEGER,
             trafficCtrlThreshold
             	Integer32,
             trafficCtrlCountDown
             	Integer32,
             trafficCtrlTimeInterval
             	Integer32
       }
       
       trafficCtrlIndex OBJECT-TYPE 
           SYNTAX      Integer32 (1..65535)
           MAX-ACCESS  read-only 
           STATUS      current 
           DESCRIPTION 
              "The traffic control index."
           ::= { trafficCtrlEntry 1 }

        trafficCtrlActionMode OBJECT-TYPE
           SYNTAX INTEGER {
           		drop(0),
           		shutdown(1)
           }
           MAX-ACCESS   read-write
           STATUS       current
           DESCRIPTION
               "The action mode of traffic control."
           ::= { trafficCtrlEntry 2 }
   
   
        trafficCtrlType OBJECT-TYPE
           SYNTAX INTEGER {
           		none(0),
           		b(1),
           		m(2),
           		mb(3),
           		u(4),
           		ub(5),
           		um(6),
           		umb(7)
           }
           MAX-ACCESS   read-write
           STATUS       current
           DESCRIPTION
               "The control type of traffic control.
               (b: Broadcast, m: Multicast, u: Unknown Unicast)"
           ::= { trafficCtrlEntry 3 }

        trafficCtrlThreshold OBJECT-TYPE
           SYNTAX       Integer32 (1..102400)  
           MAX-ACCESS   read-write
           STATUS       current
           DESCRIPTION
               "The threshold of traffic control."
           ::= { trafficCtrlEntry 4 }
 
        trafficCtrlCountDown OBJECT-TYPE
           SYNTAX       Integer32 (0..30)  
           MAX-ACCESS   read-write
           STATUS       current
           DESCRIPTION
               "The count down value of traffic control."
           ::= { trafficCtrlEntry 5 }   
              
        trafficCtrlTimeInterval OBJECT-TYPE
           SYNTAX       Integer32 (5..30)  
           MAX-ACCESS   read-write
           STATUS       current
           DESCRIPTION
               "The time interval of traffic control."
           ::= { trafficCtrlEntry 6 } 
           
       
    -- ------------------------------------------------------------------ 
    -- companySecurity
    -- ------------------------------------------------------------------
    
    -- Trusted Host
    
    securityTrustedHost       OBJECT IDENTIFIER ::= { companySecurity 1 }
    
    trustedHostStatus OBJECT-TYPE 
       SYNTAX      INTEGER {
                      enabled      (1),
                      disabled	   (2)
                   }
       MAX-ACCESS  read-write 
       STATUS      current 
       DESCRIPTION 
           "This object indicates trusted host function is enabled or disabled. 
                When trusted host function is enabled, D-Link Smart Switches will 
                only allow hosts which you trust to access and control the switch.
                Your local host IP Addresses must be one of the IP Addresses to 
                avoid disconnection." 
    
       DEFVAL  { disabled }
       ::= { securityTrustedHost 1 }
    
    
    ipv4trustedHostTable OBJECT-TYPE
       SYNTAX      SEQUENCE OF Ipv4TrustedHostEntry
       MAX-ACCESS  not-accessible
       STATUS      obsolete
       DESCRIPTION
           "A table to configure trusted host in the system."
       ::= { securityTrustedHost 2 }
    
    ipv4trustedHostEntry OBJECT-TYPE
       SYNTAX      Ipv4TrustedHostEntry
       MAX-ACCESS  not-accessible
       STATUS      obsolete
       DESCRIPTION
           "Each entry in this table represents rules for particular
            trusted host."
       INDEX { ipv4trustedHostIpAddr, ipv4trustedHostIpMask }
       ::= { ipv4trustedHostTable 1 }
    
    Ipv4TrustedHostEntry ::=
       SEQUENCE {
          ipv4trustedHostIpAddr
             IpAddress,
          ipv4trustedHostIpMask
             IpAddress,
          ipv4trustedHostRowStatus
             RowStatus
     }
    
    ipv4trustedHostIpAddr OBJECT-TYPE
       SYNTAX      IpAddress
       MAX-ACCESS  read-only
       STATUS      obsolete
       DESCRIPTION
            "The IP address of host you allow to access to D-Link Smart 
             Switch.
             Your local host IP Addresses must be one of the IP Addresses 
             to avoid disconnection."
       ::= { ipv4trustedHostEntry 1 }
    
    ipv4trustedHostIpMask OBJECT-TYPE
       SYNTAX      IpAddress
       MAX-ACCESS  read-only
       STATUS      obsolete
       DESCRIPTION
            "Used to mask with IP address, it allow you set a subnet as a 
            trusted host entry."        
       ::= { ipv4trustedHostEntry 2 }
    
    ipv4trustedHostRowStatus OBJECT-TYPE
       SYNTAX      RowStatus
       MAX-ACCESS  read-create
       STATUS      obsolete
       DESCRIPTION
             "The status of an entry in the Trusted Host Table.  Only a subset
             of the rowstatus variables (active, createAndGo, destroy) 
             are available."
       ::= { ipv4trustedHostEntry 3 }
       

    -- ipv6 
    trustedHostTable OBJECT-TYPE
       SYNTAX      SEQUENCE OF TrustedHostEntry
       MAX-ACCESS  not-accessible
       STATUS      current
       DESCRIPTION
           "A table to configure trusted host for in the system."
       ::= { securityTrustedHost 3 }
    
    trustedHostEntry OBJECT-TYPE
       SYNTAX      TrustedHostEntry
       MAX-ACCESS  not-accessible
       STATUS      current
       DESCRIPTION
           "Each entry in this table represents rules for particular
            trusted host."
       INDEX { trustedHostIPType, trustedHostIpAddr, trustedHostIpMask }
       ::= { trustedHostTable 1 }
    
    TrustedHostEntry ::=
       SEQUENCE {
          trustedHostIPType
             INTEGER,
          trustedHostIpAddr
             Ipv6Address,
          trustedHostIpMask
             Ipv6Address,
          trustedHostRowStatus
             RowStatus
     }
    
    trustedHostIPType OBJECT-TYPE
        SYNTAX    INTEGER {
               iPv4             (1),
               iPv6	            (2)
            }
           MAX-ACCESS  read-only
           STATUS      current
           DESCRIPTION
           "Type of IP interface."
        ::= { trustedHostEntry 1 }
    
    trustedHostIpAddr OBJECT-TYPE
       SYNTAX      Ipv6Address
       MAX-ACCESS  read-only
       STATUS      current
       DESCRIPTION
            "The IP address of host you allow to access to D-Link Smart 
             Switch.
             Your local host IPv4/6 Addresses must be one of the IP Addresses 
             to avoid disconnection."
       ::= { trustedHostEntry 2 }
    
    trustedHostIpMask OBJECT-TYPE
       SYNTAX      Ipv6Address
       MAX-ACCESS  read-only
       STATUS      current
       DESCRIPTION
            "Used to mask with IPv4/6 address, it allow you set a subnet as a 
            trusted host entry."        
       ::= { trustedHostEntry 3 }
    
    trustedHostRowStatus OBJECT-TYPE
       SYNTAX      RowStatus
       MAX-ACCESS  read-create
       STATUS      current
       DESCRIPTION
             "The status of an entry in the Trusted Host Table.  Only a subset
             of the rowstatus variables (active, createAndGo, destroy) 
             are available."
       ::= { trustedHostEntry 4 }
    
       

    securityARPSpoofPrevent        OBJECT IDENTIFIER ::= { companySecurity 3}

	-- aRPSpoofPrevent Control Table
	
	aRPSpoofPreventTable OBJECT-TYPE 
	   SYNTAX      SEQUENCE OF ARPSpoofPreventEntry 
	   MAX-ACCESS  not-accessible 
	   STATUS      current 
	   DESCRIPTION 
	      "A table to control ARP Spoofing prevention for the entire 
	       switch or for each interface in the switch."
	   ::= { securityARPSpoofPrevent 1 }
	
	aRPSpoofPreventEntry OBJECT-TYPE 
	   SYNTAX      ARPSpoofPreventEntry 
	   MAX-ACCESS  not-accessible 
	   STATUS      current 
	   DESCRIPTION 
	       "An entry appears in this table for each interface 
	        in the system."
	   INDEX { aRPSpoofPreventIpAddr }
	   ::= { aRPSpoofPreventTable 1 }
	
	ARPSpoofPreventEntry ::=
	   SEQUENCE {
	      aRPSpoofPreventIpAddr
	         IpAddress,
	      aRPSpoofPreventMacAddress
	         MacAddress,
	      aRPSpoofPreventPortList
	         PortList,
	      aRPSpoofPreventRowStatus
	         RowStatus   
	   }
	 
	 
	aRPSpoofPreventIpAddr OBJECT-TYPE
	   SYNTAX      IpAddress
	   MAX-ACCESS  not-accessible
	   STATUS      current
	   DESCRIPTION
	       "Specifies either the Network or Host address from which the switch
	        can be managed.
	        An address 0.0.0.0 indicates 'Any Manager'."
	   ::= { aRPSpoofPreventEntry 1 }
	
	
	aRPSpoofPreventMacAddress OBJECT-TYPE 
	   SYNTAX      MacAddress
	   MAX-ACCESS  read-write
	   STATUS      current 
	   DESCRIPTION 
	      "Ethernet Mac Address."
	      
	   DEFVAL  { '000102030405'h }
	   ::= { aRPSpoofPreventEntry 2 }
	
	aRPSpoofPreventPortList OBJECT-TYPE
	   SYNTAX       PortList
	   MAX-ACCESS   read-write
	   STATUS       current
	   DESCRIPTION
	       "Specifies the port numbers through which the authorized manager can
	        access the switch. 
	
	        By default the authorized manager is allowed to access the switch 
	        through all the ports.
	
	        If a set of ports are configured in the 'PortList', the manager can
	        access the switch only through the configured ports."
	   ::= { aRPSpoofPreventEntry 3 }
	
	aRPSpoofPreventRowStatus OBJECT-TYPE
	   SYNTAX      RowStatus
	   MAX-ACCESS  read-create
	   STATUS      current
	   DESCRIPTION
	      "This object indicates the status of this entry."
	   ::= { aRPSpoofPreventEntry 4 }

                      
    -- ------------------------------------------------------------------ 
    -- companySecurity
    -- ------------------------------------------------------------------
    
    securitySSL       OBJECT IDENTIFIER ::= { companySecurity 5 }

    sslSecurityHttpStatus OBJECT-TYPE 
       SYNTAX       INTEGER {
                    enable(1),
                    disable(2)
                    }
       MAX-ACCESS  read-write 
       STATUS      current 
       DESCRIPTION 
          "This object is for enabling or disabling secure HTTP in the system."
    
       DEFVAL  { disable } 
       ::= { securitySSL 1 }
       
    sslCiphers                  OBJECT IDENTIFIER ::= { securitySSL 2 }
       
    sslCipherSuiteList OBJECT-TYPE
      SYNTAX  BITS {
            rsa-null-md5(0),
            rsa-null-sha(1),
            rsa-des-sha(2),
            rsa-3des-sha(3),
            dh-rsa-des-sha(4),
            dh-rsa-3des-sha(5),
            rsa-exp1024-des-sha(6)
     }

      MAX-ACCESS read-write
      STATUS current
      DESCRIPTION
      
         "This object is to configure the cipher-suites list."

   ::= { sslCiphers 1}
   

                      
    -- ------------------------------------------------------------------ 
    -- companySecurity
    -- ------------------------------------------------------------------
    
    securitySSH       OBJECT IDENTIFIER ::= { companySecurity 8 }
       
    sshSecurityStatus  OBJECT-TYPE
    SYNTAX      INTEGER {
                enable(1),
                disable(2)
                } 
    MAX-ACCESS  read-write
    STATUS      current
    DESCRIPTION
        "This object is for enabling or disabling ssh in the system."
    
    DEFVAL  { disable }
    ::= { securitySSH 1}
  
sshMaxAuthFailAttempts OBJECT-TYPE
	SYNTAX INTEGER (2..20)
	MAX-ACCESS read-write
	STATUS current
	DESCRIPTION
		"This object indicates the max auth fail retry attempt times."
	::= {securitySSH 2}

sshSessionKeyRekeying OBJECT-TYPE
	SYNTAX INTEGER {
		never(0),
		ten-min(1),
		thirty-min(2),
		sixty-min(3)
		}
	MAX-ACCESS read-write
	STATUS current
	DESCRIPTION
		"This object indicates one SSH session rekey time interval."
	::= {securitySSH 3}

sshMaxSession OBJECT-TYPE
	SYNTAX INTEGER (1..8)
	MAX-ACCESS read-write
	STATUS current
	DESCRIPTION
		"This object indicates max SSH session number supported in system."
	::= {securitySSH 4}

sshConnectionTimeout OBJECT-TYPE
	SYNTAX INTEGER (120..600)
	MAX-ACCESS read-write
	STATUS current
	DESCRIPTION
		"This object indicates SSH connection timeout value."
	::= {securitySSH 5}

--************************************************************************	
-- SSH encryption algorithm group configuration
--************************************************************************
sshAuthenMethodPassWordAdmin OBJECT-TYPE
	SYNTAX INTEGER {
                enable(1),
                disable(2)
		}
	MAX-ACCESS read-write
	STATUS current
	DESCRIPTION
		"The object indicates authen method password is enabled or disabled."
	::= {securitySSH 6}

sshAuthenMethodPubKeyAdmin OBJECT-TYPE
	SYNTAX INTEGER {
                enable(1),
                disable(2)
		}
	MAX-ACCESS read-write
	STATUS current
	DESCRIPTION
		"The object indicates authen method public-key is enabled or disabled."
	::= {securitySSH 7}	

sshAuthenMethodHostKeyAdmin OBJECT-TYPE
	SYNTAX INTEGER {
                enable(1),
                disable(2)
		}
	MAX-ACCESS read-write
	STATUS current
	DESCRIPTION
		"The object indicates authen method host-key is enabled or disabled."
	::= {securitySSH 8}

    sshCipherSuiteList OBJECT-TYPE
        SYNTAX  BITS {
        tripleDESCBC(0)
        }
     
    MAX-ACCESS read-only
    STATUS current
    DESCRIPTION
      
    "This object is to configure the cipher-suites list."
          
	::= { securitySSH 9}
    
    sshMacSuiteList OBJECT-TYPE
        SYNTAX  BITS {
            hMAC-SHA1(0),
            hMAC-MD5(1)
        }
    MAX-ACCESS read-write
    STATUS current
    DESCRIPTION

    "This object is to configure the MAC-list."
            
	::= { securitySSH 10}


sshPublKeyRSAAdmin OBJECT-TYPE
	SYNTAX INTEGER {
		enabled(1),	
		disabled(2)
		}
	MAX-ACCESS read-write
	STATUS current
	DESCRIPTION
		"The object indicates Public key generating algorithm RSA is enabled or disabled."
	::= {securitySSH 11}

--************************************************************************	
-- SSH User Auth Info.
--************************************************************************
	    sshUserInfoTable OBJECT-TYPE
	       SYNTAX      SEQUENCE OF SshUserInfoEntry
	       MAX-ACCESS  not-accessible
	       STATUS      current
	       DESCRIPTION
	           "A table to configure SSH user auth in the system."
	       ::= { securitySSH 12 }
	    
	    sshUserInfoEntry OBJECT-TYPE
	       SYNTAX      SshUserInfoEntry
	       MAX-ACCESS  not-accessible
	       STATUS      current
	            DESCRIPTION
	                "An entry to configure user auth in the system."     
	       INDEX { sshUserInfoID }
	       ::= { sshUserInfoTable 1 }      
	       
	    SshUserInfoEntry ::=
	       SEQUENCE { 
	          	sshUserInfoID   		Integer32,      
	          	sshUserInfoUserName		DisplayString,
	          	sshUserInfoAuth         INTEGER,          	          	
	            sshUserInfoHostName		DisplayString,
	            sshUserInfoHostIp		IpAddress            
	     } 
	
	    sshUserInfoID OBJECT-TYPE 
	       SYNTAX      Integer32 (1..8)
	       MAX-ACCESS  read-only 
	       STATUS      current 
	            DESCRIPTION
	                "The Schedule identifier. The maximum number of Schedule entry is 
                     the number of ports supported PoE function.
	                 The value must be between 1 and 8."
	       ::= { sshUserInfoEntry 1 }
	    
	    sshUserInfoUserName OBJECT-TYPE 
	       SYNTAX      DisplayString (SIZE(1..20))
	       MAX-ACCESS  read-only 
	       STATUS      current 
	            DESCRIPTION
	                "The ssh user name associated with the SSH suer Info. entry (e.g., `admin, user')."
	       ::= { sshUserInfoEntry 2}	       

		sshUserInfoAuth OBJECT-TYPE
			SYNTAX INTEGER {
			    publickey(4),
				password(2),				
				hostbased(1)
				}
			MAX-ACCESS read-write
			STATUS current
			DESCRIPTION
				"The object indicates which auth used by the user."
			::= {sshUserInfoEntry 3}	       

	    sshUserInfoHostName OBJECT-TYPE 
	       SYNTAX      DisplayString (SIZE(1..20))
	       MAX-ACCESS  read-write 
	       STATUS      current 
	            DESCRIPTION
	                "The ssh host name associated with the SSH suer Info. entry (e.g., `DUT1, DUT2')."
	       ::= { sshUserInfoEntry 4}
	         
		sshUserInfoHostIp  OBJECT-TYPE
			SYNTAX      IpAddress
			MAX-ACCESS  read-write
			STATUS      current
			DESCRIPTION 
			  "SSH HostBased IP Address of the system."
			::= { sshUserInfoEntry 5 }
			
 -- ----------------------------------------------------------
 -- The companySecurity Groups
 -- ----------------------------------------------------------      	
    securityPortSecurity                  OBJECT IDENTIFIER ::= { companySecurity 2 }
 -- Port Security Group --------------------------------------------- --
    
    portSecTable     OBJECT-TYPE
        SYNTAX SEQUENCE OF PortSecEntry
        MAX-ACCESS not-accessible
        STATUS current
        DESCRIPTION
            "A table to control port security features of the device."
        ::= { securityPortSecurity 1 }
        
    portSecEntry OBJECT-TYPE
        SYNTAX PortSecEntry
        MAX-ACCESS not-accessible
        STATUS current
        DESCRIPTION
            "An entry appears in port security table for each interface 
 	        in the system."
        INDEX { portSecIndex }
        ::= { portSecTable 1 }
  
    PortSecEntry ::= 
           SEQUENCE { 
              portSecIndex 
                 Integer32, 
              portSecState 
                 INTEGER, 
              portSecMLA 
                 Integer32             

-- start DLINK-METRO-LIKE-LOCK-ADDRESS-MODE
              ,
              portSecLockAddrMode
                 INTEGER
-- end DLINK-METRO-LIKE-LOCK-ADDRESS-MODE
          }
        
               
         portSecIndex OBJECT-TYPE 
           SYNTAX      Integer32 
           MAX-ACCESS  read-only 
           STATUS      current 
           DESCRIPTION 
              "The interface index for which the configuration in this 
               entry applies."
           ::= { portSecEntry 1 }
            
        
         portSecState OBJECT-TYPE
           SYNTAX INTEGER  {
        		  enabled (1), disabled (2)
            }
           MAX-ACCESS  read-write
           STATUS      current
           DESCRIPTION
              "Enable / disable port security admin state for the interface.
              
              A given ports' dynamic MAC address learning will be stopped such
              that the current source MAC addresses entered into the MAC address
              forwarding table can not be changed once the port security admin 
              state is enabled."
        
           ::= { portSecEntry 2 }
        
        
        portSecMLA OBJECT-TYPE 
           SYNTAX      Integer32 (0..64)
           MAX-ACCESS  read-write 
           STATUS      current 
           DESCRIPTION 
              "Configures interface port security maximum learning address
               numbers.
                              
               When given ports' admin state is enabled, allows forwarding 
               table learning address number. The number can be set 0 to 64.
               Note: Set value 0 means cannot learn MAC address."
        
           ::= {portSecEntry 3}

-- start DLINK-METRO-LIKE-LOCK-ADDRESS-MODE
         portSecLockAddrMode OBJECT-TYPE
           SYNTAX INTEGER  {
                            deleteOnReset (1), 
                            deleteOnTimeout (2),
                            permanent(3)
	}
           MAX-ACCESS  read-write
           STATUS      current
           DESCRIPTION
              "Configures port security lock address mode for the interface.

              deleteOnReset : The locked addresses will not age out until the Switch has been reset.
              deleteOnTimeout : The locked addresses will age out after the aging timer expires.
              Permanent : The locked addresses will not age out after the aging timer expires."

           ::= { portSecEntry 4 }

    portSecFDBPermanentTable     OBJECT-TYPE
        SYNTAX SEQUENCE OF PortSecFDBPermanentEntry
        MAX-ACCESS not-accessible
        STATUS current
        DESCRIPTION
            "A table to control port security FDB Permanent of the device."
        ::= { securityPortSecurity 2 }

    portSecFDBPermanentEntry OBJECT-TYPE
        SYNTAX PortSecFDBPermanentEntry
        MAX-ACCESS not-accessible
        STATUS current
        DESCRIPTION
            "An entry appears in port security table for each interface 
 	        in the system."
        INDEX { portSecFDBPermPort, portSecFDBPermIndex}
        ::= { portSecFDBPermanentTable 1 }
  
    PortSecFDBPermanentEntry ::= 
           SEQUENCE { 
	    portSecFDBPermIndex		INTEGER,
            portSecFDBPermVlanID        INTEGER,
            portSecFDBPermMac           MacAddress,
            portSecFDBPermPort          INTEGER
          }

        portSecFDBPermIndex OBJECT-TYPE
            SYNTAX INTEGER
            MAX-ACCESS read-only
            STATUS current
            DESCRIPTION
                "The index of the port security MAC entry."
            ::= { portSecFDBPermanentEntry 1 }

        portSecFDBPermVlanID OBJECT-TYPE
            SYNTAX INTEGER
            MAX-ACCESS read-only
            STATUS current
            DESCRIPTION
                "The VLAN ID of the port security MAC entry."
            ::= { portSecFDBPermanentEntry 2 }

         portSecFDBPermMac OBJECT-TYPE
           SYNTAX MacAddress
           MAX-ACCESS read-only
           STATUS current
           DESCRIPTION
               "The MAC address associated of the port security MAC entry."
           ::= { portSecFDBPermanentEntry 3 }

        portSecFDBPermPort OBJECT-TYPE
            SYNTAX INTEGER
            MAX-ACCESS read-only
            STATUS current
            DESCRIPTION
                "The forwarding port of the port security MAC entry."
            ::= { portSecFDBPermanentEntry 4 }
        
-- end DLINK-METRO-LIKE-LOCK-ADDRESS-MODE

 -- ----------------------------------------------------------
 -- The companyCableDiagnostic Groups
 -- ----------------------------------------------------------
 -- Cable Diagnostics Group --------------------------------------------- --

         cableDiagTable OBJECT-TYPE 
           SYNTAX SEQUENCE OF CableDiagEntry
           MAX-ACCESS  not-accessible
           STATUS      current 
           DESCRIPTION 
              "A table that contains the cable situation for each port."
           ::= {companyCableDiagnostic 1 }         
    
         cableDiagEntry OBJECT-TYPE 
           SYNTAX      CableDiagEntry  
           MAX-ACCESS  not-accessible
           STATUS      current 
           DESCRIPTION 
              "A list of cable situations for each port on the device."
            INDEX { cableDiagPortIndex }
            ::= { cableDiagTable 1 }

        CableDiagEntry ::= 
          SEQUENCE {
              cableDiagPortIndex
                  Integer32,
			  cableDiagPortType
				  INTEGER,
			  cableDiagLinkStatus
				  INTEGER,
			  cableDiagPair1Status
				  INTEGER,
			  cableDiagPair2Status
				  INTEGER,
			  cableDiagPair3Status
				  INTEGER,
			  cableDiagPair4Status
				  INTEGER,
		      cableDiagPair1Length
				  Integer32,
			  cableDiagPair2Length
				  Integer32,
			  cableDiagPair3Length
			      Integer32,
		      cableDiagPair4Length
			      Integer32,
		      cableDiagAction
				  INTEGER,
			  cableDiagStatus
				  INTEGER	                
            }


        cableDiagPortIndex OBJECT-TYPE
          SYNTAX      Integer32 
          MAX-ACCESS  read-only 
          STATUS      current 
          DESCRIPTION 
             "The interface index for which the configuration in this 
              entry applies."
          ::= { cableDiagEntry 1 }

        cableDiagPortType OBJECT-TYPE
          SYNTAX INTEGER {
    			fastEthernet(0),
    			gigaEthernet(1),
    			other(2)
    	    	}
          MAX-ACCESS  read-only
          STATUS current
          DESCRIPTION
            "Indicates the supported port data rate classification."
          ::= { cableDiagEntry 2 }

        cableDiagLinkStatus OBJECT-TYPE
          SYNTAX INTEGER {
               linkdown(0),
               linkup(1),
               other(2)
               }
          MAX-ACCESS  read-only
          STATUS  current
          DESCRIPTION
            "This object indicates the link status."
          ::= { cableDiagEntry 3 }


        cableDiagPair1Status OBJECT-TYPE
          SYNTAX INTEGER  {
               ok(0),
               open(1),
               short(2),
               open-short(3),
               crosstalk(4),
               unknown(5),
               count(6),
               no-cable(7),
               other(8)
            }
          MAX-ACCESS  read-only
          STATUS      current
          DESCRIPTION
              "Cable diagnostics pair 1 test result."
          ::= {cableDiagEntry 4 }

        cableDiagPair2Status OBJECT-TYPE
          SYNTAX INTEGER  {
               ok(0),
               open(1),
               short(2),
               open-short(3),
               crosstalk(4),
               unknown(5),
               count(6),
               no-cable(7),
               other(8)
            }
          MAX-ACCESS  read-only
          STATUS      current
          DESCRIPTION
             "Cable diagnostics pair 2 test result."
          ::= {cableDiagEntry 5 }

        cableDiagPair3Status OBJECT-TYPE
          SYNTAX INTEGER  {
               ok(0),
               open(1),
               short(2),
               open-short(3),
               crosstalk(4),
               unknown(5),
               count(6),
               no-cable(7),
               other(8)
          }
          MAX-ACCESS  read-only
          STATUS      current
          DESCRIPTION
             "Cable diagnostics pair 3 test result."
          ::= {cableDiagEntry 6 }

        cableDiagPair4Status OBJECT-TYPE
          SYNTAX INTEGER  {
               ok(0),
               open(1),
               short(2),
               open-short(3),
               crosstalk(4),
               unknown(5),
               count(6),
               no-cable(7),
               other(8)
          }
          MAX-ACCESS  read-only
          STATUS      current
          DESCRIPTION
             "Cable diagnostics pair 4 test result."
          ::= {cableDiagEntry 7}

        cableDiagPair1Length  OBJECT-TYPE 
          SYNTAX      Integer32 
          MAX-ACCESS  read-only
          STATUS      current
          DESCRIPTION
             "Cable Diagnostics pair 1 fault distance."
          ::= {cableDiagEntry 8}

        cableDiagPair2Length  OBJECT-TYPE 
          SYNTAX      Integer32 
          MAX-ACCESS  read-only
          STATUS      current
          DESCRIPTION
             "Cable diagnostics pair 2 fault distance."
          ::= {cableDiagEntry 9}

        cableDiagPair3Length  OBJECT-TYPE 
          SYNTAX      Integer32 
          MAX-ACCESS  read-only
          STATUS      current
          DESCRIPTION
             "Cable diagnostics pair 3 fault distance."
          ::= {cableDiagEntry 10}

        cableDiagPair4Length  OBJECT-TYPE 
          SYNTAX      Integer32 
          MAX-ACCESS  read-only
          STATUS      current
          DESCRIPTION
             "Cable diagnostics pair 4 fault distance."
          ::= {cableDiagEntry 11}

        cableDiagAction  OBJECT-TYPE 
          SYNTAX  INTEGER {
               action(1),
               processing(2),
               other(3)
               }
         MAX-ACCESS  read-write
         STATUS  current
         DESCRIPTION
            "Function to run the cable diagnostic on selected port.
             Can not detect fiber ports"
         ::= { cableDiagEntry 12} 


        cableDiagStatus  OBJECT-TYPE 
          SYNTAX  INTEGER {
               notrun(1),
               processing(2),
               lasttestok(3),
               lasttestfailed(4)
               }
          MAX-ACCESS  read-only
          STATUS  current
          DESCRIPTION
            "Indicates the status of cable diagnostics on the port.
            	not-run - cable diagnostics has never been run for this port
            	processing - cable diagnostics is currently running on the port
            	last-test-ok - the last cable diagnostics done on the port was successful
            	last-test-failed - the last cable diagnostics done on the port failed"
          ::= { cableDiagEntry 13 } 
    -- ------------------------------------------------------------------ 
    -- companyACLGroup
    -- ------------------------------------------------------------------

        -- ACL Profile Group --------------------------------------------------
        aclProfile       OBJECT IDENTIFIER ::= { companyACLGroup 1 }
        
        ipv4aclProfileTable OBJECT-TYPE 
           SYNTAX      SEQUENCE OF Ipv4AclProfileEntry
           MAX-ACCESS  not-accessible 
           STATUS      obsolete 
           DESCRIPTION 
               " A table to ACL profile .
               "
           ::= { aclProfile 1 }
        
        ipv4aclProfileEntry OBJECT-TYPE 
           SYNTAX      Ipv4AclProfileEntry
           MAX-ACCESS  not-accessible 
           STATUS      obsolete 
           DESCRIPTION 
               " Each entry in this table is a ACL profile.
                 Index to the table is ACL profile ID. "
           INDEX { ipv4aclProfileNo}
           ::= { ipv4aclProfileTable 1 }
           
        Ipv4AclProfileEntry ::= 
           SEQUENCE { 
              ipv4aclProfileNo 
                 Integer32, 
              ipv4aclProfileType 
                 INTEGER, 
              ipv4aclProfileRuleCount 
                 Integer32,  
              ipv4aclProfileMask 
                 OCTET STRING,
              ipv4aclProfileDstMacAddrMask 
                 MacAddress,          
              ipv4aclProfileSrcMacAddrMask 
                 MacAddress,         
              ipv4aclProfileIPProtocol  
                 INTEGER, 
              ipv4aclProfileIPProtocolMask  
                 OCTET STRING,  
              ipv4aclProfileDstIpAddrMask 
                 IpAddress, 
              ipv4aclProfileSrcIpAddrMask 
                 IpAddress,
              ipv4aclProfileDstPortMask
                 OCTET STRING,         
              ipv4aclProfileSrcPortMask
                 OCTET STRING,       
              ipv4aclProfileArpSenderMacAddrMask
                 MacAddress,      
              ipv4aclProfileArpSenderIpAddrMask
                IpAddress,
              ipv4aclProfileUdfOffsetMap
                 OCTET STRING,
              ipv4aclUdfOffsetChunk1
                 Integer32,
              ipv4aclUdfOffsetMask1
                 OCTET STRING,
              ipv4aclUdfOffsetChunk2
                 Integer32,
              ipv4aclUdfOffsetMask2
                 OCTET STRING,
              ipv4aclUdfOffsetChunk3
                 Integer32,
              ipv4aclUdfOffsetMask3
                 OCTET STRING,
              ipv4aclUdfOffsetChunk4
                 Integer32,
              ipv4aclUdfOffsetMask4
                 OCTET STRING,
              ipv4aclProfileStatus
                 RowStatus
          }
        
        ipv4aclProfileNo OBJECT-TYPE 
           SYNTAX      Integer32 (1..50)
           MAX-ACCESS  read-only 
           STATUS      obsolete 
           DESCRIPTION 
              "The ACL Profile ID. The ID 1 to 50 is user-defined ACL,
               and the ID more than 50 is reserved for system-defined ACL.
               The user only allow to create user-defined ACL ID.
               And system-defined ACL is read only."
           ::= { ipv4aclProfileEntry 1 }
        
        ipv4aclProfileType OBJECT-TYPE 
           SYNTAX   INTEGER  {
                          l2 (1),
                          l3 (2),
                          impb (3),
                          arpSP-permit(4),
                          arpSP-deny(5),
                          aclQos (8) ,
                          userDefined(9)
                       }
           MAX-ACCESS   read-write 
           STATUS      obsolete 
           DESCRIPTION 
              "The ACL Profile type, possible value are
              l2 (1) - for MAC-based rule, 
              l3 (2) - for IPv4-based rule,
              arpSP-permit(4) - for ARP Spoofing prevention entry,
              arpSP-deny(5) - for ARP Spoofing prevention entry,
              voiceVlan(6) - for Voice VLAN OUI entry.
              userDefined(9) - for User Defined entry.
              Note that only l2, l3 and userDefined could be set by user, 
              other is reserved for system to show information.
              "
           ::= { ipv4aclProfileEntry 2 }
        
        ipv4aclProfileRuleCount  OBJECT-TYPE 
           SYNTAX   Integer32 (0..65535)
           MAX-ACCESS   read-only 
           STATUS      obsolete 
           DESCRIPTION 
              "The number of rules in this profile."
           ::= { ipv4aclProfileEntry 3 }
              
              
        ipv4aclProfileMask OBJECT-TYPE 
           SYNTAX   OCTET STRING
           MAX-ACCESS   read-write  
           STATUS      obsolete 
           DESCRIPTION 
              "Indicate which field want to care in the packet.
               Turn on the following bits to select the following items
               Type        Item                   BIT         
               ------------------------------------------
               L2          DST-MAC                0 (LSB)        
               L2          SRC-MAC                1         
               L2          VID                    2         
               L2          8021P-PRIORITY         3         
               L2          ETHER-TYPE             4         
               L3          DSCP                   5         
               L3          ICMP-TYPE              6         
               L3          ICMP-CODE              7         
               L3          IGMP-TYPE              8         
               L3          DST-IP                 9         
               L3    	   SRC-IP                 10        
               L3    	   DST-PORT               11        
               L3          SRC-PORT               12        
               L3          TCPFLAG                13  
               ARP-SP      ARP-SENDER-MAC         14        
               ARP-SP      ARP-SENDER-IP          15 
               L3          TOS                    16
               UDF         UDF1                   17
               UDF         UDF2                   18
               UDF         UDF3                   19
               UDF         UDF4                   20
               L3v6        TRAFFIC-CLASS          21
               L3v6        DST-IPV6               22  
               L3v6        SRC-IPV6               23  (MSB)
               -------------------------------------------
               
               The value is in Hex format.
              "
           ::= { ipv4aclProfileEntry 4 }      
       

        ipv4aclProfileDstMacAddrMask OBJECT-TYPE 
           SYNTAX      MacAddress
           MAX-ACCESS  read-write 
           STATUS      obsolete 
           DESCRIPTION 
              "The ACL Profile destination MAC address mask.
               If DST-MAC is turn on in aclProfileMask, 
               it will work with its member rule field,aclL2RuleDstMacAddr, 
               to caculate a range of MAC address which is really care.
              "
           ::= { ipv4aclProfileEntry 5 }
        
        
        ipv4aclProfileSrcMacAddrMask OBJECT-TYPE 
           SYNTAX      MacAddress
           MAX-ACCESS  read-write 
           STATUS      obsolete 
           DESCRIPTION 
              "The ACL Profile source MAC address mask.
               If SRC-MAC is turn on in aclProfileMask, 
               it will work with its member rule field,aclL2RuleSrcMacAddr, 
               to caculate a range of MAC address which is really care.
              "
           ::= { ipv4aclProfileEntry 6 }
        
        
        ipv4aclProfileIPProtocol OBJECT-TYPE 
           SYNTAX   INTEGER  {  
                         none(0),   
           				 icmp(1),
           				 igmp(2),
           				 tcp(6),
          				 udp(17),
          				 icmpv6(58)
                         ,ipProtocolMask(256)
                        }
           MAX-ACCESS  read-write 
           STATUS      obsolete 
           DESCRIPTION 
              "Indicate which IP Protocol will be care in this profile.
               Only profile type is l3 can set the IP protocol.
               For others, this field will be none.
              "
           ::= { ipv4aclProfileEntry 7 } 
        ipv4aclProfileIPProtocolMask OBJECT-TYPE 
           SYNTAX      OCTET STRING
           MAX-ACCESS  read-write 
           STATUS      obsolete 
           DESCRIPTION 
              "The ACL Profile IP protocol mask.
               If aclProfileIPProtocol set to ipMask, this field will be refered.
               It will work with its member rule field,aclL3RuleProtocol, 
               to caculate a range of IP protocol which is really care.
               The value is in HEX format.
              "
           DEFVAL  { 'FF'h }   
           ::= { ipv4aclProfileEntry 8 }
        ipv4aclProfileDstIpAddrMask OBJECT-TYPE 
           SYNTAX      IpAddress
           MAX-ACCESS  read-write 
           STATUS      obsolete 
           DESCRIPTION 
              "The ACL Profile destination IP address mask.
               If DST-IP is turn on in aclProfileMask, 
               it will work with its member rule field,aclL3RuleDstIpAddr, 
               to caculate a range of IP address which is really care.
               The value is in HEX format, for example:
               '255.255.255.0' is presented to 'FFFFFF00'
              "
           DEFVAL  { 'FFFFFFFF'h }
           ::= { ipv4aclProfileEntry 9 }
        
        
        ipv4aclProfileSrcIpAddrMask OBJECT-TYPE 
           SYNTAX      IpAddress
           MAX-ACCESS  read-write 
           STATUS      obsolete 
           DESCRIPTION 
              "The ACL Profile source IP address mask.
               If SRC-IP is turn on in aclProfileMask, 
               it will work with its member rule field,aclL3RuleSrcIpAddr, 
               to caculate a range of IP address which is really care.
               The value is in HEX format, for example:
               '255.255.255.0' is presented to 'FFFFFF00'
              "
           DEFVAL  { 'FFFFFFFF'h }
           ::= { ipv4aclProfileEntry 10 }
        
        ipv4aclProfileDstPortMask OBJECT-TYPE 
           SYNTAX      OCTET STRING
           MAX-ACCESS  read-write 
           STATUS      obsolete 
           DESCRIPTION 
              "The ACL Profile UDP/TCP destination port mask.
               If DST-PORT is turn on in aclProfileMask, 
               it will work with its member rule field,aclL3RuleTcpUdpDstPort, 
               to caculate a range of destination port which is really care.
               The value is in HEX format.
              "
           DEFVAL  { 'FFFF'h }   
           ::= { ipv4aclProfileEntry 11 }
           
        
        ipv4aclProfileSrcPortMask OBJECT-TYPE 
           SYNTAX      OCTET STRING
           MAX-ACCESS  read-write 
           STATUS      obsolete 
           DESCRIPTION 
              "The ACL Profile UDP/TCP source port mask.
               If SRC-PORT is turn on in aclProfileMask, 
               it will work with its member rule field,aclL3RuleTcpUdpSrcPort, 
               to caculate a range of source port which is really care.
               The value is in HEX format.
              "
           DEFVAL  { 'FFFF'h }     
           ::= { ipv4aclProfileEntry 12 }   
        ipv4aclProfileArpSenderMacAddrMask OBJECT-TYPE 
           SYNTAX      MacAddress
           MAX-ACCESS  read-only 
           STATUS      obsolete 
           DESCRIPTION 
              "The ACL Profile Sender MAC mask.
               This is only for ARP Spoofing Prevention which is System-defined ACL,
               and it's not allow to modify.
               The value is in HEX format.
              "
           DEFVAL  { 'FFFFFFFFFF'h }
           ::= { ipv4aclProfileEntry 13 }
        
        ipv4aclProfileArpSenderIpAddrMask OBJECT-TYPE 
           SYNTAX      IpAddress
           MAX-ACCESS  read-only 
           STATUS      obsolete 
           DESCRIPTION 
              "The ACL Profile Sender IP mask.
               This is only for ARP Spoofing Prevention which is System-defined ACL,
               and it's not allow to modify.
               The value is in HEX format.
              "
           DEFVAL  { 'FFFFFFFF'h }
           ::= { ipv4aclProfileEntry 14 }


        ipv4aclProfileUdfOffsetMap OBJECT-TYPE 
           SYNTAX   OCTET STRING
           MAX-ACCESS   read-write  
           STATUS       obsolete 
           DESCRIPTION 
              "Indicate which Udf field want to care in the packet.
               Turn on the following bits to select the following items
               Type        Item                   BIT         
               ------------------------------------------
               UDF         Offset1                 0 (LSB)        
               UDF         Offset2                 1         
               UDF         Offset3                 2         
               UDF         Offset4                 3         
               -------------------------------------------
               
               The value is in Hex format.
              "
           ::= { ipv4aclProfileEntry 15 }  

        ipv4aclUdfOffsetChunk1  OBJECT-TYPE 
           SYNTAX   Integer32 (0..31)
           MAX-ACCESS   read-write 
           STATUS      obsolete 
           DESCRIPTION 
              "The value of offset Chunk."
           ::= { ipv4aclProfileEntry 17 }

        ipv4aclUdfOffsetMask1  OBJECT-TYPE 
           SYNTAX   OCTET STRING
           MAX-ACCESS   read-write
           STATUS      obsolete 
           DESCRIPTION 
              "The value of offset MAsk."
           DEFVAL  { 'FFFFFFFF'h }
           ::= { ipv4aclProfileEntry 18 }

        ipv4aclUdfOffsetChunk2  OBJECT-TYPE 
           SYNTAX   Integer32 (0..31)
           MAX-ACCESS   read-write
           STATUS      obsolete 
           DESCRIPTION 
              "The value of offset Chunk."
           ::= { ipv4aclProfileEntry 20 }

        ipv4aclUdfOffsetMask2  OBJECT-TYPE 
           SYNTAX   OCTET STRING
           MAX-ACCESS   read-write 
           STATUS      obsolete 
           DESCRIPTION 
              "The value of offset MAsk."
           DEFVAL  { 'FFFFFFFF'h }
           ::= { ipv4aclProfileEntry 21 }
           
        ipv4aclUdfOffsetChunk3  OBJECT-TYPE 
           SYNTAX   Integer32 (0..31)
           MAX-ACCESS   read-write
           STATUS      obsolete 
           DESCRIPTION 
              "The value of offset Chunk."
           ::= { ipv4aclProfileEntry 23 }

        ipv4aclUdfOffsetMask3  OBJECT-TYPE 
           SYNTAX   OCTET STRING
           MAX-ACCESS   read-write
           STATUS      obsolete 
           DESCRIPTION 
              "The value of offset MAsk."
           DEFVAL  { 'FFFFFFFF'h }
           ::= { ipv4aclProfileEntry 24 }
           
        ipv4aclUdfOffsetChunk4  OBJECT-TYPE 
           SYNTAX   Integer32 (0..31)
           MAX-ACCESS   read-write 
           STATUS      obsolete 
           DESCRIPTION 
              "The value of offset Chunk."
           ::= { ipv4aclProfileEntry 26 }

        ipv4aclUdfOffsetMask4  OBJECT-TYPE 
           SYNTAX   OCTET STRING
           MAX-ACCESS   read-write 
           STATUS      obsolete 
           DESCRIPTION 
              "The value of offset MAsk."
           DEFVAL  { 'FFFFFFFF'h }
           ::= { ipv4aclProfileEntry 27 }

        ipv4aclProfileStatus OBJECT-TYPE 
           SYNTAX      RowStatus
           MAX-ACCESS  read-create 
           STATUS      obsolete 
           DESCRIPTION 
               " This object indicates the status of this entry, can only be set to
                 'createAndWait','active' and 'destroy'. 
                 When the value of the entry status is 'createAndWait', it could be 
                 set to 'active' only if the three values of aclProfileType,
                 aclProfileMask and ProtocolType are not conflicted.
               "
        
           ::= { ipv4aclProfileEntry 28 }

        -- IPv6 ACL Profile Group --------------------------------------------------
        aclProfileTable OBJECT-TYPE 
           SYNTAX      SEQUENCE OF AclProfileEntry
           MAX-ACCESS  not-accessible 
           STATUS      current 
           DESCRIPTION 
               " A table to ACL profile .
               "
           ::= { aclProfile 2 }
        
        aclProfileEntry OBJECT-TYPE 
           SYNTAX      AclProfileEntry
           MAX-ACCESS  not-accessible 
           STATUS      current 
           DESCRIPTION 
               " Each entry in this table is a ACL profile.
                 Index to the table is ACL profile ID. "
           INDEX { aclProfileNo}
           ::= { aclProfileTable 1 }
           
        AclProfileEntry ::= 
           SEQUENCE { 
              aclProfileNo 
                 Integer32, 
              aclProfileType 
                 INTEGER, 
              aclProfileRuleCount 
                 Integer32,  
              aclProfileMask 
                 OCTET STRING,
              aclProfileDstMacAddrMask 
                 MacAddress,          
              aclProfileSrcMacAddrMask 
                 MacAddress,         
              aclProfileIPProtocol  
                 INTEGER, 
              aclProfileIPProtocolMask  
                 OCTET STRING,  
              aclProfileDstIpAddrMaskType  
                 INTEGER, 
              aclProfileDstIpAddrMask 
                 Ipv6Address,
              aclProfileSrcIpAddrMaskType  
                 INTEGER, 
              aclProfileSrcIpAddrMask 
                 Ipv6Address,
              aclProfileDstPortMask
                 OCTET STRING,         
              aclProfileSrcPortMask
                 OCTET STRING,       
              aclProfileArpSenderMacAddrMask
                 MacAddress,      
              aclProfileArpSenderIpAddrMask
                Ipv6Address,
              aclProfileUdfOffsetMap
                 OCTET STRING,
              aclUdfOffsetChunk1
                 Integer32,
              aclUdfOffsetMask1
                 OCTET STRING,
              aclUdfOffsetChunk2
                 Integer32,
              aclUdfOffsetMask2
                 OCTET STRING,
              aclUdfOffsetChunk3
                 Integer32,
              aclUdfOffsetMask3
                 OCTET STRING,
              aclUdfOffsetChunk4
                 Integer32,
              aclUdfOffsetMask4
                 OCTET STRING,
              aclProfileStatus
                 RowStatus
          }
        
        aclProfileNo OBJECT-TYPE 
           SYNTAX      Integer32 (1..50)
           MAX-ACCESS  read-only 
           STATUS      current 
           DESCRIPTION 
              "The ACL Profile ID. The ID 1 to 50 is user-defined ACL,
               and the ID more than 50 is reserved for system-defined ACL.
               The user only allow to create user-defined ACL ID.
               And system-defined ACL is read only."
           ::= { aclProfileEntry 1 }
        
        aclProfileType OBJECT-TYPE 
           SYNTAX   INTEGER  {
                          l2 (1),
                          l3v4 (2),
                          l3v6 (11),
                          impb (3),
                          arpSP-permit(4),
                          arpSP-deny(5),
                          aclQos (8) ,
                          userDefined(9)
                       }
           MAX-ACCESS   read-write 
           STATUS      current 
           DESCRIPTION 
              "The ACL Profile type, possible value are
              l2 (1) - for MAC-based rule, 
              l3v4 (2) - for IPv4-based rule,
              l3v6 (11) - for IPv6-based rule,              
              arpSP-permit(4) - for ARP Spoofing prevention entry,
              arpSP-deny(5) - for ARP Spoofing prevention entry,
              voiceVlan(6) - for Voice VLAN OUI entry.
              userDefined(9) - for User Defined entry.
              Note that only l2, l3 and userDefined could be set by user, 
              other is reserved for system to show information.
              "
           ::= { aclProfileEntry 2 }
        
        aclProfileRuleCount  OBJECT-TYPE 
           SYNTAX   Integer32 (0..65535)
           MAX-ACCESS   read-only 
           STATUS      current 
           DESCRIPTION 
              "The number of rules in this profile."
           ::= { aclProfileEntry 3 }
              
              
        aclProfileMask OBJECT-TYPE 
           SYNTAX   OCTET STRING
           MAX-ACCESS   read-write  
           STATUS      current 
           DESCRIPTION 
              "Indicate which field want to care in the packet.
               Turn on the following bits to select the following items
               Type        Item                   BIT         
               ------------------------------------------
               L2          DST-MAC                0 (LSB)        
               L2          SRC-MAC                1         
               L2          VID                    2         
               L2          8021P-PRIORITY         3         
               L2          ETHER-TYPE             4         
               L3          DSCP                   5         
               L3          ICMP-TYPE              6         
               L3          ICMP-CODE              7         
               L3          IGMP-TYPE              8         
               L3          DST-IP                 9         
               L3    	   SRC-IP                 10        
               L3    	   DST-PORT               11        
               L3          SRC-PORT               12        
               L3          TCPFLAG                13  
               ARP-SP      ARP-SENDER-MAC         14        
               ARP-SP      ARP-SENDER-IP          15 
               L3          TRAFFIC-CLASS          21 
               L3          TOS                    16
               UDF         UDF1                   17
               UDF         UDF2                   18
               UDF         UDF3                   19
               UDF         UDF4                   20
               L3v6        TRAFFIC-CLASS          21
               L3v6        DST-IPV6               22  
               L3v6        SRC-IPV6               23  (MSB)
               -------------------------------------------
               
               The value is in Hex format.
              "
           ::= { aclProfileEntry 4 }      
       

        aclProfileDstMacAddrMask OBJECT-TYPE 
           SYNTAX      MacAddress
           MAX-ACCESS  read-write 
           STATUS      current 
           DESCRIPTION 
              "The ACL Profile destination MAC address mask.
               If DST-MAC is turn on in aclProfileMask, 
               it will work with its member rule field,aclL2RuleDstMacAddr, 
               to caculate a range of MAC address which is really care.
              "
           ::= { aclProfileEntry 5 }
        
        
        aclProfileSrcMacAddrMask OBJECT-TYPE 
           SYNTAX      MacAddress
           MAX-ACCESS  read-write 
           STATUS      current 
           DESCRIPTION 
              "The ACL Profile source MAC address mask.
               If SRC-MAC is turn on in aclProfileMask, 
               it will work with its member rule field,aclL2RuleSrcMacAddr, 
               to caculate a range of MAC address which is really care.
              "
           ::= { aclProfileEntry 6 }
        
        
        aclProfileIPProtocol OBJECT-TYPE 
           SYNTAX   INTEGER  {  
                         none(0),   
           				 icmp(1),
           				 igmp(2),
           				 tcp(6),
          				 udp(17),
          				 icmpv6(58)
                         ,ipProtocolMask(256)
                        }
           MAX-ACCESS  read-write 
           STATUS      current 
           DESCRIPTION 
              "Indicate which IP Protocol will be care in this profile.
               Only profile type is l3 can set the IP protocol.
               For others, this field will be none.
              "
           ::= { aclProfileEntry 7 } 
        aclProfileIPProtocolMask OBJECT-TYPE 
           SYNTAX      OCTET STRING
           MAX-ACCESS  read-write 
           STATUS      current 
           DESCRIPTION 
              "The ACL Profile IP protocol mask.
               If aclProfileIPProtocol set to ipMask, this field will be refered.
               It will work with its member rule field,aclL3RuleProtocol, 
               to caculate a range of IP protocol which is really care.
               The value is in HEX format.
              "
           DEFVAL  { 'FF'h }   
           ::= { aclProfileEntry 8 }
		aclProfileDstIpAddrMaskType OBJECT-TYPE
	          SYNTAX    INTEGER {
                        iPv4 (1),
                        iPv6 (2)
              }
              MAX-ACCESS  read-write
              STATUS      current
	          DESCRIPTION
                  "IPv6 Address type."
              ::= { aclProfileEntry 9 }
        aclProfileDstIpAddrMask OBJECT-TYPE 
           SYNTAX      Ipv6Address
           MAX-ACCESS  read-write 
           STATUS      current 
           DESCRIPTION 
              "The ACL Profile destination IP address mask.
               If DST-IP is turn on in aclProfileMask, 
               it will work with its member rule field,aclL3RuleDstIpAddr, 
               to caculate a range of IP address which is really care.
               The value is in HEX format, for example:
               '255.255.255.0' is presented to 'FFFFFF00'
              "
           DEFVAL  { 'FFFFFFFF'h }
           ::= { aclProfileEntry 10 }
        
		aclProfileSrcIpAddrMaskType OBJECT-TYPE
	          SYNTAX    INTEGER {
                        iPv4 (1),
                        iPv6 (2)
              }
              MAX-ACCESS  read-write
              STATUS      current
	          DESCRIPTION
                  "IPv6 Address type."
              ::= { aclProfileEntry 11 }
        
        aclProfileSrcIpAddrMask OBJECT-TYPE 
           SYNTAX      Ipv6Address
           MAX-ACCESS  read-write 
           STATUS      current 
           DESCRIPTION 
              "The ACL Profile source IP address mask.
               If SRC-IP is turn on in aclProfileMask, 
               it will work with its member rule field,aclL3RuleSrcIpAddr, 
               to caculate a range of IP address which is really care.
               The value is in HEX format, for example:
               '255.255.255.0' is presented to 'FFFFFF00'
              "
           DEFVAL  { 'FFFFFFFF'h }
           ::= { aclProfileEntry 12 }
        
        aclProfileDstPortMask OBJECT-TYPE 
           SYNTAX      OCTET STRING
           MAX-ACCESS  read-write 
           STATUS      current 
           DESCRIPTION 
              "The ACL Profile UDP/TCP destination port mask.
               If DST-PORT is turn on in aclProfileMask, 
               it will work with its member rule field,aclL3RuleTcpUdpDstPort, 
               to caculate a range of destination port which is really care.
               The value is in HEX format.
              "
           DEFVAL  { 'FFFF'h }   
           ::= { aclProfileEntry 13 }
           
        
        aclProfileSrcPortMask OBJECT-TYPE 
           SYNTAX      OCTET STRING
           MAX-ACCESS  read-write 
           STATUS      current 
           DESCRIPTION 
              "The ACL Profile UDP/TCP source port mask.
               If SRC-PORT is turn on in aclProfileMask, 
               it will work with its member rule field,aclL3RuleTcpUdpSrcPort, 
               to caculate a range of source port which is really care.
               The value is in HEX format.
              "
           DEFVAL  { 'FFFF'h }     
           ::= { aclProfileEntry 14 }   
        aclProfileArpSenderMacAddrMask OBJECT-TYPE 
           SYNTAX      MacAddress
           MAX-ACCESS  read-only 
           STATUS      current 
           DESCRIPTION 
              "The ACL Profile Sender MAC mask.
               This is only for ARP Spoofing Prevention which is System-defined ACL,
               and it's not allow to modify.
               The value is in HEX format.
              "
           DEFVAL  { 'FFFFFFFFFF'h }
           ::= { aclProfileEntry 15 }
        
        aclProfileArpSenderIpAddrMask OBJECT-TYPE 
           SYNTAX      Ipv6Address
           MAX-ACCESS  read-only 
           STATUS      current 
           DESCRIPTION 
              "The ACL Profile Sender IP mask.
               This is only for ARP Spoofing Prevention which is System-defined ACL,
               and it's not allow to modify.
               The value is in HEX format.
              "
           DEFVAL  { 'FFFFFFFF'h }
           ::= { aclProfileEntry 16 }


        aclProfileUdfOffsetMap OBJECT-TYPE 
           SYNTAX   OCTET STRING
           MAX-ACCESS   read-write  
           STATUS      current 
           DESCRIPTION 
              "Indicate which Udf field want to care in the packet.
               Turn on the following bits to select the following items
               Type        Item                   BIT         
               ------------------------------------------
               UDF         Offset1                 0 (LSB)        
               UDF         Offset2                 1         
               UDF         Offset3                 2         
               UDF         Offset4                 3         
               -------------------------------------------
               
               The value is in Hex format.
              "
           ::= { aclProfileEntry 17 }  
           
        aclUdfOffsetChunk1  OBJECT-TYPE 
           SYNTAX   Integer32 (0..31)
           MAX-ACCESS   read-write 
           STATUS      current 
           DESCRIPTION 
              "The value of offset Chunk."
           ::= { aclProfileEntry 19 }

        aclUdfOffsetMask1  OBJECT-TYPE 
           SYNTAX   OCTET STRING
           MAX-ACCESS   read-write
           STATUS      current 
           DESCRIPTION 
              "The value of offset MAsk."
           DEFVAL  { 'FFFFFFFF'h }
           ::= { aclProfileEntry 20 }

        aclUdfOffsetChunk2  OBJECT-TYPE 
           SYNTAX   Integer32 (0..31)
           MAX-ACCESS   read-write
           STATUS      current 
           DESCRIPTION 
              "The value of offset Chunk."
           ::= { aclProfileEntry 22 }

        aclUdfOffsetMask2  OBJECT-TYPE 
           SYNTAX   OCTET STRING
           MAX-ACCESS   read-write 
           STATUS      current 
           DESCRIPTION 
              "The value of offset MAsk."
           DEFVAL  { 'FFFFFFFF'h }
           ::= { aclProfileEntry 23 }
           
        aclUdfOffsetChunk3  OBJECT-TYPE 
           SYNTAX   Integer32 (0..31)
           MAX-ACCESS   read-write
           STATUS      current 
           DESCRIPTION 
              "The value of offset Chunk."
           ::= { aclProfileEntry 25 }

        aclUdfOffsetMask3  OBJECT-TYPE 
           SYNTAX   OCTET STRING
           MAX-ACCESS   read-write
           STATUS      current 
           DESCRIPTION 
              "The value of offset MAsk."
           DEFVAL  { 'FFFFFFFF'h }
           ::= { aclProfileEntry 26 }
           
        aclUdfOffsetChunk4  OBJECT-TYPE 
           SYNTAX   Integer32 (0..31)
           MAX-ACCESS   read-write 
           STATUS      current 
           DESCRIPTION 
              "The value of offset Chunk."
           ::= { aclProfileEntry 28 }

        aclUdfOffsetMask4  OBJECT-TYPE 
           SYNTAX   OCTET STRING
           MAX-ACCESS   read-write 
           STATUS      current 
           DESCRIPTION 
              "The value of offset MAsk."
           DEFVAL  { 'FFFFFFFF'h }
           ::= { aclProfileEntry 29 }

        aclProfileStatus OBJECT-TYPE 
           SYNTAX      RowStatus
           MAX-ACCESS  read-create 
           STATUS      current 
           DESCRIPTION 
               " This object indicates the status of this entry, can only be set to
                 'createAndWait','active' and 'destroy'. 
                 When the value of the entry status is 'createAndWait', it could be 
                 set to 'active' only if the three values of aclProfileType,
                 aclProfileMask and ProtocolType are not conflicted.
               "
        
           ::= { aclProfileEntry 30 }

        -- ------------------------------------------------------------------ 
        -- L2 Filter Group --------------------------------------------------
        aclL2Rule       OBJECT IDENTIFIER ::= { companyACLGroup 2 }

        aclL2RuleTable OBJECT-TYPE 
        
           SYNTAX      SEQUENCE OF AclL2RuleEntry
           MAX-ACCESS  not-accessible 
           STATUS      current 
           DESCRIPTION 
               "A table to configure L2 filter rules in the system."
           ::= { aclL2Rule 1 }
        
        aclL2RuleEntry OBJECT-TYPE 
           SYNTAX      AclL2RuleEntry
           MAX-ACCESS  not-accessible 
           STATUS      current 
           DESCRIPTION 
               "Each entry in this table is a L2 filter rule.
               Index to the table is the L2 filter number and Profile ID."
           INDEX {aclL2ProfileID, aclL2AccessID}
           ::= { aclL2RuleTable 1 }
           
        AclL2RuleEntry ::= 
           SEQUENCE { 
              aclL2AccessID 
                 Integer32,        
              aclL2ProfileID 
                 Integer32, 
              aclL2RuleEtherType 
                 Integer32, 
              aclL2RuleDstMacAddr 
                 MacAddress, 
              aclL2RuleSrcMacAddr 
                 MacAddress, 
              aclL2RuleVlanId 
                 Integer32,
              aclL2Rule1pPriority
                 Integer32,
              aclL2RuleDstMacAddrMask 
                 MacAddress, 
              aclL2RuleSrcMacAddrMask 
                 MacAddress,   
              aclL2RuleAction 
                 INTEGER, 
              aclL2RuleRateLimit 
                 Unsigned32, 
              aclL2RuleReplaceDSCP 
                 Integer32, 
              aclL2RuleReplace1P 
                 Integer32, 
              aclL2RuleReplaceQueue 
                 Integer32,  
              aclL2RuleFilterTimeRange 
                OCTET STRING,
              aclL2RuleInPortList 
                 PortList,
              aclL2RuleInVlanList 
                 OCTET STRING,
			  aclL2RuleVlanIdMask
				OCTET STRING,
              aclL2RuleStatus
                 RowStatus      
          }
        
        aclL2AccessID OBJECT-TYPE 
           SYNTAX      Integer32 (0..250)
           MAX-ACCESS  read-only 
           STATUS      current 
           DESCRIPTION 
              "L2 Filter rule ID. 0 means auto assign."
           ::= { aclL2RuleEntry 1 }
            
        aclL2ProfileID OBJECT-TYPE 
           SYNTAX      Integer32 (1..50)
           MAX-ACCESS  read-only  
           STATUS      current 
           DESCRIPTION 
              "ACL Profile ID which this rule join."
           DEFVAL  { 1 }
           ::= { aclL2RuleEntry 2 }
           
        aclL2RuleEtherType OBJECT-TYPE 
           SYNTAX      Integer32  (-1 | 1501..65535)
           MAX-ACCESS  read-write 
           STATUS      current 
           DESCRIPTION 
              "The value in the Type/Len field of a frame that will
              be matched to trigger this filter. The default value of
              this object is '-1', which means the rule don't care this 
              condition."
           DEFVAL  { -1 }
           ::= { aclL2RuleEntry 3 }
                      
        aclL2RuleDstMacAddr OBJECT-TYPE 
           SYNTAX      MacAddress
           MAX-ACCESS  read-write 
           STATUS      current 
           DESCRIPTION 
              "Destination MAC address to be matched with the packet. By Default, the
               Destination Mac Address will be zero,which means the rule don't care this 
               condition." 
           ::= { aclL2RuleEntry 4 }
        
        aclL2RuleSrcMacAddr OBJECT-TYPE 
           SYNTAX      MacAddress
           MAX-ACCESS  read-write 
           STATUS      current 
           DESCRIPTION 
              "Source MAC address to be matched with the packet. By Default, the Source 
               Mac Address will be zero, which means the rule don't care this condition..
               address"
           ::= { aclL2RuleEntry 5 }
                
        aclL2RuleVlanId OBJECT-TYPE 
           SYNTAX      Integer32 (-1..4094)
           MAX-ACCESS  read-write 
           STATUS      current 
           DESCRIPTION 
              "Vlan Id to be filtered. In case of Provider bridges, This Vlan Id will
              be treated as customer Vlan Id. By Default, the value will be '-1', 
              which means the rule don't care this condition."
           DEFVAL  { -1 }
           ::= { aclL2RuleEntry 6 }        
         
         aclL2Rule1pPriority OBJECT-TYPE 
           SYNTAX      Integer32  (-1..7)
           MAX-ACCESS  read-write 
           STATUS      current 
           DESCRIPTION 
              "802.1p priority to be matched with the packet. By Default, the value
              will be '-1', which means the rule don't care this condition."
          DEFVAL  { -1 }
           ::= { aclL2RuleEntry 7 }   
        
        aclL2RuleDstMacAddrMask OBJECT-TYPE 
           SYNTAX      MacAddress
           MAX-ACCESS  read-only 
           STATUS      current 
           DESCRIPTION 
              "The MAC address Mask work for Destination MAC address.
              This field is read-only and copy from it's Profile setting."
              
           ::= { aclL2RuleEntry 8 }
        
        aclL2RuleSrcMacAddrMask OBJECT-TYPE 
           SYNTAX      MacAddress
           MAX-ACCESS  read-only 
           STATUS      current 
           DESCRIPTION 
              "The MAC address Mask work for Source MAC address.
              This field is read-only and copy from it's Profile setting."
        
           ::= { aclL2RuleEntry 9 } 
        
        aclL2RuleAction OBJECT-TYPE 
           SYNTAX      INTEGER {
                          allow (1)
                          ,drop  (2)
                          ,mirror (3)
                          ,rateLimit(4)
                          ,replaceDSCP(5)
                          ,replace1P(6)
                          ,replaceQueue(7)
                       }
           MAX-ACCESS  read-write 
           STATUS      current 
           DESCRIPTION 
              "Specifies the action to be taken on the packet if the filter
              rule matches.
              If the action is 'allow', the packet will be forwarded according
              to the forwarding rules.
              If the action is 'drop', the packet will be discarded."
           DEFVAL  { allow } 
           ::= { aclL2RuleEntry 11 }
         aclL2RuleRateLimit OBJECT-TYPE 
           SYNTAX      Unsigned32
           MAX-ACCESS  read-write 
           STATUS      current 
           DESCRIPTION 
              "Rate limit for matched packet."
        
           ::= { aclL2RuleEntry 12 }

          aclL2RuleReplaceDSCP OBJECT-TYPE 
           SYNTAX      Integer32  (-1..63)
           MAX-ACCESS  read-write 
           STATUS      current 
           DESCRIPTION 
              "Replace DSCP for matched packet."
        
           ::= { aclL2RuleEntry 13 }
           
          aclL2RuleReplace1P OBJECT-TYPE 
           SYNTAX      Integer32  (-1..7)
           MAX-ACCESS  read-write 
           STATUS      current 
           DESCRIPTION 
              "Replace DSCP for matched packet."
        
           ::= { aclL2RuleEntry 14 }
         aclL2RuleReplaceQueue OBJECT-TYPE 
           SYNTAX      Integer32  
           MAX-ACCESS  read-write 
           STATUS      current 
           DESCRIPTION 
              "ACL L2 Rule Replace Queue."
        
           ::= { aclL2RuleEntry 15 }

        aclL2RuleFilterTimeRange OBJECT-TYPE
           SYNTAX      OCTET STRING 
           MAX-ACCESS  read-create
           STATUS  current
           DESCRIPTION
            "ACL L2 Filter Time Range"
        ::= { aclL2RuleEntry 16 }   
         
	aclL2RuleVlanIdMask OBJECT-TYPE 
           SYNTAX      OCTET STRING
           MAX-ACCESS  read-write 
           STATUS      current 
           DESCRIPTION 
              
              "Vlan Id to be filtered. In case of Provider bridges, This Vlan Id will
              be treated as customer Vlan Id. By Default, the value will be '-1', 
              which means the rule don't care this condition."
              
           DEFVAL  { 'FFFF'h }   
           ::= { aclL2RuleEntry 17 }


                           
        aclL2RuleInPortList OBJECT-TYPE 
           SYNTAX      PortList
           MAX-ACCESS  read-write 
           STATUS      current 
           DESCRIPTION 
              "Specifies the complete set of ports over which this filter is applied
               for packets ingress at ports in this list." 
           ::= { aclL2RuleEntry 51 }
           
        aclL2RuleInVlanList OBJECT-TYPE 
           SYNTAX      OCTET STRING
           MAX-ACCESS  read-write 
           STATUS      current 
           DESCRIPTION 
              "Specifies the complete set of Vlan over which this filter is applied
               for packets ingress at vlan . Notice : Only support one VLAN." 
           ::= { aclL2RuleEntry 52 }
           
         aclL2RuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { aclL2RuleEntry 99 }    

        -- ------------------------------------------------------------------ 
        -- L3 Filter Group --------------------------------------------------
        aclL3Rule       OBJECT IDENTIFIER ::= { companyACLGroup 3 }
         
        aclL3RuleTable OBJECT-TYPE 
           SYNTAX      SEQUENCE OF AclL3RuleEntry
           MAX-ACCESS  not-accessible 
           STATUS      current 
           DESCRIPTION 
               " A table to configure L3 filter rules in the system.
               "
           ::= { aclL3Rule 1 }
        
        aclL3RuleEntry OBJECT-TYPE 
           SYNTAX      AclL3RuleEntry
           MAX-ACCESS  not-accessible 
           STATUS      current 
           DESCRIPTION 
               " Each entry in this table is a L3 filter rule.
                 Index to the table is L3 filter number and Profile ID."
           INDEX {aclL3RuleProfileNo, aclL3RuleAccessID }
           ::= { aclL3RuleTable 1 }
           
        AclL3RuleEntry ::= 
           SEQUENCE { 
              aclL3RuleAccessID 
                 Integer32, 
              aclL3RuleProfileNo 
                 Integer32,
              aclL3RuleProtocol  
                 INTEGER, 
              aclL3RuleProtocolMask  
                 OCTET STRING, 
              aclL3RuleICMPMessageType 
                 Integer32, 
              aclL3RuleICMPMessageCode 
                 Integer32, 
              aclL3RuleDstIpAddr 
                 IpAddress, 
              aclL3RuleSrcIpAddr 
                 IpAddress, 
              aclL3RuleDstIpAddrMask 
                 IpAddress, 
              aclL3RuleSrcIpAddrMask 
                 IpAddress,
              aclL3RuleTcpUdpDstPort
                 Integer32, 
              aclL3RuleTcpUdpSrcPort
                 Integer32, 
              aclL3RuleTcpUdpDstPortMask
                OCTET STRING,         
              aclL3RuleTcpUdpSrcPortMask
                OCTET STRING,         
              aclL3RuleTcpAckBit
                 INTEGER,
              aclL3RuleTcpRstBit
                 INTEGER,
              aclL3RuleTcpUrgBit
                 INTEGER,
              aclL3RuleTcpPshBit
                 INTEGER,
              aclL3RuleTcpSynBit
                 INTEGER,
              aclL3RuleTcpFinBit
                 INTEGER,
              aclL3RuleDscp
                 Integer32,
              aclL3RuleTos
                 Integer32,
              aclL3RuleIgmpType
                 Integer32,
              aclL3RuleAction 
                 INTEGER, 
              aclL3RuleRateLimit 
                 Unsigned32,
              aclL3RuleReplaceDSCP 
                 Integer32,
              aclL3RuleReplace1P 
                 Integer32,
              aclL3RuleReplaceQueue 
                 Integer32, 
              aclL3RuleFilterTimeRange 
                 OCTET STRING,
              aclL3RulePortList 
                 PortList,
              aclL3RuleVlanList 
                 OCTET STRING,
              aclL3RuleStatus
                 RowStatus         
          }
        
        aclL3RuleAccessID OBJECT-TYPE 
           SYNTAX      Integer32 (0..250)
           MAX-ACCESS  read-only 
           STATUS      current 
           DESCRIPTION 
              "L3 Filter rule ID. 0 means auto assign."
           ::= { aclL3RuleEntry 1 }
            
        aclL3RuleProfileNo OBJECT-TYPE 
           SYNTAX      Integer32 (1..50)
           MAX-ACCESS  read-only  
           STATUS      current 
           DESCRIPTION 
              "The Profile ID which this rule join."
           ::= { aclL3RuleEntry 2 }
              
        aclL3RuleProtocol OBJECT-TYPE 
           SYNTAX      INTEGER  {     
           				 icmp(1),
           				 igmp(2),
           				 tcp(6),
          				 udp(17)
                        } 
           MAX-ACCESS  read-write 
           STATUS      current 
           DESCRIPTION 
              " The type of protocol to be checked against the packet."
           ::= { aclL3RuleEntry 3 }
           
        aclL3RuleProtocolMask OBJECT-TYPE 
           SYNTAX      OCTET STRING
           MAX-ACCESS  read-only 
           STATUS      current 
           DESCRIPTION 
              "The IP protocol mask.
               This field is read-only and copy from it's Profile setting.
               It will work with the other field,aclL3RuleProtocol, 
               to caculate a range of IP protocol which is really care.
               The value is in HEX format.
              "
           DEFVAL  { 'FF'h }   
           ::= { aclL3RuleEntry 4 }

        aclL3RuleICMPMessageType OBJECT-TYPE 
           SYNTAX      Integer32 (-1..255)
           MAX-ACCESS  read-write 
           STATUS      current 
           DESCRIPTION 
             " The message type to be checked against the packet. If the
              message type matches with the packet, then the packet will be
              dropped / allowed based on the action set in aclL3RuleAction.
              The default value is '-1',which means the rule don't care this 
              condition.
              Some ICMP message types are: 
                   echoReply(0),
                   destinationUnreachable(3),
                   sourceQuench(4),
                   redirect(5),
                   echoRequest(8),
                   timeExceeded(11),
                   parameterProblem(12),
                   timestampRequest(13),
                   timestampReply(14),
                   informationRequest(15),
                   informationReply(16),
                   addressMaskRequest(17),
                   addressMaskReply (18),
              "
           DEFVAL  { -1 }
           ::= { aclL3RuleEntry 5 }
        
        aclL3RuleICMPMessageCode OBJECT-TYPE 
           SYNTAX      Integer32 (-1..255)
           MAX-ACCESS  read-write 
           STATUS      current 
           DESCRIPTION 
              " The message code to be checked against the packet. If the
              packet matches with the message code, then the packet will
              be dropped / allowed based on the action set in aclL3RuleAction.
              The default value is '-1', which means the rule don't care this 
              condition.
              Some ICMP message codes are :
                   networkUnreachable(0),
                   hostUnreachable(1),
                   protocolUnreachable(2),
                   portUnreachable(3),
                   fragmentNeed(4),
                   sourceRouteFail(5),
                   destNetworkUnknown(6),
                   destHostUnknown(7),
                   srcHostIsolated(8),
                   destNetworkAdminProhibited(9),
                   destHostAdminProhibited(10),
                   networkUnreachableTOS(11),
                   hostUnreachableTOS(12),
              "
           DEFVAL   { -1 }
           ::= { aclL3RuleEntry 6 }     
        
        aclL3RuleDstIpAddr OBJECT-TYPE 
           SYNTAX      IpAddress
           MAX-ACCESS  read-write 
           STATUS      current 
           DESCRIPTION 
              "Destination IP address to be matched with the packet.
               The default value will be zero, which means the rule 
               don't care this condition."
           DEFVAL  { '00000000'h }
           ::= { aclL3RuleEntry 7 }
        
        aclL3RuleSrcIpAddr OBJECT-TYPE 
           SYNTAX      IpAddress
           MAX-ACCESS  read-write 
           STATUS      current 
           DESCRIPTION 
              "Source IP address to be matched with the packet.
              The default value will be zero, which means the 
              rule don't care this condition."

           DEFVAL  { '00000000'h }
           ::= { aclL3RuleEntry 8 }
        
        aclL3RuleDstIpAddrMask OBJECT-TYPE 
           SYNTAX      IpAddress
           MAX-ACCESS  read-only 
           STATUS      current 
           DESCRIPTION 
              "The IP subnet mask for Destination IP address.
               This field is read-only and copy from it's Profile setting.
              "
           
           DEFVAL  { 'FFFFFFFF'h }
           ::= { aclL3RuleEntry 9 }
        
        aclL3RuleSrcIpAddrMask OBJECT-TYPE 
           SYNTAX      IpAddress
           MAX-ACCESS  read-only 
           STATUS      current 
           DESCRIPTION 
              "The IP subnet mask for Source IP address.
               This field is read-only and copy from it's Profile setting.
              "
           
           DEFVAL  { 'FFFFFFFF'h }
           ::= { aclL3RuleEntry 10 }
        
        aclL3RuleTcpUdpDstPort OBJECT-TYPE
           SYNTAX      Integer32 (-1..65535)
           MAX-ACCESS  read-write
           STATUS      current
           DESCRIPTION
              "The TCP / UDP destination port. The default value is -1, 
              which means the rule don't care this condition."
           DEFVAL   { -1 }
           ::= { aclL3RuleEntry 11 }
        
        aclL3RuleTcpUdpSrcPort OBJECT-TYPE
           SYNTAX      Integer32 (-1..65535)
           MAX-ACCESS  read-write
           STATUS      current
           DESCRIPTION
              "The TCP / UDP source port. The default value is -1, 
              which means the rule don't care this condition."
           DEFVAL   { -1 }
           ::= { aclL3RuleEntry 12 }
           
        aclL3RuleTcpUdpDstPortMask OBJECT-TYPE
           SYNTAX      OCTET STRING
           MAX-ACCESS  read-only
           STATUS      current
           DESCRIPTION
              "The TCP / UDP Destination port Mask.
               This field is read-only and copy from it's Profile setting.
              "
           ::= { aclL3RuleEntry 13 }
        
        aclL3RuleTcpUdpSrcPortMask OBJECT-TYPE
           SYNTAX      OCTET STRING
           MAX-ACCESS  read-only
           STATUS      current
           DESCRIPTION
              "The TCP / UDP Source port Mask.
               This field is read-only and copy from it's Profile setting.
              "
           ::= { aclL3RuleEntry 14 } 
           
        aclL3RuleTcpAckBit		OBJECT-TYPE
        	SYNTAX	INTEGER	{
        	                    dont-care(-1),	
        						establish(1),
        						notEstablish(2)
        					}
        	MAX-ACCESS	read-create
        	STATUS		current
        	DESCRIPTION
        		" The TCP ACK bit to be checked against the packet. The default 
        		value is 'dont-care'(-1), which means the rule don't care this 
        		condition."
        	DEFVAL	{ dont-care }
        	::= { aclL3RuleEntry 15 }
        
        aclL3RuleTcpRstBit	 OBJECT-TYPE
        	SYNTAX	INTEGER	{
        	                    dont-care(-1),	
        						establish(1),
        						notEstablish(2)
        					}
        	MAX-ACCESS	read-create
        	STATUS		current
        	DESCRIPTION
        		" The TCP RST bit to be checked against the packet. The default 
        		value is 'dont-care'(-1), which means the rule don't care this 
        		condition."
        	DEFVAL	{ dont-care }
        	::= { aclL3RuleEntry 16 }
        
        aclL3RuleTcpUrgBit	 OBJECT-TYPE
        	SYNTAX	INTEGER	{
        	                    dont-care(-1),	
        						establish(1),
        						notEstablish(2)
        					}
        	MAX-ACCESS	read-create
        	STATUS		current
        	DESCRIPTION
        		" The TCP Urg bit to be checked against the packet. The default 
        		value is 'dont-care'(-1), which means the rule don't care this 
        		condition."
        	DEFVAL	{ dont-care }
        	::= { aclL3RuleEntry 17 }
        	
        aclL3RuleTcpPshBit	 OBJECT-TYPE
        	SYNTAX	INTEGER	{
        	                    dont-care(-1),	
        						establish(1),
        						notEstablish(2)
        					}
        	MAX-ACCESS	read-create
        	STATUS		current
        	DESCRIPTION
        		" The TCP Psh bit to be checked against the packet. The default 
        		value is 'dont-care'(-1). which means the rule don't care this 
        		condition."
        	DEFVAL	{ dont-care }
        	::= { aclL3RuleEntry 18 }	
        
        aclL3RuleTcpSynBit	 OBJECT-TYPE
        	SYNTAX	INTEGER	{
        	                    dont-care(-1),	
        						establish(1),
        						notEstablish(2)
        					}
        	MAX-ACCESS	read-create
        	STATUS		current
        	DESCRIPTION
        		" The TCP Syn bit to be checked against the packet. The default 
        		value is 'dont-care'(-1), which means the rule don't care this condition."
        	DEFVAL	{ dont-care }
        	::= { aclL3RuleEntry 19 }		
        
        aclL3RuleTcpFinBit	 OBJECT-TYPE
        	SYNTAX	INTEGER	{
        	                    dont-care(-1),	
        						establish(1),
        						notEstablish(2)
        					}
        	MAX-ACCESS	read-create
        	STATUS		current
        	DESCRIPTION
        		" The TCP Fin bit to be checked against the packet. The default 
        		value is 'dont-care'(-1), which means the rule don't care this 
        		condition."
        	DEFVAL	{ dont-care }
        	::= { aclL3RuleEntry 20 }		  
        
        aclL3RuleDscp		OBJECT-TYPE
        	SYNTAX		Integer32 (-1..63)
        	MAX-ACCESS	read-create
        	STATUS		current
        	DESCRIPTION
        		" The IP Dscp value to be checked against the packet. 
                A default value is '-1', which means the rule don't 
                care this condition."
        	DEFVAL	{ -1 }
        	::= { aclL3RuleEntry 21 }
        	
        aclL3RuleTos		OBJECT-TYPE
        	SYNTAX		Integer32 (-1..7)
        	MAX-ACCESS	read-create
        	STATUS		current
        	DESCRIPTION
        		" The IP Dscp value to be checked against the packet. 
                A default value is '-1', which means the rule don't 
                care this condition."
        	DEFVAL	{ -1 }
        	::= { aclL3RuleEntry 22 }

        aclL3RuleIgmpType	 OBJECT-TYPE
        	SYNTAX      Integer32 (-1..255)
           MAX-ACCESS  read-write 
           STATUS      current 
           DESCRIPTION 
             " The IGMP Type to be checked against the packet.A default value is '-1',
             which means the rule don't care this condition."
           DEFVAL  { -1 }
           ::= { aclL3RuleEntry 23 }
           
           
        aclL3RuleAction OBJECT-TYPE 
           SYNTAX      INTEGER {
                          allow (1)
                          ,drop  (2)
                          ,mirror (3)
                          ,rateLimit(4)
                          ,replaceDSCP(5)
                          ,replace1P(6)
                          ,replaceQueue(7)
                       }
           MAX-ACCESS  read-write 
           STATUS      current 
           DESCRIPTION 
              "Specifies the action to be taken on the packet if the filter
              rule matches."
           DEFVAL  { allow } 
           ::= { aclL3RuleEntry 25 }
        aclL3RuleRateLimit OBJECT-TYPE 
           SYNTAX      Unsigned32
           MAX-ACCESS  read-write 
           STATUS      current 
           DESCRIPTION 
              "Rate limit for matched packet."
        
           ::= { aclL3RuleEntry 26 }
        aclL3RuleReplaceDSCP OBJECT-TYPE 
           SYNTAX      Integer32  (-1..63)
           MAX-ACCESS  read-write 
           STATUS      current 
           DESCRIPTION 
              "ReplaceDSCP for matched packet."
        
           ::= { aclL3RuleEntry 27 }

        aclL3RuleReplace1P OBJECT-TYPE 
           SYNTAX      Integer32  (-1..7)
           MAX-ACCESS  read-write 
           STATUS      current 
           DESCRIPTION 
              "ReplaceDSCP for matched packet."
        
           ::= { aclL3RuleEntry 28 }
        aclL3RuleReplaceQueue OBJECT-TYPE 
           SYNTAX      Integer32
           MAX-ACCESS  read-write 
           STATUS      current 
           DESCRIPTION 
              "Acl L3 Rule Replace Queue."
            ::= { aclL3RuleEntry 29 }
        aclL3RuleFilterTimeRange OBJECT-TYPE
           SYNTAX      OCTET STRING
           MAX-ACCESS  read-create
           STATUS  current
           DESCRIPTION
            "ACL L3 Filter Time Range"
        ::= { aclL3RuleEntry 30 }  

           
        aclL3RulePortList OBJECT-TYPE 
           SYNTAX      PortList
           MAX-ACCESS  read-write 
           STATUS      current 
           DESCRIPTION 
              "Specifies the complete set of ports over which if the packet arrives
              this filter rule will be applicable."
 
           ::= { aclL3RuleEntry 51 }
         	       	
           
        aclL3RuleVlanList OBJECT-TYPE 
           SYNTAX      OCTET STRING
           MAX-ACCESS  read-write 
           STATUS      current 
           DESCRIPTION 
              "Specifies the complete set of vlan over which if the packet arrives
              this filter rule will be applicable. Notice : only support one vlan."
 
           ::= { aclL3RuleEntry 52 }
           
        aclL3RuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { aclL3RuleEntry 99 }

----------------------------------------------------------------------------------------

        aclv6L3RuleTable OBJECT-TYPE 
           SYNTAX      SEQUENCE OF Aclv6L3RuleEntry
           MAX-ACCESS  not-accessible 
           STATUS      current 
           DESCRIPTION 
               " A table to configure L3 filter rules in the system.
               "
           ::= { aclL3Rule 2 }
        
        aclv6L3RuleEntry OBJECT-TYPE 
           SYNTAX      Aclv6L3RuleEntry
           MAX-ACCESS  not-accessible 
           STATUS      current 
           DESCRIPTION 
               " Each entry in this table is a L3 filter rule.
                 Index to the table is L3 filter number and Profile ID."
           INDEX {aclv6L3RuleProfileNo, aclv6L3RuleAccessID }
           ::= { aclv6L3RuleTable 1 }
           
        Aclv6L3RuleEntry ::= 
           SEQUENCE { 
              aclv6L3RuleAccessID 
                 Integer32, 
              aclv6L3RuleProfileNo 
                 Integer32,
              aclv6L3RuleProtocol  
                 INTEGER, 
              aclv6L3RuleProtocolMask  
                 OCTET STRING, 
              aclv6L3RuleICMPMessageType 
                 Integer32, 
              aclv6L3RuleICMPMessageCode 
                 Integer32, 
              aclv6L3RuleDstIpAddr 
                 Ipv6Address,
              aclv6L3RuleSrcIpAddr 
                 Ipv6Address, 
              aclv6L3RuleDstIpAddrMask 
                 Ipv6Address, 
              aclv6L3RuleSrcIpAddrMask 
                 Ipv6Address,
              aclv6L3RuleTcpUdpDstPort
                 Integer32, 
              aclv6L3RuleTcpUdpSrcPort
                 Integer32, 
              aclv6L3RuleTcpUdpDstPortMask
                OCTET STRING,         
              aclv6L3RuleTcpUdpSrcPortMask
                OCTET STRING,         
              aclv6L3RuleTcpAckBit
                 INTEGER,
              aclv6L3RuleTcpRstBit
                 INTEGER,
              aclv6L3RuleTcpUrgBit
                 INTEGER,
              aclv6L3RuleTcpPshBit
                 INTEGER,
              aclv6L3RuleTcpSynBit
                 INTEGER,
              aclv6L3RuleTcpFinBit
                 INTEGER,
              aclv6L3RuleTrafficClass
                 Integer32,
              aclv6L3RuleAction 
                 INTEGER, 
              aclv6L3RuleRateLimit 
                 Unsigned32,
              aclv6L3RuleReplaceDSCP 
                 Integer32,
              aclv6L3RuleReplace1P 
                 Integer32,
              aclv6L3RuleReplaceQueue 
                 Integer32, 
              aclv6L3RuleFilterTimeRange 
                 OCTET STRING,
              aclv6L3RulePortList 
                 PortList,
              aclv6L3RuleVlanList 
                 OCTET STRING,
              aclv6L3RuleStatus
                 RowStatus         
          }
        
        aclv6L3RuleAccessID OBJECT-TYPE 
           SYNTAX      Integer32 (0..250)
           MAX-ACCESS  read-only 
           STATUS      current 
           DESCRIPTION 
              "L3 Filter rule ID.  0 means auto assign."
           ::= { aclv6L3RuleEntry 1 }
            
        aclv6L3RuleProfileNo OBJECT-TYPE 
           SYNTAX      Integer32 (1..50)
           MAX-ACCESS  read-only  
           STATUS      current 
           DESCRIPTION 
              "The Profile ID which this rule join."
           ::= { aclv6L3RuleEntry 2 }
              
        aclv6L3RuleProtocol OBJECT-TYPE 
           SYNTAX      INTEGER  {     
           				 tcp(6),
          				 udp(17),
           				 icmpv6(58)
                        } 
           MAX-ACCESS  read-write 
           STATUS      current 
           DESCRIPTION 
              " The type of protocol to be checked against the packet."
           ::= { aclv6L3RuleEntry 3 }
           
        aclv6L3RuleProtocolMask OBJECT-TYPE 
           SYNTAX      OCTET STRING
           MAX-ACCESS  read-only 
           STATUS      current 
           DESCRIPTION 
              "The IP protocol mask.
               This field is read-only and copy from it's Profile setting.
               It will work with the other field,aclL3RuleProtocol, 
               to caculate a range of IP protocol which is really care.
               The value is in HEX format.
              "
           DEFVAL  { 'FF'h }   
           ::= { aclv6L3RuleEntry 4 }

        aclv6L3RuleICMPMessageType OBJECT-TYPE 
           SYNTAX      Integer32 (-1..255)
           MAX-ACCESS  read-write 
           STATUS      current 
           DESCRIPTION 
             " The message type to be checked against the packet. If the
              message type matches with the packet, then the packet will be
              dropped / allowed based on the action set in aclL3RuleAction.
              The default value is '-1',which means the rule don't care this 
              condition.
              Some ICMP message types are: 
                   echoReply(0),
                   destinationUnreachable(3),
                   sourceQuench(4),
                   redirect(5),
                   echoRequest(8),
                   timeExceeded(11),
                   parameterProblem(12),
                   timestampRequest(13),
                   timestampReply(14),
                   informationRequest(15),
                   informationReply(16),
                   addressMaskRequest(17),
                   addressMaskReply (18),
              "
           DEFVAL  { -1 }
           ::= { aclv6L3RuleEntry 5 }
        
        aclv6L3RuleICMPMessageCode OBJECT-TYPE 
           SYNTAX      Integer32 (-1..255)
           MAX-ACCESS  read-write 
           STATUS      current 
           DESCRIPTION 
              " The message code to be checked against the packet. If the
              packet matches with the message code, then the packet will
              be dropped / allowed based on the action set in aclL3RuleAction.
              The default value is '-1', which means the rule don't care this 
              condition.
              Some ICMP message codes are :
                   networkUnreachable(0),
                   hostUnreachable(1),
                   protocolUnreachable(2),
                   portUnreachable(3),
                   fragmentNeed(4),
                   sourceRouteFail(5),
                   destNetworkUnknown(6),
                   destHostUnknown(7),
                   srcHostIsolated(8),
                   destNetworkAdminProhibited(9),
                   destHostAdminProhibited(10),
                   networkUnreachableTOS(11),
                   hostUnreachableTOS(12),
              "
           DEFVAL   { -1 }
           ::= { aclv6L3RuleEntry 6 }     
        
        aclv6L3RuleDstIpAddr OBJECT-TYPE 
           SYNTAX      Ipv6Address
           MAX-ACCESS  read-write 
           STATUS      current 
           DESCRIPTION 
              "Destination IP address to be matched with the packet.
               The default value will be zero, which means the rule 
               don't care this condition."
           DEFVAL  { '00000000'h }
           ::= { aclv6L3RuleEntry 7 }
        
        aclv6L3RuleSrcIpAddr OBJECT-TYPE 
           SYNTAX      Ipv6Address
           MAX-ACCESS  read-write 
           STATUS      current 
           DESCRIPTION 
              "Source IP address to be matched with the packet.
              The default value will be zero, which means the 
              rule don't care this condition."

           DEFVAL  { '00000000'h }
           ::= { aclv6L3RuleEntry 8 }
        
        aclv6L3RuleDstIpAddrMask OBJECT-TYPE 
           SYNTAX      Ipv6Address
           MAX-ACCESS  read-only 
           STATUS      current 
           DESCRIPTION 
              "The IP subnet mask for Destination IP address.
               This field is read-only and copy from it's Profile setting.
              "
           
           DEFVAL  { 'FFFFFFFF'h }
           ::= { aclv6L3RuleEntry 9 }
        
        aclv6L3RuleSrcIpAddrMask OBJECT-TYPE 
           SYNTAX      Ipv6Address
           MAX-ACCESS  read-only 
           STATUS      current 
           DESCRIPTION 
              "The IP subnet mask for Source IP address.
               This field is read-only and copy from it's Profile setting.
              "
           
           DEFVAL  { 'FFFFFFFF'h }
           ::= { aclv6L3RuleEntry 10 }
        
        aclv6L3RuleTcpUdpDstPort OBJECT-TYPE
           SYNTAX      Integer32 (-1..65535)
           MAX-ACCESS  read-write
           STATUS      current
           DESCRIPTION
              "The TCP / UDP destination port. The default value is -1, 
              which means the rule don't care this condition."
           DEFVAL   { -1 }
           ::= { aclv6L3RuleEntry 11 }
        
        aclv6L3RuleTcpUdpSrcPort OBJECT-TYPE
           SYNTAX      Integer32 (-1..65535)
           MAX-ACCESS  read-write
           STATUS      current
           DESCRIPTION
              "The TCP / UDP source port. The default value is -1, 
              which means the rule don't care this condition."
           DEFVAL   { -1 }
           ::= { aclv6L3RuleEntry 12 }
           
        aclv6L3RuleTcpUdpDstPortMask OBJECT-TYPE
           SYNTAX      OCTET STRING
           MAX-ACCESS  read-only
           STATUS      current
           DESCRIPTION
              "The TCP / UDP Destination port Mask.
               This field is read-only and copy from it's Profile setting.
              "
           ::= { aclv6L3RuleEntry 13 }
        
        aclv6L3RuleTcpUdpSrcPortMask OBJECT-TYPE
           SYNTAX      OCTET STRING
           MAX-ACCESS  read-only
           STATUS      current
           DESCRIPTION
              "The TCP / UDP Source port Mask.
               This field is read-only and copy from it's Profile setting.
              "
           ::= { aclv6L3RuleEntry 14 } 
           
        aclv6L3RuleTcpAckBit		OBJECT-TYPE
        	SYNTAX	INTEGER	{
        	                    dont-care(-1),	
        						establish(1),
        						notEstablish(2)
        					}
        	MAX-ACCESS	read-create
        	STATUS		current
        	DESCRIPTION
        		" The TCP ACK bit to be checked against the packet. The default 
        		value is 'dont-care'(-1), which means the rule don't care this 
        		condition."
        	DEFVAL	{ dont-care }
        	::= { aclv6L3RuleEntry 15 }
        
        aclv6L3RuleTcpRstBit	 OBJECT-TYPE
        	SYNTAX	INTEGER	{
        	                    dont-care(-1),	
        						establish(1),
        						notEstablish(2)
        					}
        	MAX-ACCESS	read-create
        	STATUS		current
        	DESCRIPTION
        		" The TCP RST bit to be checked against the packet. The default 
        		value is 'dont-care'(-1), which means the rule don't care this 
        		condition."
        	DEFVAL	{ dont-care }
        	::= { aclv6L3RuleEntry 16 }
        
        aclv6L3RuleTcpUrgBit	 OBJECT-TYPE
        	SYNTAX	INTEGER	{
        	                    dont-care(-1),	
        						establish(1),
        						notEstablish(2)
        					}
        	MAX-ACCESS	read-create
        	STATUS		current
        	DESCRIPTION
        		" The TCP Urg bit to be checked against the packet. The default 
        		value is 'dont-care'(-1), which means the rule don't care this 
        		condition."
        	DEFVAL	{ dont-care }
        	::= { aclv6L3RuleEntry 17 }
        	
        aclv6L3RuleTcpPshBit	 OBJECT-TYPE
        	SYNTAX	INTEGER	{
        	                    dont-care(-1),	
        						establish(1),
        						notEstablish(2)
        					}
        	MAX-ACCESS	read-create
        	STATUS		current
        	DESCRIPTION
        		" The TCP Psh bit to be checked against the packet. The default 
        		value is 'dont-care'(-1). which means the rule don't care this 
        		condition."
        	DEFVAL	{ dont-care }
        	::= { aclv6L3RuleEntry 18 }	
        
        aclv6L3RuleTcpSynBit	 OBJECT-TYPE
        	SYNTAX	INTEGER	{
        	                    dont-care(-1),	
        						establish(1),
        						notEstablish(2)
        					}
        	MAX-ACCESS	read-create
        	STATUS		current
        	DESCRIPTION
        		" The TCP Syn bit to be checked against the packet. The default 
        		value is 'dont-care'(-1), which means the rule don't care this condition."
        	DEFVAL	{ dont-care }
        	::= { aclv6L3RuleEntry 19 }		
        
        aclv6L3RuleTcpFinBit	 OBJECT-TYPE
        	SYNTAX	INTEGER	{
        	                    dont-care(-1),	
        						establish(1),
        						notEstablish(2)
        					}
        	MAX-ACCESS	read-create
        	STATUS		current
        	DESCRIPTION
        		" The TCP Fin bit to be checked against the packet. The default 
        		value is 'dont-care'(-1), which means the rule don't care this 
        		condition."
        	DEFVAL	{ dont-care }
        	::= { aclv6L3RuleEntry 20 }		  
        
        aclv6L3RuleTrafficClass		OBJECT-TYPE
        	SYNTAX		Integer32 (-1..63)
        	MAX-ACCESS	read-create
        	STATUS		current
        	DESCRIPTION
        		" The IP Dscp value to be checked against the packet. 
                A default value is '-1', which means the rule don't 
                care this condition."
        	DEFVAL	{ -1 }
        	::= { aclv6L3RuleEntry 21 }       
           
        aclv6L3RuleAction OBJECT-TYPE 
           SYNTAX      INTEGER {
                          allow (1)
                          ,drop  (2)
                          ,mirror (3)
                          ,rateLimit(4)
                          ,replaceDSCP(5)     
                          ,replace1P(6)
                          ,replaceQueue(7) 
                       }
           MAX-ACCESS  read-write 
           STATUS      current 
           DESCRIPTION 
              "Specifies the action to be taken on the packet if the filter
              rule matches."
           DEFVAL  { allow } 
           ::= { aclv6L3RuleEntry 24 }
        aclv6L3RuleRateLimit OBJECT-TYPE 
           SYNTAX      Unsigned32
           MAX-ACCESS  read-write 
           STATUS      current 
           DESCRIPTION 
              "Rate limit for matched packet."
        
           ::= { aclv6L3RuleEntry 25 }
        aclv6L3RuleReplaceDSCP OBJECT-TYPE 
           SYNTAX      Integer32  (-1..63)
           MAX-ACCESS  read-write 
           STATUS      current 
           DESCRIPTION 
              "Replace DSCP for matched packet."
        
           ::= { aclv6L3RuleEntry 26 }
           
        aclv6L3RuleReplace1P OBJECT-TYPE 
           SYNTAX      Integer32  (-1..7)
           MAX-ACCESS  read-write 
           STATUS      current 
           DESCRIPTION 
              "Replace DSCP for matched packet."
        
           ::= { aclv6L3RuleEntry 27 }  
        aclv6L3RuleReplaceQueue OBJECT-TYPE 
           SYNTAX      Integer32
           MAX-ACCESS  read-write 
           STATUS      current 
           DESCRIPTION 
              "Acl IPV6 L3 Rule Replace Queue."
            ::= { aclv6L3RuleEntry 28 } 
        aclv6L3RuleFilterTimeRange OBJECT-TYPE
           SYNTAX      OCTET STRING
           MAX-ACCESS  read-create
           STATUS  current
           DESCRIPTION
            "ACL IPV6 L3 Filter Time Range"
        ::= { aclv6L3RuleEntry 29 }      
           
        aclv6L3RulePortList OBJECT-TYPE 
           SYNTAX      PortList
           MAX-ACCESS  read-write 
           STATUS      current 
           DESCRIPTION 
              "Specifies the complete set of ports over which if the packet arrives
              this filter rule will be applicable."
 
           ::= { aclv6L3RuleEntry 51 }
           	
           
        aclv6L3RuleVlanList OBJECT-TYPE 
           SYNTAX      OCTET STRING
           MAX-ACCESS  read-write 
           STATUS      current 
           DESCRIPTION 
              "Specifies the complete set of vlan over which if the packet arrives
              this filter rule will be applicable. Notice : only support one vlan."
 
           ::= { aclv6L3RuleEntry 52 }
                  	       	
        aclv6L3RuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { aclv6L3RuleEntry 99 }


        -- ------------------------------------------------------------------ 
        -- PacketContent Filter Group --------------------------------------------------
        aclPacketRule       OBJECT IDENTIFIER ::= { companyACLGroup 4 }

        aclPacketRuleTable OBJECT-TYPE 
        
           SYNTAX      SEQUENCE OF AclPacketRuleEntry
           MAX-ACCESS  not-accessible 
           STATUS      current 
           DESCRIPTION 
               "A table to configure Packet Content filter rules in the system."
           ::= { aclPacketRule 1 }
        
        aclPacketRuleEntry OBJECT-TYPE 
           SYNTAX      AclPacketRuleEntry
           MAX-ACCESS  not-accessible 
           STATUS      current 
           DESCRIPTION 
               "Each entry in this table is a Packet filter rule.
               Index to the table is the Packet filter number and Profile ID."
           INDEX {aclPacketProfileID, aclPacketAccessID}
           ::= { aclPacketRuleTable 1 }
           
        AclPacketRuleEntry ::= 
           SEQUENCE { 
              aclPacketAccessID 
                 Integer32,        
              aclPacketProfileID 
                 Integer32, 
              aclPacketRuleOffsetValue1 
                 OCTET STRING, 
              aclPacketRuleOffsetValue2 
                 OCTET STRING, 
              aclPacketRuleOffsetValue3 
                 OCTET STRING, 
              aclPacketRuleOffsetValue4 
                 OCTET STRING, 
              aclPacketRuleAction 
                 INTEGER, 
              aclPacketRuleRateLimit 
                 Unsigned32, 
              aclPacketRuleReplaceDSCP 
                 Integer32, 
              aclPacketRuleReplace1P 
                 Integer32, 
              aclPacketRuleReplaceQueue 
                 Integer32, 
              aclPacketRuleFilterTimeRange 
                 OCTET STRING,
			aclPacketRuleOffsetValue1Mask
			     OCTET STRING,
			aclPacketRuleOffsetValue2Mask
			     OCTET STRING,
			aclPacketRuleOffsetValue3Mask
				 OCTET STRING,
			aclPacketRuleOffsetValue4Mask
			     OCTET STRING, 
              aclPacketRuleInPortList 
                 PortList,
              aclPacketRuleInVlanList 
                 OCTET STRING,
              aclPacketRuleStatus
                 RowStatus      
          }
        
        aclPacketAccessID OBJECT-TYPE 
           SYNTAX      Integer32 (0..250)
           MAX-ACCESS  read-only 
           STATUS      current 
           DESCRIPTION 
              "Packet Filter rule ID.  0 means auto assign."
           ::= { aclPacketRuleEntry 1 }
            
        aclPacketProfileID OBJECT-TYPE 
           SYNTAX      Integer32 (1..50)
           MAX-ACCESS  read-only  
           STATUS      current 
           DESCRIPTION 
              "ACL Profile ID which this rule join."
           ::= { aclPacketRuleEntry 2 }
           
        aclPacketRuleOffsetValue1 OBJECT-TYPE 
           SYNTAX      OCTET STRING
           MAX-ACCESS  read-write 
           STATUS      current 
           DESCRIPTION 
              "The filter value of Offset 1."
           ::= { aclPacketRuleEntry 3 }
           
        aclPacketRuleOffsetValue2 OBJECT-TYPE 
           SYNTAX      OCTET STRING
           MAX-ACCESS  read-write 
           STATUS      current 
           DESCRIPTION 
              "The filter value of Offset 2."
           ::= { aclPacketRuleEntry 4 }
           
        aclPacketRuleOffsetValue3 OBJECT-TYPE 
           SYNTAX      OCTET STRING
           MAX-ACCESS  read-write 
           STATUS      current 
           DESCRIPTION 
              "The filter value of Offset 3."
           ::= { aclPacketRuleEntry 5 }
           
        aclPacketRuleOffsetValue4 OBJECT-TYPE 
           SYNTAX      OCTET STRING
           MAX-ACCESS  read-write 
           STATUS      current 
           DESCRIPTION 
              "The filter value of Offset 4."
           ::= { aclPacketRuleEntry 6 }
                      
                         
        aclPacketRuleAction OBJECT-TYPE 
           SYNTAX      INTEGER {
                          allow (1)
                          ,drop  (2)
                          ,mirror (3)
                          ,rateLimit(4)
                          ,replaceDSCP(5)     
                          ,replace1P(6)
                          ,replaceQueue(7) 
                       }
           MAX-ACCESS  read-write 
           STATUS      current 
           DESCRIPTION 
              "Specifies the action to be taken on the packet if the filter
              rule matches.
              If the action is 'allow', the packet will be forwarded according
              to the forwarding rules.
              If the action is 'drop', the packet will be discarded."
           DEFVAL  { allow } 
           ::= { aclPacketRuleEntry 8 }
           
         aclPacketRuleRateLimit OBJECT-TYPE 
           SYNTAX      Unsigned32
           MAX-ACCESS  read-write 
           STATUS      current 
           DESCRIPTION 
              "Rate limit for matched packet."
        
           ::= { aclPacketRuleEntry 9 }

          aclPacketRuleReplaceDSCP OBJECT-TYPE 
           SYNTAX      Integer32  (-1..63)
           MAX-ACCESS  read-write 
           STATUS      current 
           DESCRIPTION 
              "Replace DSCP for matched packet."
        
           ::= { aclPacketRuleEntry 10 }
           
          aclPacketRuleReplace1P OBJECT-TYPE 
           SYNTAX      Integer32  (-1..7)
           MAX-ACCESS  read-write 
           STATUS      current 
           DESCRIPTION 
              "Replace 1p for matched packet."
        
           ::= { aclPacketRuleEntry 11 }
          aclPacketRuleReplaceQueue OBJECT-TYPE 
           SYNTAX      Integer32 
           MAX-ACCESS  read-write 
           STATUS      current 
           DESCRIPTION 
              "Acl Rule Replace Queue."
        
           ::= { aclPacketRuleEntry 12 }
         aclPacketRuleFilterTimeRange OBJECT-TYPE
           SYNTAX      OCTET STRING
           MAX-ACCESS  read-create
           STATUS  current
           DESCRIPTION
            "Acl Filter Time Range"
        ::= { aclPacketRuleEntry 13 }
        
        aclPacketRuleOffsetValue1Mask OBJECT-TYPE 
           SYNTAX      OCTET STRING
           MAX-ACCESS  read-write 
           STATUS      current 
           DESCRIPTION 
              "The filter Mask of Offset 1."
           DEFVAL  { 'FFFF'h }   
           ::= { aclPacketRuleEntry 14 }
           
		aclPacketRuleOffsetValue2Mask OBJECT-TYPE 
           SYNTAX      OCTET STRING
           MAX-ACCESS  read-write 
           STATUS      current 
           DESCRIPTION 
              "The filter Mask of Offset 2."
           DEFVAL  { 'FFFF'h }   
           ::= { aclPacketRuleEntry 15 }
           
		aclPacketRuleOffsetValue3Mask OBJECT-TYPE 
           SYNTAX      OCTET STRING
           MAX-ACCESS  read-write 
           STATUS      current 
           DESCRIPTION 
              "The filter Mask of Offset 3."
           DEFVAL  { 'FFFF'h }   
           ::= { aclPacketRuleEntry 16 }
           
		aclPacketRuleOffsetValue4Mask OBJECT-TYPE 
           SYNTAX      OCTET STRING
           MAX-ACCESS  read-write 
           STATUS      current 
           DESCRIPTION 
              "The filter Mask of Offset 4."
           DEFVAL  { 'FFFF'h }   
           ::= { aclPacketRuleEntry 17 }      
  
        aclPacketRuleInPortList OBJECT-TYPE 
           SYNTAX      PortList
           MAX-ACCESS  read-write 
           STATUS      current 
           DESCRIPTION 
              "Specifies the complete set of ports over which this filter is applied
               for packets ingress at ports in this list." 
           ::= { aclPacketRuleEntry 51 }
        
  
        aclPacketRuleInVlanList OBJECT-TYPE 
           SYNTAX      OCTET STRING
           MAX-ACCESS  read-write 
           STATUS      current 
           DESCRIPTION 
              "Specifies the complete set of vlan over which this filter is applied
               for packets ingress at vlan. Notice : Only support one vlan." 
           ::= { aclPacketRuleEntry 52 }
        

         aclPacketRuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { aclPacketRuleEntry 99 }    


        -- Flow Meter Group --------------------------------------------------
        aclFlowMeterRule       OBJECT IDENTIFIER ::= { companyACLGroup 10 }

        aclFlowMeterTable OBJECT-TYPE 
        
           SYNTAX      SEQUENCE OF AclFlowMeterEntry
           MAX-ACCESS  not-accessible 
           STATUS      current 
           DESCRIPTION 
               "A table to configure L2 filter rules in the system."
           ::= { aclFlowMeterRule 1 }
        
        aclFlowMeterEntry OBJECT-TYPE 
           SYNTAX      AclFlowMeterEntry
           MAX-ACCESS  not-accessible 
           STATUS      current 
           DESCRIPTION 
               "Each entry in this table is a L2 filter rule.
               Index to the table is the L2 filter number and Profile ID."
           INDEX {aclFlowMeterProfileID, aclFlowMeterAccessID}
           ::= { aclFlowMeterTable 1 }
           
        AclFlowMeterEntry ::= 
           SEQUENCE {      
              aclFlowMeterProfileID 
                 Integer32, 
              aclFlowMeterAccessID 
                 Integer32,   
              aclFlowMeterRate 
                 Integer32, 
              aclFlowMeterBurstSize
                 Integer32,
              aclFlowMeterReplaceDscp
                 Integer32,
              aclFlowMeterAction 
                 INTEGER, 
              aclFlowMeterStatus
                 RowStatus      
          }
        
        aclFlowMeterProfileID OBJECT-TYPE 
           SYNTAX      Integer32 (1..50)
           MAX-ACCESS  read-only  
           STATUS      current 
           DESCRIPTION 
              "ACL Profile ID which this flow meter join."
           ::= { aclFlowMeterEntry 1 }

        aclFlowMeterAccessID OBJECT-TYPE 
           SYNTAX      Integer32 (1..250)
           MAX-ACCESS  read-only 
           STATUS      current 
           DESCRIPTION 
              "ACL Access ID which this flow meter join."
           ::= { aclFlowMeterEntry 2 }
           
        aclFlowMeterRate OBJECT-TYPE 
           SYNTAX      Integer32 (64..1024000)
           MAX-ACCESS  read-write 
           STATUS      current 
           DESCRIPTION 
              "The rate limiter of meter."
           ::= { aclFlowMeterEntry 3 }
                      
        aclFlowMeterBurstSize OBJECT-TYPE 
           SYNTAX      Integer32 (0..1016)
           MAX-ACCESS  read-write 
           STATUS      current 
           DESCRIPTION 
              "The burst size of meter."
           ::= { aclFlowMeterEntry 4 }        
         
         aclFlowMeterReplaceDscp OBJECT-TYPE 
           SYNTAX      Integer32 (0..63)
           MAX-ACCESS  read-write 
           STATUS      current 
           DESCRIPTION 
              "Replace DSCP for matched out-band packets when aclFlowMeterAction is replace DSCP."
           ::= { aclFlowMeterEntry 5 }   
        
        
        aclFlowMeterAction OBJECT-TYPE 
           SYNTAX      INTEGER {
                          drop  (2)      
                          ,replaceDSCP(5)
                       }
           MAX-ACCESS  read-write 
           STATUS      current 
           DESCRIPTION 
              "Specifies the action to be taken on the out-band packet if the filter
              rule matches.
              If the action is 'drop', the packet will be discarded."
           DEFVAL  { drop } 
           ::= { aclFlowMeterEntry 6 }

         aclFlowMeterStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { aclFlowMeterEntry 99 }    


        -- Vlan Based Profile Group --------------------------------------------------
--        aclVlanBasedProfile       OBJECT IDENTIFIER ::= { companyACLGroup 20 }
--
--        aclVlanBasedProfileTable OBJECT-TYPE 
--        
--           SYNTAX      SEQUENCE OF AclVlanBasedProfileEntry
--           MAX-ACCESS  not-accessible 
--           STATUS      current 
--           DESCRIPTION 
--               "A table to configure L2 filter rules in the system."
--           ::= { aclVlanBasedProfile 1 }
--        
--        aclVlanBasedProfileEntry OBJECT-TYPE 
--           SYNTAX      AclVlanBasedProfileEntry
--           MAX-ACCESS  not-accessible 
--           STATUS      current 
--           DESCRIPTION 
--               "Each entry in this table is a L2 filter rule.
--               Index to the table is the L2 filter number and Profile ID."
--           INDEX {aclVlanBasedProfileNo}
--           ::= { aclVlanBasedProfileTable 1 }
--           
--        AclVlanBasedProfileEntry ::= 
--           SEQUENCE {      
--              aclVlanBasedProfileNo 
--                 Integer32, 
--              aclVlanBasedProfileActiveVlan 
--                 Integer32,   
--              aclVlanBasedProfileActivePortList 
--                 PortList 
--          }
--        
--        aclVlanBasedProfileNo OBJECT-TYPE 
--           SYNTAX      Integer32 (1..50)
--           MAX-ACCESS  read-only  
--           STATUS      current 
--           DESCRIPTION 
--              "ACL Profile ID which this flow meter join."
--           ::= { aclVlanBasedProfileEntry 1 }
--
--        aclVlanBasedProfileActiveVlan OBJECT-TYPE 
--           SYNTAX      Integer32 (0..4094)
--           MAX-ACCESS  read-write 
--           STATUS      current 
--           DESCRIPTION 
--              "ACL Access ID which this flow meter join."
--           ::= { aclVlanBasedProfileEntry 2 }
--           
--        aclVlanBasedProfileActivePortList OBJECT-TYPE 
--           SYNTAX      PortList
--           MAX-ACCESS  read-write 
--           STATUS      current 
--           DESCRIPTION 
--              "The rate limiter of meter."
--           ::= { aclVlanBasedProfileEntry 3 }
                      

    -- ------------------------------------------------------------------ 
    -- companyCPUInterfaceFilterGroup
    -- ------------------------------------------------------------------

        -- CPU Interface Filter Profile Group --------------------------------------------------
        cpuFilterProfile       OBJECT IDENTIFIER ::= { companyCPUInterfaceFilterGroup 1 }
        
        ipv4cpuFilterProfileTable OBJECT-TYPE 
           SYNTAX      SEQUENCE OF Ipv4CpuFilterProfileEntry
           MAX-ACCESS  not-accessible 
           STATUS      current 
           DESCRIPTION 
               " A table to CPUInterfaceFilter profile .
               "
           ::= { cpuFilterProfile 1 }
        
        ipv4cpuFilterProfileEntry OBJECT-TYPE 
           SYNTAX      Ipv4CpuFilterProfileEntry
           MAX-ACCESS  not-accessible 
           STATUS      current 
           DESCRIPTION 
               " Each entry in this table is a CPUInterfaceFilter profile.
                 Index to the table is CPUInterfaceFilter profile ID. "
           INDEX { ipv4cpuFilterProfileNo}
           ::= { ipv4cpuFilterProfileTable 1 }
           
        Ipv4CpuFilterProfileEntry ::= 
           SEQUENCE { 
              ipv4cpuFilterProfileNo 
                 Integer32, 
              ipv4cpuFilterProfileType 
                 INTEGER, 
              ipv4cpuFilterProfileRuleCount 
                 Integer32,  
              ipv4cpuFilterProfileMask 
                 OCTET STRING,
              ipv4cpuFilterProfileDstMacAddrMask 
                 MacAddress,          
              ipv4cpuFilterProfileSrcMacAddrMask 
                 MacAddress,         
              ipv4cpuFilterProfileIPProtocol  
                 INTEGER, 
              ipv4cpuFilterProfileIPProtocolMask  
                 OCTET STRING,  
              ipv4cpuFilterProfileDstIpAddrMask 
                 IpAddress, 
              ipv4cpuFilterProfileSrcIpAddrMask 
                 IpAddress,
              ipv4cpuFilterProfileDstPortMask
                 OCTET STRING,         
              ipv4cpuFilterProfileSrcPortMask
                 OCTET STRING,       
              ipv4cpuFilterProfileStatus
                 RowStatus
          }
        
        ipv4cpuFilterProfileNo OBJECT-TYPE 
           SYNTAX      Integer32 (1..3)
           MAX-ACCESS  read-only 
           STATUS      current 
           DESCRIPTION 
              "The CPUInterfaceFilter Profile ID. The ID 1 to 50 is user-defined CPUInterfaceFilter,
               and the ID more than 50 is reserved for system-defined CPUInterfaceFilter.
               The user only allow to create user-defined CPUInterfaceFilter ID.
               And system-defined CPUInterfaceFilter is read only."
           ::= { ipv4cpuFilterProfileEntry 1 }
        
        ipv4cpuFilterProfileType OBJECT-TYPE 
           SYNTAX   INTEGER  {
                          l2 (1),
                          l3 (2)
                       }
           MAX-ACCESS   read-write 
           STATUS      current 
           DESCRIPTION 
              "The CPUInterfaceFilter Profile type, possible value are
              l2 (1) - for MAC-based rule, 
              l3 (2) - for IPv4-based rule,
              "
           ::= { ipv4cpuFilterProfileEntry 2 }
        
        ipv4cpuFilterProfileRuleCount  OBJECT-TYPE 
           SYNTAX   Integer32 (0..65535)
           MAX-ACCESS   read-only 
           STATUS      current 
           DESCRIPTION 
              "The number of rules in this profile."
           ::= { ipv4cpuFilterProfileEntry 3 }
              
              
        ipv4cpuFilterProfileMask OBJECT-TYPE 
           SYNTAX   OCTET STRING
           MAX-ACCESS   read-write  
           STATUS      current 
           DESCRIPTION 
              "Indicate which field want to care in the packet.
               Turn on the following bits to select the following items
               Type        Item                   BIT         
               ------------------------------------------
               L2          DST-MAC                0 (LSB)        
               L2          SRC-MAC                1         
               L2          VID                    2         
               L2          8021P-PRIORITY         3         
               L2          ETHER-TYPE             4         
               L3          DSCP                   5         
               L3          ICMP-TYPE              6         
               L3          ICMP-CODE              7         
               L3          IGMP-TYPE              8         
               L3          DST-IP                 9         
               L3          SRC-IP                 10        
               L3          DST-PORT               11        
               L3          SRC-PORT               12        
               L3          TCPFLAG                13 (MSB)
               -------------------------------------------
               
               The value is in Hex format.
              "
           ::= { ipv4cpuFilterProfileEntry 4 }
       

        ipv4cpuFilterProfileDstMacAddrMask OBJECT-TYPE 
           SYNTAX      MacAddress
           MAX-ACCESS  read-write 
           STATUS      current 
           DESCRIPTION 
              "The CPUInterfaceFilter Profile destination MAC address mask.
               If DST-MAC is turn on in cpuFilterProfileMask, 
               it will work with its member rule field,cpuFilterL2RuleDstMacAddr, 
               to caculate a range of MAC address which is really care.
              "
           ::= { ipv4cpuFilterProfileEntry 5 }
        
        
        ipv4cpuFilterProfileSrcMacAddrMask OBJECT-TYPE 
           SYNTAX      MacAddress
           MAX-ACCESS  read-write 
           STATUS      current 
           DESCRIPTION 
              "The CPUInterfaceFilter Profile source MAC address mask.
               If SRC-MAC is turn on in cpuFilterProfileMask, 
               it will work with its member rule field,cpuFilterL2RuleSrcMacAddr, 
               to caculate a range of MAC address which is really care.
              "
           ::= { ipv4cpuFilterProfileEntry 6 }
        
        
        ipv4cpuFilterProfileIPProtocol OBJECT-TYPE 
           SYNTAX   INTEGER  {  
                         none(0),   
                                         icmp(1),
                                         igmp(2),
                                         tcp(6),
                                         udp(17)
                         ,ipMask(255)
                        }
           MAX-ACCESS  read-write 
           STATUS      current 
           DESCRIPTION 
              "Indicate which IP Protocol will be care in this profile.
               Only profile type is l3 can set the IP protocol.
               For others, this field will be none.
              "
           ::= { ipv4cpuFilterProfileEntry 7 } 
        ipv4cpuFilterProfileIPProtocolMask OBJECT-TYPE 
           SYNTAX      OCTET STRING
           MAX-ACCESS  read-write 
           STATUS      current 
           DESCRIPTION 
              "The CPUInterfaceFilter Profile IP protocol mask.
               If cpuFilterProfileIPProtocol set to ipMask, this field will be refered.
               It will work with its member rule field,cpuFilterL3RuleProtocol, 
               to caculate a range of IP protocol which is really care.
               The value is in HEX format.
              "
           DEFVAL  { 'FF'h }   
           ::= { ipv4cpuFilterProfileEntry 8 }
        ipv4cpuFilterProfileDstIpAddrMask OBJECT-TYPE 
           SYNTAX      IpAddress
           MAX-ACCESS  read-write 
           STATUS      current 
           DESCRIPTION 
              "The CPUInterfaceFilter Profile destination IP address mask.
               If DST-IP is turn on in cpuFilterProfileMask, 
               it will work with its member rule field,cpuFilterL3RuleDstIpAddr, 
               to caculate a range of IP address which is really care.
               The value is in HEX format, for example:
               '255.255.255.0' is presented to 'FFFFFF00'
              "
           DEFVAL  { 'FFFFFFFF'h }
           ::= { ipv4cpuFilterProfileEntry 9 }
        
        
        ipv4cpuFilterProfileSrcIpAddrMask OBJECT-TYPE 
           SYNTAX      IpAddress
           MAX-ACCESS  read-write 
           STATUS      current 
           DESCRIPTION 
              "The CPUInterfaceFilter Profile source IP address mask.
               If SRC-IP is turn on in cpuFilterProfileMask, 
               it will work with its member rule field,cpuFilterL3RuleSrcIpAddr, 
               to caculate a range of IP address which is really care.
               The value is in HEX format, for example:
               '255.255.255.0' is presented to 'FFFFFF00'
              "
           DEFVAL  { 'FFFFFFFF'h }
           ::= { ipv4cpuFilterProfileEntry 10 }
        
        ipv4cpuFilterProfileDstPortMask OBJECT-TYPE 
           SYNTAX      OCTET STRING
           MAX-ACCESS  read-write 
           STATUS      current 
           DESCRIPTION 
              "The CPUInterfaceFilter Profile UDP/TCP destination port mask.
               If DST-PORT is turn on in cpuFilterProfileMask, 
               it will work with its member rule field,cpuFilterL3RuleTcpUdpDstPort, 
               to caculate a range of destination port which is really care.
               The value is in HEX format.
              "
           DEFVAL  { 'FFFF'h }   
           ::= { ipv4cpuFilterProfileEntry 11 }
           
        
        ipv4cpuFilterProfileSrcPortMask OBJECT-TYPE 
           SYNTAX      OCTET STRING
           MAX-ACCESS  read-write 
           STATUS      current 
           DESCRIPTION 
              "The CPUInterfaceFilter Profile UDP/TCP source port mask.
               If SRC-PORT is turn on in cpuFilterProfileMask, 
               it will work with its member rule field,cpuFilterL3RuleTcpUdpSrcPort, 
               to caculate a range of source port which is really care.
               The value is in HEX format.
              "
           DEFVAL  { 'FFFF'h }     
           ::= { ipv4cpuFilterProfileEntry 12 }   

        ipv4cpuFilterProfileStatus OBJECT-TYPE 
           SYNTAX      RowStatus
           MAX-ACCESS  read-create 
           STATUS      current 
           DESCRIPTION 
               " This object indicates the status of this entry, can only be set to
                 'createAndWait','active' and 'destroy'. 
                 When the value of the entry status is 'createAndWait', it could be 
                 set to 'active' only if the three values of cpuFilterProfileType,
                 cpuFilterProfileMask and ProtocolType are not conflicted.
               "
        
           ::= { ipv4cpuFilterProfileEntry 15 }

-------------------------------------------------------------------------------------------

        cpuFilterProfileTable OBJECT-TYPE 
           SYNTAX      SEQUENCE OF CpuFilterProfileEntry
           MAX-ACCESS  not-accessible 
           STATUS      current 
           DESCRIPTION 
               " A table to CPUInterfaceFilter profile .
               "
           ::= { cpuFilterProfile 2 }
        
        cpuFilterProfileEntry OBJECT-TYPE 
           SYNTAX      CpuFilterProfileEntry
           MAX-ACCESS  not-accessible 
           STATUS      current 
           DESCRIPTION 
               " Each entry in this table is a CPUInterfaceFilter profile.
                 Index to the table is CPUInterfaceFilter profile ID. "
           INDEX { cpuFilterProfileNo}
           ::= { cpuFilterProfileTable 1 }
           
        CpuFilterProfileEntry ::= 
           SEQUENCE { 
              cpuFilterProfileNo 
                 Integer32, 
              cpuFilterProfileType 
                 INTEGER, 
              cpuFilterProfileRuleCount 
                 Integer32,  
              cpuFilterProfileMask 
                 OCTET STRING,
              cpuFilterProfileDstMacAddrMask 
                 MacAddress,          
              cpuFilterProfileSrcMacAddrMask 
                 MacAddress,         
              cpuFilterProfileIPProtocol  
                 INTEGER, 
              cpuFilterProfileIPProtocolMask  
                 OCTET STRING,  
              cpuFilterProfileDstIpAddrMaskType  
                 INTEGER, 
              cpuFilterProfileDstIpAddrMask 
                 Ipv6Address,
              cpuFilterProfileSrcIpAddrMaskType  
                 INTEGER, 
              cpuFilterProfileSrcIpAddrMask 
                 Ipv6Address,
              cpuFilterProfileDstPortMask
                 OCTET STRING,         
              cpuFilterProfileSrcPortMask
                 OCTET STRING,       
              cpuFilterProfileStatus
                 RowStatus
          }
        
        cpuFilterProfileNo OBJECT-TYPE 
           SYNTAX      Integer32 (1..3)
           MAX-ACCESS  read-only 
           STATUS      current 
           DESCRIPTION 
              "The CPUInterfaceFilter Profile ID. The ID 1 to 50 is user-defined CPUInterfaceFilter,
               and the ID more than 50 is reserved for system-defined CPUInterfaceFilter.
               The user only allow to create user-defined CPUInterfaceFilter ID.
               And system-defined CPUInterfaceFilter is read only."
           ::= { cpuFilterProfileEntry 1 }
        
        cpuFilterProfileType OBJECT-TYPE 
           SYNTAX   INTEGER  {
                          l2 (1),
                          l3 (2)
                       }
           MAX-ACCESS   read-write 
           STATUS      current 
           DESCRIPTION 
              "The CPUInterfaceFilter Profile type, possible value are
              l2 (1) - for MAC-based rule, 
              l3 (2) - for IPv4-based rule,
              "
           ::= { cpuFilterProfileEntry 2 }
        
        cpuFilterProfileRuleCount  OBJECT-TYPE 
           SYNTAX   Integer32 (0..65535)
           MAX-ACCESS   read-only 
           STATUS      current 
           DESCRIPTION 
              "The number of rules in this profile."
           ::= { cpuFilterProfileEntry 3 }
              
              
        cpuFilterProfileMask OBJECT-TYPE 
           SYNTAX   OCTET STRING
           MAX-ACCESS   read-write  
           STATUS      current 
           DESCRIPTION 
              "Indicate which field want to care in the packet.
               Turn on the following bits to select the following items
               Type        Item                   BIT         
               ------------------------------------------
               L2          DST-MAC                0 (LSB)        
               L2          SRC-MAC                1         
               L2          VID                    2         
               L2          8021P-PRIORITY         3         
               L2          ETHER-TYPE             4         
               L3          DSCP                   5         
               L3          ICMP-TYPE              6         
               L3          ICMP-CODE              7         
               L3          IGMP-TYPE              8         
               L3          DST-IP                 9         
               L3          SRC-IP                 10        
               L3          DST-PORT               11        
               L3          SRC-PORT               12        
               L3          TCPFLAG                13 (MSB)
               L3          TRAFFIC-CLASS          21
               -------------------------------------------
               
               The value is in Hex format.
              "
           ::= { cpuFilterProfileEntry 4 }
       

        cpuFilterProfileDstMacAddrMask OBJECT-TYPE 
           SYNTAX      MacAddress
           MAX-ACCESS  read-write 
           STATUS      current 
           DESCRIPTION 
              "The CPUInterfaceFilter Profile destination MAC address mask.
               If DST-MAC is turn on in cpuFilterProfileMask, 
               it will work with its member rule field,cpuFilterL2RuleDstMacAddr, 
               to caculate a range of MAC address which is really care.
              "
           ::= { cpuFilterProfileEntry 5 }
        
        
        cpuFilterProfileSrcMacAddrMask OBJECT-TYPE 
           SYNTAX      MacAddress
           MAX-ACCESS  read-write 
           STATUS      current 
           DESCRIPTION 
              "The CPUInterfaceFilter Profile source MAC address mask.
               If SRC-MAC is turn on in cpuFilterProfileMask, 
               it will work with its member rule field,cpuFilterL2RuleSrcMacAddr, 
               to caculate a range of MAC address which is really care.
              "
           ::= { cpuFilterProfileEntry 6 }
        
        
        cpuFilterProfileIPProtocol OBJECT-TYPE 
           SYNTAX   INTEGER  {  
                         none(0),   
                                         icmp(1),
                                         igmp(2),
                                         tcp(6),
                                         udp(17)
                         ,ipMask(255)
                        }
           MAX-ACCESS  read-write 
           STATUS      current 
           DESCRIPTION 
              "Indicate which IP Protocol will be care in this profile.
               Only profile type is l3 can set the IP protocol.
               For others, this field will be none.
              "
           ::= { cpuFilterProfileEntry 7 } 
        cpuFilterProfileIPProtocolMask OBJECT-TYPE 
           SYNTAX      OCTET STRING
           MAX-ACCESS  read-write 
           STATUS      current 
           DESCRIPTION 
              "The CPUInterfaceFilter Profile IP protocol mask.
               If cpuFilterProfileIPProtocol set to ipMask, this field will be refered.
               It will work with its member rule field,cpuFilterL3RuleProtocol, 
               to caculate a range of IP protocol which is really care.
               The value is in HEX format.
              "
           DEFVAL  { 'FF'h }   
           ::= { cpuFilterProfileEntry 8 }

		cpuFilterProfileDstIpAddrMaskType OBJECT-TYPE
	          SYNTAX    INTEGER {
                        iPv4 (1),
                        iPv6 (2)
              }
              MAX-ACCESS  read-write
              STATUS      current
	          DESCRIPTION
                  "IPv6 Address type."
              ::= { cpuFilterProfileEntry 9 }

        cpuFilterProfileDstIpAddrMask OBJECT-TYPE 
           SYNTAX      Ipv6Address
           MAX-ACCESS  read-write 
           STATUS      current 
           DESCRIPTION 
              "The CPUInterfaceFilter Profile destination IP address mask.
               If DST-IP is turn on in cpuFilterProfileMask, 
               it will work with its member rule field,cpuFilterL3RuleDstIpAddr, 
               to caculate a range of IP address which is really care.
               The value is in HEX format, for example:
               '255.255.255.0' is presented to 'FFFFFF00'
              "
           DEFVAL  { 'FFFFFFFF'h }
           ::= { cpuFilterProfileEntry 10 }
        
		cpuFilterProfileSrcIpAddrMaskType OBJECT-TYPE
	          SYNTAX    INTEGER {
                        iPv4 (1),
                        iPv6 (2)
              }
              MAX-ACCESS  read-write
              STATUS      current
	          DESCRIPTION
                  "IPv6 Address type."
              ::= { cpuFilterProfileEntry 11 }

        cpuFilterProfileSrcIpAddrMask OBJECT-TYPE 
           SYNTAX      Ipv6Address
           MAX-ACCESS  read-write 
           STATUS      current 
           DESCRIPTION 
              "The CPUInterfaceFilter Profile source IP address mask.
               If SRC-IP is turn on in cpuFilterProfileMask, 
               it will work with its member rule field,cpuFilterL3RuleSrcIpAddr, 
               to caculate a range of IP address which is really care.
               The value is in HEX format, for example:
               '255.255.255.0' is presented to 'FFFFFF00'
              "
           DEFVAL  { 'FFFFFFFF'h }
           ::= { cpuFilterProfileEntry 12 }
        
        cpuFilterProfileDstPortMask OBJECT-TYPE 
           SYNTAX      OCTET STRING
           MAX-ACCESS  read-write 
           STATUS      current 
           DESCRIPTION 
              "The CPUInterfaceFilter Profile UDP/TCP destination port mask.
               If DST-PORT is turn on in cpuFilterProfileMask, 
               it will work with its member rule field,cpuFilterL3RuleTcpUdpDstPort, 
               to caculate a range of destination port which is really care.
               The value is in HEX format.
              "
           DEFVAL  { 'FFFF'h }   
           ::= { cpuFilterProfileEntry 13 }
           
        
        cpuFilterProfileSrcPortMask OBJECT-TYPE 
           SYNTAX      OCTET STRING
           MAX-ACCESS  read-write 
           STATUS      current 
           DESCRIPTION 
              "The CPUInterfaceFilter Profile UDP/TCP source port mask.
               If SRC-PORT is turn on in cpuFilterProfileMask, 
               it will work with its member rule field,cpuFilterL3RuleTcpUdpSrcPort, 
               to caculate a range of source port which is really care.
               The value is in HEX format.
              "
           DEFVAL  { 'FFFF'h }     
           ::= { cpuFilterProfileEntry 14 }   

        cpuFilterProfileStatus OBJECT-TYPE 
           SYNTAX      RowStatus
           MAX-ACCESS  read-create 
           STATUS      current 
           DESCRIPTION 
               " This object indicates the status of this entry, can only be set to
                 'createAndWait','active' and 'destroy'. 
                 When the value of the entry status is 'createAndWait', it could be 
                 set to 'active' only if the three values of cpuFilterProfileType,
                 cpuFilterProfileMask and ProtocolType are not conflicted.
               "
        
           ::= { cpuFilterProfileEntry 15 }


        -- ------------------------------------------------------------------ 
        -- L2 Filter Group --------------------------------------------------
        cpuFilterL2Rule       OBJECT IDENTIFIER ::= { companyCPUInterfaceFilterGroup 2 }

        cpuFilterL2RuleTable OBJECT-TYPE 
        
           SYNTAX      SEQUENCE OF CpuFilterL2RuleEntry
           MAX-ACCESS  not-accessible 
           STATUS      current 
           DESCRIPTION 
               "A table to configure L2 filter rules in the system."
           ::= { cpuFilterL2Rule 1 }
        
        cpuFilterL2RuleEntry OBJECT-TYPE 
           SYNTAX      CpuFilterL2RuleEntry
           MAX-ACCESS  not-accessible 
           STATUS      current 
           DESCRIPTION 
               "Each entry in this table is a L2 filter rule.
               Index to the table is the L2 filter number and Profile ID."
           INDEX { cpuFilterL2ProfileID, cpuFilterL2AccessID}
           ::= { cpuFilterL2RuleTable 1 }
           
        CpuFilterL2RuleEntry ::= 
           SEQUENCE { 
              cpuFilterL2ProfileID 
                 Integer32,        
              cpuFilterL2AccessID 
                 Integer32, 
              cpuFilterL2RuleEtherType 
                 Integer32, 
              cpuFilterL2RuleDstMacAddr 
                 MacAddress, 
              cpuFilterL2RuleSrcMacAddr 
                 MacAddress, 
              cpuFilterL2RuleVlanId 
                 Integer32,
              cpuFilterL2Rule1pPriority
                 Integer32,
              cpuFilterL2RuleDstMacAddrMask 
                 MacAddress, 
              cpuFilterL2RuleSrcMacAddrMask 
                 MacAddress,   
              cpuFilterL2RuleInPortList 
                 PortList,
              cpuFilterL2RuleAction 
                 INTEGER, 
              cpuFilterL2RuleStatus
                 RowStatus      
          }
        
        cpuFilterL2ProfileID OBJECT-TYPE 
           SYNTAX      Integer32 (1..3)
           MAX-ACCESS  read-only 
           STATUS      current 
           DESCRIPTION 
              "L2 Filter rule ID."
           ::= { cpuFilterL2RuleEntry 1 }
            
        cpuFilterL2AccessID OBJECT-TYPE 
           SYNTAX      Integer32 (1..5)
           MAX-ACCESS  read-only  
           STATUS      current 
           DESCRIPTION 
              "CPUInterfaceFilter Profile ID which this rule join."
           DEFVAL  { 1 }
           ::= { cpuFilterL2RuleEntry 2 }
           
        cpuFilterL2RuleEtherType OBJECT-TYPE 
           SYNTAX      Integer32  (-1 | 1501..65535)
           MAX-ACCESS  read-write 
           STATUS      current 
           DESCRIPTION 
              "The value in the Type/Len field of a frame that will
              be matched to trigger this filter. The default value of
              this object is '-1', which means the rule don't care this 
              condition."
           DEFVAL  { -1 }
           ::= { cpuFilterL2RuleEntry 3 }
                      
        cpuFilterL2RuleDstMacAddr OBJECT-TYPE 
           SYNTAX      MacAddress
           MAX-ACCESS  read-write 
           STATUS      current 
           DESCRIPTION 
              "Destination MAC address to be matched with the packet. By Default, the
               Destination Mac Address will be zero,which means the rule don't care this 
               condition." 
           ::= { cpuFilterL2RuleEntry 4 }
        
        cpuFilterL2RuleSrcMacAddr OBJECT-TYPE 
           SYNTAX      MacAddress
           MAX-ACCESS  read-write 
           STATUS      current 
           DESCRIPTION 
              "Source MAC address to be matched with the packet. By Default, the Source 
               Mac Address will be zero, which means the rule don't care this condition..
               address"
           ::= { cpuFilterL2RuleEntry 5 }
                
        cpuFilterL2RuleVlanId OBJECT-TYPE 
           SYNTAX      Integer32 (-1..4094)
           MAX-ACCESS  read-write 
           STATUS      current 
           DESCRIPTION 
              "Vlan Id to be filtered. In case of Provider bridges, This Vlan Id will
              be treated as customer Vlan Id. By Default, the value will be '-1', 
              which means the rule don't care this condition."
           DEFVAL  { -1 }
           ::= { cpuFilterL2RuleEntry 6 }        
         
         cpuFilterL2Rule1pPriority OBJECT-TYPE 
           SYNTAX      Integer32  (-1..7)
           MAX-ACCESS  read-write 
           STATUS      current 
           DESCRIPTION 
              "802.1p priority to be matched with the packet. By Default, the value
              will be '-1', which means the rule don't care this condition."
          DEFVAL  { -1 }
           ::= { cpuFilterL2RuleEntry 7 }   
        
        cpuFilterL2RuleDstMacAddrMask OBJECT-TYPE 
           SYNTAX      MacAddress
           MAX-ACCESS  read-only 
           STATUS      current 
           DESCRIPTION 
              "The MAC address Mask work for Destination MAC address.
              This field is read-only and copy from it's Profile setting."
              
           ::= { cpuFilterL2RuleEntry 8 }

        cpuFilterL2RuleSrcMacAddrMask OBJECT-TYPE 
           SYNTAX      MacAddress
           MAX-ACCESS  read-only 
           STATUS      current 
           DESCRIPTION 
              "The MAC address Mask work for Source MAC address.
              This field is read-only and copy from it's Profile setting."

           ::= { cpuFilterL2RuleEntry 9 } 

        cpuFilterL2RuleInPortList OBJECT-TYPE 
           SYNTAX      PortList
           MAX-ACCESS  read-write 
           STATUS      current 
           DESCRIPTION 
              "Specifies the complete set of ports over which this filter is applied
               for packets ingress at ports in this list." 
           ::= { cpuFilterL2RuleEntry 10 }
        
        cpuFilterL2RuleAction OBJECT-TYPE 
           SYNTAX      INTEGER {
                          allow (1)
                          ,drop  (2)
                       }
           MAX-ACCESS  read-write 
           STATUS      current 
           DESCRIPTION 
              "Specifies the action to be taken on the packet if the filter
              rule matches.
              If the action is 'allow', the packet will be forwarded according
              to the forwarding rules.
              If the action is 'drop', the packet will be discarded."
           DEFVAL  { allow } 
           ::= { cpuFilterL2RuleEntry 11 }

         cpuFilterL2RuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { cpuFilterL2RuleEntry 14 }    

        -- ------------------------------------------------------------------ 
        -- L3 Filter Group --------------------------------------------------
        cpuFilterL3Rule       OBJECT IDENTIFIER ::= { companyCPUInterfaceFilterGroup 3 }
         
        cpuFilterL3RuleTable OBJECT-TYPE 
           SYNTAX      SEQUENCE OF CpuFilterL3RuleEntry
           MAX-ACCESS  not-accessible 
           STATUS      current 
           DESCRIPTION 
               " A table to configure L3 filter rules in the system.
               "
           ::= { cpuFilterL3Rule 1 }

        cpuFilterL3RuleEntry OBJECT-TYPE 
           SYNTAX      CpuFilterL3RuleEntry
           MAX-ACCESS  not-accessible 
           STATUS      current 
           DESCRIPTION 
               " Each entry in this table is a L3 filter rule.
                 Index to the table is L3 filter number and Profile ID."
           INDEX { cpuFilterL3RuleProfileNo, cpuFilterL3RuleAccessID}
           ::= { cpuFilterL3RuleTable 1 }

        CpuFilterL3RuleEntry ::= 
           SEQUENCE { 
              cpuFilterL3RuleProfileNo 
                 Integer32, 
              cpuFilterL3RuleAccessID 
                 Integer32,
              cpuFilterL3RuleProtocol  
                 INTEGER, 
              cpuFilterL3RuleProtocolMask  
                 OCTET STRING, 
              cpuFilterL3RuleICMPMessageType 
                 Integer32, 
              cpuFilterL3RuleICMPMessageCode 
                 Integer32, 
              cpuFilterL3RuleDstIpAddr 
                 IpAddress, 
              cpuFilterL3RuleSrcIpAddr 
                 IpAddress, 
              cpuFilterL3RuleDstIpAddrMask 
                 IpAddress, 
              cpuFilterL3RuleSrcIpAddrMask 
                 IpAddress,
              cpuFilterL3RuleTcpUdpDstPort
                 Integer32, 
              cpuFilterL3RuleTcpUdpSrcPort
                 Integer32, 
              cpuFilterL3RuleTcpUdpDstPortMask
                OCTET STRING,         
              cpuFilterL3RuleTcpUdpSrcPortMask
                OCTET STRING,         
              cpuFilterL3RuleTcpAckBit
                 INTEGER,
              cpuFilterL3RuleTcpRstBit
                 INTEGER,
              cpuFilterL3RuleTcpUrgBit
                 INTEGER,
              cpuFilterL3RuleTcpPshBit
                 INTEGER,
              cpuFilterL3RuleTcpSynBit
                 INTEGER,
              cpuFilterL3RuleTcpFinBit
                 INTEGER,
              cpuFilterL3RuleDscp
                 Integer32,
              cpuFilterL3RuleIgmpType
                 Integer32,
              cpuFilterL3RulePortList 
                 PortList,
              cpuFilterL3RuleAction 
                 INTEGER, 
              cpuFilterL3RuleStatus
                 RowStatus
          }
        
        cpuFilterL3RuleProfileNo OBJECT-TYPE 
           SYNTAX      Integer32 (1..5)
           MAX-ACCESS  read-only 
           STATUS      current 
           DESCRIPTION 
              "L3 Filter rule ID."
           ::= { cpuFilterL3RuleEntry 1 }
            
        cpuFilterL3RuleAccessID OBJECT-TYPE 
           SYNTAX      Integer32 (1..3)
           MAX-ACCESS  read-only  
           STATUS      current 
           DESCRIPTION 
              "The Profile ID which this rule join."
           ::= { cpuFilterL3RuleEntry 2 }
              
        cpuFilterL3RuleProtocol OBJECT-TYPE 
           SYNTAX      INTEGER  {     
                                         icmp(1),
                                         igmp(2),
                                         tcp(6),
                                         udp(17)
                        } 
           MAX-ACCESS  read-write 
           STATUS      current 
           DESCRIPTION 
              " The type of protocol to be checked against the packet."
           ::= { cpuFilterL3RuleEntry 3 }
           
        cpuFilterL3RuleProtocolMask OBJECT-TYPE 
           SYNTAX      OCTET STRING
           MAX-ACCESS  read-only 
           STATUS      current 
           DESCRIPTION 
              "The IP protocol mask.
               This field is read-only and copy from it's Profile setting.
               It will work with the other field,cpuFilterL3RuleProtocol, 
               to caculate a range of IP protocol which is really care.
               The value is in HEX format.
              "
           DEFVAL  { 'FF'h }   
           ::= { cpuFilterL3RuleEntry 4 }

        cpuFilterL3RuleICMPMessageType OBJECT-TYPE 
           SYNTAX      Integer32 (-1..255)
           MAX-ACCESS  read-write 
           STATUS      current 
           DESCRIPTION 
             " The message type to be checked against the packet. If the
              message type matches with the packet, then the packet will be
              dropped / allowed based on the action set in cpuFilterL3RuleAction.
              The default value is '-1',which means the rule don't care this 
              condition.
              Some ICMP message types are: 
                   echoReply(0),
                   destinationUnreachable(3),
                   sourceQuench(4),
                   redirect(5),
                   echoRequest(8),
                   timeExceeded(11),
                   parameterProblem(12),
                   timestampRequest(13),
                   timestampReply(14),
                   informationRequest(15),
                   informationReply(16),
                   addressMaskRequest(17),
                   addressMaskReply (18),
              "
           DEFVAL  { -1 }
           ::= { cpuFilterL3RuleEntry 5 }
        
        cpuFilterL3RuleICMPMessageCode OBJECT-TYPE 
           SYNTAX      Integer32 (-1..255)
           MAX-ACCESS  read-write 
           STATUS      current 
           DESCRIPTION 
              " The message code to be checked against the packet. If the
              packet matches with the message code, then the packet will
              be dropped / allowed based on the action set in cpuFilterL3RuleAction.
              The default value is '-1', which means the rule don't care this 
              condition.
              Some ICMP message codes are :
                   networkUnreachable(0),
                   hostUnreachable(1),
                   protocolUnreachable(2),
                   portUnreachable(3),
                   fragmentNeed(4),
                   sourceRouteFail(5),
                   destNetworkUnknown(6),
                   destHostUnknown(7),
                   srcHostIsolated(8),
                   destNetworkAdminProhibited(9),
                   destHostAdminProhibited(10),
                   networkUnreachableTOS(11),
                   hostUnreachableTOS(12),
              "
           DEFVAL   { -1 }
           ::= { cpuFilterL3RuleEntry 6 }

        cpuFilterL3RuleDstIpAddr OBJECT-TYPE 
           SYNTAX      IpAddress
           MAX-ACCESS  read-write 
           STATUS      current 
           DESCRIPTION 
              "Destination IP address to be matched with the packet.
               The default value will be zero, which means the rule 
               don't care this condition."
           DEFVAL  { '00000000'h }
           ::= { cpuFilterL3RuleEntry 7 }
        
        cpuFilterL3RuleSrcIpAddr OBJECT-TYPE 
           SYNTAX      IpAddress
           MAX-ACCESS  read-write 
           STATUS      current 
           DESCRIPTION 
              "Source IP address to be matched with the packet.
              The default value will be zero, which means the 
              rule don't care this condition."

           DEFVAL  { '00000000'h }
           ::= { cpuFilterL3RuleEntry 8 }
        
        cpuFilterL3RuleDstIpAddrMask OBJECT-TYPE 
           SYNTAX      IpAddress
           MAX-ACCESS  read-only 
           STATUS      current 
           DESCRIPTION 
              "The IP subnet mask for Destination IP address.
               This field is read-only and copy from it's Profile setting.
              "

           DEFVAL  { 'FFFFFFFF'h }
           ::= { cpuFilterL3RuleEntry 9 }
        
        cpuFilterL3RuleSrcIpAddrMask OBJECT-TYPE 
           SYNTAX      IpAddress
           MAX-ACCESS  read-only 
           STATUS      current 
           DESCRIPTION 
              "The IP subnet mask for Source IP address.
               This field is read-only and copy from it's Profile setting.
              "
           
           DEFVAL  { 'FFFFFFFF'h }
           ::= { cpuFilterL3RuleEntry 10 }

        cpuFilterL3RuleTcpUdpDstPort OBJECT-TYPE
           SYNTAX      Integer32 (-1..65535)
           MAX-ACCESS  read-write
           STATUS      current
           DESCRIPTION
              "The TCP / UDP destination port. The default value is -1, 
              which means the rule don't care this condition."
           DEFVAL   { -1 }
           ::= { cpuFilterL3RuleEntry 11 }
        
        cpuFilterL3RuleTcpUdpSrcPort OBJECT-TYPE
           SYNTAX      Integer32 (-1..65535)
           MAX-ACCESS  read-write
           STATUS      current
           DESCRIPTION
              "The TCP / UDP source port. The default value is -1, 
              which means the rule don't care this condition."
           DEFVAL   { -1 }
           ::= { cpuFilterL3RuleEntry 12 }
           
        cpuFilterL3RuleTcpUdpDstPortMask OBJECT-TYPE
           SYNTAX      OCTET STRING
           MAX-ACCESS  read-only
           STATUS      current
           DESCRIPTION
              "The TCP / UDP Destination port Mask.
               This field is read-only and copy from it's Profile setting.
              "
           ::= { cpuFilterL3RuleEntry 13 }

        cpuFilterL3RuleTcpUdpSrcPortMask OBJECT-TYPE
           SYNTAX      OCTET STRING
           MAX-ACCESS  read-only
           STATUS      current
           DESCRIPTION
              "The TCP / UDP Source port Mask.
               This field is read-only and copy from it's Profile setting.
              "
           ::= { cpuFilterL3RuleEntry 14 } 
           
        cpuFilterL3RuleTcpAckBit                OBJECT-TYPE
                SYNTAX  INTEGER {
                                    dontcare(-1),
                                                        establish(1),
                                                        notEstablish(2)
                                                }
                MAX-ACCESS      read-create
                STATUS          current
                DESCRIPTION
                        " The TCP ACK bit to be checked against the packet. The default 
                        value is 'dontcare'(-1), which means the rule don't care this 
                        condition."
                DEFVAL  { dontcare }
                ::= { cpuFilterL3RuleEntry 15 }
        
        cpuFilterL3RuleTcpRstBit         OBJECT-TYPE
                SYNTAX  INTEGER {
                                    dontcare(-1),
                                                        establish(1),
                                                        notEstablish(2)
                                                }
                MAX-ACCESS      read-create
                STATUS          current
                DESCRIPTION
                        " The TCP RST bit to be checked against the packet. The default 
                        value is 'dontcare'(-1), which means the rule don't care this 
                        condition."
                DEFVAL  { dontcare }
                ::= { cpuFilterL3RuleEntry 16 }
        
        cpuFilterL3RuleTcpUrgBit         OBJECT-TYPE
                SYNTAX  INTEGER {
                                    dontcare(-1),
                                                        establish(1),
                                                        notEstablish(2)
                                                }
                MAX-ACCESS      read-create
                STATUS          current
                DESCRIPTION
                        " The TCP Urg bit to be checked against the packet. The default 
                        value is 'dontcare'(-1), which means the rule don't care this 
                        condition."
                DEFVAL  { dontcare }
                ::= { cpuFilterL3RuleEntry 17 }
                
        cpuFilterL3RuleTcpPshBit         OBJECT-TYPE
                SYNTAX  INTEGER {
                                    dontcare(-1),
                                                        establish(1),
                                                        notEstablish(2)
                                                }
                MAX-ACCESS      read-create
                STATUS          current
                DESCRIPTION
                        " The TCP Psh bit to be checked against the packet. The default 
                        value is 'dontcare'(-1). which means the rule don't care this 
                        condition."
                DEFVAL  { dontcare }
                ::= { cpuFilterL3RuleEntry 18 } 
        
        cpuFilterL3RuleTcpSynBit         OBJECT-TYPE
                SYNTAX  INTEGER {
                                    dontcare(-1),
                                                        establish(1),
                                                        notEstablish(2)
                                                }
                MAX-ACCESS      read-create
                STATUS          current
                DESCRIPTION
                        " The TCP Syn bit to be checked against the packet. The default 
                        value is 'dontcare'(-1), which means the rule don't care this condition."
                DEFVAL  { dontcare }
                ::= { cpuFilterL3RuleEntry 19 }

        cpuFilterL3RuleTcpFinBit         OBJECT-TYPE
                SYNTAX  INTEGER {
                                    dontcare(-1),
                                                        establish(1),
                                                        notEstablish(2)
                                                }
                MAX-ACCESS      read-create
                STATUS          current
                DESCRIPTION
                        " The TCP Fin bit to be checked against the packet. The default 
                        value is 'dontcare'(-1), which means the rule don't care this 
                        condition."
                DEFVAL  { dontcare }
                ::= { cpuFilterL3RuleEntry 20 }
        
        cpuFilterL3RuleDscp             OBJECT-TYPE
                SYNTAX          Integer32 (-1..63)
                MAX-ACCESS      read-create
                STATUS          current
                DESCRIPTION
                        " The IP Dscp value to be checked against the packet. 
                A default value is '-1', which means the rule don't 
                care this condition."
                DEFVAL  { -1 }
                ::= { cpuFilterL3RuleEntry 21 }
                
        cpuFilterL3RuleIgmpType  OBJECT-TYPE
                SYNTAX      Integer32 (-1..255)
           MAX-ACCESS  read-write 
           STATUS      current 
           DESCRIPTION 
             " The IGMP Type to be checked against the packet.A default value is '-1',
             which means the rule don't care this condition."
           DEFVAL  { -1 }
           ::= { cpuFilterL3RuleEntry 22 }
           
        cpuFilterL3RulePortList OBJECT-TYPE 
           SYNTAX      PortList
           MAX-ACCESS  read-write 
           STATUS      current 
           DESCRIPTION 
              "Specifies the complete set of ports over which if the packet arrives
              this filter rule will be applicable."

           ::= { cpuFilterL3RuleEntry 23 }

        cpuFilterL3RuleAction OBJECT-TYPE 
           SYNTAX      INTEGER {
                          allow (1)
                          ,drop  (2)
                       }
           MAX-ACCESS  read-write 
           STATUS      current 
           DESCRIPTION 
              "Specifies the action to be taken on the packet if the filter
              rule matches."
           DEFVAL  { allow } 
           ::= { cpuFilterL3RuleEntry 24 }

        cpuFilterL3RuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { cpuFilterL3RuleEntry 27 }


        -- L3 IPv6 Filter Group --------------------------------------------------
         
        cpuFilterv6L3RuleTable OBJECT-TYPE 
           SYNTAX      SEQUENCE OF CpuFilterv6L3RuleEntry
           MAX-ACCESS  not-accessible 
           STATUS      current 
           DESCRIPTION 
               " A table to configure L3 filter rules in the system.
               "
           ::= { cpuFilterL3Rule 2 }

        cpuFilterv6L3RuleEntry OBJECT-TYPE 
           SYNTAX      CpuFilterv6L3RuleEntry
           MAX-ACCESS  not-accessible 
           STATUS      current 
           DESCRIPTION 
               " Each entry in this table is a L3 filter rule.
                 Index to the table is L3 filter number and Profile ID."
           INDEX { cpuFilterv6L3RuleProfileNo, cpuFilterv6L3RuleAccessID}
           ::= { cpuFilterv6L3RuleTable 1 }

        CpuFilterv6L3RuleEntry ::= 
           SEQUENCE { 
              cpuFilterv6L3RuleProfileNo 
                 Integer32, 
              cpuFilterv6L3RuleAccessID 
                 Integer32,
              cpuFilterv6L3RuleProtocol  
                 INTEGER, 
              cpuFilterv6L3RuleProtocolMask  
                 OCTET STRING, 
              cpuFilterv6L3RuleICMPMessageType 
                 Integer32, 
              cpuFilterv6L3RuleICMPMessageCode 
                 Integer32, 
              cpuFilterv6L3RuleDstIpAddr 
                 Ipv6Address, 
              cpuFilterv6L3RuleSrcIpAddr 
                 Ipv6Address, 
              cpuFilterv6L3RuleDstIpAddrMask 
                 Ipv6Address, 
              cpuFilterv6L3RuleSrcIpAddrMask 
                 Ipv6Address,
              cpuFilterv6L3RuleTcpUdpDstPort
                 Integer32, 
              cpuFilterv6L3RuleTcpUdpSrcPort
                 Integer32, 
              cpuFilterv6L3RuleTcpUdpDstPortMask
                OCTET STRING,         
              cpuFilterv6L3RuleTcpUdpSrcPortMask
                OCTET STRING,         
              cpuFilterv6L3RuleTcpAckBit
                 INTEGER,
              cpuFilterv6L3RuleTcpRstBit
                 INTEGER,
              cpuFilterv6L3RuleTcpUrgBit
                 INTEGER,
              cpuFilterv6L3RuleTcpPshBit
                 INTEGER,
              cpuFilterv6L3RuleTcpSynBit
                 INTEGER,
              cpuFilterv6L3RuleTcpFinBit
                 INTEGER,
              cpuFilterv6L3RuleTrafficClass
                 Integer32,
              cpuFilterv6L3RulePortList 
                 PortList,
              cpuFilterv6L3RuleAction 
                 INTEGER, 
              cpuFilterv6L3RuleStatus
                 RowStatus
          }
        
        cpuFilterv6L3RuleProfileNo OBJECT-TYPE 
           SYNTAX      Integer32 (1..5)
           MAX-ACCESS  read-only 
           STATUS      current 
           DESCRIPTION 
              "L3 Filter rule ID."
           ::= { cpuFilterv6L3RuleEntry 1 }
            
        cpuFilterv6L3RuleAccessID OBJECT-TYPE 
           SYNTAX      Integer32 (1..3)
           MAX-ACCESS  read-only  
           STATUS      current 
           DESCRIPTION 
              "The Profile ID which this rule join."
           ::= { cpuFilterv6L3RuleEntry 2 }
              
        cpuFilterv6L3RuleProtocol OBJECT-TYPE 
           SYNTAX      INTEGER  {     
                                         icmp(1),
                                         tcp(6),
                                         udp(17)
                        } 
           MAX-ACCESS  read-write 
           STATUS      current 
           DESCRIPTION 
              " The type of protocol to be checked against the packet."
           ::= { cpuFilterv6L3RuleEntry 3 }
           
        cpuFilterv6L3RuleProtocolMask OBJECT-TYPE 
           SYNTAX      OCTET STRING
           MAX-ACCESS  read-only 
           STATUS      current 
           DESCRIPTION 
              "The IP protocol mask.
               This field is read-only and copy from it's Profile setting.
               It will work with the other field,cpuFilterL3RuleProtocol, 
               to caculate a range of IP protocol which is really care.
               The value is in HEX format.
              "
           DEFVAL  { 'FF'h }   
           ::= { cpuFilterv6L3RuleEntry 4 }

        cpuFilterv6L3RuleICMPMessageType OBJECT-TYPE 
           SYNTAX      Integer32 (-1..255)
           MAX-ACCESS  read-write 
           STATUS      current 
           DESCRIPTION 
             " The message type to be checked against the packet. If the
              message type matches with the packet, then the packet will be
              dropped / allowed based on the action set in cpuFilterL3RuleAction.
              The default value is '-1',which means the rule don't care this 
              condition.
              Some ICMP message types are: 
                   echoReply(0),
                   destinationUnreachable(3),
                   sourceQuench(4),
                   redirect(5),
                   echoRequest(8),
                   timeExceeded(11),
                   parameterProblem(12),
                   timestampRequest(13),
                   timestampReply(14),
                   informationRequest(15),
                   informationReply(16),
                   addressMaskRequest(17),
                   addressMaskReply (18),
              "
           DEFVAL  { -1 }
           ::= { cpuFilterv6L3RuleEntry 5 }
        
        cpuFilterv6L3RuleICMPMessageCode OBJECT-TYPE 
           SYNTAX      Integer32 (-1..255)
           MAX-ACCESS  read-write 
           STATUS      current 
           DESCRIPTION 
              " The message code to be checked against the packet. If the
              packet matches with the message code, then the packet will
              be dropped / allowed based on the action set in cpuFilterL3RuleAction.
              The default value is '-1', which means the rule don't care this 
              condition.
              Some ICMP message codes are :
                   networkUnreachable(0),
                   hostUnreachable(1),
                   protocolUnreachable(2),
                   portUnreachable(3),
                   fragmentNeed(4),
                   sourceRouteFail(5),
                   destNetworkUnknown(6),
                   destHostUnknown(7),
                   srcHostIsolated(8),
                   destNetworkAdminProhibited(9),
                   destHostAdminProhibited(10),
                   networkUnreachableTOS(11),
                   hostUnreachableTOS(12),
              "
           DEFVAL   { -1 }
           ::= { cpuFilterv6L3RuleEntry 6 }

        cpuFilterv6L3RuleDstIpAddr OBJECT-TYPE 
           SYNTAX      Ipv6Address
           MAX-ACCESS  read-write 
           STATUS      current 
           DESCRIPTION 
              "Destination IP address to be matched with the packet.
               The default value will be zero, which means the rule 
               don't care this condition."
           DEFVAL  { '00000000'h }
           ::= { cpuFilterv6L3RuleEntry 7 }
        
        cpuFilterv6L3RuleSrcIpAddr OBJECT-TYPE 
           SYNTAX      Ipv6Address
           MAX-ACCESS  read-write 
           STATUS      current 
           DESCRIPTION 
              "Source IP address to be matched with the packet.
              The default value will be zero, which means the 
              rule don't care this condition."

           DEFVAL  { '00000000'h }
           ::= { cpuFilterv6L3RuleEntry 8 }
        
        cpuFilterv6L3RuleDstIpAddrMask OBJECT-TYPE 
           SYNTAX      Ipv6Address
           MAX-ACCESS  read-only 
           STATUS      current 
           DESCRIPTION 
              "The IP subnet mask for Destination IP address.
               This field is read-only and copy from it's Profile setting.
              "

           DEFVAL  { 'FFFFFFFF'h }
           ::= { cpuFilterv6L3RuleEntry 9 }
        
        cpuFilterv6L3RuleSrcIpAddrMask OBJECT-TYPE 
           SYNTAX      Ipv6Address
           MAX-ACCESS  read-only 
           STATUS      current 
           DESCRIPTION 
              "The IP subnet mask for Source IP address.
               This field is read-only and copy from it's Profile setting.
              "
           
           DEFVAL  { 'FFFFFFFF'h }
           ::= { cpuFilterv6L3RuleEntry 10 }

        cpuFilterv6L3RuleTcpUdpDstPort OBJECT-TYPE
           SYNTAX      Integer32 (-1..65535)
           MAX-ACCESS  read-write
           STATUS      current
           DESCRIPTION
              "The TCP / UDP destination port. The default value is -1, 
              which means the rule don't care this condition."
           DEFVAL   { -1 }
           ::= { cpuFilterv6L3RuleEntry 11 }
        
        cpuFilterv6L3RuleTcpUdpSrcPort OBJECT-TYPE
           SYNTAX      Integer32 (-1..65535)
           MAX-ACCESS  read-write
           STATUS      current
           DESCRIPTION
              "The TCP / UDP source port. The default value is -1, 
              which means the rule don't care this condition."
           DEFVAL   { -1 }
           ::= { cpuFilterv6L3RuleEntry 12 }
           
        cpuFilterv6L3RuleTcpUdpDstPortMask OBJECT-TYPE
           SYNTAX      OCTET STRING
           MAX-ACCESS  read-only
           STATUS      current
           DESCRIPTION
              "The TCP / UDP Destination port Mask.
               This field is read-only and copy from it's Profile setting.
              "
           ::= { cpuFilterv6L3RuleEntry 13 }

        cpuFilterv6L3RuleTcpUdpSrcPortMask OBJECT-TYPE
           SYNTAX      OCTET STRING
           MAX-ACCESS  read-only
           STATUS      current
           DESCRIPTION
              "The TCP / UDP Source port Mask.
               This field is read-only and copy from it's Profile setting.
              "
           ::= { cpuFilterv6L3RuleEntry 14 } 
           
        cpuFilterv6L3RuleTcpAckBit                OBJECT-TYPE
                SYNTAX  INTEGER {
                                    dontcare(-1),
                                                        establish(1),
                                                        notEstablish(2)
                                                }
                MAX-ACCESS      read-create
                STATUS          current
                DESCRIPTION
                        " The TCP ACK bit to be checked against the packet. The default 
                        value is 'dontcare'(-1), which means the rule don't care this 
                        condition."
                DEFVAL  { dontcare }
                ::= { cpuFilterv6L3RuleEntry 15 }
        
        cpuFilterv6L3RuleTcpRstBit         OBJECT-TYPE
                SYNTAX  INTEGER {
                                    dontcare(-1),
                                                        establish(1),
                                                        notEstablish(2)
                                                }
                MAX-ACCESS      read-create
                STATUS          current
                DESCRIPTION
                        " The TCP RST bit to be checked against the packet. The default 
                        value is 'dontcare'(-1), which means the rule don't care this 
                        condition."
                DEFVAL  { dontcare }
                ::= { cpuFilterv6L3RuleEntry 16 }
        
        cpuFilterv6L3RuleTcpUrgBit         OBJECT-TYPE
                SYNTAX  INTEGER {
                                    dontcare(-1),
                                                        establish(1),
                                                        notEstablish(2)
                                                }
                MAX-ACCESS      read-create
                STATUS          current
                DESCRIPTION
                        " The TCP Urg bit to be checked against the packet. The default 
                        value is 'dontcare'(-1), which means the rule don't care this 
                        condition."
                DEFVAL  { dontcare }
                ::= { cpuFilterv6L3RuleEntry 17 }
                
        cpuFilterv6L3RuleTcpPshBit         OBJECT-TYPE
                SYNTAX  INTEGER {
                                    dontcare(-1),
                                                        establish(1),
                                                        notEstablish(2)
                                                }
                MAX-ACCESS      read-create
                STATUS          current
                DESCRIPTION
                        " The TCP Psh bit to be checked against the packet. The default 
                        value is 'dontcare'(-1). which means the rule don't care this 
                        condition."
                DEFVAL  { dontcare }
                ::= { cpuFilterv6L3RuleEntry 18 } 
        
        cpuFilterv6L3RuleTcpSynBit         OBJECT-TYPE
                SYNTAX  INTEGER {
                                    dontcare(-1),
                                                        establish(1),
                                                        notEstablish(2)
                                                }
                MAX-ACCESS      read-create
                STATUS          current
                DESCRIPTION
                        " The TCP Syn bit to be checked against the packet. The default 
                        value is 'dontcare'(-1), which means the rule don't care this condition."
                DEFVAL  { dontcare }
                ::= { cpuFilterv6L3RuleEntry 19 }

        cpuFilterv6L3RuleTcpFinBit         OBJECT-TYPE
                SYNTAX  INTEGER {
                                    dontcare(-1),
                                                        establish(1),
                                                        notEstablish(2)
                                                }
                MAX-ACCESS      read-create
                STATUS          current
                DESCRIPTION
                        " The TCP Fin bit to be checked against the packet. The default 
                        value is 'dontcare'(-1), which means the rule don't care this 
                        condition."
                DEFVAL  { dontcare }
                ::= { cpuFilterv6L3RuleEntry 20 }
        
        cpuFilterv6L3RuleTrafficClass             OBJECT-TYPE
                SYNTAX          Integer32 (-1..63)
                MAX-ACCESS      read-create
                STATUS          current
                DESCRIPTION
                        " The IP Dscp value to be checked against the packet. 
                A default value is '-1', which means the rule don't 
                care this condition."
                DEFVAL  { -1 }
                ::= { cpuFilterv6L3RuleEntry 21 }
           
        cpuFilterv6L3RulePortList OBJECT-TYPE 
           SYNTAX      PortList
           MAX-ACCESS  read-write 
           STATUS      current 
           DESCRIPTION 
              "Specifies the complete set of ports over which if the packet arrives
              this filter rule will be applicable."

           ::= { cpuFilterv6L3RuleEntry 22 }

        cpuFilterv6L3RuleAction OBJECT-TYPE 
           SYNTAX      INTEGER {
                          allow (1)
                          ,drop  (2)
                       }
           MAX-ACCESS  read-write 
           STATUS      current 
           DESCRIPTION 
              "Specifies the action to be taken on the packet if the filter
              rule matches."
           DEFVAL  { allow } 
           ::= { cpuFilterv6L3RuleEntry 23 }

        cpuFilterv6L3RuleStatus OBJECT-TYPE 
           SYNTAX      RowStatus
           MAX-ACCESS  read-create 
           STATUS      current 
           DESCRIPTION 
                "This object indicates the status of this entry. An entry is
                created in this table when this object is SET to 'createAndWait'.
                The entry in this table is used when the status of this object 
                is SET 'active'. The entry in this table is not used when this 
                object is SET 'notInService'. An entry created in this table is
                be deleted when this object is SET 'destroy'."
           ::= { cpuFilterv6L3RuleEntry 24 }

      snmpGlobalState OBJECT-TYPE
           SYNTAX      INTEGER {
                          enabled(1),
                          disabled(2)
                       }
           MAX-ACCESS  read-write
           STATUS      current
           DESCRIPTION
               "This object is for enabling or disabling SNMP Community function."

           ::= { companySNMPV3 1 }

      snmpV3User                    OBJECT IDENTIFIER ::= { companySNMPV3 2 }
      snmpV3Group                   OBJECT IDENTIFIER ::= { companySNMPV3 3 }
      snmpV3ViewTree                OBJECT IDENTIFIER ::= { companySNMPV3 4 }
      snmpV3Community               OBJECT IDENTIFIER ::= { companySNMPV3 5 }
      snmpV3Host                    OBJECT IDENTIFIER ::= { companySNMPV3 6 }

      snmpV3EngineID OBJECT-TYPE
              SYNTAX  SnmpEngineID
              MAX-ACCESS read-write
              STATUS current
		      DESCRIPTION
		         "An SNMP engine's administratively-unique identifier.

                 In a simple agent, this value is always that agent's
                 own snmpEngineID value.

                 The value can also take the value of the snmpEngineID
                 of a remote SNMP engine with which this user can
                 communicate."

         ::=  { companySNMPV3  7 }

      snmpV3Trap                    OBJECT IDENTIFIER ::= { companySNMPV3 8 }

      -- ----------------------------------------------------------------
      -- The snmpV3User group
      -- ----------------------------------------------------------------

      snmpV3UserTable OBJECT-TYPE
           SYNTAX SEQUENCE OF SnmpV3UserEntry
           MAX-ACCESS not-accessible
           STATUS     current
           DESCRIPTION
              ""
           ::= { snmpV3User 1 }

      snmpV3UserEntry OBJECT-TYPE
           SYNTAX      SnmpV3UserEntry
           MAX-ACCESS  not-accessible
           STATUS      current
           DESCRIPTION
              ""
           INDEX { snmpV3UserName , snmpV3UserVersion}
           ::= { snmpV3UserTable 1 }

      SnmpV3UserEntry ::= SEQUENCE {
                snmpV3UserName                      SnmpAdminString,
                snmpV3UserVersion                   INTEGER,
                snmpV3UserGroupName                 SnmpAdminString,
                snmpV3UserAuthProtocol              INTEGER,
                snmpV3UserAuthProtocolPassword      SnmpAdminString,
                snmpV3UserPrivProtocol              INTEGER,
                snmpV3UserPrivProtocolPassword      SnmpAdminString,
                snmpV3UserStatus                    RowStatus
            }

      snmpV3UserName       OBJECT-TYPE
            SYNTAX       SnmpAdminString (SIZE(1..32))
            MAX-ACCESS   read-only
            STATUS       current
            DESCRIPTION "A human readable string representing the name of
                         the user.

                         This is the (User-based Security) Model dependent
                         security ID.
                        "
      ::= { snmpV3UserEntry 1 }

        snmpV3UserVersion  OBJECT-TYPE
            SYNTAX    INTEGER {
                      v1            (1),
                      v2c	        (2),
                      v3            (3)
                   }
            MAX-ACCESS   read-only
            STATUS       current
            DESCRIPTION "A human readable string representing the name of
                         the user.

                         This is the (User-based Security) Model dependent
                         security ID.
                        "
            ::= { snmpV3UserEntry 2 }


        snmpV3UserGroupName      OBJECT-TYPE
            SYNTAX       SnmpAdminString (SIZE(1..32))
            MAX-ACCESS   read-create
            STATUS       current
            DESCRIPTION "The name of the group to which this entry (e.g., the
                         combination of securityModel and securityName)
                         belongs.

                         This groupName is used as index into the
                         vacmAccessTable to select an access control policy.
                         However, a value in this table does not imply that an
                         instance with the value exists in table vacmAccesTable.
                        "
            ::= { snmpV3UserEntry 3 }

        snmpV3UserAuthProtocol OBJECT-TYPE
            SYNTAX    INTEGER {
                      none          (1),
                      md5	        (2),
                      sha           (3)
                   }
            MAX-ACCESS   read-create
            STATUS       current
            DESCRIPTION "An indication of whether messages sent on behalf of
                 this user to/from the SNMP engine identified by
                 usmUserEngineID, can be authenticated, and if so,
                 the type of authentication protocol which is used.

                 An instance of this object is created concurrently
                 with the creation of any other object instance for
                 the same user (i.e., as part of the processing of
                 the set operation which creates the first object
                 instance in the same conceptual row).

                 If an initial set operation (i.e. at row creation time)
                 tries to set a value for an unknown or unsupported
                 protocol, then a 'wrongValue' error must be returned.

                 The value will be overwritten/set when a set operation
                 is performed on the corresponding instance of
                 UserCloneFrom.

                 Once instantiated, the value of such an instance of
                 this object can only be changed via a set operation to
                 the value of the NoAuthProtocol.

                 If a set operation tries to change the value of an


                 existing instance of this object to any value other
                 than NoAuthProtocol, then an 'inconsistentValue'
                 error must be returned.

                 If a set operation tries to set the value to the
                 NoAuthProtocol while the UserPrivProtocol value
                 in the same row is not equal to NoPrivProtocol,
                 then an 'inconsistentValue' error must be returned.
                 That means that an SNMP command generator application
                 must first ensure that the UserPrivProtocol is set
                 to the NoPrivProtocol value before it can set
                 the UserAuthProtocol value to NoAuthProtocol.
                "
            ::= { snmpV3UserEntry 4 }

        snmpV3UserAuthProtocolPassword OBJECT-TYPE
        SYNTAX       SnmpAdminString (SIZE(1..32))
            MAX-ACCESS   read-create
            STATUS       current
            DESCRIPTION  ""
            ::= { snmpV3UserEntry 5 }


        snmpV3UserPrivProtocol OBJECT-TYPE
            SYNTAX    INTEGER {
                      none          (1),
                      des	        (2)
                   }
            MAX-ACCESS   read-create
            STATUS       current
            DESCRIPTION "An indication of whether messages sent on behalf of
                 this user to/from the SNMP engine identified by
                 usmUserEngineID, can be protected from disclosure,
                 and if so, the type of privacy protocol which is used.

                 An instance of this object is created concurrently
                 with the creation of any other object instance for
                 the same user (i.e., as part of the processing of
                 the set operation which creates the first object
                 instance in the same conceptual row).

                 If an initial set operation (i.e. at row creation time)
                 tries to set a value for an unknown or unsupported
                 protocol, then a 'wrongValue' error must be returned.

                 The value will be overwritten/set when a set operation
                 is performed on the corresponding instance of
                 usmUserCloneFrom.

                 Once instantiated, the value of such an instance of
                 this object can only be changed via a set operation to
                 the value of the NoPrivProtocol.

                 If a set operation tries to change the value of an
                 existing instance of this object to any value other
                 than NoPrivProtocol, then an 'inconsistentValue'
                 error must be returned.

                 Note that if any privacy protocol is used, then you
                 must also use an authentication protocol. In other
                 words, if usmUserPrivProtocol is set to anything else
                 than NoPrivProtocol, then the corresponding instance
                 of usmUserAuthProtocol cannot have a value of

                 usmNoAuthProtocol. If it does, then an
                 'inconsistentValue' error must be returned.
                "
            ::= { snmpV3UserEntry 6 }

        snmpV3UserPrivProtocolPassword OBJECT-TYPE
        SYNTAX       SnmpAdminString (SIZE(1..32))
            MAX-ACCESS   read-create
            STATUS       current
            DESCRIPTION  ""
            ::= { snmpV3UserEntry 7 }


        snmpV3UserStatus  OBJECT-TYPE
            SYNTAX       RowStatus
            MAX-ACCESS   read-create
            STATUS       current
            DESCRIPTION "The status of this conceptual row.

                 Until instances of all corresponding columns are
                 appropriately configured, the value of the
                 corresponding instance of the usmUserStatus column
                 is 'notReady'.

                 In particular, a newly created row for a user who
                 employs authentication, cannot be made active until the
                 corresponding usmUserCloneFrom and usmUserAuthKeyChange
                 have been set.

                 Further, a newly created row for a user who also
                 employs privacy, cannot be made active until the
                 usmUserPrivKeyChange has been set.

                 The RowStatus TC [RFC2579] requires that this
                 DESCRIPTION clause states under which circumstances
                 other objects in this row can be modified:

                 The value of this object has no effect on whether
                 other objects in this conceptual row can be modified,
                 except for usmUserOwnAuthKeyChange and
                 usmUserOwnPrivKeyChange. For these 2 objects, the
                 value of usmUserStatus MUST be active.
                "
    ::= { snmpV3UserEntry 8 }


      -- ----------------------------------------------------------------
      -- The snmpV3Group group
      -- ----------------------------------------------------------------
        snmpV3GroupTable OBJECT-TYPE
           SYNTAX SEQUENCE OF SnmpV3GroupEntry
           MAX-ACCESS not-accessible
           STATUS     current
           DESCRIPTION
              ""
           ::= { snmpV3Group 1 }

        snmpV3GroupEntry OBJECT-TYPE
           SYNTAX      SnmpV3GroupEntry
           MAX-ACCESS  not-accessible
           STATUS      current
           DESCRIPTION
              ""
           INDEX { snmpV3GroupName ,snmpV3GroupSecurityModel ,snmpV3GroupSecurityLevel}
           ::= { snmpV3GroupTable 1 }

        SnmpV3GroupEntry ::= SEQUENCE {
                snmpV3GroupName              SnmpAdminString,
                snmpV3GroupSecurityModel     INTEGER,
                snmpV3GroupSecurityLevel     SnmpSecurityLevel,
                snmpV3GroupReadViewName      SnmpAdminString,
                snmpV3GroupWriteViewName     SnmpAdminString,
                snmpV3GroupNotifyViewName    SnmpAdminString,
                snmpV3GroupStatus            RowStatus
            }

        snmpV3GroupName  OBJECT-TYPE
            SYNTAX       SnmpAdminString (SIZE(1..32))
            MAX-ACCESS   read-only
            STATUS       current
            DESCRIPTION "The name of the group to which this entry (e.g., the
                         combination of securityModel and securityName)
                         belongs.

                         This groupName is used as index into the
                         vacmAccessTable to select an access control policy.
                         However, a value in this table does not imply that an
                         instance with the value exists in table vacmAccesTable.
                        "
            ::= { snmpV3GroupEntry 1 }

        snmpV3GroupSecurityModel OBJECT-TYPE
            SYNTAX    INTEGER {
                      v1            (1),
                      v2c	        (2),
                      v3            (3)
                   }
            MAX-ACCESS   read-only
            STATUS       current
            DESCRIPTION "In order to gain the access rights allowed by this
                         conceptual row, this securityModel must be in use.
                        "
            ::= { snmpV3GroupEntry 2 }

        snmpV3GroupSecurityLevel OBJECT-TYPE
            SYNTAX       SnmpSecurityLevel
            MAX-ACCESS   read-only
            STATUS       current
            DESCRIPTION "The minimum level of security required in order to
                         gain the access rights allowed by this conceptual
                         row.  A securityLevel of noAuthNoPriv is less than
                         authNoPriv which in turn is less than authPriv.

                         If multiple entries are equally indexed except for
                         this vacmAccessSecurityLevel index, then the entry
                         which has the highest value for
                         vacmAccessSecurityLevel is selected.
                        "
            ::= { snmpV3GroupEntry 3 }

        snmpV3GroupReadViewName OBJECT-TYPE
            SYNTAX       SnmpAdminString (SIZE(0..32))
            MAX-ACCESS   read-create
            STATUS       current
            DESCRIPTION "The value of an instance of this object identifies
                         the MIB view of the SNMP context to which this
                         conceptual row authorizes read access.

                         The identified MIB view is that one for which the
                         vacmViewTreeFamilyViewName has the same value as the
                         instance of this object; if the value is the empty
                         string or if there is no active MIB view having this
                         value of vacmViewTreeFamilyViewName, then no access
                         is granted.
                        "
        --    DEFVAL      { ''H }   -- -- the empty string --
            ::= { snmpV3GroupEntry 4 }

        snmpV3GroupWriteViewName OBJECT-TYPE
            SYNTAX       SnmpAdminString (SIZE(0..32))
            MAX-ACCESS   read-create
            STATUS       current
            DESCRIPTION "The value of an instance of this object identifies
                         the MIB view of the SNMP context to which this
                         conceptual row authorizes write access.

                         The identified MIB view is that one for which the
                         vacmViewTreeFamilyViewName has the same value as the
                         instance of this object; if the value is the empty
                         string or if there is no active MIB view having this
                         value of vacmViewTreeFamilyViewName, then no access
                         is granted.
                        "
        --    DEFVAL      { ''H }   -- -- the empty string --

            ::= { snmpV3GroupEntry 5 }

        snmpV3GroupNotifyViewName OBJECT-TYPE
            SYNTAX       SnmpAdminString (SIZE(0..32))
            MAX-ACCESS   read-create
            STATUS       current
            DESCRIPTION "The value of an instance of this object identifies
                         the MIB view of the SNMP context to which this
                         conceptual row authorizes access for notifications.

                         The identified MIB view is that one for which the
                         vacmViewTreeFamilyViewName has the same value as the
                         instance of this object; if the value is the empty
                         string or if there is no active MIB view having this
                         value of vacmViewTreeFamilyViewName, then no access
                         is granted.
                        "
        --    DEFVAL      { ''H }   -- -- the empty string --
            ::= { snmpV3GroupEntry 6 }

        snmpV3GroupStatus     OBJECT-TYPE
            SYNTAX       RowStatus
            MAX-ACCESS   read-create
            STATUS       current
            DESCRIPTION "The status of this conceptual row.

                         The  RowStatus TC [RFC2579] requires that this
                         DESCRIPTION clause states under which circumstances
                         other objects in this row can be modified:

                         The value of this object has no effect on whether
                         other objects in this conceptual row can be modified.
                        "
            ::= { snmpV3GroupEntry 7 }


      -- ----------------------------------------------------------------
      -- The snmpV3ViewTree group
      -- ----------------------------------------------------------------
        snmpV3ViewTreeTable OBJECT-TYPE
           SYNTAX SEQUENCE OF SnmpV3ViewTreeEntry
           MAX-ACCESS not-accessible
           STATUS     current
           DESCRIPTION
              ""
           ::= { snmpV3ViewTree 1 }

        snmpV3ViewTreeEntry OBJECT-TYPE
           SYNTAX      SnmpV3ViewTreeEntry
           MAX-ACCESS  not-accessible
           STATUS      current
           DESCRIPTION
              ""
           INDEX { snmpV3viewTreeName ,snmpV3viewTreeSubtree }
           ::= { snmpV3ViewTreeTable 1 }

        SnmpV3ViewTreeEntry ::= SEQUENCE
            {
                snmpV3viewTreeName         SnmpAdminString,
                snmpV3viewTreeSubtree      OBJECT IDENTIFIER,
                snmpV3viewTreeMask         OCTET STRING,
                snmpV3viewTreeType         INTEGER,
                snmpV3viewTreeStatus       RowStatus
            }

        snmpV3viewTreeName OBJECT-TYPE
            SYNTAX       SnmpAdminString (SIZE(1..32))
            MAX-ACCESS   read-only
            STATUS       current
            DESCRIPTION "The human readable name for a family of view subtrees.
                        "

            ::= { snmpV3ViewTreeEntry 1 }

        snmpV3viewTreeSubtree OBJECT-TYPE
            SYNTAX       OBJECT IDENTIFIER
            MAX-ACCESS   read-only
            STATUS       current
            DESCRIPTION "The MIB subtree which when combined with the
                         corresponding instance of vacmViewTreeFamilyMask
                         defines a family of view subtrees.
                        "
            ::= { snmpV3ViewTreeEntry 2 }

        snmpV3viewTreeMask OBJECT-TYPE
            SYNTAX       OCTET STRING (SIZE (0..16))
            MAX-ACCESS   read-create
            STATUS       current
            DESCRIPTION "The bit mask which, in combination with the
                         corresponding instance of vacmViewTreeFamilySubtree,
                         defines a family of view subtrees.

                         Each bit of this bit mask corresponds to a
                         sub-identifier of vacmViewTreeFamilySubtree, with the
                         most significant bit of the i-th octet of this octet
                         string value (extended if necessary, see below)
                         corresponding to the (8*i - 7)-th sub-identifier, and
                         the least significant bit of the i-th octet of this
                         octet string corresponding to the (8*i)-th
                         sub-identifier, where i is in the range 1 through 16.

                         Each bit of this bit mask specifies whether or not
                         the corresponding sub-identifiers must match when
                         determining if an OBJECT IDENTIFIER is in this
                         family of view subtrees; a '1' indicates that an
                         exact match must occur; a '0' indicates 'wild card',
                         i.e., any sub-identifier value matches.

                         Thus, the OBJECT IDENTIFIER X of an object instance
                         is contained in a family of view subtrees if, for
                         each sub-identifier of the value of
                         vacmViewTreeFamilySubtree, either:

                           the i-th bit of vacmViewTreeFamilyMask is 0, or

                           the i-th sub-identifier of X is equal to the i-th
                           sub-identifier of the value of
                           vacmViewTreeFamilySubtree.

                         If the value of this bit mask is M bits long and

                         there are more than M sub-identifiers in the
                         corresponding instance of vacmViewTreeFamilySubtree,
                         then the bit mask is extended with 1's to be the
                         required length.

                         Note that when the value of this object is the
                         zero-length string, this extension rule results in
                         a mask of all-1's being used (i.e., no 'wild card'),
                         and the family of view subtrees is the one view
                         subtree uniquely identified by the corresponding
                         instance of vacmViewTreeFamilySubtree.

                         Note that masks of length greater than zero length
                         do not need to be supported.  In this case this
                         object is made read-only.
                        "
        --    DEFVAL      { ''H }
            ::= { snmpV3ViewTreeEntry 3 }

        snmpV3viewTreeType OBJECT-TYPE
            SYNTAX       INTEGER  { included(1), excluded(2) }
            MAX-ACCESS   read-create
            STATUS       current
            DESCRIPTION "Indicates whether the corresponding instances of
                         vacmViewTreeFamilySubtree and vacmViewTreeFamilyMask
                         define a family of view subtrees which is included in
                         or excluded from the MIB view.
                        "
        --    DEFVAL      { included }
            ::= { snmpV3ViewTreeEntry 4 }

        snmpV3viewTreeStatus OBJECT-TYPE
            SYNTAX       RowStatus
            MAX-ACCESS   read-create
            STATUS       current
            DESCRIPTION "The status of this conceptual row.

                         The  RowStatus TC [RFC2579] requires that this
                         DESCRIPTION clause states under which circumstances
                         other objects in this row can be modified:

                         The value of this object has no effect on whether
                         other objects in this conceptual row can be modified.
                        "
            ::= { snmpV3ViewTreeEntry 5 }


      -- ----------------------------------------------------------------
      -- The snmpV3Community group
      -- ----------------------------------------------------------------

        snmpV3CommunityTable OBJECT-TYPE
           SYNTAX SEQUENCE OF SnmpV3CommunityEntry
           MAX-ACCESS not-accessible
           STATUS     current
           DESCRIPTION
              ""
           ::= { snmpV3Community 1 }

        snmpV3CommunityEntry OBJECT-TYPE
           SYNTAX      SnmpV3CommunityEntry
           MAX-ACCESS  not-accessible
           STATUS      current
           DESCRIPTION
              ""
           INDEX { snmpV3CommunityName }
           ::= { snmpV3CommunityTable 1 }

        SnmpV3CommunityEntry ::= SEQUENCE
            {
                snmpV3CommunityName                OCTET STRING,
                snmpV3CommunityPolicy              SnmpAdminString,
                snmpV3CommunityStatus              RowStatus
            }

        snmpV3CommunityName OBJECT-TYPE
            SYNTAX      OCTET STRING
            MAX-ACCESS  read-only
            STATUS      current
            DESCRIPTION
                "The unique index value of a row in this table."
            ::= { snmpV3CommunityEntry 1 }

        snmpV3CommunityPolicy OBJECT-TYPE
            SYNTAX       SnmpAdminString (SIZE(1..32))
            MAX-ACCESS   read-create
            STATUS       current
            DESCRIPTION
                "A human readable string representing the corresponding
                 value of snmpCommunityName in a Security Model
                 independent format."
            ::= { snmpV3CommunityEntry 2 }

        snmpV3CommunityStatus OBJECT-TYPE
            SYNTAX       RowStatus
            MAX-ACCESS   read-create
            STATUS       current
            DESCRIPTION
                "The status of this conceptual row in the
                 snmpCommunityTable.

                 An entry in this table is not qualified for activation
                 until instances of all corresponding columns have been
                 initialized, either through default values, or through
                 Set operations.  The snmpCommunityName and
                 snmpCommunitySecurityName objects must be explicitly set.

                 There is no restriction on setting columns in this table
                 when the value of snmpCommunityStatus is active(1)."
            ::= { snmpV3CommunityEntry 3 }


      -- ----------------------------------------------------------------
      -- The snmpV3Host group
      -- ----------------------------------------------------------------

        ipv4snmpV3HostTable OBJECT-TYPE
           SYNTAX SEQUENCE OF Ipv4snmpV3HostEntry
           MAX-ACCESS not-accessible
           STATUS     obsolete
           DESCRIPTION
              ""
           ::= { snmpV3Host 1 }

        ipv4snmpV3HostEntry OBJECT-TYPE
           SYNTAX      Ipv4snmpV3HostEntry
           MAX-ACCESS  not-accessible
           STATUS      obsolete
           DESCRIPTION
              ""
           INDEX { ipv4snmpV3HostAddress }
           ::= { ipv4snmpV3HostTable 1 }

        Ipv4snmpV3HostEntry ::= SEQUENCE
            {
                ipv4snmpV3HostAddress           IpAddress,
                ipv4snmpV3HostCommunityName     SnmpAdminString,
                ipv4snmpV3HostVersion           INTEGER,
                ipv4snmpV3HostStatus            RowStatus
            }

        ipv4snmpV3HostAddress OBJECT-TYPE
               SYNTAX      IpAddress
               MAX-ACCESS  read-only
               STATUS      obsolete
               DESCRIPTION
                   "This object contains a transport address.  The format of
                    this address depends on the value of the
                    snmpTargetAddrTDomain object. And this object is unique
                    identifier associated with this snmpNotifyEntry."
               ::= { ipv4snmpV3HostEntry 1 }

        ipv4snmpV3HostCommunityName OBJECT-TYPE
               SYNTAX      SnmpAdminString (SIZE(1..32))
               MAX-ACCESS  read-create
               STATUS      obsolete
               DESCRIPTION
                   "The locally arbitrary."
               ::= { ipv4snmpV3HostEntry 2 }


        ipv4snmpV3HostVersion OBJECT-TYPE
               SYNTAX    INTEGER {
                      v1                (1),
                      v2c	            (2),
                      v3NoAuthNoPriv    (3),
                      v3AuthNoPriv      (4),
                      v3AuthPriv        (5)
                   }
               MAX-ACCESS  read-create
               STATUS      obsolete
               DESCRIPTION
                   "The Level of Security to be used when generating
                    SNMP messages using this entry."
               ::= { ipv4snmpV3HostEntry 3 }

        ipv4snmpV3HostStatus OBJECT-TYPE
               SYNTAX       RowStatus
               MAX-ACCESS   read-create
               STATUS       obsolete
               DESCRIPTION
                ""
               ::= { ipv4snmpV3HostEntry 4 }

      -- ----------------------------------------------------------------
      -- The snmpV3Host group
      -- ----------------------------------------------------------------

        snmpV3HostTable OBJECT-TYPE
           SYNTAX SEQUENCE OF SnmpV3HostEntry
           MAX-ACCESS not-accessible
           STATUS     current
           DESCRIPTION
              ""
           ::= { snmpV3Host 2 }

        snmpV3HostEntry OBJECT-TYPE
           SYNTAX      SnmpV3HostEntry
           MAX-ACCESS  not-accessible
           STATUS      current
           DESCRIPTION
              ""
           INDEX { snmpV3HostAddress, snmpV3IPType }
           ::= { snmpV3HostTable 1 }
              
        SnmpV3HostEntry ::= SEQUENCE
            {                
                snmpV3HostAddress           Ipv6Address,
                snmpV3IPType                INTEGER,
                snmpV3HostCommunityName     SnmpAdminString,
                snmpV3HostVersion           INTEGER,
                snmpV3HostInterfaceName     OCTET STRING,
                snmpV3HostStatus            RowStatus       
            }    
        
        snmpV3HostAddress OBJECT-TYPE
               SYNTAX      Ipv6Address
               MAX-ACCESS  read-only
               STATUS      current
               DESCRIPTION
                   "This object contains a transport address.  The format of
                    this address depends on the value of the
                    snmpTargetAddrTDomain object. And this object is unique 
                    identifier associated with this snmpNotifyEntry."
               ::= { snmpV3HostEntry 1 }

        snmpV3IPType OBJECT-TYPE
               SYNTAX    INTEGER {
                      iPv4              (1),
                      iPv6	            (2)
                   }
               MAX-ACCESS  read-only
               STATUS      current
               DESCRIPTION
                   "Type of IP interface."
               ::= { snmpV3HostEntry 2 }
               
        snmpV3HostCommunityName OBJECT-TYPE
               SYNTAX      SnmpAdminString (SIZE(1..32))
               MAX-ACCESS  read-create
               STATUS      current
               DESCRIPTION
                   "The locally arbitrary."
               ::= { snmpV3HostEntry 3 } 
        
        snmpV3HostVersion OBJECT-TYPE
               SYNTAX    INTEGER {
                      v1                (1),
                      v2c	            (2),
                      v3NoAuthNoPriv    (3),
                      v3AuthNoPriv      (4),
                      v3AuthPriv        (5)
                   }
               MAX-ACCESS  read-create
               STATUS      current
               DESCRIPTION
                   "The Level of Security to be used when generating
                    SNMP messages using this entry."
               ::= { snmpV3HostEntry 4 }
               
        snmpV3HostInterfaceName OBJECT-TYPE
               SYNTAX      OCTET STRING
               MAX-ACCESS  read-create
               STATUS      current
               DESCRIPTION
                   "Specifies the interface name when the syslogSrvIP is linklocal address."
               ::= { snmpV3HostEntry 5 }
        
        snmpV3HostStatus OBJECT-TYPE
               SYNTAX       RowStatus
               MAX-ACCESS   read-create
               STATUS       current
               DESCRIPTION
                ""
               ::= { snmpV3HostEntry 6 }

      -- ----------------------------------------------------------------
      -- The snmpV3Trap group
      -- ----------------------------------------------------------------

        snmpV3TrapSNMPAuthentication  OBJECT-TYPE
            SYNTAX INTEGER  {
        		 enabled(1),
        		 disabled(2)
            }
            MAX-ACCESS read-write
            STATUS current
            DESCRIPTION
                "This object is for enabling or disabling SNMP login fail
                event trap in the system."
            ::= { snmpV3Trap 1 }

        snmpV3TrapColdStart  OBJECT-TYPE
            SYNTAX INTEGER  {
        		 enabled(1),
        		 disabled(2)
            }
            MAX-ACCESS read-write
            STATUS current
            DESCRIPTION
                "This object is for enabling or disabling devie Bootup event
                trap in the system."
            ::= { snmpV3Trap 2 }

        snmpV3TrapWarmStart  OBJECT-TYPE
            SYNTAX INTEGER  {
        		 enabled(1),
        		 disabled(2)
            }
            MAX-ACCESS read-write
            STATUS current
            DESCRIPTION
                "This object is for enabling or disabling devie Bootup event
                trap in the system."
            ::= { snmpV3Trap 3 }

        snmpV3TrapLinkUpDown  OBJECT-TYPE
            SYNTAX INTEGER  {
        		 enabled(1),
        		 disabled(2)
            }
            MAX-ACCESS read-write
            STATUS current
            DESCRIPTION
                "This object is for enabling or disabling Copper link up / link down
                event trap in the system."
            ::= { snmpV3Trap 4 }

        snmpV3TrapRSTPStateChange  OBJECT-TYPE
            SYNTAX INTEGER  {
        		 enabled(1),
        		 disabled(2)
            }
            MAX-ACCESS read-write
            STATUS current
            DESCRIPTION
                "This object is for enabling or disabling RSTP topology change
                event trap in the system."
            ::= { snmpV3Trap 5 }

        snmpV3TrapFirmUpgrade   OBJECT-TYPE
            SYNTAX INTEGER  {
        		 enabled(1),
        		 disabled(2)
            }
            MAX-ACCESS read-write
            STATUS current
            DESCRIPTION
                "This object is for enabling or disabling Firmware upgrade
                suess or fail event trap in the system."
            ::= { snmpV3Trap 6 }

        snmpV3TrapPoePowerOnOff    OBJECT-TYPE
            SYNTAX INTEGER  {
        		 enabled(1),
        		 disabled(2)
            }
            MAX-ACCESS read-write
            STATUS current
            DESCRIPTION
                "This object is for enabling or disabling PoE power
                on /off event in the system."
            ::= { snmpV3Trap 7 }

        snmpV3TrapPoePowerError    OBJECT-TYPE
            SYNTAX INTEGER  {
        		 enabled(1),
        		 disabled(2)
            }
            MAX-ACCESS read-write
            STATUS current
            DESCRIPTION
                "This object is for enabling or disabling PoE power
                error event in the system.
                There are four(short circuit, over load, power denied,
                and thermal shutdown) error types in this event."
            ::= { snmpV3Trap 8 }

        snmpV3TrapOverMaxPowerBudget    OBJECT-TYPE
            SYNTAX INTEGER  {
        		 enabled(1),
        		 disabled(2)
            }
            MAX-ACCESS read-write
            STATUS current
            DESCRIPTION
                "This object is for enabling or disabling PoE over
                max power budget event in the system."
            ::= { snmpV3Trap 9 }
    snmpV3TrapBPDUAttack    OBJECT-TYPE
           SYNTAX      INTEGER {
                          none(1),
                          attackDetected(2),
                          attackCleared(3),
                          both(4)
                       }
           MAX-ACCESS  read-write
           STATUS      current
           DESCRIPTION
               "Used to configure trap settings for BPDU attack protection events."

           DEFVAL  { none }
        ::= { snmpV3Trap 11 }

-- start CAMEO-PORT-SECURITY
    snmpV3TrapPortSecurity    OBJECT-TYPE
        SYNTAX INTEGER {
            enabled(1),
            disabled(2)
        }
        MAX-ACCESS read-write
        STATUS current
        DESCRIPTION
            ""
        ::= { snmpV3Trap 12 }
-- end CAMEO-PORT-SECURITY
-- start CAMEO-IMPBv2
    snmpV3TrapIMPBViolation    OBJECT-TYPE
        SYNTAX INTEGER {
            enabled(1),
            disabled(2)
        }
        MAX-ACCESS read-write
        STATUS current
        DESCRIPTION
            ""
        ::= { snmpV3Trap 13 }
-- end CAMEO-IMPBv2
-- start CAMEO-LBD
    snmpV3TrapLBD    OBJECT-TYPE
        SYNTAX INTEGER {
            enabled(1),
            disabled(2)
        }
        MAX-ACCESS read-write
        STATUS current
        DESCRIPTION
            ""
        ::= { snmpV3Trap 14 }
-- end CAMEO-LBD
-- start CAMEO-DHCP-SCREEN
    snmpV3TrapDHCPServerScreening    OBJECT-TYPE
        SYNTAX INTEGER {
            enabled(1),
            disabled(2)
        }
        MAX-ACCESS read-write
        STATUS current
        DESCRIPTION
            ""
        ::= { snmpV3Trap 15 }
-- end CAMEO-DHCP-SCREEN
    snmpV3TrapDuplicateIPDetected    OBJECT-TYPE
        SYNTAX INTEGER {
            enabled(1),
            disabled(2)
        }
        MAX-ACCESS read-write
        STATUS current
        DESCRIPTION
            "This object is for enabling or disabling send gratuitous
             trap when IP address conflicted in the network."
        ::= { snmpV3Trap 16 }


    snmpV3CommunityEncryption OBJECT-TYPE
        SYNTAX INTEGER {
            enabled(1),
            disabled(2)
        }
        MAX-ACCESS read-write
        STATUS current
        DESCRIPTION
            "This object is for enabling or disabling community encryption."
         ::=  { companySNMPV3  9 }


 
    -- ------------------------------------------------------------------ 
    -- companySyslog
    -- ------------------------------------------------------------------
        syslogSettingGroup          OBJECT IDENTIFIER ::= { companySyslog 1 }

syslogEnable OBJECT-TYPE
   SYNTAX       INTEGER {
                enable(1),
                disabled(2)
               }
   MAX-ACCESS  read-write 
   STATUS      current 
   DESCRIPTION 
      "This object is for enabling or disabling syslog alert features in
       the system and the syslog will save to flash or send to remote 
       syslog server.
       System Logs record and manage events, as well as report errors and 
       informational messages."

   DEFVAL  { disabled } 
   ::= { syslogSettingGroup 1 }


syslogSaveMode OBJECT-TYPE
   SYNTAX       INTEGER {
                onDemand(0),
                timeInterval(1),
                logTrigger(2)
               }
   MAX-ACCESS  read-write 
   STATUS      current 
   DESCRIPTION 
      "This object is for choosing the method to save syslog into flash."

   DEFVAL  { logTrigger } 
   ::= { syslogSettingGroup 2 }

syslogSaveMinutes OBJECT-TYPE
   SYNTAX       INTEGER (1..65535)
   MAX-ACCESS  read-write 
   STATUS      current 
   DESCRIPTION 
      "When savemode is time interval, it's used to set the interval minutes of 
      system save syslog to flash."
   DEFVAL  { 30 } 
   ::= { syslogSettingGroup 3 }


    -- ------------------------------------------------------------------
    -- smtpRecvMailAddrTable
    -- ------------------------------------------------------------------
            ipv4syslogServerGroup          OBJECT IDENTIFIER ::= { companySyslog 2 }
            
    ipv4syslogServTable  OBJECT-TYPE
        SYNTAX     SEQUENCE OF Ipv4SyslogServEntry 
        MAX-ACCESS not-accessible
        STATUS     current
        DESCRIPTION
           "The table of syslog remote server."
        ::= { ipv4syslogServerGroup 1 }

    ipv4syslogServEntry OBJECT-TYPE
        SYNTAX     Ipv4SyslogServEntry 
        MAX-ACCESS not-accessible
        STATUS     current
        DESCRIPTION
              "The list of syslog remote server entry."

        INDEX { ipv4syslogServIndex }
        ::= { ipv4syslogServTable 1 }

    Ipv4SyslogServEntry  ::= 
            SEQUENCE {
              ipv4syslogServIndex          INTEGER,
              ipv4syslogServAddr           IpAddress,
              ipv4syslogServSeverity       INTEGER,
              ipv4syslogServFacility       INTEGER,
              ipv4syslogServUDPport        INTEGER,
              ipv4syslogServSrvStatus      INTEGER,
              ipv4syslogServSrvRowStatus   RowStatus
              }

    ipv4syslogServIndex OBJECT-TYPE
       SYNTAX       INTEGER (1..4)
       MAX-ACCESS   read-only
       STATUS       current
       DESCRIPTION
         "The index of syslog remote server." 
        ::= { ipv4syslogServEntry  1 }

    ipv4syslogServAddr  OBJECT-TYPE
        SYNTAX      IpAddress
        MAX-ACCESS  read-create
        STATUS      current
        DESCRIPTION
              "The IP Address of syslog remote server."
        ::= { ipv4syslogServEntry  2 }

    ipv4syslogServSeverity OBJECT-TYPE 
        SYNTAX       INTEGER{
                      warning(4),   -- For logging warning messages.
                      information(6),      -- For logging informational messages.
                      all(7)      -- For logging debug messages.
                    }
        MAX-ACCESS  read-create 
        STATUS      current 
        DESCRIPTION 
           "Specifies the log level option to be set for a specific server."
 
        ::= { ipv4syslogServEntry 3 }



    ipv4syslogServFacility OBJECT-TYPE 
       SYNTAX         INTEGER {
                   local0(128),     -- Reserved local use
                   local1(136),     -- Reserved local use
                   local2(144),     -- Reserved local use
                   local3(152),     -- Reserved local use
                   local4(160),     -- Reserved local use
                   local5(168),     -- Reserved local use
                   local6(176),     -- Reserved local use
                   local7(184)      -- Reserved local use
                  }
       MAX-ACCESS  read-create 
       STATUS      current 
       DESCRIPTION 
         "The Syslog standard facilities.
          The facility to be used when sending Syslog messages to this server."

       DEFVAL  { local0 } 
       ::= { ipv4syslogServEntry 4 }

    ipv4syslogServUDPport OBJECT-TYPE
       SYNTAX  INTEGER (514 | 6000..65535)
       MAX-ACCESS  read-create
       STATUS  current
       DESCRIPTION
          "The value is for setting UDP Port."
       ::= { ipv4syslogServEntry 5 }

    ipv4syslogServSrvStatus OBJECT-TYPE 
        SYNTAX       INTEGER {
                enabled(1),
                disabled(2)
               }
        MAX-ACCESS  read-create 
        STATUS      current 
        DESCRIPTION 
           "The status for this server. If enable, system will send message to 
           this server."
 
        ::= { ipv4syslogServEntry 6 }


    ipv4syslogServSrvRowStatus OBJECT-TYPE
       SYNTAX RowStatus
       MAX-ACCESS read-write
       STATUS current
       DESCRIPTION
         "Row status of this server entry."
       ::= { ipv4syslogServEntry 7 }    

    -- ------------------------------------------------------------------
    -- syslogServTable
    -- ------------------------------------------------------------------
            syslogServerGroup          OBJECT IDENTIFIER ::= { companySyslog 3 }

    syslogServTable  OBJECT-TYPE
        SYNTAX     SEQUENCE OF SyslogServEntry 
        MAX-ACCESS not-accessible
        STATUS     current
        DESCRIPTION
           "The table of syslog remote server."
        ::= { syslogServerGroup 1 }

    syslogServEntry OBJECT-TYPE
        SYNTAX     SyslogServEntry 
        MAX-ACCESS not-accessible
        STATUS     current
        DESCRIPTION
              "The list of syslog remote server entry."

        INDEX { syslogServIndex }
        ::= { syslogServTable 1 }

    SyslogServEntry  ::= 
            SEQUENCE {
              syslogServIndex          INTEGER,
              syslogServAddrType       INTEGER,
              syslogServAddr           Ipv6Address,
              syslogServInterfaceName  OCTET STRING,
              syslogServSeverity       INTEGER,
              syslogServFacility       INTEGER,
              syslogServUDPport        INTEGER,
              syslogServSrvStatus      INTEGER,
              syslogServSrvRowStatus   RowStatus
              }

    syslogServIndex OBJECT-TYPE
       SYNTAX       INTEGER (1..4)
       MAX-ACCESS   read-only
       STATUS       current
       DESCRIPTION
         "The index of syslog remote server." 
        ::= { syslogServEntry  1 }

    syslogServAddrType    OBJECT-TYPE
        SYNTAX              INTEGER {
                                 ipv4(1),
                                 ipv6(2)
                              }
        MAX-ACCESS             read-create
        STATUS                 current
        DESCRIPTION
           "Specifies the Address type of server.Address type shall be ipv4 or ipv6."
        ::= { syslogServEntry 2 }

     syslogServAddr         OBJECT-TYPE
         SYNTAX                 Ipv6Address
         MAX-ACCESS             read-create
         STATUS                 current
         DESCRIPTION
            "Specifies the ServerIP to which the syslog shall be forwarded."
         ::= { syslogServEntry 3 }

    syslogServInterfaceName   OBJECT-TYPE
        SYNTAX      OCTET STRING
        MAX-ACCESS  read-create
        STATUS      current
        DESCRIPTION
            "Specifies the interface name when the syslogServInterfaceName is linklocal address."
            ::= { syslogServEntry 4 } 

    syslogServSeverity OBJECT-TYPE 
        SYNTAX       INTEGER{
                      warning(4),   -- For logging warning messages.
                      information(6),      -- For logging informational messages.
                      all(7)      -- For logging debug messages.
                    }
        MAX-ACCESS  read-create 
        STATUS      current 
        DESCRIPTION 
           "Specifies the log level option to be set for a specific server."
 
        ::= { syslogServEntry 5 }



    syslogServFacility OBJECT-TYPE 
       SYNTAX         INTEGER {
                   local0(128),     -- Reserved local use
                   local1(136),     -- Reserved local use
                   local2(144),     -- Reserved local use
                   local3(152),     -- Reserved local use
                   local4(160),     -- Reserved local use
                   local5(168),     -- Reserved local use
                   local6(176),     -- Reserved local use
                   local7(184)      -- Reserved local use
                  }
       MAX-ACCESS  read-create 
       STATUS      current 
       DESCRIPTION 
         "The Syslog standard facilities.
          The facility to be used when sending Syslog messages to this server."

       DEFVAL  { local0 } 
       ::= { syslogServEntry 6 }

    syslogServUDPport OBJECT-TYPE
       SYNTAX  INTEGER (514 | 6000..65535)
       MAX-ACCESS  read-create
       STATUS  current
       DESCRIPTION
          "The value is for setting UDP Port."
       ::= { syslogServEntry 7 }

    syslogServSrvStatus OBJECT-TYPE 
        SYNTAX       INTEGER {
                enabled(1),
                disabled(2)
               }
        MAX-ACCESS  read-write 
        STATUS      current 
        DESCRIPTION 
           "The status for this server. If enable, system will send message to 
           this server."
 
        ::= { syslogServEntry 8 }


    syslogServSrvRowStatus OBJECT-TYPE
       SYNTAX RowStatus
       MAX-ACCESS read-write
       STATUS current
       DESCRIPTION
         "Row status of this server entry."
       ::= { syslogServEntry 9 }   

  
-- LBD Group ------------------------------------------------------    
    sysLBDStateEnable OBJECT-TYPE 
           SYNTAX      INTEGER {
                          enabled(1),
                          disabled(2)
                       }
           MAX-ACCESS  read-write 
           STATUS      current 
           DESCRIPTION 
               "Enable/Disable Loopback detection function.
                The Loopback Detection function is used to detect the loop created
                by a specific port while Spanning Tree Protocol (STP) is not 
                enabled in the network, especially when the down links are hubs 
                or unmanaged switchs.The Switch will automatically shutdown the 
                port and sends a log to the administrator."
        
           DEFVAL  { disabled }
           ::= { companyLBD 1 }
        
    sysLBDMode OBJECT-TYPE 
           SYNTAX      INTEGER {
                          port(1),
                          vlan(2)
                       }
           MAX-ACCESS  read-write 
           STATUS      current 
           DESCRIPTION 
               "Loopback detection function mode."
        
           DEFVAL  { port }
           ::= { companyLBD 2 }

    sysLBDInterval  OBJECT-TYPE
           SYNTAX      Integer32 (1..32767)
           MAX-ACCESS  read-write
           STATUS      current
           DESCRIPTION
            "Set a Loop detection Interval between 1 and 32767 seconds.
             The default is 2 seconds.
             This time interval to be used at counting time seconds to
            resend the CTP packet automatically."  
           DEFVAL  { 2 }
           ::= { companyLBD 3 }
           
    sysLBDRecoverTime  OBJECT-TYPE
           SYNTAX      Integer32 (0 | 60..1000000)
           MAX-ACCESS  read-write
           STATUS      current
           DESCRIPTION
            "This time interval to be used at counting time seconds to
            recover the disabled port automatically. 
            The Loop Detection Recover Time can be set at 0 seconds, 
            or 60 to 1000000 seconds.
            Entering 0 will disable the Loop Detection Recover Time.
            The default is 60 seconds."  
           DEFVAL  { 60 }
           ::= { companyLBD 4 }       
        
        -- LBD Port Control Table
        
        sysLBDCtrlTable OBJECT-TYPE 
           SYNTAX      SEQUENCE OF SysLBDCtrlEntry 
           MAX-ACCESS  not-accessible 
           STATUS      current 
           DESCRIPTION 
              "A table to control Loopback detection features either for 
              the entire switch or for each interface in the switch."
           ::= { companyLBD 5 }
        
        sysLBDCtrlEntry OBJECT-TYPE 
           SYNTAX      SysLBDCtrlEntry 
           MAX-ACCESS  not-accessible 
           STATUS      current 
           DESCRIPTION 
               "An entry appears in this table for each interface 
                in the system."
           INDEX { sysLBDCtrlIndex }
           ::= { sysLBDCtrlTable 1 }
           
        SysLBDCtrlEntry ::= 
           SEQUENCE { 
              sysLBDCtrlIndex
                 Integer32, 
              sysLBDPortStatus 
                 INTEGER, 
              sysLBDPortLoopStatus 
                 INTEGER 
          }
        
        sysLBDCtrlIndex OBJECT-TYPE 
           SYNTAX      Integer32 
           MAX-ACCESS  read-only 
           STATUS      current 
           DESCRIPTION 
              "The interface index of the port for which the configuration
              in this entry applies."
           ::= { sysLBDCtrlEntry 1 }
            
        sysLBDPortStatus OBJECT-TYPE 
           SYNTAX      INTEGER {
                       enabled(1),
                       disabled(2)
                       }
           MAX-ACCESS  read-write 
           STATUS      current 
           DESCRIPTION 
               "Provides control to per port enable or disable the loopback detection 
                function. Default is disabled."
           DEFVAL  { disabled }
           ::= { sysLBDCtrlEntry 2 }
        
        sysLBDPortLoopStatus OBJECT-TYPE 
           SYNTAX      INTEGER {
                       normal(1),
                       loop(2)
                      }
           MAX-ACCESS  read-only 
           STATUS      current 
           DESCRIPTION 
               "The loop status for this port."
           ::= { sysLBDCtrlEntry 3 }

        -- LBD Vlan Loop Table
        
        sysLBDVlanLoopTable OBJECT-TYPE 
           SYNTAX      SEQUENCE OF SysLBDVlanLoopEntry 
           MAX-ACCESS  not-accessible 
           STATUS      current 
           DESCRIPTION 
              "A table to display Loopback detection features by vlan
               mode ."
           ::= { companyLBD 6 }
        
        sysLBDVlanLoopEntry OBJECT-TYPE 
           SYNTAX      SysLBDVlanLoopEntry 
           MAX-ACCESS  not-accessible 
           STATUS      current 
           DESCRIPTION 
               "An entry appears in this table for each interface 
                in the system."
           INDEX { sysLBDVlanLoopIndex }
           ::= { sysLBDVlanLoopTable 1 }
           
        SysLBDVlanLoopEntry ::= 
           SEQUENCE { 
              sysLBDVlanLoopIndex
                 Integer32, 
              sysLBDVlanLoopPorts 
                 PortList
          }
        
        sysLBDVlanLoopIndex OBJECT-TYPE 
           SYNTAX      Integer32 
           MAX-ACCESS  read-only 
           STATUS      current 
           DESCRIPTION 
              "Display port lists loop status by vlan."
           ::= { sysLBDVlanLoopEntry 1 }
            
        sysLBDVlanLoopPorts OBJECT-TYPE 
           SYNTAX      PortList
           MAX-ACCESS  read-only 
           STATUS      current 
           DESCRIPTION 
               "Display port lists loop status by vlan."
           ::= { sysLBDVlanLoopEntry 2 }


    -- ------------------------------------------------------------------    
    -- Mirror Group 
    -- ------------------------------------------------------------------
    

	sysMirrorStatus OBJECT-TYPE 
           SYNTAX      INTEGER {
                          enabled 	     (1),
                          disabled       (2)
                       }
           MAX-ACCESS  read-write 
           STATUS      current 
           DESCRIPTION 
               "Enable/Disable Port Mirroring function.
               Default is disabled.
               Port Mirroring is a method of monitoring network traffic that 
               forwards a copy of each incoming and/or outgoing packet from one 
               port of the Switch to another port where the packet can be studied."
         --    "Provides control over the mirroring feature in the switch." --
        
           DEFVAL  { disabled }
           ::= { companyMirror 1 }
        
        sysMirrorTargetPort OBJECT-TYPE 
           SYNTAX      Integer32
           MAX-ACCESS  read-write 
           STATUS      current 
           DESCRIPTION 
               "Specifies the port to which the mirrored traffic in the system 
                is to be copied." 
           ::= { companyMirror 2 }
        
        sysMirrorCtrlIngressMirroring OBJECT-TYPE 
           SYNTAX      PortList
           MAX-ACCESS  read-write 
           STATUS      current 
           DESCRIPTION 
               "Provides control to enable or disable mirroring of ingress 
                traffic over this interface to the mirrored-to port."
           ::= { companyMirror 3 }
        
        sysMirrorCtrlEgressMirroring OBJECT-TYPE 
           SYNTAX      PortList
           MAX-ACCESS  read-write 
           STATUS      current 
           DESCRIPTION 
               "Provides control to enable or disable mirroring of egress 
                traffic over this interface to the mirrored-to port."
           ::= { companyMirror 4 }
	 
-- ------------------------------------------------------------------     
-- SNTP Timesetting
      -- ------------------------------------------------------------------


ipv4sysSNTPTimeSeconds  OBJECT-TYPE
   SYNTAX      Integer32
   MAX-ACCESS  read-write
   STATUS      obsolete
   DESCRIPTION
       "This object is for setting the system time in seconds 
        from  Epoch (00:00:00 UTC, January 1, 2009). Notice : 
        input value must larger than 1230768000 (00:00:00 UTC, 
        January 1, 2009) and smaller than 2145916799 (23:59:59
        UTC, December 31, 2037)."
   ::= { companySNTPSetting 1 }
   
ipv4sysSNTPFirstServer  OBJECT-TYPE
   SYNTAX      IpAddress
   MAX-ACCESS  read-write
   STATUS      obsolete
   DESCRIPTION
       "SNTP First Server's IP Address"
   ::= { companySNTPSetting 2 }
   
ipv4sysSNTPSecondServer  OBJECT-TYPE
   SYNTAX      IpAddress
   MAX-ACCESS  read-write
   STATUS      obsolete
   DESCRIPTION
       "SNTP Second Server's IP Address"
   ::= { companySNTPSetting 3 }
   
ipv4sysSNTPPollInterval  OBJECT-TYPE
   SYNTAX      Integer32
   MAX-ACCESS  read-write
   STATUS      obsolete
   DESCRIPTION
       "SNTP Poll Interval In Seconds  (30-99999) "
   ::= { companySNTPSetting 4 }

ipv4sysSNTPState  OBJECT-TYPE
   SYNTAX       INTEGER {
                sntp(1),
                local(2)
               }
   MAX-ACCESS  read-write
   STATUS      obsolete
   DESCRIPTION
      "Enable/Disable SNTP function in the system."
   ::= { companySNTPSetting 5 }

-- SNTP TimeZonesetting


ipv4sysSNTPDSTOffset  OBJECT-TYPE
   SYNTAX       INTEGER  {
                offset30min (30),
                offset60min (60),
                offset90min (90),
                offset120min (120)
                }
   MAX-ACCESS   read-write
   STATUS       obsolete
   DESCRIPTION
      "This object is for Daylight Saving Time Offset In (30/60/90/120) Minutes."

   ::= { companySNTPSetting 6 }

ipv4sysSNTPGMTMinutes  OBJECT-TYPE
   SYNTAX       INTEGER  
   MAX-ACCESS   read-write
   STATUS       obsolete
   DESCRIPTION
      "Specifies the Time Zone Offset from GMT in +/- Minutes. (+780 ~ -720)"

   ::= { companySNTPSetting 7 }

ipv4sysSNTPDSTStartMon  OBJECT-TYPE
   SYNTAX       INTEGER  
   MAX-ACCESS   read-write
   STATUS       obsolete
   DESCRIPTION
      "The start month of Daylight Saving Time."

   ::= { companySNTPSetting 8 }

ipv4sysSNTPDSTStartDay  OBJECT-TYPE
   SYNTAX       INTEGER  
   MAX-ACCESS   read-write
   STATUS       obsolete
   DESCRIPTION
      "The start day of Daylight Saving Time."

   ::= { companySNTPSetting 9 }

ipv4sysSNTPDSTStartHour  OBJECT-TYPE
   SYNTAX       INTEGER  
   MAX-ACCESS   read-write
   STATUS       obsolete
   DESCRIPTION
      "The start hour of Daylight Saving Time."

   ::= { companySNTPSetting 10 }

ipv4sysSNTPDSTStartMin  OBJECT-TYPE
   SYNTAX       INTEGER  
   MAX-ACCESS   read-write
   STATUS       obsolete
   DESCRIPTION
      "The start minute of Daylight Saving Time."

   ::= { companySNTPSetting 11 }

ipv4sysSNTPDSTEndMon  OBJECT-TYPE
   SYNTAX       INTEGER  
   MAX-ACCESS   read-write
   STATUS       obsolete
   DESCRIPTION
      "The end month of Daylight Saving Time."

   ::= { companySNTPSetting 12 }

ipv4sysSNTPDSTEndDay  OBJECT-TYPE
   SYNTAX       INTEGER  
   MAX-ACCESS   read-write
   STATUS       obsolete
   DESCRIPTION
      "The end day of Daylight Saving Time."

   ::= { companySNTPSetting 13 }

ipv4sysSNTPDSTEndHour  OBJECT-TYPE
   SYNTAX       INTEGER  
   MAX-ACCESS   read-write
   STATUS       obsolete
   DESCRIPTION
      "The end hour of Daylight Saving Time."

   ::= { companySNTPSetting 14 }

ipv4sysSNTPDSTEndMin  OBJECT-TYPE
   SYNTAX       INTEGER  
   MAX-ACCESS   read-write
   STATUS       obsolete
   DESCRIPTION
      "The end minute of Daylight Saving Time."

   ::= { companySNTPSetting 15 }
	 
ipv4sysSNTPDSTState  OBJECT-TYPE
   SYNTAX       INTEGER {
                annual(1),
                disabled(2)
               }
   MAX-ACCESS  read-write
   STATUS      obsolete
   DESCRIPTION
      "This object is for Annual(1) or Disabled(2) DST state in the system."
   ::= { companySNTPSetting 16 }

--IPv6 sntp server Table

		sysSNTPServerTable OBJECT IDENTIFIER ::= { companySNTPSetting 17 }
              
		sysSNTPTimeSeconds  OBJECT-TYPE
              SYNTAX      Integer32
              MAX-ACCESS  read-write
              STATUS      current
              DESCRIPTION
                  "This object is for setting the system time in seconds 
                   from  Epoch (00:00:00 UTC, January 1, 2009). Notice : 
                   input value must larger than 1230768000 (00:00:00 UTC, 
                   January 1, 2009) and smaller than 2145916799 (23:59:59
                   UTC, December 31, 2037)."
              ::= { sysSNTPServerTable 1 }         
         
		sysSNTPFirstServer  OBJECT-TYPE
              SYNTAX      Ipv6Address
              MAX-ACCESS  read-write
              STATUS      current
              DESCRIPTION
                  "SNTP First Server's IPv6 Address"
              ::= { sysSNTPServerTable 2 }
   
		sysSNTPFirstType OBJECT-TYPE
	          SYNTAX    INTEGER {
                        iPv4 (1),
                        iPv6 (2)
              }
              MAX-ACCESS  read-write
              STATUS      current
	          DESCRIPTION
                  "SNTP First Server's IPv6 Address type."
              ::= { sysSNTPServerTable 3 }

        sysSNTPFirstInterfaceName   OBJECT-TYPE
              SYNTAX      OCTET STRING
              MAX-ACCESS  read-write
              STATUS      current
              DESCRIPTION
                  "Specifies the interface name when the sysSNTPFirstServer is linklocal address."
              ::= { sysSNTPServerTable 4 } 
   
		sysSNTPSecondServer  OBJECT-TYPE
              SYNTAX      Ipv6Address
              MAX-ACCESS  read-write
              STATUS      current
              DESCRIPTION
                  "SNTP Second Server's IPv6 Address"
              ::= { sysSNTPServerTable 5 }    
   
		sysSNTPSecondType OBJECT-TYPE	          
	          SYNTAX    INTEGER {
                        iPv4 (1),
                        iPv6 (2)
              }
              MAX-ACCESS  read-write
              STATUS      current
	          DESCRIPTION
                  "SNTP First Server's IPv6 Address type."
              ::= { sysSNTPServerTable 6 }

        sysSNTPSecondInterfaceName   OBJECT-TYPE
              SYNTAX      OCTET STRING
              MAX-ACCESS  read-write
              STATUS      current
              DESCRIPTION
                  "Specifies the interface name when the sysSNTPSecondServer is linklocal address."
              ::= { sysSNTPServerTable 7 } 
   
		sysSNTPPollInterval  OBJECT-TYPE
   		      SYNTAX      Integer32
   		      MAX-ACCESS  read-write
   		      STATUS      current
   		      DESCRIPTION
       		      "SNTP Poll Interval In Seconds  (30-99999) "
              ::= { sysSNTPServerTable 8 }

		sysSNTPState  OBJECT-TYPE
   		      SYNTAX    INTEGER {
                        sntp(1),
                        local(2)
              }
              MAX-ACCESS  read-write
              STATUS      current
              DESCRIPTION
                  "Enable/Disable SNTP function in the system."
              ::= { sysSNTPServerTable 9 }

  -- SNTPv6 TimeZonesetting

		sysSNTPDSTOffset OBJECT-TYPE
              SYNTAX       INTEGER  {
                           offset30min (30),
                           offset60min (60),
                           offset90min (90),
                           offset120min (120)
              }
              MAX-ACCESS   read-write
              STATUS       current
              DESCRIPTION
                  "This object is for Daylight Saving Time Offset 
                   In (30/60/90/120) Minutes."
              ::= { sysSNTPServerTable 10 }

		sysSNTPGMTMinutes OBJECT-TYPE
              SYNTAX        INTEGER  
              MAX-ACCESS    read-write
              STATUS        current
              DESCRIPTION
                  "Specifies the Time Zone Offset from GMT in +/- Minutes. (+780 ~ -720)"
              ::= { sysSNTPServerTable 11 }

		sysSNTPDSTStartMon  OBJECT-TYPE
              SYNTAX       INTEGER  
              MAX-ACCESS   read-write
              STATUS       current
              DESCRIPTION
                  "The start month of Daylight Saving Time."
              ::= { sysSNTPServerTable 12 }

		sysSNTPDSTStartDay  OBJECT-TYPE
              SYNTAX       INTEGER  
              MAX-ACCESS   read-write
              STATUS       current
              DESCRIPTION
                  "The start day of Daylight Saving Time."
              ::= { sysSNTPServerTable 13 }

		sysSNTPDSTStartHour  OBJECT-TYPE
              SYNTAX       INTEGER  
              MAX-ACCESS   read-write
              STATUS       current
              DESCRIPTION
                  "The start hour of Daylight Saving Time."
              ::= { sysSNTPServerTable 14 }

		sysSNTPDSTStartMin  OBJECT-TYPE
              SYNTAX       INTEGER  
              MAX-ACCESS   read-write
              STATUS       current
              DESCRIPTION
                  "The start minute of Daylight Saving Time."
              ::= { sysSNTPServerTable 15 }

		sysSNTPDSTEndMon  OBJECT-TYPE
              SYNTAX       INTEGER  
              MAX-ACCESS   read-write
              STATUS       current
              DESCRIPTION
                  "The end month of Daylight Saving Time."
              ::= { sysSNTPServerTable 16 }

		sysSNTPDSTEndDay  OBJECT-TYPE
              SYNTAX       INTEGER  
              MAX-ACCESS   read-write
              STATUS       current
              DESCRIPTION
                  "The end day of Daylight Saving Time."
              ::= { sysSNTPServerTable 17 }

		sysSNTPDSTEndHour  OBJECT-TYPE
              SYNTAX       INTEGER  
              MAX-ACCESS   read-write
              STATUS       current
              DESCRIPTION
                  "The end hour of Daylight Saving Time."
              ::= { sysSNTPServerTable 18 }

		sysSNTPDSTEndMin  OBJECT-TYPE
              SYNTAX       INTEGER  
              MAX-ACCESS   read-write
              STATUS       current
              DESCRIPTION
                  "The end minute of Daylight Saving Time."
              ::= { sysSNTPServerTable 19 }	
               
		sysSNTPDSTState  OBJECT-TYPE
              SYNTAX       INTEGER {
                           enabled(1),
                           disabled(2)
              }
              MAX-ACCESS  read-write
              STATUS      current
              DESCRIPTION
                  "This object is for Enabled(1) or Disabled(2) DST state in the system."
              ::= { sysSNTPServerTable 20 }   
	
	

		sysSNTPDSTMethod  OBJECT-TYPE
              SYNTAX       INTEGER {
                           annual(1),
                           repeating(2)
              }
              MAX-ACCESS   read-write
              STATUS       current
              DESCRIPTION
                  "This object is for Annual(1) or Repeating(2) DST method in the system."
              ::= { sysSNTPServerTable 30 }

		sysSNTPDSTRepeatStartMon  OBJECT-TYPE
              SYNTAX       INTEGER  
              MAX-ACCESS   read-write
              STATUS       current
              DESCRIPTION
                  "The start month of Daylight Saving Time in Repeating mode."
              ::= { sysSNTPServerTable 31 }

		sysSNTPDSTRepeatStartWeek  OBJECT-TYPE
              SYNTAX       INTEGER {
                           last(0),
                           first(1),
                           second(2),
                           third(3),
                           fourth(4),
                           fifth(5)
              }
              MAX-ACCESS   read-write
              STATUS       current
              DESCRIPTION
                  "The start week of Daylight Saving Time in Repeating mode."
              ::= { sysSNTPServerTable 32 }


		sysSNTPDSTRepeatStartWeekDay  OBJECT-TYPE
              SYNTAX       INTEGER {
                           sun(0),
                           mon(1),
                           tue(2),
                           wed(3),
                           thu(4),
                           fri(5),
                           sat(6)
              }
              MAX-ACCESS   read-write
              STATUS       current
              DESCRIPTION
                  "The start weekday of Daylight Saving Time in Repeating mode."
              ::= { sysSNTPServerTable 33 }

		sysSNTPDSTRepeatStartHour  OBJECT-TYPE
              SYNTAX       INTEGER  
              MAX-ACCESS   read-write
              STATUS       current
              DESCRIPTION
                  "The start hour of Daylight Saving Time in Repeating mode.."
              ::= { sysSNTPServerTable 34 }

		sysSNTPDSTRepeatStartMin  OBJECT-TYPE
              SYNTAX       INTEGER  
              MAX-ACCESS   read-write
              STATUS       current
              DESCRIPTION
                  "The start minute of Daylight Saving Time in Repeating mode."
              ::= { sysSNTPServerTable 35 }

		sysSNTPDSTRepeatEndMon  OBJECT-TYPE
              SYNTAX       INTEGER  
              MAX-ACCESS   read-write
              STATUS       current
              DESCRIPTION
                  "The end month of Daylight Saving Time in Repeating mode."
              ::= { sysSNTPServerTable 36 }

		sysSNTPDSTRepeatEndWeek  OBJECT-TYPE
              SYNTAX       INTEGER {
                           last(0),
                           first(1),
                           second(2),
                           third(3),
                           fourth(4),
                           fifth(5)
              }
              MAX-ACCESS   read-write
              STATUS       current
              DESCRIPTION
                  "The end week of Daylight Saving Time in Repeating mode."
              ::= { sysSNTPServerTable 37 }


		sysSNTPDSTRepeatEndWeekDay  OBJECT-TYPE
              SYNTAX       INTEGER {
                           sun(0),
                           mon(1),
                           tue(2),
                           wed(3),
                           thu(4),
                           fri(5),
                           sat(6)
              }
              MAX-ACCESS   read-write
              STATUS       current
              DESCRIPTION
                  "The end weekday of Daylight Saving Time in Repeating mode."
              ::= { sysSNTPServerTable 38 }

		sysSNTPDSTRepeatEndHour  OBJECT-TYPE
              SYNTAX       INTEGER  
              MAX-ACCESS   read-write
              STATUS       current
              DESCRIPTION
                  "The end hour of Daylight Saving Time in Repeating mode.."
              ::= { sysSNTPServerTable 39 }

		sysSNTPDSTRepeatEndMin  OBJECT-TYPE
              SYNTAX       INTEGER  
              MAX-ACCESS   read-write
              STATUS       current
              DESCRIPTION
                  "The end minute of Daylight Saving Time in Repeating mode."
              ::= { sysSNTPServerTable 40 }
 

    -- ------------------------------------------------------------------    
    -- Limit IP multicast Group 
    -- ------------------------------------------------------------------

        limitIpMulticastProfileTable OBJECT-TYPE
            SYNTAX SEQUENCE OF LimitIpMulticastProfileEntry
            MAX-ACCESS not-accessible
            STATUS current
            DESCRIPTION
                "A list of the limit ip multicast Profile Table."
            ::= { companyLimitIp 1 }

        limitIpMulticastProfileEntry OBJECT-TYPE
            SYNTAX LimitIpMulticastProfileEntry
            MAX-ACCESS not-accessible
            STATUS current
            DESCRIPTION
                "A limit ip multicast entry maintain by the start IP Address, end ip address, profile id."
            INDEX { limitIpMulticastIPType, limitIpMulticastProfileID }
            ::= { limitIpMulticastProfileTable 1 }   

        LimitIpMulticastProfileEntry ::= SEQUENCE { 
        	limitIpMulticastIPType          INTEGER,
            limitIpMulticastProfileID       INTEGER,
            limitIpMulticastProfileName     DisplayString,
            limitIpMulticastProfileStatus   RowStatus
        }          
           
		limitIpMulticastIPType OBJECT-TYPE
           SYNTAX      INTEGER {
                  ipv4(1),
                  ipv6(2)
           }
           MAX-ACCESS read-only
           STATUS current
           DESCRIPTION
                "Indicate the IP type of profile."
           ::= { limitIpMulticastProfileEntry 1 }
                      
        limitIpMulticastProfileID OBJECT-TYPE 
           SYNTAX      INTEGER
           MAX-ACCESS  read-only 
           STATUS      current 
           DESCRIPTION 
               "The ProfileID of the limit ip multicast profile entry."
           ::= { limitIpMulticastProfileEntry 2 }
           
        limitIpMulticastProfileName OBJECT-TYPE
             SYNTAX DisplayString (SIZE(1..20))
             MAX-ACCESS read-write
             STATUS current
             DESCRIPTION
                 "The ProfileName of the limit ip multicast profile entry."
             ::= { limitIpMulticastProfileEntry 3 }           

        limitIpMulticastProfileStatus OBJECT-TYPE
            SYNTAX     RowStatus
            MAX-ACCESS read-write
            STATUS     current
            DESCRIPTION
                "The status of an entry in the limit ip multicast profile Table. Only a subset
                 of the rowstatus variables (active, createAndGo, destroy) 
                 are available."
            ::= { limitIpMulticastProfileEntry 4 } 



              
        limitIpMulticastEntryTable OBJECT-TYPE
            SYNTAX SEQUENCE OF LimitIpMulticastEntry
            MAX-ACCESS not-accessible
            STATUS current
            DESCRIPTION
                "A list of the limit ip multicast entry Table."
            ::= { companyLimitIp 2 }

        limitIpMulticastEntry OBJECT-TYPE
            SYNTAX LimitIpMulticastEntry
            MAX-ACCESS not-accessible
            STATUS current
            DESCRIPTION
                "A limit ip multicast entry maintain by the start IP Address, end ip address, profile id."
            INDEX { limitIpMulticastEntryIPType, limitIpMulticastEntryProfileID, limitIpMulticaststartIpAddr, limitIpMulticastendIpAddr}
            ::= { limitIpMulticastEntryTable 1 }       
                
                           
        LimitIpMulticastEntry ::= SEQUENCE {               
        	limitIpMulticastEntryIPType          INTEGER,  
            limitIpMulticastEntryProfileID       INTEGER,  
            limitIpMulticaststartIpAddr          DisplayString,
            limitIpMulticastendIpAddr            DisplayString,
            limitIpMulticastStatus               RowStatus
        }                                
        
        limitIpMulticastEntryIPType OBJECT-TYPE
           SYNTAX      INTEGER {
                  ipv4(1),
                  ipv6(2)
           }
           MAX-ACCESS read-only
           STATUS current
           DESCRIPTION
                "Indicate the IP type of entry."
           ::= { limitIpMulticastEntry 1 }

        limitIpMulticastEntryProfileID OBJECT-TYPE 
           SYNTAX      INTEGER
           MAX-ACCESS  read-only 
           STATUS      current 
           DESCRIPTION 
               "The ProfileID of the limit ip multicast entry."
           ::= { limitIpMulticastEntry 2 }
                                         
        limitIpMulticaststartIpAddr OBJECT-TYPE
              SYNTAX DisplayString (SIZE(1..16))
              MAX-ACCESS read-only
              STATUS current
              DESCRIPTION
                  "The limit ip multicast IP address is used to set start ip"
              ::= { limitIpMulticastEntry 3 }    
              
        limitIpMulticastendIpAddr OBJECT-TYPE
              SYNTAX DisplayString (SIZE(1..16))
              MAX-ACCESS read-only
              STATUS current
              DESCRIPTION
                  "The limit ip multicast IP address is used to set end ip"
              ::= { limitIpMulticastEntry 4 }

        limitIpMulticastStatus OBJECT-TYPE
            SYNTAX     RowStatus
            MAX-ACCESS read-write
            STATUS     current
            DESCRIPTION
                "The status of an entry in the limit ip multicast entry Table. Only a subset
                 of the rowstatus variables (active, createAndGo, destroy) 
                 are available."
            ::= { limitIpMulticastEntry 5 } 
            
 
              
        limitIpMulticastPortTable OBJECT-TYPE
            SYNTAX SEQUENCE OF LimitIpMulticastPortEntry
            MAX-ACCESS not-accessible
            STATUS current
            DESCRIPTION
                "A list of the limit ip multicast Port entry Table."
            ::= { companyLimitIp 3 }

        limitIpMulticastPortEntry OBJECT-TYPE
            SYNTAX LimitIpMulticastPortEntry
            MAX-ACCESS not-accessible
            STATUS current
            DESCRIPTION
                "A limit ip multicast entry maintain by the Port Index."
            INDEX { limitIpMulticastPortIPType, limitIpMulticastPortID }
            ::= { limitIpMulticastPortTable 1 }       
                
                           
        LimitIpMulticastPortEntry ::= SEQUENCE {        
        	limitIpMulticastPortIPType      INTEGER,
            limitIpMulticastPortID          INTEGER,    
            limitIpMulticastPortState       INTEGER,
            limitIpMulticastPortProfileID   PortList,
            limitIpMulticastPortMaxGrp      INTEGER
        }                           
          
        limitIpMulticastPortIPType OBJECT-TYPE
           SYNTAX      INTEGER {
                  ipv4(1),
                  ipv6(2)
           }
           MAX-ACCESS read-only
           STATUS current
           DESCRIPTION
                "Indicate the IP type of entry."
           ::= { limitIpMulticastPortEntry 1 }
           
        limitIpMulticastPortID OBJECT-TYPE 
           SYNTAX      INTEGER
           MAX-ACCESS  read-only 
           STATUS      current 
           DESCRIPTION 
               "The Port Index of the limit ip multicast port entry."
           ::= { limitIpMulticastPortEntry 2 }
                                          
		limitIpMulticastPortState OBJECT-TYPE
            SYNTAX INTEGER  {
        		  permit (1), deny (2)
            }
              MAX-ACCESS read-write
              STATUS current
              DESCRIPTION
                  "The limit ip multicast port state"
              ::= { limitIpMulticastPortEntry 3 }    
              
        limitIpMulticastPortProfileID OBJECT-TYPE
              SYNTAX PortList
              MAX-ACCESS read-write
              STATUS current
              DESCRIPTION
                  "The limit ip multicast port mapping profileID list."
              ::= { limitIpMulticastPortEntry 4 }
           
           
        limitIpMulticastPortMaxGrp OBJECT-TYPE
            SYNTAX     INTEGER (1..256)
            MAX-ACCESS read-write
            STATUS     current
            DESCRIPTION
                  "The limit ip multicast per-port max group."
            ::= { limitIpMulticastPortEntry 5 } 
            


 
	-- -----------------------------------------------------------------------------
	-- The Guest Vlan Group
	-- -----------------------------------------------------------------------------
	guestVlanName OBJECT-TYPE
	    SYNTAX      DisplayString(SIZE(1..32))
	    MAX-ACCESS  read-write
	    STATUS      current
	    DESCRIPTION
		"The VLAN name of guest VLAN."
	    ::= { companyGuestVlan 1 }

	guestVlanPort OBJECT-TYPE
	    SYNTAX      PortList
	    MAX-ACCESS  read-write
	    STATUS      current
	    DESCRIPTION
		"This object indicates the guest VLAN port members of this device."
	     ::= { companyGuestVlan 2 }

	guestVlanDelState OBJECT-TYPE
	    SYNTAX      INTEGER{
			none(1),
			start(2)
			}
	    MAX-ACCESS  read-write
	    STATUS      current
	    DESCRIPTION
		"Used to delete the guest VLAN."
	    ::= { companyGuestVlan 3 }

 
    -- -----------------------------------------------------------------------------
	-- The Protocol Group Name Table
	-- -----------------------------------------------------------------------------
	protocolGroupNameTable OBJECT-TYPE
        SYNTAX SEQUENCE OF ProtocolGroupNameEntry
        MAX-ACCESS not-accessible
        STATUS current
        DESCRIPTION
            "A table to control protocol group name features of the device."
        ::= { companyProtocolVlan 1 }
        
    protocolGroupNameEntry OBJECT-TYPE
        SYNTAX ProtocolGroupNameEntry
        MAX-ACCESS not-accessible
        STATUS current
        DESCRIPTION
            "An entry appears in protocol group name table for each interface 
 	        in the system."    
 	    INDEX {protocolGroupGID}
        ::= { protocolGroupNameTable 1 }
  
    ProtocolGroupNameEntry ::= 
        SEQUENCE {  
           protocolGroupGID
              Integer32,
           protocolGroupName
              DisplayString
        }
           
    protocolGroupGID OBJECT-TYPE
        SYNTAX      Integer32 (1..16)
        MAX-ACCESS  read-only
        STATUS      current
        DESCRIPTION
           "The group ID of protocol group name table."
        ::= { protocolGroupNameEntry 1 }
    
    protocolGroupName OBJECT-TYPE
	    SYNTAX      DisplayString(SIZE(1..32))
        MAX-ACCESS  read-write
	    STATUS      current
	    DESCRIPTION
		   "The group name of protocol group name table."
	    ::= { protocolGroupNameEntry 2 }

                  
	-- -----------------------------------------------------------------------------
	-- The Protocol Group Table
	-- -----------------------------------------------------------------------------
	protocolGroupTable OBJECT-TYPE
        SYNTAX SEQUENCE OF ProtocolGroupEntry
        MAX-ACCESS not-accessible
        STATUS current
        DESCRIPTION
            "A table to control protocol group features of the device."
        ::= { companyProtocolVlan 2 }
        
    protocolGroupEntry OBJECT-TYPE
        SYNTAX ProtocolGroupEntry
        MAX-ACCESS not-accessible
        STATUS current
        DESCRIPTION
            "An entry appears in protocol group table for each interface 
 	        in the system."    
 	    INDEX {protocolGroupId, protocolGroupFrameType, protocolGroupProtocolValue}
        ::= { protocolGroupTable 1 }
  
    ProtocolGroupEntry ::= 
        SEQUENCE {  
           protocolGroupId
              Integer32,
           protocolGroupFrameType 
              INTEGER,
           protocolGroupProtocolValue
              Integer32,
           protocolGroupRowStatus 
              RowStatus       
        }
           
    protocolGroupId OBJECT-TYPE
        SYNTAX      Integer32 (1..16)
        MAX-ACCESS  read-only
        STATUS      current
        DESCRIPTION
           "The group ID of protocol group table."
        ::= { protocolGroupEntry 1 }
        
    protocolGroupFrameType OBJECT-TYPE
	    SYNTAX INTEGER  {
        	 ethernet (1),
        	 ieee8023-snap (2)
        }
        MAX-ACCESS  read-only
	    STATUS      current
	    DESCRIPTION
		   "The frame type of protocol group table."
	    ::= { protocolGroupEntry 2 } 
	
	protocolGroupProtocolValue OBJECT-TYPE
        SYNTAX      Integer32
        MAX-ACCESS  read-only
        STATUS      current
        DESCRIPTION
           "The protocol value of protocol group table."
        ::= { protocolGroupEntry 3 }

    protocolGroupRowStatus OBJECT-TYPE
        SYNTAX      RowStatus
        MAX-ACCESS  read-create
        STATUS      current
        DESCRIPTION
            "The row status of protocol group table."
        ::= { protocolGroupEntry 99 }   
              
    
    -- -----------------------------------------------------------------------------
	-- The Protocol Vlan Table
	-- -----------------------------------------------------------------------------
	protocolVlanTable OBJECT-TYPE
        SYNTAX SEQUENCE OF ProtocolVlanEntry
        MAX-ACCESS not-accessible
        STATUS current
        DESCRIPTION
            "A table to control protocol vlan features of the device."
        ::= { companyProtocolVlan 3 }
        
    protocolVlanEntry OBJECT-TYPE
        SYNTAX ProtocolVlanEntry
        MAX-ACCESS not-accessible
        STATUS current
        DESCRIPTION
            "An entry appears in protocol vlan table for each interface 
 	        in the system."    
 	    INDEX {protocolVlanPort, protocolVlanVID, protocolVlanGroupID}
        ::= { protocolVlanTable 1 }
  
    ProtocolVlanEntry ::= 
        SEQUENCE {  
           protocolVlanPort
              Integer32,
           protocolVlanVID
              Integer32, 
           protocolVlanGroupID 
              Integer32,
           protocolVlanRowStatus 
              RowStatus       
        }
    
    protocolVlanPort OBJECT-TYPE
        SYNTAX      Integer32 (1..28)
        MAX-ACCESS  read-only
        STATUS      current
        DESCRIPTION
           "The interface number of protocol vlan table."
        ::= { protocolVlanEntry 1 }

    protocolVlanVID OBJECT-TYPE
        SYNTAX      Integer32 (1..4094)
        MAX-ACCESS  read-only
        STATUS      current
        DESCRIPTION
           "The vlan ID of protocol vlan table."
        ::= { protocolVlanEntry 2 }

    protocolVlanGroupID OBJECT-TYPE
        SYNTAX      Integer32 (1..16)
        MAX-ACCESS  read-only
        STATUS      current
        DESCRIPTION
           "The group ID of protocol vlan table."
        ::= { protocolVlanEntry 3 }

    protocolVlanRowStatus OBJECT-TYPE
        SYNTAX      RowStatus
        MAX-ACCESS  read-create
        STATUS      current
        DESCRIPTION
            "The row status of protocol vlan table."
        ::= { protocolVlanEntry 99 }


    -- ---------------------------------------------------------------------
    -- MacNotify Function
    -- ---------------------------------------------------------------------

    macNotifyState OBJECT-TYPE
        SYNTAX  INTEGER {
               enabled(1),        
               disabled(2)
               }
        MAX-ACCESS  read-write
        STATUS  current
        DESCRIPTION
           "This object can enabled or disabled MAC Notification."
        ::= { companyMacNotify 1 }        
             
    macNotifyInterval OBJECT-TYPE
	    SYNTAX  INTEGER (1..2147483647)
	    MAX-ACCESS  read-write
	    STATUS  current
	    DESCRIPTION
	        "This object indicates the time interval in second for trigger the MAC notify message. "
        --DEFVAL     { 1 }
	    ::= { companyMacNotify 2 }    

    macNotifyHistorySize OBJECT-TYPE
	    SYNTAX  INTEGER (1..500)
	    MAX-ACCESS  read-write
	    STATUS  current
	    DESCRIPTION
            "This object indicates the history size of variation MAC in address table. The default value is 1 ."
        --DEFVAL     { 1 }
    ::= { companyMacNotify 3 } 
    
    -- Mac Notify Port Control Table    
    macNotifyCtrlTable OBJECT-TYPE 
       SYNTAX      SEQUENCE OF MacNotifyCtrlEntry 
       MAX-ACCESS  not-accessible 
       STATUS      current 
       DESCRIPTION 
          "A table to control Loopback detection features either for 
          the entire switch or for each interface in the switch."
       ::= { companyMacNotify 4 }
    
    macNotifyCtrlEntry OBJECT-TYPE 
       SYNTAX      MacNotifyCtrlEntry 
       MAX-ACCESS  not-accessible 
       STATUS      current 
       DESCRIPTION 
           "An entry appears in this table for each interface 
            in the system."
       INDEX { macNotifyCtrlIndex }
       ::= { macNotifyCtrlTable 1 }
       
    MacNotifyCtrlEntry ::= 
       SEQUENCE { 
          macNotifyCtrlIndex
             Integer32, 
          macNotifyPortStatus 
             INTEGER
      }
    
    macNotifyCtrlIndex OBJECT-TYPE 
       SYNTAX      Integer32 
       MAX-ACCESS  read-only 
       STATUS      current 
       DESCRIPTION 
          "The interface index of the port for which the configuration
          in this entry applies."
       ::= { macNotifyCtrlEntry 1 }
        
    macNotifyPortStatus OBJECT-TYPE 
       SYNTAX      INTEGER {
                   enabled(1),
                   disabled(2)
                   }
       MAX-ACCESS  read-write 
       STATUS      current 
       DESCRIPTION 
           "Provides control to per port enable or disable the loopback detection 
            function. Default is disabled."
       DEFVAL  { disabled }
       ::= { macNotifyCtrlEntry 2 }
       
    macNotifyInfo  OBJECT IDENTIFIER ::= {  companyMacNotify 5 } 

    macNotifyInfoDiscription   OBJECT-TYPE
        SYNTAX          OCTET STRING(SIZE (1..1024))
        MAX-ACCESS      accessible-for-notify
        STATUS          current
        DESCRIPTION
            "This object indicates the information for the device MAC address
            changes. And the detailed information include:
            Operation Code + Port Number + MAC address

            Operation Code: 1, 2
                 1 means learned a new MAC address
                 2 means deleted an old MAC address.
            Port Number: The hysical port/port-channellearned or deleted"
        ::= { macNotifyInfo 1 }



    -- ------------------------------------------------------------------ 
    -- BPDU Attack Protection Group
    -- ------------------------------------------------------------------
    sysBPDUAttackStateEnable OBJECT-TYPE 
           SYNTAX      INTEGER {
                          enabled(1),
                          disabled(2)
                       }
           MAX-ACCESS  read-write 
           STATUS      current 
           DESCRIPTION 
               "Use this to enable BPDU attack protection.
                The BPDU Attack Protection function and Spanning Tree Protocol 
                for ports are mutually exclusive. When the STP function is enabled 
                on a particular port, BPDU Attack Protection cannot be enabled."
        
           DEFVAL  { disabled }
           ::= { companyBPDUAttack 1 }
                   
    sysBPDUAttackRecoverTime  OBJECT-TYPE
           SYNTAX      Integer32 (0 | 60..1000000)
           MAX-ACCESS  read-write
           STATUS      current
           DESCRIPTION
            "When a port enters under attack state, it can be disabled or blocked 
            based on the configuration. The state can be recovered manually or 
            by the auto recovery mechanism. This command is used to configure the 
            auto-recovery timer. To manually recover the port, the user needs to 
            disable and re-enable the port."  
           DEFVAL  { 60 }
           ::= { companyBPDUAttack 2 }       
        
        -- BPDUAttack Port Control Table
        
        sysBPDUAttackCtrlTable OBJECT-TYPE 
           SYNTAX      SEQUENCE OF SysBPDUAttackCtrlEntry 
           MAX-ACCESS  not-accessible 
           STATUS      current 
           DESCRIPTION 
              "A table to control BPDU Attack features either for 
              the entire switch or for each interface in the switch."
           ::= { companyBPDUAttack 3 }
        
        sysBPDUAttackCtrlEntry OBJECT-TYPE 
           SYNTAX      SysBPDUAttackCtrlEntry 
           MAX-ACCESS  not-accessible 
           STATUS      current 
           DESCRIPTION 
               "An entry appears in this table for each interface 
                in the system."
           INDEX { sysBPDUAttackCtrlIndex }
           ::= { sysBPDUAttackCtrlTable 1 }
           
        SysBPDUAttackCtrlEntry ::= 
           SEQUENCE {
              sysBPDUAttackCtrlIndex
                 Integer32,
              sysBPDUAttackPortState 
                 INTEGER,
              sysBPDUAttackPortMode 
                 INTEGER ,
              sysBPDUAttackPortStatus 
                 INTEGER
          }
        
        sysBPDUAttackCtrlIndex OBJECT-TYPE 
           SYNTAX      Integer32 
           MAX-ACCESS  read-only 
           STATUS      current 
           DESCRIPTION 
              "The interface index of the port for which the configuration
              in this entry applies."
           ::= { sysBPDUAttackCtrlEntry 1 }
            
        sysBPDUAttackPortState OBJECT-TYPE 
           SYNTAX      INTEGER {
                       enabled(1),
                       disabled(2)
                       }
           MAX-ACCESS  read-write 
           STATUS      current 
           DESCRIPTION 
               "Used to configure the BPDU Attack Protection state of a port.
                The default state is disable."
           DEFVAL  { disabled }
           ::= { sysBPDUAttackCtrlEntry 2 }
        
        sysBPDUAttackPortMode OBJECT-TYPE 
           SYNTAX      INTEGER {
                       drop(1),
                       block(2),
                       shutdown(3)
                      }
           MAX-ACCESS  read-write 
           STATUS      current 
           DESCRIPTION 
               "Used to configure the BPDU Attack Protection mode of a port."
           ::= { sysBPDUAttackCtrlEntry 3 }

        sysBPDUAttackPortStatus OBJECT-TYPE 
           SYNTAX      INTEGER {
                       normal(1),
                       underAttack(2)
                       }
           MAX-ACCESS  read-only 
           STATUS      current 
           DESCRIPTION 
               "Use this to view per port BPDU attack protection status."
           DEFVAL  { normal }
           ::= { sysBPDUAttackCtrlEntry 4 }
           
	    sysBPDUAttackLog    OBJECT-TYPE
	           SYNTAX      INTEGER {
	                          none(1),
	                          attackDetected(2),
	                          attackCleared(3),
	                          both(4)
	                       }
	           MAX-ACCESS  read-write
	           STATUS      current
	           DESCRIPTION
	               "Used to configure log settings for BPDU attack protection events."
	
	           DEFVAL  { none }
	        ::= { companyBPDUAttack 4 }
    -- ---------------------------------------------------------------------
    -- VLAN Trunk Function
    -- ---------------------------------------------------------------------
      vlanTrunkSystem                OBJECT IDENTIFIER ::= { companyVLANTrunk 1 }
    -- ------------------------------------------------------------------
    -- The La System Group
    -- ------------------------------------------------------------------

      vlanTrunkGlobalStatus OBJECT-TYPE
           SYNTAX      INTEGER { enabled(1), disabled(2) }
           MAX-ACCESS  read-write
           STATUS      current
           DESCRIPTION
               "This indicates the global state of the VLAN trunking feature of the device."
           ::= { vlanTrunkSystem 1 }

    vlanTrunkTable  OBJECT-TYPE
        SYNTAX     SEQUENCE OF VlanTrunkConfigEntry 
        MAX-ACCESS not-accessible
        STATUS     current
        DESCRIPTION
           "This table is used to manage the VLAN trunking feature of the device."
        ::= { vlanTrunkSystem 2 }

    vlanTrunkEntry OBJECT-TYPE
        SYNTAX     VlanTrunkConfigEntry 
        MAX-ACCESS not-accessible
        STATUS     current
        DESCRIPTION
              "There is one entry in this table for each created
               port-channel port."
        INDEX { vlanTrunkIfIndex }
        ::= { vlanTrunkTable 1 }

    VlanTrunkConfigEntry ::= 
            SEQUENCE {
              vlanTrunkIfIndex                InterfaceIndex,
              vlanTrunkState                  INTEGER
              }

    vlanTrunkIfIndex OBJECT-TYPE
        SYNTAX      InterfaceIndex
        MAX-ACCESS  read-only
        STATUS      current
        DESCRIPTION
              "The index of the port. "
        ::= { vlanTrunkEntry 1 }

    vlanTrunkState OBJECT-TYPE
       SYNTAX       INTEGER { enabled(1), disabled(2) }
       MAX-ACCESS   read-write
       STATUS       current
       DESCRIPTION
               "Sets the VLAN trunk status as enabled or disabled."
        ::= { vlanTrunkEntry 2 }

    -- ---------------------------------------------------------------------
    -- QinQ Function
    -- ---------------------------------------------------------------------
      qinqSystem                OBJECT IDENTIFIER ::= { companyQinQ 1 }
      qinqVLANTranslation       OBJECT IDENTIFIER ::= { companyQinQ 2 }
    -- ------------------------------------------------------------------
    -- The QinQ System Group
    -- ------------------------------------------------------------------

    qinqGlobalStatus OBJECT-TYPE
        SYNTAX      INTEGER { enabled(1), disabled(2) }
        MAX-ACCESS  read-write
        STATUS      current
        DESCRIPTION
            "This object is used to enable/disable the Q-in-Q status."
        ::= { qinqSystem 1 }
                              
    qinqInnerTPID OBJECT-TYPE
        SYNTAX      Unsigned32
        MAX-ACCESS  read-write
        STATUS      current
        DESCRIPTION
            "This object is used to set the Q-in-Q inner TPID."
        ::= { qinqSystem 2 }

    qinqTable  OBJECT-TYPE
        SYNTAX     SEQUENCE OF QinQConfigEntry 
        MAX-ACCESS not-accessible
        STATUS     current
        DESCRIPTION
           "A table that contains Q-in-Q information about each port."
        ::= { qinqSystem 3 }

    qinqEntry OBJECT-TYPE
        SYNTAX     QinQConfigEntry 
        MAX-ACCESS not-accessible
        STATUS     current
        DESCRIPTION
              "A list of Q-in-Q information for each port."
        INDEX { qinqIfIndex }
        ::= { qinqTable 1 }

    QinQConfigEntry ::= 
            SEQUENCE {
              qinqIfIndex                    InterfaceIndex,
              qinqRoleState                  INTEGER,
              qinqMissDropState              INTEGER,
              qinqOuterTPID                  Unsigned32,
              qinqAddInnerTagState           INTEGER,
              qinqAddInnerTagValue           Unsigned32
            }

    qinqIfIndex OBJECT-TYPE
        SYNTAX      InterfaceIndex
        MAX-ACCESS  read-only
        STATUS      current
        DESCRIPTION
              "The index of the port. "
        ::= { qinqEntry 1 }

    qinqRoleState OBJECT-TYPE
       SYNTAX       INTEGER { nni(1), uni(2) }
       MAX-ACCESS   read-write
       STATUS       current
       DESCRIPTION
               "Sets the QinQ Role as NNI or UNI."
        ::= { qinqEntry 2 }

    qinqMissDropState OBJECT-TYPE
       SYNTAX       INTEGER { enabled(1), disabled(2) }
       MAX-ACCESS   read-write
       STATUS       current
       DESCRIPTION
               "Sets the QinQ Miss Drop state as enabled or disabled."
        ::= { qinqEntry 3 }

    qinqOuterTPID OBJECT-TYPE
       SYNTAX       Unsigned32
       MAX-ACCESS   read-write
       STATUS       current
       DESCRIPTION
               "Sets the QinQ Outer TPID value."
        ::= { qinqEntry 4 }

    qinqAddInnerTagState OBJECT-TYPE
       SYNTAX       INTEGER { enabled(1), disabled(2) }
       MAX-ACCESS   read-write
       STATUS       current
       DESCRIPTION
               "Sets the QinQ Add Inner Tag state as enabled or disabled."
        ::= { qinqEntry 5 }

    qinqAddInnerTagValue OBJECT-TYPE
       SYNTAX       Unsigned32
       MAX-ACCESS   read-write
       STATUS       current
       DESCRIPTION
               "Sets the QinQ Add Inner Tag value."
        ::= { qinqEntry 6 }
        
    --
    -- Vlan Translation Table
    --
    qinqVlanTranslationTable OBJECT-TYPE
    SYNTAX      SEQUENCE OF QinQVlanTranslationEntry
    MAX-ACCESS  not-accessible
    STATUS      current
    DESCRIPTION
        "A table that contains VLAN translation information."
    ::= { qinqVLANTranslation 1 }

    qinqVlanTranslationEntry OBJECT-TYPE
    SYNTAX      QinQVlanTranslationEntry
    MAX-ACCESS  not-accessible
    STATUS      current
    DESCRIPTION
        "A list of VLAN translation information."
    INDEX   {qinqVlanTranslationIfIndex, qinqVlanTranslationCVID}
    ::= { qinqVlanTranslationTable 1 }

    QinQVlanTranslationEntry ::=
    SEQUENCE {
        qinqVlanTranslationIfIndex
            InterfaceIndex,
        qinqVlanTranslationCVID
            Unsigned32,
        qinqVlanTranslationSVID
            Unsigned32,    
        qinqVlanTranslationPriority
            Integer32,
        qinqVlanTranslationSVIDOperation
            INTEGER,
        qinqVlanTranslationRowStatus
            RowStatus
    }
    
    qinqVlanTranslationIfIndex OBJECT-TYPE
    SYNTAX      InterfaceIndex
    MAX-ACCESS  read-only
    STATUS      current
    DESCRIPTION
        "The interface index."
    ::= { qinqVlanTranslationEntry 1 }

    qinqVlanTranslationCVID OBJECT-TYPE
    SYNTAX      Unsigned32
    MAX-ACCESS  read-only
    STATUS      current
    DESCRIPTION
        "The customer VLAN identifier in a C-TAG."
    ::= { qinqVlanTranslationEntry 2 }

    qinqVlanTranslationSVID OBJECT-TYPE
    SYNTAX      Unsigned32
    MAX-ACCESS  read-write 
    STATUS      current
    DESCRIPTION
        "A VLAN identifier conveyed in an S-TAG."
    ::= { qinqVlanTranslationEntry 3 }

    qinqVlanTranslationPriority OBJECT-TYPE
    SYNTAX      Integer32
    MAX-ACCESS  read-write 
    STATUS      current
    DESCRIPTION
        "The priority of TAG."
    ::= { qinqVlanTranslationEntry 4 }
    
    qinqVlanTranslationSVIDOperation OBJECT-TYPE
    SYNTAX      INTEGER {
                  add(1),
                  replace(2)
                }
    MAX-ACCESS  read-write
    STATUS      current
    DESCRIPTION
        "The 'add' action indicates to add a tag for the assigned SP-VLAN
        before the C-VLAN tag. If there is S-TAG in the packet, this rule
        will not take effect.
        The 'replace' action indicates to replace the C-VLAN in the tag by
        the SP-VLAN. If there is no C-TAG in the packet, this rule will not
        take effect."
    ::= { qinqVlanTranslationEntry 5 }

    qinqVlanTranslationRowStatus OBJECT-TYPE
    SYNTAX      RowStatus
    MAX-ACCESS  read-create
    STATUS      current
    DESCRIPTION
        "This object indicates the status of this entry."
    ::= { qinqVlanTranslationEntry 99 }               
    
    -- ---------------------------------------------------------------------
    -- EOAM Function
    -- ---------------------------------------------------------------------
      eoamSystem                OBJECT IDENTIFIER ::= { companyEoam 1 }
      eoamLinkMonitor           OBJECT IDENTIFIER ::= { companyEoam 2 }
    -- ------------------------------------------------------------------
    -- The EOAM System Group
    -- ------------------------------------------------------------------

--    eoamGlobalStatus OBJECT-TYPE
--        SYNTAX      INTEGER { enabled(1), disabled(2) }
--        MAX-ACCESS  read-write
--        STATUS      current
--        DESCRIPTION
--            "This object is used to enable/disable the EOAM status."
--        ::= { eoamSystem 1 }

    eoamTable  OBJECT-TYPE
        SYNTAX     SEQUENCE OF EOAMConfigEntry 
        MAX-ACCESS not-accessible
        STATUS     current
        DESCRIPTION
           "A table that contains EOAM mode information about each port."
        ::= { eoamSystem 2 }

    eoamEntry OBJECT-TYPE
        SYNTAX     EOAMConfigEntry 
        MAX-ACCESS not-accessible
        STATUS     current
        DESCRIPTION
              "A list of EOAM mode information for each port."
        INDEX { eoamIfIndex }
        ::= { eoamTable 1 }

    EOAMConfigEntry ::= 
            SEQUENCE {
              eoamIfIndex                    InterfaceIndex,
              eoamState                      INTEGER,
              eoamMode                       INTEGER,
              eoamReceivedRemoteLoopback     INTEGER,
              eoamRemoteLoopback             INTEGER,
              eoamDyingGaspEnable            INTEGER,
              eoamCriticalEventEnable        INTEGER
              }

    eoamIfIndex OBJECT-TYPE
        SYNTAX      InterfaceIndex
        MAX-ACCESS  read-only
        STATUS      current
        DESCRIPTION
              "The index of the port. "
        ::= { eoamEntry 1 }

    eoamState OBJECT-TYPE
       SYNTAX       INTEGER { enabled(1), disabled(2) }
       MAX-ACCESS   read-write
       STATUS       current
       DESCRIPTION
               "Sets the EOAM state enabled or disabled."
        ::= { eoamEntry 2 }

    eoamMode OBJECT-TYPE
       SYNTAX       INTEGER { passive(1), active(2) }
       MAX-ACCESS   read-write
       STATUS       current
       DESCRIPTION
               "Sets the EOAM mode as active or passive."
        ::= { eoamEntry 3 }

    eoamReceivedRemoteLoopback OBJECT-TYPE
       SYNTAX       INTEGER { ignore(1), process(2) }
       MAX-ACCESS   read-write
       STATUS       current
       DESCRIPTION
               "Sets the EOAM received or ignore remote loopback packets."
        ::= { eoamEntry 4 }

    eoamRemoteLoopback OBJECT-TYPE
       SYNTAX       INTEGER { noLoopBack(1), 
                              startLoopBack(2),
                              remoteLoopBack(3),
                              stopLoopBack(4),
                              localLoopBack(5),
                              unknownLoopBack(6)
                              }
       MAX-ACCESS   read-write
       STATUS       current
       DESCRIPTION
               "Sets the EOAM remote loopback start or stop."
        ::= { eoamEntry 5 }

    eoamDyingGaspEnable OBJECT-TYPE
       SYNTAX       INTEGER { enabled(1), disabled(2) }
       MAX-ACCESS   read-write
       STATUS       current
       DESCRIPTION
               "Sets the EOAM dying gasp state enabled or disabled."
        ::= { eoamEntry 6 }

    eoamCriticalEventEnable OBJECT-TYPE
       SYNTAX       INTEGER { enabled(1), disabled(2) }
       MAX-ACCESS   read-write
       STATUS       current
       DESCRIPTION
               "Sets the EOAM critical event state enabled or disabled."
        ::= { eoamEntry 7 }

    -- ------------------------------------------------------------------
    -- The EOAM Link Monitor Group
    -- ------------------------------------------------------------------

    eoamLinkMonitorTable  OBJECT-TYPE
        SYNTAX     SEQUENCE OF EOAMConfigLinkMonitorEntry 
        MAX-ACCESS not-accessible
        STATUS     current
        DESCRIPTION
           "A table that contains EOAM link monitor information about each port."
        ::= { eoamLinkMonitor 1 }

    eoamLinkMonitorEntry OBJECT-TYPE
        SYNTAX     EOAMConfigLinkMonitorEntry 
        MAX-ACCESS not-accessible
        STATUS     current
        DESCRIPTION
              "A list of EOAM link monitor information for each port."
        INDEX { eoamLinkMonitorIfIndex }
        ::= { eoamLinkMonitorTable 1 }

    EOAMConfigLinkMonitorEntry ::= 
            SEQUENCE {
              eoamLinkMonitorIfIndex         InterfaceIndex,
              errorSymbolNotifyState         INTEGER,
              errorSymbolThreshold           Unsigned32,
              errorSymbolWindow              Unsigned32,
              errorFrameNotifyState          INTEGER,
              errorFrameThreshold            Unsigned32,
              errorFrameWindow               Unsigned32,
              errorFrameSecondsNotifyState   INTEGER,
              errorFrameSecondsThreshold     Unsigned32,
              errorFrameSecondsWindow        Unsigned32,
              errorFramePeriodNotifyState    INTEGER,
              errorFramePeriodThreshold      Unsigned32,
              errorFramePeriodWindow         Unsigned32
              }

    eoamLinkMonitorIfIndex OBJECT-TYPE
        SYNTAX      InterfaceIndex
        MAX-ACCESS  read-only
        STATUS      current
        DESCRIPTION
              "The index of the port. "
        ::= { eoamLinkMonitorEntry 1 }

    errorSymbolNotifyState OBJECT-TYPE
       SYNTAX       INTEGER { enabled(1), disabled(2) }
       MAX-ACCESS   read-write
       STATUS       current
       DESCRIPTION
               "Sets the EOAM error symbol notify state enabled or disabled."
        ::= { eoamLinkMonitorEntry 2 }

    errorSymbolThreshold OBJECT-TYPE
       SYNTAX       Unsigned32
       MAX-ACCESS   read-write
       STATUS       current
       DESCRIPTION
               "Sets the EOAM error symbol threshold."
        ::= { eoamLinkMonitorEntry 3 }

    errorSymbolWindow OBJECT-TYPE
       SYNTAX       Unsigned32
       MAX-ACCESS   read-write
       STATUS       current
       DESCRIPTION
               "Sets the EOAM error symbol window."
        ::= { eoamLinkMonitorEntry 4 }

    errorFrameNotifyState OBJECT-TYPE
       SYNTAX       INTEGER { enabled(1), disabled(2) }
       MAX-ACCESS   read-write
       STATUS       current
       DESCRIPTION
               "Sets the EOAM error frame notify state enabled or disabled."
        ::= { eoamLinkMonitorEntry 5 }

    errorFrameThreshold OBJECT-TYPE
       SYNTAX       Unsigned32
       MAX-ACCESS   read-write
       STATUS       current
       DESCRIPTION
               "Sets the EOAM error frame threshold."
        ::= { eoamLinkMonitorEntry 6 }

    errorFrameWindow OBJECT-TYPE
       SYNTAX       Unsigned32
       MAX-ACCESS   read-write
       STATUS       current
       DESCRIPTION
               "Sets the EOAM error symbol window."
        ::= { eoamLinkMonitorEntry 7 }


    errorFrameSecondsNotifyState OBJECT-TYPE
       SYNTAX       INTEGER { enabled(1), disabled(2) }
       MAX-ACCESS   read-write
       STATUS       current
       DESCRIPTION
               "Sets the EOAM error symbol notify state enabled or disabled."
        ::= { eoamLinkMonitorEntry 8 }

    errorFrameSecondsThreshold OBJECT-TYPE
       SYNTAX       Unsigned32
       MAX-ACCESS   read-write
       STATUS       current
       DESCRIPTION
               "Sets the EOAM error symbol threshold."
        ::= { eoamLinkMonitorEntry 9 }

    errorFrameSecondsWindow OBJECT-TYPE
       SYNTAX       Unsigned32
       MAX-ACCESS   read-write
       STATUS       current
       DESCRIPTION
               "Sets the EOAM error symbol window."
        ::= { eoamLinkMonitorEntry 10 }

    errorFramePeriodNotifyState OBJECT-TYPE
       SYNTAX       INTEGER { enabled(1), disabled(2) }
       MAX-ACCESS   read-write
       STATUS       current
       DESCRIPTION
               "Sets the EOAM error symbol notify state enabled or disabled."
        ::= { eoamLinkMonitorEntry 11 }

    errorFramePeriodThreshold OBJECT-TYPE
       SYNTAX       Unsigned32
       MAX-ACCESS   read-write
       STATUS       current
       DESCRIPTION
               "Sets the EOAM error symbol threshold."
        ::= { eoamLinkMonitorEntry 12 }

    errorFramePeriodWindow OBJECT-TYPE
       SYNTAX       Unsigned32
       MAX-ACCESS   read-write
       STATUS       current
       DESCRIPTION
               "Sets the EOAM error symbol window."
        ::= { eoamLinkMonitorEntry 13 }

    -- ---------------------------------------------------------------------
    -- EOAM Function
    -- ---------------------------------------------------------------------
      duldSystem                OBJECT IDENTIFIER ::= { companyDuld 1 }

    -- ------------------------------------------------------------------
    -- The DULD System Group
    -- ------------------------------------------------------------------

    duldTable  OBJECT-TYPE
        SYNTAX     SEQUENCE OF DULDConfigEntry 
        MAX-ACCESS not-accessible
        STATUS     current
        DESCRIPTION
           "A table that contains DULD mode information about each port."
        ::= { duldSystem 1 }

    duldEntry OBJECT-TYPE
        SYNTAX     DULDConfigEntry 
        MAX-ACCESS not-accessible
        STATUS     current
        DESCRIPTION
              "A list of DULD mode information for each port."
        INDEX { duldIfIndex }
        ::= { duldTable 1 }

    DULDConfigEntry ::= 
            SEQUENCE {
              duldIfIndex                    InterfaceIndex,
              duldState                      INTEGER,
              duldOperState                  INTEGER,
              duldMode                       INTEGER,
              duldLinkStatus                 INTEGER,
              duldDiscoveryTime              Unsigned32
              }

    duldIfIndex OBJECT-TYPE
        SYNTAX      InterfaceIndex
        MAX-ACCESS  read-only
        STATUS      current
        DESCRIPTION
              "The index of the port. "
        ::= { duldEntry 1 }

    duldState OBJECT-TYPE
       SYNTAX       INTEGER { enabled(1), disabled(2) }
       MAX-ACCESS   read-write
       STATUS       current
       DESCRIPTION
               "Sets the DULD admin state enabled or disabled."
        ::= { duldEntry 2 }

    duldOperState OBJECT-TYPE
       SYNTAX       INTEGER { enabled(1), disabled(2) }
       MAX-ACCESS   read-only
       STATUS       current
       DESCRIPTION
               "Gets the DULD Oper state enabled or disabled."
        ::= { duldEntry 3 }

    duldMode OBJECT-TYPE
       SYNTAX       INTEGER { shutdown(1), normal(2) }
       MAX-ACCESS   read-write
       STATUS       current
       DESCRIPTION
               "Sets the DULD mode as shutdown or normal."
        ::= { duldEntry 4 }

    duldLinkStatus OBJECT-TYPE
       SYNTAX       INTEGER { unknow(1), bidirectional(2), txFault(3), rxFault(4), linkDown(5) }
       MAX-ACCESS   read-only
       STATUS       current
       DESCRIPTION
               "Gets the DULD link status."
        ::= { duldEntry 5 }

    duldDiscoveryTime OBJECT-TYPE
       SYNTAX       Unsigned32 (5..65535) 
       MAX-ACCESS   read-write
       STATUS       current
       DESCRIPTION
               "Sets the DULD discovery time."
        ::= { duldEntry 6 }

    duldRecoverTime  OBJECT-TYPE
        SYNTAX     Integer32 (0 | 60..1000000)
        MAX-ACCESS read-write
        STATUS     current
        DESCRIPTION
           "Duld auto recover time."
        DEFVAL  { 60 }
        ::= { duldSystem 2 }

-- ----------------------------------------------------------
-- The companyDoSCtrl Groups
-- ----------------------------------------------------------
-- Dos prevention Group 	
						
    doSCtrlTable  OBJECT-TYPE
        SYNTAX  SEQUENCE OF DoSCtrlEntry
        MAX-ACCESS  not-accessible
        STATUS  current
        DESCRIPTION
            "A table that holds the DoS prevention settings of the device."
        ::= { companyDoSCtrl 1 }

    doSCtrlEntry OBJECT-TYPE
        SYNTAX  DoSCtrlEntry
        MAX-ACCESS  not-accessible
        STATUS  current
        DESCRIPTION
            "A list of DoS prevention settings of the device."
        INDEX   { doSCtrlType }
        ::= { doSCtrlTable 1 }

    DoSCtrlEntry ::= 
        SEQUENCE {
			doSCtrlType
				INTEGER,
			doSCtrlState
				INTEGER,
			doSCtrlActionType
				INTEGER
        }
        
    doSCtrlType OBJECT-TYPE
    	SYNTAX INTEGER {
			land-attack(1),
			blat-attack(2),
			tcp-null-scan(4),
			tcp-xmascan(5),
			tcp-synfin(6),
			tcp-syn-srcport-less-1024(7),
			ping-death-attack(8),
			tcp-tiny-fragment(9)
   	    	}
        MAX-ACCESS  read-only
        STATUS current
        DESCRIPTION
            "This object indicates the DoS prevention type."
    ::= { doSCtrlEntry 1 }
    
	  doSCtrlState OBJECT-TYPE
        SYNTAX INTEGER {
                          disabled (0),
                          enabled  (1)
               }
        MAX-ACCESS  read-write
        STATUS  current
        DESCRIPTION
            "This object indicates the status of the DoS prevention type."
    ::= { doSCtrlEntry 2 }
       
    doSCtrlActionType OBJECT-TYPE
        SYNTAX  INTEGER {
               drop(0)
               }
        MAX-ACCESS  read-write
        STATUS  current
        DESCRIPTION
            "This object indicates the action for the DoS prevention type. 
            If this object is set to 'mirror' and DoSCtrlState is set to 'enable', the configuration 
            will not take effect until a valid mirror port is specified. If mirror port is not valid
            the behavior will be the same as 'drop'"
        ::= { doSCtrlEntry 3 }

	dosCtrlTrapLogState OBJECT-TYPE 
           SYNTAX      INTEGER {
                          disabled (0),
                          enabled  (1)
                       }
           MAX-ACCESS  read-write 
           STATUS      current 
           DESCRIPTION 
               "Enable/Disable Dos Trap Log function.
               Default is disabled."
                 
           DEFVAL  { disabled }
           ::= { companyDoSCtrl 2 }

	-- -----------------------------------------------------------------
	-- The PoE Groups
	-- -----------------------------------------------------------------


    --------------------------------------------
    -- PoEPortSetting
    --------------------------------------------

    sysPoEPortSettingTable OBJECT-TYPE
            SYNTAX SEQUENCE OF SysPoEPortSettingEntry
            MAX-ACCESS not-accessible
            STATUS current
            DESCRIPTION
                "A table of objects that display and control the power
            characteristics of power Ethernet ports on a Power Source
            Entity (PSE) device."
           ::= { companyPoEGroup 1 }

    sysPoEPortSettingEntry OBJECT-TYPE
            SYNTAX SysPoEPortSettingEntry
            MAX-ACCESS not-accessible
            STATUS current
            DESCRIPTION
                "A set of objects that display and control the power
               characteristics of a power Ethernet PSE port."
           INDEX { poeportgroup, poeportid }
           ::= { sysPoEPortSettingTable 1 }

    SysPoEPortSettingEntry ::=
           SEQUENCE {
                poeportgroup
                    INTEGER,
                poeportid
                    INTEGER,
                poePortSettingState
                    INTEGER,
                poePortTimeBaseSchduleID
                    Integer32,                    
                poePortSettingPriority
                    INTEGER,
                poePortSettingPowerLimit
                    INTEGER,
                poePortSettingUserDefineState
                    INTEGER,
                poePortSettingUserDefine
                    DisplayString,
                poePortPower
                    DisplayString,
                poePortVoltage
                    DisplayString,
                poePortCurrent
                    DisplayString,
                poePortClassification
                    DisplayString,
				poePortDelayPowerDetect
					INTEGER,  
                poePortStatus
                    DisplayString
          }
    poeportgroup OBJECT-TYPE
        SYNTAX INTEGER
        MAX-ACCESS read-only
        STATUS current
        DESCRIPTION
            "This object is the PoE port group index."
        ::= { sysPoEPortSettingEntry 1 }

    poeportid OBJECT-TYPE
        SYNTAX INTEGER
        MAX-ACCESS read-only
        STATUS current
        DESCRIPTION
            "This object is the PoE Port ID Index."
        ::= { sysPoEPortSettingEntry 2 }

    poePortSettingState OBJECT-TYPE
        SYNTAX INTEGER {
                    enabled         (1),
                    disabled        (2)
        }
        MAX-ACCESS  read-write
        STATUS      current
        DESCRIPTION
            "Enable/Disable PoE function on this port."

        ::= { sysPoEPortSettingEntry 3 }

    poePortTimeBaseSchduleID OBJECT-TYPE
        SYNTAX      Integer32 (0..24)
        MAX-ACCESS  read-write
        STATUS      current
        DESCRIPTION
            "Enable timebase schedule function and join with this schedule ID on this port. 
            Setting 0 means disable timebase schedule function on this port."
        ::= { sysPoEPortSettingEntry 4 }

    poePortSettingPriority OBJECT-TYPE
        SYNTAX INTEGER {
                     low            (1),
                     normal         (2),
                     high           (3)
        }
        MAX-ACCESS  read-write
        STATUS      current
        DESCRIPTION
          "Configures PoE port priority."

        ::= { sysPoEPortSettingEntry 5 }

    poePortSettingPowerLimit OBJECT-TYPE
        SYNTAX INTEGER {
                     auto        (1),
                     class1        (2),
                     class2        (3),
                     class3        (4),
                     class4       (5)                    
        }
        MAX-ACCESS  read-write
        STATUS      current
        DESCRIPTION
          "Configures PoE port power limit."

        ::= { sysPoEPortSettingEntry 6 }

    poePortSettingUserDefineState OBJECT-TYPE
        SYNTAX INTEGER {
                    enabled         (1),
                    disabled        (2)
        }
        MAX-ACCESS  read-write
        STATUS      current
        DESCRIPTION
            "Enable/Disable manual configuring max power on this port."

        ::= { sysPoEPortSettingEntry 7 }

    poePortSettingUserDefine OBJECT-TYPE        	          	
       	SYNTAX      DisplayString (SIZE(1..4))

		MAX-ACCESS  read-write
		STATUS      current
		DESCRIPTION
        	"This object manually configures max power value(e.g., `1, 2.2, 21.8') on this port. 
        	The per-port power limit must be a multiple of 0.2.
        	If the user define state is not enabled,
        	the value is the zero-length string."
        --DEFVAL     { 0 }
        ::= { sysPoEPortSettingEntry 8 }

    poePortPower OBJECT-TYPE        	          	
       	SYNTAX      DisplayString (SIZE(1..4))

		MAX-ACCESS  read-only
		STATUS      current
		DESCRIPTION
        	"This object displays PoE port power(W)(e.g., `0.0, 2.3, 21.8').
        	If the PoE port tatus is POWER OFF, the value is 0.0."
        --DEFVAL     { 0 }
        ::= { sysPoEPortSettingEntry 9 }
        
    poePortVoltage OBJECT-TYPE        	          	
       	SYNTAX      DisplayString (SIZE(1..4))

		MAX-ACCESS  read-only
		STATUS      current
		DESCRIPTION
        	"This object displays PoE port voltage(V)(e.g., `0.0, 2.3, 21.8').
        	If the PoE port tatus is POWER OFF, the value is 0.0."
        --DEFVAL     { 0 }
        ::= { sysPoEPortSettingEntry 10 }
        
    poePortCurrent OBJECT-TYPE        	          	
       	SYNTAX      DisplayString (SIZE(1..5))

		MAX-ACCESS  read-only
		STATUS      current
		DESCRIPTION
        	"This object displays PoE port current(mA)(e.g., `0.0, 22.3, 120.8').
        	If the PoE port tatus is POWER OFF, the value is 0.0."
        --DEFVAL     { 0 }
        ::= { sysPoEPortSettingEntry 11 }
        
    poePortClassification OBJECT-TYPE        	          	
       	SYNTAX      DisplayString (SIZE(1..20))

		MAX-ACCESS  read-only
		STATUS      current
		DESCRIPTION
        	"This object displays PoE port power classification(e.g., `NA, Class 2, 20.2(User Defined)').
        	If the PoE port tatus is POWER OFF, the value is NA."
        --DEFVAL     { 0 }
        ::= { sysPoEPortSettingEntry 12 }

	poePortDelayPowerDetect OBJECT-TYPE
        SYNTAX INTEGER {
                    enabled         (1),
                    disabled        (2)
        }
        MAX-ACCESS  read-write
        STATUS      current
        DESCRIPTION
            "Enable/Disable Delay Power Detect function on this port."

        ::= { sysPoEPortSettingEntry 13}
      
    poePortStatus OBJECT-TYPE
       	SYNTAX      DisplayString (SIZE(1..20))

		MAX-ACCESS  read-only
		STATUS      current
		DESCRIPTION
        	"This object displays PoE port powering status(e.g., `POWER OFF, POWER ON')."
        --DEFVAL     { 0 }
        ::= { sysPoEPortSettingEntry 99 }                                      

    --------------------------------------------
    -- PoESystemSetting
    --------------------------------------------
    poeSystemSettingPowerThreshold OBJECT-TYPE
       	SYNTAX      DisplayString (SIZE(1..4))

		MAX-ACCESS  read-write
		STATUS      current
		DESCRIPTION
        	"This object configures available system power budget (e.g., `50.2')."
        --DEFVAL     { 0 }

        ::= { companyPoEGroup 2 }

    poeSystemSettingDisconnectMethod OBJECT-TYPE
        SYNTAX INTEGER {
                    denyNextPort        (1),
                    denyLowPriorityPort (2)
        }
        MAX-ACCESS  read-write
        STATUS      current
        DESCRIPTION
            "This object configures PoE power denied rule while system 
             entering in guard band mode."

        ::= { companyPoEGroup 3 }

    pethPsePortPowerBudget OBJECT-TYPE
       	SYNTAX      DisplayString (SIZE(1..4))

        MAX-ACCESS  read-only
        STATUS      current
        DESCRIPTION
        	"This object displays PoE system power budget (e.g., `50.2')."
        --DEFVAL     { 0 }

        ::= { companyPoEGroup 4 }
        
    pethPsePortPowerConsumption OBJECT-TYPE
       	SYNTAX      DisplayString (SIZE(1..4))

        MAX-ACCESS  read-only
        STATUS      current
        DESCRIPTION
        	"This object displays PoE total power consumption (e.g., `3.3, 15.4')."
        --DEFVAL     { 0 }

        ::= { companyPoEGroup 5 }

    pethPsePortPowerRemainder OBJECT-TYPE
       	SYNTAX      DisplayString (SIZE(1..4))

		MAX-ACCESS  read-only
		STATUS      current
		DESCRIPTION
        	"This object displays PoE power remainder (e.g., `60.2')."
        --DEFVAL     { 0 }

        ::= { companyPoEGroup 6 }

    pethPsePortPowerRatioOfSystemPower OBJECT-TYPE
       	SYNTAX      DisplayString (SIZE(1..4))

		MAX-ACCESS  read-only
		STATUS      current
		DESCRIPTION
        	"This object displays power ratio of system power in unit of percentage(e.g., `4.2')."
        --DEFVAL     { 0 }

        ::= { companyPoEGroup 7 }                
-- start POE-LEDMODE
    poeLedMode OBJECT-TYPE
        SYNTAX INTEGER
        MAX-ACCESS read-only
        STATUS current
        DESCRIPTION
            "Port led mode indicator. 1: Link/Act/Speed mode; 2: PoE mode."
        ::= { companyPoEGroup 8 }
-- end POE-LEDMODE        
        
    -- ------------------------------------------------------------------
    -- The Time Range Setting
    -- ------------------------------------------------------------------

	    swTimeRangeSettingTable OBJECT-TYPE
	       SYNTAX      SEQUENCE OF SwTimeRangeSettingEntry
	       MAX-ACCESS  not-accessible
	       STATUS      current
	       DESCRIPTION
	           "A table to configure time Range in the system."
	       ::= { companyTimeRangeMgmt 1 }
	    
	    swTimeRangeSettingEntry OBJECT-TYPE
	       SYNTAX      SwTimeRangeSettingEntry
	       MAX-ACCESS  not-accessible
	       STATUS      current
	            DESCRIPTION
	                "A schedule entry to configure time Range in the system."     
	       INDEX { swTimeRangeIndex }
	       ::= { swTimeRangeSettingTable 1 }      
	       
	    SwTimeRangeSettingEntry ::=
	       SEQUENCE { 
	          	swTimeRangeIndex     	    Integer32,      
	          	swTimeRangeName	            DisplayString,
	          	swTimeRangeDate             INTEGER,          	          	
	            swTimeRangeStartYear		INTEGER,
	            swTimeRangeStartMonth		INTEGER,
	            swTimeRangeStartDay			Integer32,
	            swTimeRangeStartHour		Integer32,
	            swTimeRangeStartMinute    	Integer32,
	            swTimeRangeEndYear			INTEGER,
	            swTimeRangeEndMonth			INTEGER,
	            swTimeRangeEndDay			Integer32,
	            swTimeRangeEndHour			Integer32,
	            swTimeRangeEndMinute       	Integer32,          
	            swTimeRangeMonday          	INTEGER,
	            swTimeRangeTuesday         	INTEGER,
	            swTimeRangeWednesday       	INTEGER,
	            swTimeRangeThursday        	INTEGER,
	            swTimeRangeFriday          	INTEGER,
	            swTimeRangeSaturday        	INTEGER,
	            swTimeRangeSunday          	INTEGER,
	          	swTimeRangeRowStatus  		RowStatus             
	     } 
	
	    swTimeRangeIndex OBJECT-TYPE 
	       SYNTAX      Integer32 (1..52)
	       MAX-ACCESS  read-only 
	       STATUS      current 
	            DESCRIPTION
	                "The Time Range identifier. The maximum number of Schedule entry is 
                     the number of ports supported PoE function.
	                 The value must be between 1 and 52."
	       ::= { swTimeRangeSettingEntry 1 }
	    
	    swTimeRangeName OBJECT-TYPE 
	       SYNTAX      DisplayString (SIZE(1..20))
	       MAX-ACCESS  read-write 
	       STATUS      current 
	            DESCRIPTION
	                "The Schedule name associated with the Schedule entry (e.g., `abc, bbb')."
	       ::= { swTimeRangeSettingEntry 2}
	
	    swTimeRangeDate  OBJECT-TYPE
	        SYNTAX INTEGER  {
	    		 enabled(1),
	    		 disabled(2)
	        }
	        MAX-ACCESS read-write
	        STATUS current
	        DESCRIPTION 
	            "Enable/Disable date range checking while executing time base PoE."
	        ::= { swTimeRangeSettingEntry 3}       
	       
		swTimeRangeStartYear  OBJECT-TYPE
	            SYNTAX INTEGER {
		               y2009(2009),
		               y2010(2010),
		               y2011(2011),
		               y2012(2012),
		               y2013(2013),
		               y2014(2014),
		               y2015(2015),
		               y2016(2016),
		               y2017(2017),
		               y2018(2018),
		               y2019(2019),
		               y2020(2020),
		               y2021(2021),
		               y2022(2022),
		               y2023(2023),
		               y2024(2024),
		               y2025(2025),
		               y2026(2026),
		               y2027(2027),
		               y2028(2028),
		               y2029(2029),
		               y2030(2030),
		               y2031(2031),
		               y2032(2032),
		               y2033(2033),
		               y2034(2034),
		               y2035(2035),
		               y2036(2036),
		               y2037(2037)
	            }
				   MAX-ACCESS   read-write
				   STATUS       current
	            DESCRIPTION
	                "Start year of the Schedule entry."
	            ::= { swTimeRangeSettingEntry 4 }
	
		swTimeRangeStartMonth  OBJECT-TYPE
	            SYNTAX INTEGER {
	                   january(1),
		               february(2),
		               march(3),
		               april(4),
		               may(5),
		               june(6),
		               july(7),
		               august(8),
		               september(9),
		               october(10),
		               november(11),
		               december(12)
	            }
	   			MAX-ACCESS   read-write
	  			STATUS       current
	            DESCRIPTION
	                "Start month of the Schedule entry."
	            ::= { swTimeRangeSettingEntry 5 }
	
		swTimeRangeStartDay  OBJECT-TYPE
	            SYNTAX Integer32 (1..31)
	   			MAX-ACCESS   read-write
	  			STATUS       current
	            DESCRIPTION
	                "Start day of the Schedule entry.
	                The value must be from 1 to 31."
	            ::= { swTimeRangeSettingEntry 6 }
		   
		swTimeRangeStartHour  OBJECT-TYPE
	            SYNTAX Integer32 (0..23)
	   			MAX-ACCESS   read-write
	  			STATUS       current
	            DESCRIPTION
	                "Start hour of the Schedule entry.
	                The value must be from 0 to 23."
	            ::= { swTimeRangeSettingEntry 7 }
		
		swTimeRangeStartMinute  OBJECT-TYPE
	            SYNTAX Integer32 (0..59)
	   			MAX-ACCESS   read-write
	  			STATUS       current
	            DESCRIPTION
	                "Start minute of the Schedule entry.
	                The value must be from 0 to 59."
	            ::= { swTimeRangeSettingEntry 8 }	   
	
		swTimeRangeEndYear  OBJECT-TYPE
	            SYNTAX INTEGER {
		               y2009(2009),
		               y2010(2010),
		               y2011(2011),
		               y2012(2012),
		               y2013(2013),
		               y2014(2014),
		               y2015(2015),
		               y2016(2016),
		               y2017(2017),
		               y2018(2018),
		               y2019(2019),
		               y2020(2020),
		               y2021(2021),
		               y2022(2022),
		               y2023(2023),
		               y2024(2024),
		               y2025(2025),
		               y2026(2026),
		               y2027(2027),
		               y2028(2028),
		               y2029(2029),
		               y2030(2030),
		               y2031(2031),
		               y2032(2032),
		               y2033(2033),
		               y2034(2034),
		               y2035(2035),
		               y2036(2036),
		               y2037(2037)
	            }
	   			MAX-ACCESS   read-write
	  			STATUS       current
	            DESCRIPTION
	                "End year of the Schedule entry."
	            ::= { swTimeRangeSettingEntry 9 }
	
		swTimeRangeEndMonth  OBJECT-TYPE
	            SYNTAX INTEGER {
	                   january(1),
		               february(2),
		               march(3),
		               april(4),
		               may(5),
		               june(6),
		               july(7),
		               august(8),
		               september(9),
		               october(10),
		               november(11),
		               december(12)
	            }
	   			MAX-ACCESS   read-write
	  			STATUS       current
	            DESCRIPTION
	                "End month of the Schedule entry."
	            ::= { swTimeRangeSettingEntry 10 }
	
		swTimeRangeEndDay  OBJECT-TYPE
	            SYNTAX Integer32 (1..31)
	   			MAX-ACCESS   read-write
	  			STATUS       current
	            DESCRIPTION
	                "End day of the Schedule entry.
	                The value must be from 1 to 31."
	            ::= { swTimeRangeSettingEntry 11 }
		   
		swTimeRangeEndHour  OBJECT-TYPE
	            SYNTAX Integer32 (0..23)
	   			MAX-ACCESS   read-write
	  			STATUS       current
	            DESCRIPTION
	                "End hour of the Schedule entry.
	                The value must be from 0 to 23."
	            ::= { swTimeRangeSettingEntry 12 }
		
		swTimeRangeEndMinute  OBJECT-TYPE
	            SYNTAX Integer32 (0..59)
	   			MAX-ACCESS   read-write
	  			STATUS       current
	            DESCRIPTION
	                "End minute of the Schedule entry.
	                The value must be from 0 to 59."
	            ::= { swTimeRangeSettingEntry 13 }

        swTimeRangeMonday OBJECT-TYPE
			SYNTAX      INTEGER {
			            enable(1),
			            disable(2)
			           }
			MAX-ACCESS  read-write
			STATUS      current
			DESCRIPTION 
			  "Enable/Disble scheduling Monday."
			  DEFVAL { disable }
			::= { swTimeRangeSettingEntry 14 }            

        swTimeRangeTuesday OBJECT-TYPE
			SYNTAX      INTEGER {
			            enable(1),
			            disable(2)
			           }
			MAX-ACCESS  read-write
			STATUS      current
			DESCRIPTION 
			  "Enable/Disble scheduling Tuesday."
			  DEFVAL { disable }
			::= { swTimeRangeSettingEntry 15 }         
            
        swTimeRangeWednesday OBJECT-TYPE
			SYNTAX      INTEGER {
			            enable(1),
			            disable(2)
			           }
			MAX-ACCESS  read-write
			STATUS      current
			DESCRIPTION 
			  "Enable/Disble scheduling Wednesday."
			  DEFVAL { disable }
			::= { swTimeRangeSettingEntry 16 } 
            
        swTimeRangeThursday OBJECT-TYPE
			SYNTAX      INTEGER {
			            enable(1),
			            disable(2)
			           }
			MAX-ACCESS  read-write
			STATUS      current
			DESCRIPTION 
			  "Enable/Disble scheduling Thursday."
			  DEFVAL { disable }
			::= { swTimeRangeSettingEntry 17 } 
            
        swTimeRangeFriday OBJECT-TYPE
			SYNTAX      INTEGER {
			            enable(1),
			            disable(2)
			           }
			MAX-ACCESS  read-write
			STATUS      current
			DESCRIPTION 
			  "Enable/Disble scheduling Friday."
			  DEFVAL { disable }
			::= { swTimeRangeSettingEntry 18 }
            
        swTimeRangeSaturday OBJECT-TYPE
			SYNTAX      INTEGER {
			            enable(1),
			            disable(2)
			           }
			MAX-ACCESS  read-write
			STATUS      current
			DESCRIPTION 
			  "Enable/Disble scheduling Saturday."
			  DEFVAL { disable }
			::= { swTimeRangeSettingEntry 19 }
            
        swTimeRangeSunday OBJECT-TYPE
			SYNTAX      INTEGER {
			            enable(1),
			            disable(2)
			           }
			MAX-ACCESS  read-write
			STATUS      current
			DESCRIPTION 
			  "Enable/Disble scheduling Sunday."
			  DEFVAL { disable }
			::= { swTimeRangeSettingEntry 20 }    
	
	    swTimeRangeRowStatus OBJECT-TYPE
	       SYNTAX      RowStatus
	       MAX-ACCESS  read-create
	       STATUS      current
	       DESCRIPTION
	             "The status of an entry in the Time Range Information Table.  Only a subset
	             of the rowstatus variables (active, notinservice, createAndWait, destroy) 
	             are available."
	       ::= { swTimeRangeSettingEntry 21 }            



    --
    -- LLDP  Settings
    --

    dlinklldpState  OBJECT-TYPE
       SYNTAX       INTEGER {
                    enable(1),
                    disable(2)
                   }
       MAX-ACCESS  read-write
       STATUS      current
       DESCRIPTION
            "This object is used for enabling or disabling LLDP in the system."

       DEFVAL  { disable }
       ::= { companyLLDPSetting 1 }

    dlinklldpMsgHoldMultiplier OBJECT-TYPE
        SYNTAX      INTEGER (2..10)
        MAX-ACCESS  read-write
        STATUS      current
        DESCRIPTION
            "The time-to-live value expressed as a multiple of the
            lldpMessageTxInterval object.The actual time-to-live value
            used in LLDP frames, transmitted on behalf of this LLDP agent,
            can be expressed by the following formula: TTL = min(65535,
            (lldpMessageTxInterval * lldpMessageTxHoldMultiplier))"
        --DEFVAL     { 4 }

        ::= { companyLLDPSetting 2 }

    dlinklldpMsgTxInterval OBJECT-TYPE
        SYNTAX      INTEGER (5..32768)
		MAX-ACCESS  read-write
		STATUS      current
		DESCRIPTION
            "This object is used for LLDP packet update frequency.
            The timer in units of seconds."
        --DEFVAL     { 30 }

        ::= { companyLLDPSetting 3 }

    dlinklldpReinitDelay OBJECT-TYPE
        SYNTAX      INTEGER (1..10)
        MAX-ACCESS  read-write
        STATUS      current
        DESCRIPTION
        	"This object is used for LLDP Reinitialization Delay.
        	The timer in units of seconds."
        --DEFVAL     { 2 }

        ::= { companyLLDPSetting 4 }

    dlinklldpTxDelay OBJECT-TYPE
        SYNTAX      INTEGER (1..8192)
        MAX-ACCESS  read-write
        STATUS      current
        DESCRIPTION
        	"The lldpTxDelay indicates the delay (in units
         	of seconds) between successive LLDP frame transmissions 
         	initiated by value/status changes in the LLDP local systems
         	MIB.  The recommended value for the lldpTxDelay is set by the
         	following  formula:
 	
 	        1 <= lldpTxDelay <= (0.25 * lldpMessageTxInterval)."
        --DEFVAL     { 2 }

        ::= { companyLLDPSetting 5 }
        
--
-- lldpManAddrConfigTxPortsTable : selection of management addresses
--                                 to be transmitted on a specified set
--                                 of ports.
-- 

    dlinklldpConfigManAddrPortsTxEnable  OBJECT-TYPE
        SYNTAX        PortList
        MAX-ACCESS    read-write
        STATUS        current
        DESCRIPTION
            "A set of ports that are identified by a PortList, in which
            each port is represented as a bit.  The corresponding local
            system management address instance will be transmitted on the
            member ports of the lldpManAddrPortsTxEnable.  
            
            The default value for lldpConfigManAddrPortsTxEnable object
            is empty binary string, which means no ports are specified
            for advertising indicated management address instance."
        REFERENCE 
                "IEEE 802.1AB-2005 10.2.1.1"

        ::= { companyLLDPSetting 6 }
 
    --
    -- LLDP-MED for PoE Port Settings
    --

    lldpMEDPortControlTable OBJECT-TYPE
        SYNTAX      SEQUENCE OF LldpMEDPortControlEntry
        MAX-ACCESS  not-accessible
        STATUS      current
        DESCRIPTION
            "A table that contains LLDP-MED control,
            A row appears in this table for each physical port."
        ::= { companyLLDPSetting 7 }

    lldpMEDPortControlEntry OBJECT-TYPE
        SYNTAX      LldpMEDPortControlEntry
        MAX-ACCESS  not-accessible
        STATUS      current
        DESCRIPTION
            "A list of LLDP-MED for PoE Port Settings
            parameters for each Port on this device."
        INDEX      { lldpMEDPortControlIndex }
      ::= { lldpMEDPortControlTable 1 }

    LldpMEDPortControlEntry ::=
      SEQUENCE {
        lldpMEDPortControlIndex
            InterfaceIndex,
        lldpMEDPortState
            INTEGER
    }

    lldpMEDPortControlIndex OBJECT-TYPE
        SYNTAX       InterfaceIndex
        MAX-ACCESS   read-only
        STATUS       current
        DESCRIPTION
            "The Control Index of the LLDP-MED Power PSE TLV port."
      ::= { lldpMEDPortControlEntry 1 }

    lldpMEDPortState  OBJECT-TYPE
      SYNTAX       INTEGER { enabled(1), disabled(2) }
      MAX-ACCESS   read-write
      STATUS       current
      DESCRIPTION
            "This object is for enabling or disabling LLDP-MED 
            Power PSE TLV Setting in the system."
      ::= { lldpMEDPortControlEntry 2 }
      
    --
    -- LLDP for Anti-Rogue Settings
    --
    dlinklldpAntiRoguePortControl  OBJECT-TYPE
       SYNTAX      PortList
       MAX-ACCESS  read-write
       STATUS      current
       DESCRIPTION
            "When LLDP anti-rogue port control is enabled , this identifies the
            port control status of each port.
            
            The default setting is disable."
       ::= { companyLLDPSetting 8 }

    dlinklldpRemOrgDefInfoTable OBJECT-TYPE
        SYNTAX      SEQUENCE OF LldpRemOrgDefInfoEntry
        MAX-ACCESS  not-accessible
        STATUS      current
        DESCRIPTION
            "This table contains one or more rows per physical network
            connection which advertises the organizationally defined
            information.
            
            Note that this table contains one or more rows of
            organizationally defined information that is not recognized
            by the local agent.
            
            If the local system is capable of recognizing any
            organizationally defined information, appropriate extension
            MIBs from the organization should be used for information
            retrieval."
        ::= { companyLLDPSetting 9 }

    lldpRemOrgDefInfoEntry OBJECT-TYPE
        SYNTAX      LldpRemOrgDefInfoEntry
        MAX-ACCESS  not-accessible
        STATUS      current
        DESCRIPTION
            "Information about the unrecognized organizationally
            defined information advertised by the remote system.
            The lldpAntiRoguePortIndex is index to this table."
        INDEX      { dlinklldpAntiRoguePortIndex }
      ::= { dlinklldpRemOrgDefInfoTable 1 }

    LldpRemOrgDefInfoEntry ::=
      SEQUENCE {
        dlinklldpAntiRoguePortIndex
            InterfaceIndex,
        dlinklldpAntiRoguePortStatus
            INTEGER,
        dlinklldpRemOrgDefInfoOUI
            OCTET STRING
    }

    dlinklldpAntiRoguePortIndex OBJECT-TYPE
        SYNTAX       InterfaceIndex
        MAX-ACCESS   read-only
        STATUS       current
        DESCRIPTION
            "The Control Index of the LLDP Anti-Rogue port."
        ::= { lldpRemOrgDefInfoEntry 1 }

    dlinklldpAntiRoguePortStatus  OBJECT-TYPE
	    SYNTAX INTEGER {
                  authenticationDisabled(0),
                  authenticationEnabled(1),
                  authenticationSuccessful(2)
           }
	    MAX-ACCESS  read-only
	    STATUS      current
	    DESCRIPTION
            "The value represents each port's authentication status.
            0: Authentication disabled.
            1: Authentication enabled but not passed.
            2: Authentication successful."

        ::= { lldpRemOrgDefInfoEntry 2 }

    dlinklldpRemOrgDefInfoOUI  OBJECT-TYPE
	    SYNTAX      OCTET STRING (SIZE(3))
	    MAX-ACCESS  read-only
	    STATUS      current
	    DESCRIPTION
            "The Organizationally Unique Identifier (OUI), as defined
            in IEEE std 802-2001, is a 24 bit (three octets) globally
            unique assigned number referenced by various standards,
            of the information received from the remote system."
        REFERENCE
                "IEEE 802.1AB-2005 9.5.1.3"
        ::= { lldpRemOrgDefInfoEntry 3 }

    dlinklldpAntiRoguePassword  OBJECT-TYPE
       SYNTAX      DisplayString (SIZE(1..20))
       MAX-ACCESS  read-write
       STATUS      current
       DESCRIPTION
            "This object is used for Anti-Rogue Password setting.
             The default LLDP Anti-Rogue password is 'admin'."
       ::= { companyLLDPSetting 10 }

	--
	-- D-Link Defined LLDP Port Configuration Table
	--	

	-- textual conventions	
	LldpPortNumber ::= TEXTUAL-CONVENTION
    DISPLAY-HINT "d"
    STATUS     current 
    DESCRIPTION
            "Each port contained in the chassis (that is known to the
            LLDP agent) is uniquely identified by a port number.

            A port number has no mandatory relationship to an
            InterfaceIndex object (of the interfaces MIB, IETF RFC 2863).
            If the LLDP agent is a IEEE 802.1D, IEEE 802.1Q bridge, the
            LldpPortNumber will have the same value as the dot1dBasePort
            object (defined in IETF RFC 1493) associated corresponding
            bridge port.  If the system hosting LLDP agent is not an
            IEEE 802.1D or an IEEE 802.1Q bridge, the LldpPortNumber
            will have the same value as the corresponding interface's
            InterfaceIndex object.

            Port numbers should be in the range of 1 and 4096 since a
            particular port is also represented by the corresponding
            port number bit in LldpPortList."
    SYNTAX 	Integer32(1..4096)
    -- textual conventions end
    
	lldpPortConfigTable   OBJECT-TYPE
	    SYNTAX      SEQUENCE OF LldpPortConfigEntry
	    MAX-ACCESS  not-accessible
	    STATUS      current
	    DESCRIPTION
	            "The table that controls LLDP frame transmission on individual
	            ports."
	    ::= { companyLLDPSetting 11 }
	
	lldpPortConfigEntry   OBJECT-TYPE
	    SYNTAX      LldpPortConfigEntry
	    MAX-ACCESS  not-accessible
	    STATUS      current
	    DESCRIPTION
	            "LLDP configuration information for a particular port.
	            This configuration parameter controls the transmission and
	            the reception of LLDP frames on those ports whose rows are
	            created in this table."
	     INDEX  { lldpPortConfigPortNum }
	    ::= { lldpPortConfigTable 1 }
	
	LldpPortConfigEntry ::= SEQUENCE {
	      lldpPortConfigPortNum            LldpPortNumber,
	      lldpPortConfigAdminStatus        INTEGER,
	      lldpPortConfigNotificationEnable TruthValue,
	      lldpPortConfigTLVsTxEnable       BITS }
	
	lldpPortConfigPortNum   OBJECT-TYPE
	    SYNTAX      LldpPortNumber 
	    MAX-ACCESS  not-accessible
	    STATUS      current
	    DESCRIPTION
	            "The index value used to identify the port component
	            (contained in the local chassis with the LLDP agent)
	            associated with this entry.
	
	            The value of this object is used as a port index to the
	            lldpPortConfigTable."
	    ::= { lldpPortConfigEntry 1 }
	
	lldpPortConfigAdminStatus  OBJECT-TYPE 
	    SYNTAX INTEGER { 
	       txOnly(1), 
	       rxOnly(2),
	       txAndRx(3),
	       disabled(4)
	    }
	    MAX-ACCESS read-write 
	    STATUS     current 
	    DESCRIPTION 
	            "The administratively desired status of the local LLDP agent.
	
	            If the associated lldpPortConfigAdminStatus object has a
	            value of 'txOnly(1)', then LLDP agent will transmit LLDP
	            frames on this port and it will not store any information
	            about the remote systems connected.
	         
	            If the associated lldpPortConfigAdminStatus object has a
	            value of 'rxOnly(2)', then the LLDP agent will receive,
	            but it will not transmit LLDP frames on this port.
	
	            If the associated lldpPortConfigAdminStatus object has a
	            value of 'txAndRx(3)', then the LLDP agent will transmit
	            and receive LLDP frames on this port.
	
	            If the associated lldpPortConfigAdminStatus object has a
	            value of 'disabled(4)', then LLDP agent will not transmit or
	            receive LLDP frames on this port.  If there is remote systems
	            information which is received on this port and stored in
	            other tables, before the port's lldpPortConfigAdminStatus
	            becomes disabled, then the information will naturally age out."
	    REFERENCE 
	            "IEEE 802.1AB-2005 10.5.1"
	    DEFVAL  { txAndRx }    
	   ::= { lldpPortConfigEntry 2 } 
	
	lldpPortConfigNotificationEnable OBJECT-TYPE 
	    SYNTAX     TruthValue
	    MAX-ACCESS read-write 
	    STATUS     current 
	    DESCRIPTION 
	            "The lldpPortConfigNotificationEnable controls, on a per
	            port basis,  whether or not notifications from the agent
	            are enabled. The value true(1) means that notifications are
	            enabled; the value false(2) means that they are not."
	    DEFVAL  { false }    
	   ::= { lldpPortConfigEntry 3 } 
	
	lldpPortConfigTLVsTxEnable OBJECT-TYPE
	    SYNTAX      BITS {
	            portDesc(0),
	            sysName(1),
	            sysDesc(2),
	            sysCap(3)
	    }
	    MAX-ACCESS  read-write
	    STATUS      current
	    DESCRIPTION
	            "The lldpPortConfigTLVsTxEnable, defined as a bitmap,
	            includes the basic set of LLDP TLVs whose transmission is
	            allowed on the local LLDP agent by the network management.
	            Each bit in the bitmap corresponds to a TLV type associated
	            with a specific optional TLV.
	
	            It should be noted that the organizationally-specific TLVs
	            are excluded from the lldpTLVsTxEnable bitmap.
	            
	            LLDP Organization Specific Information Extension MIBs should
	            have similar configuration object to control transmission
	            of their organizationally defined TLVs.
	
	            The bit 'portDesc(0)' indicates that LLDP agent should
	            transmit 'Port Description TLV'.
	
	            The bit 'sysName(1)' indicates that LLDP agent should transmit
	            'System Name TLV'.
	
	            The bit 'sysDesc(2)' indicates that LLDP agent should transmit
	            'System Description TLV'.
	
	            The bit 'sysCap(3)' indicates that LLDP agent should transmit
	            'System Capabilities TLV'.
	
	            There is no bit reserved for the management address TLV type
	            since transmission of management address TLVs are controlled
	            by another object, lldpConfigManAddrTable.
	
	            The default value for lldpPortConfigTLVsTxEnable object is
	            empty set, which means no enumerated values are set.
	
	            The value of this object must be restored from non-volatile
	            storage after a re-initialization of the management system."
	    REFERENCE 
	            "IEEE 802.1AB-2005 10.2.1.1"
	--    DEFVAL  { { } }
	    ::= { lldpPortConfigEntry 4 } 


	--
	-- D-Link Defined LLDP Extension Dot3 MIB Objects
	--	
	lldpXdot3Objects    OBJECT IDENTIFIER ::= { companyLLDPSetting 12 }
	
	-- LLDP IEEE 802.3 extension MIB groups
	lldpXdot3Config     OBJECT IDENTIFIER ::= { lldpXdot3Objects 1 }
	lldpXdot3LocalData  OBJECT IDENTIFIER ::= { lldpXdot3Objects 2 }
	lldpXdot3RemoteData OBJECT IDENTIFIER ::= { lldpXdot3Objects 3 }
	
	-- textual conventions
	
	LldpPowerPortClass ::= TEXTUAL-CONVENTION
	    STATUS      current
	    DESCRIPTION
	            "This TC describes the Power over Ethernet (PoE) port class."
	    SYNTAX  INTEGER {
	            pClassPSE(1),
	            pClassPD(2)
	    }
	
	LldpLinkAggStatusMap ::= TEXTUAL-CONVENTION
	    STATUS      current
	    DESCRIPTION
	            "This TC describes the link aggregation status.
	
	            The bit 'aggCapable(0)' indicates the link is capable of being
	            aggregated. 
	
	            The bit 'aggEnabled(1)' indicates the link is currently in
	            aggregation."
	    SYNTAX  BITS {
	            aggCapable(0),
	            aggEnabled(1)
	    }
	
	------------------------------------------------------------------------------
	-- IEEE 802.3 - Configuration
	------------------------------------------------------------------------------
	
	lldpXdot3PortConfigTable OBJECT-TYPE
	    SYNTAX      SEQUENCE OF LldpXdot3PortConfigEntry
	    MAX-ACCESS  not-accessible
	    STATUS      current
	    DESCRIPTION
	            "A table that controls selection of LLDP TLVs to be transmitted 
	            on individual ports."
	    ::= { lldpXdot3Config 1 }
	
	lldpXdot3PortConfigEntry  OBJECT-TYPE
	    SYNTAX      LldpXdot3PortConfigEntry
	    MAX-ACCESS  not-accessible
	    STATUS      current
	    DESCRIPTION
	            "LLDP configuration information that controls the
	            transmission of IEEE 802.3 organizationally defined TLVs on
	            LLDP transmission capable ports.
	
	            This configuration object augments the lldpPortConfigEntry of
	            the LLDP-MIB, therefore it is only present along with the port
	            configuration defined by the associated lldpPortConfigEntry
	            entry.
	
	            Each active lldpXdot3PortConfigEntry must be from non-volatile
	            storage (along with the corresponding lldpPortConfigEntry)
	            after a re-initialization of the management system."
	    AUGMENTS { lldpPortConfigEntry }
	    ::= { lldpXdot3PortConfigTable 1 }
	
	LldpXdot3PortConfigEntry ::= SEQUENCE {
	      lldpXdot3PortConfigTLVsTxEnable  BITS
	}
	
	lldpXdot3PortConfigTLVsTxEnable  OBJECT-TYPE
	    SYNTAX      BITS {
	            macPhyConfigStatus(0),
	            powerViaMDI(1),
	            linkAggregation(2),
	            maxFrameSize(3)
	    }
	    MAX-ACCESS  read-write
	    STATUS      current
	    DESCRIPTION
	            "The lldpXdot3PortConfigTLVsTxEnable, defined as a bitmap,
	            includes the IEEE 802.3 organizationally defined set of LLDP
	            TLVs whose transmission is allowed on the local LLDP agent by
	            the network management.  Each bit in the bitmap corresponds
	            to an IEEE 802.3 subtype associated with a specific IEEE
	            802.3 optional TLV.  The bit 0 is not used since there is
	            no corresponding subtype.
	
	            The bit 'macPhyConfigStatus(0)' indicates that LLDP agent
	            should transmit 'MAC/PHY configuration/status TLV'.
	
	            The bit 'powerViaMDI(1)' indicates that LLDP agent should
	            transmit 'Power via MDI TLV'.
	
	            The bit 'linkAggregation(2)' indicates that LLDP agent should
	            transmit 'Link Aggregation TLV'.
	
	            The bit 'maxFrameSize(3)' indicates that LLDP agent should
	            transmit 'Maximum-frame-size TLV'.
	
	            The default value for lldpXdot3PortConfigTLVsTxEnable object
	            is an empty set, which means no enumerated values are set.
	
	            The value of this object must be restored from non-volatile
	            storage after a re-initialization of the management system."
	    REFERENCE 
	            "IEEE 802.1AB-2005 10.2.1.1"
	--    DEFVAL  { { } }
	    ::= { lldpXdot3PortConfigEntry  1 }
	
	
	------------------------------------------------------------------------------
	-- IEEE 802.3 - Local Device Information 
	------------------------------------------------------------------------------
	---
	--- lldpXdot3LocPortTable: Ethernet Port AutoNeg/Speed/Duplex
	---                        Information Table
	---
	---
	lldpXdot3LocPortTable OBJECT-TYPE
	    SYNTAX      SEQUENCE OF LldpXdot3LocPortEntry
	    MAX-ACCESS  not-accessible
	    STATUS      current
	    DESCRIPTION
	            "This table contains one row per port of Ethernet port
	            information (as a part of the LLDP 802.3 organizational
	            extension) on the local system known to this agent."
	    ::= { lldpXdot3LocalData 1 }
	
	lldpXdot3LocPortEntry OBJECT-TYPE
	    SYNTAX      LldpXdot3LocPortEntry
	    MAX-ACCESS  not-accessible
	    STATUS      current
	    DESCRIPTION
	            "Information about a particular port component."
	    INDEX   { lldpXdot3LocPortAutoNegSupported }
	    ::= { lldpXdot3LocPortTable 1 }
	
	LldpXdot3LocPortEntry ::= SEQUENCE {
	              lldpXdot3LocPortAutoNegSupported     TruthValue,
	              lldpXdot3LocPortAutoNegEnabled       TruthValue,
	              lldpXdot3LocPortAutoNegAdvertisedCap OCTET STRING,
	              lldpXdot3LocPortOperMauType          Integer32
	} 
	
	lldpXdot3LocPortAutoNegSupported OBJECT-TYPE
	    SYNTAX      TruthValue
	    MAX-ACCESS  read-only
	    STATUS      current
	    DESCRIPTION
	            "The truth value used to indicate whether the given port
	            (associated with the local system) supports Auto-negotiation."
	    REFERENCE 
	            "IEEE 802.1AB-2005 G.2.1"
	    ::= { lldpXdot3LocPortEntry 1 }
	
	lldpXdot3LocPortAutoNegEnabled  OBJECT-TYPE
	    SYNTAX      TruthValue
	    MAX-ACCESS  read-only
	    STATUS      current
	    DESCRIPTION
	            "The truth value used to indicate whether port
	            Auto-negotiation is enabled on the given port associated
	            with the local system."
	    REFERENCE 
	            "IEEE 802.1AB-2005 G.2.1"
	    ::= { lldpXdot3LocPortEntry 2 }
	
	lldpXdot3LocPortAutoNegAdvertisedCap OBJECT-TYPE
	    SYNTAX      OCTET STRING(SIZE(2))
	    MAX-ACCESS  read-only
	    STATUS      current
	    DESCRIPTION
	            "This object contains the value (bitmap) of the
	            ifMauAutoNegCapAdvertisedBits object (defined in IETF RFC
	            3636) which is associated with the given port on the
	            local system."
	    REFERENCE 
	            "IEEE 802.1AB-2005 G.2.2"
	    ::= { lldpXdot3LocPortEntry 3 }
	
	lldpXdot3LocPortOperMauType  OBJECT-TYPE
	    SYNTAX 	    Integer32(0..2147483647)
	    MAX-ACCESS  read-only
	    STATUS      current
	    DESCRIPTION
	            "An integer value that indicates the operational MAU type
	            of the given port on the local system.
	
	            This object contains the integer value derived from the
	            list position of the corresponding dot3MauType as listed 
	            in IETF RFC 3636 (or subsequent revisions) and is equal
	            to the last number in the respective dot3MauType OID.
	           
	            For example, if the ifMauType object is dot3MauType1000BaseTHD
	            which corresponds to {dot3MauType 29}, the numerical value of
	            this field will be 29. For MAU types not listed in RFC 3636
	            (or subsequent revisions), the value of this field shall be
	            set to zero."
	    REFERENCE 
	            "IEEE 802.1AB-2005 G.2.3"
	    ::= { lldpXdot3LocPortEntry 4 }
	
	---
	---
	--- lldpXdot3LocPowerTable: Power Ethernet Information Table
	---
	---
	lldpXdot3LocPowerTable OBJECT-TYPE
	    SYNTAX      SEQUENCE OF LldpXdot3LocPowerEntry
	    MAX-ACCESS  not-accessible
	    STATUS      current
	    DESCRIPTION
	            "This table contains one row per port of power ethernet 
	            information (as a part of the LLDP 802.3 organizational
	            extension) on the local system known to this agent."
	    ::= { lldpXdot3LocalData 2 }
	
	lldpXdot3LocPowerEntry OBJECT-TYPE
	    SYNTAX      LldpXdot3LocPowerEntry
	    MAX-ACCESS  not-accessible
	    STATUS      current
	    DESCRIPTION
	            "Information about a particular port component."
	    INDEX   { lldpXdot3LocPowerPortClass }
	    ::= { lldpXdot3LocPowerTable 1 }
	
	LldpXdot3LocPowerEntry ::= SEQUENCE {
	              lldpXdot3LocPowerPortClass           LldpPowerPortClass,
	              lldpXdot3LocPowerMDISupported        TruthValue,
	              lldpXdot3LocPowerMDIEnabled          TruthValue,
	              lldpXdot3LocPowerPairControlable     TruthValue,
	              lldpXdot3LocPowerPairs               Integer32,
	              lldpXdot3LocPowerClass               Integer32
	} 
	
	lldpXdot3LocPowerPortClass  OBJECT-TYPE
	    SYNTAX      LldpPowerPortClass
	    MAX-ACCESS  read-only
	    STATUS      current
	    DESCRIPTION
	            "The value that identifies the port Class of the given port
	            associated with the local system."
	    REFERENCE 
	            "IEEE 802.1AB-2005 G.3.1"
	    ::= { lldpXdot3LocPowerEntry 1 }
	
	lldpXdot3LocPowerMDISupported  OBJECT-TYPE
	    SYNTAX      TruthValue
	    MAX-ACCESS  read-only
	    STATUS      current
	    DESCRIPTION
	            "The truth value used to indicate whether the MDI power is
	            supported on the given port associated with the local system."
	    REFERENCE 
	            "IEEE 802.1AB-2005 G.3.1"
	    ::= { lldpXdot3LocPowerEntry 2 }
	
	lldpXdot3LocPowerMDIEnabled  OBJECT-TYPE
	    SYNTAX      TruthValue
	    MAX-ACCESS  read-only
	    STATUS      current
	    DESCRIPTION
	            "The truth value used to identify whether MDI power is
	            enabled on the given port associated with the local system."
	    REFERENCE 
	            "IEEE 802.1AB-2005 G.3.1"
	    ::= { lldpXdot3LocPowerEntry 3 }
	
	lldpXdot3LocPowerPairControlable  OBJECT-TYPE
	    SYNTAX      TruthValue
	    MAX-ACCESS  read-only
	    STATUS      current
	    DESCRIPTION
	            "The truth value is derived from the value of
	            pethPsePortPowerPairsControlAbility object (defined in IETF
	            RFC 3621) and is used to indicate whether the pair selection
	            can be controlled on the given port associated with the
	            local system."
	    REFERENCE 
	            "IEEE 802.1AB-2005 G.3.1"
	    ::= { lldpXdot3LocPowerEntry 4 }
	
	lldpXdot3LocPowerPairs  OBJECT-TYPE
	    SYNTAX      Integer32(1|2)
	    MAX-ACCESS  read-only
	    STATUS      current
	    DESCRIPTION
	            "This object contains the value of the pethPsePortPowerPairs
	            object (defined in IETF RFC 3621) which is associated with
	            the given port on the local system."
	    REFERENCE 
	            "IEEE 802.1AB-2005 G.3.2"
	    ::= { lldpXdot3LocPowerEntry 5 }
	
	lldpXdot3LocPowerClass  OBJECT-TYPE
	    SYNTAX      Integer32(1|2|3|4|5)
	    MAX-ACCESS  read-only
	    STATUS      current
	    DESCRIPTION
	            "This object contains the value of the
	            pethPsePortPowerClassifications object (defined in IETF
	            RFC 3621) which is associated with the given port on the
	            local system."
	    REFERENCE 
	            "IEEE 802.1AB-2005 G.3.3"
	    ::= { lldpXdot3LocPowerEntry 6 }
	
	---
	---
	--- lldpXdot3LocLinkAggTable: Link Aggregation Information Table
	---
	---
	lldpXdot3LocLinkAggTable OBJECT-TYPE
	    SYNTAX      SEQUENCE OF LldpXdot3LocLinkAggEntry
	    MAX-ACCESS  not-accessible
	    STATUS      current
	    DESCRIPTION
	            "This table contains one row per port of link aggregation 
	            information (as a part of the LLDP 802.3 organizational
	            extension) on the local system known to this agent."
	    ::= { lldpXdot3LocalData 3 }
	
	lldpXdot3LocLinkAggEntry OBJECT-TYPE
	    SYNTAX      LldpXdot3LocLinkAggEntry
	    MAX-ACCESS  not-accessible
	    STATUS      current
	    DESCRIPTION
	            "Link Aggregation information about a particular port
	            component."
	    INDEX   { lldpXdot3LocLinkAggStatus }
	    ::= { lldpXdot3LocLinkAggTable 1 }
	
	LldpXdot3LocLinkAggEntry ::= SEQUENCE {
	              lldpXdot3LocLinkAggStatus       LldpLinkAggStatusMap,
	              lldpXdot3LocLinkAggPortId       Integer32
	} 
	
	lldpXdot3LocLinkAggStatus OBJECT-TYPE
	    SYNTAX      LldpLinkAggStatusMap
	    MAX-ACCESS  read-only
	    STATUS      current
	    DESCRIPTION
	            "The bitmap value contains the link aggregation capabilities
	            and the current aggregation status of the link."
	    REFERENCE 
	            "IEEE 802.1AB-2005 G.4.1"
	    ::= { lldpXdot3LocLinkAggEntry 1 }
	
	lldpXdot3LocLinkAggPortId OBJECT-TYPE
	    SYNTAX 	    Integer32(0|1..2147483647)
	    MAX-ACCESS  read-only
	    STATUS      current
	    DESCRIPTION
	            "This object contains the IEEE 802.3 aggregated port
	            identifier, aAggPortID (IEEE 802.3-2002, 30.7.2.1.1),
	            derived from the ifNumber of the ifIndex for the port
	            component in link aggregation.
	
	            If the port is not in link aggregation state and/or it
	            does not support link aggregation, this value should be set
	            to zero."
	    REFERENCE 
	            "IEEE 802.1AB-2005 G.4.2"
	    ::= { lldpXdot3LocLinkAggEntry 2 }
	
	---
	---
	--- lldpXdot3LocMaxFrameSizeTable: Maximum Frame Size information 
	---
	---
	lldpXdot3LocMaxFrameSizeTable  OBJECT-TYPE
	    SYNTAX      SEQUENCE OF LldpXdot3LocMaxFrameSizeEntry
	    MAX-ACCESS  not-accessible
	    STATUS      current
	    DESCRIPTION
	            "This table contains one row per port of maximum frame 
	            size information (as a part of the LLDP 802.3 organizational
	            extension) on the local system known to this agent."
	    ::= { lldpXdot3LocalData 4 }
	
	lldpXdot3LocMaxFrameSizeEntry OBJECT-TYPE
	    SYNTAX      LldpXdot3LocMaxFrameSizeEntry
	    MAX-ACCESS  not-accessible
	    STATUS      current
	    DESCRIPTION
	            "Maximum Frame Size information about a particular port
	            component."
	    INDEX   { lldpXdot3LocMaxFrameSize }
	    ::= { lldpXdot3LocMaxFrameSizeTable 1 }
	
	LldpXdot3LocMaxFrameSizeEntry ::= SEQUENCE {
	              lldpXdot3LocMaxFrameSize   Integer32
	} 
	
	lldpXdot3LocMaxFrameSize OBJECT-TYPE
	    SYNTAX      Integer32(0..65535)
	    MAX-ACCESS  read-only
	    STATUS      current
	    DESCRIPTION
	            "An integer value indicating the maximum supported frame 
	             size in octets on the given port of the local system."
	    REFERENCE 
	            "IEEE 802.1AB-2005 G.5.1"
	    ::= { lldpXdot3LocMaxFrameSizeEntry 1 }
	
	
	------------------------------------------------------------------------------
	-- IEEE 802.3 - Remote Devices Information
	------------------------------------------------------------------------------
	---
	---
	--- lldpXdot3RemPortTable: Ethernet Information Table
	---
	---
	lldpXdot3RemPortTable OBJECT-TYPE
	    SYNTAX      SEQUENCE OF LldpXdot3RemPortEntry
	    MAX-ACCESS  not-accessible
	    STATUS      current
	    DESCRIPTION
	            "This table contains Ethernet port information (as a part
	            of the LLDP 802.3 organizational extension) of the remote
	            system."
	    ::= { lldpXdot3RemoteData 1 }
	
	lldpXdot3RemPortEntry OBJECT-TYPE
	    SYNTAX      LldpXdot3RemPortEntry
	    MAX-ACCESS  not-accessible
	    STATUS      current
	    DESCRIPTION
	            "Information about a particular physical network connection."
	    INDEX   { lldpXdot3RemPortAutoNegSupported }
	    ::= { lldpXdot3RemPortTable 1 }
	
	LldpXdot3RemPortEntry ::= SEQUENCE {
	              lldpXdot3RemPortAutoNegSupported     TruthValue,
	              lldpXdot3RemPortAutoNegEnabled       TruthValue,
	              lldpXdot3RemPortAutoNegAdvertisedCap OCTET STRING,
	              lldpXdot3RemPortOperMauType          Integer32
	} 
	
	lldpXdot3RemPortAutoNegSupported OBJECT-TYPE
	    SYNTAX      TruthValue
	    MAX-ACCESS  read-only
	    STATUS      current
	    DESCRIPTION
	            "The truth value used to indicate whether the given port
	            (associated with remote system) supports Auto-negotiation."
	    REFERENCE 
	            "IEEE 802.1AB-2005 G.2.1"
	    ::= { lldpXdot3RemPortEntry 1 }
	
	lldpXdot3RemPortAutoNegEnabled  OBJECT-TYPE
	    SYNTAX      TruthValue
	    MAX-ACCESS  read-only
	    STATUS      current
	    DESCRIPTION
	            "The truth value used to indicate whether port
	            Auto-negotiation is enabled on the given port associated
	            with the remote system."
	    REFERENCE 
	            "IEEE 802.1AB-2005 G.2.1"
	    ::= { lldpXdot3RemPortEntry 2 }
	
	lldpXdot3RemPortAutoNegAdvertisedCap  OBJECT-TYPE
	    SYNTAX      OCTET STRING(SIZE(2))
	    MAX-ACCESS  read-only
	    STATUS      current
	    DESCRIPTION
	            "This object contains the value (bitmap) of the
	            ifMauAutoNegCapAdvertisedBits object (defined in IETF RFC
	            3636) which is associated with the given port on the
	            remote system."
	    REFERENCE 
	            "IEEE 802.1AB-2005 G.2.2"
	    ::= { lldpXdot3RemPortEntry 3 }
	
	lldpXdot3RemPortOperMauType OBJECT-TYPE
	    SYNTAX 	    Integer32(0..2147483647)
	    MAX-ACCESS  read-only
	    STATUS      current
	    DESCRIPTION
	            "An integer value that indicates the operational MAU type
	            of the sending device.
	
	            This object contains the integer value derived from the
	            list position of the corresponding dot3MauType as listed in
	            in IETF RFC 3636 (or subsequent revisions) and is equal
	            to the last number in the respective dot3MauType OID.
	           
	            For example, if the ifMauType object is dot3MauType1000BaseTHD
	            which corresponds to {dot3MauType 29}, the numerical value of
	            this field will be 29. For MAU types not listed in RFC 3636
	            (or subsequent revisions), the value of this field shall be
	            set to zero."
	    REFERENCE 
	            "IEEE 802.1AB-2005 G.2.3"
	    ::= { lldpXdot3RemPortEntry 4 }
	
	---
	---
	--- lldpXdot3RemPowerTable: Power Ethernet Information Table
	---
	---
	lldpXdot3RemPowerTable OBJECT-TYPE
	    SYNTAX      SEQUENCE OF LldpXdot3RemPowerEntry
	    MAX-ACCESS  not-accessible
	    STATUS      current
	    DESCRIPTION
	            "This table contains Ethernet power information (as a part
	            of the LLDP 802.3 organizational extension) of the remote
	            system."
	    ::= { lldpXdot3RemoteData 2 }
	
	lldpXdot3RemPowerEntry OBJECT-TYPE
	    SYNTAX      LldpXdot3RemPowerEntry
	    MAX-ACCESS  not-accessible
	    STATUS      current
	    DESCRIPTION
	            "Information about a particular physical network connection."
	    INDEX   { lldpXdot3RemPowerPortClass}
	    ::= { lldpXdot3RemPowerTable 1 }
	
	LldpXdot3RemPowerEntry ::= SEQUENCE {
	              lldpXdot3RemPowerPortClass           LldpPowerPortClass,
	              lldpXdot3RemPowerMDISupported        TruthValue,
	              lldpXdot3RemPowerMDIEnabled          TruthValue,
	              lldpXdot3RemPowerPairControlable     TruthValue,
	              lldpXdot3RemPowerPairs               Integer32,
	              lldpXdot3RemPowerClass               Integer32
	} 
	
	lldpXdot3RemPowerPortClass  OBJECT-TYPE
	    SYNTAX      LldpPowerPortClass
	    MAX-ACCESS  read-only
	    STATUS      current
	    DESCRIPTION
	            "The value that identifies the port Class of the given port
	            associated with the remote system."
	    REFERENCE 
	            "IEEE 802.1AB-2005 G.3.1"
	    ::= { lldpXdot3RemPowerEntry 1 }
	
	lldpXdot3RemPowerMDISupported  OBJECT-TYPE
	    SYNTAX      TruthValue
	    MAX-ACCESS  read-only
	    STATUS      current
	    DESCRIPTION
	            "The truth value used to indicate whether the MDI power
	            is supported on the given port associated with the remote
	            system."
	    REFERENCE 
	            "IEEE 802.1AB-2005 G.3.1"
	    ::= { lldpXdot3RemPowerEntry 2 }
	
	lldpXdot3RemPowerMDIEnabled  OBJECT-TYPE
	    SYNTAX      TruthValue
	    MAX-ACCESS  read-only
	    STATUS      current
	    DESCRIPTION
	            "The truth value used to identify whether MDI power is
	            enabled on the given port associated with the remote system."
	    REFERENCE 
	            "IEEE 802.1AB-2005 G.3.1"
	    ::= { lldpXdot3RemPowerEntry 3 }
	
	lldpXdot3RemPowerPairControlable  OBJECT-TYPE
	    SYNTAX      TruthValue
	    MAX-ACCESS  read-only
	    STATUS      current
	    DESCRIPTION
	            "The truth value is derived from the value of
	            pethPsePortPowerPairsControlAbility object (defined in IETF
	            RFC 3621) and is used to indicate whether the pair selection
	            can be controlled on the given port associated with the
	            remote system."
	    REFERENCE 
	            "IEEE 802.1AB-2005 G.3.1"
	    ::= { lldpXdot3RemPowerEntry 4 }
	
	lldpXdot3RemPowerPairs  OBJECT-TYPE
	    SYNTAX      Integer32(1|2)
	    MAX-ACCESS  read-only
	    STATUS      current
	    DESCRIPTION
	            "This object contains the value of the pethPsePortPowerPairs
	            object (defined in IETF RFC 3621) which is associated with
	            the given port on the remote system."
	    REFERENCE 
	            "IEEE 802.1AB-2005 G.3.2"
	    ::= { lldpXdot3RemPowerEntry 5 }
	
	lldpXdot3RemPowerClass  OBJECT-TYPE
	    SYNTAX      Integer32(1|2|3|4|5)
	    MAX-ACCESS  read-only
	    STATUS      current
	    DESCRIPTION
	            "This object contains the value of the
	            pethPsePortPowerClassifications object (defined in IETF
	            RFC 3621) which is associated with the given port on the
	            remote system."
	    REFERENCE 
	            "IEEE 802.1AB-2005 G.3.3"
	    ::= { lldpXdot3RemPowerEntry 6 }
	
	---
	---
	--- lldpXdot3RemLinkAggTable: Link Aggregation Information Table
	---
	---
	lldpXdot3RemLinkAggTable OBJECT-TYPE
	    SYNTAX      SEQUENCE OF LldpXdot3RemLinkAggEntry
	    MAX-ACCESS  not-accessible
	    STATUS      current
	    DESCRIPTION
	            "This table contains port link aggregation information
	            (as a part of the LLDP 802.3 organizational extension)
	            of the remote system."
	    ::= { lldpXdot3RemoteData 3 }
	
	lldpXdot3RemLinkAggEntry OBJECT-TYPE
	    SYNTAX      LldpXdot3RemLinkAggEntry
	    MAX-ACCESS  not-accessible
	    STATUS      current
	    DESCRIPTION
	            "Link Aggregation information about remote system's port
	            component."
	    INDEX   { lldpXdot3RemLinkAggStatus }
	    ::= { lldpXdot3RemLinkAggTable 1 }
	
	LldpXdot3RemLinkAggEntry ::= SEQUENCE {
	              lldpXdot3RemLinkAggStatus       LldpLinkAggStatusMap,
	              lldpXdot3RemLinkAggPortId       Integer32
	} 
	
	lldpXdot3RemLinkAggStatus OBJECT-TYPE
	    SYNTAX      LldpLinkAggStatusMap
	    MAX-ACCESS  read-only
	    STATUS      current
	    DESCRIPTION
	            "The bitmap value contains the link aggregation capabilities
	            and the current aggregation status of the link."
	    REFERENCE 
	            "IEEE 802.1AB-2005 G.4.1"
	    ::= { lldpXdot3RemLinkAggEntry 1 }
	
	lldpXdot3RemLinkAggPortId OBJECT-TYPE
	    SYNTAX 	    Integer32(0|1..2147483647)
	    MAX-ACCESS  read-only
	    STATUS      current
	    DESCRIPTION
	            "This object contains the IEEE 802.3 aggregated port
	            identifier, aAggPortID (IEEE 802.3-2002, 30.7.2.1.1),
	            derived from the ifNumber of the ifIndex for the port
	            component associated with the remote system.
	
	            If the remote port is not in link aggregation state and/or
	            it does not support link aggregation, this value should be
	            zero."
	    REFERENCE 
	            "IEEE 802.1AB-2005 G.4.2"
	    ::= { lldpXdot3RemLinkAggEntry 2 }
	
	
	---
	---
	--- lldpXdot3RemMaxFrameSizeTable: Maximum Frame Size information 
	---
	---
	lldpXdot3RemMaxFrameSizeTable  OBJECT-TYPE
	    SYNTAX      SEQUENCE OF LldpXdot3RemMaxFrameSizeEntry
	    MAX-ACCESS  not-accessible
	    STATUS      current
	    DESCRIPTION
	            "This table contains one row per port of maximum frame 
	            size information (as a part of the LLDP 802.3 organizational
	            extension) of the remote system."
	    ::= { lldpXdot3RemoteData 4 }
	
	lldpXdot3RemMaxFrameSizeEntry OBJECT-TYPE
	    SYNTAX      LldpXdot3RemMaxFrameSizeEntry
	    MAX-ACCESS  not-accessible
	    STATUS      current
	    DESCRIPTION
	            "Maximum Frame Size information about a particular port
	            component."
	    INDEX   { lldpXdot3RemMaxFrameSize }
	    ::= { lldpXdot3RemMaxFrameSizeTable 1 }
	
	LldpXdot3RemMaxFrameSizeEntry ::= SEQUENCE {
	              lldpXdot3RemMaxFrameSize   Integer32
	} 
	
	lldpXdot3RemMaxFrameSize OBJECT-TYPE
	    SYNTAX      Integer32(0..65535)
	    MAX-ACCESS  read-only
	    STATUS      current
	    DESCRIPTION
	            "An integer value indicating the maximum supported frame 
	             size in octets on the port component associated with the 
	             remote system."
	    REFERENCE 
	            "IEEE 802.1AB-2005 G.5.1"
	    ::= { lldpXdot3RemMaxFrameSizeEntry 1 }

	
	--
	-- D-Link Defined LLDP Extension Dot1 MIB Objects
	--
	lldpXdot1Objects    OBJECT IDENTIFIER ::= { companyLLDPSetting 13 }

	-- LLDP IEEE 802.1 extension MIB groups
	lldpXdot1Config     OBJECT IDENTIFIER ::= { lldpXdot1Objects 1 }
	lldpXdot1LocalData  OBJECT IDENTIFIER ::= { lldpXdot1Objects 2 }
	lldpXdot1RemoteData OBJECT IDENTIFIER ::= { lldpXdot1Objects 3 }
	
	------------------------------------------------------------------------------
	-- IEEE 802.1 - Configuration
	------------------------------------------------------------------------------
	--
	-- lldpXdot1ConfigPortVlanTable : configure the transmission of the 
	--                                Port VLAN-ID TLVs on set of ports.
	--
	
	lldpXdot1ConfigPortVlanTable OBJECT-TYPE
	    SYNTAX      SEQUENCE OF LldpXdot1ConfigPortVlanEntry
	    MAX-ACCESS  not-accessible
	    STATUS      current
	    DESCRIPTION
	            "A table that controls selection of LLDP Port VLAN-ID TLVs
	            to be transmitted on individual ports."
	    ::= { lldpXdot1Config 1 }
	
	lldpXdot1ConfigPortVlanEntry  OBJECT-TYPE
	    SYNTAX      LldpXdot1ConfigPortVlanEntry
	    MAX-ACCESS  not-accessible
	    STATUS      current
	    DESCRIPTION
	            "LLDP configuration information that controls the
	            transmission of IEEE 802.1 organizationally defined Port
	            VLAN-ID TLV on LLDP transmission capable ports.
	
	            This configuration object augments the lldpPortConfigEntry of
	            the LLDP-MIB, therefore it is only present along with the port
	            configuration defined by the associated lldpPortConfigEntry
	            entry.
	
	            Each active lldpConfigEntry must be restored from non-volatile
	            storage (along with the corresponding lldpPortConfigEntry)
	            after a re-initialization of the management system."
	    AUGMENTS { lldpPortConfigEntry }
	    ::= { lldpXdot1ConfigPortVlanTable 1 }
	
	LldpXdot1ConfigPortVlanEntry ::= SEQUENCE {
	      lldpXdot1ConfigPortVlanTxEnable  TruthValue
	}
	
	lldpXdot1ConfigPortVlanTxEnable OBJECT-TYPE
	    SYNTAX      TruthValue
	    MAX-ACCESS  read-write
	    STATUS      current
	    DESCRIPTION
	            "The lldpXdot1ConfigPortVlanTxEnable, which is defined as
	            a truth value and configured by the network management,
	            determines whether the IEEE 802.1 organizationally defined
	            port VLAN TLV transmission is allowed on a given LLDP
	            transmission capable port.
	
	            The value of this object must be restored from non-volatile
	            storage after a re-initialization of the management system."
	    REFERENCE 
	            "IEEE 802.1AB-2005 10.2.1.1"
	    DEFVAL  { false }
	    ::= { lldpXdot1ConfigPortVlanEntry 1 }
	
	--
	-- lldpXdot1LocVlanNameTable : VLAN name information about the local system
	--
	
	lldpXdot1LocVlanNameTable  OBJECT-TYPE
	    SYNTAX      SEQUENCE OF LldpXdot1LocVlanNameEntry
	    MAX-ACCESS  not-accessible
	    STATUS      current
	    DESCRIPTION
	            "This table contains one or more rows per IEEE 802.1Q VLAN
	            name information on the local system known to this agent."
	    ::= { lldpXdot1LocalData 3 }
	
	lldpXdot1LocVlanNameEntry OBJECT-TYPE
	    SYNTAX      LldpXdot1LocVlanNameEntry 
	    MAX-ACCESS  not-accessible
	    STATUS      current
	    DESCRIPTION
	            "VLAN name Information about a particular port component.
	            There may be multiple VLANs, identified by a particular
	            lldpXdot1LocVlanId, configured on the given port."
	    INDEX   { lldpXdot1LocVlanId }
	    ::= { lldpXdot1LocVlanNameTable 1 }
	
	LldpXdot1LocVlanNameEntry ::= SEQUENCE {
	      lldpXdot1LocVlanId     VlanId,
	      lldpXdot1LocVlanName   SnmpAdminString
	}
	
	lldpXdot1LocVlanId  OBJECT-TYPE
	    SYNTAX      VlanId
	    MAX-ACCESS  not-accessible
	    STATUS      current
	    DESCRIPTION
	            "The integer value used to identify the IEEE 802.1Q 
	            VLAN IDs with which the given port is compatible."
	    REFERENCE 
	            "IEEE 802.1AB-2005 F.4.2"
	    ::= { lldpXdot1LocVlanNameEntry 1 }
	
	lldpXdot1LocVlanName  OBJECT-TYPE
	    SYNTAX      SnmpAdminString (SIZE(1..32))
	    MAX-ACCESS  read-only
	    STATUS      current
	    DESCRIPTION
	            "The string value used to identify VLAN name identified by the
	            Vlan Id associated with the given port on the local system.
	
	            This object should contain the value of the dot1QVLANStaticName
	            object (defined in IETF RFC 2674) identified with the given
	            lldpXdot1LocVlanId."
	    REFERENCE 
	            "IEEE 802.1AB-2005 F.4.4"
	    ::= { lldpXdot1LocVlanNameEntry 2 }
	
	--
	-- lldpXdot1ConfigVlanNameTable : configure the transmission of the 
	--                                VLAN name instances on set of ports.
	--
	
	lldpXdot1ConfigVlanNameTable OBJECT-TYPE
	    SYNTAX      SEQUENCE OF LldpXdot1ConfigVlanNameEntry
	    MAX-ACCESS  not-accessible
	    STATUS      current
	    DESCRIPTION
	            "The table that controls selection of LLDP VLAN name TLV
	            instances to be transmitted on individual ports."
	    ::= { lldpXdot1Config 2 }
	
	lldpXdot1ConfigVlanNameEntry  OBJECT-TYPE
	    SYNTAX      LldpXdot1ConfigVlanNameEntry
	    MAX-ACCESS  not-accessible
	    STATUS      current
	    DESCRIPTION
	            "LLDP configuration information that specifies the set of
	            ports (represented as a PortList) on which the Local System
	            VLAN name instance will be transmitted.
	
	            This configuration object augments the lldpLocVlanEntry,
	            therefore it is only present along with the VLAN Name instance
	            contained in the associated lldpLocVlanNameEntry entry.
	
	            Each active lldpXdot1ConfigVlanNameEntry must be restored
	            from non-volatile storage (along with the corresponding
	            lldpXdot1LocVlanNameEntry) after a re-initialization of the
	            management system."
	    AUGMENTS { lldpXdot1LocVlanNameEntry }
	    ::= { lldpXdot1ConfigVlanNameTable 1 }
	
	LldpXdot1ConfigVlanNameEntry ::= SEQUENCE {
	      lldpXdot1ConfigVlanNameTxEnable  TruthValue 
	}
	
	lldpXdot1ConfigVlanNameTxEnable  OBJECT-TYPE
	    SYNTAX        TruthValue
	    MAX-ACCESS    read-write
	    STATUS        current
	    DESCRIPTION
	            "The boolean value that indicates whether the corresponding
	            Local System VLAN name instance will be transmitted on the
	            port defined by the given lldpXdot1LocVlanNameEntry.
	
	            The value of this object must be restored from non-volatile
	            storage after a re-initialization of the management system."
	    REFERENCE 
	            "IEEE 802.1AB-2005 10.2.1.1"
	    DEFVAL  { false }
	    ::= { lldpXdot1ConfigVlanNameEntry 1 }
	
	--
	-- lldpXdot1LocProtoVlanTable: Port and Protocol VLAN information 
	--
	
	lldpXdot1LocProtoVlanTable  OBJECT-TYPE
	    SYNTAX      SEQUENCE OF LldpXdot1LocProtoVlanEntry
	    MAX-ACCESS  not-accessible
	    STATUS      current
	    DESCRIPTION
	            "This table contains one or more rows per Port and Protocol
	            VLAN information about the local system."
	    ::= { lldpXdot1LocalData 2 }
	
	lldpXdot1LocProtoVlanEntry OBJECT-TYPE
	    SYNTAX      LldpXdot1LocProtoVlanEntry 
	    MAX-ACCESS  not-accessible
	    STATUS      current
	    DESCRIPTION
	            "Port and protocol VLAN ID Information about a particular
	            port component.  There may be multiple port and protocol VLANs,
	            identified by a particular lldpXdot1LocProtoVlanId, configured
	            on the given port."
	    INDEX   { lldpXdot1LocProtoVlanId }
	    ::= { lldpXdot1LocProtoVlanTable 1 }
	
	LldpXdot1LocProtoVlanEntry ::= SEQUENCE {
	      lldpXdot1LocProtoVlanId        Integer32,
	      lldpXdot1LocProtoVlanSupported TruthValue,
	      lldpXdot1LocProtoVlanEnabled   TruthValue
	}
	
	lldpXdot1LocProtoVlanId  OBJECT-TYPE
	    SYNTAX      Integer32(0|1..4094)
	    MAX-ACCESS  not-accessible
	    STATUS      current
	    DESCRIPTION
	            "The integer value used to identify the port and protocol
	            VLANs associated with the given port associated with the
	            local system.  A value of zero shall be used if the system
	            either does not know the protocol VLAN ID (PPVID) or does
	            not support port and protocol VLAN operation."
	    REFERENCE 
	            "IEEE 802.1AB-2005 F.3.2"
	    ::= { lldpXdot1LocProtoVlanEntry 1 }
	
	lldpXdot1LocProtoVlanSupported  OBJECT-TYPE
	    SYNTAX      TruthValue
	    MAX-ACCESS  read-only
	    STATUS      current
	    DESCRIPTION
	            "The truth value used to indicate whether the given port
	            (associated with the local system) supports port and protocol
	            VLANs."
	    REFERENCE 
	            "IEEE 802.1AB-2005 F.3.1"
	    ::= { lldpXdot1LocProtoVlanEntry 2 }
	
	lldpXdot1LocProtoVlanEnabled  OBJECT-TYPE
	    SYNTAX      TruthValue
	    MAX-ACCESS  read-only
	    STATUS      current
	    DESCRIPTION
	            "The truth value used to indicate whether the port and
	            protocol VLANs are enabled on the given port associated with
	            the local system."
	    REFERENCE 
	            "IEEE 802.1AB-2005 F.3.1"
	    ::= { lldpXdot1LocProtoVlanEntry 3 }
	
	--
	-- lldpXdot1ConfigProtoVlanTable : configure the transmission of the 
	--                                 protocol VLAN instances on set
	--                                 of ports.
	--
	
	lldpXdot1ConfigProtoVlanTable OBJECT-TYPE
	    SYNTAX      SEQUENCE OF LldpXdot1ConfigProtoVlanEntry
	    MAX-ACCESS  not-accessible
	    STATUS      current
	    DESCRIPTION
	            "The table that controls selection of LLDP Port and Protocol
	            VLAN ID TLV instances to be transmitted on individual ports."
	    ::= { lldpXdot1Config 3 }
	
	lldpXdot1ConfigProtoVlanEntry  OBJECT-TYPE
	    SYNTAX      LldpXdot1ConfigProtoVlanEntry
	    MAX-ACCESS  not-accessible
	    STATUS      current
	    DESCRIPTION
	            "LLDP configuration information that specifies the set of
	            ports (represented as a PortList) on which the Local System
	            Protocol VLAN instance will be transmitted.
	
	            This configuration object augments the lldpXdot1LocVlanEntry,
	            therefore it is only present along with the Port and
	            Protocol VLAN ID instance contained in the associated
	            lldpXdot1LocVlanEntry entry.
	
	            Each active lldpXdot1ConfigProtoVlanEntry must be restored
	            from non-volatile storage (along with the corresponding
	            lldpXdot1LocProtoVlanEntry) after a re-initialization of
	            the management system."
	
	    AUGMENTS { lldpXdot1LocProtoVlanEntry }
	    ::= { lldpXdot1ConfigProtoVlanTable 1 }
	
	LldpXdot1ConfigProtoVlanEntry ::= SEQUENCE {
	      lldpXdot1ConfigProtoVlanTxEnable   TruthValue
	}
	
	lldpXdot1ConfigProtoVlanTxEnable OBJECT-TYPE
	    SYNTAX        TruthValue
	    MAX-ACCESS    read-write
	    STATUS        current
	    DESCRIPTION
	            "The boolean value that indicates whether the corresponding
	            Local System Port and Protocol VLAN instance will
	            be transmitted on the port defined by the given
	            lldpXdot1LocProtoVlanEntry.
	
	            The value of this object must be restored from non-volatile
	            storage after a re-initialization of the management system."
	    REFERENCE 
	            "IEEE 802.1AB-2005 10.2.1.1"
	    DEFVAL  { false }
	    ::= { lldpXdot1ConfigProtoVlanEntry 1 }
	
	--
	-- lldpXdot1LocProtocolTable : Protocol Identity information 
	--
	
	lldpXdot1LocProtocolTable  OBJECT-TYPE
	    SYNTAX      SEQUENCE OF LldpXdot1LocProtocolEntry
	    MAX-ACCESS  not-accessible
	    STATUS      current
	    DESCRIPTION
	            "This table contains one or more rows per protocol identity
	            information on the local system known to this agent."
	    REFERENCE 
	            "IEEE 802.1AB-2005 F.5"
	    ::= { lldpXdot1LocalData 4 }
	
	lldpXdot1LocProtocolEntry  OBJECT-TYPE
	    SYNTAX      LldpXdot1LocProtocolEntry
	    MAX-ACCESS  not-accessible
	    STATUS      current
	    DESCRIPTION
	            "Information about particular protocols that are accessible
	            through the given port component.
	
	            There may be multiple protocols, identified by particular
	            lldpXdot1ProtocolIndex, and lldpLocPortNum."
	    REFERENCE 
	            "IEEE 802.1AB-2005 F.5"
	    INDEX   { lldpXdot1LocProtocolIndex }
	    ::= { lldpXdot1LocProtocolTable 1 }
	
	LldpXdot1LocProtocolEntry ::= SEQUENCE {
	      lldpXdot1LocProtocolIndex Integer32,
	      lldpXdot1LocProtocolId    OCTET STRING
	}
	
	lldpXdot1LocProtocolIndex  OBJECT-TYPE
	    SYNTAX      Integer32(1..2147483647)
	    MAX-ACCESS  not-accessible
	    STATUS      current
	    DESCRIPTION
	            "This object represents an arbitrary local integer value used
	            by this agent to identify a particular protocol identity."
	    ::= { lldpXdot1LocProtocolEntry 1 }
	
	lldpXdot1LocProtocolId  OBJECT-TYPE
	    SYNTAX      OCTET STRING (SIZE (1..255))
	    MAX-ACCESS  read-only
	    STATUS      current
	    DESCRIPTION
	            "The octet string value used to identify the protocols
	            associated with the given port of the local system."
	    REFERENCE 
	            "IEEE 802.1AB-2005 F.5.3"
	    ::= { lldpXdot1LocProtocolEntry 2 }
	
	--
	-- lldpXdot1ConfigProtocolTable : configure the transmission of the 
	--                                protocol instances on set
	--                                of ports.
	--
	
	lldpXdot1ConfigProtocolTable OBJECT-TYPE
	    SYNTAX      SEQUENCE OF LldpXdot1ConfigProtocolEntry
	    MAX-ACCESS  not-accessible
	    STATUS      current
	    DESCRIPTION
	            "The table that controls selection of LLDP Protocol 
	            TLV instances to be transmitted on individual ports."
	    ::= { lldpXdot1Config 4 }
	
	lldpXdot1ConfigProtocolEntry  OBJECT-TYPE
	    SYNTAX      LldpXdot1ConfigProtocolEntry
	    MAX-ACCESS  not-accessible
	    STATUS      current
	    DESCRIPTION
	            "LLDP configuration information that specifies the set of
	            ports (represented as a PortList) on which the Local System
	            Protocol instance will be transmitted.
	
	            This configuration object augments the lldpXdot1LocProtoEntry,
	            therefore it is only present along with the Protocol instance
	            contained in the associated lldpXdot1LocProtoEntry entry.
	
	            Each active lldpXdot1ConfigProtocolEntry must be restored
	            from non-volatile storage (along with the corresponding
	            lldpXdot1LocProtocolEntry) after a re-initialization of the
	            management system."
	    AUGMENTS { lldpXdot1LocProtocolEntry }
	    ::= { lldpXdot1ConfigProtocolTable 1 }
	
	LldpXdot1ConfigProtocolEntry ::= SEQUENCE {
	      lldpXdot1ConfigProtocolTxEnable   TruthValue
	}
	
	lldpXdot1ConfigProtocolTxEnable  OBJECT-TYPE
	    SYNTAX        TruthValue
	    MAX-ACCESS    read-write
	    STATUS        current
	    DESCRIPTION
	            "The boolean value that indicates whether the corresponding
	            Local System Protocol Identity instance will be transmitted
	            on the port defined by the given lldpXdot1LocProtocolEntry.
	
	            The value of this object must be restored from non-volatile
	            storage after a re-initialization of the management system."
	    REFERENCE 
	            "IEEE 802.1AB-2005 10.2.1.1"
	    DEFVAL  { false }
	    ::= { lldpXdot1ConfigProtocolEntry 1 }
	
	------------------------------------------------------------------------------
	-- IEEE 802.1 - Local System Information
	------------------------------------------------------------------------------
	lldpXdot1LocTable  OBJECT-TYPE
	    SYNTAX      SEQUENCE OF LldpXdot1LocEntry
	    MAX-ACCESS  not-accessible
	    STATUS      current
	    DESCRIPTION
	            "This table contains one row per port for IEEE 802.1
	            organizationally defined LLDP extension on the local system
	            known to this agent."
	    ::= { lldpXdot1LocalData 1 }
	
	lldpXdot1LocEntry  OBJECT-TYPE
	    SYNTAX      LldpXdot1LocEntry
	    MAX-ACCESS  not-accessible
	    STATUS      current
	    DESCRIPTION
	            "Information about IEEE 802.1 organizationally defined
	            LLDP extension."
	    INDEX   { lldpXdot1LocPortVlanId }
	    ::= { lldpXdot1LocTable 1 }
	
	LldpXdot1LocEntry ::= SEQUENCE {
	              lldpXdot1LocPortVlanId         Integer32
	} 
	
	lldpXdot1LocPortVlanId OBJECT-TYPE
	    SYNTAX      Integer32(0|1..4094)
	    MAX-ACCESS  read-only
	    STATUS      current
	    DESCRIPTION
	            "The integer value used to identify the port's VLAN identifier
	            associated with the local system.   A value of zero shall
	            be used if the system either does not know the PVID or does
	            not support port-based VLAN operation."
	    REFERENCE 
	            "IEEE 802.1AB-2005 F.2.1"
	    ::= { lldpXdot1LocEntry 1 }
	
	------------------------------------------------------------------------------
	-- IEEE 802.1 - Remote System Information
	------------------------------------------------------------------------------
	lldpXdot1RemTable OBJECT-TYPE
	    SYNTAX      SEQUENCE OF LldpXdot1RemEntry
	    MAX-ACCESS  not-accessible
	    STATUS      current
	    DESCRIPTION
	            "This table contains one or more rows per physical network
	            connection known to this agent.  The agent may wish to
	            ensure that only one lldpXdot1RemEntry is present for
	            each local port, or it may choose to maintain multiple
	            lldpXdot1RemEntries for the same local port."
	    ::= { lldpXdot1RemoteData 1 }
	
	lldpXdot1RemEntry OBJECT-TYPE
	    SYNTAX      LldpXdot1RemEntry 
	    MAX-ACCESS  not-accessible
	    STATUS      current
	    DESCRIPTION
	            "Information about a particular port component."
	    INDEX   { lldpXdot1RemPortVlanId }
	    ::= { lldpXdot1RemTable 1 }
	
	LldpXdot1RemEntry ::= SEQUENCE {
	              lldpXdot1RemPortVlanId         Integer32
	}
	
	lldpXdot1RemPortVlanId OBJECT-TYPE
	    SYNTAX      Integer32(0|1..4094)
	    MAX-ACCESS  read-only
	    STATUS      current
	    DESCRIPTION
	            "The integer value used to identify the port's VLAN identifier
	            associated with the remote system.  if the remote system
	            either does not know the PVID or does not support port-based
	            VLAN operation, the value of lldpXdot1RemPortVlanId should
	            be zero."
	    REFERENCE 
	            "IEEE 802.1AB-2005 F.2.1"
	    ::= { lldpXdot1RemEntry 1 }
	
	lldpXdot1RemProtoVlanTable  OBJECT-TYPE
	    SYNTAX      SEQUENCE OF LldpXdot1RemProtoVlanEntry
	    MAX-ACCESS  not-accessible
	    STATUS      current
	    DESCRIPTION
	            "This table contains one or more rows per Port and Protocol
	            VLAN information about the remote system, received on the
	            given port."
	    ::= { lldpXdot1RemoteData 2 }
	
	lldpXdot1RemProtoVlanEntry OBJECT-TYPE
	    SYNTAX      LldpXdot1RemProtoVlanEntry 
	    MAX-ACCESS  not-accessible
	    STATUS      current
	    DESCRIPTION
	            "Port and protocol VLAN name Information about a particular
	            port component.  There may be multiple protocol VLANs,
	            identified by a particular lldpXdot1RemProtoVlanId, configured
	            on the remote system."
	    INDEX   { lldpXdot1RemProtoVlanId }
	    ::= { lldpXdot1RemProtoVlanTable 1 }
	
	LldpXdot1RemProtoVlanEntry ::= SEQUENCE {
	      lldpXdot1RemProtoVlanId        Integer32,
	      lldpXdot1RemProtoVlanSupported TruthValue,
	      lldpXdot1RemProtoVlanEnabled   TruthValue
	}
	
	lldpXdot1RemProtoVlanId  OBJECT-TYPE
	    SYNTAX      Integer32(0|1..4094)
	    MAX-ACCESS  not-accessible
	    STATUS      current
	    DESCRIPTION
	            "The integer value used to identify the port and protocol
	            VLANs associated with the given port associated with the
	            remote system.
	
	            If port and protocol VLANs are not supported on the given
	            port associated with the remote system, or if the port is
	            not enabled with any port and protocol VLAN, the value of
	            lldpXdot1RemProtoVlanId should be zero."
	    REFERENCE 
	            "IEEE 802.1AB-2005 F.3.2"
	    ::= { lldpXdot1RemProtoVlanEntry 1 }
	
	lldpXdot1RemProtoVlanSupported  OBJECT-TYPE
	    SYNTAX      TruthValue
	    MAX-ACCESS  read-only
	    STATUS      current
	    DESCRIPTION
	            "The truth value used to indicate whether the given port
	            (associated with the remote system) is capable of supporting
	            port and protocol VLANs."
	    REFERENCE 
	            "IEEE 802.1AB-2005 F.3.1"
	    ::= { lldpXdot1RemProtoVlanEntry 2 }
	
	lldpXdot1RemProtoVlanEnabled  OBJECT-TYPE
	    SYNTAX      TruthValue
	    MAX-ACCESS  read-only
	    STATUS      current
	    DESCRIPTION
	            "The truth value used to indicate whether the port and
	            protocol VLANs are enabled on the given port associated with
	            the remote system."
	    REFERENCE 
	            "IEEE 802.1AB-2005 F.3.1"
	    ::= { lldpXdot1RemProtoVlanEntry 3 }
	
	
	-- 
	-- lldpXdot1RemVlanNameTable : VLAN name information of the remote 
	--                             systems
	--
	
	lldpXdot1RemVlanNameTable  OBJECT-TYPE
	    SYNTAX      SEQUENCE OF LldpXdot1RemVlanNameEntry
	    MAX-ACCESS  not-accessible
	    STATUS      current
	    DESCRIPTION
	            "This table contains one or more rows per IEEE 802.1Q VLAN
	            name information about the remote system, received on the
	            given port."
	    REFERENCE 
	            "IEEE 802.1AB-2005 F.4"
	    ::= { lldpXdot1RemoteData 3 }
	
	lldpXdot1RemVlanNameEntry OBJECT-TYPE
	    SYNTAX      LldpXdot1RemVlanNameEntry 
	    MAX-ACCESS  not-accessible
	    STATUS      current
	    DESCRIPTION
	            "VLAN name Information about a particular port component.
	            There may be multiple VLANs, identified by a particular
	            lldpXdot1RemVlanId, received on the given port."
	    INDEX   { lldpXdot1RemVlanId }
	    ::= { lldpXdot1RemVlanNameTable 1 }
	
	LldpXdot1RemVlanNameEntry ::= SEQUENCE {
	      lldpXdot1RemVlanId     VlanId,
	      lldpXdot1RemVlanName   SnmpAdminString
	}
	
	lldpXdot1RemVlanId  OBJECT-TYPE
	    SYNTAX      VlanId
	    MAX-ACCESS  not-accessible
	    STATUS      current
	    DESCRIPTION
	            "The integer value used to identify the IEEE 802.1Q 
	            VLAN IDs with which the given port of the remote system
	            is compatible."
	    REFERENCE 
	            "IEEE 802.1AB-2005 F.4.2"
	    ::= { lldpXdot1RemVlanNameEntry 1 }
	
	lldpXdot1RemVlanName  OBJECT-TYPE
	    SYNTAX      SnmpAdminString (SIZE(1..32))
	    MAX-ACCESS  read-only
	    STATUS      current
	    DESCRIPTION
	            "The string value used to identify VLAN name identified by the 
	            VLAN Id associated with the remote system."
	    REFERENCE 
	            "IEEE 802.1AB-2005 F.4.4"
	    ::= { lldpXdot1RemVlanNameEntry 2 }
	
	--
	-- lldpXdot1RemProtocolTable : Protocol information of the remote systems
	--
	
	lldpXdot1RemProtocolTable  OBJECT-TYPE
	    SYNTAX      SEQUENCE OF LldpXdot1RemProtocolEntry
	    MAX-ACCESS  not-accessible
	    STATUS      current
	    DESCRIPTION
	            "This table contains one or more rows per protocol information
	            about the remote system, received on the given port."
	    ::= { lldpXdot1RemoteData 4 }
	
	lldpXdot1RemProtocolEntry  OBJECT-TYPE
	    SYNTAX      LldpXdot1RemProtocolEntry
	    MAX-ACCESS  not-accessible
	    STATUS      current
	    DESCRIPTION
	            "Protocol information about a particular port component.
	            There may be multiple protocols, identified by a particular
	            lldpXdot1ProtocolIndex, received on the given port."
	    INDEX   { lldpXdot1RemProtocolIndex }
	    ::= { lldpXdot1RemProtocolTable 1 }
	
	LldpXdot1RemProtocolEntry ::= SEQUENCE {
	      lldpXdot1RemProtocolIndex Integer32,
	      lldpXdot1RemProtocolId    OCTET STRING
	}
	
	lldpXdot1RemProtocolIndex  OBJECT-TYPE
	    SYNTAX      Integer32(1..2147483647)
	    MAX-ACCESS  not-accessible
	    STATUS      current
	    DESCRIPTION
	            "This object represents an arbitrary local integer value used
	            by this agent to identify a particular protocol identity."
	    ::= { lldpXdot1RemProtocolEntry 1 }
	
	lldpXdot1RemProtocolId  OBJECT-TYPE
	    SYNTAX      OCTET STRING (SIZE (1..255))
	    MAX-ACCESS  read-only
	    STATUS      current
	    DESCRIPTION
	            "The octet string value used to identify the protocols
	            associated with the given port of remote system."
	    REFERENCE 
	            "IEEE 802.1AB-2005 F.5.3"
	    ::= { lldpXdot1RemProtocolEntry 2 }

    -- ---------------------------------------------------------------------
    -- Green Function
    -- ---------------------------------------------------------------------

      dlinkGreenLEDShutoff              OBJECT IDENTIFIER ::= { companyGreenSetting 1 }
      dlinkGreenPortShutoff             OBJECT IDENTIFIER ::= { companyGreenSetting 2 }
      dlinkGreenSystemHibernation       OBJECT IDENTIFIER ::= { companyGreenSetting 4 }

    -- ---------------------------------------------------------------------
    -- Green Disable LED
    -- ---------------------------------------------------------------------

    dlinkGreenLEDShutoffPortList    OBJECT-TYPE
        SYNTAX      PortList
        MAX-ACCESS  read-write
        STATUS      current
        DESCRIPTION
            "Provides control to disable LED port."
    ::= { dlinkGreenLEDShutoff 1 }

	dlinkGreenLEDShutoffState       OBJECT-TYPE
        SYNTAX      INTEGER {
                    disabled        (0),
                    enabled         (1)
        }
        MAX-ACCESS  read-write
        STATUS      current
        DESCRIPTION
            "Enable/Disable Green disable LED function.
            Default is disabled."

    DEFVAL  { disabled }
    ::= { dlinkGreenLEDShutoff 2 }
    
    dlinkGreenLEDShutoffTimeProfile1 OBJECT-TYPE
        SYNTAX      DisplayString (SIZE(1..20))
        MAX-ACCESS  read-write
        STATUS      current
        DESCRIPTION
            "The time profile name associated with the Schedule entry (e.g., `abc, bbb')."
    ::= { dlinkGreenLEDShutoff 3}

    dlinkGreenLEDShutoffTimeProfile2 OBJECT-TYPE
        SYNTAX      DisplayString (SIZE(1..20))
        MAX-ACCESS  read-write
        STATUS      current
        DESCRIPTION
            "The time profile name associated with the Schedule entry (e.g., `abc, bbb')."
    ::= { dlinkGreenLEDShutoff 4}
    -- ---------------------------------------------------------------------
    -- Green Disable Port
    -- ---------------------------------------------------------------------

    dlinkGreenPortShutoffPortList    OBJECT-TYPE
    SYNTAX      PortList
    MAX-ACCESS  read-write
    STATUS      current
    DESCRIPTION
        "Provides control to disable LED port."
    ::= { dlinkGreenPortShutoff 1 }

	dlinkGreenPortShutoffState       OBJECT-TYPE
        SYNTAX      INTEGER {
                    disabled        (0),
                    enabled         (1)
        }
        MAX-ACCESS  read-write
        STATUS      current
        DESCRIPTION
            "Enable/Disable Green disable LED function.
            Default is disabled."

    DEFVAL  { disabled }
    ::= { dlinkGreenPortShutoff 2 }
    
    dlinkGreenPortShutoffTimeProfile1 OBJECT-TYPE
        SYNTAX      DisplayString (SIZE(1..20))
        MAX-ACCESS  read-write
        STATUS      current
        DESCRIPTION
            "The time profile name associated with the Schedule entry (e.g., `abc, bbb')."
    ::= { dlinkGreenPortShutoff 3}
    
    dlinkGreenPortShutoffTimeProfile2 OBJECT-TYPE
        SYNTAX      DisplayString (SIZE(1..20))
        MAX-ACCESS  read-write
        STATUS      current
        DESCRIPTION
            "The time profile name associated with the Schedule entry (e.g., `abc, bbb')."
    ::= { dlinkGreenPortShutoff 4}

    
    -- ---------------------------------------------------------------------
    -- Green System Hibernation mode
    -- ---------------------------------------------------------------------

   dlinkGreenSystemHibernationState       OBJECT-TYPE
        SYNTAX      INTEGER {
                    disabled        (0),
                    enabled         (1)
        }
        MAX-ACCESS  read-write
        STATUS      current
        DESCRIPTION
            "Enable/Disable Green disable LED function.
            Default is disabled."

    DEFVAL  { disabled }
    ::= { dlinkGreenSystemHibernation 1 }
    
    dlinkGreenSystemHibernationTimeProfile1 OBJECT-TYPE
        SYNTAX      DisplayString (SIZE(1..20))
        MAX-ACCESS  read-write
        STATUS      current
        DESCRIPTION
            "The time profile name associated with the Schedule entry (e.g., `abc, bbb')."
    ::= { dlinkGreenSystemHibernation 2}

    dlinkGreenSystemHibernationTimeProfile2 OBJECT-TYPE
        SYNTAX      DisplayString (SIZE(1..20))
        MAX-ACCESS  read-write
        STATUS      current
        DESCRIPTION
            "The time profile name associated with the Schedule entry (e.g., `abc, bbb')."
    ::= { dlinkGreenSystemHibernation 3}
	
    dlinkPowerSavCableLenDetectionState       OBJECT-TYPE
        SYNTAX      INTEGER {
                    enabled         (1),
                    disabled        (2)
        }
        MAX-ACCESS  read-write
        STATUS      current
        DESCRIPTION
            "Enable/Disable Power Saving Cable Length Detection.
            Default is disabled."

    DEFVAL  { disabled }
    ::= { companyGreenSetting 5 }
    dlinkPowerSavLinkStatusDetectState      OBJECT-TYPE
        SYNTAX      INTEGER {
                    enabled         (1),
                    disabled        (2)
        }
        MAX-ACCESS  read-write
        STATUS      current
        DESCRIPTION
            "Enable/Disable Power Saving Link Status Detection.
            Default is disabled."

    DEFVAL  { disabled }
    ::= { companyGreenSetting 6 }
 -- ----------------------------------------------------------
 -- The companySecurity Groups
 -- ----------------------------------------------------------
    securityDhcpServerScreen                  OBJECT IDENTIFIER ::= { companySecurity 7 }
 -- dhcp Server Screen Group --------------------------------------------- --

    dhcpServerScreenEnablePortlist OBJECT-TYPE
       SYNTAX      PortList
       MAX-ACCESS  read-write
       STATUS      current
       DESCRIPTION
           "To enable or disable DHCP Server Screening port list."
       ::= { securityDhcpServerScreen 1 }

    dhcpServerScreenEnableVlanlist OBJECT-TYPE
       SYNTAX      OCTET STRING
       MAX-ACCESS  read-write
       STATUS      current
       DESCRIPTION
           "To enable or disable DHCP Server Screening vlan list."
       ::= { securityDhcpServerScreen 2 }
       
       
	dhcpServerScreenLogSuppressDuration OBJECT-TYPE 
           SYNTAX      INTEGER {
                          one-min (1),
                          five-min  (5),
                          thirty-min  (30)
                       }
           MAX-ACCESS  read-write 
           STATUS      current 
           DESCRIPTION 
               "DSS Trap Log Suppress Duration."
                 
           ::= { securityDhcpServerScreen 3 }

       
	-- filterDHCPServer Table

	filterDHCPServerTable OBJECT-TYPE
	   SYNTAX      SEQUENCE OF FilterDHCPServerEntry
	   MAX-ACCESS  not-accessible
	   STATUS      current
	   DESCRIPTION
	      "A table to control filter DHCP Server for the entire
	       switch or for each interface in the switch."
	   ::= { securityDhcpServerScreen 4 }

	filterDHCPServerEntry OBJECT-TYPE
	   SYNTAX      FilterDHCPServerEntry
	   MAX-ACCESS  not-accessible
	   STATUS      current
	   DESCRIPTION
	       "An entry appears in this table for each interface
	        in the system."
	   INDEX { filterDHCPServerIpAddr, filterDHCPServerClientMacAddr }
	   ::= { filterDHCPServerTable 1 }

	FilterDHCPServerEntry ::=
	   SEQUENCE {
	      filterDHCPServerIpAddr
	         IpAddress,
	      filterDHCPServerClientMacAddr
	         MacAddress,
	      filterDHCPServerPortList
	         PortList,
	      filterDHCPServerVlanList
	         OCTET STRING,
	      filterDHCPServerRowStatus
	         RowStatus
	   }


	filterDHCPServerIpAddr OBJECT-TYPE
	   SYNTAX      IpAddress
	   MAX-ACCESS  not-accessible
	   STATUS      current
	   DESCRIPTION
	       "Specifies either the Network or Host address from which the switch
	        can be managed.
	        An address 0.0.0.0 indicates 'Any Manager'."
	   ::= { filterDHCPServerEntry 1 }


	filterDHCPServerClientMacAddr OBJECT-TYPE
	   SYNTAX      MacAddress
	   MAX-ACCESS  not-accessible
	   STATUS      current
	   DESCRIPTION
	      "Ethernet Mac Address."

	   DEFVAL  { '000102030405'h }
	   ::= { filterDHCPServerEntry 2 }

	filterDHCPServerPortList OBJECT-TYPE
	   SYNTAX       PortList
	   MAX-ACCESS   read-write
	   STATUS       current
	   DESCRIPTION
	       "Specifies the port numbers through which the authorized manager can
	        access the switch.

	        By default the authorized manager is allowed to access the switch
	        through all the ports.

	        If a set of ports are configured in the 'PortList', the manager can
	        access the switch only through the configured ports."
	   ::= { filterDHCPServerEntry 3 }
	   
	filterDHCPServerVlanList OBJECT-TYPE
	   SYNTAX       OCTET STRING
	   MAX-ACCESS   read-write
	   STATUS       current
	   DESCRIPTION
	       "Specifies the port numbers through which the authorized manager can
	        access the switch.

	        By default the authorized manager is allowed to access the switch
	        through all the ports.

	        If a set of ports are configured in the 'PortList', the manager can
	        access the switch only through the configured ports."
	   ::= { filterDHCPServerEntry 4 }

	filterDHCPServerRowStatus OBJECT-TYPE
	   SYNTAX      RowStatus
	   MAX-ACCESS  read-create
	   STATUS      current
	   DESCRIPTION
	      "This object indicates the status of this entry."
	   ::= { filterDHCPServerEntry 99 }


    securityTrafficSeg                  OBJECT IDENTIFIER ::= { companySecurity 9}
  

    --
    -- Port Map Table
    --
    
    trafficSegTable  OBJECT-TYPE
        SYNTAX     SEQUENCE OF TrafficSegEntry 
        MAX-ACCESS not-accessible
        STATUS     current
        DESCRIPTION
           "A Port-channel is created through ifMain table.
           After the creation of the port-channel, corresponding logical
           interface will be created in the ifMain table. 
           This Port-channel table is indexed through Key values and allows to 
           configure link selection policy and the Mac address for 
           the port-channel. All other objects in this table displays 
           the details of the port-channel"

        ::= { securityTrafficSeg 1 }

    trafficSegEntry OBJECT-TYPE
        SYNTAX     TrafficSegEntry 
        MAX-ACCESS not-accessible
        STATUS     current
        DESCRIPTION
              "There is one entry in this table for each created
               port-channel port"

        INDEX { trafficSegIfIndex }
        ::= { trafficSegTable 1 }

    TrafficSegEntry ::= 
            SEQUENCE {
              trafficSegIfIndex                InterfaceIndex,
              trafficSegMemberList             PortList
              }

    trafficSegIfIndex OBJECT-TYPE
        SYNTAX      InterfaceIndex
        MAX-ACCESS  read-only
        STATUS      current
        DESCRIPTION
              "The ifIndex of the port-channel(Aggregator's 
               interface index). "
        ::= { trafficSegEntry 1 }

  	trafficSegMemberList OBJECT-TYPE
	   SYNTAX       PortList
	   MAX-ACCESS   read-write
	   STATUS       current
	   DESCRIPTION
	       "Port list of port channel."
	   ::= { trafficSegEntry 2 }

        
    
 -- ----------------------------------------------------------
 -- The companySecurity Groups
 -- ----------------------------------------------------------
    securityAAC                  OBJECT IDENTIFIER ::= { companySecurity 11 }

-- -------------------------------------------------------------
-- Authentication Policy and Parameter Settings
-- -------------------------------------------------------------
    aacAuthenAdminState OBJECT-TYPE
        SYNTAX  INTEGER {
                    enabled(1),
                    disabled(2)
                }
        MAX-ACCESS  read-write
        STATUS  current
        DESCRIPTION
            "This object indicates the Access Authentication is enable or
            disable."
        ::= { securityAAC 1}


    aacAuthParamResponseTimeout  OBJECT-TYPE
            SYNTAX     INTEGER (0..255)
            MAX-ACCESS read-write
            STATUS     current
            DESCRIPTION
                "Timeout in second for login authentication response."
            ::= { securityAAC 2 }

    aacAuthParamAttempt  OBJECT-TYPE
            SYNTAX     INTEGER (1..255)
            MAX-ACCESS read-write
            STATUS     current
            DESCRIPTION
                "The amount for login authentication, if login failure exceed,
                 connection or access would be locked."
            ::= { securityAAC 3 }

-- -------------------------------------------------------------
-- Application Authentication Settings
-- -------------------------------------------------------------

    aacAPAuthMethodGroup OBJECT IDENTIFIER ::= { securityAAC 4 }

    aacAPLoginMethod OBJECT IDENTIFIER ::= { aacAPAuthMethodGroup 1 }
    aacAPEnableMethod OBJECT IDENTIFIER ::= { aacAPAuthMethodGroup 2 }

    aacAPConsoleLoginMethod OBJECT-TYPE
        SYNTAX INTEGER (1..8)
        MAX-ACCESS read-write
        STATUS current
        DESCRIPTION
            "Specify the way which has to execute authentication while login the
            system and the method for authentication.Access system via local
            console"

        ::= { aacAPLoginMethod 1 }

    aacAPTelnetLoginMethod OBJECT-TYPE
        SYNTAX INTEGER (1..8)
        MAX-ACCESS read-write
        STATUS current
        DESCRIPTION
            "Specify the way which has to execute authentication while login the
            system and the method for authentication.Access system via telnet."

        ::= { aacAPLoginMethod 2 }

    aacAPSSHLoginMethod OBJECT-TYPE
        SYNTAX INTEGER (1..8)
        MAX-ACCESS read-write
        STATUS current
        DESCRIPTION
            "Specify the way which has to execute authentication while login the
            system and the method for authentication.Access system via SSH."

        ::= { aacAPLoginMethod 3 }

    aacAPHttpLoginMethod OBJECT-TYPE
        SYNTAX INTEGER (1..8)
        MAX-ACCESS read-write
        STATUS current
        DESCRIPTION
            "Specify the way which has to execute authentication while login the
            system and the method for authentication.Access system via HTTP."

        ::= { aacAPLoginMethod 4 }

    aacAPConsoleEnableMethod OBJECT-TYPE
        SYNTAX INTEGER (1..8)
        MAX-ACCESS read-write
        STATUS current
        DESCRIPTION
            "Specify the way which has to execute authentication while login the
            system and the method for authentication.Access system via local
            console."
        ::= { aacAPEnableMethod 1 }

    aacAPTelnetEnableMethod OBJECT-TYPE
        SYNTAX INTEGER (1..8)
        MAX-ACCESS read-write
        STATUS current
        DESCRIPTION
            "Specify the way which has to execute authentication while login the
            system and the method for authentication.Access system via telnet."

        ::= { aacAPEnableMethod 2 }

    aacAPSSHEnableMethod OBJECT-TYPE
        SYNTAX INTEGER (1..8)
        MAX-ACCESS read-write
        STATUS current
        DESCRIPTION
            "Specify the way which has to execute authentication while login the
            system and the method for authentication.Access system via SSH."

        ::= { aacAPEnableMethod 3 }

    aacAPHttpEnableMethod OBJECT-TYPE
        SYNTAX INTEGER (1..8)
        MAX-ACCESS read-write
        STATUS current
        DESCRIPTION
            "Specify the way which has to execute authentication while login the
            system and the method for authentication.Access system via HTTP."

        ::= { aacAPEnableMethod 4 }


-- -------------------------------------------------------------
-- Authentication Server Group setting
-- -------------------------------------------------------------
    aacServerGroupTable OBJECT-TYPE
        SYNTAX SEQUENCE OF AacServerGroupEntry
        MAX-ACCESS not-accessible
        STATUS current
        DESCRIPTION
            "A table that contains informations about server group."
        ::= { securityAAC 5 }

    aacServerGroupEntry OBJECT-TYPE
        SYNTAX AacServerGroupEntry
        MAX-ACCESS not-accessible
        STATUS current
        DESCRIPTION
            "A list of the group including servers."
        INDEX { aacServerGroupIndex }
        ::= { aacServerGroupTable 1 }

    AacServerGroupEntry ::=
        SEQUENCE {
            aacServerGroupIndex
                INTEGER,
            aacServerGroupName
                OCTET STRING,
            aacServersInGroup
                BITS,
            aacServerGroupRowStatus
                RowStatus
        }

    aacServerGroupIndex  OBJECT-TYPE
        SYNTAX     INTEGER (2..9)
        MAX-ACCESS read-only
        STATUS     current
        DESCRIPTION
            "A value that uniquely identifies this SwAACServerGroupEntry ."

        ::= { aacServerGroupEntry 1 }

    aacServerGroupName OBJECT-TYPE
        SYNTAX OCTET STRING (SIZE (1..15))
        MAX-ACCESS read-write
        STATUS current
        DESCRIPTION
            "A human-readable text string of the method group.
             The name is writable only if Group is new created,
             which the value of aacServerGroupRowStatus is 'notReady'."

        ::= { aacServerGroupEntry 2 }


    aacServersInGroup OBJECT-TYPE
        SYNTAX      BITS {
            id1(0),
            id2(1),
            id3(2),
            id4(3),
            id5(4),
            id6(5),
            id7(6),
            id8(7),
            id9(8),
            id10(9),
            id11(10),
            id12(11),
            id13(12),
            id14(13),
            id15(14),
            id16(15)
        }
        MAX-ACCESS  read-write
        STATUS      current
        DESCRIPTION
            "The list of servers in the group, each bit indicates a specified server ID.
             The server must be created before including it."

        ::= { aacServerGroupEntry 3 }

    aacServerGroupRowStatus OBJECT-TYPE
        SYNTAX      RowStatus
        MAX-ACCESS  read-create
        STATUS      current
        DESCRIPTION
            "This object indicates the status of this entry. An entry is
            created in this table when this object is SET to 'createAndWait'.
            The entry in this table is used when the status of this object
            is SET 'active'. The entry in this table is not used when this
            object is SET 'notInService'. An entry created in this table is
            be deleted when this object is SET 'destroy'."

        ::= { aacServerGroupEntry 4 }


-- -------------------------------------------------------------
-- IPv4
-- Authentication Server host setting
-- -------------------------------------------------------------

    iPv4aacServerInfoTable OBJECT-TYPE
        SYNTAX SEQUENCE OF IPv4AacServerInfoEntry
        MAX-ACCESS not-accessible
        STATUS obsolete
        DESCRIPTION
            "A table that contains information about severs."
        ::= { securityAAC 6 }

    iPv4aacServerInfoEntry OBJECT-TYPE
        SYNTAX IPv4AacServerInfoEntry
        MAX-ACCESS not-accessible
        STATUS obsolete
        DESCRIPTION
            "A list of the information of server ."
        INDEX { iPv4aacServerIndex }
        ::= { iPv4aacServerInfoTable 1 }

    IPv4AacServerInfoEntry ::=
        SEQUENCE {
            iPv4aacServerIndex
                INTEGER,
            iPv4aacServerIPAddr
                IpAddress,
            iPv4aacServerAuthProtocol
                INTEGER,
            iPv4aacServerAuthPort
                INTEGER,
            iPv4aacServerAuthKey
                OCTET STRING,
            iPv4aacServerTimeout
                INTEGER,
            iPv4aacServerRetryCount
                INTEGER,
            iPv4aacServerRowStatus
                RowStatus
        }

    iPv4aacServerIndex  OBJECT-TYPE
        SYNTAX     INTEGER (1..16)
        MAX-ACCESS read-only
        STATUS     obsolete
        DESCRIPTION
            "A value that uniquely identifies this SwAACServerGroupEntry."

        ::= { iPv4aacServerInfoEntry 1 }

    iPv4aacServerIPAddr OBJECT-TYPE
        SYNTAX      IpAddress
        MAX-ACCESS  read-write
        STATUS      obsolete
        DESCRIPTION
            "The IP address of Server"
        ::= { iPv4aacServerInfoEntry 2 }

    iPv4aacServerAuthProtocol OBJECT-TYPE
        SYNTAX      INTEGER{
                        tacacsPlus(1),
                        radius(2)
                    }
        MAX-ACCESS  read-write
        STATUS      obsolete
        DESCRIPTION
            "The authentication protocol provided by the Server."
        ::= { iPv4aacServerInfoEntry 3 }

    iPv4aacServerAuthPort OBJECT-TYPE
        SYNTAX      INTEGER(1..65535)
        MAX-ACCESS  read-write
        STATUS      obsolete
        DESCRIPTION
            "The TCP/IP port ."
        ::= { iPv4aacServerInfoEntry 4 }

    iPv4aacServerAuthKey OBJECT-TYPE
        SYNTAX OCTET STRING (SIZE (1..254))
        MAX-ACCESS read-write
        STATUS obsolete
        DESCRIPTION
            "The key used while authentication process."

        ::= { iPv4aacServerInfoEntry 5 }

    iPv4aacServerTimeout OBJECT-TYPE
        SYNTAX      INTEGER(1..255)
        MAX-ACCESS  read-write
        STATUS      obsolete
        DESCRIPTION
            "Server response timeout ."
        ::= { iPv4aacServerInfoEntry 6 }

    iPv4aacServerRetryCount OBJECT-TYPE
        SYNTAX      INTEGER(1..255)
        MAX-ACCESS  read-write
        STATUS      obsolete
        DESCRIPTION
            "Client retry count .
             (-1: No retry mechanism)"
        ::= { iPv4aacServerInfoEntry 7 }

    iPv4aacServerRowStatus OBJECT-TYPE
        SYNTAX      RowStatus
        MAX-ACCESS  read-create
        STATUS      obsolete
        DESCRIPTION
            "This object indicates the status of this entry. An entry is
            created in this table when this object is SET to 'createAndWait'.
            The entry in this table is used when the status of this object
            is SET 'active'. The entry in this table is not used when this
            object is SET 'notInService'. An entry created in this table is
            be deleted when this object is SET 'destroy'."

        ::= { iPv4aacServerInfoEntry 8 }

-- -------------------------------------------------------------
-- IPv6
-- Authentication Server host setting
-- -------------------------------------------------------------

    aacServerInfoTable OBJECT-TYPE
        SYNTAX SEQUENCE OF AacServerInfoEntry
        MAX-ACCESS not-accessible
        STATUS current
        DESCRIPTION
            "A table that contains information about severs."
        ::= { securityAAC 7 }

    aacServerInfoEntry OBJECT-TYPE
        SYNTAX AacServerInfoEntry
        MAX-ACCESS not-accessible
        STATUS current
        DESCRIPTION
            "A list of the information of server ."
        INDEX { aacServerIndex }
        ::= { aacServerInfoTable 1 }

    AacServerInfoEntry ::=
        SEQUENCE {
            aacServerIndex
                INTEGER,
            aacServerIPType
                INTEGER,
            aacServerIPAddr
                Ipv6Address,
            aacServerInterfaceName
                OCTET STRING,
            aacServerAuthProtocol
                INTEGER,
            aacServerAuthPort
                INTEGER,
            aacServerAuthKey
                OCTET STRING,
            aacServerTimeout
                INTEGER,
            aacServerRetryCount
                INTEGER,
            aacServerAccountingPort
                INTEGER,
            aacServerRowStatus
                RowStatus
        }

    aacServerIndex  OBJECT-TYPE
        SYNTAX     INTEGER (1..16)
        MAX-ACCESS read-only
        STATUS     current
        DESCRIPTION
            "A value that uniquely identifies this SwAACServerGroupEntry."

        ::= { aacServerInfoEntry 1 }

    aacServerIPType     OBJECT-TYPE
        SYNTAX          INTEGER (1..2)
        MAX-ACCESS      read-write
        STATUS          current
        DESCRIPTION
            "The IP address of the AAC server IP type
                referred to in this table entry. (IPv4=1, IPv6=2)"
        DEFVAL { 1 }
       ::= { aacServerInfoEntry 2 }

    aacServerIPAddr OBJECT-TYPE
        SYNTAX      Ipv6Address
        MAX-ACCESS  read-write
        STATUS      current
        DESCRIPTION
            "The IP address of Server"
        ::= { aacServerInfoEntry 3 }

    aacServerInterfaceName   OBJECT-TYPE
         SYNTAX      OCTET STRING
         MAX-ACCESS  read-create
         STATUS      current
         DESCRIPTION
               "Specifies the interface name when the aacServerIPAddr is linklocal address."
         ::= { aacServerInfoEntry 4 } 
         
    aacServerAuthProtocol OBJECT-TYPE
        SYNTAX      INTEGER{
                        tacacsPlus(1),
                        radius(2)
                    }
        MAX-ACCESS  read-write
        STATUS      current
        DESCRIPTION
            "The authentication protocol provided by the Server."
        ::= { aacServerInfoEntry 5 }

    aacServerAuthPort OBJECT-TYPE
        SYNTAX      INTEGER(1..65535)
        MAX-ACCESS  read-write
        STATUS      current
        DESCRIPTION
            "The TCP/IP port ."
        ::= { aacServerInfoEntry 6 }

    aacServerAuthKey OBJECT-TYPE
        SYNTAX OCTET STRING (SIZE (1..254))
        MAX-ACCESS read-write
        STATUS current
        DESCRIPTION
            "The key used while authentication process."

        ::= { aacServerInfoEntry 7 }

    aacServerTimeout OBJECT-TYPE
        SYNTAX      INTEGER(1..255)
        MAX-ACCESS  read-write
        STATUS      current
        DESCRIPTION
            "Server response timeout ."
        ::= { aacServerInfoEntry 8 }

    aacServerRetryCount OBJECT-TYPE
        SYNTAX      INTEGER(1..255)
        MAX-ACCESS  read-write
        STATUS      current
        DESCRIPTION
            "Client retry count .
             (-1: No retry mechanism)"
        ::= { aacServerInfoEntry 9 }

    aacServerAccountingPort OBJECT-TYPE
        SYNTAX      INTEGER(1..65535)
        MAX-ACCESS  read-write
        STATUS      current
        DESCRIPTION
            "The accounting port ."
        ::= { aacServerInfoEntry 10 }

    aacServerRowStatus OBJECT-TYPE
        SYNTAX      RowStatus
        MAX-ACCESS  read-create
        STATUS      current
        DESCRIPTION
            "This object indicates the status of this entry. An entry is
            created in this table when this object is SET to 'createAndWait'.
            The entry in this table is used when the status of this object
            is SET 'active'. The entry in this table is not used when this
            object is SET 'notInService'. An entry created in this table is
            be deleted when this object is SET 'destroy'."

        ::= { aacServerInfoEntry 99 }

-- -------------------------------------------------------------
-- Login Method list table
-- -------------------------------------------------------------

    aacLoginMethodListTable OBJECT-TYPE
        SYNTAX SEQUENCE OF AacLoginMethodListEntry
        MAX-ACCESS not-accessible
        STATUS current
        DESCRIPTION
            "A table that contains information about Login authentication method
            lists."

        ::= { securityAAC 8 }

    aacLoginMethodListEntry OBJECT-TYPE
        SYNTAX AacLoginMethodListEntry
        MAX-ACCESS not-accessible
        STATUS current
        DESCRIPTION
            "A list of the Authentication methods."
        INDEX { aacLoginMethodListIndex }

        ::= { aacLoginMethodListTable 1 }

    AacLoginMethodListEntry ::=
        SEQUENCE {
            aacLoginMethodListIndex
                INTEGER,
            aacLoginMethodListName
                OCTET STRING,
            aacLoginMethod1
                INTEGER,
            aacLoginMethod2
                INTEGER,
            aacLoginMethod3
                INTEGER,
            aacLoginMethod4
                INTEGER,
            aacLoginMethodListRowStatus
                RowStatus

        }

    aacLoginMethodListIndex  OBJECT-TYPE
        SYNTAX     INTEGER (1..8)
        MAX-ACCESS read-only
        STATUS     current
        DESCRIPTION
            "A value that identifies this method list."

        ::= { aacLoginMethodListEntry 1 }

    aacLoginMethodListName OBJECT-TYPE
        SYNTAX OCTET STRING (SIZE (1..15))
        MAX-ACCESS read-write
        STATUS current
        DESCRIPTION
            "A human-readable text string of the method list."

        ::= { aacLoginMethodListEntry 2 }

    aacLoginMethod1 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacLoginMethodListEntry 3 }

    aacLoginMethod2 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacLoginMethodListEntry 4 }

    aacLoginMethod3 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacLoginMethodListEntry 5 }

    aacLoginMethod4 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacLoginMethodListEntry 6 }

    aacLoginMethodListRowStatus OBJECT-TYPE
        SYNTAX      RowStatus
        MAX-ACCESS  read-create
        STATUS      current
        DESCRIPTION
            "This object indicates the status of this entry. An entry is
            created in this table when this object is SET to 'createAndWait'.
            The entry in this table is used when the status of this object
            is SET 'active'. The entry in this table is not used when this
            object is SET 'notInService'. An entry created in this table is
            be deleted when this object is SET 'destroy'."

        ::= { aacLoginMethodListEntry 7 }

-- -------------------------------------------------------------
-- Enable Method table
-- -------------------------------------------------------------
    aacEnableMethodListTable OBJECT-TYPE
        SYNTAX SEQUENCE OF AacEnableMethodListEntry
        MAX-ACCESS not-accessible
        STATUS current
        DESCRIPTION
            "A table that contains information about Enable authentication method
            lists."

        ::= { securityAAC 9 }

    aacEnableMethodListEntry OBJECT-TYPE
        SYNTAX AacEnableMethodListEntry
        MAX-ACCESS not-accessible
        STATUS current
        DESCRIPTION
            "A list of the Authentication methods."
        INDEX { aacEnableMethodListIndex }

        ::= { aacEnableMethodListTable 1 }

    AacEnableMethodListEntry ::=
        SEQUENCE {
            aacEnableMethodListIndex
                INTEGER,
            aacEnableMethodListName
                OCTET STRING,
            aacEnableMethod1
                INTEGER,
            aacEnableMethod2
                INTEGER,
            aacEnableMethod3
                INTEGER,
            aacEnableMethod4
                INTEGER,
            aacEnableMethodListRowStatus
                RowStatus
        }

    aacEnableMethodListIndex  OBJECT-TYPE
        SYNTAX     INTEGER (1..8)
        MAX-ACCESS read-only
        STATUS     current
        DESCRIPTION
            "A value that identifies this method list."

        ::= { aacEnableMethodListEntry 1 }

    aacEnableMethodListName OBJECT-TYPE
        SYNTAX OCTET STRING (SIZE(1..15))
        MAX-ACCESS read-write
        STATUS current
        DESCRIPTION
            "A human-readable text string of the method list."

        ::= { aacEnableMethodListEntry 2 }

    aacEnableMethod1 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacEnableMethodListEntry 3 }

    aacEnableMethod2 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacEnableMethodListEntry 4 }

    aacEnableMethod3 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacEnableMethodListEntry 5 }

    aacEnableMethod4 OBJECT-TYPE
        SYNTAX INTEGER {
                    none(-1),
                    local(0)
                    ,tacacsPlus(1)
                    ,radius(2)
                }
        MAX-ACCESS read-write
        STATUS current
        DESCRIPTION
            "The type of Login method list. Besides the pre-defined type, it
             also allow to be set user-defined group by aacServerGroupIndex."

        ::= { aacEnableMethodListEntry 6 }

    aacEnableMethodListRowStatus OBJECT-TYPE
        SYNTAX      RowStatus
        MAX-ACCESS  read-create
        STATUS      current
        DESCRIPTION
            "This object indicates the status of this entry. An entry is
            created in this table when this object is SET to 'createAndWait'.
            The entry in this table is used when the status of this object
            is SET 'active'. The entry in this table is not used when this
            object is SET 'notInService'. An entry created in this table is
            be deleted when this object is SET 'destroy'."

        ::= { aacEnableMethodListEntry 7 }

-- -------------------------------------------------------------
-- Local Enable Password
-- -------------------------------------------------------------
   aacLocalEnablePassword  OBJECT-TYPE
   SYNTAX      DisplayString (SIZE(1..15))
   MAX-ACCESS  read-write
   STATUS      current
   DESCRIPTION
      "This object is used to set Local Enable Password."
   ::= { securityAAC 10 }
-- -------------------------------------------------------------
--  Accounting Method list table
-- -------------------------------------------------------------

    aacAccountingMethodListTable OBJECT-TYPE
        SYNTAX SEQUENCE OF AacAccountingMethodListEntry
        MAX-ACCESS not-accessible
        STATUS current
        DESCRIPTION
            "A table that contains information about Accounting authentication method
            lists."

        ::= { securityAAC 11 }

    aacAccountingMethodListEntry OBJECT-TYPE
        SYNTAX AacAccountingMethodListEntry
        MAX-ACCESS not-accessible
        STATUS current
        DESCRIPTION
            "A list of the Authentication methods."
        INDEX { aacAccountingMethodListIndex }

        ::= { aacAccountingMethodListTable 1 }

    AacAccountingMethodListEntry ::=
        SEQUENCE {
            aacAccountingMethodListIndex
                INTEGER,
            aacAccountingMethodListName
                OCTET STRING,
            aacAccountingMethod1
                INTEGER,
            aacAccountingMethod2
                INTEGER,
            aacAccountingMethod3
                INTEGER,
            aacAccountingMethod4
                INTEGER,
            aacAccountingMethodListRowStatus
                RowStatus

        }
    aacAccountingMethodListIndex  OBJECT-TYPE
        SYNTAX     INTEGER (1..8)
        MAX-ACCESS read-only
        STATUS     current
        DESCRIPTION
            "A value that identifies this method list."

        ::= { aacAccountingMethodListEntry 1 }

    aacAccountingMethodListName OBJECT-TYPE
        SYNTAX OCTET STRING (SIZE (1..15))
        MAX-ACCESS read-write
        STATUS current
        DESCRIPTION
            "A human-readable text string of the method list."

        ::= { aacAccountingMethodListEntry 2 }

    aacAccountingMethod1 OBJECT-TYPE
        SYNTAX INTEGER {
                    none(-1),
                    local(0)
                    ,tacacsPlus(1)
                    ,radius(2)
                }
        MAX-ACCESS read-write
        STATUS current
        DESCRIPTION
            "The type of Accounting method list. Besides the pre-defined type, it
             also allow to be set user-defined group by aacServerGroupIndex."

        ::= { aacAccountingMethodListEntry 3 }

    aacAccountingMethod2 OBJECT-TYPE
        SYNTAX INTEGER {
                    none(-1),
                    local(0)
                    ,tacacsPlus(1)
                    ,radius(2)
                }
        MAX-ACCESS read-write
        STATUS current
        DESCRIPTION
            "The type of Accounting method list. Besides the pre-defined type, it
             also allow to be set user-defined group by aacServerGroupIndex."

        ::= { aacAccountingMethodListEntry 4 }

    aacAccountingMethod3 OBJECT-TYPE
        SYNTAX INTEGER {
                    none(-1),
                    local(0)
                    ,tacacsPlus(1)
                    ,radius(2)
                }
        MAX-ACCESS read-write
        STATUS current
        DESCRIPTION
            "The type of Accounting method list. Besides the pre-defined type, it
             also allow to be set user-defined group by aacServerGroupIndex."

        ::= { aacAccountingMethodListEntry 5 }

    aacAccountingMethod4 OBJECT-TYPE
        SYNTAX INTEGER {
                    none(-1),
                    local(0)
                    ,tacacsPlus(1)
                    ,radius(2)
                }
        MAX-ACCESS read-write
        STATUS current
        DESCRIPTION
            "The type of Accounting method list. Besides the pre-defined type, it
             also allow to be set user-defined group by aacServerGroupIndex."

        ::= { aacAccountingMethodListEntry 6 }

    aacAccountingMethodListRowStatus OBJECT-TYPE
        SYNTAX      RowStatus
        MAX-ACCESS  read-create
        STATUS      current
        DESCRIPTION
            "This object indicates the status of this entry. An entry is
            created in this table when this object is SET to 'createAndWait'.
            The entry in this table is used when the status of this object
            is SET 'active'. The entry in this table is not used when this
            object is SET 'notInService'. An entry created in this table is
            be deleted when this object is SET 'destroy'."

        ::= { aacAccountingMethodListEntry 7 }
-- -------------------------------------------------------------
--  Accounting Service Index
-- -------------------------------------------------------------
    aacAccountingServiceIndex      OBJECT IDENTIFIER ::= { securityAAC 12 }
    aacAccountingServiceNetwork OBJECT-TYPE
       SYNTAX      INTEGER {
                      radius-only              (0),
                      default-method-list      (1),
                      method-list-name         (2),
                      disabled	               (-1)
                   }
        MAX-ACCESS read-write 
        STATUS current
        DESCRIPTION
            "This object indicates aac Accounting Service Network is radius-only, default-method-list,
            method-list-name and disable about Accounting Service Network."

        DEFVAL  { -1 }
        ::= { aacAccountingServiceIndex 1 }

    aacAccountingServiceShell OBJECT-TYPE
       SYNTAX      INTEGER {
                      radius-only              (0),
                      default-method-list      (1),
                      method-list-name         (2),
                      disabled	               (-1)
                   }
        MAX-ACCESS read-write 
        STATUS current
        DESCRIPTION
            "This object indicates aac Accounting Service Shell is radius-only, default-method-list,
            method-list-name and disable about Accounting Service Network."

        DEFVAL  { -1 }
        ::= { aacAccountingServiceIndex 2 }

    aacAccountingServiceSystem OBJECT-TYPE
       SYNTAX      INTEGER {
                      radius-only              (0),
                      default-method-list      (1),
                      method-list-name         (2),
                      disabled	               (-1)
                   }
        MAX-ACCESS read-write 
        STATUS current
        DESCRIPTION
            "This object indicates aac Accounting System Shell is radius-only, default-method-list,
            method-list-name and disable about Accounting Service Network."

        DEFVAL  { -1 }
        ::= { aacAccountingServiceIndex 3 }
-- -------------------------------------------------------------
--  Accounting Service Command
-- -------------------------------------------------------------
    aacAccountingServiceCommand      OBJECT IDENTIFIER ::= { securityAAC 13 }

    aacAccountingServiceCommandAdministrator OBJECT-TYPE
        SYNTAX      INTEGER 
        MAX-ACCESS  read-write 
        STATUS current
        DESCRIPTION
            "This object indicates which method list Accounting Admin Command Service uses.
            If the value is -1, it means disabled."

        DEFVAL  { -1 }
        ::= { aacAccountingServiceCommand 1 }

    aacAccountingServiceCommandOperator  OBJECT-TYPE
        SYNTAX      INTEGER  
        MAX-ACCESS  read-write 
        STATUS current
        DESCRIPTION
            "This object indicates which method list Accounting Operator Command Service uses.
            If the value is -1, it means disabled."

        DEFVAL  { -1 }
        ::= { aacAccountingServiceCommand 2 }

    aacAccountingServiceCommandPoweruser OBJECT-TYPE
        SYNTAX      INTEGER
        MAX-ACCESS  read-write 
        STATUS current
        DESCRIPTION
            "This object indicates which method list Accounting PowerUser Command Service uses.
            If the value is -1, it means disabled."

        DEFVAL  { -1 }
        ::= { aacAccountingServiceCommand 3 }

    aacAccountingServiceCommandUser  OBJECT-TYPE
        SYNTAX      INTEGER
        MAX-ACCESS  read-write 
        STATUS current
        DESCRIPTION
            "This object indicates which method list Accounting User Command Service uses.
            If the value is -1, it means disabled."

        DEFVAL  { -1 }
        ::= { aacAccountingServiceCommand 4 }                   
        
-- -------------------------------------------------------------
-- Server Password Encryption
-- -------------------------------------------------------------

   aacServerPasswordEncryption  OBJECT-TYPE
   SYNTAX  INTEGER {
                    enabled(1),
                    disabled(2)
                   }
   MAX-ACCESS  read-write
   STATUS      current
   DESCRIPTION
      "This object is used to configure server password encryption status."
   ::= { securityAAC 14 }


        -- ----------------------------------------------------------------
        -- The STATIC ARP group
        -- ----------------------------------------------------------------

        staticARPTable OBJECT-TYPE
            SYNTAX SEQUENCE OF StaticARPEntry
            MAX-ACCESS not-accessible
            STATUS current
            DESCRIPTION
                "A list of the Static MACs"
            ::= { companyStaticARP  2 }

        staticARPEntry OBJECT-TYPE
            SYNTAX StaticARPEntry
            MAX-ACCESS not-accessible
            STATUS current
            DESCRIPTION
                "A Static MAC entry containing the mac and forwarding port."
            INDEX { staticARPIP, staticARPMac}
            ::= { staticARPTable 1 }

        StaticARPEntry ::= SEQUENCE {
            staticARPIP     	    IpAddress,
            staticARPMac            MacAddress,
            staticARPRowStatus      RowStatus
        }

        staticARPIP OBJECT-TYPE
            SYNTAX IpAddress
            MAX-ACCESS read-only
            STATUS current
            DESCRIPTION
                "The VLAN ID of the static ARP IP."
            ::= { staticARPEntry 2 }

         staticARPMac OBJECT-TYPE
           SYNTAX MacAddress
           MAX-ACCESS read-only
           STATUS current
           DESCRIPTION
               "The MAC address associated of the static ARP entry."
           ::= { staticARPEntry 3 }

         staticARPRowStatus OBJECT-TYPE
            SYNTAX     RowStatus
            MAX-ACCESS read-write
            STATUS     current
            DESCRIPTION
                "The status of an entry in the Static ARP Table.  Only a subset
                 of the rowstatus variables (active, createAndGo, destroy) 
                 are available. The trunk member port can not set up static ARP."
            ::= { staticARPEntry 5 }



        sysGratuitousARPGlobalSettings         OBJECT IDENTIFIER ::= { companyGratuitousARP 1 }
        sysGratuitousARPSettings               OBJECT IDENTIFIER ::= { companyGratuitousARP 2 }

      -- ----------------------------------------------------------------
      -- The sysGratuitousARPGlobalSettings group
      -- ----------------------------------------------------------------
        sysGratuitousARPIPIfStatusUp  OBJECT-TYPE
           SYNTAX      INTEGER {
                    enable(1),
                    disable(2)
           }
           MAX-ACCESS  read-write
           STATUS      current
           DESCRIPTION 
            "This object indicates Send On IP Interface Status Up is enabled or disabled."
            DEFVAL { disable }
           ::= { sysGratuitousARPGlobalSettings 1 }
         
        sysGratuitousARPDuplicateIPDetected  OBJECT-TYPE
            SYNTAX      INTEGER {
                    enable(1),
                    disable(2)
            }
            MAX-ACCESS  read-write
            STATUS      current
            DESCRIPTION 
            "This object indicates Send On Duplicate IP Detected is enabled or disabled."
            DEFVAL { disable }
            ::= { sysGratuitousARPGlobalSettings 2 }
          
        sysGratuitousARPLearning  OBJECT-TYPE
            SYNTAX      INTEGER {
                    enable(1),
                    disable(2)
            }
            MAX-ACCESS  read-write
            STATUS      current
            DESCRIPTION 
            "This object indicates Gratuitous ARP Learning is enabled or disabled."
            DEFVAL { disable }
            ::= { sysGratuitousARPGlobalSettings 3 }  

      -- ----------------------------------------------------------------
      -- The sysGratuitousARPSettings group
      -- ----------------------------------------------------------------
          
        sysGratuitousARPTable OBJECT-TYPE
           SYNTAX SEQUENCE OF SysGratuitousARPEntry
           MAX-ACCESS not-accessible
           STATUS     current
           DESCRIPTION
              "Set/Add Gratuitous ARP interface name and interval time."
           ::= { sysGratuitousARPSettings 1 }

        sysGratuitousARPEntry OBJECT-TYPE
           SYNTAX      SysGratuitousARPEntry
           MAX-ACCESS  not-accessible
           STATUS      current
           DESCRIPTION
              "The entry of gratuitous ARP!"
           INDEX { sysGratuitousARPIFName }
           ::= { sysGratuitousARPTable 1 }   
           
        SysGratuitousARPEntry ::= SEQUENCE
            {
                sysGratuitousARPIFName          OCTET STRING,
                sysGratuitousARPInterval        Integer32
            }               

        sysGratuitousARPIFName OBJECT-TYPE
            SYNTAX      OCTET STRING
            MAX-ACCESS  read-only
            STATUS      current
            DESCRIPTION
                "Interface name."
            ::= { sysGratuitousARPEntry 1 }

        sysGratuitousARPInterval OBJECT-TYPE 
          SYNTAX      Integer32 (0..65535) 
          MAX-ACCESS  read-write 
          STATUS      current 
          DESCRIPTION 
             "Gratuitous ARP interval time for each interface."
          DEFVAL  { 0 } 
          ::= { sysGratuitousARPEntry 2 } 
                  

    -- ---------------------------------------------------------------------
    -- IP Multi-Interface Function
    -- ---------------------------------------------------------------------
          
      ipv4multiIFInfo         OBJECT IDENTIFIER ::= { companyMultiIPInterface 1 }
 
        
      ipv4mulIfMainTable          OBJECT-TYPE
         SYNTAX            SEQUENCE OF Ipv4MulIfMainEntry
         MAX-ACCESS        not-accessible
         STATUS            obsolete
         DESCRIPTION
            "A list of interface entries."
         ::= { ipv4multiIFInfo 1 }

      ipv4mulIfMainEntry          OBJECT-TYPE
         SYNTAX            Ipv4MulIfMainEntry
         MAX-ACCESS        not-accessible
         STATUS            obsolete
         DESCRIPTION
            "An entry containing management information applicable
               to a particular interface."
         INDEX { ipv4mulifMainIndex, ipv4mulifVLANID }
         ::= { ipv4mulIfMainTable 1 }

      Ipv4MulIfMainEntry ::=
         SEQUENCE {
            ipv4mulifMainIndex               InterfaceIndex,
            ipv4mulifVLANID                  INTEGER,
            ipv4mulifName                    OCTET STRING,
            ipv4mulifVLANname                OCTET STRING,
            ipv4mulifIpAddr                  IpAddress,
            ipv4mulifIpSubnetMask            IpAddress,
            ipv4mulifMainAdminStatus         INTEGER,
            ipv4mulifMainOperStatus          INTEGER,
            ipv4mulifMainRowStatus           RowStatus              
            }

      ipv4mulifMainIndex          OBJECT-TYPE
         SYNTAX            InterfaceIndex
         MAX-ACCESS        read-only 
         STATUS            obsolete
         DESCRIPTION
            "The index of this interface." 
         ::= { ipv4mulIfMainEntry 1 }

      ipv4mulifVLANID OBJECT-TYPE
            SYNTAX INTEGER
            MAX-ACCESS read-only
            STATUS obsolete
            DESCRIPTION
                "The ID of VLAN that you want this interface to be in. 
                It must be a exist vlan id."
            ::= { ipv4mulIfMainEntry 2 }

      ipv4mulifName   OBJECT-TYPE
         SYNTAX      OCTET STRING
         MAX-ACCESS  read-write
         STATUS      obsolete
         DESCRIPTION
               "The Description for the interface."
         ::= { ipv4mulIfMainEntry 3 }         
         
      ipv4mulifVLANname   OBJECT-TYPE
         SYNTAX      OCTET STRING
         MAX-ACCESS  read-only
         STATUS      obsolete
         DESCRIPTION
               "The vlan name for the interface."
         ::= { ipv4mulIfMainEntry 4 }    

      ipv4mulifIpAddr             OBJECT-TYPE
         SYNTAX            IpAddress
         MAX-ACCESS        read-write 
         STATUS            obsolete
         DESCRIPTION
            "The ip address of this interface."
         DEFVAL { '00000000'H } 
         ::= { ipv4mulIfMainEntry 6 }

      ipv4mulifIpSubnetMask       OBJECT-TYPE
         SYNTAX            IpAddress
         MAX-ACCESS        read-write 
         STATUS            obsolete
         DESCRIPTION
            "The subnet mask of this interface."
         ::= { ipv4mulIfMainEntry 7 }

      ipv4mulifMainAdminStatus    OBJECT-TYPE
         SYNTAX            INTEGER {
                              enable(1), 
                              disable(2)
                              }
         MAX-ACCESS        read-create
         STATUS            obsolete
         DESCRIPTION
            "The desired state of the interface."
         DEFVAL { disable } 
         ::= { ipv4mulIfMainEntry 8 }


      ipv4mulifMainOperStatus     OBJECT-TYPE
         SYNTAX            INTEGER  {
                              linkup(1),    -- ready to pass packets
                              linkdown(2)
                              }
         MAX-ACCESS        read-only
         STATUS            obsolete
         DESCRIPTION
            "The current operational state of the interface."
         ::= { ipv4mulIfMainEntry 9 }

      ipv4mulifMainRowStatus      OBJECT-TYPE
         SYNTAX            RowStatus
         MAX-ACCESS        read-create
         STATUS            obsolete
         DESCRIPTION
            "The status of an entry in the Multi Interface Table.  Only a subset
             of the rowstatus variables (active, createAndWait, destroy) are available." 
         ::= { ipv4mulIfMainEntry 10 }                  

    -- ---------------------------------------------------------------------
    -- IPv6 Multi-Interface Function
    -- ---------------------------------------------------------------------
          
      multiIFSupportV4V6Info         OBJECT IDENTIFIER ::= { companyMultiIPInterface 2 }

    -- ---------------------------------------------------------------------    
    -- ---------------------------------------------------------------------
     
      mulIfSupportV4V6MainTable          OBJECT-TYPE
         SYNTAX            SEQUENCE OF MulIfSupportV4V6MainEntry
         MAX-ACCESS        not-accessible
         STATUS            current
         DESCRIPTION
            "A list of interface entries."
         ::= { multiIFSupportV4V6Info 1 }

      mulIfSupportV4V6MainEntry          OBJECT-TYPE
         SYNTAX            MulIfSupportV4V6MainEntry
         MAX-ACCESS        not-accessible
         STATUS            current
         DESCRIPTION
            "An entry containing management information applicable
               to a particular interface."
         INDEX { mulifMainIndex, mulifVLANID }
         ::= { mulIfSupportV4V6MainTable 1 }

      MulIfSupportV4V6MainEntry ::=
         SEQUENCE {
                mulifMainIndex                  InterfaceIndex,
                mulifVLANID                     INTEGER,
                mulifName                       OCTET STRING,
                mulifVLANname                   OCTET STRING,
                mulifIpAddr                     IpAddress,
                mulifIpSubnetMask               IpAddress,
                mulifMainAdminStatus            INTEGER,
                mulifMainOperStatus             INTEGER,
                mulifv6GlobalStatus             INTEGER,         -- Support IPv6 or not.
                mulifv6DHCPStatus               INTEGER,         -- Support DHCPv6 or not.
                mulifv6AutolinkloStatus         INTEGER,         -- Automatic Link local Address Status.
                mulifv6NSRetransmitTime         INTEGER,         -- NS Retransmit Time Settings.
                mulifMainRowStatus              RowStatus        -- Entries Row status.
            }

      mulifMainIndex     OBJECT-TYPE
         SYNTAX            InterfaceIndex
         MAX-ACCESS        read-only 
         STATUS            current
         DESCRIPTION
            "The index of this interface." 
         ::= { mulIfSupportV4V6MainEntry 1 }

      mulifVLANID         OBJECT-TYPE
            SYNTAX          INTEGER
            MAX-ACCESS      read-only
            STATUS          current
            DESCRIPTION
            "The ID of VLAN that you want this interface to be in. 
            It must be a exist vlan id."
        ::= { mulIfSupportV4V6MainEntry 2 }

      mulifName           OBJECT-TYPE
         SYNTAX             OCTET STRING
         MAX-ACCESS         read-write
         STATUS             current
         DESCRIPTION
               "The Description for the interface."
         ::= { mulIfSupportV4V6MainEntry 3 }         
         
      mulifVLANname       OBJECT-TYPE
         SYNTAX             OCTET STRING
         MAX-ACCESS         read-only
         STATUS             current
         DESCRIPTION
               "The vlan name for the interface."
         ::= { mulIfSupportV4V6MainEntry 4 }    

      mulifIpAddr         OBJECT-TYPE
         SYNTAX             IpAddress
         MAX-ACCESS         read-create
         STATUS             current
         DESCRIPTION
            "The ip address of this interface."
         DEFVAL { '00000000'H } 
         ::= { mulIfSupportV4V6MainEntry 5 }

      mulifIpSubnetMask   OBJECT-TYPE
         SYNTAX             IpAddress
         MAX-ACCESS         read-create 
         STATUS             current
         DESCRIPTION
            "The subnet mask of this interface."
         ::= { mulIfSupportV4V6MainEntry 6 }

      mulifMainAdminStatus    OBJECT-TYPE
         SYNTAX                 INTEGER {
                                    enable(1), 
                                    disable(2)
                                }
         MAX-ACCESS             read-create
         STATUS                 current
         DESCRIPTION
            "The desired state of the interface."
         DEFVAL { disable } 
         ::= { mulIfSupportV4V6MainEntry 7 }

      mulifMainOperStatus     OBJECT-TYPE
         SYNTAX                 INTEGER  {
                                    linkup(1),    -- ready to pass packets
                                    linkdown(2)
                                }
         MAX-ACCESS             read-only
         STATUS                 current
         DESCRIPTION
            "The current operational state of the interface."
         ::= { mulIfSupportV4V6MainEntry 8 }

      mulifv6GlobalStatus     OBJECT-TYPE
            SYNTAX              INTEGER   {
                                  enable(1),    
                                  disable(2)
                                }
            MAX-ACCESS          read-create
            STATUS              current
            DESCRIPTION
                "The ID of VLAN that you want this interface to be in. 
                It must be a exist vlan id."
            ::= { mulIfSupportV4V6MainEntry 9 }

      mulifv6DHCPStatus       OBJECT-TYPE
            SYNTAX              INTEGER   {
                                  enable(1),    
                                  disable(2)
                                }
            MAX-ACCESS          read-create
            STATUS              current
            DESCRIPTION
                "The state of DHCPv6 that you want this interface to be in. 
                It must be a exist vlan id."
            ::= { mulIfSupportV4V6MainEntry 10 }

      mulifv6AutolinkloStatus OBJECT-TYPE
            SYNTAX              INTEGER   {
                                  enable(1),    
                                  disable(2)
                                }
            MAX-ACCESS          read-create
            STATUS              current
            DESCRIPTION
                "The global state of link local that you want this interface to be in. 
                It must be a exist vlan id."
            ::= { mulIfSupportV4V6MainEntry 11 }

      mulifv6NSRetransmitTime OBJECT-TYPE
            SYNTAX              INTEGER
            MAX-ACCESS          read-create
            STATUS              current
            DESCRIPTION
                "The NS's retransmit time that you want this interface to be in. 
                It must be a exist vlan id."
            ::= { mulIfSupportV4V6MainEntry 12 }

      mulifMainRowStatus      OBJECT-TYPE
         SYNTAX                 RowStatus
         MAX-ACCESS             read-create
         STATUS                 current
         DESCRIPTION
            "The status of an entry in the Multi Interface Table.  Only a subset
             of the rowstatus variables (active, createAndWait, destroy) are available." 
         ::= { mulIfSupportV4V6MainEntry 13 }     

 
    -- ---------------------------------------------------------------------    
    -- ---------------------------------------------------------------------   

      mulIfV6AddressTable          OBJECT-TYPE
         SYNTAX            SEQUENCE OF MulIfV6AddressEntry
         MAX-ACCESS        not-accessible
         STATUS            current
         DESCRIPTION
            "A list of interface entries."
         ::= { multiIFSupportV4V6Info 2 }

      mulIfV6AddressEntry          OBJECT-TYPE
         SYNTAX            MulIfV6AddressEntry
         MAX-ACCESS        not-accessible
         STATUS            current
         DESCRIPTION
            "An entry containing management information applicable
               to a particular interface."
         INDEX { mulifV6AddressMainIndex, mulifV6AddressIpAddr, mulifV6AddressIpPrefix }
         ::= { mulIfV6AddressTable 1 }

      MulIfV6AddressEntry ::=
         SEQUENCE {
                mulifV6AddressMainIndex              InterfaceIndex,
                mulifV6AddressIpAddr                 Ipv6Address,     -- IPv6 Address.
                mulifV6AddressIpPrefix               INTEGER,         -- IPv6 Address Prefix.
                mulifV6AddressIpType                 INTEGER,         -- IP type (Link-local, Global, anycast).
                mulifV6AddressRowStatus              RowStatus        -- IPv6 Address entries row status.
            }

      mulifV6AddressMainIndex    OBJECT-TYPE
         SYNTAX                 InterfaceIndex
         MAX-ACCESS             read-only 
         STATUS                 current
         DESCRIPTION
            "The index of this IPv6 entry." 
         ::= { mulIfV6AddressEntry 1 }

      mulifV6AddressIpAddr       OBJECT-TYPE
         SYNTAX                 Ipv6Address
         MAX-ACCESS             read-only
         STATUS                 current
         DESCRIPTION
            "The ip address of this IPv6 entry."
         DEFVAL { '00000000'H } 
         ::= { mulIfV6AddressEntry 2 }
              
      mulifV6AddressIpPrefix     OBJECT-TYPE
            SYNTAX              INTEGER
            MAX-ACCESS          read-only
            STATUS              current
            DESCRIPTION
            "The ip prefix of this IPv6 entry."
        ::= { mulIfV6AddressEntry 3 } 

      mulifV6AddressIpType       OBJECT-TYPE
         SYNTAX                 INTEGER {
                                    unicast(1), 
                                    anycast(2),
                                    linklocal(3)
                                }
            MAX-ACCESS          read-only
            STATUS              current
            DESCRIPTION
            "The ip type of this IPv6 entry."
        ::= { mulIfV6AddressEntry 4 }
        
      mulifV6AddressRowStatus    OBJECT-TYPE
         SYNTAX                 RowStatus
         MAX-ACCESS             read-create
         STATUS                 current
         DESCRIPTION
            "The status of an entry in the Multi Interface Table.  Only a subset
             of the rowstatus variables (active, createAndWait, destroy) are available." 
         ::= { mulIfV6AddressEntry 5 }     


-- start DLINK-AGENT-BACIC-INFO

        agentCPUutilization                   OBJECT IDENTIFIER ::= { companyAgentBasicInfo  1 }
        agentMEMutilization                   OBJECT IDENTIFIER ::= { companyAgentBasicInfo  2 }
        
      -- ----------------------------------------------------------------
      -- The agentCPUutilization group
      -- ----------------------------------------------------------------
        agentCPUutilizationIn5sec OBJECT-TYPE
        SYNTAX  Integer32
        MAX-ACCESS  read-only
        STATUS  current
        DESCRIPTION
            "The time scale is set at 5 second intervals.
             The value will be between 0% (idle) and 100% (very busy)."
        ::= { agentCPUutilization 1 }
 
       agentCPUutilizationIn1min OBJECT-TYPE
        SYNTAX  Integer32
 
        MAX-ACCESS  read-only
        STATUS  current
        DESCRIPTION
            "The time scale is set at 1 minute intervals.
             The value will be between 0% (idle) and 100% (very busy)."
        ::= { agentCPUutilization 2 }
 
     agentCPUutilizationIn5min OBJECT-TYPE
        SYNTAX  Integer32
        MAX-ACCESS  read-only
        STATUS  current
        DESCRIPTION
            "The time scale is set at 5 minute intervals.
             The value will be between 0% (idle) and 100% (very busy)."
        ::= { agentCPUutilization 3 }

      -- ----------------------------------------------------------------
      -- The agentMEMutilization group
      -- ----------------------------------------------------------------
        agentMEMutilizationIn5sec OBJECT-TYPE
        SYNTAX  Integer32
        MAX-ACCESS  read-only
        STATUS  current
        DESCRIPTION
            "The time scale is set at 5 second intervals.
             The value will be between 0% (idle) and 100% (very busy)."
        ::= { agentMEMutilization 1 }
 
       agentMEMutilizationIn1min OBJECT-TYPE
        SYNTAX  Integer32
 
        MAX-ACCESS  read-only
        STATUS  current
        DESCRIPTION
            "The time scale is set at 1 minute intervals.
             The value will be between 0% (idle) and 100% (very busy)."
        ::= { agentMEMutilization 2 }
 
     agentMEMutilizationIn5min OBJECT-TYPE
        SYNTAX  Integer32
        MAX-ACCESS  read-only
        STATUS  current
        DESCRIPTION
            "The time scale is set at 5 minute intervals.
             The value will be between 0% (idle) and 100% (very busy)."
        ::= { agentMEMutilization 3 }

-- end DLINK-AGENT-BACIC-INFO

 -- ----------------------------------------------------------
 -- The companyL2PT  Groups
 -- ----------------------------------------------------------
 -- L2PT Group --------------------------------------------- --
-- -----------------------------------------------------------------------------
-- swL2PTState
-- -----------------------------------------------------------------------------
    l2PTState OBJECT-TYPE
        SYNTAX  INTEGER {
               enabled(1),
               disabled(2)
               }
        MAX-ACCESS  read-write
        STATUS  current
        DESCRIPTION
            "This object indicates the global state of Layer 2 protocol tunneling."
    	::= { companyL2PT 1 }
-- -----------------------------------------------------------------------------
-- L2PTPortTable
-- -----------------------------------------------------------------------------
         l2PTPortTable OBJECT-TYPE 
           SYNTAX SEQUENCE OF L2PTEntry
           MAX-ACCESS  not-accessible
           STATUS      current 
           DESCRIPTION 
              "A table that cont
              ains the cable situation for each port."
           ::= { companyL2PT 2 }     
    
         l2PTEntry OBJECT-TYPE 
           SYNTAX      L2PTEntry  
           MAX-ACCESS  not-accessible
           STATUS      current 
           DESCRIPTION 
              "A list of cable situations for each port on the device."
            INDEX { l2PTPortIndex }
            ::= { l2PTPortTable 1 }

        L2PTEntry ::= 
          SEQUENCE {
                l2PTPortIndex
                  INTEGER,
			    l2PTPortType
				  INTEGER,
			    l2PTProtocol
				  BITS
            }


        l2PTPortIndex OBJECT-TYPE
            SYNTAX  INTEGER
            MAX-ACCESS  not-accessible
            STATUS  current
            DESCRIPTION
        	    "This object indicates the port number."
    	    ::= { l2PTEntry 1 }

        l2PTPortType OBJECT-TYPE
            SYNTAX INTEGER {
                none(1),
                uni(2),
                nni(3)
                }
         MAX-ACCESS  read-write
            STATUS current
            DESCRIPTION
                "This object indicates the Layer 2 protocol tunneling port type.

		        The 'none' value indicates that the port is normal. Layer 2 protocol tunneling
		        is disabled on this port.
	
		        The 'uni' value indicates that the port is connected to the customer site. 
                A Layer 2 PDU received on a UNI port can be tunneled to a remote customer site across the provider network.
	
		        The 'nni' value indicates that the port is connected to the provider network. 
                A Tunneled Layer 2 PDU received on an NNI port will be restored to its original format."
	        DEFVAL { none }
    	    ::= { l2PTEntry 2 }

        l2PTProtocol  OBJECT-TYPE
		    SYNTAX BITS {
				    stp(0),
				    gvrp(1),
    		    	macCC(2),
		    	    macCD(3)
		         }
		    MAX-ACCESS read-write
		    STATUS     current
		    DESCRIPTION  
		        "This object indicates the tunneled protocols on this port.
		        This object can only be applied on a UNI port. 
		    
		        If the 'stp' BIT is set, the STP BPDU will be tunneled.
	
		        If the 'gvrp' BIT is set, the GVRP PDU will be tunneled.
		    	    
		         If the 'mac-01-00-0C-CC-CC-CC' BIT is set, the PDU with the	            
                 destination MAC address 01-00-0C-CC-CC-CC will be tunneled .
	
		        If the 'mac-01-00-0C-CC-CC-CD' BIT is set, then the PDU with the
	            destination MAC address 01-00-0C-CC-CC-CD will be tunneled."
		    ::= { l2PTEntry 3 }
-- -----------------------------------------------------------------------------
-- L2PTThresholdTable
-- -----------------------------------------------------------------------------
    l2PTThresholdTable OBJECT-TYPE
    	SYNTAX     SEQUENCE OF L2PTThresholdEntry
    	MAX-ACCESS not-accessible
    	STATUS     current
    	DESCRIPTION 
    	    "This table contains the protocol tunneling threshold of a UNI port."
    	::= { companyL2PT 3}

    l2PTThresholdEntry OBJECT-TYPE
        SYNTAX  L2PTThresholdEntry
        MAX-ACCESS  not-accessible
        STATUS  current
        DESCRIPTION
            "A list with the Layer2 Protocol tunneling threshold."
        INDEX   { l2PTPortIndex, l2PTProtocolIndex }
        ::= { l2PTThresholdTable 1 }
     
   
     L2PTThresholdEntry ::=
        SEQUENCE {
                l2PTProtocolIndex
            	    INTEGER,
                l2PTDropThreshold       
            	    INTEGER
                } 
        
    l2PTProtocolIndex   OBJECT-TYPE
		SYNTAX     INTEGER {
					stp(1),
					gvrp(2),
			    	macCC(3),
			    	macCD(4)	
			    }		
		MAX-ACCESS  not-accessible
		STATUS     current
		DESCRIPTION  
		    "This object indicates the tunneled protocol of the port."
		::= { l2PTThresholdEntry 1 }

    l2PTDropThreshold  OBJECT-TYPE
		SYNTAX     INTEGER (0..65535)
		MAX-ACCESS read-write
		STATUS     current
		DESCRIPTION  
		    "This object indicates the drop threshold for a given protocol on a UNI port.
	            If the arrival rate of a tunneled protocol has reached its threshold, the received
	            PDUs of this protocol will be dropped. 
	            The value 0 indicates there is no threshold for the protocol."
		DEFVAL { 0 }
		::= { l2PTThresholdEntry 2 }
-- ----------------------------------------------------------
-- The companyCpuProtect Groups
-- ----------------------------------------------------------
						
	  cpuProtectState OBJECT-TYPE
        SYNTAX INTEGER {
                          disabled (0),
                          enabled  (1)
               }
        MAX-ACCESS  read-write
        STATUS  current
        DESCRIPTION
            "This object indicates the status of the cpu protect."
    ::= { companyCpuProtect 1 }
    
    cpuProtectTable  OBJECT-TYPE
        SYNTAX  SEQUENCE OF CpuProtectEntry
        MAX-ACCESS  not-accessible
        STATUS  current
        DESCRIPTION
            "A table that holds the cpu protect settings of the device."
        ::= { companyCpuProtect 2 }

    cpuProtectEntry OBJECT-TYPE
        SYNTAX  CpuProtectEntry
        MAX-ACCESS  not-accessible
        STATUS  current
        DESCRIPTION
            "A list of cpu protect settings of the device."
        INDEX   { cpuProtectType }
        ::= { cpuProtectTable 1 }

    CpuProtectEntry ::= 
        SEQUENCE {
			cpuProtectType
				INTEGER,
			cpuProtectPPS
				INTEGER
        }
        
    cpuProtectType OBJECT-TYPE
    	SYNTAX INTEGER {
			arp(1),
			bpdu(2),
			icmp(3),
			igmp(4),
			snmp(5)
   	    	}
        MAX-ACCESS  read-only
        STATUS current
        DESCRIPTION
            "This object indicates the Cpu protect type."
    ::= { cpuProtectEntry 1 }
       
    cpuProtectPPS OBJECT-TYPE
    	SYNTAX INTEGER (-1..65535)
        MAX-ACCESS  read-write
        STATUS current
        DESCRIPTION
            "Specify the threshold as packet count per second at which traffic is received on the CPU port.
             If value set to -1, it means no threshold."
    ::= { cpuProtectEntry 2 }


    -- ------------------------------------------------------------------
    -- The SMTP Group
    -- ------------------------------------------------------------------

      ipv4smtpState OBJECT-TYPE
           SYNTAX      INTEGER {  disabled(0),enabled(1) }
           MAX-ACCESS  read-write
           STATUS      obsolete
           DESCRIPTION
               "Enable or Disable SMTP function."

           ::= { companySMTP 1 }

      ipv4smtpServerAddr  OBJECT-TYPE
           SYNTAX      IpAddress
           MAX-ACCESS  read-write
           STATUS      obsolete
           DESCRIPTION
              "SMTP Server's IP Address"
            ::= { companySMTP 2 }

      ipv4smtpServerPort OBJECT-TYPE
            SYNTAX INTEGER
            MAX-ACCESS read-write
            STATUS obsolete
            DESCRIPTION
                "SMTP Server's port"
            ::= { companySMTP 3}

      ipv4smtpSelfMailAddr OBJECT-TYPE
            SYNTAX      OCTET STRING
            MAX-ACCESS  read-write
            STATUS      obsolete
            DESCRIPTION
                "The sender's (DUT) mail address ."
            ::= { companySMTP  4 }
        
        

    -- ------------------------------------------------------------------
    -- smtpRecvMailAddrTable
    -- ------------------------------------------------------------------
    
    ipv4smtpRecvMailAddrTable  OBJECT-TYPE
        SYNTAX     SEQUENCE OF Ipv4SmtpRecvMailAddrEntry 
        MAX-ACCESS not-accessible
        STATUS     current
        DESCRIPTION
           "Receivers' mail address table."

        ::= { companySMTP 5 }

    ipv4smtpRecvMailAddrEntry OBJECT-TYPE
        SYNTAX     Ipv4SmtpRecvMailAddrEntry 
        MAX-ACCESS not-accessible
        STATUS     current
        DESCRIPTION
              "Receivers' mail address entry."

        INDEX { ipv4smtpRecvMailAddrIndex }
        ::= { ipv4smtpRecvMailAddrTable 1 }

    Ipv4SmtpRecvMailAddrEntry  ::= 
            SEQUENCE {
              ipv4smtpRecvMailAddrIndex          INTEGER,
              ipv4smtpRecvMailAddr               OCTET STRING,
              ipv4smtpRecvMailAddrStatus         RowStatus
              }

    ipv4smtpRecvMailAddrIndex OBJECT-TYPE
       SYNTAX       INTEGER
       MAX-ACCESS   read-only
       STATUS       current
       DESCRIPTION
         "Receivers' mail address index (1~8)." 
        ::= { ipv4smtpRecvMailAddrEntry  1 }

    ipv4smtpRecvMailAddr OBJECT-TYPE
        SYNTAX      OCTET STRING
        MAX-ACCESS  read-write
        STATUS      current
        DESCRIPTION
              "Receivers' mail address."
        ::= { ipv4smtpRecvMailAddrEntry  2 }
        
    ipv4smtpRecvMailAddrStatus OBJECT-TYPE
       SYNTAX RowStatus
       MAX-ACCESS read-write
       STATUS current
       DESCRIPTION
         "Rowstatus of the receiver's mail address."
       ::= { ipv4smtpRecvMailAddrEntry 3 }
       
--IPv6 smtp server Group

	  sysSMTPServerGroup OBJECT IDENTIFIER ::= { companySMTP  6 }
              
      smtpState OBJECT-TYPE
           SYNTAX      INTEGER {  disabled(0),enabled(1) }
           MAX-ACCESS  read-write
           STATUS      current
           DESCRIPTION
               "Enable or Disable SMTP function."

           ::= { sysSMTPServerGroup 1 }

      smtpServerAddr  OBJECT-TYPE
           SYNTAX      Ipv6Address
           MAX-ACCESS  read-write
           STATUS      current
           DESCRIPTION
              "SMTP Server's IP Address"
            ::= { sysSMTPServerGroup 2 }

      smtpServerAddrType OBJECT-TYPE
            SYNTAX    INTEGER {
                      iPv4 (1),
                      iPv6 (2)
            }
            MAX-ACCESS  read-write
            STATUS      current
            DESCRIPTION
                "SMTP Server's Address type."
            ::= { sysSMTPServerGroup 3 }

      smtpServerAddrInterfaceName   OBJECT-TYPE
            SYNTAX      OCTET STRING
            MAX-ACCESS  read-write
            STATUS      current
            DESCRIPTION
                "Specifies the interface name when the smtpServerAddrInterfaceName is linklocal address."
            ::= { sysSMTPServerGroup 4 } 
   

      smtpServerPort OBJECT-TYPE
            SYNTAX INTEGER
            MAX-ACCESS read-write
            STATUS current
            DESCRIPTION
                "SMTP Server's port"
            ::= { sysSMTPServerGroup 5}

      smtpSelfMailAddr OBJECT-TYPE
            SYNTAX      OCTET STRING
            MAX-ACCESS  read-write
            STATUS      current
            DESCRIPTION
                "The sender's (DUT) mail address ."
            ::= { sysSMTPServerGroup  6 }
        
        

    -- ------------------------------------------------------------------
    -- smtpRecvMailAddrTable
    -- ------------------------------------------------------------------
    
    smtpRecvMailAddrTable  OBJECT-TYPE
        SYNTAX     SEQUENCE OF SmtpRecvMailAddrEntry 
        MAX-ACCESS not-accessible
        STATUS     current
        DESCRIPTION
           "Receivers' mail address table."

        ::= { sysSMTPServerGroup 7 }

    smtpRecvMailAddrEntry OBJECT-TYPE
        SYNTAX     SmtpRecvMailAddrEntry 
        MAX-ACCESS not-accessible
        STATUS     current
        DESCRIPTION
              "Receivers' mail address entry."

        INDEX { smtpRecvMailAddrIndex }
        ::= { smtpRecvMailAddrTable 1 }

    SmtpRecvMailAddrEntry  ::= 
            SEQUENCE {
              smtpRecvMailAddrIndex          INTEGER,
              smtpRecvMailAddr               OCTET STRING,
              smtpRecvMailAddrStatus         RowStatus
              }

    smtpRecvMailAddrIndex OBJECT-TYPE
       SYNTAX       INTEGER
       MAX-ACCESS   read-only
       STATUS       current
       DESCRIPTION
         "Receivers' mail address index (1~8)." 
        ::= { smtpRecvMailAddrEntry  1 }

    smtpRecvMailAddr OBJECT-TYPE
        SYNTAX      OCTET STRING
        MAX-ACCESS  read-write
        STATUS      current
        DESCRIPTION
              "Receivers' mail address."
        ::= { smtpRecvMailAddrEntry  2 }
        
    smtpRecvMailAddrStatus OBJECT-TYPE
       SYNTAX RowStatus
       MAX-ACCESS read-write
       STATUS current
       DESCRIPTION
         "Rowstatus of the receiver's mail address."
       ::= { smtpRecvMailAddrEntry 3 }    

    igmpMulticastVlanStatus OBJECT-TYPE 
           SYNTAX      INTEGER {
                          enabled(1),
                          disabled(2)
                       }
           MAX-ACCESS  read-write 
           STATUS      current 
           DESCRIPTION 
               "Enable/Disable IGMP Multicast Vlan function."
        
           DEFVAL  { disabled }
           ::= { companyISMVLAN 1 }

     -- ----------------------------------------------------------
     -- igmpMulticastVlanTable Table 
     -- ----------------------------------------------------------
    
     igmpMulticastVlanTable OBJECT-TYPE
        SYNTAX  SEQUENCE OF IgmpMulticastVlanEntry
        MAX-ACCESS  not-accessible
        STATUS  current
        DESCRIPTION
            "Information about the IGMP snooping multicast VLAN table."
        ::= { companyISMVLAN 2 }
    
     igmpMulticastVlanEntry OBJECT-TYPE
        SYNTAX  IgmpMulticastVlanEntry
        MAX-ACCESS  not-accessible
        STATUS  current
        DESCRIPTION
            "The entry of igmpMulticastVlanTable."
        INDEX  { igmpMulticastVlanid}
        ::= { igmpMulticastVlanTable 1 }

    IgmpMulticastVlanEntry ::= 
        SEQUENCE {
            igmpMulticastVlanid
                INTEGER,
            igmpMulticastVlanName
                DisplayString,
            igmpMulticastVlanSourcePort
                PortList,
            igmpMulticastVlanMemberPort
                PortList,
            igmpMulticastVlanTagMemberPort
            	PortList,
            igmpMulticastVlanUntaggedSourcePort
            	PortList,
            igmpMulticastVlanState
            	INTEGER,
            igmpMulticastVlanReplaceSourceIp
            	IpAddress,
            igmpMulticastVlanRowStatus
                RowStatus
        }
        
    igmpMulticastVlanid OBJECT-TYPE
        SYNTAX  INTEGER (2..4094)
        MAX-ACCESS  read-only
        STATUS  current
        DESCRIPTION
            "This object indicates the VLAN ID of the IGMP snooping multicast 
             VLAN entry."
        ::= { igmpMulticastVlanEntry 1 }
        
    igmpMulticastVlanName OBJECT-TYPE
        SYNTAX  DisplayString (SIZE (0..32))
        MAX-ACCESS  read-create
        STATUS  current
        DESCRIPTION
            "This object indicates the VLAN name of the IGMP snooping multicast 
             VLAN entry."
        ::= { igmpMulticastVlanEntry 2 }   
            
    igmpMulticastVlanSourcePort OBJECT-TYPE
        SYNTAX  PortList
        MAX-ACCESS  read-write
        STATUS  current
        DESCRIPTION
            "This object indicates the port list of the source ports of the IGMP 
             snooping multicast VLAN. The source ports will be set as tag ports 
             of the VLAN entry and the IGMP control messages received from the
             member ports will be forwarded to the source ports."
        ::= { igmpMulticastVlanEntry 3 }   

    igmpMulticastVlanMemberPort OBJECT-TYPE
        SYNTAX  PortList
        MAX-ACCESS  read-write
        STATUS  current
        DESCRIPTION
            "This object indicates the port list of the member ports of the IGMP 
             snooping multicast VLAN. The source ports will be set as untagged ports 
             of the VLAN entry and the IGMP control messages received from the
             member ports will be forwarded to the source ports."
        ::= { igmpMulticastVlanEntry 4 }      
        
    igmpMulticastVlanTagMemberPort OBJECT-TYPE
        SYNTAX  PortList
        MAX-ACCESS  read-write
        STATUS  current
        DESCRIPTION
            "This object indicates the port list of the tag member ports of the IGMP 
             snooping multicast VLAN."
        ::= { igmpMulticastVlanEntry 5 }

    igmpMulticastVlanUntaggedSourcePort OBJECT-TYPE
        SYNTAX  PortList
        MAX-ACCESS  read-write
        STATUS  current
        DESCRIPTION
            "This object indicates the port list of the untag source ports of the IGMP 
             snooping multicast VLAN."
        ::= { igmpMulticastVlanEntry 6 }		
    igmpMulticastVlanState OBJECT-TYPE
        SYNTAX  INTEGER{
        	enabled(1),
        	disabled(2)
        	}
        MAX-ACCESS  read-write
        STATUS  current
        DESCRIPTION
            "This object can be used to enable or disable the IGMP snooping multicast VLAN."
        ::= { igmpMulticastVlanEntry 7 }
            
    igmpMulticastVlanReplaceSourceIp OBJECT-TYPE
    	SYNTAX  IpAddress
        MAX-ACCESS  read-write
        STATUS  current
        DESCRIPTION
            "The replacement source IP of this multicast VLAN."
        ::= { igmpMulticastVlanEntry 8 }
        
    igmpMulticastVlanRowStatus OBJECT-TYPE
        SYNTAX  RowStatus
        MAX-ACCESS  read-create
        STATUS  current
        DESCRIPTION
            "This object indicates the status of this entry."
        ::= { igmpMulticastVlanEntry 9 }         
          
    -- -----------------------------------------------------------------------------
    --  igmpMulticastVlanGroupTable	
    -- -----------------------------------------------------------------------------   
    igmpMulticastVlanGroupTable OBJECT-TYPE
        SYNTAX  SEQUENCE OF IgmpMulticastVlanGroupEntry
        MAX-ACCESS  not-accessible
        STATUS  current
        DESCRIPTION
            "The table containing the IGMP snooping multicast VLAN group information"
        ::= { companyISMVLAN 3 }

    igmpMulticastVlanGroupEntry OBJECT-TYPE
        SYNTAX  IgmpMulticastVlanGroupEntry
        MAX-ACCESS  not-accessible
        STATUS  current
        DESCRIPTION
            "Information about the current IGMP snooping multicast VLAN group."
        INDEX  { igmpMulticastVlanGroupVid, igmpMulticastVlanGroupFromIp, igmpMulticastVlanGroupToIp }
        ::= { igmpMulticastVlanGroupTable 1 }

    IgmpMulticastVlanGroupEntry ::= 
        SEQUENCE {
            igmpMulticastVlanGroupVid
                INTEGER,
            igmpMulticastVlanGroupFromIp
                IpAddress,
            igmpMulticastVlanGroupToIp
                IpAddress,                
            igmpMulticastVlanGroupStatus
                RowStatus
        }
    
    igmpMulticastVlanGroupVid	OBJECT-TYPE
	SYNTAX  INTEGER (1..4094)
        MAX-ACCESS  read-only
        STATUS  current
        DESCRIPTION
            "This object indicates the VID of the IGMP snooping multicast VLAN group."
        ::= { igmpMulticastVlanGroupEntry 1 }
    
    igmpMulticastVlanGroupFromIp	OBJECT-TYPE
    	SYNTAX      IpAddress
    	MAX-ACCESS  read-only
    	STATUS      current
    	DESCRIPTION
       		"Specifies the multicast address list for this VLAN."
    	::= { igmpMulticastVlanGroupEntry 2  }
    		
    igmpMulticastVlanGroupToIp	OBJECT-TYPE
    	SYNTAX      IpAddress
    	MAX-ACCESS  read-only
    	STATUS      current
    	DESCRIPTION
       		"Specifies the multicast address list for this VLAN."
    	::= { igmpMulticastVlanGroupEntry 3  }
    	
    igmpMulticastVlanGroupStatus	OBJECT-TYPE
        SYNTAX   RowStatus
        MAX-ACCESS read-create
        STATUS   current
        DESCRIPTION
        	"This object indicates the status of this entry."		
        ::= { igmpMulticastVlanGroupEntry 4 }
    


     -- ----------------------------------------------------------
     -- multicastVlanTable Table 
     -- ----------------------------------------------------------
    
     multicastVlanTable OBJECT-TYPE
        SYNTAX  SEQUENCE OF MulticastVlanEntry
        MAX-ACCESS  not-accessible
        STATUS  current
        DESCRIPTION
            "Information about the IGMP/MLD snooping multicast VLAN table."
        ::= { companyISMVLAN 4 }
    
     multicastVlanEntry OBJECT-TYPE
        SYNTAX  MulticastVlanEntry
        MAX-ACCESS  not-accessible
        STATUS  current
        DESCRIPTION
            "The entry of multicastVlanTable."
        INDEX  { multicastVlanid}
        ::= { multicastVlanTable 1 }

    MulticastVlanEntry ::= 
        SEQUENCE {
            multicastVlanid
                INTEGER,
            multicastVlanName
                DisplayString,
            multicastVlanSourcePort
                PortList,
            multicastVlanMemberPort
                PortList,
            multicastVlanTagMemberPort
            	PortList,
            multicastVlanUntaggedSourcePort
            	PortList,
            multicastVlanState
            	INTEGER,
            multicastVlanIgmpReplaceSourceIp
            	IpAddress,
            multicastVlanMldReplaceSourceIp
            	Ipv6Address,
            multicastVlanRowStatus
                RowStatus
        }
        
    multicastVlanid OBJECT-TYPE
        SYNTAX  INTEGER (2..4094)
        MAX-ACCESS  read-only
        STATUS  current
        DESCRIPTION
            "This object indicates the VLAN ID of the IGMP/MLD snooping  
             multicast VLAN entry."
        ::= { multicastVlanEntry 1 }
        
    multicastVlanName OBJECT-TYPE
        SYNTAX  DisplayString (SIZE (0..32))
        MAX-ACCESS  read-create
        STATUS  current
        DESCRIPTION
            "This object indicates the VLAN name of the IGMP/MLD snooping
             multicast VLAN entry."
        ::= { multicastVlanEntry 2 }   
            
    multicastVlanSourcePort OBJECT-TYPE
        SYNTAX  PortList
        MAX-ACCESS  read-write
        STATUS  current
        DESCRIPTION
            "This object indicates the port list of the source ports of the  
             IGMP/MLD snooping multicast VLAN. The source ports will be set as 
             tag ports of the VLAN entry and the IGMP control messages received 
             from themember ports will be forwarded to the source ports."
        ::= { multicastVlanEntry 3 }   

    multicastVlanMemberPort OBJECT-TYPE
        SYNTAX  PortList
        MAX-ACCESS  read-write
        STATUS  current
        DESCRIPTION
            "This object indicates the port list of the member ports of the 
             IGMP/MLD snooping multicast VLAN. The source ports will be set as
             untagged ports of the VLAN entry and the IGMP control messages 
             received from themember ports will be forwarded to the source ports."
        ::= { multicastVlanEntry 4 }      
        
    multicastVlanTagMemberPort OBJECT-TYPE
        SYNTAX  PortList
        MAX-ACCESS  read-write
        STATUS  current
        DESCRIPTION
            "This object indicates the port list of the tag member ports of the 
             IGMP/MLD snooping multicast VLAN."
        ::= { multicastVlanEntry 5 }

    multicastVlanUntaggedSourcePort OBJECT-TYPE
        SYNTAX  PortList
        MAX-ACCESS  read-write
        STATUS  current
        DESCRIPTION
            "This object indicates the port list of the untag source ports of the 
             IGMP/MLD snooping multicast VLAN."
        ::= { multicastVlanEntry 6 }
        	
    multicastVlanState OBJECT-TYPE
        SYNTAX  INTEGER{
        	enabled(1),
        	disabled(2)
        	}
        MAX-ACCESS  read-write
        STATUS  current
        DESCRIPTION
            "This object can be used to enable or disable the IGMP/MLD snooping 
             multicast VLAN."
        ::= { multicastVlanEntry 7 }
            
    multicastVlanIgmpReplaceSourceIp OBJECT-TYPE
    	SYNTAX  IpAddress
        MAX-ACCESS  read-write
        STATUS  current
        DESCRIPTION
            "The replacement source IP of this IGMP snooping multicast VLAN."
        ::= { multicastVlanEntry 8 }

    multicastVlanMldReplaceSourceIp OBJECT-TYPE
    	SYNTAX  Ipv6Address
        MAX-ACCESS  read-write
        STATUS  current
        DESCRIPTION
            "The replacement source IP of this MLD snooping multicast VLAN."
        ::= { multicastVlanEntry 9 }
        
    multicastVlanRowStatus OBJECT-TYPE
        SYNTAX  RowStatus
        MAX-ACCESS  read-create
        STATUS  current
        DESCRIPTION
            "This object indicates the status of this entry."
        ::= { multicastVlanEntry 10 }         
          
    -- -----------------------------------------------------------------------------
    --  igmpMulticastVlanGroupTable	
    -- -----------------------------------------------------------------------------   
    multicastVlanGroupTable OBJECT-TYPE
        SYNTAX  SEQUENCE OF MulticastVlanGroupEntry
        MAX-ACCESS  not-accessible
        STATUS  current
        DESCRIPTION
            "The table containing the IGMP/MLD snooping multicast VLAN group information"
        ::= { companyISMVLAN 5 }

    multicastVlanGroupEntry OBJECT-TYPE
        SYNTAX  MulticastVlanGroupEntry
        MAX-ACCESS  not-accessible
        STATUS  current
        DESCRIPTION
            "The entry of multicastVlanGroupTable."
        INDEX  { multicastVlanGroupVid, multicastVlanGroupIpType, multicastVlanGroupFromIp, multicastVlanGroupToIp }
        ::= { multicastVlanGroupTable 1 }

    MulticastVlanGroupEntry ::= 
        SEQUENCE {
            multicastVlanGroupVid
                INTEGER,
          	multicastVlanGroupIpType
             		INTEGER,                
            multicastVlanGroupFromIp
                Ipv6Address,
            multicastVlanGroupToIp
                Ipv6Address,                
            multicastVlanGroupStatus
                RowStatus
        }
    
    multicastVlanGroupVid	OBJECT-TYPE
				SYNTAX  INTEGER (1..4094)
        MAX-ACCESS  read-only
        STATUS  current
        DESCRIPTION
            "This object indicates the VID of the IGMP/MLD snooping multicast VLAN group."
        ::= { multicastVlanGroupEntry 1 }

    multicastVlanGroupIpType OBJECT-TYPE
        SYNTAX    INTEGER {
               iPv4             (1),
               iPv6	            (2)
            }
        MAX-ACCESS  read-only
        STATUS      current
        DESCRIPTION
        "Type of specifies the multicast address list for this VLAN."
        ::= { multicastVlanGroupEntry 2 }
    
    multicastVlanGroupFromIp	OBJECT-TYPE
    	SYNTAX      Ipv6Address
    	MAX-ACCESS  read-only
    	STATUS      current
    	DESCRIPTION
       		"Specifies the multicast address list for this VLAN."
    	::= { multicastVlanGroupEntry 3  }
    		
    multicastVlanGroupToIp	OBJECT-TYPE
    	SYNTAX      Ipv6Address
    	MAX-ACCESS  read-only
    	STATUS      current
    	DESCRIPTION
       		"Specifies the multicast address list for this VLAN."
    	::= { multicastVlanGroupEntry 4  }
    	
    multicastVlanGroupStatus	OBJECT-TYPE
        SYNTAX   RowStatus
        MAX-ACCESS read-create
        STATUS   current
        DESCRIPTION
        	"This object indicates the status of this entry."		
        ::= { multicastVlanGroupEntry 5 }          
 
	-- -----------------------------------------------------------------------------
	-- The Guest Vlan Group
	-- -----------------------------------------------------------------------------
	pppoeGlobalState OBJECT-TYPE
	    SYNTAX INTEGER  {
        	 disabled (0),
        	 enabled (1)
        }
        MAX-ACCESS  read-write
	    STATUS      current
	    DESCRIPTION
		"PPPoE global state"
	    ::= { companyPPPoE 1 }

	pppoePortTable OBJECT-TYPE
        SYNTAX SEQUENCE OF PppoePortEntry
        MAX-ACCESS not-accessible
        STATUS current
        DESCRIPTION
            "A table to control PPPoE features of the device."
        ::= { companyPPPoE 2 }
        
    pppoePortEntry OBJECT-TYPE
        SYNTAX PppoePortEntry
        MAX-ACCESS not-accessible
        STATUS current
        DESCRIPTION
            "An entry appears in PPPoE table for each interface 
 	        in the system."    
 	    INDEX {pppoePortIndex}
        ::= { pppoePortTable 1 }
  
    PppoePortEntry ::= 
        SEQUENCE {  
           pppoePortIndex
              Integer32,
           pppoePortState
              INTEGER, 
           pppoePortCircuitIDType 
              INTEGER,
           pppoePortUDFString 
              DisplayString,
           pppoePortCircuitIDVendor3String
              DisplayString,
           pppoePortRemoteIDType
              INTEGER,
           pppoePortRemoteIDVendor3String
              DisplayString
        }
           
    pppoePortIndex OBJECT-TYPE
        SYNTAX      Integer32 (1..6)
        MAX-ACCESS  read-only
        STATUS      current
        DESCRIPTION
           "Interface index of the port for the configuration
            in this entry applies."
        ::= { pppoePortEntry 1 }

    pppoePortState OBJECT-TYPE
	    SYNTAX INTEGER  {
        	 disabled (0),
        	 enabled (1)
        }
        MAX-ACCESS  read-write
	    STATUS      current
	    DESCRIPTION
		"PPPoE per port state"
	    ::= { pppoePortEntry 2 } 
	    
	pppoePortCircuitIDType OBJECT-TYPE
	    SYNTAX INTEGER  {
        	 ip (0),
        	 mac (1),
        	 udf (2),
             vendor2 (3),
             vendor3 (4)
        }
        MAX-ACCESS  read-write
	    STATUS      current
	    DESCRIPTION
		"PPPoE per port circuit ID type"
	    ::= { pppoePortEntry 3 }
     
    pppoePortUDFString OBJECT-TYPE
	    SYNTAX      DisplayString(SIZE(1..32))
        MAX-ACCESS  read-write
	    STATUS      current
	    DESCRIPTION
		"PPPoE per port UDF string"
	    ::= { pppoePortEntry 4 }    
	    
    pppoePortCircuitIDVendor3String OBJECT-TYPE
	    SYNTAX      DisplayString(SIZE(1..32))
        MAX-ACCESS  read-write
	    STATUS      current
	    DESCRIPTION
		"PPPoE per port circuit ID vendor3 string"
	    ::= { pppoePortEntry 5 }    
	    
	pppoePortRemoteIDType OBJECT-TYPE
	    SYNTAX INTEGER  {
        	 default (0),
        	 vendor2 (1),
        	 vendor3 (2)
        }
        MAX-ACCESS  read-write
	    STATUS      current
	    DESCRIPTION
		"PPPoE per port remote ID type"
	    ::= { pppoePortEntry 6 }
     
    pppoePortRemoteIDVendor3String OBJECT-TYPE
	    SYNTAX      DisplayString(SIZE(1..32))
        MAX-ACCESS  read-write
	    STATUS      current
	    DESCRIPTION
		"PPPoE per port remote ID vendor3 string"
	    ::= { pppoePortEntry 7 }    
	    
        -- ----------------------------------------------------------------
        -- The RMON group
        -- ----------------------------------------------------------------
      rmonGlobalState OBJECT-TYPE 
           SYNTAX      INTEGER {
                          enabled(1),
                          disabled(2)
                       }
           MAX-ACCESS  read-write 
           STATUS      current 
           DESCRIPTION 
               "This object is for enabling or disabling RMON function."
        
           ::= { companyRMON 1 }

     rmonStatistics        OBJECT IDENTIFIER ::= { companyRMON 2 }
     rmonHistory           OBJECT IDENTIFIER ::= { companyRMON 3 }
     rmonAlarm             OBJECT IDENTIFIER ::= { companyRMON 4 }
     rmonEvent             OBJECT IDENTIFIER ::= { companyRMON 5 }
     
-- The Ethernet Statistics Group
 --
 -- Implementation of the Ethernet Statistics group is optional.
 -- Consult the MODULE-COMPLIANCE macro for the authoritative
 -- conformance information for this MIB.
 --
 -- The ethernet statistics group contains statistics measured by the
 -- probe for each monitored interface on this device.  These
 -- statistics take the form of free running counters that start from
 -- zero when a valid entry is created.
 --
 -- This group currently has statistics defined only for
 -- Ethernet interfaces.  Each etherStatsEntry contains statistics
 -- for one Ethernet interface.  The probe must create one
 -- etherStats entry for each monitored Ethernet interface
 -- on the device.

 rmonStatsTable OBJECT-TYPE
     SYNTAX     SEQUENCE OF RmonStatsEntry
     MAX-ACCESS not-accessible
     STATUS     current
     DESCRIPTION
         "A list of Ethernet statistics entries."
     ::= { rmonStatistics 1 }

 rmonStatsEntry OBJECT-TYPE
     SYNTAX     RmonStatsEntry
     MAX-ACCESS not-accessible
     STATUS     current
     DESCRIPTION
         "A collection of statistics kept for a particular
         Ethernet interface.  As an example, an instance of the
         etherStatsPkts object might be named etherStatsPkts.1"
     INDEX { rmonStatsIndex }
     ::= { rmonStatsTable 1 }

 RmonStatsEntry ::= SEQUENCE {
     rmonStatsIndex                    Integer32,
     rmonStatsDataSource               OBJECT IDENTIFIER,
     rmonStatsOwner                    OwnerString,
     rmonStatsStatus                   RmonStatus
 }

 rmonStatsIndex OBJECT-TYPE
     SYNTAX     Integer32 (1..65535)
     MAX-ACCESS read-only
     STATUS     current
     DESCRIPTION
         "The value of this object uniquely identifies this
         etherStats entry."
     ::= { rmonStatsEntry 1 }

 rmonStatsDataSource OBJECT-TYPE
     SYNTAX     OBJECT IDENTIFIER
     MAX-ACCESS read-create
     STATUS     current
     DESCRIPTION
         "This object identifies the source of the data that
         this etherStats entry is configured to analyze.  This
         source can be any ethernet interface on this device.
         In order to identify a particular interface, this object
         shall identify the instance of the ifIndex object,
         defined in RFC 2233 [17], for the desired interface.
         For example, if an entry were to receive data from
         interface #1, this object would be set to ifIndex.1.

         The statistics in this group reflect all packets
         on the local network segment attached to the identified
         interface.

         An agent may or may not be able to tell if fundamental
         changes to the media of the interface have occurred and
         necessitate an invalidation of this entry.  For example, a
         hot-pluggable ethernet card could be pulled out and replaced
         by a token-ring card.  In such a case, if the agent has such
         knowledge of the change, it is recommended that it
         invalidate this entry.

         This object may not be modified if the associated
         etherStatsStatus object is equal to valid(1)."
     ::= { rmonStatsEntry 2 }

 rmonStatsOwner OBJECT-TYPE
     SYNTAX     OwnerString
     MAX-ACCESS read-create
     STATUS     current
     DESCRIPTION
         "The entity that configured this entry and is therefore
         using the resources assigned to it."
     ::= { rmonStatsEntry 3 }

 rmonStatsStatus OBJECT-TYPE
     SYNTAX     RmonStatus
     MAX-ACCESS read-create
     STATUS     current
     DESCRIPTION
         "The status of this etherStats entry."
     ::= { rmonStatsEntry 4 }
     

 -- The History Control Group

 -- Implementation of the History Control group is optional.
 -- Consult the MODULE-COMPLIANCE macro for the authoritative
 -- conformance information for this MIB.
 --
 -- The history control group controls the periodic statistical
 -- sampling of data from various types of networks.  The
 -- historyControlTable stores configuration entries that each
 -- define an interface, polling period, and other parameters.
 -- Once samples are taken, their data is stored in an entry
 -- in a media-specific table.  Each such entry defines one
 -- sample, and is associated with the historyControlEntry that
 -- caused the sample to be taken.  Each counter in the
 -- etherHistoryEntry counts the same event as its similarly-named
 -- counterpart in the etherStatsEntry, except that each value here
 -- is a cumulative sum during a sampling period.
 --
 -- If the probe keeps track of the time of day, it should start
 -- the first sample of the history at a time such that
 -- when the next hour of the day begins, a sample is
 -- started at that instant.  This tends to make more
 -- user-friendly reports, and enables comparison of reports
 -- from different probes that have relatively accurate time
 -- of day.
 --
 -- The probe is encouraged to add two history control entries
 -- per monitored interface upon initialization that describe a short
 -- term and a long term polling period.  Suggested parameters are 30
 -- seconds for the short term polling period and 30 minutes for
 -- the long term period.

 rmonHistoryTable OBJECT-TYPE
     SYNTAX     SEQUENCE OF RmonHistoryEntry
     MAX-ACCESS not-accessible
     STATUS     current
     DESCRIPTION
         "A list of history control entries."
     ::= { rmonHistory 1 }

 rmonHistoryEntry OBJECT-TYPE
     SYNTAX     RmonHistoryEntry
     MAX-ACCESS not-accessible
     STATUS     current
     DESCRIPTION
         "A list of parameters that set up a periodic sampling of
         statistics.  As an example, an instance of the
         historyControlInterval object might be named
         historyControlInterval.2"
     INDEX { rmonHistoryIndex }
     ::= { rmonHistoryTable 1 }

 RmonHistoryEntry ::= SEQUENCE {
     rmonHistoryIndex             Integer32,
     rmonHistoryDataSource        OBJECT IDENTIFIER,
     rmonHistoryBucketsRequested  Integer32,
     rmonHistoryInterval          Integer32,
     rmonHistoryOwner             OwnerString,
     rmonHistoryStatus            RmonStatus
 }

 rmonHistoryIndex OBJECT-TYPE
     SYNTAX     Integer32 (1..65535)
     MAX-ACCESS read-only
     STATUS     current
     DESCRIPTION
         "An index that uniquely identifies an entry in the
         historyControl table.  Each such entry defines a
         set of samples at a particular interval for an
         interface on the device."
     ::= { rmonHistoryEntry 1 }

 rmonHistoryDataSource OBJECT-TYPE
     SYNTAX     OBJECT IDENTIFIER
     MAX-ACCESS read-create
     STATUS     current
     DESCRIPTION
         "This object identifies the source of the data for
         which historical data was collected and
         placed in a media-specific table on behalf of this
         historyControlEntry.  This source can be any
         interface on this device.  In order to identify

         a particular interface, this object shall identify
         the instance of the ifIndex object, defined
         in  RFC 2233 [17], for the desired interface.
         For example, if an entry were to receive data from
         interface #1, this object would be set to ifIndex.1.

         The statistics in this group reflect all packets
         on the local network segment attached to the identified
         interface.

         An agent may or may not be able to tell if fundamental
         changes to the media of the interface have occurred and
         necessitate an invalidation of this entry.  For example, a
         hot-pluggable ethernet card could be pulled out and replaced
         by a token-ring card.  In such a case, if the agent has such
         knowledge of the change, it is recommended that it
         invalidate this entry.

         This object may not be modified if the associated
         historyControlStatus object is equal to valid(1)."
     ::= { rmonHistoryEntry 2 }

 rmonHistoryBucketsRequested OBJECT-TYPE
     SYNTAX     Integer32 (1..65535)
     MAX-ACCESS read-create
     STATUS     current
     DESCRIPTION
         "The requested number of discrete time intervals
         over which data is to be saved in the part of the
         media-specific table associated with this
         historyControlEntry.

         When this object is created or modified, the probe
         should set historyControlBucketsGranted as closely to
         this object as is possible for the particular probe
         implementation and available resources."
     DEFVAL { 50 }
     ::= { rmonHistoryEntry 3 }

 rmonHistoryInterval OBJECT-TYPE
     SYNTAX     Integer32 (1..3600)
     UNITS      "Seconds"
     MAX-ACCESS read-create
     STATUS     current
     DESCRIPTION
         "The interval in seconds over which the data is
         sampled for each bucket in the part of the
         media-specific table associated with this
         historyControlEntry.  This interval can
         be set to any number of seconds between 1 and
         3600 (1 hour).

         Because the counters in a bucket may overflow at their

         maximum value with no indication, a prudent manager will
         take into account the possibility of overflow in any of
         the associated counters.  It is important to consider the
         minimum time in which any counter could overflow on a
         particular media type and set the historyControlInterval
         object to a value less than this interval.  This is
         typically most important for the 'octets' counter in any
         media-specific table.  For example, on an Ethernet
         network, the etherHistoryOctets counter could overflow
         in about one hour at the Ethernet's maximum
         utilization.

         This object may not be modified if the associated
         historyControlStatus object is equal to valid(1)."
     DEFVAL { 1800 }
     ::= { rmonHistoryEntry 4 }

 rmonHistoryOwner OBJECT-TYPE
     SYNTAX     OwnerString
     MAX-ACCESS read-create
     STATUS     current
     DESCRIPTION
         "The entity that configured this entry and is therefore
         using the resources assigned to it."
     ::= { rmonHistoryEntry 5 }

 rmonHistoryStatus OBJECT-TYPE
     SYNTAX     RmonStatus
     MAX-ACCESS read-create
     STATUS     current
     DESCRIPTION
         "The status of this historyControl entry.

         Each instance of the media-specific table associated
         with this historyControlEntry will be deleted by the agent
         if this historyControlEntry is not equal to valid(1)."
     ::= { rmonHistoryEntry 6 }


 -- The Alarm Group

 -- Implementation of the Alarm group is optional. The Alarm Group
 -- requires the implementation of the Event group.
 -- Consult the MODULE-COMPLIANCE macro for the authoritative
 -- conformance information for this MIB.
 --
 -- The Alarm group periodically takes statistical samples from
 -- variables in the probe and compares them to thresholds that have
 -- been configured.  The alarm table stores configuration
 -- entries that each define a variable, polling period, and
 -- threshold parameters.  If a sample is found to cross the
 -- threshold values, an event is generated.  Only variables that
 -- resolve to an ASN.1 primitive type of INTEGER (INTEGER, Integer32,
 -- Counter32, Counter64, Gauge32, or TimeTicks) may be monitored in
 -- this way.
 --

 -- This function has a hysteresis mechanism to limit the generation
 -- of events.  This mechanism generates one event as a threshold
 -- is crossed in the appropriate direction.  No more events are
 -- generated for that threshold until the opposite threshold is
 -- crossed.
 --
 -- In the case of a sampling a deltaValue, a probe may implement
 -- this mechanism with more precision if it takes a delta sample
 -- twice per period, each time comparing the sum of the latest two
 -- samples to the threshold.  This allows the detection of threshold
 -- crossings that span the sampling boundary.  Note that this does
 -- not require any special configuration of the threshold value.
 -- It is suggested that probes implement this more precise algorithm.

 rmonAlarmTable OBJECT-TYPE
     SYNTAX     SEQUENCE OF RmonAlarmEntry
     MAX-ACCESS not-accessible
     STATUS     current
     DESCRIPTION
         "A list of alarm entries."
     ::= { rmonAlarm 1 }

 rmonAlarmEntry OBJECT-TYPE
     SYNTAX     RmonAlarmEntry
     MAX-ACCESS not-accessible
     STATUS     current
     DESCRIPTION
         "A list of parameters that set up a periodic checking
         for alarm conditions.  For example, an instance of the
         alarmValue object might be named alarmValue.8"
     INDEX { rmonAlarmIndex }
     ::= { rmonAlarmTable 1 }

 RmonAlarmEntry ::= SEQUENCE {
     rmonAlarmIndex                    Integer32,
     rmonAlarmInterval                 Integer32,
     rmonAlarmVariable                 OBJECT IDENTIFIER,
     rmonAlarmSampleType               INTEGER,
     rmonAlarmRisingThreshold          Integer32,
     rmonAlarmFallingThreshold         Integer32,
     rmonAlarmRisingEventIndex         Integer32,
     rmonAlarmFallingEventIndex        Integer32,
     rmonAlarmOwner                    OwnerString,
     rmonAlarmStatus                   RmonStatus
}

 rmonAlarmIndex OBJECT-TYPE
     SYNTAX     Integer32 (1..65535)
     MAX-ACCESS read-only
     STATUS     current
     DESCRIPTION
         "An index that uniquely identifies an entry in the
         alarm table.  Each such entry defines a
         diagnostic sample at a particular interval
         for an object on the device."
     ::= { rmonAlarmEntry 1 }

 rmonAlarmInterval OBJECT-TYPE
     SYNTAX     Integer32
     UNITS      "Seconds"
     MAX-ACCESS read-create
     STATUS     current
     DESCRIPTION
         "The interval in seconds over which the data is
         sampled and compared with the rising and falling
         thresholds.  When setting this variable, care
         should be taken in the case of deltaValue
         sampling - the interval should be set short enough
         that the sampled variable is very unlikely to
         increase or decrease by more than 2^31 - 1 during
         a single sampling interval.

         This object may not be modified if the associated
         alarmStatus object is equal to valid(1)."
     ::= { rmonAlarmEntry 2 }

 rmonAlarmVariable OBJECT-TYPE
     SYNTAX     OBJECT IDENTIFIER
     MAX-ACCESS read-create
     STATUS     current
     DESCRIPTION
         "The object identifier of the particular variable to be
         sampled.  Only variables that resolve to an ASN.1 primitive
         type of INTEGER (INTEGER, Integer32, Counter32, Counter64,
         Gauge, or TimeTicks) may be sampled.

         Because SNMP access control is articulated entirely
         in terms of the contents of MIB views, no access
         control mechanism exists that can restrict the value of
         this object to identify only those objects that exist
         in a particular MIB view.  Because there is thus no
         acceptable means of restricting the read access that
         could be obtained through the alarm mechanism, the
         probe must only grant write access to this object in

         those views that have read access to all objects on
         the probe.

         During a set operation, if the supplied variable name is
         not available in the selected MIB view, a badValue error
         must be returned.  If at any time the variable name of
         an established alarmEntry is no longer available in the
         selected MIB view, the probe must change the status of
         this alarmEntry to invalid(4).

         This object may not be modified if the associated
         alarmStatus object is equal to valid(1)."
     ::= { rmonAlarmEntry 3 }

 rmonAlarmSampleType OBJECT-TYPE
     SYNTAX     INTEGER {
                  absoluteValue(1),
                  deltaValue(2)
                }
     MAX-ACCESS read-create
     STATUS     current
     DESCRIPTION
         "The method of sampling the selected variable and
         calculating the value to be compared against the
         thresholds.  If the value of this object is
         absoluteValue(1), the value of the selected variable
         will be compared directly with the thresholds at the
         end of the sampling interval.  If the value of this
         object is deltaValue(2), the value of the selected
         variable at the last sample will be subtracted from
         the current value, and the difference compared with
         the thresholds.

         This object may not be modified if the associated
         alarmStatus object is equal to valid(1)."
     ::= { rmonAlarmEntry 4 }

 rmonAlarmRisingThreshold OBJECT-TYPE
     SYNTAX     Integer32
     MAX-ACCESS read-create
     STATUS     current
     DESCRIPTION
         "A threshold for the sampled statistic.  When the current
         sampled value is greater than or equal to this threshold,
         and the value at the last sampling interval was less than
         this threshold, a single event will be generated.
         A single event will also be generated if the first
         sample after this entry becomes valid is greater than or
         equal to this threshold and the associated
         alarmStartupAlarm is equal to risingAlarm(1) or
         risingOrFallingAlarm(3).

         After a rising event is generated, another such event

         will not be generated until the sampled value
         falls below this threshold and reaches the
         alarmFallingThreshold.

         This object may not be modified if the associated
         alarmStatus object is equal to valid(1)."
     ::= { rmonAlarmEntry 5 }

 rmonAlarmFallingThreshold OBJECT-TYPE
     SYNTAX     Integer32
     MAX-ACCESS read-create
     STATUS     current
     DESCRIPTION
         "A threshold for the sampled statistic.  When the current
         sampled value is less than or equal to this threshold,
         and the value at the last sampling interval was greater than
         this threshold, a single event will be generated.
         A single event will also be generated if the first
         sample after this entry becomes valid is less than or
         equal to this threshold and the associated
         alarmStartupAlarm is equal to fallingAlarm(2) or
         risingOrFallingAlarm(3).

         After a falling event is generated, another such event
         will not be generated until the sampled value
         rises above this threshold and reaches the
         alarmRisingThreshold.

         This object may not be modified if the associated
         alarmStatus object is equal to valid(1)."
     ::= { rmonAlarmEntry 6 }

 rmonAlarmRisingEventIndex OBJECT-TYPE
     SYNTAX     Integer32 (0..65535)
     MAX-ACCESS read-create
     STATUS     current
     DESCRIPTION
         "The index of the eventEntry that is
         used when a rising threshold is crossed.  The
         eventEntry identified by a particular value of
         this index is the same as identified by the same value
         of the eventIndex object.  If there is no
         corresponding entry in the eventTable, then
         no association exists.  In particular, if this value
         is zero, no associated event will be generated, as
         zero is not a valid event index.

         This object may not be modified if the associated

         alarmStatus object is equal to valid(1)."
     ::= { rmonAlarmEntry 7 }

 rmonAlarmFallingEventIndex OBJECT-TYPE
     SYNTAX     Integer32 (0..65535)
     MAX-ACCESS read-create
     STATUS     current
     DESCRIPTION
         "The index of the eventEntry that is
         used when a falling threshold is crossed.  The
         eventEntry identified by a particular value of
         this index is the same as identified by the same value
         of the eventIndex object.  If there is no
         corresponding entry in the eventTable, then
         no association exists.  In particular, if this value
         is zero, no associated event will be generated, as
         zero is not a valid event index.

         This object may not be modified if the associated
         alarmStatus object is equal to valid(1)."
     ::= { rmonAlarmEntry 8 }

 rmonAlarmOwner OBJECT-TYPE
     SYNTAX     OwnerString
     MAX-ACCESS read-create
     STATUS     current
     DESCRIPTION
         "The entity that configured this entry and is therefore
         using the resources assigned to it."
     ::= { rmonAlarmEntry 9 }

 rmonAlarmStatus OBJECT-TYPE
     SYNTAX     RmonStatus
     MAX-ACCESS read-create
     STATUS     current
     DESCRIPTION
         "The status of this alarm entry."
     ::= { rmonAlarmEntry 10 }

 -- The Event Group

 -- Implementation of the Event group is optional.
 -- Consult the MODULE-COMPLIANCE macro for the authoritative
 -- conformance information for this MIB.
 --
 -- The Event group controls the generation and notification
 -- of events from this device.  Each entry in the eventTable
 -- describes the parameters of the event that can be triggered.
 -- Each event entry is fired by an associated condition located
 -- elsewhere in the MIB.  An event entry may also be associated
 -- with a function elsewhere in the MIB that will be executed
 -- when the event is generated.  For example, a channel may
 -- be turned on or off by the firing of an event.
 --
 -- Each eventEntry may optionally specify that a log entry
 -- be created on its behalf whenever the event occurs.
 -- Each entry may also specify that notification should
 -- occur by way of SNMP trap messages.  In this case, the
 -- community for the trap message is given in the associated
 -- eventCommunity object.  The enterprise and specific trap
 -- fields of the trap are determined by the condition that
 -- triggered the event.  Two traps are defined: risingAlarm and
 -- fallingAlarm.  If the eventTable is triggered by a condition
 -- specified elsewhere, the enterprise and specific trap fields
 -- must be specified for traps generated for that condition.

 rmonEventTable OBJECT-TYPE
     SYNTAX     SEQUENCE OF RmonEventEntry
     MAX-ACCESS not-accessible
     STATUS     current
     DESCRIPTION
         "A list of events to be generated."
     ::= { rmonEvent 1 }

 rmonEventEntry OBJECT-TYPE
     SYNTAX     RmonEventEntry
     MAX-ACCESS not-accessible
     STATUS     current
     DESCRIPTION
         "A set of parameters that describe an event to be generated
         when certain conditions are met.  As an example, an instance
         of the eventLastTimeSent object might be named
         eventLastTimeSent.6"
     INDEX { rmonEventIndex }
     ::= { rmonEventTable 1 }

 RmonEventEntry ::= SEQUENCE {
     rmonEventIndex          Integer32,
     rmonEventDescription    DisplayString,
     rmonEventType           INTEGER,
     rmonEventCommunity      OCTET STRING,
     rmonEventOwner          OwnerString,
     rmonEventStatus         RmonStatus
 }

 rmonEventIndex OBJECT-TYPE
     SYNTAX     Integer32 (1..65535)
     MAX-ACCESS read-only
     STATUS     current
     DESCRIPTION
         "An index that uniquely identifies an entry in the
         event table.  Each such entry defines one event that
         is to be generated when the appropriate conditions
         occur."
     ::= { rmonEventEntry 1 }

 rmonEventDescription OBJECT-TYPE
     SYNTAX     DisplayString (SIZE (0..127))
     MAX-ACCESS read-create
     STATUS     current
     DESCRIPTION
         "A comment describing this event entry."
     ::= { rmonEventEntry 2 }

 rmonEventType OBJECT-TYPE
     SYNTAX     INTEGER {
                  none(1),
                  log(2),
                  snmptrap(3),    -- send an SNMP trap
                  logandtrap(4)
                }
     MAX-ACCESS read-create
     STATUS     current
     DESCRIPTION
         "The type of notification that the probe will make
         about this event.  In the case of log, an entry is
         made in the log table for each event.  In the case of
         snmp-trap, an SNMP trap is sent to one or more
         management stations."
     ::= { rmonEventEntry 3 }

 rmonEventCommunity OBJECT-TYPE
     SYNTAX     OCTET STRING (SIZE (0..127))
     MAX-ACCESS read-create
     STATUS     current
     DESCRIPTION
         "If an SNMP trap is to be sent, it will be sent to
         the SNMP community specified by this octet string."
     ::= { rmonEventEntry 4 }

 rmonEventOwner OBJECT-TYPE
     SYNTAX     OwnerString
     MAX-ACCESS read-create
     STATUS     current
     DESCRIPTION
         "The entity that configured this entry and is therefore
         using the resources assigned to it.

         If this object contains a string starting with 'monitor'
         and has associated entries in the log table, all connected
         management stations should retrieve those log entries,
         as they may have significance to all management stations
         connected to this device"
     ::= { rmonEventEntry 5 }

 rmonEventStatus OBJECT-TYPE
     SYNTAX     RmonStatus
     MAX-ACCESS read-create
     STATUS     current
     DESCRIPTION
         "The status of this event entry.

         If this object is not equal to valid(1), all associated
         log entries shall be deleted by the agent."
     ::= { rmonEventEntry 6 }
                  

        -- ----------------------------------------------------------------
        -- The Neighbor Setting group
        -- ----------------------------------------------------------------

        neighborTable OBJECT-TYPE
            SYNTAX SEQUENCE OF NeighborEntry
            MAX-ACCESS not-accessible
            STATUS current
            DESCRIPTION
                "A list of the Neighbor Cache Table."
            ::= { companyNeighbor  1 }

        neighborEntry OBJECT-TYPE
            SYNTAX NeighborEntry
            MAX-ACCESS not-accessible
            STATUS current
            DESCRIPTION
                "A Neighbor cache entry containing the ifindex and ipv6 addr."
            INDEX { neighborIfindex, neighborIPv6Addr, neighborMACAddr}
            ::= { neighborTable 1 }

        NeighborEntry ::= SEQUENCE {
            neighborIfindex         INTEGER,
            neighborIPv6Addr        Ipv6Address,
            neighborMACAddr         MacAddress,
            neighborType            INTEGER,
            neighborCacheState      INTEGER,
            neighborActiveStatus    INTEGER,
            neighborRowStatus       RowStatus
        }

         neighborIfindex OBJECT-TYPE
           SYNTAX  INTEGER
           MAX-ACCESS read-only
           STATUS current
           DESCRIPTION
               "The interface index of the Neighbor entry."
           ::= { neighborEntry 1 }

        neighborIPv6Addr  OBJECT-TYPE
           SYNTAX      Ipv6Address
           MAX-ACCESS  read-only
           STATUS      current
           DESCRIPTION 
              "Allows the entry of an IP address that will be a Neighbor entry into
               the Neighbor Cache Table."
           ::= { neighborEntry 2 }

         neighborMACAddr OBJECT-TYPE
           SYNTAX MacAddress
           MAX-ACCESS read-only
           STATUS current
           DESCRIPTION
               "The MAC address associated of the Neighbor entry."
           ::= { neighborEntry 3 }

         neighborType OBJECT-TYPE
           SYNTAX  INTEGER {
                       static(1),
                       dynamic(2)
                   }
           MAX-ACCESS read-only
           STATUS current
           DESCRIPTION
               "The type associated of the Neighbor entry."
           ::= { neighborEntry 4 }

         neighborCacheState OBJECT-TYPE
           SYNTAX  INTEGER {
                       static(1),
                       reachable(2),
                       incomplete(3),
                       stale(4),
                       delay(5),
                       probe(6),
                       notinservice(7)
                   }
           MAX-ACCESS read-only
           STATUS current
           DESCRIPTION
               "The type associated of the Neighbor entry."
           ::= { neighborEntry 5 }

         neighborActiveStatus OBJECT-TYPE
           SYNTAX  INTEGER {
                       active(1),
                       inactive(2)
                   }
           MAX-ACCESS read-only
           STATUS current
           DESCRIPTION
               "The active status of the Neighbor entry."
           ::= { neighborEntry 6 }

         neighborRowStatus OBJECT-TYPE
            SYNTAX     RowStatus
            MAX-ACCESS read-write
            STATUS     current
            DESCRIPTION
                "The status of an entry in the Neighbor Cache Table.  Only a subset
                 of the rowstatus variables (active, createAndGo, destroy) are available."
            ::= { neighborEntry 7 }


        dhcpv6RelayControl                   OBJECT IDENTIFIER ::= { companyDHCPv6Relay 1 }
        dhcpv6RelayManagement                OBJECT IDENTIFIER ::= { companyDHCPv6Relay 2 }
        dhcpv6RelayOption37                  OBJECT IDENTIFIER ::= { companyDHCPv6Relay 3 }
        dhcpv6RelayOption38                  OBJECT IDENTIFIER ::= { companyDHCPv6Relay 4 }
        dhcpv6RelayOption18                  OBJECT IDENTIFIER ::= { companyDHCPv6Relay 5 }
        -- ----------------------------------------------------------
		-- The DHCPv6 Relay
		-- ----------------------------------------------------------

		-- The DHCPv6 Relay Control

            dhcpv6RelayState OBJECT-TYPE
                SYNTAX  INTEGER {
                    enabled(1),
                    disabled(2)
                }
                MAX-ACCESS  read-write
                STATUS  current
                DESCRIPTION
                    "This object indicates DHCPv6 relay function is enabled or disabled."
            ::= { dhcpv6RelayControl 1 }

            dhcpv6RelayHopCount OBJECT-TYPE
                SYNTAX  INTEGER (1..16)
                MAX-ACCESS  read-write
                STATUS  current
                DESCRIPTION
                    "This object indicates the maximum number of router hops that the DHCPv6 packets can cross."
            ::= { dhcpv6RelayControl 2 }


		-- The DHCPv6 Relay Management
		-- The DHCPv6 Relay Interface Settings Table

            dhcpv6RelayInterfaceSettingsTable OBJECT-TYPE
                SYNTAX  SEQUENCE OF DHCPv6RelayInterfaceSettings
                MAX-ACCESS  not-accessible
                STATUS  current
                DESCRIPTION
                    "This table indicates the IP address as a destination to forward (relay) DHCP packets to."
            ::= { dhcpv6RelayManagement 1 }

            dhcpv6RelayInterfaceSettingsEntry OBJECT-TYPE
                SYNTAX  DHCPv6RelayInterfaceSettings
                MAX-ACCESS  not-accessible
                STATUS  current
                DESCRIPTION
                    "A list of information indicates the IP address as a destination to forward (relay) DHCP packets to."
                INDEX  { dhcpv6RelayInterface,  dhcpv6RelayServerIP}
            ::= { dhcpv6RelayInterfaceSettingsTable 1 }

            DHCPv6RelayInterfaceSettings ::=
                SEQUENCE {
                    dhcpv6RelayInterface
                        DisplayString,
                    dhcpv6RelayServerIP
                        Ipv6Address,
                    dhcpv6RelayInterfaceSettingsRowStatus
                        RowStatus
                }
            dhcpv6RelayInterface OBJECT-TYPE
                SYNTAX  DisplayString (SIZE(0..12))
                MAX-ACCESS  read-only
                STATUS  current
                DESCRIPTION
                    "This object indicates the maximum number of router hops that the DHCPv6 packets can cross."
            ::= { dhcpv6RelayInterfaceSettingsEntry 1 }
            
            dhcpv6RelayServerIP OBJECT-TYPE
                SYNTAX Ipv6Address
                MAX-ACCESS  read-only
                STATUS current
                DESCRIPTION
                    "This object indicates the DHCP server IP address."
            ::= { dhcpv6RelayInterfaceSettingsEntry 2 }

            dhcpv6RelayInterfaceSettingsRowStatus OBJECT-TYPE
                SYNTAX  RowStatus
                MAX-ACCESS  read-create
                STATUS  current
                DESCRIPTION
                    "This object indicates the status of this entry."
            ::= { dhcpv6RelayInterfaceSettingsEntry 99 }


		-- The DHCPv6 Relay Option37

            dhcpv6RelayOption37State OBJECT-TYPE
                SYNTAX  INTEGER {
                    disabled(0),
                    enabled(1)
                }
                MAX-ACCESS  read-write
                STATUS  current
                DESCRIPTION
                    "This object indicates DHCPv6 relay option 37 function is enabled or disabled."
            ::= { dhcpv6RelayOption37 1 }

            dhcpv6RelayOption37CheckState OBJECT-TYPE
                SYNTAX  INTEGER {
                    disabled(0),
                    enabled(1)
                }
                MAX-ACCESS  read-write
                STATUS  current
                DESCRIPTION
                    "This object indicates DHCPv6 relay option 37 Check function is enabled or disabled."
            ::= { dhcpv6RelayOption37 2 }

--            dhcpv6RelayOption37Policy OBJECT-TYPE
--                SYNTAX  INTEGER {
--                    replace(1),
--                    drop(2),
--                    keep(3)
--                }
--                MAX-ACCESS  read-write
--                STATUS  current
--                DESCRIPTION
--                    "This object indicates DHCPv6 relay option 37 policy."
--            ::= { dhcpv6RelayOption37 3 }

	        dhcpv6RelayOption37RemoteIDType OBJECT-TYPE
                SYNTAX  INTEGER {
                    default(0),
                    cid-with-user-define(1),
                    user-define(2)
                }
                MAX-ACCESS  read-write
                STATUS  current
                DESCRIPTION
                    "This object indicates the type of remote ID."
            ::= { dhcpv6RelayOption37 3 }

	        dhcpv6RelayOption37RemoteID OBJECT-TYPE
                SYNTAX  DisplayString
                MAX-ACCESS  read-write
                STATUS  current
                DESCRIPTION
                    "This object displays the current remote ID of the device.
                    If RemoteIDType is set to default, the value will be the MAC address of the device,
                    and this object cannot be modified.
                    If RemoteIDType is set to user-defined, a new value can be written to this object."
            ::= { dhcpv6RelayOption37 4 }
            

    dhcpv6RelayOpt38Table     OBJECT-TYPE
        SYNTAX SEQUENCE OF Dhcpv6RelayOpt38Entry
        MAX-ACCESS not-accessible
        STATUS current
        DESCRIPTION
            "A table to control port security features of the device."
        ::= { dhcpv6RelayOption38 1 }
        
    dhcpv6RelayOpt38Entry OBJECT-TYPE
        SYNTAX Dhcpv6RelayOpt38Entry
        MAX-ACCESS not-accessible
        STATUS current
        DESCRIPTION
            "An entry appears in port security table for each interface 
 	        in the system."
        INDEX { dhcpv6RelayOpt38PortIndex }
        ::= { dhcpv6RelayOpt38Table 1 }
  
    Dhcpv6RelayOpt38Entry ::= 
           SEQUENCE { 
              dhcpv6RelayOpt38PortIndex 
                 Integer32, 
              dhcpv6RelayOpt38PortState 
                 INTEGER, 
              dhcpv6RelayOpt38PortType 
                 INTEGER, 
              dhcpv6RelayOpt38PortID 
                 DisplayString             
          }
        
               
         dhcpv6RelayOpt38PortIndex OBJECT-TYPE 
           SYNTAX      Integer32 
           MAX-ACCESS  read-only 
           STATUS      current 
           DESCRIPTION 
              "The interface index for which the configuration in this 
               entry applies."
           ::= { dhcpv6RelayOpt38Entry 1 }
            
        
         dhcpv6RelayOpt38PortState OBJECT-TYPE
           SYNTAX INTEGER  {
        		  disabled (0), enabled (1)
            }
           MAX-ACCESS  read-write
           STATUS      current
           DESCRIPTION
              "Enable / disable option 38 port state."
        
           ::= { dhcpv6RelayOpt38Entry 2 }
        
        
        dhcpv6RelayOpt38PortType OBJECT-TYPE 
           SYNTAX INTEGER  {
        		  default (0), user-defined (1)
            }
           MAX-ACCESS  read-write 
           STATUS      current 
           DESCRIPTION 
              "Configure option 38 port Type."
        
           ::= {dhcpv6RelayOpt38Entry 3}

        dhcpv6RelayOpt38PortID OBJECT-TYPE 
           SYNTAX      DisplayString
           MAX-ACCESS  read-write 
           STATUS      current 
           DESCRIPTION 
              "Configure option 38 port ID. Only works when type is user-defined"
        
           ::= {dhcpv6RelayOpt38Entry 4}
           
		-- The DHCPv6 Relay Option18

            dhcpv6RelayOption18State OBJECT-TYPE
                SYNTAX  INTEGER {
                    disabled(0),
                    enabled(1)
                }
                MAX-ACCESS  read-write
                STATUS  current
                DESCRIPTION
                    "This object indicates DHCPv6 relay option 18 function is enabled or disabled."
            ::= { dhcpv6RelayOption18 1 }

            dhcpv6RelayOption18CheckState OBJECT-TYPE
                SYNTAX  INTEGER {
                    disabled(0),
                    enabled(1)
                }
                MAX-ACCESS  read-write
                STATUS  current
                DESCRIPTION
                    "This object indicates DHCPv6 relay option 18 Check function is enabled or disabled."
            ::= { dhcpv6RelayOption18 2 }

	        dhcpv6RelayOption18InterfaceIDType OBJECT-TYPE
                SYNTAX  INTEGER {
                    default(0),
                    cid(1),
                    vendor1(2)
                }
                MAX-ACCESS  read-write
                STATUS  current
                DESCRIPTION
                    "This object indicates the type of Interface ID."
            ::= { dhcpv6RelayOption18 3 }
           
    -- -----------------------------------------------------------------
    -- 1. MAC-based Access Control Settings
    -- -----------------------------------------------------------------
    macBasedCtrlGroup   OBJECT IDENTIFIER ::= { companyMacAuthGroup 1 }
    --------------------------------------------

    macBasedCtrlState   OBJECT-TYPE
        SYNTAX          INTEGER {
                            enabled(1),
                            disabled(2)
                            }
        MAX-ACCESS 	    read-write
        STATUS          current
        DESCRIPTION
        "Enable/Disable MAC-based Access Control Global Settings."
        ::= { macBasedCtrlGroup 1 }

    macBasedMethod      OBJECT-TYPE 
        SYNTAX          INTEGER {
                          radius(1),
                          local(2)
                       }
        MAX-ACCESS  read-write 
        STATUS      current 
        DESCRIPTION 
        "Select MAC-based Access Control Methods."
        DEFVAL  { radius }
        ::= { macBasedCtrlGroup 2 }

    macBasedRadiusPassword      OBJECT-TYPE
        SYNTAX                  DisplayString (SIZE(1..32))
        MAX-ACCESS              read-write
        STATUS                  current
        DESCRIPTION
        "Set the password about the method Mac-Based Authentication, 
         the maximum length are 32 chars."
        ::=  { macBasedCtrlGroup 3 }

    macBasedRadiusAuthStatus    OBJECT-TYPE
        SYNTAX                  INTEGER   {
                                    enable(1),    
                                    disable(2)
                                }
        MAX-ACCESS              read-create
        STATUS                  current
        DESCRIPTION
        "The state of Radius Authorization. "
        ::= { macBasedCtrlGroup 4 }

    macBasedLocalAuthStatus    OBJECT-TYPE
        SYNTAX                 INTEGER   {
                                  enable(1),    
                                  disable(2)
                               }
        MAX-ACCESS             read-create
        STATUS                 current
        DESCRIPTION
        "The state of Local Authorization. "
        ::= { macBasedCtrlGroup 5 }

    macBasedTrapStatus    OBJECT-TYPE
        SYNTAX            INTEGER   {
                            enable(1),    
                            disable(2)
                          }
        MAX-ACCESS        read-create
        STATUS            current
        DESCRIPTION
        "The state of Trap of MAC-based Authorization."
        ::= { macBasedCtrlGroup 6 }

    macBasedLogStatus    OBJECT-TYPE
        SYNTAX           INTEGER   {
                              enable(1),    
                              disable(2)
                         }
        MAX-ACCESS       read-create
        STATUS           current
        DESCRIPTION
        ""
        ::= { macBasedCtrlGroup 7 }

    macBasedMaxUsr    OBJECT-TYPE
        SYNTAX        Integer32 (1..1000)
        MAX-ACCESS    read-write
        STATUS        current
        DESCRIPTION
        ""  
        DEFVAL  { 128 }
        ::= { macBasedCtrlGroup 8 }

    macBasedPortCtrlTable   OBJECT-TYPE 
        SYNTAX              SEQUENCE OF MacBasedPortCtrlEntry
        MAX-ACCESS          not-accessible 
        STATUS              current 
        DESCRIPTION 
        ""
           ::= { macBasedCtrlGroup 11 }
        
    macBasedPortCtrlEntry   OBJECT-TYPE 
           SYNTAX           MacBasedPortCtrlEntry
           MAX-ACCESS       not-accessible 
           STATUS           current 
           DESCRIPTION 
           ""
           INDEX { macBasedPortCtrlIndex }
           ::= { macBasedPortCtrlTable 1 }

    MacBasedPortCtrlEntry ::= 
           SEQUENCE { 
              macBasedPortCtrlIndex          Integer32, 
              macBasedPortCtrlState          INTEGER, 
              macBasedPortCtrlAgingTime      Integer32,
              macBasedPortCtrlBlockTime      Integer32, 
              macBasedPortCtrlMaxUsr         Integer32
          }

    macBasedPortCtrlIndex   OBJECT-TYPE 
        SYNTAX              Integer32 (1..65535)
        MAX-ACCESS          read-only 
        STATUS              current 
        DESCRIPTION 
        ""
        ::= { macBasedPortCtrlEntry 1 }

    macBasedPortCtrlState   OBJECT-TYPE
        SYNTAX              INTEGER   {
                                enable(1),    
                                disable(2)
                            }
        MAX-ACCESS          read-create
        STATUS              current
        DESCRIPTION
        ""
        ::= { macBasedPortCtrlEntry 2 }

    macBasedPortCtrlAgingTime   OBJECT-TYPE
        SYNTAX                  Integer32 (1..1440)
        MAX-ACCESS              read-write
        STATUS                  current
        DESCRIPTION
        ""  
        ::= { macBasedPortCtrlEntry 3 }

    macBasedPortCtrlBlockTime   OBJECT-TYPE
        SYNTAX                  Integer32 (0..300)
        MAX-ACCESS              read-write
        STATUS                  current
        DESCRIPTION
        ""  
        ::= { macBasedPortCtrlEntry 4 }

    macBasedPortCtrlMaxUsr      OBJECT-TYPE
        SYNTAX                  Integer32 (1..1000)
        MAX-ACCESS              read-write
        STATUS                  current
        DESCRIPTION
        ""  
        DEFVAL  { 128 }
        ::= { macBasedPortCtrlEntry 5 }

    -- -----------------------------------------------------------------
    -- 2. MAC-based Access Control Local Settings 
    -- -----------------------------------------------------------------
    macBasedCtrlLocalGroup   OBJECT IDENTIFIER ::= { companyMacAuthGroup 2 }
    --------------------------------------------
 
    macBasedCtrlLocalTable      OBJECT-TYPE 
        SYNTAX                  SEQUENCE OF MacBasedCtrlLocalEntry
        MAX-ACCESS              not-accessible 
        STATUS                  current 
        DESCRIPTION 
        ""
           ::= { macBasedCtrlLocalGroup 1 }
        
    macBasedCtrlLocalEntry      OBJECT-TYPE 
           SYNTAX               MacBasedCtrlLocalEntry
           MAX-ACCESS           not-accessible 
           STATUS               current 
           DESCRIPTION 
           ""
           INDEX { macBasedCtrlLocalMacAddress, macBasedCtrlLocalVID }
           ::= { macBasedCtrlLocalTable 1 }

    MacBasedCtrlLocalEntry ::= 
           SEQUENCE { 
              macBasedCtrlLocalMacAddress    MacAddress, 
              macBasedCtrlLocalVID           INTEGER, 
              macBasedCtrlLocalVlanName      SnmpAdminString,
              macBasedCtrlLocalRowStatus     RowStatus 
           }

    macBasedCtrlLocalMacAddress     OBJECT-TYPE
        SYNTAX                      MacAddress
        MAX-ACCESS                  read-only
        STATUS                      current
        DESCRIPTION
        "The MacAddress of the MAC-based Access Control Local Setting Table."
        ::= { macBasedCtrlLocalEntry 1 }

    macBasedCtrlLocalVID        OBJECT-TYPE
        SYNTAX                  INTEGER
        MAX-ACCESS              read-only
        STATUS                  current
        DESCRIPTION
        "The VLAN ID of the MAC-based Access Control Local Setting entry."
        ::= { macBasedCtrlLocalEntry 2 }

    macBasedCtrlLocalVlanName       OBJECT-TYPE
        SYNTAX                      SnmpAdminString (SIZE (0..20))
        MAX-ACCESS                  read-only
        STATUS                      current
        DESCRIPTION
        "An administratively assigned string, which may be used
         to identify the VLAN."
        REFERENCE
        "IEEE 802.1Q/D11 Section 12.10.2.1"
        ::= { macBasedCtrlLocalEntry 3 }

    macBasedCtrlLocalRowStatus    OBJECT-TYPE
        SYNTAX                    RowStatus
        MAX-ACCESS                read-write
        STATUS                    current
        DESCRIPTION
        "The  Row status of an entry in the MAC-based Access Control Local Setting Table.
         Only a subset of the rowstatus variables (active, createAndGo, destroy) are available"
        ::= { macBasedCtrlLocalEntry 4 }
   
    -- -----------------------------------------------------------------
    -- 3. MAC-based Access Control Authentication State 
    -- -----------------------------------------------------------------
    macBasedCtrlAuthGroup   OBJECT IDENTIFIER ::= { companyMacAuthGroup 3 }
    --------------------------------------------

    macBasedCtrlAuthTable   OBJECT-TYPE 
        SYNTAX              SEQUENCE OF MacBasedCtrlAuthEntry
        MAX-ACCESS          not-accessible 
        STATUS              current 
        DESCRIPTION 
        ""
           ::= { macBasedCtrlAuthGroup 1 }
        
    macBasedCtrlAuthEntry   OBJECT-TYPE 
           SYNTAX           MacBasedCtrlAuthEntry
           MAX-ACCESS       not-accessible 
           STATUS           current 
           DESCRIPTION 
           ""
           INDEX { macBasedCtrlAuthPort, macBasedCtrlAuthMacAddress, macBasedCtrlAuthRxVID }
           ::= { macBasedCtrlAuthTable 1 }

    MacBasedCtrlAuthEntry ::= 
           SEQUENCE {
              macBasedCtrlAuthPort          Integer32,
              macBasedCtrlAuthMacAddress    MacAddress,
              macBasedCtrlAuthRxVID         INTEGER,
              macBasedCtrlAuthState         INTEGER,
              macBasedCtrlAuthVID           INTEGER,
              macBasedCtrlAuthPriority      INTEGER,
              macBasedCtrlAuthAgingTime     INTEGER,
              macBasedCtrlAuthBlockTime     INTEGER
           }

    macBasedCtrlAuthPort        OBJECT-TYPE 
        SYNTAX                  Integer32 
        MAX-ACCESS                  read-only
        STATUS                      current
        DESCRIPTION
        ""
        ::= { macBasedCtrlAuthEntry 1 }

    macBasedCtrlAuthMacAddress      OBJECT-TYPE
        SYNTAX                      MacAddress
        MAX-ACCESS              read-only
        STATUS                  current
        DESCRIPTION
        "The MacAddress of the MAC-based Access Control Authentication State Table."
        ::= { macBasedCtrlAuthEntry 2 }

    macBasedCtrlAuthRxVID       OBJECT-TYPE
        SYNTAX                  INTEGER
        MAX-ACCESS              read-only 
        STATUS                  current 
        DESCRIPTION 
        ""
        ::= { macBasedCtrlAuthEntry 3 }

    macBasedCtrlAuthState   OBJECT-TYPE
        SYNTAX              INTEGER {
                                authenticating(1), 
                                authenticated(2), 
                                blocked(3) 
                            }
        MAX-ACCESS read-only
        STATUS current
        DESCRIPTION
        ""
        ::= { macBasedCtrlAuthEntry 4 }

    macBasedCtrlAuthVID     OBJECT-TYPE
        SYNTAX              INTEGER
        MAX-ACCESS          read-only
        STATUS              current
        DESCRIPTION
        ""
        ::= { macBasedCtrlAuthEntry 5 }

    macBasedCtrlAuthPriority    OBJECT-TYPE
        SYNTAX                  INTEGER
        MAX-ACCESS              read-only
        STATUS                  current
        DESCRIPTION
        ""
        ::= { macBasedCtrlAuthEntry 6 }

    macBasedCtrlAuthAgingTime   OBJECT-TYPE
        SYNTAX                  INTEGER
        MAX-ACCESS              read-only
        STATUS                  current
        DESCRIPTION
        ""
        ::= { macBasedCtrlAuthEntry 7 }

    macBasedCtrlAuthBlockTime   OBJECT-TYPE
        SYNTAX                  INTEGER
        MAX-ACCESS              read-only
        STATUS                  current
        DESCRIPTION
        ""
        ::= { macBasedCtrlAuthEntry 8 }

-- -------------------------------------------------------------
-- groups in the WAC Global Setting Auth MIB
-- -------------------------------------------------------------
	wacAuthCtrl  OBJECT IDENTIFIER ::= { companyWACAuthGroup 1 }
-- -----------------------------------------------------------------------------
-- wacAuthCtrl
-- -----------------------------------------------------------------------------

    wacStatus OBJECT-TYPE
        SYNTAX INTEGER {
                   enabled(1),
                   disabled(2)
        }
        MAX-ACCESS 			read-write
        STATUS              current
        DESCRIPTION
        "Enable/Disable WAC Global Settings"
        ::= { wacAuthCtrl 1 }

    wacVirtualIPv4  OBJECT-TYPE
       SYNTAX      IpAddress
       MAX-ACCESS  read-write
       STATUS      current
       DESCRIPTION 
          "Virtual IPv4"
       ::= { wacAuthCtrl 2 }

    wacVirtualIPv6  OBJECT-TYPE
       SYNTAX      Ipv6Address
       MAX-ACCESS  read-write
       STATUS      current
       DESCRIPTION 
          "Virtual IPv6"
       ::= { wacAuthCtrl 3 }
       
    wacRedirPath  OBJECT-TYPE
       SYNTAX      OCTET STRING
       MAX-ACCESS  read-write
       STATUS      current
       DESCRIPTION 
          "Redirection Path"
       ::= { wacAuthCtrl 4 }       

    wacClrRedirPath OBJECT-TYPE
        SYNTAX INTEGER {
                   yes(1),
                   no(2)
        }
        MAX-ACCESS 			read-write
        STATUS              current
        DESCRIPTION
        "yes/no WAC Clear Redirection path Settings"
        ::= { wacAuthCtrl 5 }

    wacRadiusAuth OBJECT-TYPE
        SYNTAX INTEGER {
                   enabled(1),
                   disabled(2)
        }
        MAX-ACCESS 			read-write
        STATUS              current
        DESCRIPTION
        "Enable/Disable WAC RADIUS AUTH Settings"
        ::= { wacAuthCtrl 6 }

    waclocalAuth OBJECT-TYPE
        SYNTAX INTEGER {
                   enabled(1),
                   disabled(2)
        }
        MAX-ACCESS 			read-write
        STATUS              current
        DESCRIPTION
        "Enable/Disable WAC LOCAL AUTH Settings"
        ::= { wacAuthCtrl 7 }

    wacAuthMethod OBJECT-TYPE
        SYNTAX INTEGER {
                   radius(1),
                   local(2)
        }
        MAX-ACCESS 			read-write
        STATUS              current
        DESCRIPTION
        "Enable/Disable WAC Auth Method Settings"
        ::= { wacAuthCtrl 8 }

    wacAuthPortMethod OBJECT-TYPE
        SYNTAX INTEGER {
                   http(1),
                   https(2)
        }
        MAX-ACCESS 			read-write
        STATUS              current
        DESCRIPTION
        "Authorization Port Method"
        ::= { wacAuthCtrl 9 }

    wacAuthPort OBJECT-TYPE
        SYNTAX                   INTEGER (1..65535)
        MAX-ACCESS 			read-write
        STATUS              current
        DESCRIPTION
        "HTTP(s) Port."
        ::= { wacAuthCtrl 10 }

-- -------------------------------------------------------------
-- groups in the User Settings Control MIB
-- -------------------------------------------------------------
	wacUsrCtrl  OBJECT IDENTIFIER ::= { companyWACAuthGroup 2 }
-- -----------------------------------------------------------------------------
-- wacUsrCtrl
-- -----------------------------------------------------------------------------

    wacUsrCtrlTable OBJECT-TYPE
        SYNTAX SEQUENCE OF WACUsrCtrlEntry
        MAX-ACCESS 			not-accessible
        STATUS              current
        DESCRIPTION
        "A table that contains the configuration objects for the
         Authenticator PAE associated with each port.
         An entry appears in this table for each port that may
         authenticate access to itself."
        ::= { wacUsrCtrl 1 }

    wacUsrCtrlEntry OBJECT-TYPE
        SYNTAX              WACUsrCtrlEntry
        MAX-ACCESS 			not-accessible
        STATUS              current
        DESCRIPTION
        "The configuration information for an Authenticator Port."
        INDEX { authUserName }
        ::= { wacUsrCtrlTable 1 }

    WACUsrCtrlEntry ::= SEQUENCE {
        authUserName                      SnmpAdminString,
        authUserVID                       INTEGER,        
        authUserPassword                  DisplayString,
        authUserStatus                    RowStatus
    }

    authUserName OBJECT-TYPE
        SYNTAX      SnmpAdminString (SIZE(1..15))
        MAX-ACCESS  read-only
        STATUS      current
        DESCRIPTION
            "The unique index value of a row in this table.

            This object is used to set 802.1X Local user name,
            The following characters are allowed to input:
            semicolon, question mark, space, and double quotation mark."
        ::= { wacUsrCtrlEntry 1 }

      authUserVID OBJECT-TYPE
        SYNTAX     INTEGER
        MAX-ACCESS  read-write
        STATUS      current
            DESCRIPTION
                "The ID of VLAN that you want this interface to be in. 
                It must be a exist vlan id."
            ::= { wacUsrCtrlEntry 2 }

    authUserPassword  OBJECT-TYPE
       SYNTAX      DisplayString (SIZE(1..15))
       MAX-ACCESS  read-write
       STATUS      current
       DESCRIPTION
          "This object is used to set 802.1X Local user Password,
          The following characters are allowed to input:
          semicolon, question mark, space, and double quotation mark."
       ::= { wacUsrCtrlEntry 3 }

    authUserStatus OBJECT-TYPE
        SYNTAX       RowStatus
        MAX-ACCESS   read-create
        STATUS       current
        DESCRIPTION
            "The status of this conceptual row in the swAuthUserTable.

            An entry in this table is not qualified for activation
            until instances of all corresponding columns have been
            initialized, either through default values, or through
            Set operations.  The swAuthUserName objects must be
            explicitly set."
        ::= { wacUsrCtrlEntry 4 }

-- -------------------------------------------------------------
-- groups in the Port Settings Control MIB
-- -------------------------------------------------------------
	wacPortCtrl  OBJECT IDENTIFIER ::= { companyWACAuthGroup 3 }
-- -----------------------------------------------------------------------------
-- wacPortCtrl
-- -----------------------------------------------------------------------------
    -- Port Control Table 
    
        wacPortCtrlTable OBJECT-TYPE 
           SYNTAX      SEQUENCE OF WACPortCtrlEntry
           MAX-ACCESS  not-accessible 
           STATUS      current 
           DESCRIPTION 
               "A table to control the port specific parameters of the device like speed,
                duplex mode, etc."
           ::= { wacPortCtrl 1 }
        
        wacPortCtrlEntry OBJECT-TYPE 
           SYNTAX      WACPortCtrlEntry
           MAX-ACCESS  not-accessible 
           STATUS      current 
           DESCRIPTION 
               "An entry appears in this table for each interface in the system.
           
               Index to the table is the interface index of the port."
        
           INDEX { wacPortCtrlIndex }
           ::= { wacPortCtrlTable 1 }
           
        WACPortCtrlEntry ::= 
           SEQUENCE { 
              wacPortCtrlIndex 
                 Integer32, 
              wacPortCtrlState
                 INTEGER, 
              wacPortCtrlAgetime
                 INTEGER,
              wacPortCtrlBlocktime
                 INTEGER
          }
        
        wacPortCtrlIndex OBJECT-TYPE 
           SYNTAX      Integer32 (1..65535)
           MAX-ACCESS  read-only 
           STATUS      current 
           DESCRIPTION 
              "Interface index of the port for the configuration
              in this entry applies."
           
           ::= { wacPortCtrlEntry 1 }

        wacPortCtrlState OBJECT-TYPE 
           SYNTAX      INTEGER {
                         enable     (1),
                         disable    (2)
                      }
           MAX-ACCESS  read-write 
           STATUS      current 
           DESCRIPTION 
              "Enables / disables flow control for the interface."
        
           ::= { wacPortCtrlEntry 2 }
        
        wacPortCtrlAgetime OBJECT-TYPE
            SYNTAX              INTEGER (1..65535)
            MAX-ACCESS 			read-write
            STATUS              current
            DESCRIPTION
            "Aging time"
            ::= { wacPortCtrlEntry 3 }
            
        wacPortCtrlBlocktime OBJECT-TYPE
            SYNTAX              INTEGER (1..65535)
            MAX-ACCESS 			read-write
            STATUS              current
            DESCRIPTION
            "Aging time"
            ::= { wacPortCtrlEntry 4 }

-- -------------------------------------------------------------
-- groups in the Authentication State Control MIB
-- -------------------------------------------------------------
	wacAuthState  OBJECT IDENTIFIER ::= { companyWACAuthGroup 4 }
-- -----------------------------------------------------------------------------
-- wacAuthState for IPv4(and IPv6)
-- -----------------------------------------------------------------------------
        wacAuthStateTable OBJECT-TYPE
            SYNTAX SEQUENCE OF WACAuthStateEntry
            MAX-ACCESS not-accessible
            STATUS current
            DESCRIPTION
                "A list of the Auth States"
            ::= { wacAuthState 1 }

        wacAuthStateEntry OBJECT-TYPE
            SYNTAX WACAuthStateEntry
            MAX-ACCESS not-accessible
            STATUS current
            DESCRIPTION
                "A Auth State entry containing the mac and forwarding port."
            INDEX {wacAuthStatePort, wacAuthStateMac, wacAuthStateRXVID}
            ::= { wacAuthStateTable 1 }

        WACAuthStateEntry ::= SEQUENCE {
            wacAuthStatePort          INTEGER,
            wacAuthStateMac           MacAddress,
            wacAuthStateRXVID     	INTEGER,
            wacAuthStateflag 	        INTEGER,        
            wacAuthStateVID     	    INTEGER,
            wacAuthAssignPriority  	INTEGER,
            wacAuthStateAgetime       INTEGER,
            wacAuthStateRowStatus     RowStatus
        }

        wacAuthStatePort OBJECT-TYPE
            SYNTAX INTEGER
            MAX-ACCESS read-only
            STATUS current
            DESCRIPTION
                "The auth port state of the Auth State entry."
            ::= { wacAuthStateEntry 1 }

         wacAuthStateMac OBJECT-TYPE
           SYNTAX MacAddress
           MAX-ACCESS read-only
           STATUS current
           DESCRIPTION
               "The auth state mac of the Auth State entry."
           ::= { wacAuthStateEntry 2 }

        wacAuthStateRXVID OBJECT-TYPE
            SYNTAX INTEGER
            MAX-ACCESS read-only
            STATUS current
            DESCRIPTION
                "The Rx VID of the Auth State entry."
            ::= { wacAuthStateEntry 3 }

        wacAuthStateflag OBJECT-TYPE
            SYNTAX INTEGER
            MAX-ACCESS read-only
            STATUS current
            DESCRIPTION
                "The auth state flag of the Auth State entry."
            ::= { wacAuthStateEntry 4 }

        wacAuthStateVID OBJECT-TYPE
            SYNTAX INTEGER
            MAX-ACCESS read-only
            STATUS current
            DESCRIPTION
                "The auth state VID of the Auth State entry."
            ::= { wacAuthStateEntry 5 }

        wacAuthAssignPriority OBJECT-TYPE
            SYNTAX INTEGER
            MAX-ACCESS read-only
            STATUS current
            DESCRIPTION
                "The auth assign priority of the Auth State entry."
            ::= { wacAuthStateEntry 6 }

        wacAuthStateAgetime OBJECT-TYPE
            SYNTAX INTEGER

            MAX-ACCESS read-only
            STATUS current
            DESCRIPTION
                "The auth state age time of the Auth State entry."
            ::= { wacAuthStateEntry 7 }
            
		wacAuthStateRowStatus OBJECT-TYPE
            SYNTAX RowStatus

            MAX-ACCESS read-only
            STATUS current
            DESCRIPTION
                "The auth state row status."
            ::= { wacAuthStateEntry 99 }

            
     
	-- ----------------------------------------------------------------------------
	-- The Vlan Mac Map Table
	-- ---------------------------------------------------------------------------- 
	 
	macBasedVlanTable OBJECT-TYPE 
	   SYNTAX      SEQUENCE OF MacBasedVlanEntry 
	   MAX-ACCESS  not-accessible 
	   STATUS      current 
	   DESCRIPTION 
	      "A table that contains information on Vlan-MAC address 
	      mapping." 
	   ::= { companyMacBasedVlan 1 } 
	 
	macBasedVlanEntry OBJECT-TYPE
	   SYNTAX      MacBasedVlanEntry
	   MAX-ACCESS  not-accessible 
	   STATUS      current 
	   DESCRIPTION 
	      "Entry that contains Vlan-MAC address mapping." 
	   INDEX { vlanMacMapIndex }
	   ::= { macBasedVlanTable 1 }
	    
        MacBasedVlanEntry ::=
            SEQUENCE {
                vlanMacMapIndex
                    Integer32,            
                vlanMacMapAddr
                    MacAddress,          
                vlanMacMapAddrMask
                    MacAddress,
                vlanMacMapVid
                    VlanIndex,
                vlanMacStatus
                    DisplayString,
                vlanMacType
                    DisplayString,
                vlanMacMapRowStatus
                    RowStatus
            }

	vlanMacMapIndex OBJECT-TYPE
       SYNTAX      Integer32 (1..128) 
       MAX-ACCESS  read-only 
       STATUS      current 
       DESCRIPTION 
        "Index of cmMacBasedVlanEntry. This object indicates the mac vlan entry for which 
        the configurations in cmMacBasedVlanEntry is to be done." 
   	   ::= { macBasedVlanEntry 1 }	

	vlanMacMapAddr OBJECT-TYPE
	   SYNTAX      MacAddress  
	   MAX-ACCESS  read-write 
	   STATUS      current 
	   DESCRIPTION 
	      "The Mac address for which the Vlan mapping is present in the entry." 
	      
	   ::= { macBasedVlanEntry 2 }
	vlanMacMapAddrMask OBJECT-TYPE
	   SYNTAX      MacAddress  
	   MAX-ACCESS  read-write 
	   STATUS      current 
	   DESCRIPTION 
	      "The Mac address for which the Vlan mapping is present in the entry." 
	   ::= { macBasedVlanEntry 3 }
	 
	vlanMacMapVid OBJECT-TYPE
	   SYNTAX      VlanIndex 
	   MAX-ACCESS  read-write 
	   STATUS      current 
	   DESCRIPTION 
	      "The Vlan to which the mac address of this entry is mapped to." 
	   ::= { macBasedVlanEntry 4 }
	 
	vlanMacStatus OBJECT-TYPE
	   SYNTAX      DisplayString 
	   MAX-ACCESS  read-only
	   STATUS      current 
	   DESCRIPTION 
	      "The status given to the mac-vlan entry." 
	   ::= { macBasedVlanEntry 5 }
	   
	vlanMacType OBJECT-TYPE
	   SYNTAX      DisplayString 
	   MAX-ACCESS  read-only
	   STATUS      current 
	   DESCRIPTION 
	      "The type given to the mac-vlan entry." 
	   ::= { macBasedVlanEntry 6 }

	 
	vlanMacMapRowStatus OBJECT-TYPE
	   SYNTAX      RowStatus 
	   MAX-ACCESS  read-write 
	   STATUS      current 
	   DESCRIPTION 
	      "The row status of the entry."  
	   ::= { macBasedVlanEntry 99 }
    
	macBasedVlanMethod OBJECT-TYPE 
       SYNTAX      INTEGER {
                    single(1),
                    range(2)
                   }
       MAX-ACCESS  read-write
       STATUS      current
	   DESCRIPTION 
	      "A method of Vlan-MAC address mapping." 
	   ::= { companyMacBasedVlan 2 } 


    -- ----------------------------------------------------------
		-- The sfpVendorInfoTable
		-- ----------------------------------------------------------
		
		
            sfpVendorInfoTable OBJECT-TYPE
                SYNTAX  SEQUENCE OF SfpVendorInfoEntry
                MAX-ACCESS  not-accessible
                STATUS  current
                DESCRIPTION
                    "This table indicates the IP address as a destination to forward (relay) DHCP packets to."
            ::= { companySfpVendorInfo 1 }

            sfpVendorInfoEntry OBJECT-TYPE
                SYNTAX  SfpVendorInfoEntry
                MAX-ACCESS  not-accessible
                STATUS  current
                DESCRIPTION
                    "A list of information indicates the IP address as a destination to forward (relay) DHCP packets to."
                INDEX  { sfpPortIndex }
            ::= { sfpVendorInfoTable 1 }

            SfpVendorInfoEntry ::= 
                   SEQUENCE { 
                      sfpPortIndex 
                         Integer32, 
                      sfpConnectorType 
                         DisplayString, 
                      sfpTranceiverCode
                         DisplayString, 
                      sfpBaudRate
                         DisplayString, 
                      sfpVendorName
                         DisplayString, 
                      sfpVendorOui
                         DisplayString, 
                      sfpVendorPn
                         DisplayString, 
                      sfpVendorRev
                         DisplayString, 
                      sfpWavelength
                         DisplayString, 
                      sfpVendorSn
                         DisplayString, 
                      sfpDateCode
                         DisplayString
                  }
            

                 sfpPortIndex     OBJECT-TYPE 
                   SYNTAX      Integer32 
                   MAX-ACCESS  read-only 
                   STATUS      current 
                   DESCRIPTION 
                      ""
                   ::= { sfpVendorInfoEntry 1 }

                sfpConnectorType OBJECT-TYPE 
                   SYNTAX      DisplayString
                   MAX-ACCESS  read-only 
                   STATUS      current 
                   DESCRIPTION 
                      ""
                   ::= {sfpVendorInfoEntry 2}

                sfpTranceiverCode OBJECT-TYPE 
                   SYNTAX      DisplayString
                   MAX-ACCESS  read-only 
                   STATUS      current 
                   DESCRIPTION 
                      ""
                   ::= {sfpVendorInfoEntry 3}

                sfpBaudRate OBJECT-TYPE 
                   SYNTAX      DisplayString
                   MAX-ACCESS  read-only 
                   STATUS      current 
                   DESCRIPTION 
                      ""
                   ::= {sfpVendorInfoEntry 4}

                sfpVendorName OBJECT-TYPE 
                   SYNTAX      DisplayString
                   MAX-ACCESS  read-only 
                   STATUS      current 
                   DESCRIPTION 
                      ""
                   ::= {sfpVendorInfoEntry 5}

                sfpVendorOui OBJECT-TYPE 
                   SYNTAX      DisplayString
                   MAX-ACCESS  read-only 
                   STATUS      current 
                   DESCRIPTION 
                      ""
                   ::= {sfpVendorInfoEntry 6}

                sfpVendorPn OBJECT-TYPE 
                   SYNTAX      DisplayString
                   MAX-ACCESS  read-only 
                   STATUS      current 
                   DESCRIPTION 
                      ""
                   ::= {sfpVendorInfoEntry 7}

                sfpVendorRev OBJECT-TYPE 
                   SYNTAX      DisplayString
                   MAX-ACCESS  read-only 
                   STATUS      current 
                   DESCRIPTION 
                      ""
                   ::= {sfpVendorInfoEntry 8}

                sfpWavelength OBJECT-TYPE 
                   SYNTAX      DisplayString
                   MAX-ACCESS  read-only 
                   STATUS      current 
                   DESCRIPTION 
                      ""
                   ::= {sfpVendorInfoEntry 9}

                sfpVendorSn OBJECT-TYPE 
                   SYNTAX      DisplayString
                   MAX-ACCESS  read-only 
                   STATUS      current 
                   DESCRIPTION 
                      ""
                   ::= {sfpVendorInfoEntry 10}

                sfpDateCode OBJECT-TYPE 
                   SYNTAX      DisplayString
                   MAX-ACCESS  read-only 
                   STATUS      current 
                   DESCRIPTION 
                      ""
                   ::= {sfpVendorInfoEntry 11}


-- --------------------------------------------------------------------------
    ddmCtrl	            OBJECT IDENTIFIER ::={companyDDM 1}
    ddmInfo	            OBJECT IDENTIFIER ::={companyDDM 2}
-- --------------------------------------------------------------------------
--  DdmCtrl
-- --------------------------------------------------------------------------

    ddmPowerUnit    OBJECT-TYPE
        SYNTAX  INTEGER {
                         mw(0),
                         dbm(1)
                        }
        MAX-ACCESS  read-write
        STATUS  current
        DESCRIPTION
            "This object indicates the TX/RX power global unit."
        DEFVAL{mw}
            ::= {ddmCtrl 1}
        		
--ddmActionMgmt
 
    ddmActionMgmtTable	OBJECT-TYPE
    		SYNTAX  SEQUENCE OF DdmActionMgmtEntry
    		MAX-ACCESS  not-accessible
        STATUS  obsolete
        DESCRIPTION
                "This table contains the configuration of the action taken 
                when any parameter exceeds its threshold."
            ::= {ddmCtrl 2}
          
    ddmActionMgmtEntry	OBJECT-TYPE
    		SYNTAX	DdmActionMgmtEntry
    		MAX-ACCESS  not-accessible
        STATUS  obsolete
        DESCRIPTION
          "This is an entry of the swDdmConfigActionTable."
        INDEX  {ddmActionPort }
          ::= {ddmActionMgmtTable 1}
    
    DdmActionMgmtEntry ::=
        SEQUENCE {
              ddmActionPort
                    INTEGER,
              ddmActionState
                    INTEGER,
              ddmActionShutdown
                    INTEGER
                 }  
                 
    ddmActionPort	OBJECT-TYPE
    		SYNTAX  INTEGER 
        MAX-ACCESS  read-only
        STATUS  current
        DESCRIPTION
            "This object indicates the port."
            ::= {ddmActionMgmtEntry 1}	
    
    
    ddmActionState OBJECT-TYPE
    		SYNTAX  INTEGER {
    					disable(0),
    					enable(1)
    					}
        MAX-ACCESS  read-write
        STATUS  obsolete
        DESCRIPTION
            "This object indicates the action type."
            ::= {ddmActionMgmtEntry 2} 
    
    ddmActionShutdown OBJECT-TYPE
    		SYNTAX  INTEGER {
    		            none(0),
    					alarm(1),
    					warning(2)
    					}
        MAX-ACCESS  read-write
        STATUS  obsolete
        DESCRIPTION
            "This object indicates the action type."
            ::= {ddmActionMgmtEntry 3} 
  

--ddmThresholdMgmt

    ddmThresholdMgmtTable	OBJECT-TYPE
    		SYNTAX  SEQUENCE OF DdmThresholdMgmtEntry
    		MAX-ACCESS  not-accessible
        STATUS  current
        DESCRIPTION
                "This table contains DDM temperature configuration information."
            ::= {ddmCtrl 3}
            
    ddmThresholdMgmtEntry OBJECT-TYPE
    		SYNTAX  DdmThresholdMgmtEntry
        MAX-ACCESS  not-accessible
        STATUS  current
        DESCRIPTION
          "This is an entry of the swDdmConfigThresholdTable."
        INDEX  {ddmThresholdPort ,ddmThresholdType}
          ::= {ddmThresholdMgmtTable 1}
    
    DdmThresholdMgmtEntry	::=
        SEQUENCE {
                  ddmThresholdPort
                      INTEGER,
                  ddmThresholdType
                      INTEGER,
                  ddmHighAlarm
                      DisplayString,
                  ddmLowAlarm
                      DisplayString,
                  ddmHighWarning
                      DisplayString,
                  ddmLowWarning
                      DisplayString
                  }
            
    ddmThresholdPort	OBJECT-TYPE
    		SYNTAX  INTEGER 
        MAX-ACCESS  read-only
        STATUS  current
        DESCRIPTION
            "This object indicates the port."
            ::= {ddmThresholdMgmtEntry 1}	
    
    ddmThresholdType	OBJECT-TYPE
    		SYNTAX	INTEGER{
                     	temperature(0),
                    	voltage(1),
                    	bias(2),
                    	txPower(3),
                    	rxPower(4)
                  }  
        MAX-ACCESS  read-only
        STATUS  current
        DESCRIPTION
            "This object indicates the threshold type."
            ::= {ddmThresholdMgmtEntry 2}  
            
    ddmHighAlarm	OBJECT-TYPE
    		SYNTAX  DisplayString
        MAX-ACCESS  read-write
        STATUS  current
        DESCRIPTION
            "This object indicates the high alarm threshold value to be configured. As the 
            value is a floating point data type, the DisplayString type is used to define this parameter."
            ::= {ddmThresholdMgmtEntry 3}  
            
    ddmLowAlarm 	OBJECT-TYPE
    		SYNTAX  DisplayString
        MAX-ACCESS  read-write
        STATUS  current
        DESCRIPTION
            "This object indicates the low alarm threshold value to be configured. As the
             value is a floating data type, the DisplayString type is used to define this parameter."
            ::= {ddmThresholdMgmtEntry 4}  
                             
    ddmHighWarning	OBJECT-TYPE
    		SYNTAX  DisplayString
        MAX-ACCESS  read-write
        STATUS  current
        DESCRIPTION
            "This object indicates the high warning threshold value to be configured. As 
            the value is a floating data type, the DisplayString type is used to define this parameter."
            ::= {ddmThresholdMgmtEntry 5} 
            
    ddmLowWarning  OBJECT-TYPE
        SYNTAX  DisplayString
        MAX-ACCESS  read-write
        STATUS  current
        DESCRIPTION
            "This object indicates the low warning threshold value to be configured. As 
            the value is a floating data type, the DisplayString type is used to define this parameter."
            ::= {ddmThresholdMgmtEntry 6}     



-- --------------------------------------------------------------------------
-- DdmInfo
-- --------------------------------------------------------------------------
    ddmStatus  OBJECT IDENTIFIER ::= { ddmInfo 1 }

--DdmStatus
    ddmStatusTable	OBJECT-TYPE
    		SYNTAX	SEQUENCE OF DdmStatusEntry
    		MAX-ACCESS  not-accessible
    		STATUS  current
        DESCRIPTION
                "This table contains the DDM status information."
            ::= {ddmStatus 1}
            
    ddmStatusEntry OBJECT-TYPE
    		SYNTAX	DdmStatusEntry
    		MAX-ACCESS  not-accessible
    		STATUS	current
    		DESCRIPTION
    				"This is an entry of the ddmStatusTable."
    		INDEX  {ddmStatusPort}
    				::= {ddmStatusTable 1}
    
    DdmStatusEntry ::=
    		SEQUENCE {
    				ddmStatusPort
                    INTEGER,
    				ddmTemperature
    							DisplayString,
    				ddmVoltage
    							DisplayString,
    				ddmBiasCurrent
    							DisplayString,
    				ddmTxPower
    							DisplayString,
    				ddmRxPower
    							DisplayString
    				}

    ddmStatusPort	OBJECT-TYPE
    		SYNTAX  INTEGER 
        MAX-ACCESS  read-only
        STATUS  current
        DESCRIPTION
            "This object indicates the port."
            ::= {ddmStatusEntry 1}	
            				 
    ddmTemperature OBJECT-TYPE
    		SYNTAX  DisplayString
        MAX-ACCESS  read-only
        STATUS  current
        DESCRIPTION
            "This object indicates the real time value of the temperature. As the value 
             is a floating point data type, the DisplayString type is used to define this parameter."
            ::= {ddmStatusEntry 2}  
            
    ddmVoltage OBJECT-TYPE
    		SYNTAX  DisplayString
        MAX-ACCESS  read-only
        STATUS  current
        DESCRIPTION
            "This object indicates the real time value of the supply voltage. As the value 
             value is a floating point data type, the DisplayString type is used to define this parameter."
            ::= {ddmStatusEntry 3} 
            
    ddmBiasCurrent OBJECT-TYPE
    		SYNTAX  DisplayString
        MAX-ACCESS  read-only
        STATUS  current
        DESCRIPTION
            "This object indicates the real time value of the tx bias."
            ::= {ddmStatusEntry 4} 
            
    ddmTxPower OBJECT-TYPE
    		SYNTAX  DisplayString
        MAX-ACCESS  read-only
        STATUS  current
        DESCRIPTION
            "This object indicates the real time value of the tx power. As the value 
             is a floating point data type, the DisplayString type is used to define this parameter."
            ::= {ddmStatusEntry 5} 
            
    ddmRxPower OBJECT-TYPE
    		SYNTAX  DisplayString
        MAX-ACCESS  read-only
        STATUS  current
        DESCRIPTION
            "This object indicates the real time value of the rx power. As the value is 
            a floating data type, the DisplayString type is used to define this parameter."
            ::= {ddmStatusEntry 6} 
      

          
		-- *****************************************************************
		--
		--  Enterprise Trap group 
		--
		-- *****************************************************************
		        
END
