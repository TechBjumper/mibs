-- Copyright 1995 by 3Com Corporation.  All rights reserved.
-- MIB file name:  linkconv.mib
-- available in these 3Com devices:  LinkConverter
-- For support or more info, check 3Com's web page at http://www.3com.com

SYNC-RESEARCH-MIB DEFINITIONS ::= BEGIN

	IMPORTS
		-- If any of the MIB compilers have problems with the 
		-- internet, mgmt, NetworkAddress, IpAddess, Counter, Gauge,
		-- TimeTicks, enterprises, uncomment the next two lines and\
		-- comment the next third and forth line.

		--internet, mgmt, NetworkAddress, IpAddress, Counter, Gauge,
		--TimeTicks, enterprises

		enterprises, IpAddress, Counter
			FROM RFC1155-SMI
		OBJECT-TYPE
			FROM RFC-1212
		--syncResearch
			--FROM SYNC-RESEARCH-COMMUNITY-MIB
		TRAP-TYPE
			FROM RFC-1215
		PhysAddress, DisplayString FROM SNMPv2-TC;
	--
	-- Sync Research interNode MIB Version 2.0
	--
	-- The MIB was developed by Sync Research. It is not compatible
        -- with prior versions of MIBs published by Sync Research.
	--
	-- The MIB was developed by Sync Research. It is not compatible
        -- with prior versions of MIBs published by Sync Research.
	--
	-- Last Modification:
	--
	-- 01/27/95 Pam Tossey, Added variables to puControlGroup, and 
	-- netviewControlGroup to count connection attempts.  
	-- Addeded two new traps, puConnectionStatusUp and 
	-- puConnectionStatusDown if the connection state changes for PU, netview
 	-- PUs, and alternate netview PUs. Trap number 808 is no longer generated.
	-- The varbind list for port and PU traps was changed to include port and
        -- PU ids.
        --
	-- 12/27/94 Pam Tossey, Modified IMPORTS definitions of the MIB module 
	-- (synccomb.mib) so that it is compiled using Sync's tools (amc).
	-- MIB module synccomb.mib contains all objects for Sync's MIB and 
	-- Sync Community MIB and Traps.
	--
	-- 12/21/94 Steve Christle, corrected bug in msExtBoardType definition.
	--
	-- 11/17/94 Pam Tossey, Modified password and configpassword to have 
	-- read-write access.
	--
	-- 11/08/94 Pam Tossey, Modified Sync's MIBs to include our OEM partners
	-- new products.    
	--
	-- 08/31/94 Pam Tossey, changed variable access of dateTimeField to
	-- read-write. 
	-- 
	-- 06/13/94 Steve Christle, Pam Tossey, Sync Research, Version 2.0
	-- initial definition supporting FN4R2, CN4
	--
	--  This MIB module uses the extended OBJECT-TYPE macro as
	--  defined in RFC1212.
	--
	-- If any of the MIB compilers have problems with the DisplayString
	-- or PhysAddress, uncomment the next two lines.
	--
--	DisplayString		::=	OCTET STRING
--	PhysAddress		::=	OCTET STRING
 				
	-- internet      	OBJECT IDENTIFIER ::= { iso org(3) dod(6) 1 }
	-- directory     	OBJECT IDENTIFIER ::= { internet 1 }
	-- mgmt	  		OBJECT IDENTIFIER ::= { internet 2 }
	-- experimental  	OBJECT IDENTIFIER ::= { internet 3 }
	-- private       	OBJECT IDENTIFIER ::= { internet 4 }
	-- enterprises   	OBJECT IDENTIFIER ::= { private 1 }

	syncResearch		OBJECT IDENTIFIER ::= { enterprises 485 }

	-- The next variable agent object ID.

	syncResearchAgent	OBJECT IDENTIFIER ::= { syncResearch 1 }

	-- The syncProducts group contains both Sync Research's Frame Node and
	-- Conversion Node.

	syncProducts		OBJECT IDENTIFIER ::= { syncResearchAgent 1 }

	-- The oemProducts group contains Sync Research's OEM products

	oemProducts		OBJECT IDENTIFIER ::= { syncResearchAgent 2 }

	-- Subgroup of syncProducts

	boundary	 	OBJECT IDENTIFIER ::= { syncProducts 1 }
	centralSite		OBJECT IDENTIFIER ::= { syncProducts 2 }
	
	-- Subgroups of the Boundary Group

	syncCN2R2b		OBJECT IDENTIFIER ::= { boundary 1 }
	syncFN2R2b		OBJECT IDENTIFIER ::= { boundary 2 }
	syncCN4R2b		OBJECT IDENTIFIER ::= { boundary 3 }
	syncFN4R2b		OBJECT IDENTIFIER ::= { boundary 4 }
	syncQN4R2b		OBJECT IDENTIFIER ::= { boundary 5 }

	-- Subgroups of the CentralSite Group

	syncCN4R2c		OBJECT IDENTIFIER ::= { centralSite 1 }
	syncFN4R2c		OBJECT IDENTIFIER ::= { centralSite 2 }
	syncQN4R2c		OBJECT IDENTIFIER ::= { centralSite 3 }

	-- Subgroups of oemProducts
	
	threeCom		OBJECT IDENTIFIER ::= { oemProducts 1 }
	cableTron		OBJECT IDENTIFIER ::= { oemProducts 2 }
	chipcom			OBJECT IDENTIFIER ::= { oemProducts 3 }

	-- Subgroups of the threeCom EOM

	linkConverter		OBJECT IDENTIFIER ::= { threeCom 1 }

	-- Subgroups of the CableTron OEM

	oemSNACXR2C		OBJECT IDENTIFIER ::= { cableTron 1 }
	oemSNACXR2W		OBJECT IDENTIFIER ::= { cableTron 2 }
	oemSNACMR2C		OBJECT IDENTIFIER ::= { cableTron 3 }
	oemSNACMR2W		OBJECT IDENTIFIER ::= { cableTron 4 }

	-- The Node group contains both the Frame Node and Conversion Node.

	srNodeGroup		OBJECT IDENTIFIER ::= { syncResearch 3 }

	-- Subgroups of the Node group.

	nodeUnitGroup		OBJECT IDENTIFIER ::= { srNodeGroup 1 }
	nodeNetViewPUGroup	OBJECT IDENTIFIER ::= { srNodeGroup 2 }
	nodeBridgeGroup		OBJECT IDENTIFIER ::= { srNodeGroup 3 }
	nodeLANGroup 		OBJECT IDENTIFIER ::= { srNodeGroup 4 }
	nodeLineGroup 		OBJECT IDENTIFIER ::= { srNodeGroup 5 }
	nodePUGroup		OBJECT IDENTIFIER ::= { srNodeGroup 6 }
	nodeDeviceGroup		OBJECT IDENTIFIER ::= { srNodeGroup 7 }

	-- Subgroups of the Unit Group

	unitControlGroup	OBJECT IDENTIFIER ::= { nodeUnitGroup 1 }
	unitStatusGroup		OBJECT IDENTIFIER ::= { nodeUnitGroup 2 }
	unitConfigGroup		OBJECT IDENTIFIER ::= { nodeUnitGroup 3 }
	unitStatisticsGroup	OBJECT IDENTIFIER ::= { nodeUnitGroup 4 }

	-- Subgroups of the Netview Group

	netViewPUStatusGroup	OBJECT IDENTIFIER ::= { nodeNetViewPUGroup 1 }
	netViewPUConfigGroup	OBJECT IDENTIFIER ::= { nodeNetViewPUGroup 2 }

	-- Subgroups of the Bridge Group

	bridgeConfigGroup	OBJECT IDENTIFIER ::= { nodeBridgeGroup 1 }

	-- Subgroups of the LAN Group

	lanControlGroup		OBJECT IDENTIFIER ::= { nodeLANGroup 1 }
	lanTokenRingGroup	OBJECT IDENTIFIER ::= { nodeLANGroup 2 }

	-- Subgroups of the Line Group

	lineControlGroup	OBJECT IDENTIFIER ::= { nodeLineGroup 1 }
	linePhysicalGroup	OBJECT IDENTIFIER ::= { nodeLineGroup 2 }
	lineSDLCGroup		OBJECT IDENTIFIER ::= { nodeLineGroup 3 }
	lineBisyncGroup         OBJECT IDENTIFIER ::= { nodeLineGroup 4 }
	lineFrameRelayGroup	OBJECT IDENTIFIER ::= { nodeLineGroup 5 }

	-- Other future Line types (e.g. X.25) would be added here.

	-- Note Token Ring Statistics are obtained via the 802.5 standard
	-- MIB as defined in RFC 1231, and Ethernet via 802.3 standard MIB

	-- Subgroups of the PU Group

	puControlGroup		OBJECT IDENTIFIER ::= { nodePUGroup 1 }
	puSDLCGroup		OBJECT IDENTIFIER ::= { nodePUGroup 2 }
	puBisyncGroup           OBJECT IDENTIFIER ::= { nodePUGroup 3 }
	puMappingGroup          OBJECT IDENTIFIER ::= { nodePUGroup 4 }


	-- Subgroups of the Device Group

	deviceControlGroup	OBJECT IDENTIFIER ::= { nodeDeviceGroup 1 }
	deviceBSCGroup		OBJECT IDENTIFIER ::= { nodeDeviceGroup 2 }


	-- The Sync Research Community Name and Trap Group

	srCommTrapGroup		OBJECT IDENTIFIER ::= { syncResearch 2 }

	commCount OBJECT-TYPE
		SYNTAX	INTEGER (0..32)
		ACCESS	read-only
		STATUS	mandatory
		DESCRIPTION
			"The number of possible community name entries
			in the table."
		::= { srCommTrapGroup 1 }

	commTable OBJECT-TYPE
		SYNTAX	SEQUENCE OF CommEntry
		ACCESS	not-accessible
		STATUS	mandatory
		DESCRIPTION
			"This table houses the information for trivial
			authentication and sending traps."
		::= { srCommTrapGroup 2 }

	commEntry OBJECT-TYPE
		SYNTAX	CommEntry
		ACCESS	not-accessible
		STATUS	mandatory
		DESCRIPTION
			"Each entry contains a community name and access code
			for SNMP trivial authenticationm an enable/disable traps
			options, as well as network and physical addressing
			information for traps."
		INDEX	{ commIndex }
		::= { commTable 1 }

	CommEntry ::= SEQUENCE {
		commIndex
			INTEGER,
		commName
			OCTET STRING,
		commTrap
			INTEGER,
		commIPAddr
			IpAddress,
		commMACAddr
			OCTET STRING,
		commAccess
			INTEGER
		}

	commIndex OBJECT-TYPE
		SYNTAX	INTEGER
		ACCESS	read-only
		STATUS	mandatory
		DESCRIPTION
			"A unique value for each community entry. Its value
			ranges between 1 and commCount."
		::= { commEntry 1 }

	commName OBJECT-TYPE
		SYNTAX	OCTET STRING
		ACCESS	read-write
		STATUS	mandatory
		DESCRIPTION
			"A community name that will be used to access MIB
			objects within the device. Each community name is
			associated with an access code of either NO_ACCESS, RO,
			RW, or SU."
		::= { commEntry 2 }

	commTrap OBJECT-TYPE
		SYNTAX	INTEGER {
			trapoff(1),
			trapon(2)
			}
		ACCESS	read-write
		STATUS	mandatory
		DESCRIPTION
			"This object is checked to determine if traps should be
			sent to the corresponding network address associated
			with it."
		::= { commEntry 3 }

	commIPAddr OBJECT-TYPE
		SYNTAX	IpAddress
		ACCESS	read-write
		STATUS	mandatory
		DESCRIPTION
			"The network address of the device that will receive
			traps from the agent. This IP address also qualifies
			who may use this community name to access MIB objects.
			If this community name is use by some one with a 
			different IP address, an Authentication Trap will
			be generated. If the IP address is set to 0.0.0.0,
			anyone may use this address, however, traps will
			not be sent since the address is invalid." 
		::= { commEntry 4 }

	commMACAddr OBJECT-TYPE
		SYNTAX	OCTET STRING
		ACCESS	read-only
		STATUS	mandatory
		DESCRIPTION
			"The physical address of the device receiving traps
			from the agent."
		::= { commEntry 5 }

	commAccess OBJECT-TYPE
		SYNTAX	INTEGER {
			noAccess(1),
			ro(2),
			rw(3),
			su(4)
			}
		ACCESS	read-write
		STATUS	mandatory
		DESCRIPTION
			"Access code assiciated with the community name of the
			same entry. noAccess indicates a community name with
			zero privileges. ro has read-only access to MIB objects.
			rw allows you to read and write MIB objects. SU (super-
			user) gives you privileges to read and write any MIB
			object. The community table itself can only be written 
			to with an access of SU as well as the setting of the 
			IP Address on a device."
		::= { commEntry 6 }



	--
	-- The Unit Control Group
	--

	unitRestart	OBJECT-TYPE
		SYNTAX	INTEGER {
			restart-unit(1),
			dummy-restart(2)
			}
		ACCESS	read-write
		STATUS	mandatory
		DESCRIPTION
			"Setting this variable to a value of 1 will
			force the unit to restart. Setting this variable
			to any other value will cause an SNMP error.
			This variable always returns a value of 2."
		::= { unitControlGroup 1 }

	dumpOnRestart	OBJECT-TYPE
		SYNTAX	INTEGER {
			dump-on-start(1),
			dont-dump(2)
			}
		ACCESS	read-write
		STATUS	mandatory
		DESCRIPTION
			"Setting this variable to a value of 1 will
			force the unit to perform a dump on restart. Setting 
			this variable to a value of 2 will force it to not
			to dump on restart."
		::= { unitControlGroup 2 }

	initiateInstall	OBJECT-TYPE
		SYNTAX	INTEGER {
			start-install(1),
			dummy-install(2)
			}
		ACCESS	read-write
		STATUS	mandatory
		DESCRIPTION
			"Setting this variable to a value of 1 will force
			the unit to initiate an install process. This variable
			always returns a value of 2."
		::= { unitControlGroup 3 }


	initializeStats	OBJECT-TYPE
		SYNTAX	INTEGER {
			init-stats(1),
			dummy-init-stats(2)
			}
		ACCESS	read-write
		STATUS	mandatory
		DESCRIPTION
			"Setting this variable to a value of 1 will force
			the unit to initialize (clear) all statistics kept
			by the unit.
			This variable always returns a value of 2."
		::= { unitControlGroup 4 }

	clearDump	OBJECT-TYPE
		SYNTAX	INTEGER {
			clear-dump-file(1),
			dummy-clear(2)
			}
		ACCESS	read-write
		STATUS	mandatory
		DESCRIPTION
			"Setting this variable to a value of 1 will
			force the unit to clear a dump.
			This variable always returns a value of 2."
		::= { unitControlGroup 5 }
	--
	-- Unit Status Group
	--
	-- This group contains the device status variables. There exists
	-- only one instance of this group per unit.
	--

	unitModel	OBJECT-TYPE
		SYNTAX	INTEGER {
			boundary(1),
			lic(2),
			chipcomPED(3),
			snacMIM(4),
			microMac(5)
			}
		ACCESS	read-only
		STATUS	mandatory
		DESCRIPTION
			"This variable defines the base hardware model of
			 the unit:

			 A boundary platform is the 486 single board unit. 
                         A LIC is the Central Site chassis card."

		::= { unitStatusGroup 1 }

	softwareVersion	OBJECT-TYPE
		SYNTAX	DisplayString (SIZE(1..6))
		ACCESS	read-only
		STATUS	mandatory
		DESCRIPTION
			"The current version number of the operating 
			 software in xx.yyy where xx = major release,
			 yyy = revision."
		::= { unitStatusGroup 2 }


	productType	OBJECT-TYPE
		SYNTAX	DisplayString (SIZE(1..8))
		ACCESS	read-only
		STATUS	mandatory
		DESCRIPTION
			"The product type string returned is set in the
                         MS.SYS file and defines the product."
		::= { unitStatusGroup 3 }

	maxPortNumber	OBJECT-TYPE
		SYNTAX	INTEGER
		ACCESS	read-only
		STATUS	mandatory
		DESCRIPTION
			"The maximum number of ports this unit can
			support (total number of serial access ports plus
			total number of LAN ports)."
		::= { unitStatusGroup 4 }

	maxPU		OBJECT-TYPE
		SYNTAX	INTEGER
		ACCESS	read-only
		STATUS	mandatory
		DESCRIPTION
			"The maximum number of PUs this unit can
			support (total number that can be configured)."
		::= { unitStatusGroup 5 }


	maxSession		OBJECT-TYPE
		SYNTAX	INTEGER
		ACCESS	read-only
		STATUS	mandatory
		DESCRIPTION
			"The maximum number of sessions this unit can
			support (total number that can be configured)."
		::= { unitStatusGroup 6 }

	maxDevice		OBJECT-TYPE
		SYNTAX	INTEGER
		ACCESS	read-only
		STATUS	mandatory
		DESCRIPTION
			"The maximum number of devices this unit can
			support (total number that can be configured)."
		::= { unitStatusGroup 7 }

	msBoardType		OBJECT-TYPE
		SYNTAX	INTEGER {
			not-expected(1),
			two-port-RS232(16),
			two-port-RS422(17),
			two-port-V35(18),
			v35-RS232(22),
			rs422-RS232(23)
			}
		ACCESS	read-only
		STATUS	mandatory
		DESCRIPTION
			"Indicates the type of serial I/O ports on
			 main board.  It returns 1 if not expected." 
		::= { unitStatusGroup 8 }

	msExtBoardType		OBJECT-TYPE
		SYNTAX	INTEGER {
			not-present(1),
			two-port-RS232(19),
			two-port-RS422(20),
			two-port-V35(21),
                        two-port-hspeedRS232(24),
                        two-port-hspeedV35(25)
			}
		ACCESS	read-only
		STATUS	mandatory
		DESCRIPTION
			"Indicates the type of serial I/O ports on
			 extension board. It returns 1 if not present."
		::= { unitStatusGroup 9 }

	dumpFileStatus	 OBJECT-TYPE
		SYNTAX	INTEGER	{
			none (1),
			dump-available(2)
			}
		ACCESS	read-only
		STATUS	mandatory
		DESCRIPTION
			"Indicates the presence of a dump file."
		::= { unitStatusGroup 10 }

	dumpFileName OBJECT-TYPE
		SYNTAX	DisplayString (SIZE(1..11))
		ACCESS	read-only
		STATUS	mandatory
		DESCRIPTION
			"The dump file name."
		::= { unitStatusGroup 11 }

	unitSerialNumber OBJECT-TYPE
		SYNTAX	DisplayString (SIZE(1..9))
		ACCESS	read-only
		STATUS	mandatory
		DESCRIPTION
			"The base unit serial number."
		::= { unitStatusGroup 12 }

	expansionSerialNumber OBJECT-TYPE
		SYNTAX	DisplayString (SIZE(1..9))
		ACCESS	read-only
		STATUS	mandatory
		DESCRIPTION
			"The expansion board serial number."
		::= { unitStatusGroup 13 }

	romVersion OBJECT-TYPE
		SYNTAX	DisplayString (SIZE(1..16))
		ACCESS	read-only
		STATUS	mandatory
		DESCRIPTION
			"The ROM version number."
		::= { unitStatusGroup 14 }

	processorType OBJECT-TYPE
		SYNTAX	INTEGER	{
			i286 (1),
			i386 (2),
                        i486SX (3),
                        i486DX (4)
			}
		ACCESS	read-only
		STATUS	mandatory
		DESCRIPTION
			"The base unit processor type."
		::= { unitStatusGroup 15 }

	chassisSlot 	OBJECT-TYPE
		SYNTAX	INTEGER (1..99)
		ACCESS	read-only
		STATUS	mandatory
		DESCRIPTION
			"If the unit is a blade in a chassis, then
                        this variable indicates the slot number. If
                        not applicable, a value of 99 will be returned."
		::= { unitStatusGroup 16 }

	lastTrapSeqNumber 	OBJECT-TYPE
		SYNTAX	INTEGER (0..65535)
		ACCESS	read-only
		STATUS	mandatory
		DESCRIPTION
			"This entry contains the last sequence number of the
                         last trap generated by the unit. When this value
                         reaches its maximum, it then rolls back to 0."
		::= { unitStatusGroup 17 }

	lastInstallErrCode      OBJECT-TYPE
		SYNTAX	INTEGER (0..9999)
		ACCESS	read-only
		STATUS	mandatory
		DESCRIPTION
			"This entry contains the status of last install. 
			 If the last install was successful, 0 is returned,
			 9999 indicates installation is in progress, 
                         otherwise an error code is returned." 
		::= { unitStatusGroup 18 }

	unitPartNumber OBJECT-TYPE
		SYNTAX	DisplayString (SIZE(1..19))
		ACCESS	read-only
		STATUS	mandatory
		DESCRIPTION
			"The base unit part number."
		::= { unitStatusGroup 19 }

	expansionPartNumber OBJECT-TYPE
		SYNTAX	DisplayString (SIZE(1..19))
		ACCESS	read-only
		STATUS	mandatory
		DESCRIPTION
			"The expansion board part number."
		::= { unitStatusGroup 20 }

	--
	-- The Unit Configuration Group

	-- Contains the current operational configuration of the unit

	unitId		OBJECT-TYPE
		SYNTAX	DisplayString (SIZE(1..8))
		ACCESS	read-only
		STATUS	mandatory
		DESCRIPTION
			"This is the unit id.  It consists of a 1 to 8 octet
			 right justified case-sensitive ASCII field which
			 uniquely identifies the unit.
			 This ID is displayed on the LCD display, all system
			 dumps, and any ASCII alarms.
			 The defalult value for this field is startup."
		::= { unitConfigGroup 1 }

	nmsSerialSpeed	OBJECT-TYPE
		SYNTAX	INTEGER {
			speed1200(12),
			speed2400(24),
			speed4800(48),
			speed9600(96),
			speed19200(192)
			}
		ACCESS	read-only
		STATUS	mandatory
		DESCRIPTION
			"The async serial port speed for NMS console port.
			 The speed is expressed in bits per second (i.e.
			 9.6 Kbps is represented as 96 decimal).
			 Currently supported speeds are:
				1200
				2400
                            4800
				9600
				19200
			 Default speed is 9600 bits per second."
		::= { unitConfigGroup 2 }

	serialPortLogoffTimer 	OBJECT-TYPE
		SYNTAX	INTEGER (0..60)
		ACCESS	read-only
		STATUS	mandatory
		DESCRIPTION
			"Units are minutes. Default value is 0, indicating
                      that no timer is active."
		::= { unitConfigGroup 3 }

	callRetryTimer	OBJECT-TYPE
		SYNTAX	INTEGER (2..999)
		ACCESS	read-only
		STATUS	mandatory
		DESCRIPTION
			"The call retry timer (a.k.a Session Retry Timer).

			 The number of seconds to wait before trying
			 to retry a failed LLC connection attempt.
			 Currently supported values are 2 - 999 seconds.
			 The default is 30 seconds."
		::= { unitConfigGroup 4 }

	password	OBJECT-TYPE
		SYNTAX	DisplayString (SIZE(1..8))
		ACCESS	read-write
		STATUS	mandatory
		DESCRIPTION
			"The unit's password.
			 This field indicates the system password used to
			 log into the unit for operating the NMS interface.

			 This field is a one to eight byte case-sensitive
			 left justified ASCII data field and may not be
			 left blank.

			 The default value is 'sri' (for Sync Research Inc.)."
		::= { unitConfigGroup 5 }

	configPassword	OBJECT-TYPE
		SYNTAX	DisplayString (SIZE(1..8))
		ACCESS	read-write
		STATUS	mandatory
		DESCRIPTION
			"The configuration password.
			 This field indicates the password used to
			 enter the configuration subsystem.

			 This field is a one to eight byte case-sensitive
			 left justified ASCII data field and may not be
			 left blank.

			 The default value is 'sri' (for Sync Research Inc.)."
		::= { unitConfigGroup 6 }

	dateTimeField	OBJECT-TYPE
		SYNTAX	OCTET STRING (SIZE(6))
		ACCESS	read-write
		STATUS	mandatory
		DESCRIPTION
			"The date and time.
			 This field is stored as 6 bytes of BCD Data in the
			 following order:
			    Month:      0x01 - 0x12
			    Day:        0x01 - 0x31
			    Year:       0x00 - 0x99
			    Hour:       0x00 - 0x23
			    Minute:     0x00 - 0x59
			    Second:     0x00 - 0x59"
		::= { unitConfigGroup 7 }

	configId		OBJECT-TYPE
		SYNTAX	DisplayString (SIZE(1..8))
		ACCESS	read-only
		STATUS	mandatory
		DESCRIPTION
			"The configuration identifer.
			 This field is the configuration ID assigned
			 when a new configuration is activated for the 
			 first time.  It is assigned by the unit
			 automatically and is not user assignable."
		::= { unitConfigGroup 8 }

	internalMacAddress 	OBJECT-TYPE
		SYNTAX	PhysAddress
		ACCESS	read-only
		STATUS	mandatory
		DESCRIPTION
			"Embedded conversion node MAC address. Applicable
                         to Frame Node only."
		::= { unitConfigGroup 9 }

	internalRingNumber 	OBJECT-TYPE
		SYNTAX	INTEGER (1..4095)
		ACCESS	read-only
		STATUS	mandatory
		DESCRIPTION
			"Embedded conversion node ring number. This should
			 be unique within the network. Applicable
                         to Frame Node only."
		::= { unitConfigGroup 10 }

	internalBridgeNumber 	OBJECT-TYPE
		SYNTAX	INTEGER (1..15)
		ACCESS	read-only
		STATUS	mandatory
		DESCRIPTION
			"Embedded conversion node bridge number. This 
                      parameter is currently not used. Applicable
                         to Frame Node only."
		::= { unitConfigGroup 11 }


	--
	-- The Unit Statistics Group
	--


	numberSamples	OBJECT-TYPE
		SYNTAX	Counter
		ACCESS	read-only
		STATUS	mandatory
		DESCRIPTION
			"The number of internal system level samples
			 performed.  Samples are taken every 10th of a
			 second."
		::= { unitStatisticsGroup 1 }

	systemBufferFreeCounts	OBJECT-TYPE
		SYNTAX	INTEGER
		ACCESS	read-only
		STATUS	mandatory
		DESCRIPTION
			"The average number of system buffers free in
			 the system during the system sample period.
			 The number of available buffers varies by
			 system type and configuration.  To determine
			 the maximum number of buffers for a given
			 configuration, view a sample when there is no
			 activity in the unit.

			 A heavily loaded unit will display a small number
			 of available buffers and low Processor Idle counts."
		::= { unitStatisticsGroup 2 }

	cpuIdleSumCounts OBJECT-TYPE
		SYNTAX	Counter
		ACCESS	read-only
		STATUS	mandatory
		DESCRIPTION
			"The main processor average idle sum count.
			 This is the average number of times the idle counter
			 was incremented over the sampling period divided
			 by 1000.  This is an absolute value of performance
			 as does not vary by performance.

			 A heavily loaded unit will display a small number
			 of available buffers and low Processor Idle counts."
		::= { unitStatisticsGroup 3 }


	--
	-- NetView PU Status Group
	--
	-- This group contains status variables. There exists
	-- only one instance of this group per unit.
	--

	netviewConnectionStatus	OBJECT-TYPE
		SYNTAX	INTEGER	{
			connected(1),
			not-connected(2)
			}
		ACCESS	read-only
		STATUS	mandatory
		DESCRIPTION
			"The status of the Primary Netview Connection"
		::= { netViewPUStatusGroup 1 }

	netviewLastClearCode    OBJECT-TYPE
		SYNTAX	OCTET STRING (SIZE(2))
		ACCESS	read-only
		STATUS	mandatory
		DESCRIPTION
			"A two octet field indicating the Last Clearing
			 Cause and Diagnostic Field of the last failed primary
			 NetView connection attempt (a.k.a. call attempt) or
			 Netview active connection (a.k.a. session).

			 For LLC type 2 connections the first octet (cause)
			 is always 0.  The second octet (diagnostic)
			 indicates the reason for the last connection failure.
			 The second octet is set to 0 when a sucessful
			 call has been placed, or if no call has ever been
			 placed (e.g. PU never came up).
			 If the second octet is non-zero then it indicates
			 the reason for the connection attempt failure.
			 See current product documentation for list of possible 
                         values."

		::= { netViewPUStatusGroup 2 }

	netviewAltConnectionStatus	OBJECT-TYPE
		SYNTAX	INTEGER	{
			connected(1),
			not-connected(2)
			}
		ACCESS	read-only
		STATUS	mandatory
		DESCRIPTION
			"The status of the alternate Netview Connection"
		::= { netViewPUStatusGroup 3 }

	netviewAltLastClearCode    OBJECT-TYPE
		SYNTAX	OCTET STRING (SIZE(2))
		ACCESS	read-only
		STATUS	mandatory
		DESCRIPTION
			"A two octet field indicating the Last Clearing
			 Cause and Diagnostic Field of the last failed alternate
			 NetView connection attempt (a.k.a. call attempt) or
			 Netview active connection (a.k.a. session).

			 For LLC type 2 connections the first octet (cause)
			 is always 0.  The second octet (diagnostic)
			 indicates the reason for the last connection failure.
			 The second octet is set to 0 when a sucessful
			 call has been placed, or if no call has ever been
			 placed (e.g. PU never came up).
			 If the second octet is non-zero then it indicates
			 the reason for the connection attempt failure.
			 See current product documentation for list of possible 
                         values."

		::= { netViewPUStatusGroup 4 }

	netviewConnectionAttemptCount 	OBJECT-TYPE
		SYNTAX	Counter	
		ACCESS	read-only
		STATUS	mandatory
		DESCRIPTION
			"The number of connection attempts performed on the  
			 Primary NetView PU. This count is set to zero at 
                         startup, and after every loss of an estabished 
                         session."   
		::= { netViewPUStatusGroup 5 }

	netviewAltConnectionAttemptCount 	OBJECT-TYPE
		SYNTAX	Counter	
		ACCESS	read-only
		STATUS	mandatory
		DESCRIPTION
			"The number of connection attempts performed on the  
			 Alternate NetView PU. This count is set to zero at 
                         startup, and after every loss of an estabished 
                         session."   
		::= { netViewPUStatusGroup 6 }

	--
	-- The NetView PU Configuration Group

	-- Contains the current operational configuration 
        --

	netviewPUXID	OBJECT-TYPE
		SYNTAX	OCTET STRING (SIZE(4))
		ACCESS	read-only
		STATUS	mandatory
		DESCRIPTION
			"Primary NetView PU XID.
			 This field indicates the XID data to be
			 sent to the host for establishing Netview Session.

			 This field is a maximum four byte hexadecimal
			 data field.

			 This field should be set to all zeroes if no
			 Netview session is to be established.

			 The default value is all zeroes."
		::= { netViewPUConfigGroup 1 }

	alternateNetviewPUXID 	OBJECT-TYPE
		SYNTAX	OCTET STRING (SIZE(4))
		ACCESS	read-only
		STATUS	mandatory
		DESCRIPTION
			"Alternate NetView PU XID.
			 This field indicates the XID data to be
			 sent to the host for establishing Netview Session.

			 This field is a maximum four byte hexadecimal
			 data field.

			 This field should be set to all zeroes if no
			 Netview session is to be established.

			 The default value is all zeroes."
		::= { netViewPUConfigGroup 2 }

	netviewConnectID OBJECT-TYPE
		SYNTAX	OCTET STRING (SIZE(2))
		ACCESS	read-only
		STATUS	mandatory
		DESCRIPTION
			"The primary NetView PU connection ID.

			 The default value is 0."
		::= { netViewPUConfigGroup 3 }

	alternateNetviewConnectID OBJECT-TYPE
		SYNTAX	OCTET STRING (SIZE(2))
		ACCESS	read-only
		STATUS	mandatory
		DESCRIPTION
			"The alternate NetView PU connection ID.

			 The default value is 0."
		::= { netViewPUConfigGroup 4 }

	netviewSpecialConnect OBJECT-TYPE
		SYNTAX	INTEGER {
                        answer (1),
                        originate (2)
                        }
		ACCESS	read-only
		STATUS	mandatory
		DESCRIPTION
			"The primary NetView PU connection type.

			 The default value is originate."
		::= { netViewPUConfigGroup 5 }

	alternateNetviewSpecialConnect OBJECT-TYPE
		SYNTAX	INTEGER {
                        answer (1),
                        originate (2)
                        }
		ACCESS	read-only
		STATUS	mandatory
		DESCRIPTION
			"The alternate NetView PU connection type.

			 The default value is originate."
		::= { netViewPUConfigGroup 6 }

	--
	-- The Bridge Configuration Group

	-- Contains the current operational configuration 
        --

	brEnableBridging        OBJECT-TYPE
		SYNTAX	INTEGER {
			yes(1),
			no(2)
			}
		ACCESS	read-only
		STATUS	mandatory
		DESCRIPTION
			"This flag indicates if bridging is to be performed
                         on this unit.

			 The default value for this field is 'No'"
		::= { bridgeConfigGroup 1 }

	bridgePriority 	OBJECT-TYPE
		SYNTAX	INTEGER (0..65535)
		ACCESS	read-only
		STATUS	mandatory
		DESCRIPTION
			"Sometimes referred to as the ROOT id. Determines the 
			 priority component of the Bridge identifier used in 
			 determining the Root Bridge for a spanning tree network."
		::= { bridgeConfigGroup 2 }

	brMaxAge 	OBJECT-TYPE
		SYNTAX	INTEGER (6..40)
		ACCESS	read-only
		STATUS	mandatory
		DESCRIPTION
			"The time at which a configuration message is descarded.
			 Units are in seconds. Default value is 10 seconds"
		::= { bridgeConfigGroup 3 }

	brHelloTimer 	OBJECT-TYPE
		SYNTAX	INTEGER (1..10)
		ACCESS	read-only
		STATUS	mandatory
		DESCRIPTION
			"The time interval between issuing configuration
			 messages. Units are seconds. Default value is 2 seconds"
		::= { bridgeConfigGroup 4 }

	brFilterIPX 	OBJECT-TYPE
		SYNTAX	INTEGER {
			yes(1),
			no(2)
			}
		ACCESS	read-only
		STATUS	mandatory
		DESCRIPTION
			"If set to yes, all IPX frames are filtered (if 
                         bridge is enabled). Default is Yes."
		::= { bridgeConfigGroup 5 }

	brFilterIP 	OBJECT-TYPE
		SYNTAX	INTEGER {
			yes(1),
			no(2)
			}
		ACCESS	read-only
		STATUS	mandatory
		DESCRIPTION
			"If set to yes, all IP frames are filtered (if bridging
                         is enabled). Default is Yes."
		::= { bridgeConfigGroup 6 }

	brFilterNetBIOS	OBJECT-TYPE
		SYNTAX	INTEGER {
			yes(1),
			no(2)
			}
		ACCESS	read-only
		STATUS	mandatory
		DESCRIPTION
			"If set to yes, all NetBIOS frames are filtered 
                         (if bridging is enabled). Default is Yes."
		::= { bridgeConfigGroup 7 }

	brFilterLLC2 	OBJECT-TYPE
		SYNTAX	INTEGER {
			yes(1),
			no(2)
			}
		ACCESS	read-only
		STATUS	mandatory
		DESCRIPTION
			"If set to yes, all LAN attached SNA LLC2 frames are 
                         filtered (if bridging is enabled). Default is Yes."
		::= { bridgeConfigGroup 8 }

	brFilterSMAN 	OBJECT-TYPE
		SYNTAX	INTEGER {
			yes(1),
			no(2)
			}
		ACCESS	read-only
		STATUS	mandatory
		DESCRIPTION
			"If set to yes, all SyncManager LLC2 frames are
                         filtered (if bridging is enabled). Default is Yes."
		::= { bridgeConfigGroup 9 }

	brForwardOther 	OBJECT-TYPE
		SYNTAX	INTEGER {
			yes(1),
			no(2)
			}
		ACCESS	read-only
		STATUS	mandatory
		DESCRIPTION
			"If set to yes, all other frames are forwarded (if
                         bridging is enabled). Default is No."
		::= { bridgeConfigGroup 10 }

	brIPXtargetPort	OBJECT-TYPE
		SYNTAX	INTEGER   
		ACCESS	read-only
		STATUS	mandatory
		DESCRIPTION
			"If IPX filtering is set to no, then this parameter
                         defines a specific FR port to deliver IPX frames to.
                         Used in conjunction with brIPXtargetDLCI.

			 The valid range is 0 to 5.  A value of 0 indicates that
			 the IPX target port/DLCI is not configured. 
		
			 This field has the default value of 0."
		::= { bridgeConfigGroup 11 }

	brIPXtargetDLCI	OBJECT-TYPE
		SYNTAX	INTEGER (1..1023) 
		ACCESS	read-only
		STATUS	mandatory
		DESCRIPTION
			"If IPX filtering is set to no, then this parameter
                         defines a specific FR DLCI to deliver IPX frames to.
                         Used in conjunction with brIPXtargetPort.
	
			 If the value of brIPXtargetport is 0, then the value of
			 brIPXtargetDLCI is not significant." 
		::= { bridgeConfigGroup 12 }

	brIPtargetPort	OBJECT-TYPE
		SYNTAX	INTEGER 
		ACCESS	read-only
		STATUS	mandatory
		DESCRIPTION
			"If IP filtering is set to no, then this parameter
                         defines a specific FR port to deliver IP frames to.
                         Used in conjunction with brIPtargetDLCI.

			 The valid range is 0 to 5.  A value of 0 indicates that
			 the IP target port/DLCI is not configured. 
		
			 This field has the default value of 0."
		::= { bridgeConfigGroup 13 }

	brIPtargetDLCI	OBJECT-TYPE
		SYNTAX	INTEGER 
		ACCESS	read-only
		STATUS	mandatory
		DESCRIPTION
			"If IP filtering is set to no, then this parameter
                         defines a specific FR DLCI to deliver IP frames to.
                         Used in conjunction with brIPtargetPort.

			 If the value of brIPtargetport is 0, then the value of
			 brIPtargetDLCI is not significant." 
		::= { bridgeConfigGroup 14 }


	brNetBIOStargetPort	OBJECT-TYPE
		SYNTAX	INTEGER 
		ACCESS	read-only
		STATUS	mandatory
		DESCRIPTION
			"If NetBIOS filtering is set to no, then this parameter
                         defines a specific FR port to deliver NetBIOS frames 
                         to. Used in conjunction with brNetBIOStargetDLCI.
			 
			 The valid range is 0 to 5.  A value of 0 indicates that
			 the NetBIOS target port/DLCI is not configured.
		
			 This field has the default value of 0."
		::= { bridgeConfigGroup 15 }


	brNetBIOStargetDLCI	OBJECT-TYPE
		SYNTAX	INTEGER 
		ACCESS	read-only
		STATUS	mandatory
		DESCRIPTION
			"If NetBIOS filtering is set to no, then this parameter
                         defines a specific FR DLCI to deliver NetBIOS frames 
                         to. Used in conjunction with brNetBIOStargetPort.

			 If the value of brNetBIOStargetport is 0, then the
			 value of brNetBIOStargetDLCI is not significant." 

		::= { bridgeConfigGroup 16 }


	brLLC2targetPort	OBJECT-TYPE
		SYNTAX	INTEGER 
		ACCESS	read-only
		STATUS	mandatory
		DESCRIPTION
			"If SNA LLC2 filtering is set to no, then this parameter
                         defines a specific FR port to deliver LLC2 frames to.
                         Used in conjunction with brLLC2targetDLCI.

			 The valid range is 0 to 5.  A value of 0 indicates that
			 the brLLC2targetport/brLLC2targetDLCI is not configured. 
		
			 This field has the default value of 0."
		::= { bridgeConfigGroup 17 }


	brLLC2targetDLCI	OBJECT-TYPE
		SYNTAX	INTEGER 
		ACCESS	read-only
		STATUS	mandatory
		DESCRIPTION
			"If SNA LLC2 filtering is set to no, then this parameter
                         defines a specific FR DLCI to deliver LLC2 frames to.
                         Used in conjunction with brLLC2targetPort.

			 If the value of brLLC2targetport is 0, then the value
			 of brLLC2targetDLCI is not significant." 
		::= { bridgeConfigGroup 18 }


	brOthertargetPort	OBJECT-TYPE
		SYNTAX	INTEGER 
		ACCESS	read-only
		STATUS	mandatory
		DESCRIPTION
			"If Other forwarding is set to yes, then this parameter
                         defines a specific FR port to deliver Other frames to.
                         Used in conjunction with brOthertargetDLCI. 

			 The valid range is 0 to 5.  The value 0 indicates that
			 the brOthertargetport/brOthertargetDLCI is not 
			 configured. 
		
			 This field has the default value of 0."
		::= { bridgeConfigGroup 19 }


	brOthertargetDLCI	OBJECT-TYPE
		SYNTAX	INTEGER 
		ACCESS	read-only
		STATUS	mandatory
		DESCRIPTION
			"If Other forwarding is set to yes, then this parameter
                         defines a specific FR DLCI to deliver Other frames to.
                         Used in conjunction with brOthertargetPort.

			 If the value of brOthertargetport is 0, then the value
			 of brOthertargetDLCI is not significant." 
		::= { bridgeConfigGroup 20 }

	brSerialPriority	OBJECT-TYPE
		SYNTAX	INTEGER {
                        urgent (1),
                        high (2),
                        medium (3),
                        low (4)
                        }
		ACCESS	read-only
		STATUS	mandatory
		DESCRIPTION
			"This parameter defines the transmit priority for       
                         Frame Relay of serial attached port traffic."
		::= { bridgeConfigGroup 21 }


	brTerminatedLLC2Priority	OBJECT-TYPE
		SYNTAX	INTEGER {
                        urgent (1),
                        high (2),
                        medium (3),
                        low (4)
                        }
		ACCESS	read-only
		STATUS	mandatory
		DESCRIPTION
			"This parameter defines the transmit priority for
			 Frame Relay of terminated LLC2 traffic." 
		::= { bridgeConfigGroup 22 }


	brLLC2Priority	OBJECT-TYPE
		SYNTAX	INTEGER {
                        urgent (1),
                        high (2),
                        medium (3),
                        low (4)
                        }
		ACCESS	read-only
		STATUS	mandatory
		DESCRIPTION
			"This parameter defines the transmit priority for
                         Frame Relay of SNA LLC2 traffic."
		::= { bridgeConfigGroup 23 }


	brIPXPriority	OBJECT-TYPE
		SYNTAX	INTEGER {
                        urgent (1),
                        high (2),
                        medium (3),
                        low (4)
                        }
		ACCESS	read-only
		STATUS	mandatory
		DESCRIPTION
			"This parameter defines the transmit priority for
			 Frame Relay of IPX traffic."
		::= { bridgeConfigGroup 24 }


	brIPPriority	OBJECT-TYPE
		SYNTAX	INTEGER {
                        urgent (1),
                        high (2),
                        medium (3),
                        low (4)
                        }
		ACCESS	read-only
		STATUS	mandatory
		DESCRIPTION
			"This parameter defines the transmit priority for
			 Frame Relay of IP traffic."
		::= { bridgeConfigGroup 25 }


	brNetBIOSPriority	OBJECT-TYPE
		SYNTAX	INTEGER {
                        urgent (1),
                        high (2),
                        medium (3),
                        low (4)
                        }
		ACCESS	read-only
		STATUS	mandatory
		DESCRIPTION
			"This parameter defines the transmit priority for
			 Frame Relay of NetBIOS traffic."
		::= { bridgeConfigGroup 26 }


	brOtherPriority	OBJECT-TYPE
		SYNTAX	INTEGER {
                        urgent (1),
                        high (2),
                        medium (3),
                        low (4)
                        }
		ACCESS	read-only
		STATUS	mandatory
		DESCRIPTION
			"This parameter defines the transmit priority for
			 Frame Relay of other traffic."
		::= { bridgeConfigGroup 27 }

	brHighPriorityBandwidth	OBJECT-TYPE
		SYNTAX	INTEGER (0..100)
		ACCESS	read-only
		STATUS	mandatory
		DESCRIPTION
			"This parameter defines the high priority bandwidth.
			 The sum of high, medium, and low priority bandwidth 
			 cannot exceed 100.
			 
			 Default value is 40."
		::= { bridgeConfigGroup 28 }


	brMediumPriorityBandwidth	OBJECT-TYPE
		SYNTAX	INTEGER (0..100)
		ACCESS	read-only
		STATUS	mandatory
		DESCRIPTION
			"This parameter defines the medium priority bandwidth.
			 The sum of high, medium, and low priority bandwidth 
			 cannot exceed 100.

			 Default value is 30."
		::= { bridgeConfigGroup 29 }


	brLowPriorityBandwidth	OBJECT-TYPE
		SYNTAX	INTEGER (0..100)
		ACCESS	read-only
		STATUS	mandatory
		DESCRIPTION
			"This parameter defines the low priority bandwidth.
			 The sum of high, medium, and low priority bandwidth 
			 cannot exceed 100.

			 Default value is 20."
		::= { bridgeConfigGroup 30 }

	--
	-- The LAN control
	--

	lanControlTable OBJECT-TYPE
		SYNTAX SEQUENCE OF LanControlEntry
		ACCESS 	not-accessible
		STATUS	mandatory
		DESCRIPTION
			"A table for controlling LAN ports and obtaining
			 information." 
		::= { lanControlGroup 1 }

	lanControlEntry OBJECT-TYPE
		SYNTAX  LanControlEntry
		ACCESS 	not-accessible
		STATUS	mandatory
		DESCRIPTION
			"An entry consisting of port information for a
			 particular LAN port." 
		INDEX { lanControlIndex }
		::= { lanControlTable 1 }

	LanControlEntry ::=
		SEQUENCE {
			lanControlIndex
				INTEGER,
			lanControlType
				INTEGER,
			lanStatus
				INTEGER,
			lanControlFailureCode
				OCTET STRING,
			lanControlNAUName
                            DisplayString
		}
				

	lanControlIndex	OBJECT-TYPE
		SYNTAX	INTEGER 
		ACCESS	read-only
		STATUS	mandatory
		DESCRIPTION
			"The number that uniquely identifies
			 this LAN port.
			 Currently only one LAN port per unit is supported."
		::= { lanControlEntry 1 }


	lanControlType	OBJECT-TYPE
		SYNTAX	INTEGER {
			token-ring-type(21),
			ethernet-type(17)
			}
		ACCESS	read-only
		STATUS	mandatory
		DESCRIPTION
			"The LAN type.

			 Token-Ring ports run the IEEE 802.5 protocol.
			 Ethernet-type run the IEEE 802.3 and Ethernet 
			 Version 2.

			 Other LAN protocols may be added in
			 the future."
		::= { lanControlEntry 2 }

	lanStatus		OBJECT-TYPE
		SYNTAX	INTEGER {
			enable(1),
			disable(2),
			failed(3),
			restart(4)
			}
		ACCESS	read-write
		STATUS	mandatory
		DESCRIPTION
			"The status of the port.
			 To change status of a port an enable, enable all
			 or disable may be set.

			 Valid Return status are enable(d), disable(d),
			 or failed.

			 Commands:
			 An enable command will attempt to bring up the LAN.

			 An enable all command will perform the same function
			 as enable, since there are no sub elements on a LAN.

			 A disable command will disable the LAN.
			 
			 Status:
			 Enable(d) indicates the LAN is enabled and running.
			 Disable(d) indicates the LAN has been disabled.
			 Failed indicates the LAN is enabled and not 
			 Running."
		::= { lanControlEntry 3 }

	lanControlFailureCode 	OBJECT-TYPE
		SYNTAX	OCTET STRING (SIZE (2))
		ACCESS	read-only
		STATUS	mandatory
		DESCRIPTION
			"This entry contains the failure codes if the
			 associated LAN interface is in the failed state."
		::= { lanControlEntry 4 }


	lanControlNAUName 	OBJECT-TYPE
		SYNTAX	DisplayString (SIZE(1..8))
		ACCESS	read-only
		STATUS	mandatory
		DESCRIPTION
			"The NAU name of this port.
			 The default value for this field is all blank
			 (filled with ASCII space 0x20 characters)."
		::= { lanControlEntry 5 }

	--
	-- The LAN Configuration Group
	--

	lanPortTable	OBJECT-TYPE
		SYNTAX  SEQUENCE OF LanPortEntry
		ACCESS 	not-accessible
		STATUS	mandatory
		DESCRIPTION
			"A table of LAN information." 
		::= { lanTokenRingGroup 1 }

	lanPortEntry	OBJECT-TYPE
		SYNTAX  LanPortEntry
		ACCESS 	not-accessible
		STATUS	mandatory
		DESCRIPTION
			"An entry consisting of port information for a
			 particular LAN port." 
		INDEX { lanPortIndex }
		::= { lanPortTable 1 }

	LanPortEntry ::=
		SEQUENCE {
			lanPortIndex
				INTEGER,
			lanPortType
				INTEGER,
			lanMACAddress
				PhysAddress,
			lanPROMMACAddress
				PhysAddress,
			lanSpeed
				INTEGER,
			lanT1Timer
				INTEGER,
			lanT2Timer
				INTEGER,
			lanTiTimer
				INTEGER,
			lanRxWindowSize
				INTEGER,
			lanTxWindowSize
				INTEGER,
			lanMaxRetries
				INTEGER,
			lanRingNumber
                            INTEGER,
			lanBridgeNumber
                            INTEGER,
			lanEthernetFrameFormat
                            INTEGER,
			lanSendLocalTest
                            INTEGER,
			lanBroadcastType
                            INTEGER,
			lanIPAddress
				IpAddress,
			lanNetworkMask
				IpAddress,
			lanDefaultGateway
				IpAddress,
			lanNAUName
                            DisplayString,
			lanInterfaceType
				INTEGER,
			lanIPEthernetFrameType
				INTEGER,
			lanInitState
				INTEGER
		}
				

	lanPortIndex	OBJECT-TYPE
		SYNTAX	INTEGER 
		ACCESS	read-only
		STATUS	mandatory
		DESCRIPTION
			"The port number that uniquely identifies
			 this port.
			 Currently only one LANtoken ring port per unit is
			 supported with the port index = 1."
		::= { lanPortEntry 1 }


	lanPortType	OBJECT-TYPE
		SYNTAX	INTEGER {
			token-ring-type(21),
			ethernet-type(17)
			}
		ACCESS	read-only
		STATUS	mandatory
		DESCRIPTION
			"The LAN port type."
		::= { lanPortEntry 2 }

	lanMACAddress	OBJECT-TYPE
		SYNTAX	PhysAddress
		ACCESS	read-only
		STATUS	mandatory
		DESCRIPTION
			"The user configured LANtoken ring MAC address.
			 If the address is set to 0 then the burned-in Address
			 is used.  This field contains a user configured
			 address if any.  If a user configured address
			 is desired, then it must be configured as
			 a valid individual, user defined - MAC address.
			 The address must be configured in the native 
			 format convention used by the LAN port.

			 For token Ring LAN ports the address follows
                         User configured addresses must follow IEEE 802.5
			 IEEE 802.5 rules (most significant bit transmitted first)
			 and must be between 400000000000 and 7FFFFFFFFFFF
			 hexadecimal inclusive.

			 For Ethernet LAN ports the format is must
			 follow IEEE 802.3 rules.where the two least
			 significant bits of the first octet must be
			 zero.  This means the first octet must be
			 in the set of numbers 0x00, 0x04, 0x08, ...
			0xFC.....
			
			 The Default Value for this field is all zeroes."
		::= { lanPortEntry 3 }

	lanPROMMACAddress OBJECT-TYPE
		SYNTAX	PhysAddress
		ACCESS	read-only
		STATUS	mandatory
		DESCRIPTION
			"The burned in MAC address.

			 This is the MAC address assigned by the factory
			 when the unit is shipped.  If the User configured
			 address is set to 0, then this will be the address
			 used by the adapter for the source address field
			 for all frames sent by the LAN adapter.

			 The format ordering of bits is as defined in
			 IEEE 802.5.  This ordering is where the Most
			 Significant Bit is transmitted first.  This is
			 different from other protocols (e.g. 802.3) where
			 the least significant bit is transmitted first.
			 The representation of the MAC address is 
			 in the format native for the LAN port.

			 Boundary platform Token-Ring LAN ports start with the
                         first six digits (three octects) equal	to
                         0002F6 which indicates a Sync Research Token Ring
			 MAC address.

			 Boundary platform Ethernet LAN ports start with
			 the first six digits (three octects) equal to
 			 to 00406F which indicates a Sync Research 
			 Ethernet MAC address.

			 This field is not changable via any commands
			 and will always contain the manufactured
			 MAC address for the LAN port."
		::= { lanPortEntry 4 }

	lanSpeed		OBJECT-TYPE
		SYNTAX	INTEGER {
			speed-4Mbs(4),
			speed-10Mbs(10),
			speed-16Mbs(16)
			}
		ACCESS	read-only
		STATUS	mandatory
		DESCRIPTION
			"The LAN port speed in Megabits/second.
			 For Token-Ring boundary platforms, the speed is 
			 changable via the front panel keypad and LCD menus,
			 and NMS console port.

			 For Token-Ring LIC the speed is changed
			 by a jumper on the back of the board (top
			 two pins = 4, bottom two pins = 16).

			 For Ethernet boundary platforms and LIC, the speed is 
			 not configurable." 
		::= { lanPortEntry 5 }

	lanT1Timer	OBJECT-TYPE
		SYNTAX	INTEGER (1..25)
		ACCESS	read-only
		STATUS	mandatory
		DESCRIPTION
			"The default LLC T1 timer value in seconds.
			 T1 should be greater than T2 and less than Ti.
			 Currently supported values are 1 to 25 seconds.
			 The default value for this field is 3 seconds."
		::= { lanPortEntry 6 }

	lanT2Timer	OBJECT-TYPE
		SYNTAX	INTEGER (0..50)
		ACCESS	read-only
		STATUS	mandatory
		DESCRIPTION
			"The default LLC T2 timer value in tenths of seconds.
			 If configured for 0 then the T2 timer is disabled
			 and an RR frame will be sent for every I frame
			 received.
			 Current supported values are 0 and 2-50.
			 T2 should be less than T1.
			 The default value for this field is 0 (disabled)."
		::= { lanPortEntry 7 }

	lanTiTimer	OBJECT-TYPE
		SYNTAX	INTEGER (2..50)
		ACCESS	read-only
		STATUS	mandatory
		DESCRIPTION
			"The default LLC Ti (inactivity) timer value
			 in seconds.
			 Ti should be greater than T1.
			 Currently supported values are 2 to 50 seconds.
			 The default value for this field is 30 seconds."
		::= { lanPortEntry 8 }

	lanRxWindowSize OBJECT-TYPE
		SYNTAX	INTEGER (1..7)
		ACCESS	read-only
		STATUS	mandatory
		DESCRIPTION
			"The default LLC receive window (N3) size.
			 Note that this is not the same receive window as 
			 defined in IEEE 802.2 LLC.  This is N3 which is the
			 number of I frames received before an RR frame is
			 sent (defined as N3 in IEEE 802.2 LLC).
			 Current allowable values are 1-7.
			 The default value for this field is 7."
		::= { lanPortEntry 9 }

	lanTxWindowSize OBJECT-TYPE
		SYNTAX	INTEGER (1..7)
		ACCESS	read-only
		STATUS	mandatory
		DESCRIPTION
			"The defalut LLC transmit window size.
			 Current allowable values are 1-7.
			 The default value for this field is 7."
		::= { lanPortEntry 10 }

	lanMaxRetries	OBJECT-TYPE
		SYNTAX	INTEGER (1..99)
		ACCESS	read-only
		STATUS	mandatory
		DESCRIPTION
			"The default LLC maximum number of retries (N2 value).
			 Current allowable values are 1-99.
			 The default value for this field is 3."
		::= { lanPortEntry 11 }

	lanRingNumber	OBJECT-TYPE
		SYNTAX	INTEGER (0..4095)
		ACCESS	read-only
		STATUS	mandatory
		DESCRIPTION
			"802.5 bridging parameter.
			 This variable returns a value of 0, if it is not 
			 defined.  
			 This value is not applicable to Ethernet."
		::= { lanPortEntry 12 }

	lanBridgeNumber	OBJECT-TYPE
		SYNTAX	INTEGER (1..15)
		ACCESS	read-only
		STATUS	mandatory
		DESCRIPTION
			"802.5 bridging parameter.
			 The default value for this field is 1.
			 This value is not applicable to Ethernet."
		::= { lanPortEntry 13 }

	lanEthernetFrameFormat
		OBJECT-TYPE
		SYNTAX	INTEGER {
			not-applicable(1),
			e802-3-type(2),
			ethernet-type-2(3)
			}
		ACCESS	read-only
		STATUS	mandatory
		DESCRIPTION
			"The Ethernet frame format used on this LAN.
			 The default value for this field is 802.3.
			 Not used if Token Ring, and 1 is returned."
		::= { lanPortEntry 14 }

	lanSendLocalTest	OBJECT-TYPE
		SYNTAX	INTEGER {
			not-applicable(1),
			yes(2),
			no(3)
			}
		ACCESS	read-only
		STATUS	mandatory
		DESCRIPTION
			"This port's send local test option. 

			 Identifies whether a test frame should be sent on the
			 local ring to discover a destination MAC address.

			 If all destinations for the unit are located on a 
			 remote ring, setting this field to No allows the unit
			 to bypass discovery of a destination MAC address on
			 the local ring.  If this field is set to 'No' then
			 the broadcastType field must be set to all routes or
			 single route broadcast.

			 If the any destination is on a local ring or unknown,
			 this parameter should be set to 'Yes'.

			 The default value for this field is 'Yes'.

			 Not used if Ethernet, and 1 is returned."
		::= { lanPortEntry 15 }

	lanBroadcastType	OBJECT-TYPE
		SYNTAX	INTEGER {
			not-applicable(1),
			none-bc(2),
			all-bc(3),
			single-bc(4)
			}
		ACCESS	read-only
		STATUS	mandatory
		DESCRIPTION
			"This port's broadcast type. Not used if Ethernet.

			 Types are:  none, all-routes, and single-route.
			 Identifies the form of a broadcast test frame
			 sent to discover the route to a destination MAC
			 address.

			 If all destinations are located on the local ring,
			 this field may be set to 'None' to prevent a
			 broadcast search for a destination MAC address.  If
			 set to 'None', then the sendLocalTest field must be
			 set to 'Yes'.

			 If set as 'All-routes', the unit will send an
			 All-routes broadcast TEST command frame and expect a 
			 non-broadcast TEST response frame in return.

			 If set to Single-route, the unit will send a
			 Single-route broadcast TEST command frame and expect a 
			 all-routes TEST response frame in return.

			 The default for this field is all routes broadcast. 

			 Not used if Ethernet, and 1 is returned."
		::= { lanPortEntry 16 }

	lanIPAddress OBJECT-TYPE
		SYNTAX	IpAddress
		ACCESS	read-only
		STATUS	mandatory
		DESCRIPTION
			"This is the IP Address of this interface."
		::= { lanPortEntry 17 }

	lanNetworkMask OBJECT-TYPE
		SYNTAX	IpAddress
		ACCESS	read-only
		STATUS	mandatory
		DESCRIPTION
			"This is the network mask to be used on this 
                      interface."
		::= { lanPortEntry 18 }

	lanDefaultGateway OBJECT-TYPE
		SYNTAX	IpAddress
		ACCESS	read-only
		STATUS	mandatory
		DESCRIPTION
			"Default gateway address to be used when sending
                      responses on this interface."
		::= { lanPortEntry 19 }

	lanNAUName 	OBJECT-TYPE
		SYNTAX	DisplayString (SIZE(1..8))
		ACCESS	read-only
		STATUS	mandatory
		DESCRIPTION
			"The NAU name of this port.
			 The default value for this field is all blank
			 (filled with ASCII space 0x20 characters)."
		::= { lanPortEntry 20 }

	lanInterfaceType	OBJECT-TYPE
		SYNTAX	INTEGER {
			not-applicable(1),
			aui(2),
			bnc(3),
			utp(4)
			}
		ACCESS	read-only
		STATUS	mandatory
		DESCRIPTION
			"This port's physical interface type. Only used if
			 Ethernet.  The default for this field is utp.  
			 Not used if Token Ring, and 1 is returned."
		::= { lanPortEntry 21 }

	lanIPEthernetFrameType 		OBJECT-TYPE
		SYNTAX	INTEGER {
			not-applicable(1),
			e802-3-type(2),
			ethernet-type-2(3)
			}
		ACCESS	read-only
		STATUS	mandatory
		DESCRIPTION
			"The IP Ethernet frame format used on this LAN for IP
			 frames. The default value for this field is 802.3.
			 Not used if Token Ring, and 1 is returned."
		::= { lanPortEntry 22 }

	lanInitState	OBJECT-TYPE
		SYNTAX	INTEGER {
			in-service(1),
			out-of-service(2)
			}
		ACCESS	read-only
		STATUS	mandatory
		DESCRIPTION
			"The initial state of the LAN port.

			 If configured for 'in-service', then the LAN port will
			 be brougt up automattically when the unit is powered
			 up.

			 If configured for 'out-of-service', the the LAN port 
			 must be manually enabled by operator intervention (i.e.
			 enable command must be sent).

			 The default value is 'enabled'."
		::= { lanPortEntry 23 }

	--
	-- The Line Control Group
	--

	lineControlTable OBJECT-TYPE
		SYNTAX SEQUENCE OF LineControlEntry
		ACCESS 	not-accessible
		STATUS	mandatory
		DESCRIPTION
			"A table for controlling lines and obtaining
			 information." 
		::= { lineControlGroup 1 }

	lineControlEntry OBJECT-TYPE
		SYNTAX  LineControlEntry
		ACCESS 	not-accessible
		STATUS	mandatory
		DESCRIPTION
			"An entry consisting of port information for a
			 particular port." 
		INDEX { lineControlIndex }
		::= { lineControlTable 1 }

	LineControlEntry ::=
		SEQUENCE {
			lineControlIndex
				INTEGER,
			lineControlType
				INTEGER,
			lineStatus
				INTEGER,
                    	lineControlFailureCode
                            	OCTET STRING,
                        lineControlNAUName
                            DisplayString
		}
				

	lineControlIndex	OBJECT-TYPE
		SYNTAX	INTEGER 
		ACCESS	read-only
		STATUS	mandatory
		DESCRIPTION
			"The port number that uniquely identifies
			 this port."
		::= { lineControlEntry 1 }


	lineControlType	OBJECT-TYPE
		SYNTAX	INTEGER {
			hbsc-type(1),
			tbsc-type(2),
			hsdlc-type(11),
			tsdlc-type(12),
			frameRelay-type(19)
			}
		ACCESS	read-only
		STATUS	mandatory
		DESCRIPTION
			"The port type.

			 TSDLC (Terminal SDLC) ports emulate a Host
			 and poll the downstream PUs (e.g. 3274 or 3174
			 SDLC/SNA controllers).

			 HSDLC ports (Host SDLC) ports emulate a line with
			 Terminal Controllers (PUs) and respond to polls
			 from the Host or upstream PU.

			 TBSC (Terminal Bisync) ports emulate a Host
			 and poll the downstream CUs (e.g. 3274 or ATM
			 Bisync controllers).

			 HBSC ports (Host Bisync) ports emulate a line with
			 Terminal Controllers (CUs) and respond to polls
			 from the Host or upstream CU.

			 Frame Relay ports support Frame Relay PVC.

			 Future line types (e.g. X.25) may be added here."
		::= { lineControlEntry 2 }

	lineStatus	OBJECT-TYPE
		SYNTAX	INTEGER {
			enable(1),
			disable(2),
			failed(3),
			restart(4),
			enable-all(5)
			}
		ACCESS	read-write
		STATUS	mandatory
		DESCRIPTION
			"The status of the port.
			 To change status of a port an enable, enable all
			 or disable may be set.

		
			 Valid Return status are enable(d), disable(d),
			 or failed.

			 Commands:
			 An enable command will attempt to bring up the line.
			 An enable all command will attempt to bring up
			 the line and any lower layer entities (e.g. PUs).
			 A disable command will disable the line.
			 
			 Status:
			 Enable(d) indicates the line is enabled and running.
			 Disable(d) indicates the line has been disabled.
			 Failed indicates the line is enabled and not 
			 Running."
		::= { lineControlEntry 3 }

	lineControlFailureCode 	OBJECT-TYPE
		SYNTAX	OCTET STRING (SIZE (2))
		ACCESS	read-only
		STATUS	mandatory
		DESCRIPTION
			"This entry contains the failure codes if the
                      associated port interface is in the failed state."
		::= { lineControlEntry 4 }

	lineControlNAUName 	OBJECT-TYPE
		SYNTAX	DisplayString (SIZE(1..8))
		ACCESS	read-only
		STATUS	mandatory
		DESCRIPTION
			"The NAU name of this port.
			 The default value for this field is all blank
			 (filled with ASCII space 0x20 characters)."
		::= { lineControlEntry 5 }


	--
	-- The Line Physical Control Group
	--
	-- This is a separate group as not all 'lines' have an RS-232
	-- or other WAN physical interface (e.g. V.35, RS-449 etc.)
	--

	linePhysicalTable OBJECT-TYPE
		SYNTAX  SEQUENCE OF LinePhysicalEntry
		ACCESS 	not-accessible
		STATUS	mandatory
		DESCRIPTION
			"A table for obtaining physical signal status
			 information." 
		::= { linePhysicalGroup 1 }

	linePhysicalEntry OBJECT-TYPE
		SYNTAX  LinePhysicalEntry
		ACCESS 	not-accessible
		STATUS	mandatory
		DESCRIPTION
			"An entry consisting of port information for a
			 particular port." 
		INDEX { linePhysicalIndex }
		::= { linePhysicalTable 1 }

	LinePhysicalEntry ::=
		SEQUENCE {
			linePhysicalIndex
				INTEGER,
			linePhysicalType
				INTEGER,
			lineEIAStatus
				INTEGER,
			lineQualityFrameCount
				Counter,
			lineQualityCRCErrors
				Counter,
			lineQualityAborts
				Counter
		}
				

	linePhysicalIndex	OBJECT-TYPE
		SYNTAX	INTEGER 
		ACCESS	read-only
		STATUS	mandatory
		DESCRIPTION
			"The port number that uniquely identifies
			 this port."
		::= { linePhysicalEntry 1 }


	linePhysicalType OBJECT-TYPE
		SYNTAX	INTEGER {
			tbsc-type(1),
			hbsc-type(2),
			frameRelay-type(19),
			hsdlc-type(11),
			tsdlc-type(12)
			}
		ACCESS	read-only
		STATUS	mandatory
		DESCRIPTION
			"The port type.

			 TSDLC (Terminal SDLC) ports emulate a Host
			 and poll the downstream PUs (e.g. 3274 or 3174
			 SDLC/SNA controllers).

			 HSDLC ports (Host SDLC) ports emulate a line with
			 Terminal Controllers (PUs) and respond to polls
			 from the Host or upstream PU.

			 TBSC (Terminal Bisync) ports emulate a Host
			 and poll the downstream CUs (e.g. 3274 or ATM
			 Bisync controllers).

			 HBSC ports (Host Bisync) ports emulate a line with
			 Terminal Controllers (CUs) and respond to polls
			 from the Host or upstream CU.

			 Frame Relay ports support Frame Relay PVC."

		::= { linePhysicalEntry 2 }

	lineEIAStatus	OBJECT-TYPE
		SYNTAX	INTEGER (0..65535)
		ACCESS	read-only
		STATUS	mandatory
		DESCRIPTION
			"A port's current control signal status.

			 All SDLC ports have the ability to read
			 the current status of RS-232 or equivalent
			 control signals.

			 The value returned is a 16 bit value where each
			 bit signifies a signal status where 1 means the
			 signal is active and 0 means the signal is inactive.

			 The value returned is a snapshot taken when the
			 command actually is sent to the driver software and
			 wherever possible actually goes out to the driver
			 or receiver control chips to get the value.

			 Currently defined bit values are as follows*:
			  128 : Data Terminal Ready  0x0080 RS-232 pin 20
			   64 : Data Set Ready       0x0040 RS-232 pin 6
			   32 : Clear to Send        0x0020 RS-232 pin 5
			   16 : Clear to Send Ext.   0x0010 RS-232 pin 11**
			    8 : Data Carrier Detect  0x0008 RS-232 pin 8
			    4 : Busy Out             0x0004 RS-232 pin 25
			    2 : Request to send      0x0002 RS-232 pin 4
			    1 : Ring Indicator       0x0001 RS-232 pin 22

			 Note*: Bit values higher than 128 are reserved for
				future use.

			 Note**: Clear to Send External is extended (non-
				 standard) pin and reserved for future use
				 by Sync Research."
		::= { linePhysicalEntry 3 }

	lineQualityFrameCount	OBJECT-TYPE
		SYNTAX	Counter
		ACCESS	read-only
		STATUS	mandatory
		DESCRIPTION
			"This entry contains the number of frames received. 
			 For every 255 incoming frames, a trap is generated by  
			 the unit if lineQualityCRCErrors or lineQualityAborts
			 exceeds 5.  When this value reaches its maximum, it  
			 then rolls back to 0.  Applicable to SDLC only."
		::= { linePhysicalEntry 4}

	lineQualityCRCErrors	OBJECT-TYPE
		SYNTAX	Counter
		ACCESS	read-only
		STATUS	mandatory
		DESCRIPTION
			"This entry contains the number of frames with CRC  
			 errors.  For every 255 incoming frames, a trap is 
			 generated by the unit if lineQualityCRCErrors or 
			 lineQualityAborts exceeds 5.  Applicable to SDLC only."
		::= { linePhysicalEntry 5 }


	lineQualityAborts	OBJECT-TYPE
		SYNTAX	Counter
		ACCESS	read-only
		STATUS	mandatory
		DESCRIPTION
			"This entry contains the number of aborts received.
			 For every 255 incoming frames, a trap is generated  
			 by the unit if lineQualityCRCErrors or 
			 lineQualityAborts exceeds 5.
			 Applicable to SDLC only."
		::= { linePhysicalEntry 6 }


	--
	-- The SDLC Port Level Configuration Group
	--

	--
	-- The SDLC Configuration Table:
	--

	sdlcConfigTable	OBJECT-TYPE
		SYNTAX SEQUENCE OF SdlcConfigEntry
		ACCESS 	not-accessible
		STATUS	mandatory
		DESCRIPTION
			"A table of SDLC information." 
		::= { lineSDLCGroup 1 }

	sdlcConfigEntry	OBJECT-TYPE
		SYNTAX  SdlcConfigEntry
		ACCESS 	not-accessible
		STATUS	mandatory
		DESCRIPTION
			"An entry consisting of port information for a
			 particular SDLC port." 
		INDEX { sdlcConfigPortIndex }
		::= { sdlcConfigTable 1 }

	SdlcConfigEntry ::=
		SEQUENCE {
			sdlcConfigPortIndex
				INTEGER,
			sdlcConfigType
				INTEGER,
			sdlcInitState
				INTEGER,
			sdlcCarrier
				INTEGER,
			sdlcClocking
				INTEGER,
			sdlcSpeed
				INTEGER,
			sdlcPause
				INTEGER,
			sdlcNRZI
				INTEGER,
			sdlcT1Timer
				INTEGER,
			sdlcSlowPollTimer
				INTEGER,
			sdlcMaxRetries
				INTEGER,
                     sdlcNAUName
                            DisplayString,
                     sdlcMultiFlagInsertion
                            INTEGER
		}
				

	sdlcConfigPortIndex	OBJECT-TYPE
		SYNTAX	INTEGER 
		ACCESS	read-only
		STATUS	mandatory
		DESCRIPTION
			"The port number that uniquely identifies
			 this port.
			 Current supported SDLC numbers are 1-4."
		::= { sdlcConfigEntry 1 }


	sdlcConfigType	OBJECT-TYPE
		SYNTAX	INTEGER {
			hsdlc-type(11),
			tsdlc-type(12)
			}
		ACCESS	read-only
		STATUS	mandatory
		DESCRIPTION
			"The port type.

			 TSDLC (Terminal SDLC) ports emulate a Host
			 and poll the downstream PUs (e.g. 3274 or 3174
			 SDLC/SNA controllers).

			 HSDLC ports (Host SDLC) ports emulate a line with
			 Terminal Controllers (PUs) and respond to polls
			 from the Host or upstream PU.

			 Note that all ports must currently be defined as
			 the same time for a given unit (i.e. no mixing of
			 HSDLC and TSDLC ports is allowed)."
		::= { sdlcConfigEntry 2 }

	sdlcInitState	OBJECT-TYPE
		SYNTAX	INTEGER {
			in-service(1),
			out-of-service(2)
			}
		ACCESS	read-only
		STATUS	mandatory
		DESCRIPTION
			"The initial state of the SDLC port.

			 If configured for 'in-service', then the SDLC port will
			 be brougt up automattically when the unit is powered
			 up.

			 If configured for 'out-of-service', the the SDLC port must
			 be manually enabled by operator intervention (i.e.
			 enable command must be sent).

			 The default value is 'enabled'."
		::= { sdlcConfigEntry 3 }

	sdlcCarrier	OBJECT-TYPE
		SYNTAX	INTEGER {
			constant(1),
			switched(2)
			}
		ACCESS	read-only
		STATUS	mandatory
		DESCRIPTION
			"This field indicates whether Carrier (a.k.a. CD or
			 DCD, RS-232 pin 8) is constant or switched for 
			 DCE devices (internally clocked), or Request To
			 Send (a.k.a. RTS, RS-232 pin 4) is constant or
			 switched.

			 This parameter also affects SDLC flag generation.
			 If configured for constant then the line will
			 transmit flags in an idle (no data being sent) state.
			 If configured for switched then the line will
			 transmit all one bits (mark state).

			 The default value for this parameter is 'constant'."
		::= { sdlcConfigEntry 4 }

	sdlcClocking	OBJECT-TYPE
		SYNTAX	INTEGER {
			external(1),
			internal(2),
			x21-external(3),
			x21-internal(4)
			}
		ACCESS	read-only
		STATUS	mandatory
		DESCRIPTION
			"Clocking source for this port.
			 Setting 'internal' will cause the
			 port to emulate a physical DCE, and setting
			 external will cause the port to emulate a
			 physical DTE.
			 X21 External and Internal are used (with the
                         proper external adapter) to support X.21 Leased
			 Line operation for RS-422/RS-530 (25 pin balanced)
                         interfaces.  X21 operation is not supported for
			 boards that operate RS-232 or V.35.
			 The default value for this field is 'external'."
		::= { sdlcConfigEntry 5 }

	sdlcSpeed	OBJECT-TYPE
		SYNTAX	INTEGER 
--			{
--			speed1200(12),
--			speed2000(20),
--			speed2400(24),
--			speed3600(36),
--			speed4800(48),
--			speed7200(72),
--			speed9600(96),
--			speed14400(144),
--			speed19200(192),
--			speed28800(288),
--			speed48000(480),
--			speed56000(560),
--			speed64000(640),
--			speed128000(1280)
--			}
		ACCESS	read-only
		STATUS	mandatory
		DESCRIPTION
			"The ports speed in bits per second.
			 The default value is 9600 bits per second.
			 Speeds higher than 19200 are not supported on
			 RS-232 ports units (must be V.35 or RS-422)."
		::= { sdlcConfigEntry 6 }

	sdlcPause	OBJECT-TYPE
		SYNTAX	INTEGER 
		ACCESS	read-only
		STATUS	mandatory
		DESCRIPTION
			"This parameter defines the amount of time
			 between polls in 1/100 second (10 millisecond)
			 intervals.  If set to zero then the port will
			 poll the PUs as fast as possible.  The minimum
			 value for this parameter is 5 and the timer
			 has a resolution of 25 milliseconds.
			 The default value is 20 (.20 seconds).
			 This field is not applicable to Host port.  It
			 returns a dummy value."
		::= { sdlcConfigEntry 7 }

	sdlcNRZI	OBJECT-TYPE
		SYNTAX	INTEGER {
			yes(1),
			no(2)
			}
		ACCESS	read-only
		STATUS	mandatory
		DESCRIPTION
			"This parameter indicates whether the port is
			 configured for NRZI (yes) or NRZ (no) bit
			 encoding.
			 The default value is 'No' (NRZ encoding selected)."
		::= { sdlcConfigEntry 8 }

	sdlcT1Timer	OBJECT-TYPE
		SYNTAX	INTEGER
		ACCESS	read-only
		STATUS	mandatory
		DESCRIPTION
			"The SDLC T1 timer value in 20ths of a second.
			 The default value is 20 (5 seconds).
			 This field is not applicable to Host ports.  It
			 returns a dummy value."
		::= { sdlcConfigEntry 9 }

	sdlcSlowPollTimer OBJECT-TYPE
		SYNTAX	INTEGER
		ACCESS	read-only
		STATUS	mandatory
		DESCRIPTION
			"The slow poll timer value in 20ths of a second.
			 The slow poll timer is the amount of time to wait
			 to contact (send SNRM) failed PUs.
			 The default value for this field is 600 (30 seconds).
			 This field is not applicable to Host ports.  It
			 returns a dummy value."
		::= { sdlcConfigEntry 10 }

	sdlcMaxRetries	OBJECT-TYPE
		SYNTAX	INTEGER (1..99)
		ACCESS	read-only
		STATUS	mandatory
		DESCRIPTION
			"The maximum number of retries (N2 value) before
			 failing a PU.
			 The default value for this field is 3.
			 This field is not applicable to Host ports.  It
			 returns a dummy value."

		::= { sdlcConfigEntry 11 }
	
	sdlcNAUName 	OBJECT-TYPE
		SYNTAX	DisplayString (SIZE(1..8))
		ACCESS	read-only
		STATUS	mandatory
		DESCRIPTION
			"The NAU name of this port.
			 The default value for this field is all blank
			 (filled with ASCII space 0x20 characters)."
		::= { sdlcConfigEntry 12 }

       sdlcMultiFlagInsertion 	OBJECT-TYPE
		SYNTAX	INTEGER {
			yes(1),
			no(2)
			}
		ACCESS	read-only
		STATUS	mandatory
		DESCRIPTION
			"This parameter indicates whether the port is
			 configured to send multiple interframe flags. 
			 The default value is 'No' (single flags)."
		::= { sdlcConfigEntry 13 }


	--
	-- The SDLC Port Statistics Table:
	--

	sdlcStatsTable	OBJECT-TYPE
		SYNTAX SEQUENCE OF SdlcStatsEntry
		ACCESS 	not-accessible
		STATUS	mandatory
		DESCRIPTION
			"A table of SDLC information." 
		::= { lineSDLCGroup 2 }

	sdlcStatsEntry	OBJECT-TYPE
		SYNTAX  SdlcStatsEntry
		ACCESS 	not-accessible
		STATUS	mandatory
		DESCRIPTION
			"An entry consisting of port information for a
			 particular SDLC port." 
		INDEX { sdlcStatsPortIndex }
		::= { sdlcStatsTable 1 }

	SdlcStatsEntry ::=
		SEQUENCE {
			sdlcStatsPortIndex
				INTEGER,
			sdlcPortType
				INTEGER,
			sdlcInOctets
				Counter,
			sdlcOutOctets
				Counter,
			sdlcInFrames
				Counter,
			sdlcOutFrames
				Counter,
			sdlcOverruns
				Counter,
			sdlcCRCErrors
				Counter,
			sdlcRecvAborts
				Counter
		}
				

	sdlcStatsPortIndex OBJECT-TYPE
		SYNTAX	INTEGER 
		ACCESS	read-only
		STATUS	mandatory
		DESCRIPTION
			"The port number that uniquely identifies
			 this SDLC port.
			 Current supported numbers on are 1-4."
		::= { sdlcStatsEntry 1 }


	sdlcPortType	OBJECT-TYPE
		SYNTAX	INTEGER {
			hsdlc-type(11),
			tsdlc-type(12)
			}
		ACCESS	read-only
		STATUS	mandatory
		DESCRIPTION
			"The port type.
			 TSDLC (Terminal SDLC) ports emulate a Host
			 and poll the downstream PUs (e.g. 3274 or 3174
			 SDLC/SNA controllers).
			 HSDLC ports (Host SDLC) ports emulate a line with
			 Terminal Controllers (PUs) and respond to polls
			 from the Host or upstream PU."
		::= { sdlcStatsEntry 2 }

	sdlcInOctets OBJECT-TYPE
		SYNTAX	Counter
		ACCESS	read-only
		STATUS	mandatory
		DESCRIPTION
			"The number of bytes received."
		::= { sdlcStatsEntry 3 }

	sdlcOutOctets OBJECT-TYPE
		SYNTAX	Counter
		ACCESS	read-only
		STATUS	mandatory
		DESCRIPTION
			"The number of bytes sent."
		::= { sdlcStatsEntry 4 }

	sdlcInFrames OBJECT-TYPE
		SYNTAX	Counter
		ACCESS	read-only
		STATUS	mandatory
		DESCRIPTION
			"The number of I-frames received."
		::= { sdlcStatsEntry 5 }

	sdlcOutFrames OBJECT-TYPE
		SYNTAX	Counter
		ACCESS	read-only
		STATUS	mandatory
		DESCRIPTION
			"The number of I-frames sent."
		::= { sdlcStatsEntry 6 }

	sdlcOverruns	OBJECT-TYPE
		SYNTAX	Counter
		ACCESS	read-only
		STATUS	mandatory
		DESCRIPTION
			"The number of overruns."
		::= { sdlcStatsEntry 7 }

	sdlcCRCErrors	OBJECT-TYPE
		SYNTAX	Counter
		ACCESS	read-only
		STATUS	mandatory
		DESCRIPTION
			"The number of CRC errors."
		::= { sdlcStatsEntry 8 }


	sdlcRecvAborts	OBJECT-TYPE
		SYNTAX	Counter
		ACCESS	read-only
		STATUS	mandatory
		DESCRIPTION
			"The number of aborts received."
		::= { sdlcStatsEntry 9 }


	--
	-- The Bisync Port Level Group
	--
	--
	-- The Bisync Configuration Table:
	--

	bisyncConfigTable	OBJECT-TYPE
		SYNTAX SEQUENCE OF BisyncConfigEntry
		ACCESS 	not-accessible
		STATUS	mandatory
		DESCRIPTION
			"A table of Bisync port information." 
		::= { lineBisyncGroup 1 }

	bisyncConfigEntry	OBJECT-TYPE
		SYNTAX  BisyncConfigEntry
		ACCESS 	not-accessible
		STATUS	mandatory
		DESCRIPTION
			"An entry consisting of port information for a
			 particular Bisync port." 
		INDEX { bisyncConfigPortIndex }
		::= { bisyncConfigTable 1 }

	BisyncConfigEntry ::=
		SEQUENCE {
			bisyncConfigPortIndex
				INTEGER,
			bisyncConfigType
				INTEGER,
                        bisyncNAUName
                                DisplayString,
			bisyncInitState
				INTEGER,
			bisyncCarrier
				INTEGER,
			bisyncClocking
				INTEGER,
			bisyncSpeed
				INTEGER,
			bisyncPause
				INTEGER,
			bisyncReplyTimer
				INTEGER,
			bisyncRetries
				INTEGER,
			bisyncSlowpollTimer
				INTEGER,
			bisyncSessTerm
				INTEGER
		}
				
	bisyncConfigPortIndex	OBJECT-TYPE
		SYNTAX	INTEGER 
		ACCESS	read-only
		STATUS	mandatory
		DESCRIPTION
			"The port number that uniquely identifies
			 this port.
			 Current supported Bisync numbers are 1-4."
		::= { bisyncConfigEntry 1 }


	bisyncConfigType	OBJECT-TYPE
		SYNTAX	INTEGER {
			hbsc-type(1),
			tbsc-type(2)
			}
		ACCESS	read-only
		STATUS	mandatory
		DESCRIPTION
			"The port type.

			 TBSC (Terminal Bisync) ports emulate a Host
			 and polls the downstream controllers).

			 HBSC ports (Host Bisync) ports emulate a line with
			 Terminal Controllers (CUs) and respond to polls
			 from the Host."

		::= { bisyncConfigEntry 2 }

	bisyncNAUName 	OBJECT-TYPE
		SYNTAX	DisplayString (SIZE(1..8))
		ACCESS	read-only
		STATUS	mandatory
		DESCRIPTION
			"The NAU name of this port.
			 The default value for this field is all blank
			 (filled with ASCII space 0x20 characters)."
		::= { bisyncConfigEntry 3 }

	bisyncInitState	OBJECT-TYPE
		SYNTAX	INTEGER {
			in-service(1),
			out-of-service(2)
			}
		ACCESS	read-only
		STATUS	mandatory
		DESCRIPTION
			"The initial state of the Bisync port.

			 If configured for 'in-service', then the Bisync port will
			 be brougt up automattically when the unit is powered
			 up.

			 If configured for 'out-of-service', then the Bisync port must
			 be manually enabled by operator intervention (i.e.
			 enable command must be sent).

			 The default value is 'enabled'."
		::= { bisyncConfigEntry 4 }

	bisyncCarrier	OBJECT-TYPE
		SYNTAX	INTEGER {
			constant(1),
			switched(2)
			}
		ACCESS	read-only
		STATUS	mandatory
		DESCRIPTION
			"This field indicates whether Carrier (a.k.a. CD or
			 DCD, RS-232 pin 8) is constant or switched for 
			 DCE devices (internally clocked), or Request To
			 Send (a.k.a. RTS, RS-232 pin 4) is constant or
			 switched.

			 The default value for this parameter is 'constant'."
		::= { bisyncConfigEntry 5 }

	bisyncClocking	OBJECT-TYPE
		SYNTAX	INTEGER {
			external(1),
			internal(2),
			x21-external(3),
			x21-internal(4)
			}
		ACCESS	read-only
		STATUS	mandatory
		DESCRIPTION
			"Clocking source for this port.
			 Setting 'internal' will cause the
			 port to emulate a physical DCE, and setting
			 external will cause the port to emulate a
			 physical DTE.
			 X21 External and Internal are used (with the
			 proper external adapter) to support X.21 Leased
			 Line operation for RS-422/RS-530 (25 pin balanced)
			 interfaces.  X21 operation is not supported for
			 boards that operate RS-232 or V.35.
			 The default value for this field is 'external'."
		::= { bisyncConfigEntry 6 }

	bisyncSpeed	OBJECT-TYPE
		SYNTAX	INTEGER 
--			{
--			speed1200(12),
--			speed2000(20),
--			speed2400(24),
--			speed3600(36),
--			speed4800(48),
--			speed7200(72),
--			speed9600(96),
--			speed14400(144),
--			speed19200(192),
--			speed28800(288),
--			speed48000(480),
--			speed56000(560),
--			speed64000(640)
--			}
		ACCESS	read-only
		STATUS	mandatory
		DESCRIPTION
			"The ports speed in bits per second.
			 The default value is 9600 bits per second.
			 Speeds higher than 64000 are not supported."
		::= { bisyncConfigEntry 7 }

	bisyncPause OBJECT-TYPE
		SYNTAX	INTEGER
		ACCESS	read-only
		STATUS	mandatory
		DESCRIPTION
			"This parameter defines the amount of time
			 between polls in 1/100 second (10 millisecond)
			 intervals.  If set to zero then the port will
			 poll the CUs as fast as possible.  The minimum
			 value for this parameter is 5 and the timer
			 has a resolution of 25 milliseconds.
			 The default value is 20 (.20 seconds).
			 This field is not applicable to a Host port. It
			 returns a dummy value."
		::= { bisyncConfigEntry 8 }

	bisyncReplyTimer	OBJECT-TYPE
		SYNTAX	INTEGER (1..99)
		ACCESS	read-only
		STATUS	mandatory
		DESCRIPTION
			"The time to wait for a response in seconds.
			 The default value for this field is 3 seconds."

		::= { bisyncConfigEntry 9 }
	
	bisyncRetries	OBJECT-TYPE
		SYNTAX	INTEGER (1..99)
		ACCESS	read-only
		STATUS	mandatory
		DESCRIPTION
			"The maximum number of retries (N2 value) before
			 failing a CU.
			 The default value for this field is 5."

		::= { bisyncConfigEntry 10 }
	
	bisyncSlowpollTimer	OBJECT-TYPE
		SYNTAX	INTEGER (1..99)
		ACCESS	read-only
		STATUS	mandatory
		DESCRIPTION
			"The time to wait in seconds before attempting a 
                         slowpoll.
			 The default value for this field is 30 seconds."

		::= { bisyncConfigEntry 11 }
	
	bisyncSessTerm 	OBJECT-TYPE
		SYNTAX	INTEGER {
                        none (1),
                        interventionReq (2),
                        unformattedLogoff (3)
                        }
		ACCESS	read-only
		STATUS	mandatory
		DESCRIPTION
			"The type of session termination used. Only
			 applies to Host BSC ports."
		::= { bisyncConfigEntry 12 }


	--
	-- The Bisync Port Statistics Table:
	--

	bisyncStatsTable	 OBJECT-TYPE
		SYNTAX SEQUENCE OF BisyncStatsEntry
		ACCESS 	not-accessible
		STATUS	mandatory
		DESCRIPTION
			"A table of Bisync information." 
		::= { lineBisyncGroup 2 }

	bisyncStatsEntry	 OBJECT-TYPE
		SYNTAX  BisyncStatsEntry
		ACCESS 	not-accessible
		STATUS	mandatory
		DESCRIPTION
			"An entry consisting of port information for a
			 particular Bisync port." 
		INDEX { bisyncStatsPortIndex }
		::= { bisyncStatsTable 1 }

	BisyncStatsEntry ::=
		SEQUENCE {
			bisyncStatsPortIndex
				INTEGER,
			bisyncPortType
				INTEGER,
			bisyncInOctets
				Counter,
			bisyncOutOctets
				Counter,
			bisyncOverruns
				Counter,
			bisyncCRCErrors
				Counter,
                        bisyncRcvTimeout
				Counter,
                        bisyncXmtTimeout
				Counter
		}
				

	bisyncStatsPortIndex OBJECT-TYPE
		SYNTAX	INTEGER 
		ACCESS	read-only
		STATUS	mandatory
		DESCRIPTION
			"The port number that uniquely identifies
			 this Bisync port.
			 Current supported numbers are 1-4."
		::= { bisyncStatsEntry 1 }


	bisyncPortType	OBJECT-TYPE
		SYNTAX	INTEGER {
			hbsc-type(1),
			tbsc-type(2)
			}
		ACCESS	read-only
		STATUS	mandatory
		DESCRIPTION
			"The port type.
			 TBSC (Terminal Bisync) ports emulate a Host
			 and poll the downstream controllers).
			 HBSC ports (Host Bisync) ports emulate a line with
			 Terminal Controllers (PUs) and respond to polls
			 from the Host or upstream PU."
		::= { bisyncStatsEntry 2 }

	bisyncInOctets OBJECT-TYPE
		SYNTAX	Counter
		ACCESS	read-only
		STATUS	mandatory
		DESCRIPTION
			"The number of bytes received."
		::= { bisyncStatsEntry 3 }

	bisyncOutOctets OBJECT-TYPE
		SYNTAX	Counter
		ACCESS	read-only
		STATUS	mandatory
		DESCRIPTION
			"The number of bytes sent."
		::= { bisyncStatsEntry 4 }

	bisyncOverruns	OBJECT-TYPE
		SYNTAX	Counter
		ACCESS	read-only
		STATUS	mandatory
		DESCRIPTION
			"The number of receiver overruns."
		::= { bisyncStatsEntry 5 }

	bisyncCRCErrors	OBJECT-TYPE
		SYNTAX	Counter
		ACCESS	read-only
		STATUS	mandatory
		DESCRIPTION
			"The number of receive frame CRC errors."
		::= { bisyncStatsEntry 6 }

	bisyncRcvTimeout OBJECT-TYPE
		SYNTAX	Counter
		ACCESS	read-only
		STATUS	mandatory
		DESCRIPTION
			"The number of receive timeout."
		::= { bisyncStatsEntry 7 }

	bisyncXmtTimeout OBJECT-TYPE
		SYNTAX	Counter
		ACCESS	read-only
		STATUS	mandatory
		DESCRIPTION
			"The number of transmit timeout."
		::= { bisyncStatsEntry 8 }

	--
	-- The Frame Relay Port Level Group
	--
	--
	-- The Frame Relay Configuration Table:
	--

	frameRelayConfigTable	OBJECT-TYPE
		SYNTAX SEQUENCE OF FrameRelayConfigEntry
		ACCESS 	not-accessible
		STATUS	mandatory
		DESCRIPTION
			"A table of Sync product Frame Relay information." 
		::= { lineFrameRelayGroup 1 }

	frameRelayConfigEntry	OBJECT-TYPE
		SYNTAX  FrameRelayConfigEntry
		ACCESS 	not-accessible
		STATUS	mandatory
		DESCRIPTION
			"An entry consisting of port information for a
			 particular Sync product Frame Relay port." 
		INDEX { frameRelayConfigPortIndex }
		::= { frameRelayConfigTable 1 }

	FrameRelayConfigEntry ::=
		SEQUENCE {
			frameRelayConfigPortIndex
				INTEGER,
			frameRelayPortType
				INTEGER,
			frameRelayInitState
				INTEGER,
			frameRelayClocking
				INTEGER,
			frameRelaySpeed
				INTEGER,
			frameRelayLocalManagementProtocol
				INTEGER,
			frameRelayLinkPollingTimer
				INTEGER,
			frameRelayFullStatusPollingCount
				INTEGER,
			frameRelayT1Timer	
				INTEGER,
			frameRelayT2Timer
				INTEGER,
			frameRelayTiTimer
				INTEGER,
			frameRelayRxWindowSize
				INTEGER,
			frameRelayTxWindowSize
				INTEGER,
			frameRelayMaxRetries	
				INTEGER,
                     frameRelayNAUName
                            DisplayString,
                     frameRelayVirtualMACAddress 
                            PhysAddress,
                     frameRelayVirtualRingNumber
                            INTEGER,
                     frameRelayVirtualBridgeNumber
				INTEGER,
			frameRelayIPAddress 
				IpAddress,
			frameRelayNetworkMask 
				IpAddress,
			frameRelayDefaultGatewayAddress 
				IpAddress
		}
				
	frameRelayConfigPortIndex	OBJECT-TYPE
		SYNTAX	INTEGER 
		ACCESS	read-only
		STATUS	mandatory
		DESCRIPTION
			"The port number that uniquely identifies
			 this port."
		::= { frameRelayConfigEntry 1 }

	frameRelayPortType	OBJECT-TYPE
		SYNTAX	INTEGER {
			frame-relay-type(19)
			}
		ACCESS	read-only
		STATUS	mandatory
		DESCRIPTION
			"The Frame Relay port type."
		::= { frameRelayConfigEntry 2 }
	frameRelayInitState	OBJECT-TYPE
		SYNTAX	INTEGER {
			in-service(1),
			out-of-service(2)
			}
		ACCESS	read-only
		STATUS	mandatory
		DESCRIPTION
			"The initial state of the Frame Relay port.

			 If configured for 'in-service', then the Frame Relay port will
			 be brougt up automatically when the unit is powered
			 up.

			 If configured for 'out-of-service', then the Frame Relay port must
			 be manually enabled by operator intervention (i.e.
			 enable command must be sent).

			 The default value is 'enabled'."
		::= { frameRelayConfigEntry 3 }

	frameRelayClocking	OBJECT-TYPE
		SYNTAX	INTEGER {
			external(1),
			internal(2),
			x21-external(3),
			x21-internal(4)
			}
		ACCESS	read-only
		STATUS	mandatory
		DESCRIPTION
			"Clocking source for this port.
			 Setting 'internal' will cause the
			 port to emulate a physical DCE, and setting
			 external will cause the port to emulate a
			 physical DTE.
			 X21 External and Internal are used (with the
			 proper external adapter) to support X.21 Leased
			 Line operation for RS-422/RS-530 (25 pin balanced)
			 interfaces.  X21 operation is not supported for
			 boards that operate RS-232 or V.35.
			 The default value for this field is 'external'."
		::= { frameRelayConfigEntry 4 }

	frameRelaySpeed	OBJECT-TYPE
		SYNTAX	INTEGER 
--			{
--			speed1200(12),
--			speed2000(20),
--			speed2400(24),
--			speed3600(36),
--			speed4800(48),
--			speed7200(72),
--			speed9600(96),
--			speed14400(144),
--			speed19200(192),
--			speed28800(288),
--			speed48000(480),
--			speed56000(560),
--			speed64000(640),
--			speed128000(1280),
--			speed256000(2560)
--			}
		ACCESS	read-only
		STATUS	mandatory
		DESCRIPTION
			"The ports speed in bits per second.
			 The default value is 9600 bits per second.
			 Speeds higher than 19200 are not supported on
			 RS-232 port Sync products (must be V.35 or RS-422)."
		::= { frameRelayConfigEntry 5 }

	frameRelayLocalManagementProtocol OBJECT-TYPE
		SYNTAX	INTEGER {
			annexD(1),
			lmi(2)
			}
		ACCESS	read-only
		STATUS	mandatory
		DESCRIPTION
			"The ports management protocol type.
			 Annex D = ANSI T1.617 Annex D
			 LMI = Frame Relay Manufacturers LMI
			 The default value is Annex D."
		::= { frameRelayConfigEntry 6 }

	frameRelayLinkPollingTimer OBJECT-TYPE
		SYNTAX	INTEGER (5..30)
		ACCESS	read-only
		STATUS	mandatory
		DESCRIPTION
			"Measured in seconds, intervals of 5
			 T391 - Annex D
			 nT1  - LMI
			 The default value for this field is 5 seconds."
		::= { frameRelayConfigEntry 7 }

	frameRelayFullStatusPollingCount OBJECT-TYPE
		SYNTAX	INTEGER (1..255)
		ACCESS	read-only
		STATUS	mandatory
		DESCRIPTION
			"The number of polls that a full status poll is
			 issued.
			 N391 - Annex D
			 nT1  - LMI
			 The default value for this field is 6."
		::= { frameRelayConfigEntry 8 }

	frameRelayT1Timer	OBJECT-TYPE
		SYNTAX	INTEGER (1..25)
		ACCESS	read-only
		STATUS	mandatory
		DESCRIPTION
			"The default LLC T1 timer value in seconds.
			 T1 should be greater than T2 and less than Ti.
			 Currently supported values are 1 to 25 seconds.
			 The default value for this field is 3 seconds."
		::= { frameRelayConfigEntry 9 }

	frameRelayT2Timer	OBJECT-TYPE
		SYNTAX	INTEGER (0..50)
		ACCESS	read-only
		STATUS	mandatory
		DESCRIPTION
			"The default LLC T2 timer value in tenths of seconds.
			 If configured for 0 then the T2 timer is disabled
			 and an RR frame will be sent for every I frame
			 received.
			 Current supported values are 0 and 2-50.
			 T2 should be less than T1.
			 The default value for this field is 0 (disabled)."
		::= { frameRelayConfigEntry 10 }

	frameRelayTiTimer	OBJECT-TYPE
		SYNTAX	INTEGER (2..50)
		ACCESS	read-only
		STATUS	mandatory
		DESCRIPTION
			"The default LLC Ti (inactivity) timer value
			 in seconds.
			 Ti should be greater than T1.
			 Currently supported values are 2 to 50 seconds.
			 The default value for this field is 30 seconds."
		::= { frameRelayConfigEntry 11 }

	frameRelayRxWindowSize OBJECT-TYPE
		SYNTAX	INTEGER (1..7)
		ACCESS	read-only
		STATUS	mandatory
		DESCRIPTION
			"The default LLC receive window (N3) size.
			 Note that this is not the same receive window as 
			 defined in IEEE 802.2 LLC.  This is N3 which is the
			 number of I frames received before an RR frame is
			 sent (defined as N3 in IEEE 802.2 LLC).
			 Current allowable values are 1-7.
			 The default value for this field is 7."
		::= { frameRelayConfigEntry 12 }

	frameRelayTxWindowSize OBJECT-TYPE
		SYNTAX	INTEGER (1..7)
		ACCESS	read-only
		STATUS	mandatory
		DESCRIPTION
			"The defalut LLC transmit window size.
			 Current allowable values are 1-7.
			 The default value for this field is 7."
		::= { frameRelayConfigEntry 13 }

	frameRelayMaxRetries	OBJECT-TYPE
		SYNTAX	INTEGER (1..20)
		ACCESS	read-only
		STATUS	mandatory
		DESCRIPTION
			"The default LLC maximum number of retries (N2 value).
			 The default value for this field is 15."
		::= { frameRelayConfigEntry 14 }

	frameRelayNAUName 	OBJECT-TYPE
		SYNTAX	DisplayString (SIZE(1..8))
		ACCESS	read-only
		STATUS	mandatory
		DESCRIPTION
			"The NAU name of this port.
			 The default value for this field is all blank
			 (filled with ASCII space 0x20 characters)."
		::= { frameRelayConfigEntry 15 }

	frameRelayVirtualMACAddress OBJECT-TYPE
		SYNTAX	PhysAddress
		ACCESS	read-only
		STATUS	mandatory
		DESCRIPTION
			"The F/R WAN is treated as a token ring. This address is
                      used for communication with other bridges in the
                      network."
		::= { frameRelayConfigEntry 16 }

	frameRelayVirtualRingNumber OBJECT-TYPE
		SYNTAX	INTEGER (1..4095)
		ACCESS	read-only
		STATUS	mandatory
		DESCRIPTION
			"The F/R WAN is treated as a token ring. This is the ring
			 number for the F/R network to which the port is attached.
			 It must be a unique ring number in the network.
			 The default value for this field is 1."
		::= { frameRelayConfigEntry 17 }

	frameRelayVirtualBridgeNumber OBJECT-TYPE
		SYNTAX	INTEGER (1..15)
		ACCESS	read-only
		STATUS	mandatory
		DESCRIPTION
			"The F/R WAN is treated as a token ring. This variable only
			 has significance if more than 1 F/R port is configured. 
			 The default value for this field is 1."
		::= { frameRelayConfigEntry 18 }

	frameRelayIPAddress OBJECT-TYPE
		SYNTAX	IpAddress
		ACCESS	read-only
		STATUS	mandatory
		DESCRIPTION
			"This is the IP Address of this interface."
		::= { frameRelayConfigEntry 19 }

	frameRelayNetworkMask OBJECT-TYPE
		SYNTAX	IpAddress
		ACCESS	read-only
		STATUS	mandatory
		DESCRIPTION
			"This is the network mask to be used on this 
                      interface."
		::= { frameRelayConfigEntry 20 }

	frameRelayDefaultGatewayAddress OBJECT-TYPE
		SYNTAX	IpAddress
		ACCESS	read-only
		STATUS	mandatory
		DESCRIPTION
			"Default gateway address to be used when sending
                      responses on this interface."
		::= { frameRelayConfigEntry 21 }


	--
	-- The Frame Relay Port Statistics Table:
	--

	frameRelayStatsTable	OBJECT-TYPE
		SYNTAX SEQUENCE OF FrameRelayStatsEntry
		ACCESS 	not-accessible
		STATUS	mandatory
		DESCRIPTION
			"A table of Frame Relay information." 
		::= { lineFrameRelayGroup 2 }

	frameRelayStatsEntry	OBJECT-TYPE
		SYNTAX  FrameRelayStatsEntry
		ACCESS 	not-accessible
		STATUS	mandatory
		DESCRIPTION
			"An entry consisting of port information for a
			 particular Frame Relay port." 
		INDEX { frameRelayStatsPortIndex }
		::= { frameRelayStatsTable 1 }

	FrameRelayStatsEntry ::=
		SEQUENCE {
			frameRelayStatsPortIndex
				INTEGER,
			frameRelayInOctets
				Counter,
			frameRelayOutOctets
				Counter,
			frameRelaySampleDuration
				INTEGER,
			frameRelayOverruns
				Counter,
			frameRelayCRCErrors
				Counter,
			frameRelayRecvAborts
				Counter
		}
				
	frameRelayStatsPortIndex OBJECT-TYPE
		SYNTAX	INTEGER 
		ACCESS	read-only
		STATUS	mandatory
		DESCRIPTION
			"The port number that uniquely identifies
			 this Frame Relay port."
		::= { frameRelayStatsEntry 1 }

	frameRelayInOctets OBJECT-TYPE
		SYNTAX	Counter
		ACCESS	read-only
		STATUS	mandatory
		DESCRIPTION
			"The number of bytes received inclusive
			 of all valid bytes in the frame relay
			 frame except for the CRC field (frame
			 relay header included)."
		::= { frameRelayStatsEntry 2 }

	frameRelayOutOctets OBJECT-TYPE
		SYNTAX	Counter
		ACCESS	read-only
		STATUS	mandatory
		DESCRIPTION
			"The number of bytes transmitted inclusive
			 of all bytes in the frame relay
			 frame except for the CRC field (frame
			 relay header included)."
		::= { frameRelayStatsEntry 3 }

	frameRelaySampleDuration OBJECT-TYPE
		SYNTAX	INTEGER 
		ACCESS	read-only
		STATUS	mandatory
		DESCRIPTION
			"The sample duration in seconds for 
			 Frame Relay Statistics for this port."
		::= { frameRelayStatsEntry 4 }

	frameRelayOverruns	OBJECT-TYPE
		SYNTAX	Counter
		ACCESS	read-only
		STATUS	mandatory
		DESCRIPTION
			"The number of receiver overruns."
		::= { frameRelayStatsEntry 5 }

	frameRelayCRCErrors	OBJECT-TYPE
		SYNTAX	Counter
		ACCESS	read-only
		STATUS	mandatory
		DESCRIPTION
			"The number of received CRC errors."
		::= { frameRelayStatsEntry 6 }

	frameRelayRecvAborts	OBJECT-TYPE
		SYNTAX	Counter
		ACCESS	read-only
		STATUS	mandatory
		DESCRIPTION
			"The number of received frame aborts
			 received."
		::= { frameRelayStatsEntry 7 }

	--
	-- The PU Control Group
	--

	puControlTable OBJECT-TYPE
		SYNTAX SEQUENCE OF PuControlEntry
		ACCESS 	not-accessible
		STATUS	mandatory
		DESCRIPTION
			"A table for controlling lines and obtaining
			 information." 
		::= { puControlGroup 1 }

	puControlEntry OBJECT-TYPE
		SYNTAX  PuControlEntry
		ACCESS 	not-accessible
		STATUS	mandatory
		DESCRIPTION
			"An entry consisting of PU information for a
			 particular port." 
		INDEX { puControlLineIndex, puControlPUAddress }
		::= { puControlTable 1 }

	PuControlEntry ::=
		SEQUENCE {
			puControlLineIndex
				INTEGER,
			puControlPUAddress
				OCTET STRING,
			puStatus
				INTEGER,
			puConnectionStatus
				INTEGER,
			puLastClearCode
				OCTET STRING,
			puControlFailureCode
				OCTET STRING,
                        puControlNAUName
                                DisplayString,
			puConnectionAttemptCount
				Counter
		}
				

	puControlLineIndex OBJECT-TYPE
		SYNTAX	INTEGER 
		ACCESS	read-only
		STATUS	mandatory
		DESCRIPTION
			"The port number that has a given PU."
		::= { puControlEntry 1 }


	puControlPUAddress OBJECT-TYPE
		SYNTAX	OCTET STRING (SIZE(1))
		ACCESS	read-only
		STATUS	mandatory
		DESCRIPTION
			"The PU address in the range of 0x01 to 0xfe."
		::= { puControlEntry 2 }

	puStatus	OBJECT-TYPE
		SYNTAX	INTEGER {
			enable(1),
			disable(2),
			failed(3),
			restart(4),
			enable-all(5)
			}
		ACCESS	read-write
		STATUS	mandatory
		DESCRIPTION
			"The status of the PU.
			 To change status of a port an enable, enable all
			 or disable may be set.

		
			 Valid Return status are enable(d), disable(d),
			 or failed.

			 Commands:
			 An enable command will attempt to bring up the PU.
			 An enable all command will attempt to bring up
			 the line and any lower layer entities (e.g. PUs).
			 A disable command will disable the PU.
			 
			 Status:
			 Enable(d) indicates the PU is enabled and running.
			 Disable(d) indicates the PU has been disabled.
			 Failed indicates the PU is enabled and not 
			 Running."
		::= { puControlEntry 3 }

	puConnectionStatus	OBJECT-TYPE
		SYNTAX	INTEGER	{
			connected(1),
			not-connected(2)
			}
		ACCESS	read-only
		STATUS	mandatory
		DESCRIPTION
			"The status of the LLC type 2 Connection for this
			 SDLC PU."
		::= { puControlEntry 4 }


	puLastClearCode    OBJECT-TYPE
		SYNTAX	OCTET STRING (SIZE(2))
		ACCESS	read-only
		STATUS	mandatory
		DESCRIPTION
			"A two octet field indicating the Last Clearing
			 Cause and Diagnostic Field of the last failed
			 connection attempt (a.k.a. call attempt) or
			 active connection (a.k.a. session).

			 For LLC type 2 connections the first octet (cause)
			 is always 0.  The second octet (diagnostic)
			 indicates the reason for the last connection failure.
			 The second octet is set to 0 when a sucessful
			 call has been placed, or if no call has ever been
			 placed (e.g. PU never came up).
			 If the second octet is non-zero then it indicates
			 the reason for the connection attempt failure.

			 See User's Guide for information"

		::= { puControlEntry 5 }

	puControlFailureCode 	OBJECT-TYPE
		SYNTAX	OCTET STRING (SIZE (2))
		ACCESS	read-only
		STATUS	mandatory
		DESCRIPTION
			"This entry contains the failure codes if the
			 associated PU is in the failed state."
		::= { puControlEntry 6 }

	puControlNAUName 	OBJECT-TYPE
		SYNTAX	DisplayString (SIZE(1..8))
		ACCESS	read-only
		STATUS	mandatory
		DESCRIPTION
			"The NAU name of this PU.
			 The default value for this field is all blank
			 (filled with ASCII space 0x20 characters)."
		::= { puControlEntry 7 }

	puConnectionAttemptCount 	OBJECT-TYPE
		SYNTAX	Counter	
		ACCESS	read-only
		STATUS	mandatory
		DESCRIPTION
			"The number of connection attempts performed. This 
                        count is set to zero at startup, and after every
                        loss of an estabished session."   
		::= { puControlEntry 8 }

	--
	-- The PU Configuration Group
	--
	-- The PU Configuration Group contains information on the lines' 
	-- configured PUs.

	sdlcPuConfigTable	OBJECT-TYPE
			SYNTAX	SEQUENCE OF SdlcPuConfigEntry
			ACCESS	not-accessible
			STATUS	mandatory
			DESCRIPTION
				"A list of PU entries."	
			::= { puSDLCGroup 1 }

	sdlcPuConfigEntry	OBJECT-TYPE
			SYNTAX	SdlcPuConfigEntry
			ACCESS	not-accessible
			STATUS	mandatory
			DESCRIPTION
				"This entry contains information about
				a given PU. The entry is indexed by the
				port number and the PU number."
			INDEX	{ sdlcPuConfigLineIndex, sdlcPuConfigAddress }
			::= { sdlcPuConfigTable 1 }

	SdlcPuConfigEntry ::= 
		SEQUENCE {
			sdlcPuConfigLineIndex
				INTEGER,
			sdlcPuConfigAddress
				OCTET STRING,
			sdlcPuNAUName
				DisplayString,
			sdlcPuInitialState
				INTEGER,
			sdlcPuXID
				OCTET STRING,
			sdlcPuType
				INTEGER,
			sdlcPuGroupPollAddress
				OCTET STRING,
			sdlcPuConnectionID
				OCTET STRING,
                        sdlcPuMAXOUT
                                INTEGER,
                        sdlcPuConnectType
                                INTEGER
			}

	
	sdlcPuConfigLineIndex OBJECT-TYPE
		SYNTAX	INTEGER
		ACCESS	read-only
		STATUS	mandatory
		DESCRIPTION
			"The port number for which the line (CU)is configured 
			 (first level)."
		::= { sdlcPuConfigEntry 1 }

	sdlcPuConfigAddress	OBJECT-TYPE
		SYNTAX	OCTET STRING (SIZE(1))
		ACCESS	read-only
		STATUS	mandatory
		DESCRIPTION
			"The PU address in the range of 0x00 to 0xfe."
		::= { sdlcPuConfigEntry 2 }

	sdlcPuNAUName 	OBJECT-TYPE
		SYNTAX	DisplayString (SIZE(1..8))
		ACCESS	read-only
		STATUS	mandatory
		DESCRIPTION
			"The NAU name of this PU.
			 The default value for this field is all blank
			 (filled with ASCII space 0x20 characters)."
		::= { sdlcPuConfigEntry 3 }

	sdlcPuInitialState	OBJECT-TYPE
		SYNTAX	INTEGER	{
			in-service(1),
			out-of-service(2)
			}
		ACCESS	read-only
		STATUS	mandatory
		DESCRIPTION
			"The initial state of the PU.

			 If configured for 'in-service', then the SDLC PU will
			 be brougt up automattically when the unit is powered
			 up.

			 If configured for 'out-of-service', the the SDLC PU must
			 be manually enabled by operator intervention (i.e.
			 enable command must be sent).

			 The default value is 'in-service'."
		::= { sdlcPuConfigEntry 4 }

	sdlcPuXID		OBJECT-TYPE
		SYNTAX	OCTET STRING (SIZE(4))
		ACCESS	read-only
		STATUS	mandatory
		DESCRIPTION
			"The XID value for this PU.

			 The XID is used to identify the PU during the LLC
			 connection process to the remote Host or Gateway.
			 If the field is configured to 0 then the unit
			 will solicit the XID from the downstream PU
			 and send the XID data received from SDLC to the XID
			 data sent for the LLC connection process.
			 If not sent to 0, then the unit will insert the
			 data configured in the LLC sent to the host
			 during the LLC connection process on behalf of
			 the CU.

			 For incoming LLC connections on Sync Research
			 products this field is parsed to route the
			 connection to the proper PU.  

			 The default value for this field is all zeroes
			 (solicit XID from PU)."
		::= { sdlcPuConfigEntry 5 }

	sdlcPuType		OBJECT-TYPE
		SYNTAX	INTEGER {
			type1(1),
			type2(2),
			type2-1(3),
			type4(4),
			type5(5)
			}
		ACCESS	read-only
		STATUS	mandatory
		DESCRIPTION
			"The SNA PU type.
			 1 = PU type 1
			 2 = PU type 2
			 3 = PU type 2.1
			 4 = PU type 4 (not supported, reserved)
			 5 = PU type 5 (not supported, reserved)
			 This parameter defaults to a value of 2."
		::= { sdlcPuConfigEntry 6 }

	sdlcPuGroupPollAddress	OBJECT-TYPE
		SYNTAX	OCTET STRING (SIZE(1))
		ACCESS	read-only
		STATUS	mandatory
		DESCRIPTION
			"The PU's group address in the range of 0x01 to 0xfe.
			 setting this value to 0 will disable the group poll
			 feature for polling this and other PUs in a group.
			 The default value for this field is 0."
		::= { sdlcPuConfigEntry 7 }

	sdlcPuConnectionID 	OBJECT-TYPE
		SYNTAX	OCTET STRING (SIZE(2))
		ACCESS	read-only
		STATUS	mandatory
		DESCRIPTION
			"This entry defines the Connection ID
                      	 to a corresponding entry in the mapping table.  

			 The default value for this field is all zeroes."
		::= { sdlcPuConfigEntry 8 }

	sdlcPuMAXOUT 	OBJECT-TYPE
		SYNTAX	INTEGER
		ACCESS	read-only
		STATUS	mandatory
		DESCRIPTION
			"This entry defines the maximum number of outstanding 
                         I frames that the PU will allow.
			
			 This field is applicable to TSDLC only." 
		::= { sdlcPuConfigEntry 9 }

	sdlcPuConnectType	OBJECT-TYPE
		SYNTAX	INTEGER {
			answer(1),
			originate(2)
			}
		ACCESS	read-only
		STATUS	mandatory
		DESCRIPTION
			"The SNA PU Connection type."
		::= { sdlcPuConfigEntry 10 }

	--				
	-- The SDLC PU Statistics Table:
	--
	-- The SDLC PU Statisctics table contains statistical information on the
	-- lines' configured PUs.

	sdlcPuStatsTable	OBJECT-TYPE
			SYNTAX	SEQUENCE OF SdlcPuStatsEntry
			ACCESS	not-accessible
			STATUS	mandatory
			DESCRIPTION
				"A list of PU statistics entries."	
			::= { puSDLCGroup 2 }

	sdlcPuStatsEntry	OBJECT-TYPE
			SYNTAX	SdlcPuStatsEntry
			ACCESS	not-accessible
			STATUS	mandatory
			DESCRIPTION
				"This entry contains information about
				a given PU. The entry is indexed by the
				port number and the PU number."
			INDEX	{ sdlcPuStatsLineIndex, sdlcPuStatsAddress }
			::= { sdlcPuStatsTable 1 }

	SdlcPuStatsEntry ::= 
		SEQUENCE {
			sdlcPuStatsLineIndex
				INTEGER,
			sdlcPuStatsAddress
				OCTET STRING,
			sdlcPuInIFrames
				Counter,
			sdlcPuOutIFrames
				Counter,
			sdlcPuInRRFrames
				Counter,
			sdlcPuOutRRFrames
				Counter,
			sdlcPuInRNRFrames
				Counter,
			sdlcPuOutRNRFrames
				Counter,
			sdlcPuInXIDFrames
				Counter,
			sdlcPuOutXIDFrames
				Counter,
			sdlcPuInTESTFrames
				Counter,
			sdlcPuOutTESTFrames
				Counter,
			sdlcPuInSNRMFrames
				Counter,
			sdlcPuOutSNRMFrames
				Counter,
			sdlcPuInDISCFrames
				Counter,
			sdlcPuOutDISCFrames
				Counter,
			sdlcPuInDMFrames
				Counter,
			sdlcPuOutDMFrames
				Counter,
			sdlcPuInUAFrames
				Counter,
			sdlcPuOutUAFrames
				Counter,
			sdlcPuInFRMRFrames
				Counter,
			sdlcPuOutFRMRFrames
				Counter,
			sdlcPuInRDFrames
				Counter,
			sdlcPuOutRDFrames
				Counter,
			sdlcPuInUIFrames
				Counter,
			sdlcPuOutUIFrames
				Counter,
			sdlcPuReTxIFrames
				Counter,
			sdlcPuPollResponseTimeouts
				Counter
			}

	
	sdlcPuStatsLineIndex OBJECT-TYPE
		SYNTAX	INTEGER
		ACCESS	read-only
		STATUS	mandatory
		DESCRIPTION
			"The port number for which PU is configured on."
		::= { sdlcPuStatsEntry 1 }

	sdlcPuStatsAddress	OBJECT-TYPE
		SYNTAX	OCTET STRING (SIZE(1))
		ACCESS	read-only
		STATUS	mandatory
		DESCRIPTION
			"The PU address in the range of 0x00 to 0xfe."
		::= { sdlcPuStatsEntry 2 }

	sdlcPuInIFrames	OBJECT-TYPE
		SYNTAX	Counter
		ACCESS	read-only
		STATUS	mandatory
		DESCRIPTION
			"The number of I frames received on this PU."
		::= { sdlcPuStatsEntry 3 }

	sdlcPuOutIFrames	OBJECT-TYPE
		SYNTAX	Counter
		ACCESS	read-only
		STATUS	mandatory
		DESCRIPTION
			"The number of I frames trasnmitted on this PU."
		::= { sdlcPuStatsEntry 4 }

	sdlcPuInRRFrames	OBJECT-TYPE
		SYNTAX	Counter
		ACCESS	read-only
		STATUS	mandatory
		DESCRIPTION
			"The number of RR frames received on this PU."
		::= { sdlcPuStatsEntry 5 }

	sdlcPuOutRRFrames	OBJECT-TYPE
		SYNTAX	Counter
		ACCESS	read-only
		STATUS	mandatory
		DESCRIPTION
			"The number of RR frames transmitted on this PU."
		::= { sdlcPuStatsEntry 6 }

	sdlcPuInRNRFrames	OBJECT-TYPE
		SYNTAX	Counter
		ACCESS	read-only
		STATUS	mandatory
		DESCRIPTION
			"The number of RNR frames received on this PU."
		::= { sdlcPuStatsEntry 7 }

	sdlcPuOutRNRFrames	OBJECT-TYPE
		SYNTAX	Counter
		ACCESS	read-only
		STATUS	mandatory
		DESCRIPTION
			"The number of RNR frames transmitted on this PU."
		::= { sdlcPuStatsEntry 8 }

	sdlcPuInXIDFrames	OBJECT-TYPE
		SYNTAX	Counter
		ACCESS	read-only
		STATUS	mandatory
		DESCRIPTION
			"The number of XID frames received on this PU."
		::= { sdlcPuStatsEntry 9 }

	sdlcPuOutXIDFrames	OBJECT-TYPE
		SYNTAX	Counter
		ACCESS	read-only
		STATUS	mandatory
		DESCRIPTION
			"The number of XID frames transmitted on this PU."
		::= { sdlcPuStatsEntry 10 }

	sdlcPuInTESTFrames	OBJECT-TYPE
		SYNTAX	Counter
		ACCESS	read-only
		STATUS	mandatory
		DESCRIPTION
			"The number of TEST frames received on this PU."
		::= { sdlcPuStatsEntry 11 }

	sdlcPuOutTESTFrames	OBJECT-TYPE
		SYNTAX	Counter
		ACCESS	read-only
		STATUS	mandatory
		DESCRIPTION
			"The number of TEST frames transmitted on this PU."
		::= { sdlcPuStatsEntry 12 }

	sdlcPuInSNRMFrames	OBJECT-TYPE
		SYNTAX	Counter
		ACCESS	read-only
		STATUS	mandatory
		DESCRIPTION
			"The number of SNRM frames received on this PU."
		::= { sdlcPuStatsEntry 13 }

	sdlcPuOutSNRMFrames	OBJECT-TYPE
		SYNTAX	Counter
		ACCESS	read-only
		STATUS	mandatory
		DESCRIPTION
			"The number of SNRM frames transmitted on this PU."
		::= { sdlcPuStatsEntry 14 }


	sdlcPuInDISCFrames	OBJECT-TYPE
		SYNTAX	Counter
		ACCESS	read-only
		STATUS	mandatory
		DESCRIPTION
			"The number of DISC frames received on this PU."
		::= { sdlcPuStatsEntry 15 }

	sdlcPuOutDISCFrames	OBJECT-TYPE
		SYNTAX	Counter
		ACCESS	read-only
		STATUS	mandatory
		DESCRIPTION
			"The number of DISC frames transmitted on this PU."
		::= { sdlcPuStatsEntry 16 }

	sdlcPuInDMFrames	OBJECT-TYPE
		SYNTAX	Counter
		ACCESS	read-only
		STATUS	mandatory
		DESCRIPTION
			"The number of DM frames received on this PU."
		::= { sdlcPuStatsEntry 17 }

	sdlcPuOutDMFrames	OBJECT-TYPE
		SYNTAX	Counter
		ACCESS	read-only
		STATUS	mandatory
		DESCRIPTION
			"The number of DM frames transmitted on this PU."
		::= { sdlcPuStatsEntry 18 }

	sdlcPuInUAFrames	OBJECT-TYPE
		SYNTAX	Counter
		ACCESS	read-only
		STATUS	mandatory
		DESCRIPTION
			"The number of UA frames received on this PU."
		::= { sdlcPuStatsEntry 19 }

	sdlcPuOutUAFrames	OBJECT-TYPE
		SYNTAX	Counter
		ACCESS	read-only
		STATUS	mandatory
		DESCRIPTION
			"The number of UA frames transmitted on this PU."
		::= { sdlcPuStatsEntry 20 }

	sdlcPuInFRMRFrames	OBJECT-TYPE
		SYNTAX	Counter
		ACCESS	read-only
		STATUS	mandatory
		DESCRIPTION
			"The number of FRMR frames received on this PU."
		::= { sdlcPuStatsEntry 21 }

	sdlcPuOutFRMRFrames	OBJECT-TYPE
		SYNTAX	Counter
		ACCESS	read-only
		STATUS	mandatory
		DESCRIPTION
			"The number of FRMR frames transmitted on this PU."
		::= { sdlcPuStatsEntry 22 }


	sdlcPuInRDFrames	OBJECT-TYPE
		SYNTAX	Counter
		ACCESS	read-only
		STATUS	mandatory
		DESCRIPTION
			"The number of RD frames received on this PU."
		::= { sdlcPuStatsEntry 23 }

	sdlcPuOutRDFrames	OBJECT-TYPE
		SYNTAX	Counter
		ACCESS	read-only
		STATUS	mandatory
		DESCRIPTION
			"The number of RD frames transmitted on this PU."
		::= { sdlcPuStatsEntry 24 }

	sdlcPuInUIFrames	OBJECT-TYPE
		SYNTAX	Counter
		ACCESS	read-only
		STATUS	mandatory
		DESCRIPTION
			"The number of UI frames received on this PU."
		::= { sdlcPuStatsEntry 25 }

	sdlcPuOutUIFrames	OBJECT-TYPE
		SYNTAX	Counter
		ACCESS	read-only
		STATUS	mandatory
		DESCRIPTION
			"The number of UI frames transmitted on this PU."
		::= { sdlcPuStatsEntry 26 }

	sdlcPuReTxIFrames	OBJECT-TYPE
		SYNTAX	Counter
		ACCESS	read-only
		STATUS	mandatory
		DESCRIPTION
			"The number of re-transmitted I frames on this PU."
		::= { sdlcPuStatsEntry 27 }

	sdlcPuPollResponseTimeouts OBJECT-TYPE
		SYNTAX	Counter
		ACCESS	read-only
		STATUS	mandatory
		DESCRIPTION
			"The number of PU Poll Response timeouts for this PU."
		::= { sdlcPuStatsEntry 28 }
				
	--
	-- The Bisync PU Group
	--
	-- The Bisync PU Configuration Table:
	--

	bisyncPuConfigTable	OBJECT-TYPE
			SYNTAX	SEQUENCE OF BisyncPuConfigEntry
			ACCESS	not-accessible
			STATUS	mandatory
			DESCRIPTION
				"A list of Bisync CU entries."	
			::= { puBisyncGroup 1 }

	bisyncPuConfigEntry	OBJECT-TYPE
			SYNTAX	BisyncPuConfigEntry
			ACCESS	not-accessible
			STATUS	mandatory
			DESCRIPTION
				"This entry contains information about
				a given PU. The entry is indexed by the
				port number and the PU number."
			INDEX	{ bisyncPuConfigLineIndex, bisyncPuConfigAddress }
			::= { bisyncPuConfigTable 1 }

	BisyncPuConfigEntry ::= 
		SEQUENCE {
			bisyncPuConfigLineIndex
				INTEGER,
			bisyncPuConfigAddress
				OCTET STRING,
			bisyncPuNAUName
				DisplayString,
			bisyncPuInitialState
				INTEGER,
			bisyncPuXID
				OCTET STRING,
			bisyncPuTargetHostType
				INTEGER,
			bisyncPuMaxData	
				INTEGER,
			bisyncPuConnectionID
				OCTET STRING,
			bisyncPuConnectType
				INTEGER
		}

	
	bisyncPuConfigLineIndex OBJECT-TYPE
		SYNTAX	INTEGER
		ACCESS	read-only
		STATUS	mandatory
		DESCRIPTION
			"The port number for which PU is configured on."
		::= { bisyncPuConfigEntry 1 }

	bisyncPuConfigAddress	OBJECT-TYPE
		SYNTAX	OCTET STRING (SIZE(1))
		ACCESS	read-only
		STATUS	mandatory
		DESCRIPTION
			"The PU address in the range of 0x00 to 0xfe."
		::= { bisyncPuConfigEntry 2 }

	bisyncPuNAUName 	OBJECT-TYPE
		SYNTAX	DisplayString (SIZE(1..8))
		ACCESS	read-only
		STATUS	mandatory
		DESCRIPTION
			"The NAU name of this PU.
			 The default value for this field is all blank
			 (filled with ASCII space 0x20 characters)."
		::= { bisyncPuConfigEntry 3 }

	bisyncPuInitialState	OBJECT-TYPE
		SYNTAX	INTEGER	{
			in-service(1),
			out-of-service(2)
			}
		ACCESS	read-only
		STATUS	mandatory
		DESCRIPTION
			"The initial state of the PU.

			 If configured for 'in-service', then the SDLC PU will
			 be brougt up automattically when the unit is powered
			 up.

			 If configured for 'out-of-service', the the SDLC PU must
			 be manually enabled by operator intervention (i.e.
			 enable command must be sent).

			 The default value is 'in-service'."
		::= { bisyncPuConfigEntry 4 }

	bisyncPuXID		OBJECT-TYPE
		SYNTAX	OCTET STRING (SIZE(4))
		ACCESS	read-only
		STATUS	mandatory
		DESCRIPTION
			"The XID value for this PU.

			 The XID is used to identify the PU during the LLC
			 connection process to the remote Host or Gateway.
			 
			 The unit will insert the
			 data configured in the LLC XID sent to the host
			 during the LLC connection process on behalf of
			 the CU.

			 For bisync control units, this field is required
			 as bisync cannot solicit an XID.

			 For incoming LLC connections on Sync Research
			 products this field is parsed to route the
			 connection to the proper PU.  

			 The default value for this field is all zeroes."
		::= { bisyncPuConfigEntry 5 }

	bisyncPuTargetHostType		OBJECT-TYPE
		SYNTAX	INTEGER {
			sna-host-type(1),
			bisync-host-type(2)
			}
		ACCESS	read-only
		STATUS	mandatory
		DESCRIPTION
			"The Target Host type.
			 1 = SNA host type
			 2 = Bisync host type 
			 This field specifies the target host type for TBSC 
			 and is applicable to BSC-to-SNA conversion only.
			
			 This parameter defaults to a value of 2."
		::= { bisyncPuConfigEntry 6 }

	bisyncPuMaxData 	OBJECT-TYPE
		SYNTAX	INTEGER
		ACCESS	read-only
		STATUS	mandatory
		DESCRIPTION
			"This entry defines the SNA frame size which is 
			 the sum of SNA data and SNA header.  This value must
			 match the MAXData configured for SNA host and is   
			 applicable to BSC-to-SNA conversion only.	
			
			 The default value is 521. The valid range  is 265, 
			 521, 777, 1033, 1289."	
		::= { bisyncPuConfigEntry 7 }

	bisyncPuConnectionID	OBJECT-TYPE
		SYNTAX	OCTET STRING (SIZE(2))
		ACCESS	read-only
		STATUS	mandatory
		DESCRIPTION
			"This entry defines the Connection ID
                      to a corresponding entry in the mapping table.  

			 The default value for this field is all zeroes."
		::= { bisyncPuConfigEntry 8 }

	bisyncPuConnectType	OBJECT-TYPE
		SYNTAX	INTEGER {
			answer(1),
			originate(2)
			}
		ACCESS	read-only
		STATUS	mandatory
		DESCRIPTION
			"The Bisync PU Connection type."
		::= { bisyncPuConfigEntry 9 }

	--				
	-- The Bisync PU Statistics Table:
	--
	-- The Bisync PU Statisctics table contains statistical information on 
	-- the lines' configured PUs.

	bisyncPuStatsTable	OBJECT-TYPE
			SYNTAX	SEQUENCE OF BisyncPuStatsEntry
			ACCESS	not-accessible
			STATUS	mandatory
			DESCRIPTION
				"A list of PU statistics entries."	
			::= { puBisyncGroup 2 }

	bisyncPuStatsEntry	OBJECT-TYPE
			SYNTAX	BisyncPuStatsEntry
			ACCESS	not-accessible
			STATUS	mandatory
			DESCRIPTION
				"This entry contains information about
				a given PU. The entry is indexed by the
				port number and the PU number."
			INDEX	{ bisyncPuStatsLineIndex, bisyncPuStatsAddress }
			::= { bisyncPuStatsTable 1 }

	BisyncPuStatsEntry ::= 
		SEQUENCE {
			bisyncPuStatsLineIndex
				INTEGER,
			bisyncPuStatsAddress
				OCTET STRING,
                        bisyncPuInTransactions
				Counter,
                        bisyncPuOutTransactions
				Counter,
                        bisyncPuSlowPolls
                                Counter,
                        bisyncPuPolls
                                Counter
			}

	
	bisyncPuStatsLineIndex OBJECT-TYPE
		SYNTAX	INTEGER
		ACCESS	read-only
		STATUS	mandatory
		DESCRIPTION
			"The port number for which PU is configured on."
		::= { bisyncPuStatsEntry 1 }

	bisyncPuStatsAddress	OBJECT-TYPE
		SYNTAX	OCTET STRING (SIZE(1))
		ACCESS	read-only
		STATUS	mandatory
		DESCRIPTION
			"The PU address in the range of 0x00 to 0xfe."
		::= { bisyncPuStatsEntry 2 }

	bisyncPuInTransactions OBJECT-TYPE
		SYNTAX	Counter
		ACCESS	read-only
		STATUS	mandatory
		DESCRIPTION
			"The number of PU Poll Response timeouts for this PU."
		::= { bisyncPuStatsEntry 3 }

	bisyncPuOutTransactions OBJECT-TYPE
		SYNTAX	Counter
		ACCESS	read-only
		STATUS	mandatory
		DESCRIPTION
			"The number of PU Poll Response timeouts for this PU."
		::= { bisyncPuStatsEntry 4 }

	bisyncPuSlowPolls OBJECT-TYPE
		SYNTAX	Counter
		ACCESS	read-only
		STATUS	mandatory
		DESCRIPTION
			"The number of PU slow polls for this PU."
		::= { bisyncPuStatsEntry 5 }

	bisyncPuPolls OBJECT-TYPE
		SYNTAX	Counter
		ACCESS	read-only
		STATUS	mandatory
		DESCRIPTION
			"The number of PU Polls for this PU."
		::= { bisyncPuStatsEntry 6 }


	--
	-- The Mapping PU Group
	--
	-- The Mapping PU Configuration Table contains mapping information 
	-- on the lines' configured PUs.

	mappingPuConfigTable	OBJECT-TYPE
			SYNTAX	SEQUENCE OF MappingPuConfigEntry
			ACCESS	not-accessible
			STATUS	mandatory
			DESCRIPTION
				"A list of PU mapping entries."	
			::= { puMappingGroup 1 }

	mappingPuConfigEntry	OBJECT-TYPE
			SYNTAX	MappingPuConfigEntry
			ACCESS	not-accessible
			STATUS	mandatory
			DESCRIPTION
				"This entry contains information about a given
				 mapping PU. Each entry includes MAC/SAP
        			 information for a source PU and a similar 
				 information for the partner (mapped) PU.  
			         Depending upon whether the PU is LAN-attached, 
			         SDLC-attached or Frame Relay-attached, one 
				 or more fields may not apply.  Some fields,
        			 for example, mappingPuNAU, mappingPuXID,  
		        	 mappingPuConnectID are common to both end 
        			 points.  The entry is indexed by the port 
				 number and the PU number."
			INDEX	{ mappingPuConfigLineIndex, mappingPuConfigAddress }
			::= { mappingPuConfigTable 1 }

	MappingPuConfigEntry ::= 
		SEQUENCE {
			mappingPuConfigLineIndex
				INTEGER,
			mappingPuConfigAddress
				OCTET STRING,
			mappingPuSourceSAP
				OCTET STRING,
			mappingPuDestinationSAP
				OCTET STRING,
			mappingPuDestinationMAC
				PhysAddress,
			mappingPuPartnerConfigLineIndex
				INTEGER,
			mappingPuPartnerConfigAddress
				OCTET STRING,
			mappingPuPartnerSourceSAP
				OCTET STRING,
			mappingPuPartnerDestSAP
				OCTET STRING,
			mappingPuPartnerDestMAC
				PhysAddress,
			mappingPuNAU
        			DisplayString,
			mappingPuConnectID
				OCTET STRING,
			mappingPuXID
				OCTET STRING,
			mappingPuDirectDLCI
				OCTET STRING
			}
	
	mappingPuConfigLineIndex OBJECT-TYPE
		SYNTAX	INTEGER
		ACCESS	read-only
		STATUS	mandatory
		DESCRIPTION
			"The port number for which PU is associated with.  
			 Port number 99 is a special value which is used to
      			 indicate NetView PU."
		::= { mappingPuConfigEntry 1 }

	mappingPuConfigAddress	OBJECT-TYPE
		SYNTAX	OCTET STRING (SIZE(1))
		ACCESS	read-only
		STATUS	mandatory
		DESCRIPTION
			"The PU address in the range of 0x01 to 0xfe."
		::= { mappingPuConfigEntry 2 }

	mappingPuSourceSAP	OBJECT-TYPE
		SYNTAX	OCTET STRING (SIZE(1))
		ACCESS	read-only
		STATUS	mandatory
		DESCRIPTION
			"The LLC source SAP value for this PU.

			 Typically the source SAP will vary for each PU.
			 This is due to the fact that most Sync products are
			 configured to always call the same remote
			 Token-Ring Host or Gateway for all connections
			 configured.  This means that all the Destination
			 SAP (usually set to 4) and Destination MAC addresses
			 are the same, so the Source SAP field must be set
			 to a unique value in order to uniquely identify
			 the LLC connection to the Host.  (SNA does not allow
			 multiplexing of PUs on one LLC connection.  Each
			 PU must have its own LLC Type 2 connection.)
			 This field must be set to a range between 04 and 
			 E8 hexadecimal and it must be evenly divisible by
			 4 (802.2 LLC rules for user assigned SAPs). 

			 This field is not applicable in all cases, if not it
			 returns a dummy value.

			 This parameter defaults to a value of 4."
		::= { mappingPuConfigEntry 3 }

	mappingPuDestinationSAP OBJECT-TYPE
		SYNTAX	OCTET STRING (SIZE(1))
 		ACCESS	read-only
		STATUS	mandatory
		DESCRIPTION
			"The LLC Destination SAP value for this PU.

			 For SNA typically the destination is almost
			 always SAP 4.  However both Host Front Ends
			 (e.g. 3745) or Gateways (e.g. 3174) allow SAPs
			 to be configured for any value betwee 0x04 and
			 0xEC as long as the SAP ID is a user assignable
			 individual SAP ID (any value evenly divisable
			 by 4).

			 This field is not applicable to all cases.  If not it
			 returns a dummy value.

			 This parameter defaults to a value of 4."
		::= { mappingPuConfigEntry 4 }

	mappingPuDestinationMAC OBJECT-TYPE
		SYNTAX	PhysAddress
		ACCESS	read-only
		STATUS	mandatory
		DESCRIPTION
			"The LAN Destination MAC address used in
			 the LLC Type 2 connection for this PU.

			 The Token-Ring format for this field is a 6 octet 
			 (48 bit) field represented in IEEE 802.5 format where
			 the first bit transmitted is the most significant bit.
			 The destination MAC must also be an 'Individual'
			 address.  Therefore valid addresses are between
			 000000000001 and 7FFFFFFFFFFF (an address of all
			 zeroes is not supported).

			 The Ethernet format for this field is a 6 octet 
			 (48 bit) field represented in IEEE 802.3 format where
			 the first bit transmitted is the least significant bit.
			 The destination MAC must also be an 'Individual'
			 address.  Therefore valid addresses must start
			 with the least significant bit equal to 0.  In other
			 words, the first two digits must be in the set
			 of 0x00, 0x02, 0x04, ... 0xFE (an address of all
			 12 digits equal to zeroes is not supported).


			 This field is not applicable to all cases.  If not it
			 returns a dummy value."

		::= { mappingPuConfigEntry 5 }

	mappingPuPartnerConfigLineIndex OBJECT-TYPE
		SYNTAX	INTEGER
		ACCESS	read-only
		STATUS	mandatory
		DESCRIPTION
			"The port number for the partner PU associated with 
      			 source PU.  Port number 99 is a special value which 
			 is used to indicate NetView PU." 
		::= { mappingPuConfigEntry 6 }

	mappingPuPartnerConfigAddress	OBJECT-TYPE
		SYNTAX	OCTET STRING (SIZE(1))
		ACCESS	read-only
		STATUS	mandatory
		DESCRIPTION
			"The PU address of the partner PU in the range of 
			 0x01 to 0xfe."
		::= { mappingPuConfigEntry 7 }

	mappingPuPartnerSourceSAP	OBJECT-TYPE
		SYNTAX	OCTET STRING (SIZE(1))
		ACCESS	read-only
		STATUS	mandatory
		DESCRIPTION
			"The LLC source SAP value for a partner PU.

			 Typically the source SAP will vary for each PU.
			 This is due to the fact that most Sync products are
			 configured to always call the same remote
			 Token-Ring Host or Gateway for all connections
			 configured.  This means that all the Destination
			 SAP (usually set to 4) and Destination MAC addresses
			 are the same, so the Source SAP field must be set
			 to a unique value in order to uniquely identify
			 the LLC connection to the Host.  (SNA does not allow
			 multiplexing of PUs on one LLC connection.  Each
			 PU must have its own LLC Type 2 connection.)
			 This field must be set to a range between 04 and 
			 E8 hexadecimal and it must be evenly divisible by
			 4 (802.2 LLC rules for user assigned SAPs). 

			 This field is not applicable in all cases, if not it
			 returns a dummy value.

			 This parameter defaults to a value of 4."
		::= { mappingPuConfigEntry 8 }

	mappingPuPartnerDestSAP OBJECT-TYPE
		SYNTAX	OCTET STRING (SIZE(1))
		ACCESS	read-only
		STATUS	mandatory
		DESCRIPTION
			"The LLC Destination SAP value for the partner PU.

			 For SNA typically the destination is almost
			 always SAP 4.  However both Host Front Ends
			 (e.g. 3745) or Gateways (e.g. 3174) allow SAPs
			 to be configured for any value betwee 0x04 and
			 0xEC as long as the SAP ID is a user assignable
			 individual SAP ID (any value evenly divisable
			 by 4).

			 This field is not applicable to all cases.  It
			 returns a dummy value.

			 This parameter defaults to a value of 4."
		::= { mappingPuConfigEntry 9 }

	mappingPuPartnerDestMAC OBJECT-TYPE
		SYNTAX	PhysAddress
		ACCESS	read-only
		STATUS	mandatory
		DESCRIPTION
			"The LAN Destination MAC address used in
			 the LLC Type 2 connection for the partner PU.

			 The Token-Ring format for this field is a 6 octet
			 (48 bit) field represented in IEEE 802.5 format where
			 the first bit transmitted is the most significant bit.
			 The destination MAC must also be an 'Individual'
			 address.  Therefore valid addresses are between
			 000000000001 and 7FFFFFFFFFFF (an address of all
			 zeroes is not supported).

			 The Ethernet format for this field is a 6 octet 
			 (48 bit) field represented in IEEE 802.3 format where 
			 the first bit transmitted is the least significant bit.
			 The destination MAC must also be an 'Individual'
			 address.  Therefore valid addresses must start
			 with the least significant bit equal to 0.  In other
			 words, the first two digits must be in the set
			 of 0x00, 0x02, 0x04, ... 0xFE (an address of all
			 12 digits equal to zeroes is not supported).

			 This field is not applicable to all cases.  If not it
			 returns a dummy value." 

		::= { mappingPuConfigEntry 10 }

	mappingPuNAU	OBJECT-TYPE
		SYNTAX	DisplayString (SIZE(1..8))
		ACCESS	read-only
		STATUS	mandatory
		DESCRIPTION
			"The NAU Name.  The NAU name is same for both the
      			 source PU and the partner PU.  It represents one 
			 physical PU in a network."
		::= { mappingPuConfigEntry 11 }

	mappingPuConnectID OBJECT-TYPE
		SYNTAX	OCTET STRING (SIZE(2))
		ACCESS	read-only
		STATUS	mandatory
		DESCRIPTION
			"The connection ID. This must match a connection ID 
			 of an access line PU or another mapping PU Connection 
		 	 ID.

			 The connnection ID is 0 if there is no mapping."
		::= { mappingPuConfigEntry 12 }

	mappingPuXID		OBJECT-TYPE
		SYNTAX	OCTET STRING (SIZE(4))
		ACCESS	read-only
		STATUS	mandatory
		DESCRIPTION
			"The XID value for this PU.

			 The XID is used to identify the PU during the LLC
			 connection process to the remote Host or Gateway.
			 For incoming LLC connections on Sync Research
			 products this field is parsed to route the
			 connection to the proper PU.  

       			 The XID is same for both the source PU and the partner
       			 PU.  It represents one physical PU in a network.

			 The default value for this field is all zeroes."
		::= { mappingPuConfigEntry 13 }

	mappingPuDirectDLCI OBJECT-TYPE
		SYNTAX	OCTET STRING (SIZE(4))
		ACCESS	read-only
		STATUS	mandatory
		DESCRIPTION
			"The Frame Relay DLCI used in 
			 the LLC Type 2 connection for this PU.

			 The Frame Relay format for this field is a 2 
			 octet (16 bit) field represented in BCD format.
			 A valid DLCI would be from 0001 to 1023 (0000 is
       			 reserved for AnnexD management. 1023 is reserved for
       			 LMI mangement.).

		   	 This value is applicable to Frame Relay-attached PU
       			 only.  The field corresponds to a source port or a 
		 	 partner port depending upon whether the source PU is
       			 a Frame Relay-attached PU or the partner PU is 
       			 Frame Relay-attached PU.  For Frame Relay-attached PU
       			 if this value is not configured, 0 is returned."

		::= { mappingPuConfigEntry 14 }

	--
	-- The Device Control Group
	--

	deviceControlTable OBJECT-TYPE
		SYNTAX SEQUENCE OF DeviceControlEntry
		ACCESS 	not-accessible
		STATUS	mandatory
		DESCRIPTION
			"A table for controlling devices and obtaining
			 information." 
		::= { deviceControlGroup 1 }

	deviceControlEntry OBJECT-TYPE
		SYNTAX  DeviceControlEntry
		ACCESS 	not-accessible
		STATUS	mandatory
		DESCRIPTION
			"An entry consisting of device information for a
			 particular device." 
		INDEX { deviceControlIndex, deviceControlCUIndex,
			deviceControlAddress }
		::= { deviceControlTable 1 }

	DeviceControlEntry ::=
		SEQUENCE {
			deviceControlIndex
				INTEGER,
			deviceControlCUIndex 
				INTEGER,
			deviceControlAddress
				OCTET STRING,
			deviceStatus
				INTEGER,
                    	deviceControlFailureCode
                            OCTET STRING
		}
				

	deviceControlIndex	OBJECT-TYPE
		SYNTAX	INTEGER 
		ACCESS	read-only
		STATUS	mandatory
		DESCRIPTION
			"The number that uniquely identifies
			 this device."
		::= { deviceControlEntry 1 }

	deviceControlCUIndex	OBJECT-TYPE
		SYNTAX	INTEGER
		ACCESS	read-only
		STATUS	mandatory
		DESCRIPTION
			"The CU index for this device."
		::= { deviceControlEntry 2 }

	deviceControlAddress	OBJECT-TYPE
		SYNTAX	OCTET STRING (SIZE(1))
		ACCESS	read-only
		STATUS	mandatory
		DESCRIPTION
			"The device address."
		::= { deviceControlEntry 3 }

	deviceStatus	OBJECT-TYPE
		SYNTAX	INTEGER {
			enable(1),
			disable(2),
			failed(3),
			restart(4),
			enable-all(5)
			}
		ACCESS	read-write
		STATUS	mandatory
		DESCRIPTION
			"The status of the device.

			 To change (write) status of a device, enable, disable, 
			 restart or enable all may be set.

			 Valid Return (read) status are enable(d), disable(d),
			 or failed (d).	
			 
			 Commands:
			 An enable command will attempt to bring up the device.

			 An enable all command will perform the same function
			 as enable, since there are no sub elements on a device.

			 A disable command will disable the device.

			 Status:
			 Enable(d) indicates the device is enabled and running.
			 Disable(d) indicates the device has been disabled.
			 Failed (d) indicates the device is enabled and not 
			 Running."
		::= { deviceControlEntry 4 }

	deviceControlFailureCode 	OBJECT-TYPE
		SYNTAX	OCTET STRING (SIZE (2))
		ACCESS	read-only
		STATUS	mandatory
		DESCRIPTION
			"This entry contains the failure codes if the
                      associated device is in the failed state."
		::= { deviceControlEntry 5 }

	--
	-- The Device Configuration Group 
	--
	-- The Device Configuration Group contains information on the lines' 
	-- configured Devices.
	--
	-- The Device Configuration Table 

	deviceConfigTable	OBJECT-TYPE
			SYNTAX	SEQUENCE OF DeviceConfigEntry
			ACCESS	not-accessible
			STATUS	mandatory
			DESCRIPTION
				"A list of device entries."	
			::= { deviceBSCGroup 1 }

	deviceConfigEntry	OBJECT-TYPE
			SYNTAX	DeviceConfigEntry
			ACCESS	not-accessible
			STATUS	mandatory
			DESCRIPTION
				"This entry contains information about
				a given device. The entry is indexed by the
				port number, CU index, and device."
			INDEX	{ deviceConfigLineIndex, deviceConfigCUIndex, 
				  deviceConfigAddress }
			::= { deviceConfigTable 1 }

	DeviceConfigEntry ::= 
		SEQUENCE {
			deviceConfigLineIndex
				INTEGER,
			deviceConfigCUIndex
				INTEGER,
			deviceConfigAddress
				OCTET STRING,
			deviceConfigType
				INTEGER
			}

	
	deviceConfigLineIndex OBJECT-TYPE
		SYNTAX	INTEGER
		ACCESS	read-only
		STATUS	mandatory
		DESCRIPTION
			"The port number for which the line (CU)is configured 
			 (line level)."
		::= { deviceConfigEntry 1 }

	deviceConfigCUIndex	OBJECT-TYPE
		SYNTAX	INTEGER
		ACCESS	read-only
		STATUS	mandatory
		DESCRIPTION
			"The CU index which this device is configured on 
			 (CU level)."
		::= { deviceConfigEntry 2 }

	deviceConfigAddress	OBJECT-TYPE
		SYNTAX	OCTET STRING (SIZE(1))
		ACCESS	read-only
		STATUS	mandatory
		DESCRIPTION
			"The device address in the legal range of BSC poll
                         addresses (device level)."
		::= { deviceConfigEntry 3 }

	deviceConfigType	OBJECT-TYPE
		SYNTAX	INTEGER {
                        crt (1),
                        printer (2)
                        }
		ACCESS	read-only
		STATUS	mandatory
		DESCRIPTION
			"The device type. The default value is crt."
		::= { deviceConfigEntry 4 }

	--
	-- The Device Statistics Table 
	--

	deviceStatsTable	OBJECT-TYPE
			SYNTAX	SEQUENCE OF DeviceStatsEntry
			ACCESS	not-accessible
			STATUS	mandatory
			DESCRIPTION
				"A table of device statistics information."	
			::= { deviceBSCGroup 2 }

	deviceStatsEntry	OBJECT-TYPE
			SYNTAX	DeviceStatsEntry
			ACCESS	not-accessible
			STATUS	mandatory
			DESCRIPTION
				"This entry contains information about
				a given device. The entry is indexed by the
				port number, CU index, and device."
			INDEX	{ bscDeviceLineIndex, bscDeviceCUIndex, 
				  bscDeviceAddress }
			::= { deviceStatsTable 1 }

	DeviceStatsEntry ::= 
		SEQUENCE {
			bscDeviceLineIndex
				INTEGER,
			bscDeviceCUIndex
				INTEGER,
			bscDeviceAddress
				OCTET STRING,
			bscDeviceInTransactions
				Counter,
			bscDeviceOutTransactions
				Counter,
			bscDeviceSumCount
				Counter,
			bscDeviceResponseDelaySum
				Counter,
			bscDeviceResponseDelaySqSum
				Counter
			}

	
	bscDeviceLineIndex OBJECT-TYPE
		SYNTAX	INTEGER
		ACCESS	read-only
		STATUS	mandatory
		DESCRIPTION
			"The port number for which the line (CU)is configured 
			 (line level)."
		::= { deviceStatsEntry 1 }

	bscDeviceCUIndex	OBJECT-TYPE
		SYNTAX	INTEGER
		ACCESS	read-only
		STATUS	mandatory
		DESCRIPTION
			"The CU index which this device is configured on
			 (CU level)."
		::= { deviceStatsEntry 2 }

	bscDeviceAddress	OBJECT-TYPE
		SYNTAX	OCTET STRING (SIZE(1))
		ACCESS	read-only
		STATUS	mandatory
		DESCRIPTION
			"The device address in the legal range of BSC poll
                         addresses (device level)."
		::= { deviceStatsEntry 3 }

	bscDeviceInTransactions	OBJECT-TYPE
		SYNTAX	Counter
		ACCESS	read-only
		STATUS	mandatory
		DESCRIPTION
			"The number of device receiving transactions."
		::= { deviceStatsEntry 4 }

	bscDeviceOutTransactions OBJECT-TYPE
		SYNTAX	Counter
		ACCESS	read-only
		STATUS	mandatory
		DESCRIPTION
			"The number of device transmitting transactions."
		::= { deviceStatsEntry 5 }

	bscDeviceSumCount	OBJECT-TYPE
		SYNTAX	Counter 
		ACCESS	read-only
		STATUS	mandatory
		DESCRIPTION
			"The device sum count."
		::= { deviceStatsEntry 6 }

	bscDeviceResponseDelaySum OBJECT-TYPE
		SYNTAX	Counter 
		ACCESS	read-only
		STATUS	mandatory
		DESCRIPTION
			"The device sum count."
		::= { deviceStatsEntry 7 }

	bscDeviceResponseDelaySqSum OBJECT-TYPE
		SYNTAX	Counter 
		ACCESS	read-only
		STATUS	mandatory
		DESCRIPTION
			"The device sum count."
		::= { deviceStatsEntry 8 }


	--
	-- Sync Research TRAP MIB 
	--
	-- This MIB was jointly developed by Sync Research, Cabletron Systems,
	-- and Avatar Consultants.
	--
	-- Last Modification:
  	-- 06/27/93 Suketu Pandya, Sync Research, Version 1.0
	--	New version.  This version obsoletes previous version 0.1
	--
	--  This MIB module uses the extended TRAP-TYPE macro as
	--  defined in RFC 1215.


    
        configChanged TRAP-TYPE
		ENTERPRISE 	syncResearch
		VARIABLES	{ lastTrapSeqNumber, configId }
		DESCRIPTION
			"This trap indicates that the configuration of
      the unit has been changed."
		::= 800

        configError TRAP-TYPE
		ENTERPRISE 	syncResearch
		VARIABLES	{ lastTrapSeqNumber, lastInstallErrCode }
		DESCRIPTION
			"This trap indicates that the activation of configuration
      of the unit has resulted in an error.  New configuration
      has not been successfully activated."
		::= 801

            dumpExists TRAP-TYPE
		ENTERPRISE 	syncResearch
		VARIABLES	{ lastTrapSeqNumber, dumpFileName }
		DESCRIPTION
			"This trap indicates that a memory core dump exists."
		::= 802

            dumpArchived TRAP-TYPE
		ENTERPRISE 	syncResearch
		VARIABLES	{ lastTrapSeqNumber }
		DESCRIPTION
			"This trap indicates that the memory dump file has been
      archived."
		::= 803


        lineStatusChanged TRAP-TYPE
		ENTERPRISE 	syncResearch
		VARIABLES	{ lastTrapSeqNumber, lineStatus, lineControlFailureCode, linePhysicalIndex }
		DESCRIPTION
			"This trap indicates that the indicated Line or Port has 
      changed state.  It has either been enabled, failed or
      disabled."
		::= 804

        lanStatusChanged TRAP-TYPE
		ENTERPRISE 	syncResearch
		VARIABLES	{ lastTrapSeqNumber, lanStatus, lanControlFailureCode }
		DESCRIPTION
			"This trap indicates that the indicated LAN Port has 
      changed state.  It has either been enabled, failed or
      disabled."
		::= 805

        lineQuality TRAP-TYPE
		ENTERPRISE 	syncResearch
		VARIABLES	{ lastTrapSeqNumber, lineQualityFrameCount,
                lineQualityCRCErrors, lineQualityAborts, linePhysicalIndex }
		DESCRIPTION
      			" "
		::= 806

        puStatusChanged TRAP-TYPE
		ENTERPRISE 	syncResearch
		VARIABLES	{ lastTrapSeqNumber, puStatus, 
                                  puControlFailureCode, linePhysicalIndex,
                                  puControlPUAddress }
		DESCRIPTION
			"This trap indicates that the indicated PU has 
      changed state.  It has either been enabled, failed or
      disabled."
		::= 807

        puConnectionStatusChanged TRAP-TYPE
		ENTERPRISE 	syncResearch
		VARIABLES	{ lastTrapSeqNumber, puConnectionStatus, puLastClearCode }
		DESCRIPTION
			"Note this trap is obsolete. This trap indicates that the indicated PU has 
      changed connection state.  Its connection has either been 
      established, disconnected, or rejected."
		::= 808

        netviewConnectionStatusChanged TRAP-TYPE
		ENTERPRISE 	syncResearch
		VARIABLES	{ lastTrapSeqNumber, netviewConnectionStatus,
                netviewLastClearCode }
		DESCRIPTION
			"Note this trap is obsolete. This trap indicates that the NetView PU has 
      changed connection state.  Its connection has either been 
      established, disconnected, or rejected."
		::= 809

        netviewAltConnectionStatusChanged TRAP-TYPE
		ENTERPRISE 	syncResearch
		VARIABLES	{ lastTrapSeqNumber, netviewAltConnectionStatus,
                netviewAltLastClearCode }
		DESCRIPTION
			"Note this trap is obsolete. This trap indicates that the Alternate NetView PU has 
      changed connection state.  Its connection has either been 
      established, disconnected, or rejected."
		::= 810

        puConnectionStatusUp TRAP-TYPE
		ENTERPRISE 	syncResearch
		VARIABLES	{ lastTrapSeqNumber, linePhysicalIndex, puControlPUAddress }
		DESCRIPTION
			"This trap indicates that the indicated PU has 
      changed connection state.  Its connection had been established." 
		::= 811

        puConnectionStatusDown TRAP-TYPE
		ENTERPRISE 	syncResearch
		VARIABLES	{ lastTrapSeqNumber, puLastClearCode, linePhysicalIndex, puControlPUAddress }
		DESCRIPTION
			"This trap indicates that the indicated PU has 
      changed connection state.  Its connection has been disconnected.
      If the indicated PU is not in session, the trap is generated only
      if the clear code is different from the puLastClearCode." 
		::= 812

        netviewConnectionStatusUp TRAP-TYPE
		ENTERPRISE 	syncResearch
		VARIABLES	{ lastTrapSeqNumber }
		DESCRIPTION
			"This trap indicates that the indicated NetView PU has 
      changed connection state.  Its connection has been established." 
		::= 813

        netviewConnectionStatusDown TRAP-TYPE
		ENTERPRISE 	syncResearch
		VARIABLES	{ lastTrapSeqNumber, netviewLastClearCode }
		DESCRIPTION
			"This trap indicates that the indicated NetView PU has 
      changed connection state.  Its connection had been disconnected. 
      If the indicated PU is not in session, the trap is generated only
      if the clear code is different from the netviewLastClearCode." 
		::= 814

        netviewAltConnectionStatusUp TRAP-TYPE
		ENTERPRISE 	syncResearch
		VARIABLES	{ lastTrapSeqNumber }
		DESCRIPTION
			"This trap indicates that the indicated Alternate  
      NetView PU has changed connection state.  Its connection has been 
      established." 
		::= 815

        netviewAltConnectionStatusDown TRAP-TYPE
		ENTERPRISE 	syncResearch
		VARIABLES	{ lastTrapSeqNumber, netviewAltLastClearCode }
		DESCRIPTION
			"This trap indicates that the indicated Alternate 
      NetView PU has changed connection state.  Its connection had been 
      disconnected. If the indicated PU is not in session, the trap is generated
      only if the clear code is different from the netviewAltLastClearCode." 
		::= 816
END
