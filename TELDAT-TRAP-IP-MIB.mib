-- file automatically created


TELDAT-TRAP-IP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IP event subsystem."
    REVISION "201401200930Z"
    DESCRIPTION "Initial implementation"
        ::= { telEventTraps 10 }


ipEventsGroup	OBJECT IDENTIFIER	::= { ipTrapsMIB 1 }

ipNotifications	OBJECT IDENTIFIER	::= { ipTrapsMIB 2 }
ipNotificationsPrefix	OBJECT IDENTIFIER	::= { ipNotifications 0 }

ipEventObjects1 OBJECT-IDENTITY
    STATUS current
    DESCRIPTION
        "Event IP.1
        This message is generated when the forwarder must discard a packet that
        was not forwarded via the IP cache because of an input queue overflow.
        Note that this event does not get counted in ELS, it is instead counted
        in the IP console.
        The counters (kept per input interface) can be read using the
        IP>COUNTERS command."
    ::= { ipEventsGroup 1 }

ip1-source-ip-address OBJECT-TYPE
    SYNTAX IpAddress
    MAX-ACCESS accessible-for-notify
    STATUS current
    DESCRIPTION
        "Parameter 'source-ip-address' in event IP.1"
    ::= { ipEventObjects1 1 }

ip1-destination-ip-address OBJECT-TYPE
    SYNTAX IpAddress
    MAX-ACCESS accessible-for-notify
    STATUS current
    DESCRIPTION
        "Parameter 'destination-ip-address' in event IP.1"
    ::= { ipEventObjects1 2 }

ip1-interface OBJECT-TYPE
    SYNTAX DisplayString
    MAX-ACCESS accessible-for-notify
    STATUS current
    DESCRIPTION
        "Parameter 'interface' in event IP.1"
    ::= { ipEventObjects1 3 }

ipEventObjects2 OBJECT-IDENTITY
    STATUS current
    DESCRIPTION
        "Event IP.2
        This message is generated when a packet has an incorrect version number."
    ::= { ipEventsGroup 2 }

ip2-version-number OBJECT-TYPE
    SYNTAX Integer32
    MAX-ACCESS accessible-for-notify
    STATUS current
    DESCRIPTION
        "Parameter 'version-number' in event IP.2"
    ::= { ipEventObjects2 1 }

ip2-interface OBJECT-TYPE
    SYNTAX DisplayString
    MAX-ACCESS accessible-for-notify
    STATUS current
    DESCRIPTION
        "Parameter 'interface' in event IP.2"
    ::= { ipEventObjects2 2 }

ipEventObjects3 OBJECT-IDENTITY
    STATUS current
    DESCRIPTION
        "Event IP.3
        This message is generated when a packet's indicated header length is
        below the minimum possible length."
    ::= { ipEventsGroup 3 }

ip3-header-length OBJECT-TYPE
    SYNTAX Integer32
    MAX-ACCESS accessible-for-notify
    STATUS current
    DESCRIPTION
        "Parameter 'header-length' in event IP.3"
    ::= { ipEventObjects3 1 }

ip3-packet-length OBJECT-TYPE
    SYNTAX Integer32
    MAX-ACCESS accessible-for-notify
    STATUS current
    DESCRIPTION
        "Parameter 'packet-length' in event IP.3"
    ::= { ipEventObjects3 2 }

ip3-interface OBJECT-TYPE
    SYNTAX DisplayString
    MAX-ACCESS accessible-for-notify
    STATUS current
    DESCRIPTION
        "Parameter 'interface' in event IP.3"
    ::= { ipEventObjects3 3 }

ipEventObjects4 OBJECT-IDENTITY
    STATUS current
    DESCRIPTION
        "Event IP.4
        This message is generated when a packet has an invalid checksum.
        The received checksum, together with the correct checksum,
        are displayed."
    ::= { ipEventsGroup 4 }

ip4-checksum OBJECT-TYPE
    SYNTAX Integer32
    MAX-ACCESS accessible-for-notify
    STATUS current
    DESCRIPTION
        "Parameter 'checksum' in event IP.4"
    ::= { ipEventObjects4 1 }

ip4-expected-checksum OBJECT-TYPE
    SYNTAX Integer32
    MAX-ACCESS accessible-for-notify
    STATUS current
    DESCRIPTION
        "Parameter 'expected-checksum' in event IP.4"
    ::= { ipEventObjects4 2 }

ip4-source-ip-address OBJECT-TYPE
    SYNTAX IpAddress
    MAX-ACCESS accessible-for-notify
    STATUS current
    DESCRIPTION
        "Parameter 'source-ip-address' in event IP.4"
    ::= { ipEventObjects4 3 }

ip4-destination-ip-address OBJECT-TYPE
    SYNTAX IpAddress
    MAX-ACCESS accessible-for-notify
    STATUS current
    DESCRIPTION
        "Parameter 'destination-ip-address' in event IP.4"
    ::= { ipEventObjects4 4 }

ipEventObjects5 OBJECT-IDENTITY
    STATUS current
    DESCRIPTION
        "Event IP.5
        This message is generated when the packet length specified in the header
        is greater than the packet buffer length."
    ::= { ipEventsGroup 5 }

ip5-specified-length OBJECT-TYPE
    SYNTAX Integer32
    MAX-ACCESS accessible-for-notify
    STATUS current
    DESCRIPTION
        "Parameter 'specified-length' in event IP.5"
    ::= { ipEventObjects5 1 }

ip5-true-length OBJECT-TYPE
    SYNTAX Integer32
    MAX-ACCESS accessible-for-notify
    STATUS current
    DESCRIPTION
        "Parameter 'true-length' in event IP.5"
    ::= { ipEventObjects5 2 }

ip5-source-ip-address OBJECT-TYPE
    SYNTAX IpAddress
    MAX-ACCESS accessible-for-notify
    STATUS current
    DESCRIPTION
        "Parameter 'source-ip-address' in event IP.5"
    ::= { ipEventObjects5 3 }

ip5-destination-ip-address OBJECT-TYPE
    SYNTAX IpAddress
    MAX-ACCESS accessible-for-notify
    STATUS current
    DESCRIPTION
        "Parameter 'destination-ip-address' in event IP.5"
    ::= { ipEventObjects5 4 }

ipEventObjects6 OBJECT-IDENTITY
    STATUS current
    DESCRIPTION
        "Event IP.6
        An attempt was made to send the packet on the specified interface, but
        it was not accepted for transmission on that network. The reason-code
        indicates why the packet was not accepted. If the reason was
        flow-control, an ICMP source quench will be sent to the sender,
        otherwise an ICMP destination unreachable will be sent."
    ::= { ipEventsGroup 6 }

ip6-source-ip-address OBJECT-TYPE
    SYNTAX IpAddress
    MAX-ACCESS accessible-for-notify
    STATUS current
    DESCRIPTION
        "Parameter 'source-ip-address' in event IP.6"
    ::= { ipEventObjects6 1 }

ip6-destination-ip-address OBJECT-TYPE
    SYNTAX IpAddress
    MAX-ACCESS accessible-for-notify
    STATUS current
    DESCRIPTION
        "Parameter 'destination-ip-address' in event IP.6"
    ::= { ipEventObjects6 2 }

ip6-reason-code OBJECT-TYPE
    SYNTAX Integer32
    MAX-ACCESS accessible-for-notify
    STATUS current
    DESCRIPTION
        "Parameter 'reason-code' in event IP.6"
    ::= { ipEventObjects6 3 }

ip6-interface OBJECT-TYPE
    SYNTAX DisplayString
    MAX-ACCESS accessible-for-notify
    STATUS current
    DESCRIPTION
        "Parameter 'interface' in event IP.6"
    ::= { ipEventObjects6 4 }

ipEventObjects7 OBJECT-IDENTITY
    STATUS current
    DESCRIPTION
        "Event IP.7
        This message is generated for each packet which has passed first-level
        reasonableness checks."
    ::= { ipEventsGroup 7 }

ip7-source-ip-address OBJECT-TYPE
    SYNTAX IpAddress
    MAX-ACCESS accessible-for-notify
    STATUS current
    DESCRIPTION
        "Parameter 'source-ip-address' in event IP.7"
    ::= { ipEventObjects7 1 }

ip7-destination-ip-address OBJECT-TYPE
    SYNTAX IpAddress
    MAX-ACCESS accessible-for-notify
    STATUS current
    DESCRIPTION
        "Parameter 'destination-ip-address' in event IP.7"
    ::= { ipEventObjects7 2 }

ipEventObjects8 OBJECT-IDENTITY
    STATUS current
    DESCRIPTION
        "Event IP.8
        This message is generated when a packet is discarded because there is
        no route to the destination."
    ::= { ipEventsGroup 8 }

ip8-source-ip-address OBJECT-TYPE
    SYNTAX IpAddress
    MAX-ACCESS accessible-for-notify
    STATUS current
    DESCRIPTION
        "Parameter 'source-ip-address' in event IP.8"
    ::= { ipEventObjects8 1 }

ip8-destination-ip-address OBJECT-TYPE
    SYNTAX IpAddress
    MAX-ACCESS accessible-for-notify
    STATUS current
    DESCRIPTION
        "Parameter 'destination-ip-address' in event IP.8"
    ::= { ipEventObjects8 2 }

ipEventObjects9 OBJECT-IDENTITY
    STATUS current
    DESCRIPTION
        "Event IP.9
        This message is generated when a packet is discarded because
        the time-to-live expired."
    ::= { ipEventsGroup 9 }

ip9-source-ip-address OBJECT-TYPE
    SYNTAX IpAddress
    MAX-ACCESS accessible-for-notify
    STATUS current
    DESCRIPTION
        "Parameter 'source-ip-address' in event IP.9"
    ::= { ipEventObjects9 1 }

ip9-destination-ip-address OBJECT-TYPE
    SYNTAX IpAddress
    MAX-ACCESS accessible-for-notify
    STATUS current
    DESCRIPTION
        "Parameter 'destination-ip-address' in event IP.9"
    ::= { ipEventObjects9 2 }

ipEventObjects10 OBJECT-IDENTITY
    STATUS current
    DESCRIPTION
        "Event IP.10
        This message is generated by the fake IP forwarder for each packet
        which is received."
    ::= { ipEventsGroup 10 }

ip10-source-ip-address OBJECT-TYPE
    SYNTAX IpAddress
    MAX-ACCESS accessible-for-notify
    STATUS current
    DESCRIPTION
        "Parameter 'source-ip-address' in event IP.10"
    ::= { ipEventObjects10 1 }

ip10-destination-ip-address OBJECT-TYPE
    SYNTAX IpAddress
    MAX-ACCESS accessible-for-notify
    STATUS current
    DESCRIPTION
        "Parameter 'destination-ip-address' in event IP.10"
    ::= { ipEventObjects10 2 }

ip10-interface OBJECT-TYPE
    SYNTAX DisplayString
    MAX-ACCESS accessible-for-notify
    STATUS current
    DESCRIPTION
        "Parameter 'interface' in event IP.10"
    ::= { ipEventObjects10 3 }

ipEventObjects11 OBJECT-IDENTITY
    STATUS current
    DESCRIPTION
        "Event IP.11
        This message is generated when an unsupported multicast packet
        is received."
    ::= { ipEventsGroup 11 }

ip11-source-ip-address OBJECT-TYPE
    SYNTAX IpAddress
    MAX-ACCESS accessible-for-notify
    STATUS current
    DESCRIPTION
        "Parameter 'source-ip-address' in event IP.11"
    ::= { ipEventObjects11 1 }

ip11-destination-ip-address OBJECT-TYPE
    SYNTAX IpAddress
    MAX-ACCESS accessible-for-notify
    STATUS current
    DESCRIPTION
        "Parameter 'destination-ip-address' in event IP.11"
    ::= { ipEventObjects11 2 }

ipEventObjects12 OBJECT-IDENTITY
    STATUS current
    DESCRIPTION
        "Event IP.12
        This message is generated when a packet is destined for a network
        which is not class A, B, C or D."
    ::= { ipEventsGroup 12 }

ip12-source-ip-address OBJECT-TYPE
    SYNTAX IpAddress
    MAX-ACCESS accessible-for-notify
    STATUS current
    DESCRIPTION
        "Parameter 'source-ip-address' in event IP.12"
    ::= { ipEventObjects12 1 }

ip12-destination-ip-address OBJECT-TYPE
    SYNTAX IpAddress
    MAX-ACCESS accessible-for-notify
    STATUS current
    DESCRIPTION
        "Parameter 'destination-ip-address' in event IP.12"
    ::= { ipEventObjects12 2 }

ipEventObjects13 OBJECT-IDENTITY
    STATUS current
    DESCRIPTION
        "Event IP.13
        This message is generated when an unsupported broadcast packet
        is received."
    ::= { ipEventsGroup 13 }

ip13-source-ip-address OBJECT-TYPE
    SYNTAX IpAddress
    MAX-ACCESS accessible-for-notify
    STATUS current
    DESCRIPTION
        "Parameter 'source-ip-address' in event IP.13"
    ::= { ipEventObjects13 1 }

ip13-destination-ip-address OBJECT-TYPE
    SYNTAX IpAddress
    MAX-ACCESS accessible-for-notify
    STATUS current
    DESCRIPTION
        "Parameter 'destination-ip-address' in event IP.13"
    ::= { ipEventObjects13 2 }

ipEventObjects17 OBJECT-IDENTITY
    STATUS current
    DESCRIPTION
        "Event IP.17
        This message is generated when a network cannot be added to the
        routing table because the table is full."
    ::= { ipEventsGroup 17 }

ip17-network-address OBJECT-TYPE
    SYNTAX IpAddress
    MAX-ACCESS accessible-for-notify
    STATUS current
    DESCRIPTION
        "Parameter 'network-address' in event IP.17"
    ::= { ipEventObjects17 1 }

ipEventObjects18 OBJECT-IDENTITY
    STATUS current
    DESCRIPTION
        "Event IP.18
        This message is generated when a network cannot be added to the
        routing table because of a bad network number."
    ::= { ipEventsGroup 18 }

ip18-network-address OBJECT-TYPE
    SYNTAX IpAddress
    MAX-ACCESS accessible-for-notify
    STATUS current
    DESCRIPTION
        "Parameter 'network-address' in event IP.18"
    ::= { ipEventObjects18 1 }

ipEventObjects19 OBJECT-IDENTITY
    STATUS current
    DESCRIPTION
        "Event IP.19
        This message is generated when a static route to a network is brought
        back into use."
    ::= { ipEventsGroup 19 }

ip19-network OBJECT-TYPE
    SYNTAX IpAddress
    MAX-ACCESS accessible-for-notify
    STATUS current
    DESCRIPTION
        "Parameter 'network' in event IP.19"
    ::= { ipEventObjects19 1 }

ipEventObjects20 OBJECT-IDENTITY
    STATUS current
    DESCRIPTION
        "Event IP.20
        This message is generated when a network cannot be added to the
        routing table because the access was denied."
    ::= { ipEventsGroup 20 }

ip20-network OBJECT-TYPE
    SYNTAX IpAddress
    MAX-ACCESS accessible-for-notify
    STATUS current
    DESCRIPTION
        "Parameter 'network' in event IP.20"
    ::= { ipEventObjects20 1 }

ipEventObjects21 OBJECT-IDENTITY
    STATUS current
    DESCRIPTION
        "Event IP.21
        This message is generated when a new route is added to the routing
        table. This is a directly connected network."
    ::= { ipEventsGroup 21 }

ip21-network OBJECT-TYPE
    SYNTAX IpAddress
    MAX-ACCESS accessible-for-notify
    STATUS current
    DESCRIPTION
        "Parameter 'network' in event IP.21"
    ::= { ipEventObjects21 1 }

ip21-mask OBJECT-TYPE
    SYNTAX Integer32
    MAX-ACCESS accessible-for-notify
    STATUS current
    DESCRIPTION
        "Parameter 'mask' in event IP.21"
    ::= { ipEventObjects21 2 }

ip21-interface OBJECT-TYPE
    SYNTAX DisplayString
    MAX-ACCESS accessible-for-notify
    STATUS current
    DESCRIPTION
        "Parameter 'interface' in event IP.21"
    ::= { ipEventObjects21 3 }

ipEventObjects22 OBJECT-IDENTITY
    STATUS current
    DESCRIPTION
        "Event IP.22
        This message is generated when a new local network is added to the
        routing table."
    ::= { ipEventsGroup 22 }

ip22-local-ip-network OBJECT-TYPE
    SYNTAX IpAddress
    MAX-ACCESS accessible-for-notify
    STATUS current
    DESCRIPTION
        "Parameter 'local-ip-network' in event IP.22"
    ::= { ipEventObjects22 1 }

ip22-local-ip-mask OBJECT-TYPE
    SYNTAX Integer32
    MAX-ACCESS accessible-for-notify
    STATUS current
    DESCRIPTION
        "Parameter 'local-ip-mask' in event IP.22"
    ::= { ipEventObjects22 2 }

ip22-interface OBJECT-TYPE
    SYNTAX DisplayString
    MAX-ACCESS accessible-for-notify
    STATUS current
    DESCRIPTION
        "Parameter 'interface' in event IP.22"
    ::= { ipEventObjects22 3 }

ipEventObjects23 OBJECT-IDENTITY
    STATUS current
    DESCRIPTION
        "Event IP.23
        This message is generated when a new route is added to the routing
        table. The gateway is directly connected."
    ::= { ipEventsGroup 23 }

ip23-network OBJECT-TYPE
    SYNTAX IpAddress
    MAX-ACCESS accessible-for-notify
    STATUS current
    DESCRIPTION
        "Parameter 'network' in event IP.23"
    ::= { ipEventObjects23 1 }

ip23-mask OBJECT-TYPE
    SYNTAX Integer32
    MAX-ACCESS accessible-for-notify
    STATUS current
    DESCRIPTION
        "Parameter 'mask' in event IP.23"
    ::= { ipEventObjects23 2 }

ip23-gateway OBJECT-TYPE
    SYNTAX IpAddress
    MAX-ACCESS accessible-for-notify
    STATUS current
    DESCRIPTION
        "Parameter 'gateway' in event IP.23"
    ::= { ipEventObjects23 3 }

ip23-interface OBJECT-TYPE
    SYNTAX DisplayString
    MAX-ACCESS accessible-for-notify
    STATUS current
    DESCRIPTION
        "Parameter 'interface' in event IP.23"
    ::= { ipEventObjects23 4 }

ipEventObjects24 OBJECT-IDENTITY
    STATUS current
    DESCRIPTION
        "Event IP.24
        This message is generated when a bad static route or IP filter
        is encountered."
    ::= { ipEventsGroup 24 }

ip24-network OBJECT-TYPE
    SYNTAX IpAddress
    MAX-ACCESS accessible-for-notify
    STATUS current
    DESCRIPTION
        "Parameter 'network' in event IP.24"
    ::= { ipEventObjects24 1 }

ip24-mask OBJECT-TYPE
    SYNTAX Integer32
    MAX-ACCESS accessible-for-notify
    STATUS current
    DESCRIPTION
        "Parameter 'mask' in event IP.24"
    ::= { ipEventObjects24 2 }

ipEventObjects25 OBJECT-IDENTITY
    STATUS current
    DESCRIPTION
        "Event IP.25
        This message is generated when a new route is added to the routing
        table. The route is indirectly connected."
    ::= { ipEventsGroup 25 }

ip25-network OBJECT-TYPE
    SYNTAX IpAddress
    MAX-ACCESS accessible-for-notify
    STATUS current
    DESCRIPTION
        "Parameter 'network' in event IP.25"
    ::= { ipEventObjects25 1 }

ip25-mask OBJECT-TYPE
    SYNTAX Integer32
    MAX-ACCESS accessible-for-notify
    STATUS current
    DESCRIPTION
        "Parameter 'mask' in event IP.25"
    ::= { ipEventObjects25 2 }

ip25-gateway OBJECT-TYPE
    SYNTAX IpAddress
    MAX-ACCESS accessible-for-notify
    STATUS current
    DESCRIPTION
        "Parameter 'gateway' in event IP.25"
    ::= { ipEventObjects25 3 }

ipEventObjects26 OBJECT-IDENTITY
    STATUS current
    DESCRIPTION
        "Event IP.26
        This message is generated for each packet which has passed
        NAT in."
    ::= { ipEventsGroup 26 }

ip26-source-ip-address OBJECT-TYPE
    SYNTAX IpAddress
    MAX-ACCESS accessible-for-notify
    STATUS current
    DESCRIPTION
        "Parameter 'source-ip-address' in event IP.26"
    ::= { ipEventObjects26 1 }

ip26-destination-ip-address OBJECT-TYPE
    SYNTAX IpAddress
    MAX-ACCESS accessible-for-notify
    STATUS current
    DESCRIPTION
        "Parameter 'destination-ip-address' in event IP.26"
    ::= { ipEventObjects26 2 }

ip26-source-ip-address-nat OBJECT-TYPE
    SYNTAX IpAddress
    MAX-ACCESS accessible-for-notify
    STATUS current
    DESCRIPTION
        "Parameter 'source-ip-address-nat' in event IP.26"
    ::= { ipEventObjects26 3 }

ip26-destination-ip-address-nat OBJECT-TYPE
    SYNTAX IpAddress
    MAX-ACCESS accessible-for-notify
    STATUS current
    DESCRIPTION
        "Parameter 'destination-ip-address-nat' in event IP.26"
    ::= { ipEventObjects26 4 }

ipEventObjects27 OBJECT-IDENTITY
    STATUS current
    DESCRIPTION
        "Event IP.27
        This message is generated for each packet which has passed
        NAT out."
    ::= { ipEventsGroup 27 }

ip27-source-ip-address OBJECT-TYPE
    SYNTAX IpAddress
    MAX-ACCESS accessible-for-notify
    STATUS current
    DESCRIPTION
        "Parameter 'source-ip-address' in event IP.27"
    ::= { ipEventObjects27 1 }

ip27-destination-ip-address OBJECT-TYPE
    SYNTAX IpAddress
    MAX-ACCESS accessible-for-notify
    STATUS current
    DESCRIPTION
        "Parameter 'destination-ip-address' in event IP.27"
    ::= { ipEventObjects27 2 }

ip27-source-ip-address-nat OBJECT-TYPE
    SYNTAX IpAddress
    MAX-ACCESS accessible-for-notify
    STATUS current
    DESCRIPTION
        "Parameter 'source-ip-address-nat' in event IP.27"
    ::= { ipEventObjects27 3 }

ip27-destination-ip-address-nat OBJECT-TYPE
    SYNTAX IpAddress
    MAX-ACCESS accessible-for-notify
    STATUS current
    DESCRIPTION
        "Parameter 'destination-ip-address-nat' in event IP.27"
    ::= { ipEventObjects27 4 }

ipEventObjects28 OBJECT-IDENTITY
    STATUS current
    DESCRIPTION
        "Event IP.28
        This message is generated for each packet which has no been
        NATed in."
    ::= { ipEventsGroup 28 }

ip28-source-ip-address OBJECT-TYPE
    SYNTAX IpAddress
    MAX-ACCESS accessible-for-notify
    STATUS current
    DESCRIPTION
        "Parameter 'source-ip-address' in event IP.28"
    ::= { ipEventObjects28 1 }

ip28-destination-ip-address OBJECT-TYPE
    SYNTAX IpAddress
    MAX-ACCESS accessible-for-notify
    STATUS current
    DESCRIPTION
        "Parameter 'destination-ip-address' in event IP.28"
    ::= { ipEventObjects28 2 }

ipEventObjects29 OBJECT-IDENTITY
    STATUS current
    DESCRIPTION
        "Event IP.29
        This message is generated for each packet which has no been
        NATed out."
    ::= { ipEventsGroup 29 }

ip29-source-ip-address OBJECT-TYPE
    SYNTAX IpAddress
    MAX-ACCESS accessible-for-notify
    STATUS current
    DESCRIPTION
        "Parameter 'source-ip-address' in event IP.29"
    ::= { ipEventObjects29 1 }

ip29-destination-ip-address OBJECT-TYPE
    SYNTAX IpAddress
    MAX-ACCESS accessible-for-notify
    STATUS current
    DESCRIPTION
        "Parameter 'destination-ip-address' in event IP.29"
    ::= { ipEventObjects29 2 }

ipEventObjects30 OBJECT-IDENTITY
    STATUS current
    DESCRIPTION
        "Event IP.30
        This message is generated when an outgoing packet is not translated
        because there is not free nat entries."
    ::= { ipEventsGroup 30 }

ip30-source-ip-address OBJECT-TYPE
    SYNTAX IpAddress
    MAX-ACCESS accessible-for-notify
    STATUS current
    DESCRIPTION
        "Parameter 'source-ip-address' in event IP.30"
    ::= { ipEventObjects30 1 }

ip30-destination-ip-address OBJECT-TYPE
    SYNTAX IpAddress
    MAX-ACCESS accessible-for-notify
    STATUS current
    DESCRIPTION
        "Parameter 'destination-ip-address' in event IP.30"
    ::= { ipEventObjects30 2 }

ipEventObjects31 OBJECT-IDENTITY
    STATUS current
    DESCRIPTION
        "Event IP.31
        An attempt has been made to configure an interface as unnumbered,
        yet either the interface is not a serial line or the interface has
        already been assigned an IP address. The unnumbered configuration
        request is ignored."
    ::= { ipEventsGroup 31 }

ip31-interface OBJECT-TYPE
    SYNTAX DisplayString
    MAX-ACCESS accessible-for-notify
    STATUS current
    DESCRIPTION
        "Parameter 'interface' in event IP.31"
    ::= { ipEventObjects31 1 }

ipEventObjects32 OBJECT-IDENTITY
    STATUS current
    DESCRIPTION
        "Event IP.32
        This message is generated when an incoming fragment is discarded
        because the fragment queue overflowed."
    ::= { ipEventsGroup 32 }

ip32-source-ip-address OBJECT-TYPE
    SYNTAX IpAddress
    MAX-ACCESS accessible-for-notify
    STATUS current
    DESCRIPTION
        "Parameter 'source-ip-address' in event IP.32"
    ::= { ipEventObjects32 1 }

ip32-destination-ip-address OBJECT-TYPE
    SYNTAX IpAddress
    MAX-ACCESS accessible-for-notify
    STATUS current
    DESCRIPTION
        "Parameter 'destination-ip-address' in event IP.32"
    ::= { ipEventObjects32 2 }

ip32-interface OBJECT-TYPE
    SYNTAX DisplayString
    MAX-ACCESS accessible-for-notify
    STATUS current
    DESCRIPTION
        "Parameter 'interface' in event IP.32"
    ::= { ipEventObjects32 3 }

ipEventObjects33 OBJECT-IDENTITY
    STATUS current
    DESCRIPTION
        "Event IP.33
        This message is generated when an outgoing packet needs to be
        fragmented but has the 'don't fragment' bit set."
    ::= { ipEventsGroup 33 }

ip33-source-ip-address OBJECT-TYPE
    SYNTAX IpAddress
    MAX-ACCESS accessible-for-notify
    STATUS current
    DESCRIPTION
        "Parameter 'source-ip-address' in event IP.33"
    ::= { ipEventObjects33 1 }

ip33-destination-ip-address OBJECT-TYPE
    SYNTAX IpAddress
    MAX-ACCESS accessible-for-notify
    STATUS current
    DESCRIPTION
        "Parameter 'destination-ip-address' in event IP.33"
    ::= { ipEventObjects33 2 }

ip33-interface OBJECT-TYPE
    SYNTAX DisplayString
    MAX-ACCESS accessible-for-notify
    STATUS current
    DESCRIPTION
        "Parameter 'interface' in event IP.33"
    ::= { ipEventObjects33 3 }

ipEventObjects34 OBJECT-IDENTITY
    STATUS current
    DESCRIPTION
        "Event IP.34
        This message is generated when an outgoing packet has an invalid length
        of fragment offset."
    ::= { ipEventsGroup 34 }

ip34-source-ip-address OBJECT-TYPE
    SYNTAX IpAddress
    MAX-ACCESS accessible-for-notify
    STATUS current
    DESCRIPTION
        "Parameter 'source-ip-address' in event IP.34"
    ::= { ipEventObjects34 1 }

ip34-destination-ip-address OBJECT-TYPE
    SYNTAX IpAddress
    MAX-ACCESS accessible-for-notify
    STATUS current
    DESCRIPTION
        "Parameter 'destination-ip-address' in event IP.34"
    ::= { ipEventObjects34 2 }

ip34-offset OBJECT-TYPE
    SYNTAX Integer32
    MAX-ACCESS accessible-for-notify
    STATUS current
    DESCRIPTION
        "Parameter 'offset' in event IP.34"
    ::= { ipEventObjects34 3 }

ipEventObjects35 OBJECT-IDENTITY
    STATUS current
    DESCRIPTION
        "Event IP.35
        This message is generated when no buffer is available to fragment
        a packet."
    ::= { ipEventsGroup 35 }

ip35-interface OBJECT-TYPE
    SYNTAX DisplayString
    MAX-ACCESS accessible-for-notify
    STATUS current
    DESCRIPTION
        "Parameter 'interface' in event IP.35"
    ::= { ipEventObjects35 1 }

ipEventObjects36 OBJECT-IDENTITY
    STATUS current
    DESCRIPTION
        "Event IP.36
        This message is generated for each packet destined for the router."
    ::= { ipEventsGroup 36 }

ip36-protocol OBJECT-TYPE
    SYNTAX Integer32
    MAX-ACCESS accessible-for-notify
    STATUS current
    DESCRIPTION
        "Parameter 'protocol' in event IP.36"
    ::= { ipEventObjects36 1 }

ip36-source-ip-address OBJECT-TYPE
    SYNTAX IpAddress
    MAX-ACCESS accessible-for-notify
    STATUS current
    DESCRIPTION
        "Parameter 'source-ip-address' in event IP.36"
    ::= { ipEventObjects36 2 }

ipEventObjects37 OBJECT-IDENTITY
    STATUS current
    DESCRIPTION
        "Event IP.37
        This message is generated when a broadcast packet arrives for an
        unknown protocol."
    ::= { ipEventsGroup 37 }

ip37-source-ip-address OBJECT-TYPE
    SYNTAX IpAddress
    MAX-ACCESS accessible-for-notify
    STATUS current
    DESCRIPTION
        "Parameter 'source-ip-address' in event IP.37"
    ::= { ipEventObjects37 1 }

ip37-destination-ip-address OBJECT-TYPE
    SYNTAX IpAddress
    MAX-ACCESS accessible-for-notify
    STATUS current
    DESCRIPTION
        "Parameter 'destination-ip-address' in event IP.37"
    ::= { ipEventObjects37 2 }

ip37-protocol OBJECT-TYPE
    SYNTAX Integer32
    MAX-ACCESS accessible-for-notify
    STATUS current
    DESCRIPTION
        "Parameter 'protocol' in event IP.37"
    ::= { ipEventObjects37 3 }

ipEventObjects38 OBJECT-IDENTITY
    STATUS current
    DESCRIPTION
        "Event IP.38
        This message is generated when a packet arrives for an
        unknown protocol. The packet was destined for the router."
    ::= { ipEventsGroup 38 }

ip38-source-ip-address OBJECT-TYPE
    SYNTAX IpAddress
    MAX-ACCESS accessible-for-notify
    STATUS current
    DESCRIPTION
        "Parameter 'source-ip-address' in event IP.38"
    ::= { ipEventObjects38 1 }

ip38-destination-ip-address OBJECT-TYPE
    SYNTAX IpAddress
    MAX-ACCESS accessible-for-notify
    STATUS current
    DESCRIPTION
        "Parameter 'destination-ip-address' in event IP.38"
    ::= { ipEventObjects38 2 }

ip38-protocol OBJECT-TYPE
    SYNTAX Integer32
    MAX-ACCESS accessible-for-notify
    STATUS current
    DESCRIPTION
        "Parameter 'protocol' in event IP.38"
    ::= { ipEventObjects38 3 }

ipEventObjects42 OBJECT-IDENTITY
    STATUS current
    DESCRIPTION
        "Event IP.42
        This message is generated when an ARP subnet request is not honored
        due to illegal source or destination IP addresses in the ARP packet."
    ::= { ipEventsGroup 42 }

ip42-source-ip-address OBJECT-TYPE
    SYNTAX IpAddress
    MAX-ACCESS accessible-for-notify
    STATUS current
    DESCRIPTION
        "Parameter 'source-ip-address' in event IP.42"
    ::= { ipEventObjects42 1 }

ip42-destination-ip-address OBJECT-TYPE
    SYNTAX IpAddress
    MAX-ACCESS accessible-for-notify
    STATUS current
    DESCRIPTION
        "Parameter 'destination-ip-address' in event IP.42"
    ::= { ipEventObjects42 2 }

ipEventObjects43 OBJECT-IDENTITY
    STATUS current
    DESCRIPTION
        "Event IP.43
        This message is generated when an ARP subnet request is received."
    ::= { ipEventsGroup 43 }

ip43-source-ip-address OBJECT-TYPE
    SYNTAX IpAddress
    MAX-ACCESS accessible-for-notify
    STATUS current
    DESCRIPTION
        "Parameter 'source-ip-address' in event IP.43"
    ::= { ipEventObjects43 1 }

ip43-destination-ip-address OBJECT-TYPE
    SYNTAX IpAddress
    MAX-ACCESS accessible-for-notify
    STATUS current
    DESCRIPTION
        "Parameter 'destination-ip-address' in event IP.43"
    ::= { ipEventObjects43 2 }

ipEventObjects44 OBJECT-IDENTITY
    STATUS current
    DESCRIPTION
        "Event IP.44
        This message is generated when an ARP subnet request is not answered
        because the route to the target subnet is via another router on the
        same physical network as the originator."
    ::= { ipEventsGroup 44 }

ip44-source-ip-address OBJECT-TYPE
    SYNTAX IpAddress
    MAX-ACCESS accessible-for-notify
    STATUS current
    DESCRIPTION
        "Parameter 'source-ip-address' in event IP.44"
    ::= { ipEventObjects44 1 }

ip44-destination-ip-address OBJECT-TYPE
    SYNTAX IpAddress
    MAX-ACCESS accessible-for-notify
    STATUS current
    DESCRIPTION
        "Parameter 'destination-ip-address' in event IP.44"
    ::= { ipEventObjects44 2 }

ipEventObjects45 OBJECT-IDENTITY
    STATUS current
    DESCRIPTION
        "Event IP.45
        This message is generated when an ARP subnet request is answered."
    ::= { ipEventsGroup 45 }

ip45-source-ip-address OBJECT-TYPE
    SYNTAX IpAddress
    MAX-ACCESS accessible-for-notify
    STATUS current
    DESCRIPTION
        "Parameter 'source-ip-address' in event IP.45"
    ::= { ipEventObjects45 1 }

ip45-destination-ip-address OBJECT-TYPE
    SYNTAX IpAddress
    MAX-ACCESS accessible-for-notify
    STATUS current
    DESCRIPTION
        "Parameter 'destination-ip-address' in event IP.45"
    ::= { ipEventObjects45 2 }

ipEventObjects46 OBJECT-IDENTITY
    STATUS current
    DESCRIPTION
        "Event IP.46
        This message is generated when an unknown option is specified in the
        IP header of a packet."
    ::= { ipEventsGroup 46 }

ip46-option OBJECT-TYPE
    SYNTAX Integer32
    MAX-ACCESS accessible-for-notify
    STATUS current
    DESCRIPTION
        "Parameter 'option' in event IP.46"
    ::= { ipEventObjects46 1 }

ip46-source-ip-address OBJECT-TYPE
    SYNTAX IpAddress
    MAX-ACCESS accessible-for-notify
    STATUS current
    DESCRIPTION
        "Parameter 'source-ip-address' in event IP.46"
    ::= { ipEventObjects46 2 }

ipEventObjects47 OBJECT-IDENTITY
    STATUS current
    DESCRIPTION
        "Event IP.47
        This message is generated when an option is incorrectly formatted in
        the IP header."
    ::= { ipEventsGroup 47 }

ip47-option OBJECT-TYPE
    SYNTAX Integer32
    MAX-ACCESS accessible-for-notify
    STATUS current
    DESCRIPTION
        "Parameter 'option' in event IP.47"
    ::= { ipEventObjects47 1 }

ip47-source-ip-address OBJECT-TYPE
    SYNTAX IpAddress
    MAX-ACCESS accessible-for-notify
    STATUS current
    DESCRIPTION
        "Parameter 'source-ip-address' in event IP.47"
    ::= { ipEventObjects47 2 }

ipEventObjects48 OBJECT-IDENTITY
    STATUS current
    DESCRIPTION
        "Event IP.48
        This message is generated when the next hop specified in the strict
        source route is invalid."
    ::= { ipEventsGroup 48 }

ip48-source-ip-address OBJECT-TYPE
    SYNTAX IpAddress
    MAX-ACCESS accessible-for-notify
    STATUS current
    DESCRIPTION
        "Parameter 'source-ip-address' in event IP.48"
    ::= { ipEventObjects48 1 }

ip48-destination-ip-address OBJECT-TYPE
    SYNTAX IpAddress
    MAX-ACCESS accessible-for-notify
    STATUS current
    DESCRIPTION
        "Parameter 'destination-ip-address' in event IP.48"
    ::= { ipEventObjects48 2 }

ipEventObjects49 OBJECT-IDENTITY
    STATUS current
    DESCRIPTION
        "Event IP.49
        This message is generated when the format of the timestamp option
        is invalid."
    ::= { ipEventsGroup 49 }

ip49-timestamp OBJECT-TYPE
    SYNTAX Integer32
    MAX-ACCESS accessible-for-notify
    STATUS current
    DESCRIPTION
        "Parameter 'timestamp' in event IP.49"
    ::= { ipEventObjects49 1 }

ip49-source-ip-address OBJECT-TYPE
    SYNTAX IpAddress
    MAX-ACCESS accessible-for-notify
    STATUS current
    DESCRIPTION
        "Parameter 'source-ip-address' in event IP.49"
    ::= { ipEventObjects49 2 }

ipEventObjects50 OBJECT-IDENTITY
    STATUS current
    DESCRIPTION
        "Event IP.50
        This message is generated when the timestamp list is full and the
        new timestamp cannot be added."
    ::= { ipEventsGroup 50 }

ip50-source-ip-address OBJECT-TYPE
    SYNTAX IpAddress
    MAX-ACCESS accessible-for-notify
    STATUS current
    DESCRIPTION
        "Parameter 'source-ip-address' in event IP.50"
    ::= { ipEventObjects50 1 }

ip50-destination-ip-address OBJECT-TYPE
    SYNTAX IpAddress
    MAX-ACCESS accessible-for-notify
    STATUS current
    DESCRIPTION
        "Parameter 'destination-ip-address' in event IP.50"
    ::= { ipEventObjects50 2 }

ipEventObjects51 OBJECT-IDENTITY
    STATUS current
    DESCRIPTION
        "Event IP.51
        This message is generated when a new packet needs re-assembly but
        the maximum number of re-assembly buffers has already been assigned."
    ::= { ipEventsGroup 51 }

ip51-port-number OBJECT-TYPE
    SYNTAX Integer32
    MAX-ACCESS accessible-for-notify
    STATUS current
    DESCRIPTION
        "Parameter 'port-number' in event IP.51"
    ::= { ipEventObjects51 1 }

ip51-source-ip-address OBJECT-TYPE
    SYNTAX IpAddress
    MAX-ACCESS accessible-for-notify
    STATUS current
    DESCRIPTION
        "Parameter 'source-ip-address' in event IP.51"
    ::= { ipEventObjects51 2 }

ipEventObjects52 OBJECT-IDENTITY
    STATUS current
    DESCRIPTION
        "Event IP.52
        This message is generated when a new packet needs re-assembly but
        there is not enough storage to allocate a re-assembly buffer."
    ::= { ipEventsGroup 52 }

ip52-port-number OBJECT-TYPE
    SYNTAX Integer32
    MAX-ACCESS accessible-for-notify
    STATUS current
    DESCRIPTION
        "Parameter 'port-number' in event IP.52"
    ::= { ipEventObjects52 1 }

ip52-source-ip-address OBJECT-TYPE
    SYNTAX IpAddress
    MAX-ACCESS accessible-for-notify
    STATUS current
    DESCRIPTION
        "Parameter 'source-ip-address' in event IP.52"
    ::= { ipEventObjects52 2 }

ipEventObjects53 OBJECT-IDENTITY
    STATUS current
    DESCRIPTION
        "Event IP.53
        This message is generated when a new packet needs re-assembly but it is
        larger than the maximum size re-assembly buffer. The packet-size is
        how large the packet would be after adding this fragment, which
        may not be the last."
    ::= { ipEventsGroup 53 }

ip53-packet-size OBJECT-TYPE
    SYNTAX Integer32
    MAX-ACCESS accessible-for-notify
    STATUS current
    DESCRIPTION
        "Parameter 'packet-size' in event IP.53"
    ::= { ipEventObjects53 1 }

ip53-port-number OBJECT-TYPE
    SYNTAX Integer32
    MAX-ACCESS accessible-for-notify
    STATUS current
    DESCRIPTION
        "Parameter 'port-number' in event IP.53"
    ::= { ipEventObjects53 2 }

ip53-source-ip-address OBJECT-TYPE
    SYNTAX IpAddress
    MAX-ACCESS accessible-for-notify
    STATUS current
    DESCRIPTION
        "Parameter 'source-ip-address' in event IP.53"
    ::= { ipEventObjects53 3 }

ipEventObjects54 OBJECT-IDENTITY
    STATUS current
    DESCRIPTION
        "Event IP.54
        This message is generated when a packet being re-assembled has
        its time-to-live expire."
    ::= { ipEventsGroup 54 }

ip54-port-number OBJECT-TYPE
    SYNTAX Integer32
    MAX-ACCESS accessible-for-notify
    STATUS current
    DESCRIPTION
        "Parameter 'port-number' in event IP.54"
    ::= { ipEventObjects54 1 }

ip54-source-ip-address OBJECT-TYPE
    SYNTAX IpAddress
    MAX-ACCESS accessible-for-notify
    STATUS current
    DESCRIPTION
        "Parameter 'source-ip-address' in event IP.54"
    ::= { ipEventObjects54 2 }

ipEventObjects55 OBJECT-IDENTITY
    STATUS current
    DESCRIPTION
        "Event IP.55
        This message is generated when a re-assembly buffer is de-allocated."
    ::= { ipEventsGroup 55 }

ip55-port-number OBJECT-TYPE
    SYNTAX Integer32
    MAX-ACCESS accessible-for-notify
    STATUS current
    DESCRIPTION
        "Parameter 'port-number' in event IP.55"
    ::= { ipEventObjects55 1 }

ip55-source-ip-address OBJECT-TYPE
    SYNTAX IpAddress
    MAX-ACCESS accessible-for-notify
    STATUS current
    DESCRIPTION
        "Parameter 'source-ip-address' in event IP.55"
    ::= { ipEventObjects55 2 }

ipEventObjects56 OBJECT-IDENTITY
    STATUS current
    DESCRIPTION
        "Event IP.56
        This message is generated when an interface using a default gateway
        comes up."
    ::= { ipEventsGroup 56 }

ip56-ip-address OBJECT-TYPE
    SYNTAX IpAddress
    MAX-ACCESS accessible-for-notify
    STATUS current
    DESCRIPTION
        "Parameter 'ip-address' in event IP.56"
    ::= { ipEventObjects56 1 }

ip56-interface OBJECT-TYPE
    SYNTAX DisplayString
    MAX-ACCESS accessible-for-notify
    STATUS current
    DESCRIPTION
        "Parameter 'interface' in event IP.56"
    ::= { ipEventObjects56 2 }

ipEventObjects57 OBJECT-IDENTITY
    STATUS current
    DESCRIPTION
        "Event IP.57
        This message is generated when a default gateway is deleted."
    ::= { ipEventsGroup 57 }

ip57-ip-address OBJECT-TYPE
    SYNTAX IpAddress
    MAX-ACCESS accessible-for-notify
    STATUS current
    DESCRIPTION
        "Parameter 'ip-address' in event IP.57"
    ::= { ipEventObjects57 1 }

ipEventObjects58 OBJECT-IDENTITY
    STATUS current
    DESCRIPTION
        "Event IP.58
        This message is generated when a network goes down."
    ::= { ipEventsGroup 58 }

ip58-network OBJECT-TYPE
    SYNTAX IpAddress
    MAX-ACCESS accessible-for-notify
    STATUS current
    DESCRIPTION
        "Parameter 'network' in event IP.58"
    ::= { ipEventObjects58 1 }

ip58-gateway OBJECT-TYPE
    SYNTAX IpAddress
    MAX-ACCESS accessible-for-notify
    STATUS current
    DESCRIPTION
        "Parameter 'gateway' in event IP.58"
    ::= { ipEventObjects58 2 }

ip58-interface OBJECT-TYPE
    SYNTAX DisplayString
    MAX-ACCESS accessible-for-notify
    STATUS current
    DESCRIPTION
        "Parameter 'interface' in event IP.58"
    ::= { ipEventObjects58 3 }

ipEventObjects59 OBJECT-IDENTITY
    STATUS current
    DESCRIPTION
        "Event IP.59
        This message is generated when a new subnetted network is defined."
    ::= { ipEventsGroup 59 }

ip59-network OBJECT-TYPE
    SYNTAX IpAddress
    MAX-ACCESS accessible-for-notify
    STATUS current
    DESCRIPTION
        "Parameter 'network' in event IP.59"
    ::= { ipEventObjects59 1 }

ipEventObjects60 OBJECT-IDENTITY
    STATUS current
    DESCRIPTION
        "Event IP.60
        This message is generated when a subnetted network is deleted.
        This happens when there are no longer any interfaces to that network."
    ::= { ipEventsGroup 60 }

ip60-network OBJECT-TYPE
    SYNTAX IpAddress
    MAX-ACCESS accessible-for-notify
    STATUS current
    DESCRIPTION
        "Parameter 'network' in event IP.60"
    ::= { ipEventObjects60 1 }

ipEventObjects62 OBJECT-IDENTITY
    STATUS current
    DESCRIPTION
        "Event IP.62
        This message is generated when an IP fragment, requiring re-assembly
        is received."
    ::= { ipEventsGroup 62 }

ip62-source-ip-address OBJECT-TYPE
    SYNTAX IpAddress
    MAX-ACCESS accessible-for-notify
    STATUS current
    DESCRIPTION
        "Parameter 'source-ip-address' in event IP.62"
    ::= { ipEventObjects62 1 }

ipEventObjects63 OBJECT-IDENTITY
    STATUS current
    DESCRIPTION
        "Event IP.63
        This message is generated when an IP packet has been successfully
        re-assembled."
    ::= { ipEventsGroup 63 }

ip63-source-ip-address OBJECT-TYPE
    SYNTAX IpAddress
    MAX-ACCESS accessible-for-notify
    STATUS current
    DESCRIPTION
        "Parameter 'source-ip-address' in event IP.63"
    ::= { ipEventObjects63 1 }

ipEventObjects64 OBJECT-IDENTITY
    STATUS current
    DESCRIPTION
        "Event IP.64
        This message is generated when an IP packet needs to be fragmented
        for transmission."
    ::= { ipEventsGroup 64 }

ip64-source-ip-address OBJECT-TYPE
    SYNTAX IpAddress
    MAX-ACCESS accessible-for-notify
    STATUS current
    DESCRIPTION
        "Parameter 'source-ip-address' in event IP.64"
    ::= { ipEventObjects64 1 }

ip64-destination-ip-address OBJECT-TYPE
    SYNTAX IpAddress
    MAX-ACCESS accessible-for-notify
    STATUS current
    DESCRIPTION
        "Parameter 'destination-ip-address' in event IP.64"
    ::= { ipEventObjects64 2 }

ipEventObjects65 OBJECT-IDENTITY
    STATUS current
    DESCRIPTION
        "Event IP.65
        This message is generated when an IP packet fragment is put on
        the output fragment queue."
    ::= { ipEventsGroup 65 }

ip65-source-ip-address OBJECT-TYPE
    SYNTAX IpAddress
    MAX-ACCESS accessible-for-notify
    STATUS current
    DESCRIPTION
        "Parameter 'source-ip-address' in event IP.65"
    ::= { ipEventObjects65 1 }

ip65-destination-ip-address OBJECT-TYPE
    SYNTAX IpAddress
    MAX-ACCESS accessible-for-notify
    STATUS current
    DESCRIPTION
        "Parameter 'destination-ip-address' in event IP.65"
    ::= { ipEventObjects65 2 }

ipEventObjects66 OBJECT-IDENTITY
    STATUS current
    DESCRIPTION
        "Event IP.66
        This message is generated by the stub IP forwarder for each packet
        which is received on an interface for which IP is not enabled."
    ::= { ipEventsGroup 66 }

ip66-source-ip-address OBJECT-TYPE
    SYNTAX IpAddress
    MAX-ACCESS accessible-for-notify
    STATUS current
    DESCRIPTION
        "Parameter 'source-ip-address' in event IP.66"
    ::= { ipEventObjects66 1 }

ip66-destination-ip-address OBJECT-TYPE
    SYNTAX IpAddress
    MAX-ACCESS accessible-for-notify
    STATUS current
    DESCRIPTION
        "Parameter 'destination-ip-address' in event IP.66"
    ::= { ipEventObjects66 2 }

ip66-interface OBJECT-TYPE
    SYNTAX DisplayString
    MAX-ACCESS accessible-for-notify
    STATUS current
    DESCRIPTION
        "Parameter 'interface' in event IP.66"
    ::= { ipEventObjects66 3 }

ipEventObjects67 OBJECT-IDENTITY
    STATUS current
    DESCRIPTION
        "Event IP.67
        The router is configured with variable length subnet masks on the
        same network, which RIP can't handle. Thus RIP1 is disabled on
        the interface."
    ::= { ipEventsGroup 67 }

ip67-interface-ip-address OBJECT-TYPE
    SYNTAX IpAddress
    MAX-ACCESS accessible-for-notify
    STATUS current
    DESCRIPTION
        "Parameter 'interface-ip-address' in event IP.67"
    ::= { ipEventObjects67 1 }

ipEventObjects70 OBJECT-IDENTITY
    STATUS current
    DESCRIPTION
        "Event IP.70
        The IP routing cache entry for the listed destination has been cleared."
    ::= { ipEventsGroup 70 }

ip70-ip-destination OBJECT-TYPE
    SYNTAX IpAddress
    MAX-ACCESS accessible-for-notify
    STATUS current
    DESCRIPTION
        "Parameter 'ip-destination' in event IP.70"
    ::= { ipEventObjects70 1 }

ipEventObjects72 OBJECT-IDENTITY
    STATUS current
    DESCRIPTION
        "Event IP.72
        This message is generated when an attempt is made to forward an
        IP packet that was received as a link level broadcast/multicast.
        Such packets are not forwarded, and are discarded without even
        sending back an ICMP message to the source."
    ::= { ipEventsGroup 72 }

ip72-source-ip-address OBJECT-TYPE
    SYNTAX IpAddress
    MAX-ACCESS accessible-for-notify
    STATUS current
    DESCRIPTION
        "Parameter 'source-ip-address' in event IP.72"
    ::= { ipEventObjects72 1 }

ip72-destination-ip-address OBJECT-TYPE
    SYNTAX IpAddress
    MAX-ACCESS accessible-for-notify
    STATUS current
    DESCRIPTION
        "Parameter 'destination-ip-address' in event IP.72"
    ::= { ipEventObjects72 2 }

ipEventObjects73 OBJECT-IDENTITY
    STATUS current
    DESCRIPTION
        "Event IP.73
        This message is generated when an attempt is made to copy a packet for
        one of the router's internal applications (e.g., during multicast
        forwarding), and the router is unable to get a buffer. The requested
        service then fails."
    ::= { ipEventsGroup 73 }

ip73-source-ip-address OBJECT-TYPE
    SYNTAX IpAddress
    MAX-ACCESS accessible-for-notify
    STATUS current
    DESCRIPTION
        "Parameter 'source-ip-address' in event IP.73"
    ::= { ipEventObjects73 1 }

ip73-destination-ip-address OBJECT-TYPE
    SYNTAX IpAddress
    MAX-ACCESS accessible-for-notify
    STATUS current
    DESCRIPTION
        "Parameter 'destination-ip-address' in event IP.73"
    ::= { ipEventObjects73 2 }

ipEventObjects74 OBJECT-IDENTITY
    STATUS current
    DESCRIPTION
        "Event IP.74
        The MSS value of a TCP SYN packet has been adjusted."
    ::= { ipEventsGroup 74 }

ip74-source-ip OBJECT-TYPE
    SYNTAX IpAddress
    MAX-ACCESS accessible-for-notify
    STATUS current
    DESCRIPTION
        "Parameter 'source-ip' in event IP.74"
    ::= { ipEventObjects74 1 }

ip74-source-port OBJECT-TYPE
    SYNTAX Integer32
    MAX-ACCESS accessible-for-notify
    STATUS current
    DESCRIPTION
        "Parameter 'source-port' in event IP.74"
    ::= { ipEventObjects74 2 }

ip74-destination-ip OBJECT-TYPE
    SYNTAX IpAddress
    MAX-ACCESS accessible-for-notify
    STATUS current
    DESCRIPTION
        "Parameter 'destination-ip' in event IP.74"
    ::= { ipEventObjects74 3 }

ip74-destination-port OBJECT-TYPE
    SYNTAX Integer32
    MAX-ACCESS accessible-for-notify
    STATUS current
    DESCRIPTION
        "Parameter 'destination-port' in event IP.74"
    ::= { ipEventObjects74 4 }

ip74-old-mss OBJECT-TYPE
    SYNTAX Integer32
    MAX-ACCESS accessible-for-notify
    STATUS current
    DESCRIPTION
        "Parameter 'old-mss' in event IP.74"
    ::= { ipEventObjects74 5 }

ip74-new-mss OBJECT-TYPE
    SYNTAX Integer32
    MAX-ACCESS accessible-for-notify
    STATUS current
    DESCRIPTION
        "Parameter 'new-mss' in event IP.74"
    ::= { ipEventObjects74 6 }

ip74-interface OBJECT-TYPE
    SYNTAX DisplayString
    MAX-ACCESS accessible-for-notify
    STATUS current
    DESCRIPTION
        "Parameter 'interface' in event IP.74"
    ::= { ipEventObjects74 7 }

ipEventObjects78 OBJECT-IDENTITY
    STATUS current
    DESCRIPTION
        "Event IP.78
        This message is generated when a IP packet matches none of the
        access control records. The packet will be dropped."
    ::= { ipEventsGroup 78 }

ip78-source-ip-address OBJECT-TYPE
    SYNTAX IpAddress
    MAX-ACCESS accessible-for-notify
    STATUS current
    DESCRIPTION
        "Parameter 'source-ip-address' in event IP.78"
    ::= { ipEventObjects78 1 }

ip78-destination-ip-address OBJECT-TYPE
    SYNTAX IpAddress
    MAX-ACCESS accessible-for-notify
    STATUS current
    DESCRIPTION
        "Parameter 'destination-ip-address' in event IP.78"
    ::= { ipEventObjects78 2 }

ip78-protocol OBJECT-TYPE
    SYNTAX Integer32
    MAX-ACCESS accessible-for-notify
    STATUS current
    DESCRIPTION
        "Parameter 'protocol' in event IP.78"
    ::= { ipEventObjects78 3 }

ipEventObjects79 OBJECT-IDENTITY
    STATUS current
    DESCRIPTION
        "Event IP.79
        This message is generated when a IP packet matches none of the
        access control records. The packet will be dropped."
    ::= { ipEventsGroup 79 }

ip79-source-ip-address OBJECT-TYPE
    SYNTAX IpAddress
    MAX-ACCESS accessible-for-notify
    STATUS current
    DESCRIPTION
        "Parameter 'source-ip-address' in event IP.79"
    ::= { ipEventObjects79 1 }

ip79-destination-ip-address OBJECT-TYPE
    SYNTAX IpAddress
    MAX-ACCESS accessible-for-notify
    STATUS current
    DESCRIPTION
        "Parameter 'destination-ip-address' in event IP.79"
    ::= { ipEventObjects79 2 }

ip79-protocol OBJECT-TYPE
    SYNTAX DisplayString
    MAX-ACCESS accessible-for-notify
    STATUS current
    DESCRIPTION
        "Parameter 'protocol' in event IP.79"
    ::= { ipEventObjects79 3 }

ip79-source-port OBJECT-TYPE
    SYNTAX Integer32
    MAX-ACCESS accessible-for-notify
    STATUS current
    DESCRIPTION
        "Parameter 'source-port' in event IP.79"
    ::= { ipEventObjects79 4 }

ip79-destination-port OBJECT-TYPE
    SYNTAX Integer32
    MAX-ACCESS accessible-for-notify
    STATUS current
    DESCRIPTION
        "Parameter 'destination-port' in event IP.79"
    ::= { ipEventObjects79 5 }

ipEventObjects80 OBJECT-IDENTITY
    STATUS current
    DESCRIPTION
        "Event IP.80
        A new router has been discovered, either through static configuration,
        an ICMP redirect, RIP or ICMP router discovery. This message is
        produced only when running as an IP host (i.e., when IP routing
        disabled)."
    ::= { ipEventsGroup 80 }

ip80-router-address OBJECT-TYPE
    SYNTAX IpAddress
    MAX-ACCESS accessible-for-notify
    STATUS current
    DESCRIPTION
        "Parameter 'router-address' in event IP.80"
    ::= { ipEventObjects80 1 }

ipEventObjects81 OBJECT-IDENTITY
    STATUS current
    DESCRIPTION
        "Event IP.81
        An IP address was configured for a type of network which currently
        doesn't support IP."
    ::= { ipEventsGroup 81 }

ip81-interface OBJECT-TYPE
    SYNTAX DisplayString
    MAX-ACCESS accessible-for-notify
    STATUS current
    DESCRIPTION
        "Parameter 'interface' in event IP.81"
    ::= { ipEventObjects81 1 }

ipEventObjects82 OBJECT-IDENTITY
    STATUS current
    DESCRIPTION
        "Event IP.82
        This message is generated when a packet's indicated length is below
        the minimum possible length. The packet is discarded."
    ::= { ipEventsGroup 82 }

ip82-packet-length OBJECT-TYPE
    SYNTAX Integer32
    MAX-ACCESS accessible-for-notify
    STATUS current
    DESCRIPTION
        "Parameter 'packet-length' in event IP.82"
    ::= { ipEventObjects82 1 }

ip82-source-ip-address OBJECT-TYPE
    SYNTAX IpAddress
    MAX-ACCESS accessible-for-notify
    STATUS current
    DESCRIPTION
        "Parameter 'source-ip-address' in event IP.82"
    ::= { ipEventObjects82 2 }

ip82-destination-ip-address OBJECT-TYPE
    SYNTAX IpAddress
    MAX-ACCESS accessible-for-notify
    STATUS current
    DESCRIPTION
        "Parameter 'destination-ip-address' in event IP.82"
    ::= { ipEventObjects82 3 }

ipEventObjects83 OBJECT-IDENTITY
    STATUS current
    DESCRIPTION
        "Event IP.83
        This message is generated when a IP packet matches one of the exclusive
        access control entries. The packet will be dropped.
        The record-number is the number of the access control record matched,
        or zero for no record (end-of-list). The cache-status will be
        ''cache-hit'' or ''cache-miss''."
    ::= { ipEventsGroup 83 }

ip83-record-number OBJECT-TYPE
    SYNTAX Integer32
    MAX-ACCESS accessible-for-notify
    STATUS current
    DESCRIPTION
        "Parameter 'record-number' in event IP.83"
    ::= { ipEventObjects83 1 }

ip83-cache-status OBJECT-TYPE
    SYNTAX DisplayString
    MAX-ACCESS accessible-for-notify
    STATUS current
    DESCRIPTION
        "Parameter 'cache-status' in event IP.83"
    ::= { ipEventObjects83 2 }

ip83-source-ip-address OBJECT-TYPE
    SYNTAX IpAddress
    MAX-ACCESS accessible-for-notify
    STATUS current
    DESCRIPTION
        "Parameter 'source-ip-address' in event IP.83"
    ::= { ipEventObjects83 3 }

ip83-destination-ip-address OBJECT-TYPE
    SYNTAX IpAddress
    MAX-ACCESS accessible-for-notify
    STATUS current
    DESCRIPTION
        "Parameter 'destination-ip-address' in event IP.83"
    ::= { ipEventObjects83 4 }

ip83-protcol-number OBJECT-TYPE
    SYNTAX Integer32
    MAX-ACCESS accessible-for-notify
    STATUS current
    DESCRIPTION
        "Parameter 'protcol-number' in event IP.83"
    ::= { ipEventObjects83 5 }

ipEventObjects84 OBJECT-IDENTITY
    STATUS current
    DESCRIPTION
        "Event IP.84
        This message is generated when a IP packet matches one of the inclusive
        access control entries. The packet may be forwarded.
        The record-number is the number of the access control record matched.
        The cache-status will be ''cache-hit'' or ''cache-miss''."
    ::= { ipEventsGroup 84 }

ip84-record-number OBJECT-TYPE
    SYNTAX Integer32
    MAX-ACCESS accessible-for-notify
    STATUS current
    DESCRIPTION
        "Parameter 'record-number' in event IP.84"
    ::= { ipEventObjects84 1 }

ip84-cache-status OBJECT-TYPE
    SYNTAX DisplayString
    MAX-ACCESS accessible-for-notify
    STATUS current
    DESCRIPTION
        "Parameter 'cache-status' in event IP.84"
    ::= { ipEventObjects84 2 }

ip84-source-ip-address OBJECT-TYPE
    SYNTAX IpAddress
    MAX-ACCESS accessible-for-notify
    STATUS current
    DESCRIPTION
        "Parameter 'source-ip-address' in event IP.84"
    ::= { ipEventObjects84 3 }

ip84-destination-ip-address OBJECT-TYPE
    SYNTAX IpAddress
    MAX-ACCESS accessible-for-notify
    STATUS current
    DESCRIPTION
        "Parameter 'destination-ip-address' in event IP.84"
    ::= { ipEventObjects84 4 }

ip84-protcol-number OBJECT-TYPE
    SYNTAX Integer32
    MAX-ACCESS accessible-for-notify
    STATUS current
    DESCRIPTION
        "Parameter 'protcol-number' in event IP.84"
    ::= { ipEventObjects84 5 }

ipEventObjects85 OBJECT-IDENTITY
    STATUS current
    DESCRIPTION
        "Event IP.85
        This message is generated when a IP packet matches one of the TCP or UDP
        exclusive access control entries. The packet will be dropped.
        The record-number is the number of the access control record matched,
        or zero for no record (end-of-list). The cache-status will be
        ''cache-hit'' or ''cache-miss''."
    ::= { ipEventsGroup 85 }

ip85-record-number OBJECT-TYPE
    SYNTAX Integer32
    MAX-ACCESS accessible-for-notify
    STATUS current
    DESCRIPTION
        "Parameter 'record-number' in event IP.85"
    ::= { ipEventObjects85 1 }

ip85-cache-status OBJECT-TYPE
    SYNTAX DisplayString
    MAX-ACCESS accessible-for-notify
    STATUS current
    DESCRIPTION
        "Parameter 'cache-status' in event IP.85"
    ::= { ipEventObjects85 2 }

ip85-source-ip-address OBJECT-TYPE
    SYNTAX IpAddress
    MAX-ACCESS accessible-for-notify
    STATUS current
    DESCRIPTION
        "Parameter 'source-ip-address' in event IP.85"
    ::= { ipEventObjects85 3 }

ip85-destination-ip-address OBJECT-TYPE
    SYNTAX IpAddress
    MAX-ACCESS accessible-for-notify
    STATUS current
    DESCRIPTION
        "Parameter 'destination-ip-address' in event IP.85"
    ::= { ipEventObjects85 4 }

ip85-protocol OBJECT-TYPE
    SYNTAX DisplayString
    MAX-ACCESS accessible-for-notify
    STATUS current
    DESCRIPTION
        "Parameter 'protocol' in event IP.85"
    ::= { ipEventObjects85 5 }

ip85-source-port OBJECT-TYPE
    SYNTAX Integer32
    MAX-ACCESS accessible-for-notify
    STATUS current
    DESCRIPTION
        "Parameter 'source-port' in event IP.85"
    ::= { ipEventObjects85 6 }

ip85-destination-port OBJECT-TYPE
    SYNTAX Integer32
    MAX-ACCESS accessible-for-notify
    STATUS current
    DESCRIPTION
        "Parameter 'destination-port' in event IP.85"
    ::= { ipEventObjects85 7 }

ipEventObjects86 OBJECT-IDENTITY
    STATUS current
    DESCRIPTION
        "Event IP.86
        This message is generated when a IP packet matches one of the TCP or UDP
        inclusive access control entries. The packet may be forwarded.
        The record-number is the number of the access control record matched.
        The cache-status will be ''cache-hit'' or ''cache-miss''."
    ::= { ipEventsGroup 86 }

ip86-record-number OBJECT-TYPE
    SYNTAX Integer32
    MAX-ACCESS accessible-for-notify
    STATUS current
    DESCRIPTION
        "Parameter 'record-number' in event IP.86"
    ::= { ipEventObjects86 1 }

ip86-cache-status OBJECT-TYPE
    SYNTAX DisplayString
    MAX-ACCESS accessible-for-notify
    STATUS current
    DESCRIPTION
        "Parameter 'cache-status' in event IP.86"
    ::= { ipEventObjects86 2 }

ip86-source-ip-address OBJECT-TYPE
    SYNTAX IpAddress
    MAX-ACCESS accessible-for-notify
    STATUS current
    DESCRIPTION
        "Parameter 'source-ip-address' in event IP.86"
    ::= { ipEventObjects86 3 }

ip86-destination-ip-address OBJECT-TYPE
    SYNTAX IpAddress
    MAX-ACCESS accessible-for-notify
    STATUS current
    DESCRIPTION
        "Parameter 'destination-ip-address' in event IP.86"
    ::= { ipEventObjects86 4 }

ip86-protocol OBJECT-TYPE
    SYNTAX DisplayString
    MAX-ACCESS accessible-for-notify
    STATUS current
    DESCRIPTION
        "Parameter 'protocol' in event IP.86"
    ::= { ipEventObjects86 5 }

ip86-source-port OBJECT-TYPE
    SYNTAX Integer32
    MAX-ACCESS accessible-for-notify
    STATUS current
    DESCRIPTION
        "Parameter 'source-port' in event IP.86"
    ::= { ipEventObjects86 6 }

ip86-destination-port OBJECT-TYPE
    SYNTAX Integer32
    MAX-ACCESS accessible-for-notify
    STATUS current
    DESCRIPTION
        "Parameter 'destination-port' in event IP.86"
    ::= { ipEventObjects86 7 }

ipEventObjects87 OBJECT-IDENTITY
    STATUS current
    DESCRIPTION
        "Event IP.87
        Message is generated when a IP packet does not match the access-group
        per-interface access control list."
    ::= { ipEventsGroup 87 }

ip87-interface OBJECT-TYPE
    SYNTAX DisplayString
    MAX-ACCESS accessible-for-notify
    STATUS current
    DESCRIPTION
        "Parameter 'interface' in event IP.87"
    ::= { ipEventObjects87 1 }

ip87-access-list OBJECT-TYPE
    SYNTAX Integer32
    MAX-ACCESS accessible-for-notify
    STATUS current
    DESCRIPTION
        "Parameter 'access-list' in event IP.87"
    ::= { ipEventObjects87 2 }

ip87-direction OBJECT-TYPE
    SYNTAX DisplayString
    MAX-ACCESS accessible-for-notify
    STATUS current
    DESCRIPTION
        "Parameter 'direction' in event IP.87"
    ::= { ipEventObjects87 3 }

ipEventObjects88 OBJECT-IDENTITY
    STATUS current
    DESCRIPTION
        "Event IP.88
        Message is generated when a IP packet does not verify the unicast
        reverse route criteria."
    ::= { ipEventsGroup 88 }

ip88-interface OBJECT-TYPE
    SYNTAX DisplayString
    MAX-ACCESS accessible-for-notify
    STATUS current
    DESCRIPTION
        "Parameter 'interface' in event IP.88"
    ::= { ipEventObjects88 1 }

ip88-source-ip OBJECT-TYPE
    SYNTAX IpAddress
    MAX-ACCESS accessible-for-notify
    STATUS current
    DESCRIPTION
        "Parameter 'source-ip' in event IP.88"
    ::= { ipEventObjects88 2 }

ip88-destination-ip OBJECT-TYPE
    SYNTAX IpAddress
    MAX-ACCESS accessible-for-notify
    STATUS current
    DESCRIPTION
        "Parameter 'destination-ip' in event IP.88"
    ::= { ipEventObjects88 3 }

ipEventObjects89 OBJECT-IDENTITY
    STATUS current
    DESCRIPTION
        "Event IP.89
        Found a static route configured whose next-hop is given for the DHCP
        parameters received on that interface."
    ::= { ipEventsGroup 89 }

ip89-destination OBJECT-TYPE
    SYNTAX IpAddress
    MAX-ACCESS accessible-for-notify
    STATUS current
    DESCRIPTION
        "Parameter 'destination' in event IP.89"
    ::= { ipEventObjects89 1 }

ip89-mask OBJECT-TYPE
    SYNTAX IpAddress
    MAX-ACCESS accessible-for-notify
    STATUS current
    DESCRIPTION
        "Parameter 'mask' in event IP.89"
    ::= { ipEventObjects89 2 }

ip89-interface OBJECT-TYPE
    SYNTAX DisplayString
    MAX-ACCESS accessible-for-notify
    STATUS current
    DESCRIPTION
        "Parameter 'interface' in event IP.89"
    ::= { ipEventObjects89 3 }

ipEventObjects90 OBJECT-IDENTITY
    STATUS current
    DESCRIPTION
        "Event IP.90
        Deleting a static route configured whose next-hop was given for the DHCP
        parameters received on that interface."
    ::= { ipEventsGroup 90 }

ip90-destination OBJECT-TYPE
    SYNTAX IpAddress
    MAX-ACCESS accessible-for-notify
    STATUS current
    DESCRIPTION
        "Parameter 'destination' in event IP.90"
    ::= { ipEventObjects90 1 }

ip90-mask OBJECT-TYPE
    SYNTAX IpAddress
    MAX-ACCESS accessible-for-notify
    STATUS current
    DESCRIPTION
        "Parameter 'mask' in event IP.90"
    ::= { ipEventObjects90 2 }

ip90-interface OBJECT-TYPE
    SYNTAX DisplayString
    MAX-ACCESS accessible-for-notify
    STATUS current
    DESCRIPTION
        "Parameter 'interface' in event IP.90"
    ::= { ipEventObjects90 3 }


ipNotification1 NOTIFICATION-TYPE
    OBJECTS { 
              ip1-source-ip-address, 
              ip1-destination-ip-address,
              ip1-interface 
            }
    STATUS current
    DESCRIPTION
        "Notification of Event IP.1

        Message: 'Queue overflow on packet from $1 for $2 from interface $3'

        Parameters list:
              $1: ip1-source-ip-address
              $2: ip1-destination-ip-address
              $3: ip1-interface

        This message is generated when the forwarder must discard a packet that
        was not forwarded via the IP cache because of an input queue overflow.
        Note that this event does not get counted in ELS, it is instead counted
        in the IP console.
        The counters (kept per input interface) can be read using the
        IP>COUNTERS command."
    ::= { ipNotificationsPrefix 1 }

ipNotification2 NOTIFICATION-TYPE
    OBJECTS { 
              ip2-version-number, 
              ip2-interface 
            }
    STATUS current
    DESCRIPTION
        "Notification of Event IP.2

        Message: 'Not version 4 header ($1) in packet from interface $2'

        Parameters list:
              $1: ip2-version-number
              $2: ip2-interface

        This message is generated when a packet has an incorrect version number."
    ::= { ipNotificationsPrefix 2 }

ipNotification3 NOTIFICATION-TYPE
    OBJECTS { 
              ip3-header-length, 
              ip3-packet-length,
              ip3-interface 
            }
    STATUS current
    DESCRIPTION
        "Notification of Event IP.3

        Message: 'Header too short ($1 bytes) in $2 byte packet from interface $3'

        Parameters list:
              $1: ip3-header-length
              $2: ip3-packet-length
              $3: ip3-interface

        This message is generated when a packet's indicated header length is
        below the minimum possible length."
    ::= { ipNotificationsPrefix 3 }

ipNotification4 NOTIFICATION-TYPE
    OBJECTS { 
              ip4-checksum, 
              ip4-expected-checksum,
              ip4-source-ip-address,
              ip4-destination-ip-address 
            }
    STATUS current
    DESCRIPTION
        "Notification of Event IP.4

        Message: 'Bad header checksum 0x$1 (expected 0x$2) in packet from $3 for $4'

        Parameters list:
              $1: ip4-checksum
              $2: ip4-expected-checksum
              $3: ip4-source-ip-address
              $4: ip4-destination-ip-address

        This message is generated when a packet has an invalid checksum.
        The received checksum, together with the correct checksum,
        are displayed."
    ::= { ipNotificationsPrefix 4 }

ipNotification5 NOTIFICATION-TYPE
    OBJECTS { 
              ip5-specified-length, 
              ip5-true-length,
              ip5-source-ip-address,
              ip5-destination-ip-address 
            }
    STATUS current
    DESCRIPTION
        "Notification of Event IP.5

        Message: 'Packet truncated from $1 to $2 bytes from $3 for $4'

        Parameters list:
              $1: ip5-specified-length
              $2: ip5-true-length
              $3: ip5-source-ip-address
              $4: ip5-destination-ip-address

        This message is generated when the packet length specified in the header
        is greater than the packet buffer length."
    ::= { ipNotificationsPrefix 5 }

ipNotification6 NOTIFICATION-TYPE
    OBJECTS { 
              ip6-source-ip-address, 
              ip6-destination-ip-address,
              ip6-reason-code,
              ip6-interface 
            }
    STATUS current
    DESCRIPTION
        "Notification of Event IP.6

        Message: 'Packet from $1 for $2 discarded for reason $3, interface $4'

        Parameters list:
              $1: ip6-source-ip-address
              $2: ip6-destination-ip-address
              $3: ip6-reason-code
              $4: ip6-interface

        An attempt was made to send the packet on the specified interface, but
        it was not accepted for transmission on that network. The reason-code
        indicates why the packet was not accepted. If the reason was
        flow-control, an ICMP source quench will be sent to the sender,
        otherwise an ICMP destination unreachable will be sent."
    ::= { ipNotificationsPrefix 6 }

ipNotification7 NOTIFICATION-TYPE
    OBJECTS { 
              ip7-source-ip-address, 
              ip7-destination-ip-address 
            }
    STATUS current
    DESCRIPTION
        "Notification of Event IP.7

        Message: 'Accepting packet from $1 for $2'

        Parameters list:
              $1: ip7-source-ip-address
              $2: ip7-destination-ip-address

        This message is generated for each packet which has passed first-level
        reasonableness checks."
    ::= { ipNotificationsPrefix 7 }

ipNotification8 NOTIFICATION-TYPE
    OBJECTS { 
              ip8-source-ip-address, 
              ip8-destination-ip-address 
            }
    STATUS current
    DESCRIPTION
        "Notification of Event IP.8

        Message: 'No route for packet from $1 for $2; packet discarded'

        Parameters list:
              $1: ip8-source-ip-address
              $2: ip8-destination-ip-address

        This message is generated when a packet is discarded because there is
        no route to the destination."
    ::= { ipNotificationsPrefix 8 }

ipNotification9 NOTIFICATION-TYPE
    OBJECTS { 
              ip9-source-ip-address, 
              ip9-destination-ip-address 
            }
    STATUS current
    DESCRIPTION
        "Notification of Event IP.9

        Message: 'Time-to-live expired on packet from $1 for $2'

        Parameters list:
              $1: ip9-source-ip-address
              $2: ip9-destination-ip-address

        This message is generated when a packet is discarded because
        the time-to-live expired."
    ::= { ipNotificationsPrefix 9 }

ipNotification10 NOTIFICATION-TYPE
    OBJECTS { 
              ip10-source-ip-address, 
              ip10-destination-ip-address,
              ip10-interface 
            }
    STATUS current
    DESCRIPTION
        "Notification of Event IP.10

        Message: 'Discarded packet from $1 for $2 interface $3, no IP forwarder'

        Parameters list:
              $1: ip10-source-ip-address
              $2: ip10-destination-ip-address
              $3: ip10-interface

        This message is generated by the fake IP forwarder for each packet
        which is received."
    ::= { ipNotificationsPrefix 10 }

ipNotification11 NOTIFICATION-TYPE
    OBJECTS { 
              ip11-source-ip-address, 
              ip11-destination-ip-address 
            }
    STATUS current
    DESCRIPTION
        "Notification of Event IP.11

        Message: 'Unsupported multicast from $1 for $2'

        Parameters list:
              $1: ip11-source-ip-address
              $2: ip11-destination-ip-address

        This message is generated when an unsupported multicast packet
        is received."
    ::= { ipNotificationsPrefix 11 }

ipNotification12 NOTIFICATION-TYPE
    OBJECTS { 
              ip12-source-ip-address, 
              ip12-destination-ip-address 
            }
    STATUS current
    DESCRIPTION
        "Notification of Event IP.12

        Message: 'Bad network class from $1 for $2'

        Parameters list:
              $1: ip12-source-ip-address
              $2: ip12-destination-ip-address

        This message is generated when a packet is destined for a network
        which is not class A, B, C or D."
    ::= { ipNotificationsPrefix 12 }

ipNotification13 NOTIFICATION-TYPE
    OBJECTS { 
              ip13-source-ip-address, 
              ip13-destination-ip-address 
            }
    STATUS current
    DESCRIPTION
        "Notification of Event IP.13

        Message: 'Unsupported broadcast from $1 for $2'

        Parameters list:
              $1: ip13-source-ip-address
              $2: ip13-destination-ip-address

        This message is generated when an unsupported broadcast packet
        is received."
    ::= { ipNotificationsPrefix 13 }

ipNotification14 NOTIFICATION-TYPE
    STATUS current
    DESCRIPTION
        "Notification of Event IP.14

        Message: '---'

        Reserved for possible future use."
    ::= { ipNotificationsPrefix 14 }

ipNotification15 NOTIFICATION-TYPE
    STATUS current
    DESCRIPTION
        "Notification of Event IP.15

        Message: '---'

        Reserved for possible future use."
    ::= { ipNotificationsPrefix 15 }

ipNotification16 NOTIFICATION-TYPE
    STATUS current
    DESCRIPTION
        "Notification of Event IP.16

        Message: '---'

        Reserved for possible future use."
    ::= { ipNotificationsPrefix 16 }

ipNotification17 NOTIFICATION-TYPE
    OBJECTS { 
              ip17-network-address 
            }
    STATUS current
    DESCRIPTION
        "Notification of Event IP.17

        Message: 'Add failed for net $1; routing table overflow'

        Parameters list:
              $1: ip17-network-address

        This message is generated when a network cannot be added to the
        routing table because the table is full."
    ::= { ipNotificationsPrefix 17 }

ipNotification18 NOTIFICATION-TYPE
    OBJECTS { 
              ip18-network-address 
            }
    STATUS current
    DESCRIPTION
        "Notification of Event IP.18

        Message: 'Add failed for net $1; bad network number'

        Parameters list:
              $1: ip18-network-address

        This message is generated when a network cannot be added to the
        routing table because of a bad network number."
    ::= { ipNotificationsPrefix 18 }

ipNotification19 NOTIFICATION-TYPE
    OBJECTS { 
              ip19-network 
            }
    STATUS current
    DESCRIPTION
        "Notification of Event IP.19

        Message: 'Re-adding static route to net $1'

        Parameters list:
              $1: ip19-network

        This message is generated when a static route to a network is brought
        back into use."
    ::= { ipNotificationsPrefix 19 }

ipNotification20 NOTIFICATION-TYPE
    OBJECTS { 
              ip20-network 
            }
    STATUS current
    DESCRIPTION
        "Notification of Event IP.20

        Message: 'Add of interface for net $1 failed; duplicate address'

        Parameters list:
              $1: ip20-network

        This message is generated when a network cannot be added to the
        routing table because the access was denied."
    ::= { ipNotificationsPrefix 20 }

ipNotification21 NOTIFICATION-TYPE
    OBJECTS { 
              ip21-network, 
              ip21-mask,
              ip21-interface 
            }
    STATUS current
    DESCRIPTION
        "Notification of Event IP.21

        Message: 'Added route to $1/$2 via interface $3'

        Parameters list:
              $1: ip21-network
              $2: ip21-mask
              $3: ip21-interface

        This message is generated when a new route is added to the routing
        table. This is a directly connected network."
    ::= { ipNotificationsPrefix 21 }

ipNotification22 NOTIFICATION-TYPE
    OBJECTS { 
              ip22-local-ip-network, 
              ip22-local-ip-mask,
              ip22-interface 
            }
    STATUS current
    DESCRIPTION
        "Notification of Event IP.22

        Message: 'Added local network $1/$2 to interface $3'

        Parameters list:
              $1: ip22-local-ip-network
              $2: ip22-local-ip-mask
              $3: ip22-interface

        This message is generated when a new local network is added to the
        routing table."
    ::= { ipNotificationsPrefix 22 }

ipNotification23 NOTIFICATION-TYPE
    OBJECTS { 
              ip23-network, 
              ip23-mask,
              ip23-gateway,
              ip23-interface 
            }
    STATUS current
    DESCRIPTION
        "Notification of Event IP.23

        Message: 'Added route to $1/$2 via $3 on interface $4'

        Parameters list:
              $1: ip23-network
              $2: ip23-mask
              $3: ip23-gateway
              $4: ip23-interface

        This message is generated when a new route is added to the routing
        table. The gateway is directly connected."
    ::= { ipNotificationsPrefix 23 }

ipNotification24 NOTIFICATION-TYPE
    OBJECTS { 
              ip24-network, 
              ip24-mask 
            }
    STATUS current
    DESCRIPTION
        "Notification of Event IP.24

        Message: 'Ignoring bad static route/filter to $1, mask $2'

        Parameters list:
              $1: ip24-network
              $2: ip24-mask

        This message is generated when a bad static route or IP filter
        is encountered."
    ::= { ipNotificationsPrefix 24 }

ipNotification25 NOTIFICATION-TYPE
    OBJECTS { 
              ip25-network, 
              ip25-mask,
              ip25-gateway 
            }
    STATUS current
    DESCRIPTION
        "Notification of Event IP.25

        Message: 'Added route to $1/$2 via $3'

        Parameters list:
              $1: ip25-network
              $2: ip25-mask
              $3: ip25-gateway

        This message is generated when a new route is added to the routing
        table. The route is indirectly connected."
    ::= { ipNotificationsPrefix 25 }

ipNotification26 NOTIFICATION-TYPE
    OBJECTS { 
              ip26-source-ip-address, 
              ip26-destination-ip-address,
              ip26-source-ip-address-nat,
              ip26-destination-ip-address-nat 
            }
    STATUS current
    DESCRIPTION
        "Notification of Event IP.26

        Message: 'NAT-IN: ($1, $2)->($3, $4)'

        Parameters list:
              $1: ip26-source-ip-address
              $2: ip26-destination-ip-address
              $3: ip26-source-ip-address-nat
              $4: ip26-destination-ip-address-nat

        This message is generated for each packet which has passed
        NAT in."
    ::= { ipNotificationsPrefix 26 }

ipNotification27 NOTIFICATION-TYPE
    OBJECTS { 
              ip27-source-ip-address, 
              ip27-destination-ip-address,
              ip27-source-ip-address-nat,
              ip27-destination-ip-address-nat 
            }
    STATUS current
    DESCRIPTION
        "Notification of Event IP.27

        Message: 'NAT-OUT: ($1, $2)->($3, $4)'

        Parameters list:
              $1: ip27-source-ip-address
              $2: ip27-destination-ip-address
              $3: ip27-source-ip-address-nat
              $4: ip27-destination-ip-address-nat

        This message is generated for each packet which has passed
        NAT out."
    ::= { ipNotificationsPrefix 27 }

ipNotification28 NOTIFICATION-TYPE
    OBJECTS { 
              ip28-source-ip-address, 
              ip28-destination-ip-address 
            }
    STATUS current
    DESCRIPTION
        "Notification of Event IP.28

        Message: 'NAT-IN: ($1, $2)-> no nat'

        Parameters list:
              $1: ip28-source-ip-address
              $2: ip28-destination-ip-address

        This message is generated for each packet which has no been
        NATed in."
    ::= { ipNotificationsPrefix 28 }

ipNotification29 NOTIFICATION-TYPE
    OBJECTS { 
              ip29-source-ip-address, 
              ip29-destination-ip-address 
            }
    STATUS current
    DESCRIPTION
        "Notification of Event IP.29

        Message: 'NAT-OUT: ($1, $2)-> no nat'

        Parameters list:
              $1: ip29-source-ip-address
              $2: ip29-destination-ip-address

        This message is generated for each packet which has no been
        NATed out."
    ::= { ipNotificationsPrefix 29 }

ipNotification30 NOTIFICATION-TYPE
    OBJECTS { 
              ip30-source-ip-address, 
              ip30-destination-ip-address 
            }
    STATUS current
    DESCRIPTION
        "Notification of Event IP.30

        Message: 'NAT-OUT: Cannot allocate nat entry, ($1, $2)-> no nat'

        Parameters list:
              $1: ip30-source-ip-address
              $2: ip30-destination-ip-address

        This message is generated when an outgoing packet is not translated
        because there is not free nat entries."
    ::= { ipNotificationsPrefix 30 }

ipNotification31 NOTIFICATION-TYPE
    OBJECTS { 
              ip31-interface 
            }
    STATUS current
    DESCRIPTION
        "Notification of Event IP.31

        Message: 'Unnumbered address rejected, interface $1'

        Parameters list:
              $1: ip31-interface

        An attempt has been made to configure an interface as unnumbered,
        yet either the interface is not a serial line or the interface has
        already been assigned an IP address. The unnumbered configuration
        request is ignored."
    ::= { ipNotificationsPrefix 31 }

ipNotification32 NOTIFICATION-TYPE
    OBJECTS { 
              ip32-source-ip-address, 
              ip32-destination-ip-address,
              ip32-interface 
            }
    STATUS current
    DESCRIPTION
        "Notification of Event IP.32

        Message: 'Fragment queue overflow from $1 for $2 on interface $3'

        Parameters list:
              $1: ip32-source-ip-address
              $2: ip32-destination-ip-address
              $3: ip32-interface

        This message is generated when an incoming fragment is discarded
        because the fragment queue overflowed."
    ::= { ipNotificationsPrefix 32 }

ipNotification33 NOTIFICATION-TYPE
    OBJECTS { 
              ip33-source-ip-address, 
              ip33-destination-ip-address,
              ip33-interface 
            }
    STATUS current
    DESCRIPTION
        "Notification of Event IP.33

        Message: 'Cannot fragment packet from $1 for $2 interface $3'

        Parameters list:
              $1: ip33-source-ip-address
              $2: ip33-destination-ip-address
              $3: ip33-interface

        This message is generated when an outgoing packet needs to be
        fragmented but has the 'don't fragment' bit set."
    ::= { ipNotificationsPrefix 33 }

ipNotification34 NOTIFICATION-TYPE
    OBJECTS { 
              ip34-source-ip-address, 
              ip34-destination-ip-address,
              ip34-offset 
            }
    STATUS current
    DESCRIPTION
        "Notification of Event IP.34

        Message: 'Bad fragment from $1 for $2 with fragment offset $3'

        Parameters list:
              $1: ip34-source-ip-address
              $2: ip34-destination-ip-address
              $3: ip34-offset

        This message is generated when an outgoing packet has an invalid length
        of fragment offset."
    ::= { ipNotificationsPrefix 34 }

ipNotification35 NOTIFICATION-TYPE
    OBJECTS { 
              ip35-interface 
            }
    STATUS current
    DESCRIPTION
        "Notification of Event IP.35

        Message: 'Cannot allocate buffer for fragment for interface $1'

        Parameters list:
              $1: ip35-interface

        This message is generated when no buffer is available to fragment
        a packet."
    ::= { ipNotificationsPrefix 35 }

ipNotification36 NOTIFICATION-TYPE
    OBJECTS { 
              ip36-protocol, 
              ip36-source-ip-address 
            }
    STATUS current
    DESCRIPTION
        "Notification of Event IP.36

        Message: 'Received packet for protocol $1 from $2'

        Parameters list:
              $1: ip36-protocol
              $2: ip36-source-ip-address

        This message is generated for each packet destined for the router."
    ::= { ipNotificationsPrefix 36 }

ipNotification37 NOTIFICATION-TYPE
    OBJECTS { 
              ip37-source-ip-address, 
              ip37-destination-ip-address,
              ip37-protocol 
            }
    STATUS current
    DESCRIPTION
        "Notification of Event IP.37

        Message: 'Broadcast packet from $1, for $2, protocol $3; no server'

        Parameters list:
              $1: ip37-source-ip-address
              $2: ip37-destination-ip-address
              $3: ip37-protocol

        This message is generated when a broadcast packet arrives for an
        unknown protocol."
    ::= { ipNotificationsPrefix 37 }

ipNotification38 NOTIFICATION-TYPE
    OBJECTS { 
              ip38-source-ip-address, 
              ip38-destination-ip-address,
              ip38-protocol 
            }
    STATUS current
    DESCRIPTION
        "Notification of Event IP.38

        Message: 'Packet from $1, for $2, protocol $3; no server'

        Parameters list:
              $1: ip38-source-ip-address
              $2: ip38-destination-ip-address
              $3: ip38-protocol

        This message is generated when a packet arrives for an
        unknown protocol. The packet was destined for the router."
    ::= { ipNotificationsPrefix 38 }

ipNotification39 NOTIFICATION-TYPE
    STATUS current
    DESCRIPTION
        "Notification of Event IP.39

        Message: '---'

        Reserved for possible future use."
    ::= { ipNotificationsPrefix 39 }

ipNotification40 NOTIFICATION-TYPE
    STATUS current
    DESCRIPTION
        "Notification of Event IP.40

        Message: '---'

        Reserved for possible future use."
    ::= { ipNotificationsPrefix 40 }

ipNotification41 NOTIFICATION-TYPE
    STATUS current
    DESCRIPTION
        "Notification of Event IP.41

        Message: '---'

        Reserved for possible future use."
    ::= { ipNotificationsPrefix 41 }

ipNotification42 NOTIFICATION-TYPE
    OBJECTS { 
              ip42-source-ip-address, 
              ip42-destination-ip-address 
            }
    STATUS current
    DESCRIPTION
        "Notification of Event IP.42

        Message: 'Illegal ARP subnet request in packet from $1 for $2'

        Parameters list:
              $1: ip42-source-ip-address
              $2: ip42-destination-ip-address

        This message is generated when an ARP subnet request is not honored
        due to illegal source or destination IP addresses in the ARP packet."
    ::= { ipNotificationsPrefix 42 }

ipNotification43 NOTIFICATION-TYPE
    OBJECTS { 
              ip43-source-ip-address, 
              ip43-destination-ip-address 
            }
    STATUS current
    DESCRIPTION
        "Notification of Event IP.43

        Message: 'Received ARP subnet route request from $1 for $2'

        Parameters list:
              $1: ip43-source-ip-address
              $2: ip43-destination-ip-address

        This message is generated when an ARP subnet request is received."
    ::= { ipNotificationsPrefix 43 }

ipNotification44 NOTIFICATION-TYPE
    OBJECTS { 
              ip44-source-ip-address, 
              ip44-destination-ip-address 
            }
    STATUS current
    DESCRIPTION
        "Notification of Event IP.44

        Message: 'ARP subnet request ignored from $1 for $2'

        Parameters list:
              $1: ip44-source-ip-address
              $2: ip44-destination-ip-address

        This message is generated when an ARP subnet request is not answered
        because the route to the target subnet is via another router on the
        same physical network as the originator."
    ::= { ipNotificationsPrefix 44 }

ipNotification45 NOTIFICATION-TYPE
    OBJECTS { 
              ip45-source-ip-address, 
              ip45-destination-ip-address 
            }
    STATUS current
    DESCRIPTION
        "Notification of Event IP.45

        Message: 'Sent ARP route from $1 for $2'

        Parameters list:
              $1: ip45-source-ip-address
              $2: ip45-destination-ip-address

        This message is generated when an ARP subnet request is answered."
    ::= { ipNotificationsPrefix 45 }

ipNotification46 NOTIFICATION-TYPE
    OBJECTS { 
              ip46-option, 
              ip46-source-ip-address 
            }
    STATUS current
    DESCRIPTION
        "Notification of Event IP.46

        Message: 'Unknown option $1 from $2'

        Parameters list:
              $1: ip46-option
              $2: ip46-source-ip-address

        This message is generated when an unknown option is specified in the
        IP header of a packet."
    ::= { ipNotificationsPrefix 46 }

ipNotification47 NOTIFICATION-TYPE
    OBJECTS { 
              ip47-option, 
              ip47-source-ip-address 
            }
    STATUS current
    DESCRIPTION
        "Notification of Event IP.47

        Message: 'Bad format for option $1 from $2'

        Parameters list:
              $1: ip47-option
              $2: ip47-source-ip-address

        This message is generated when an option is incorrectly formatted in
        the IP header."
    ::= { ipNotificationsPrefix 47 }

ipNotification48 NOTIFICATION-TYPE
    OBJECTS { 
              ip48-source-ip-address, 
              ip48-destination-ip-address 
            }
    STATUS current
    DESCRIPTION
        "Notification of Event IP.48

        Message: 'Bad next hop in strict source route from $1 for $2'

        Parameters list:
              $1: ip48-source-ip-address
              $2: ip48-destination-ip-address

        This message is generated when the next hop specified in the strict
        source route is invalid."
    ::= { ipNotificationsPrefix 48 }

ipNotification49 NOTIFICATION-TYPE
    OBJECTS { 
              ip49-timestamp, 
              ip49-source-ip-address 
            }
    STATUS current
    DESCRIPTION
        "Notification of Event IP.49

        Message: 'Bad timestamp format $1 from $2'

        Parameters list:
              $1: ip49-timestamp
              $2: ip49-source-ip-address

        This message is generated when the format of the timestamp option
        is invalid."
    ::= { ipNotificationsPrefix 49 }

ipNotification50 NOTIFICATION-TYPE
    OBJECTS { 
              ip50-source-ip-address, 
              ip50-destination-ip-address 
            }
    STATUS current
    DESCRIPTION
        "Notification of Event IP.50

        Message: 'Timestamp list overflow in packet from $1 for $2'

        Parameters list:
              $1: ip50-source-ip-address
              $2: ip50-destination-ip-address

        This message is generated when the timestamp list is full and the
        new timestamp cannot be added."
    ::= { ipNotificationsPrefix 50 }

ipNotification51 NOTIFICATION-TYPE
    OBJECTS { 
              ip51-port-number, 
              ip51-source-ip-address 
            }
    STATUS current
    DESCRIPTION
        "Notification of Event IP.51

        Message: 'Too many re-assembly buffers active; port $1 from $2'

        Parameters list:
              $1: ip51-port-number
              $2: ip51-source-ip-address

        This message is generated when a new packet needs re-assembly but
        the maximum number of re-assembly buffers has already been assigned."
    ::= { ipNotificationsPrefix 51 }

ipNotification52 NOTIFICATION-TYPE
    OBJECTS { 
              ip52-port-number, 
              ip52-source-ip-address 
            }
    STATUS current
    DESCRIPTION
        "Notification of Event IP.52

        Message: 'Insufficient storage for packet re-assembly; port $1 from $2'

        Parameters list:
              $1: ip52-port-number
              $2: ip52-source-ip-address

        This message is generated when a new packet needs re-assembly but
        there is not enough storage to allocate a re-assembly buffer."
    ::= { ipNotificationsPrefix 52 }

ipNotification53 NOTIFICATION-TYPE
    OBJECTS { 
              ip53-packet-size, 
              ip53-port-number,
              ip53-source-ip-address 
            }
    STATUS current
    DESCRIPTION
        "Notification of Event IP.53

        Message: 'Re-assembled packet too large ($1 bytes); port $2 from $3'

        Parameters list:
              $1: ip53-packet-size
              $2: ip53-port-number
              $3: ip53-source-ip-address

        This message is generated when a new packet needs re-assembly but it is
        larger than the maximum size re-assembly buffer. The packet-size is
        how large the packet would be after adding this fragment, which
        may not be the last."
    ::= { ipNotificationsPrefix 53 }

ipNotification54 NOTIFICATION-TYPE
    OBJECTS { 
              ip54-port-number, 
              ip54-source-ip-address 
            }
    STATUS current
    DESCRIPTION
        "Notification of Event IP.54

        Message: 'Re-assembly TTL expired; port $1 from $2'

        Parameters list:
              $1: ip54-port-number
              $2: ip54-source-ip-address

        This message is generated when a packet being re-assembled has
        its time-to-live expire."
    ::= { ipNotificationsPrefix 54 }

ipNotification55 NOTIFICATION-TYPE
    OBJECTS { 
              ip55-port-number, 
              ip55-source-ip-address 
            }
    STATUS current
    DESCRIPTION
        "Notification of Event IP.55

        Message: 'Re-assembly buffer free; port $1 from $2'

        Parameters list:
              $1: ip55-port-number
              $2: ip55-source-ip-address

        This message is generated when a re-assembly buffer is de-allocated."
    ::= { ipNotificationsPrefix 55 }

ipNotification56 NOTIFICATION-TYPE
    OBJECTS { 
              ip56-ip-address, 
              ip56-interface 
            }
    STATUS current
    DESCRIPTION
        "Notification of Event IP.56

        Message: 'Added default gateway $1 interface $2'

        Parameters list:
              $1: ip56-ip-address
              $2: ip56-interface

        This message is generated when an interface using a default gateway
        comes up."
    ::= { ipNotificationsPrefix 56 }

ipNotification57 NOTIFICATION-TYPE
    OBJECTS { 
              ip57-ip-address 
            }
    STATUS current
    DESCRIPTION
        "Notification of Event IP.57

        Message: 'Deleted default gateway $1'

        Parameters list:
              $1: ip57-ip-address

        This message is generated when a default gateway is deleted."
    ::= { ipNotificationsPrefix 57 }

ipNotification58 NOTIFICATION-TYPE
    OBJECTS { 
              ip58-network, 
              ip58-gateway,
              ip58-interface 
            }
    STATUS current
    DESCRIPTION
        "Notification of Event IP.58

        Message: 'Deleted net $1 route via $2 interface $3'

        Parameters list:
              $1: ip58-network
              $2: ip58-gateway
              $3: ip58-interface

        This message is generated when a network goes down."
    ::= { ipNotificationsPrefix 58 }

ipNotification59 NOTIFICATION-TYPE
    OBJECTS { 
              ip59-network 
            }
    STATUS current
    DESCRIPTION
        "Notification of Event IP.59

        Message: 'Subnet $1 defined'

        Parameters list:
              $1: ip59-network

        This message is generated when a new subnetted network is defined."
    ::= { ipNotificationsPrefix 59 }

ipNotification60 NOTIFICATION-TYPE
    OBJECTS { 
              ip60-network 
            }
    STATUS current
    DESCRIPTION
        "Notification of Event IP.60

        Message: 'Deleting subnetted network $1'

        Parameters list:
              $1: ip60-network

        This message is generated when a subnetted network is deleted.
        This happens when there are no longer any interfaces to that network."
    ::= { ipNotificationsPrefix 60 }

ipNotification61 NOTIFICATION-TYPE
    STATUS current
    DESCRIPTION
        "Notification of Event IP.61

        Message: 'Added locally generated packet to IP output queue'

        This message is generated whenever a locally generated packet is put
        on the IP output queue."
    ::= { ipNotificationsPrefix 61 }

ipNotification62 NOTIFICATION-TYPE
    OBJECTS { 
              ip62-source-ip-address 
            }
    STATUS current
    DESCRIPTION
        "Notification of Event IP.62

        Message: 'Received IP fragment from $1'

        Parameters list:
              $1: ip62-source-ip-address

        This message is generated when an IP fragment, requiring re-assembly
        is received."
    ::= { ipNotificationsPrefix 62 }

ipNotification63 NOTIFICATION-TYPE
    OBJECTS { 
              ip63-source-ip-address 
            }
    STATUS current
    DESCRIPTION
        "Notification of Event IP.63

        Message: 'Successfully re-assembled packet from $1'

        Parameters list:
              $1: ip63-source-ip-address

        This message is generated when an IP packet has been successfully
        re-assembled."
    ::= { ipNotificationsPrefix 63 }

ipNotification64 NOTIFICATION-TYPE
    OBJECTS { 
              ip64-source-ip-address, 
              ip64-destination-ip-address 
            }
    STATUS current
    DESCRIPTION
        "Notification of Event IP.64

        Message: 'Packet from $1 for $2 requires fragmentation'

        Parameters list:
              $1: ip64-source-ip-address
              $2: ip64-destination-ip-address

        This message is generated when an IP packet needs to be fragmented
        for transmission."
    ::= { ipNotificationsPrefix 64 }

ipNotification65 NOTIFICATION-TYPE
    OBJECTS { 
              ip65-source-ip-address, 
              ip65-destination-ip-address 
            }
    STATUS current
    DESCRIPTION
        "Notification of Event IP.65

        Message: 'Added fragment to output fragment queue from $1 for $2'

        Parameters list:
              $1: ip65-source-ip-address
              $2: ip65-destination-ip-address

        This message is generated when an IP packet fragment is put on
        the output fragment queue."
    ::= { ipNotificationsPrefix 65 }

ipNotification66 NOTIFICATION-TYPE
    OBJECTS { 
              ip66-source-ip-address, 
              ip66-destination-ip-address,
              ip66-interface 
            }
    STATUS current
    DESCRIPTION
        "Notification of Event IP.66

        Message: 'Discarded packet from $1 for $2 interface $3, no IP on interface'

        Parameters list:
              $1: ip66-source-ip-address
              $2: ip66-destination-ip-address
              $3: ip66-interface

        This message is generated by the stub IP forwarder for each packet
        which is received on an interface for which IP is not enabled."
    ::= { ipNotificationsPrefix 66 }

ipNotification67 NOTIFICATION-TYPE
    OBJECTS { 
              ip67-interface-ip-address 
            }
    STATUS current
    DESCRIPTION
        "Notification of Event IP.67

        Message: 'RIP1 disabled on $1 variable length subnet masks'

        Parameters list:
              $1: ip67-interface-ip-address

        The router is configured with variable length subnet masks on the
        same network, which RIP can't handle. Thus RIP1 is disabled on
        the interface."
    ::= { ipNotificationsPrefix 67 }

ipNotification68 NOTIFICATION-TYPE
    STATUS current
    DESCRIPTION
        "Notification of Event IP.68

        Message: 'routing cache cleared'

        The IP routing cache has been cleared, probably as the result of
        a routing table change."
    ::= { ipNotificationsPrefix 68 }

ipNotification69 NOTIFICATION-TYPE
    STATUS current
    DESCRIPTION
        "Notification of Event IP.69

        Message: 'routing cache garbage collecting...'

        The IP routing cache is collecting nonsense data. This takes
        several passes, and is only done when the cache starts overflowing."
    ::= { ipNotificationsPrefix 69 }

ipNotification70 NOTIFICATION-TYPE
    OBJECTS { 
              ip70-ip-destination 
            }
    STATUS current
    DESCRIPTION
        "Notification of Event IP.70

        Message: 'routing cache entry for destination $1 cleared'

        Parameters list:
              $1: ip70-ip-destination

        The IP routing cache entry for the listed destination has been cleared."
    ::= { ipNotificationsPrefix 70 }

ipNotification71 NOTIFICATION-TYPE
    STATUS current
    DESCRIPTION
        "Notification of Event IP.71

        Message: '---'

        Reserved for possible future use."
    ::= { ipNotificationsPrefix 71 }

ipNotification72 NOTIFICATION-TYPE
    OBJECTS { 
              ip72-source-ip-address, 
              ip72-destination-ip-address 
            }
    STATUS current
    DESCRIPTION
        "Notification of Event IP.72

        Message: 'Received link level broadcast from $1 for $2, discarded'

        Parameters list:
              $1: ip72-source-ip-address
              $2: ip72-destination-ip-address

        This message is generated when an attempt is made to forward an
        IP packet that was received as a link level broadcast/multicast.
        Such packets are not forwarded, and are discarded without even
        sending back an ICMP message to the source."
    ::= { ipNotificationsPrefix 72 }

ipNotification73 NOTIFICATION-TYPE
    OBJECTS { 
              ip73-source-ip-address, 
              ip73-destination-ip-address 
            }
    STATUS current
    DESCRIPTION
        "Notification of Event IP.73

        Message: 'Can't copy packet from $1 for $2, discarded'

        Parameters list:
              $1: ip73-source-ip-address
              $2: ip73-destination-ip-address

        This message is generated when an attempt is made to copy a packet for
        one of the router's internal applications (e.g., during multicast
        forwarding), and the router is unable to get a buffer. The requested
        service then fails."
    ::= { ipNotificationsPrefix 73 }

ipNotification74 NOTIFICATION-TYPE
    OBJECTS { 
              ip74-source-ip, 
              ip74-source-port,
              ip74-destination-ip,
              ip74-destination-port,
              ip74-old-mss,
              ip74-new-mss,
              ip74-interface 
            }
    STATUS current
    DESCRIPTION
        "Notification of Event IP.74

        Message: 'TCP SYN MSS Adjusted ($1:$2 -> $3:$4) ($5 => $6), interface $7'

        Parameters list:
              $1: ip74-source-ip
              $2: ip74-source-port
              $3: ip74-destination-ip
              $4: ip74-destination-port
              $5: ip74-old-mss
              $6: ip74-new-mss
              $7: ip74-interface

        The MSS value of a TCP SYN packet has been adjusted."
    ::= { ipNotificationsPrefix 74 }

ipNotification75 NOTIFICATION-TYPE
    STATUS current
    DESCRIPTION
        "Notification of Event IP.75

        Message: '---'

        Reserved for possible future use."
    ::= { ipNotificationsPrefix 75 }

ipNotification76 NOTIFICATION-TYPE
    STATUS current
    DESCRIPTION
        "Notification of Event IP.76

        Message: '---'

        Reserved for possible future use."
    ::= { ipNotificationsPrefix 76 }

ipNotification77 NOTIFICATION-TYPE
    STATUS current
    DESCRIPTION
        "Notification of Event IP.77

        Message: '---'

        Reserved for possible future use."
    ::= { ipNotificationsPrefix 77 }

ipNotification78 NOTIFICATION-TYPE
    OBJECTS { 
              ip78-source-ip-address, 
              ip78-destination-ip-address,
              ip78-protocol 
            }
    STATUS current
    DESCRIPTION
        "Notification of Event IP.78

        Message: 'Access control miss dropped, packet from $1 to $2, IP protocol number $3'

        Parameters list:
              $1: ip78-source-ip-address
              $2: ip78-destination-ip-address
              $3: ip78-protocol

        This message is generated when a IP packet matches none of the
        access control records. The packet will be dropped."
    ::= { ipNotificationsPrefix 78 }

ipNotification79 NOTIFICATION-TYPE
    OBJECTS { 
              ip79-source-ip-address, 
              ip79-destination-ip-address,
              ip79-protocol,
              ip79-source-port,
              ip79-destination-port 
            }
    STATUS current
    DESCRIPTION
        "Notification of Event IP.79

        Message: 'Access control miss dropped, packet from $1 to $2, $3 port number $4 to $5'

        Parameters list:
              $1: ip79-source-ip-address
              $2: ip79-destination-ip-address
              $3: ip79-protocol
              $4: ip79-source-port
              $5: ip79-destination-port

        This message is generated when a IP packet matches none of the
        access control records. The packet will be dropped."
    ::= { ipNotificationsPrefix 79 }

ipNotification80 NOTIFICATION-TYPE
    OBJECTS { 
              ip80-router-address 
            }
    STATUS current
    DESCRIPTION
        "Notification of Event IP.80

        Message: 'new router $1 has been discovered'

        Parameters list:
              $1: ip80-router-address

        A new router has been discovered, either through static configuration,
        an ICMP redirect, RIP or ICMP router discovery. This message is
        produced only when running as an IP host (i.e., when IP routing
        disabled)."
    ::= { ipNotificationsPrefix 80 }

ipNotification81 NOTIFICATION-TYPE
    OBJECTS { 
              ip81-interface 
            }
    STATUS current
    DESCRIPTION
        "Notification of Event IP.81

        Message: 'IP protocol does not run over interface $1'

        Parameters list:
              $1: ip81-interface

        An IP address was configured for a type of network which currently
        doesn't support IP."
    ::= { ipNotificationsPrefix 81 }

ipNotification82 NOTIFICATION-TYPE
    OBJECTS { 
              ip82-packet-length, 
              ip82-source-ip-address,
              ip82-destination-ip-address 
            }
    STATUS current
    DESCRIPTION
        "Notification of Event IP.82

        Message: 'IP length of $1 in packet from $2 -> $3 is too short'

        Parameters list:
              $1: ip82-packet-length
              $2: ip82-source-ip-address
              $3: ip82-destination-ip-address

        This message is generated when a packet's indicated length is below
        the minimum possible length. The packet is discarded."
    ::= { ipNotificationsPrefix 82 }

ipNotification83 NOTIFICATION-TYPE
    OBJECTS { 
              ip83-record-number, 
              ip83-cache-status,
              ip83-source-ip-address,
              ip83-destination-ip-address,
              ip83-protcol-number 
            }
    STATUS current
    DESCRIPTION
        "Notification of Event IP.83

        Message: 'Access control number $1 dropped, $2, packet from $3 to $4, IP protocol number $5'

        Parameters list:
              $1: ip83-record-number
              $2: ip83-cache-status
              $3: ip83-source-ip-address
              $4: ip83-destination-ip-address
              $5: ip83-protcol-number

        This message is generated when a IP packet matches one of the exclusive
        access control entries. The packet will be dropped.
        The record-number is the number of the access control record matched,
        or zero for no record (end-of-list). The cache-status will be
        ''cache-hit'' or ''cache-miss''."
    ::= { ipNotificationsPrefix 83 }

ipNotification84 NOTIFICATION-TYPE
    OBJECTS { 
              ip84-record-number, 
              ip84-cache-status,
              ip84-source-ip-address,
              ip84-destination-ip-address,
              ip84-protcol-number 
            }
    STATUS current
    DESCRIPTION
        "Notification of Event IP.84

        Message: 'Access control number $1 passed, $2, packet from $3 to $4, IP protocol number $5'

        Parameters list:
              $1: ip84-record-number
              $2: ip84-cache-status
              $3: ip84-source-ip-address
              $4: ip84-destination-ip-address
              $5: ip84-protcol-number

        This message is generated when a IP packet matches one of the inclusive
        access control entries. The packet may be forwarded.
        The record-number is the number of the access control record matched.
        The cache-status will be ''cache-hit'' or ''cache-miss''."
    ::= { ipNotificationsPrefix 84 }

ipNotification85 NOTIFICATION-TYPE
    OBJECTS { 
              ip85-record-number, 
              ip85-cache-status,
              ip85-source-ip-address,
              ip85-destination-ip-address,
              ip85-protocol,
              ip85-source-port,
              ip85-destination-port 
            }
    STATUS current
    DESCRIPTION
        "Notification of Event IP.85

        Message: 'Access control number $1 dropped, $2, packet from $3 to $4, $5 port number $6 to $7'

        Parameters list:
              $1: ip85-record-number
              $2: ip85-cache-status
              $3: ip85-source-ip-address
              $4: ip85-destination-ip-address
              $5: ip85-protocol
              $6: ip85-source-port
              $7: ip85-destination-port

        This message is generated when a IP packet matches one of the TCP or UDP
        exclusive access control entries. The packet will be dropped.
        The record-number is the number of the access control record matched,
        or zero for no record (end-of-list). The cache-status will be
        ''cache-hit'' or ''cache-miss''."
    ::= { ipNotificationsPrefix 85 }

ipNotification86 NOTIFICATION-TYPE
    OBJECTS { 
              ip86-record-number, 
              ip86-cache-status,
              ip86-source-ip-address,
              ip86-destination-ip-address,
              ip86-protocol,
              ip86-source-port,
              ip86-destination-port 
            }
    STATUS current
    DESCRIPTION
        "Notification of Event IP.86

        Message: 'Access control number $1 passed, $2, packet from $3 to $4, $5 port number $6 to $7'

        Parameters list:
              $1: ip86-record-number
              $2: ip86-cache-status
              $3: ip86-source-ip-address
              $4: ip86-destination-ip-address
              $5: ip86-protocol
              $6: ip86-source-port
              $7: ip86-destination-port

        This message is generated when a IP packet matches one of the TCP or UDP
        inclusive access control entries. The packet may be forwarded.
        The record-number is the number of the access control record matched.
        The cache-status will be ''cache-hit'' or ''cache-miss''."
    ::= { ipNotificationsPrefix 86 }

ipNotification87 NOTIFICATION-TYPE
    OBJECTS { 
              ip87-interface, 
              ip87-access-list,
              ip87-direction 
            }
    STATUS current
    DESCRIPTION
        "Notification of Event IP.87

        Message: 'Access-Group dropped, $1 $2 [$3]'

        Parameters list:
              $1: ip87-interface
              $2: ip87-access-list
              $3: ip87-direction

        Message is generated when a IP packet does not match the access-group
        per-interface access control list."
    ::= { ipNotificationsPrefix 87 }

ipNotification88 NOTIFICATION-TYPE
    OBJECTS { 
              ip88-interface, 
              ip88-source-ip,
              ip88-destination-ip 
            }
    STATUS current
    DESCRIPTION
        "Notification of Event IP.88

        Message: 'verify unicast failed ifc $1 $2 -> $3'

        Parameters list:
              $1: ip88-interface
              $2: ip88-source-ip
              $3: ip88-destination-ip

        Message is generated when a IP packet does not verify the unicast
        reverse route criteria."
    ::= { ipNotificationsPrefix 88 }

ipNotification89 NOTIFICATION-TYPE
    OBJECTS { 
              ip89-destination, 
              ip89-mask,
              ip89-interface 
            }
    STATUS current
    DESCRIPTION
        "Notification of Event IP.89

        Message: 'found a static route to $1 $2 via dhcp default gateway on $3'

        Parameters list:
              $1: ip89-destination
              $2: ip89-mask
              $3: ip89-interface

        Found a static route configured whose next-hop is given for the DHCP
        parameters received on that interface."
    ::= { ipNotificationsPrefix 89 }

ipNotification90 NOTIFICATION-TYPE
    OBJECTS { 
              ip90-destination, 
              ip90-mask,
              ip90-interface 
            }
    STATUS current
    DESCRIPTION
        "Notification of Event IP.90

        Message: 'deleting a static route to $1 $2 via dhcp default gateway on $3'

        Parameters list:
              $1: ip90-destination
              $2: ip90-mask
              $3: ip90-interface

        Deleting a static route configured whose next-hop was given for the DHCP
        parameters received on that interface."
    ::= { ipNotificationsPrefix 90 }


END
