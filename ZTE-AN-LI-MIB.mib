ZTE-AN-LI-MIB DEFINITIONS ::= BEGIN

    IMPORTS
        ifIndex
            FROM IF-MIB
        InetAddressType, InetAddress
            FROM INET-ADDRESS-MIB
        OBJECT-GROUP, MODULE-COMPLIANCE
            FROM SNMPv2-CONF
        Integer32, OBJECT-TYPE, MODULE-IDENTITY, IpAddress
            FROM SNMPv2-SMI
        DisplayString, RowStatus, MacAddress, TEXTUAL-CONVENTION, DateAndTime
            FROM SNMPv2-TC
        zxAnSubIfIndex
            FROM ZTE-AN-IF-MIB
        zxAnServiceSecurity
            FROM ZTE-AN-SMI;

    zxAnLiMib MODULE-IDENTITY
        LAST-UPDATED    "201911290000Z"
        ORGANIZATION    "ZTE Corporation"
        CONTACT-INFO    "Di cuixia
                         Mail: di.cuixia@zte.com.cn
                         Tel : +86-021-6889xxxx"
        DESCRIPTION     "The MIB module for the management of lawful intercept."
        REVISION        "201911290000Z"
        DESCRIPTION
            "Initial version of this MIB module."
        ::= { zxAnServiceSecurity 90 }


--------------------------------------------------------------------------------
-- Following objects are defined.
-- 1. Global Objects
-- 2. zxAnLawfulInterceptTable

--------------------------------------------------------------------------------

    zxAnLiObjects         OBJECT IDENTIFIER ::= { zxAnLiMib 2 }

    zxAnLiConformance     OBJECT IDENTIFIER ::= { zxAnLiMib 4 }


--------------------------------------------------------------------------------
-- 2. zxAnLawfulInterceptTable
--------------------------------------------------------------------------------

    zxAnLawfulInterceptConfTable OBJECT-TYPE
        SYNTAX SEQUENCE OF ZxAnLawfulInterceptConfEntry
        MAX-ACCESS  not-accessible
        STATUS      current
        DESCRIPTION
            "Lawful intercept table."
        ::= { zxAnLiObjects 1 }


    zxAnLawfulInterceptConfEntry OBJECT-TYPE
        SYNTAX ZxAnLawfulInterceptConfEntry
        MAX-ACCESS  not-accessible
        STATUS      current
        DESCRIPTION
            "Lawful intercept entry."
        INDEX { zxAnLiConfNumber }
        ::= { zxAnLawfulInterceptConfTable 1 }


    ZxAnLawfulInterceptConfEntry ::=
        SEQUENCE {
            zxAnLiConfNumber         Integer32,
            zxAnLiConfUserName       DisplayString,
            zxAnLiConfPassword       DisplayString,
            zxAnLiConfSrcIpType      InetAddressType,
            zxAnLiConfSrcIp          InetAddress,
            zxAnLiConfSrcMac         MacAddress,
            zxAnLiConfUdpDstIpType   InetAddressType,
            zxAnLiConfUdpDstIp       InetAddress,
            zxAnLiConfUdpSrcPort     Integer32,
            zxAnLiConfUdpDstPort     Integer32,
            zxAnLiConfStartTime      DateAndTime,
            zxAnLiConfEndTime        DateAndTime,
            zxAnLiConfAuthStatus     INTEGER,
            zxAnLiConfRowStatus      RowStatus
         }

    zxAnLiConfNumber OBJECT-TYPE
        SYNTAX      Integer32(1..8)
        MAX-ACCESS  not-accessible
        STATUS      current
        DESCRIPTION
            "The number of the lawful intercept."
        ::= { zxAnLawfulInterceptConfEntry 1 }


    zxAnLiConfUserName OBJECT-TYPE
        SYNTAX      DisplayString(SIZE (1..32))
        MAX-ACCESS  read-create
        STATUS      current
        DESCRIPTION
            "The name of the user for authentication."
        ::= { zxAnLawfulInterceptConfEntry 2 }


    zxAnLiConfPassword OBJECT-TYPE
        SYNTAX      DisplayString (SIZE (1..32))
        MAX-ACCESS  read-create
        STATUS      current
        DESCRIPTION
            "The password of the user for authentication."
        ::= { zxAnLawfulInterceptConfEntry 3 }
        
    zxAnLiConfSrcIpType OBJECT-TYPE
        SYNTAX      InetAddressType
        MAX-ACCESS  read-create
        STATUS      current
        DESCRIPTION
            "The type of the source IP address of packets to be matched for 
             lawful intercept."
        DEFVAL { ipv4 }
        ::= { zxAnLawfulInterceptConfEntry 4 }        

    zxAnLiConfSrcIp OBJECT-TYPE
        SYNTAX      InetAddress
        MAX-ACCESS  read-create
        STATUS      current
        DESCRIPTION
            "The source IP address of packets to be matched for lawful 
             intercept.
             Only one of zxAnLiConfSrcIp and zxAnLiConfSrcMac 
             can be configured in the same row."
        DEFVAL { '00000000'h }
        ::= { zxAnLawfulInterceptConfEntry 5 }

    zxAnLiConfSrcMac OBJECT-TYPE
        SYNTAX      MacAddress
        MAX-ACCESS  read-create
        STATUS      current
        DESCRIPTION
            "The source MAC address of packets to be matched for lawful 
             intercept.
             Only one of zxAnLiConfSrcIp and zxAnLiConfSrcMac 
             can be configured in the same row."
        DEFVAL { '000000000000'h }
        ::= { zxAnLawfulInterceptConfEntry 6 }

    zxAnLiConfUdpDstIpType OBJECT-TYPE
        SYNTAX      InetAddressType
        MAX-ACCESS  read-create
        STATUS      current
        DESCRIPTION
            "The type of the destination IP address that the packets are sent 
             to."
        DEFVAL { ipv4 }
        ::= { zxAnLawfulInterceptConfEntry 7 }
        
    zxAnLiConfUdpDstIp OBJECT-TYPE
        SYNTAX      InetAddress
        MAX-ACCESS  read-create
        STATUS      current
        DESCRIPTION
            "The UDP destination IP address that the packets are sent to."
        ::= { zxAnLawfulInterceptConfEntry 8 }

    zxAnLiConfUdpSrcPort OBJECT-TYPE
        SYNTAX      Integer32 (0..65535)
        MAX-ACCESS  read-create
        STATUS      current
        DESCRIPTION
            "The UDP source port number of the encapsulated UDP packets."
        DEFVAL { 30004 }
        ::= { zxAnLawfulInterceptConfEntry 9 }

    zxAnLiConfUdpDstPort OBJECT-TYPE
        SYNTAX      Integer32 (0..65535)
        MAX-ACCESS  read-create
        STATUS      current
        DESCRIPTION
            "The UDP destination port number of the encapsulated UDP packets."
        DEFVAL { 9000 }
        ::= { zxAnLawfulInterceptConfEntry 10 }

    zxAnLiConfStartTime OBJECT-TYPE
        SYNTAX      DateAndTime
        MAX-ACCESS  read-create
        STATUS      current
        DESCRIPTION
            "The starting time for intercept."
        ::= { zxAnLawfulInterceptConfEntry 11 }

    zxAnLiConfEndTime OBJECT-TYPE
        SYNTAX      DateAndTime
        MAX-ACCESS  read-create
        STATUS       current
        DESCRIPTION
            "The ending time for intercept."
        ::= { zxAnLawfulInterceptConfEntry 12 }

    zxAnLiConfAuthStatus OBJECT-TYPE
        SYNTAX      INTEGER {
            succeeded(1),
            failed(2)
        }
        MAX-ACCESS  read-only
        STATUS      current
        DESCRIPTION
            "The authentication status."
        DEFVAL { failed }
        ::= { zxAnLawfulInterceptConfEntry 13 }

    zxAnLiConfRowStatus OBJECT-TYPE
        SYNTAX RowStatus
        MAX-ACCESS read-create
        STATUS current
        DESCRIPTION
            "The status of this conceptual row.

            The supported actions of this conceptual row only include:
            'createAndGo' and 'destroy'. Don't support update.
            To create a row in this table, a manager must set this object to
            createAndGo(4), and must comply with the multi-variables binding
            described in zxAnLawfulInterceptConfEntry.

            To delete a row in this table, a manager must set this object to
            destroy(6).

            To get this object, the agent always returns active(1)."
        ::= { zxAnLawfulInterceptConfEntry 50}


    zxAnLiCompliances OBJECT IDENTIFIER ::= { zxAnLiConformance 1 }


    zxAnLiCompliance MODULE-COMPLIANCE
        STATUS current
        DESCRIPTION
            "The compliance statement for the ZTE-AN-LI-MIB."
        MODULE 
            MANDATORY-GROUPS { zxAnLiGroup   }
        ::= { zxAnLiCompliances 1 }


    zxAnLiGroups OBJECT IDENTIFIER ::= { zxAnLiConformance 2 }


    zxAnLiGroup OBJECT-GROUP
        OBJECTS {
                zxAnLiConfUserName,
                zxAnLiConfPassword,
                zxAnLiConfSrcIp,
                zxAnLiConfSrcMac,
                zxAnLiConfUdpDstIp,
                zxAnLiConfUdpSrcPort,
                zxAnLiConfUdpDstPort,
                zxAnLiConfStartTime,
                zxAnLiConfEndTime,
                zxAnLiConfRowStatus   }
        STATUS current
        DESCRIPTION
            "A collection of objects providing the lawful intercept
             configuration information."
        ::= { zxAnLiGroups 1 }

    END
--
--
--
