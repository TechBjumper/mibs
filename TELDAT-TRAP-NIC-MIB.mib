-- file automatically created


TELDAT-TRAP-NIC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


nicTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NIC event subsystem."
    REVISION "201401200930Z"
    DESCRIPTION "Initial implementation"
        ::= { telEventTraps 242 }


nicEventsGroup	OBJECT IDENTIFIER	::= { nicTrapsMIB 1 }

nicNotifications	OBJECT IDENTIFIER	::= { nicTrapsMIB 2 }
nicNotificationsPrefix	OBJECT IDENTIFIER	::= { nicNotifications 0 }

nicEventObjects1 OBJECT-IDENTITY
    STATUS current
    DESCRIPTION
        "Event NIC.1
        On initializing, the associated base interface has not been found."
    ::= { nicEventsGroup 1 }

nic1-ifcname OBJECT-TYPE
    SYNTAX DisplayString
    MAX-ACCESS accessible-for-notify
    STATUS current
    DESCRIPTION
        "Parameter 'ifcname' in event NIC.1"
    ::= { nicEventObjects1 1 }

nicEventObjects2 OBJECT-IDENTITY
    STATUS current
    DESCRIPTION
        "Event NIC.2
        An event has been sent to associated dialer."
    ::= { nicEventsGroup 2 }

nic2-inddesc OBJECT-TYPE
    SYNTAX DisplayString
    MAX-ACCESS accessible-for-notify
    STATUS current
    DESCRIPTION
        "Parameter 'inddesc' in event NIC.2"
    ::= { nicEventObjects2 1 }

nic2-indvalue OBJECT-TYPE
    SYNTAX Integer32
    MAX-ACCESS accessible-for-notify
    STATUS current
    DESCRIPTION
        "Parameter 'indvalue' in event NIC.2"
    ::= { nicEventObjects2 2 }

nic2-callstat OBJECT-TYPE
    SYNTAX Integer32
    MAX-ACCESS accessible-for-notify
    STATUS current
    DESCRIPTION
        "Parameter 'callstat' in event NIC.2"
    ::= { nicEventObjects2 3 }

nic2-ifcname OBJECT-TYPE
    SYNTAX DisplayString
    MAX-ACCESS accessible-for-notify
    STATUS current
    DESCRIPTION
        "Parameter 'ifcname' in event NIC.2"
    ::= { nicEventObjects2 4 }

nicEventObjects3 OBJECT-IDENTITY
    STATUS current
    DESCRIPTION
        "Event NIC.3
        Received a command from associated dialer."
    ::= { nicEventsGroup 3 }

nic3-dialer OBJECT-TYPE
    SYNTAX DisplayString
    MAX-ACCESS accessible-for-notify
    STATUS current
    DESCRIPTION
        "Parameter 'dialer' in event NIC.3"
    ::= { nicEventObjects3 1 }

nic3-cmddesc OBJECT-TYPE
    SYNTAX DisplayString
    MAX-ACCESS accessible-for-notify
    STATUS current
    DESCRIPTION
        "Parameter 'cmddesc' in event NIC.3"
    ::= { nicEventObjects3 2 }

nic3-cmdval OBJECT-TYPE
    SYNTAX Integer32
    MAX-ACCESS accessible-for-notify
    STATUS current
    DESCRIPTION
        "Parameter 'cmdval' in event NIC.3"
    ::= { nicEventObjects3 3 }

nic3-callstat OBJECT-TYPE
    SYNTAX Integer32
    MAX-ACCESS accessible-for-notify
    STATUS current
    DESCRIPTION
        "Parameter 'callstat' in event NIC.3"
    ::= { nicEventObjects3 4 }

nic3-ifcname OBJECT-TYPE
    SYNTAX DisplayString
    MAX-ACCESS accessible-for-notify
    STATUS current
    DESCRIPTION
        "Parameter 'ifcname' in event NIC.3"
    ::= { nicEventObjects3 5 }

nicEventObjects4 OBJECT-IDENTITY
    STATUS current
    DESCRIPTION
        "Event NIC.4
        Error detected when receive a command from dialer."
    ::= { nicEventsGroup 4 }

nic4-error OBJECT-TYPE
    SYNTAX DisplayString
    MAX-ACCESS accessible-for-notify
    STATUS current
    DESCRIPTION
        "Parameter 'error' in event NIC.4"
    ::= { nicEventObjects4 1 }

nic4-ifcname OBJECT-TYPE
    SYNTAX DisplayString
    MAX-ACCESS accessible-for-notify
    STATUS current
    DESCRIPTION
        "Parameter 'ifcname' in event NIC.4"
    ::= { nicEventObjects4 2 }

nicEventObjects5 OBJECT-IDENTITY
    STATUS current
    DESCRIPTION
        "Event NIC.5
        Error detected on cellular commands exchange."
    ::= { nicEventsGroup 5 }

nic5-error OBJECT-TYPE
    SYNTAX DisplayString
    MAX-ACCESS accessible-for-notify
    STATUS current
    DESCRIPTION
        "Parameter 'error' in event NIC.5"
    ::= { nicEventObjects5 1 }

nic5-ifcname OBJECT-TYPE
    SYNTAX DisplayString
    MAX-ACCESS accessible-for-notify
    STATUS current
    DESCRIPTION
        "Parameter 'ifcname' in event NIC.5"
    ::= { nicEventObjects5 2 }

nicEventObjects6 OBJECT-IDENTITY
    STATUS current
    DESCRIPTION
        "Event NIC.6
        Error detected on cellular commands exchange."
    ::= { nicEventsGroup 6 }

nic6-command OBJECT-TYPE
    SYNTAX DisplayString
    MAX-ACCESS accessible-for-notify
    STATUS current
    DESCRIPTION
        "Parameter 'command' in event NIC.6"
    ::= { nicEventObjects6 1 }

nic6-ifcname OBJECT-TYPE
    SYNTAX DisplayString
    MAX-ACCESS accessible-for-notify
    STATUS current
    DESCRIPTION
        "Parameter 'ifcname' in event NIC.6"
    ::= { nicEventObjects6 2 }

nicEventObjects7 OBJECT-IDENTITY
    STATUS current
    DESCRIPTION
        "Event NIC.7
        A correct answer has been received from cellular base interface."
    ::= { nicEventsGroup 7 }

nic7-response OBJECT-TYPE
    SYNTAX DisplayString
    MAX-ACCESS accessible-for-notify
    STATUS current
    DESCRIPTION
        "Parameter 'response' in event NIC.7"
    ::= { nicEventObjects7 1 }

nic7-ifcname OBJECT-TYPE
    SYNTAX DisplayString
    MAX-ACCESS accessible-for-notify
    STATUS current
    DESCRIPTION
        "Parameter 'ifcname' in event NIC.7"
    ::= { nicEventObjects7 2 }

nicEventObjects8 OBJECT-IDENTITY
    STATUS current
    DESCRIPTION
        "Event NIC.8
        Call progress information."
    ::= { nicEventsGroup 8 }

nic8-info-str OBJECT-TYPE
    SYNTAX DisplayString
    MAX-ACCESS accessible-for-notify
    STATUS current
    DESCRIPTION
        "Parameter 'info-str' in event NIC.8"
    ::= { nicEventObjects8 1 }

nic8-call-state OBJECT-TYPE
    SYNTAX Integer32
    MAX-ACCESS accessible-for-notify
    STATUS current
    DESCRIPTION
        "Parameter 'call-state' in event NIC.8"
    ::= { nicEventObjects8 2 }

nic8-ifcname OBJECT-TYPE
    SYNTAX DisplayString
    MAX-ACCESS accessible-for-notify
    STATUS current
    DESCRIPTION
        "Parameter 'ifcname' in event NIC.8"
    ::= { nicEventObjects8 3 }

nicEventObjects9 OBJECT-IDENTITY
    STATUS current
    DESCRIPTION
        "Event NIC.9
        A connectios has been requested."
    ::= { nicEventsGroup 9 }

nic9-ifcname OBJECT-TYPE
    SYNTAX DisplayString
    MAX-ACCESS accessible-for-notify
    STATUS current
    DESCRIPTION
        "Parameter 'ifcname' in event NIC.9"
    ::= { nicEventObjects9 1 }

nicEventObjects10 OBJECT-IDENTITY
    STATUS current
    DESCRIPTION
        "Event NIC.10
        Disconnection has been requested."
    ::= { nicEventsGroup 10 }

nic10-pdp-name OBJECT-TYPE
    SYNTAX DisplayString
    MAX-ACCESS accessible-for-notify
    STATUS current
    DESCRIPTION
        "Parameter 'pdp-name' in event NIC.10"
    ::= { nicEventObjects10 1 }

nic10-call-state OBJECT-TYPE
    SYNTAX Integer32
    MAX-ACCESS accessible-for-notify
    STATUS current
    DESCRIPTION
        "Parameter 'call-state' in event NIC.10"
    ::= { nicEventObjects10 2 }

nic10-ifcname OBJECT-TYPE
    SYNTAX DisplayString
    MAX-ACCESS accessible-for-notify
    STATUS current
    DESCRIPTION
        "Parameter 'ifcname' in event NIC.10"
    ::= { nicEventObjects10 3 }

nicEventObjects11 OBJECT-IDENTITY
    STATUS current
    DESCRIPTION
        "Event NIC.11
        An accessibility control condition has triggered, release active call."
    ::= { nicEventsGroup 11 }

nic11-acc-type OBJECT-TYPE
    SYNTAX DisplayString
    MAX-ACCESS accessible-for-notify
    STATUS current
    DESCRIPTION
        "Parameter 'acc-type' in event NIC.11"
    ::= { nicEventObjects11 1 }

nic11-ifcname OBJECT-TYPE
    SYNTAX DisplayString
    MAX-ACCESS accessible-for-notify
    STATUS current
    DESCRIPTION
        "Parameter 'ifcname' in event NIC.11"
    ::= { nicEventObjects11 2 }

nicEventObjects12 OBJECT-IDENTITY
    STATUS current
    DESCRIPTION
        "Event NIC.12
        Accessibility control progress information."
    ::= { nicEventsGroup 12 }

nic12-acc-info OBJECT-TYPE
    SYNTAX DisplayString
    MAX-ACCESS accessible-for-notify
    STATUS current
    DESCRIPTION
        "Parameter 'acc-info' in event NIC.12"
    ::= { nicEventObjects12 1 }

nic12-ifcname OBJECT-TYPE
    SYNTAX DisplayString
    MAX-ACCESS accessible-for-notify
    STATUS current
    DESCRIPTION
        "Parameter 'ifcname' in event NIC.12"
    ::= { nicEventObjects12 2 }

nicEventObjects13 OBJECT-IDENTITY
    STATUS current
    DESCRIPTION
        "Event NIC.13
        Performs a reset of the Cellular module on disconnection time."
    ::= { nicEventsGroup 13 }

nic13-ifcname OBJECT-TYPE
    SYNTAX DisplayString
    MAX-ACCESS accessible-for-notify
    STATUS current
    DESCRIPTION
        "Parameter 'ifcname' in event NIC.13"
    ::= { nicEventObjects13 1 }

nicEventObjects14 OBJECT-IDENTITY
    STATUS current
    DESCRIPTION
        "Event NIC.14
        A Cellular module with NIC interface has been detected."
    ::= { nicEventsGroup 14 }

nic14-ifcname OBJECT-TYPE
    SYNTAX DisplayString
    MAX-ACCESS accessible-for-notify
    STATUS current
    DESCRIPTION
        "Parameter 'ifcname' in event NIC.14"
    ::= { nicEventObjects14 1 }

nicEventObjects15 OBJECT-IDENTITY
    STATUS current
    DESCRIPTION
        "Event NIC.15
        A Cellular module with NIC interface has been released."
    ::= { nicEventsGroup 15 }

nic15-ifcname OBJECT-TYPE
    SYNTAX DisplayString
    MAX-ACCESS accessible-for-notify
    STATUS current
    DESCRIPTION
        "Parameter 'ifcname' in event NIC.15"
    ::= { nicEventObjects15 1 }

nicEventObjects16 OBJECT-IDENTITY
    STATUS current
    DESCRIPTION
        "Event NIC.16
        A unsolicited result code has been received from cellular base interface."
    ::= { nicEventsGroup 16 }

nic16-response OBJECT-TYPE
    SYNTAX DisplayString
    MAX-ACCESS accessible-for-notify
    STATUS current
    DESCRIPTION
        "Parameter 'response' in event NIC.16"
    ::= { nicEventObjects16 1 }

nic16-ifcname OBJECT-TYPE
    SYNTAX DisplayString
    MAX-ACCESS accessible-for-notify
    STATUS current
    DESCRIPTION
        "Parameter 'ifcname' in event NIC.16"
    ::= { nicEventObjects16 2 }

nicEventObjects17 OBJECT-IDENTITY
    STATUS current
    DESCRIPTION
        "Event NIC.17
        Start time to make new call due delayed calls is enabled."
    ::= { nicEventsGroup 17 }

nic17-time OBJECT-TYPE
    SYNTAX Integer32
    MAX-ACCESS accessible-for-notify
    STATUS current
    DESCRIPTION
        "Parameter 'time' in event NIC.17"
    ::= { nicEventObjects17 1 }

nic17-ifcname OBJECT-TYPE
    SYNTAX DisplayString
    MAX-ACCESS accessible-for-notify
    STATUS current
    DESCRIPTION
        "Parameter 'ifcname' in event NIC.17"
    ::= { nicEventObjects17 2 }

nicEventObjects18 OBJECT-IDENTITY
    STATUS current
    DESCRIPTION
        "Event NIC.18
        QMI procedure."
    ::= { nicEventsGroup 18 }

nic18-ifcname OBJECT-TYPE
    SYNTAX DisplayString
    MAX-ACCESS accessible-for-notify
    STATUS current
    DESCRIPTION
        "Parameter 'ifcname' in event NIC.18"
    ::= { nicEventObjects18 1 }

nic18-result-or-information OBJECT-TYPE
    SYNTAX DisplayString
    MAX-ACCESS accessible-for-notify
    STATUS current
    DESCRIPTION
        "Parameter 'result-or-information' in event NIC.18"
    ::= { nicEventObjects18 2 }

nicEventObjects19 OBJECT-IDENTITY
    STATUS current
    DESCRIPTION
        "Event NIC.19
        Control information has been received from cellular module."
    ::= { nicEventsGroup 19 }

nic19-message OBJECT-TYPE
    SYNTAX DisplayString
    MAX-ACCESS accessible-for-notify
    STATUS current
    DESCRIPTION
        "Parameter 'message' in event NIC.19"
    ::= { nicEventObjects19 1 }


nicNotification1 NOTIFICATION-TYPE
    OBJECTS { 
              nic1-ifcname 
            }
    STATUS current
    DESCRIPTION
        "Notification of Event NIC.1

        Message: 'The base interface $1 has not been found'

        Parameters list:
              $1: nic1-ifcname

        On initializing, the associated base interface has not been found."
    ::= { nicNotificationsPrefix 1 }

nicNotification2 NOTIFICATION-TYPE
    OBJECTS { 
              nic2-inddesc, 
              nic2-indvalue,
              nic2-callstat,
              nic2-ifcname 
            }
    STATUS current
    DESCRIPTION
        "Notification of Event NIC.2

        Message: 'Send event $1[$2] to dialer, call state $3 on interface $4'

        Parameters list:
              $1: nic2-inddesc
              $2: nic2-indvalue
              $3: nic2-callstat
              $4: nic2-ifcname

        An event has been sent to associated dialer."
    ::= { nicNotificationsPrefix 2 }

nicNotification3 NOTIFICATION-TYPE
    OBJECTS { 
              nic3-dialer, 
              nic3-cmddesc,
              nic3-cmdval,
              nic3-callstat,
              nic3-ifcname 
            }
    STATUS current
    DESCRIPTION
        "Notification of Event NIC.3

        Message: 'Received from dialer $1 the command $2[$3], call state $4 on interface $5'

        Parameters list:
              $1: nic3-dialer
              $2: nic3-cmddesc
              $3: nic3-cmdval
              $4: nic3-callstat
              $5: nic3-ifcname

        Received a command from associated dialer."
    ::= { nicNotificationsPrefix 3 }

nicNotification4 NOTIFICATION-TYPE
    OBJECTS { 
              nic4-error, 
              nic4-ifcname 
            }
    STATUS current
    DESCRIPTION
        "Notification of Event NIC.4

        Message: 'Error on received command from dialer: $1, on interface $2'

        Parameters list:
              $1: nic4-error
              $2: nic4-ifcname

        Error detected when receive a command from dialer."
    ::= { nicNotificationsPrefix 4 }

nicNotification5 NOTIFICATION-TYPE
    OBJECTS { 
              nic5-error, 
              nic5-ifcname 
            }
    STATUS current
    DESCRIPTION
        "Notification of Event NIC.5

        Message: 'Cellular command error: $1, on interface $2'

        Parameters list:
              $1: nic5-error
              $2: nic5-ifcname

        Error detected on cellular commands exchange."
    ::= { nicNotificationsPrefix 5 }

nicNotification6 NOTIFICATION-TYPE
    OBJECTS { 
              nic6-command, 
              nic6-ifcname 
            }
    STATUS current
    DESCRIPTION
        "Notification of Event NIC.6

        Message: 'Send command to cellular interface: $1, on interface $2'

        Parameters list:
              $1: nic6-command
              $2: nic6-ifcname

        Error detected on cellular commands exchange."
    ::= { nicNotificationsPrefix 6 }

nicNotification7 NOTIFICATION-TYPE
    OBJECTS { 
              nic7-response, 
              nic7-ifcname 
            }
    STATUS current
    DESCRIPTION
        "Notification of Event NIC.7

        Message: 'Cellular command response OK: $1 ,on interface $2'

        Parameters list:
              $1: nic7-response
              $2: nic7-ifcname

        A correct answer has been received from cellular base interface."
    ::= { nicNotificationsPrefix 7 }

nicNotification8 NOTIFICATION-TYPE
    OBJECTS { 
              nic8-info-str, 
              nic8-call-state,
              nic8-ifcname 
            }
    STATUS current
    DESCRIPTION
        "Notification of Event NIC.8

        Message: 'Call information: $1 call state $2 interface $3'

        Parameters list:
              $1: nic8-info-str
              $2: nic8-call-state
              $3: nic8-ifcname

        Call progress information."
    ::= { nicNotificationsPrefix 8 }

nicNotification9 NOTIFICATION-TYPE
    OBJECTS { 
              nic9-ifcname 
            }
    STATUS current
    DESCRIPTION
        "Notification of Event NIC.9

        Message: 'Connection request, interface $1'

        Parameters list:
              $1: nic9-ifcname

        A connectios has been requested."
    ::= { nicNotificationsPrefix 9 }

nicNotification10 NOTIFICATION-TYPE
    OBJECTS { 
              nic10-pdp-name, 
              nic10-call-state,
              nic10-ifcname 
            }
    STATUS current
    DESCRIPTION
        "Notification of Event NIC.10

        Message: 'Call released on PDP $1, call state $2 interface $3'

        Parameters list:
              $1: nic10-pdp-name
              $2: nic10-call-state
              $3: nic10-ifcname

        Disconnection has been requested."
    ::= { nicNotificationsPrefix 10 }

nicNotification11 NOTIFICATION-TYPE
    OBJECTS { 
              nic11-acc-type, 
              nic11-ifcname 
            }
    STATUS current
    DESCRIPTION
        "Notification of Event NIC.11

        Message: 'Accessibility control $1 triggered, clear call interface $2'

        Parameters list:
              $1: nic11-acc-type
              $2: nic11-ifcname

        An accessibility control condition has triggered, release active call."
    ::= { nicNotificationsPrefix 11 }

nicNotification12 NOTIFICATION-TYPE
    OBJECTS { 
              nic12-acc-info, 
              nic12-ifcname 
            }
    STATUS current
    DESCRIPTION
        "Notification of Event NIC.12

        Message: 'Accessibility control: $1 interface $2'

        Parameters list:
              $1: nic12-acc-info
              $2: nic12-ifcname

        Accessibility control progress information."
    ::= { nicNotificationsPrefix 12 }

nicNotification13 NOTIFICATION-TYPE
    OBJECTS { 
              nic13-ifcname 
            }
    STATUS current
    DESCRIPTION
        "Notification of Event NIC.13

        Message: 'Perform module reset on disconnection interface $1'

        Parameters list:
              $1: nic13-ifcname

        Performs a reset of the Cellular module on disconnection time."
    ::= { nicNotificationsPrefix 13 }

nicNotification14 NOTIFICATION-TYPE
    OBJECTS { 
              nic14-ifcname 
            }
    STATUS current
    DESCRIPTION
        "Notification of Event NIC.14

        Message: 'Module detected with NIC on interface $1'

        Parameters list:
              $1: nic14-ifcname

        A Cellular module with NIC interface has been detected."
    ::= { nicNotificationsPrefix 14 }

nicNotification15 NOTIFICATION-TYPE
    OBJECTS { 
              nic15-ifcname 
            }
    STATUS current
    DESCRIPTION
        "Notification of Event NIC.15

        Message: 'Module released with NIC interface, interface $1'

        Parameters list:
              $1: nic15-ifcname

        A Cellular module with NIC interface has been released."
    ::= { nicNotificationsPrefix 15 }

nicNotification16 NOTIFICATION-TYPE
    OBJECTS { 
              nic16-response, 
              nic16-ifcname 
            }
    STATUS current
    DESCRIPTION
        "Notification of Event NIC.16

        Message: 'Cellular received unsolicited result code: $1 ,on interface $2'

        Parameters list:
              $1: nic16-response
              $2: nic16-ifcname

        A unsolicited result code has been received from cellular base interface."
    ::= { nicNotificationsPrefix 16 }

nicNotification17 NOTIFICATION-TYPE
    OBJECTS { 
              nic17-time, 
              nic17-ifcname 
            }
    STATUS current
    DESCRIPTION
        "Notification of Event NIC.17

        Message: 'Delayed call timer starts: time to call $1 seconds, inteface $2'

        Parameters list:
              $1: nic17-time
              $2: nic17-ifcname

        Start time to make new call due delayed calls is enabled."
    ::= { nicNotificationsPrefix 17 }

nicNotification18 NOTIFICATION-TYPE
    OBJECTS { 
              nic18-ifcname, 
              nic18-result-or-information 
            }
    STATUS current
    DESCRIPTION
        "Notification of Event NIC.18

        Message: 'QMI: interface $1 $2'

        Parameters list:
              $1: nic18-ifcname
              $2: nic18-result-or-information

        QMI procedure."
    ::= { nicNotificationsPrefix 18 }

nicNotification19 NOTIFICATION-TYPE
    OBJECTS { 
              nic19-message 
            }
    STATUS current
    DESCRIPTION
        "Notification of Event NIC.19

        Message: 'Cellular received control information: $1'

        Parameters list:
              $1: nic19-message

        Control information has been received from cellular module."
    ::= { nicNotificationsPrefix 19 }


END
