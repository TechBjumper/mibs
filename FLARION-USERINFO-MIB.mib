-- $Id: FLARION-USERINFO-MIB.txt,v 1.1.2.1 2004/11/01 21:56:19 mkanaka Exp $


FLARION-USERINFO-MIB DEFINITIONS ::= BEGIN

IMPORTS
        MODULE-IDENTITY, OBJECT-TYPE, NOTIFICATION-TYPE,
        IpAddress, TimeTicks, Unsigned32, Counter32
            FROM SNMPv2-SMI

        DisplayString, TruthValue
            FROM SNMPv2-TC

        flarion, FloatAsString
            FROM FLARION-MIB;


rrUserInfo          OBJECT IDENTIFIER ::= { flarion 4 }

usrSiteInfo         OBJECT IDENTIFIER ::= { rrUserInfo 1 }
usrSectorInfo       OBJECT IDENTIFIER ::= { rrUserInfo 2 }


--
-- Site Identity
--
siteIdentity        OBJECT IDENTIFIER ::= { usrSiteInfo 1 }

siteId          OBJECT-TYPE
    SYNTAX      DisplayString
    MAX-ACCESS  read-write
    STATUS      current
    DESCRIPTION "The name given to the basestation by the wireless carrier. The
                siteId is controlled by the carrier."
    ::= { siteIdentity 1 }

siteName        OBJECT-TYPE
    SYNTAX      DisplayString
    MAX-ACCESS  read-write
    STATUS      current
    DESCRIPTION "The site name as chosen by the carrier. The name may be
                derived from the siteId or from the siteCity."
    ::= { siteIdentity 2 }

siteOwner       OBJECT-TYPE
    SYNTAX      DisplayString
    MAX-ACCESS  read-write
    STATUS      current
    DESCRIPTION "The owner of the basestation."
    ::= { siteIdentity 3 }

siteInstallDate OBJECT-TYPE
    SYNTAX      DisplayString
    MAX-ACCESS  read-write
    STATUS      current
    DESCRIPTION "Date of installation of the basestation."
    ::= { siteIdentity 4 }

siteCommissionDate  OBJECT-TYPE
    SYNTAX      DisplayString
    MAX-ACCESS  read-write
    STATUS      current
    DESCRIPTION "Date of completing commissioning of the basestation."
    ::= { siteIdentity 5 }

siteOtherInfo   OBJECT-TYPE
    SYNTAX      DisplayString
    MAX-ACCESS  read-write
    STATUS      current
    DESCRIPTION "This field is reserved to store any information that the
                carrier chooses to use."
    ::= { siteIdentity 6 }


--
-- Site Location
--
siteLocation        OBJECT IDENTIFIER ::= { usrSiteInfo 2 }

siteStreet      OBJECT-TYPE
    SYNTAX      DisplayString
    MAX-ACCESS  read-write
    STATUS      current
    DESCRIPTION "Street address."
    ::= { siteLocation 1 }

siteCity        OBJECT-TYPE
    SYNTAX      DisplayString
    MAX-ACCESS  read-write
    STATUS      current
    DESCRIPTION "City name."
    ::= { siteLocation 2 }

siteCounty      OBJECT-TYPE
    SYNTAX      DisplayString
    MAX-ACCESS  read-write
    STATUS      current
    DESCRIPTION "County (if applicable)."
    ::= { siteLocation 3 }

siteState       OBJECT-TYPE
    SYNTAX      DisplayString
    MAX-ACCESS  read-write
    STATUS      current
    DESCRIPTION "State (if applicable)."
    ::= { siteLocation 4 }

sitePostalLocation  OBJECT-TYPE
    SYNTAX      DisplayString
    MAX-ACCESS  read-write
    STATUS      current
    DESCRIPTION "Zip code or postal code (if applicable)."
    ::= { siteLocation 5 }

siteCountry     OBJECT-TYPE
    SYNTAX      DisplayString
    MAX-ACCESS  read-write
    STATUS      current
    DESCRIPTION "Country."
    ::= { siteLocation 6 }

siteLatitude    OBJECT-TYPE
    SYNTAX      FloatAsString
    MAX-ACCESS  read-write
    STATUS      current
    DESCRIPTION "The site angular distance north or south of the earth's
                equator, measured in degrees along a meridian."
    ::= { siteLocation 7 }

siteLongitude   OBJECT-TYPE
    SYNTAX      FloatAsString
    MAX-ACCESS  read-write
    STATUS      current
    DESCRIPTION "The site angular distance on the earth's surface, measured
                east or west and expressed in degrees."
    ::= { siteLocation 8 }

siteGroundElevation    OBJECT-TYPE
    SYNTAX      FloatAsString
    MAX-ACCESS  read-write
    STATUS      current
    DESCRIPTION "The ground elevation of the site, in feet."
    ::= { siteLocation 9 }


--
-- RF Environment
--
siteRfEnv           OBJECT IDENTIFIER ::= { usrSiteInfo 3 }

siteStructureType   OBJECT-TYPE
    SYNTAX      DisplayString
    MAX-ACCESS  read-write
    STATUS      current
    DESCRIPTION "The method by which the antenna is mounted in the field.
                Possible options include monopole, flagpole, self support,
                water tank, etc."
    ::= { siteRfEnv 1 }

siteAntennaConfig   OBJECT-TYPE
    SYNTAX      DisplayString
    MAX-ACCESS  read-write
    STATUS      current
    DESCRIPTION "Used to indicate if the basestation antennae are configured as:
                    Sectorized - radiates RF energy in 1,2, or 3 sectors

                    Omni - radiates RF power in all directions

                    Simulcast Low Power - radiates RF energy to each antenna
                        sector by splitting the carrier's signal output after
                        the signal is amplified, thus requiring a single power
                        amplifier

                    Simulcast High Power - radiates the same information to
                        each antenna sector by splitting the carrier's signal
                        output prior to amplification, thus requiring multiple
                        power amplifiers."
    ::= { siteRfEnv 2 }

siteNumSectors  OBJECT-TYPE
    SYNTAX      INTEGER (0..3)
    MAX-ACCESS  read-write
    STATUS      current
    DESCRIPTION "This parameter is used to indicate the number of sectors in
                the base station. Options are:
                    0 = omni
                    1 = one sector
                    2 = two sectors
                    3 = three sectors"
    ::= { siteRfEnv 3 }


--
-- Site Connectivity
--
siteConnectivity    OBJECT IDENTIFIER ::= { usrSiteInfo 4 }

siteCluster     OBJECT-TYPE
    SYNTAX      DisplayString
    MAX-ACCESS  read-write
    STATUS      current
    DESCRIPTION "For EMS management purposes, the network may be divided into
                clusters. This field identifies the cluster associated with the
                basestation."
    ::= { siteConnectivity 1 }

siteDomain      OBJECT-TYPE
    SYNTAX      DisplayString
    MAX-ACCESS  read-write
    STATUS      current
    DESCRIPTION "The site domain is used with the siteId to form the hostname
                of the basestation."
    ::= { siteConnectivity 2 }



--
-- Sector Antenna Information
--
sectorAntennaTable  OBJECT-TYPE
    SYNTAX          SEQUENCE OF SectorAntennaEntry
    MAX-ACCESS      not-accessible
    STATUS          current
DESCRIPTION ""
    ::= { usrSectorInfo 1 }

sectorAntennaEntry  OBJECT-TYPE
    SYNTAX          SectorAntennaEntry
    MAX-ACCESS      not-accessible
    STATUS          current
DESCRIPTION ""
    INDEX           { secAntIndex }
    ::= { sectorAntennaTable 1 }

SectorAntennaEntry ::= SEQUENCE {
    secAntIndex             INTEGER,
    secAntName              DisplayString,
    secAntMorphology        DisplayString,
    secAntManufacturer      DisplayString,
    secAntSharing           DisplayString,
    secAntRxDiv             TruthValue,
    secAntSpatialDiv        TruthValue,
    secAntPolarDiv          TruthValue,
    secAntModel             DisplayString
}

secAntIndex     OBJECT-TYPE
    SYNTAX      INTEGER
    MAX-ACCESS  read-only
    STATUS      current
    DESCRIPTION "Sector index."
    ::= { sectorAntennaEntry 1 }

secAntName      OBJECT-TYPE
    SYNTAX      DisplayString
    MAX-ACCESS  read-write
    STATUS      current
    DESCRIPTION "Sector name. For example, alpha, beta, gamme, omni."
    ::= { sectorAntennaEntry 2 }

secAntMorphology    OBJECT-TYPE
    SYNTAX      DisplayString
    MAX-ACCESS  read-write
    STATUS      current
    DESCRIPTION "An indication of the RF classification for the coverage area
                of the sector. Possible values include Rural, Dense Rural,
                Light Suburban, Suburban, Dense Suburban, Light Urban, Urban,
                and Dense Urban."
    ::= { sectorAntennaEntry 3 }

secAntManufacturer  OBJECT-TYPE
    SYNTAX      DisplayString
    MAX-ACCESS  read-write
    STATUS      current
    DESCRIPTION "Name of the manufacturer of the antenna used in this sector."
    ::= { sectorAntennaEntry 4 }

secAntSharing   OBJECT-TYPE
    SYNTAX      DisplayString
    MAX-ACCESS  read-write
    STATUS      current
    DESCRIPTION "Used to indicate and explain if the antenna is shared with
                other basestations or other technologies."
    ::= { sectorAntennaEntry 5 }

secAntRxDiv     OBJECT-TYPE
    SYNTAX      TruthValue
    MAX-ACCESS  read-write
    STATUS      current
    DESCRIPTION "Indicates if two antennae are used in order to obtain
                diversity."
    ::= { sectorAntennaEntry 6 }

secAntSpatialDiv OBJECT-TYPE
    SYNTAX      TruthValue
    MAX-ACCESS  read-write
    STATUS      current
    DESCRIPTION "Indicates if antenna spatial diversity (two antennas physically
                separated) is used."
    ::= { sectorAntennaEntry 7 }

secAntPolarDiv  OBJECT-TYPE
    SYNTAX      TruthValue
    MAX-ACCESS  read-write
    STATUS      current
    DESCRIPTION "Indicates if antenna polarization diversity is used."
    ::= { sectorAntennaEntry 8 }

secAntModel     OBJECT-TYPE
    SYNTAX      DisplayString
    MAX-ACCESS  read-write
    STATUS      current
    DESCRIPTION "The model number of the antenna."
    ::= { sectorAntennaEntry 9 }


--
-- Sector Antenna Characteristics
--
sectorAntennaCharTable  OBJECT-TYPE
    SYNTAX          SEQUENCE OF SectorAntennaCharEntry
    MAX-ACCESS      not-accessible
    STATUS          current
DESCRIPTION ""
    ::= { usrSectorInfo 2 }

sectorAntennaCharEntry  OBJECT-TYPE
    SYNTAX          SectorAntennaCharEntry
    MAX-ACCESS      not-accessible
    STATUS          current
DESCRIPTION ""
    INDEX           { secAntCharIndex }
    ::= { sectorAntennaCharTable 1 }

SectorAntennaCharEntry ::= SEQUENCE {
    secAntCharIndex             INTEGER,
    secAntCharGain              FloatAsString,
    secAntCharHorizontalBw      FloatAsString,
    secAntCharVertcalBw         FloatAsString,
    secAntCharRadOnCenter       INTEGER,
    secAntCharAzimuth           INTEGER,
    secAntCharMechanicalTilt    INTEGER,
    secAntCharElectricalTilt    INTEGER
}

secAntCharIndex OBJECT-TYPE
    SYNTAX      INTEGER
    MAX-ACCESS  read-only
    STATUS      current
    DESCRIPTION "Sector index."
    ::= { sectorAntennaCharEntry 1 }

secAntCharGain  OBJECT-TYPE
    SYNTAX      FloatAsString
    MAX-ACCESS  read-write
    STATUS      current
    DESCRIPTION "The antenna gain in dBd (a measure of how well the antenna
                will send or pick up a radio signal compared to a dipole
                antenna). Valid values are 0 to 100."
    ::= { sectorAntennaCharEntry 2 }

secAntCharHorizontalBw  OBJECT-TYPE
    SYNTAX      FloatAsString
    MAX-ACCESS  read-write
    STATUS      current
    DESCRIPTION "An indication of the RF aperture of the antenna based on the
                1/2 power (3dB) point as measured off the main beam in the
                horizontal plane. This value is used along with 
                sectorAntennaVerticalBw in propagation tools to mask the
                path-loss and model coverage area. Valid values are 0 to 360."
    ::= { sectorAntennaCharEntry 3 }

secAntCharVertcalBw OBJECT-TYPE
    SYNTAX      FloatAsString
    MAX-ACCESS  read-write
    STATUS      current
    DESCRIPTION "An indication of the RF aperture of the antenna based on the
                1/2 power (3dB) point as measured off the main beam in the
                vertical plane. This value is used along with 
                sectorAntennaHorizontalBw in propagation tools to mask the
                path-loss and model coverage area. Valid values are 0 to 180."
    ::= { sectorAntennaCharEntry 4 }

secAntCharRadOnCenter   OBJECT-TYPE
    SYNTAX      INTEGER (1..1000)
    MAX-ACCESS  read-write
    STATUS      current
    DESCRIPTION "This is a measurement of the antenna center line mounting
                height, in feet Above Ground Level (AGL)."
    ::= { sectorAntennaCharEntry 5 }

secAntCharAzimuth   OBJECT-TYPE
    SYNTAX      INTEGER (0..359)
    MAX-ACCESS  read-write
    STATUS      current
    DESCRIPTION "This is a measure of the antenna main-beam orientation with
                respect to true north in the horizontal plane."
    ::= { sectorAntennaCharEntry 6 }

secAntCharMechanicalTilt    OBJECT-TYPE
    SYNTAX      INTEGER (-20..90)
    MAX-ACCESS  read-write
    STATUS      current
    DESCRIPTION "This is a measure of the physical mounting of the antenna with
                respect to plumb (vertical). This value indicates values
                relative to plumb which is assumed to be 0 degrees. Negative
                values would indicate up-tilt, which is occasionally done to
                adjust for excessive electrical tilt."
    ::= { sectorAntennaCharEntry 7 }

secAntCharElectricalTilt    OBJECT-TYPE
    SYNTAX      INTEGER (-20..90)
    MAX-ACCESS  read-write
    STATUS      current
    DESCRIPTION "A measure of the down-tilt designed into the antenna pattern.
                This is typically measured relative to a point at 90 degrees to
                a plumb back plane in the main beam of the antenna. These values
                may be fixed of variable for a given antenna model."
    ::= { sectorAntennaCharEntry 8 }


--
-- Sector LNA Information
--
sectorLnaTable      OBJECT-TYPE
    SYNTAX          SEQUENCE OF SectorLnaEntry
    MAX-ACCESS      not-accessible
    STATUS          current
DESCRIPTION ""
    ::= { usrSectorInfo 3 }

sectorLnaEntry      OBJECT-TYPE
    SYNTAX          SectorLnaEntry
    MAX-ACCESS      not-accessible
    STATUS          current
DESCRIPTION ""
    INDEX           { secLnaIndex }
    ::= { sectorLnaTable 1 }

SectorLnaEntry ::= SEQUENCE {
    secLnaIndex         INTEGER,
    secLnaFilterType    DisplayString,
    secLnaTowerTop      TruthValue
}

secLnaIndex     OBJECT-TYPE
    SYNTAX      INTEGER
    MAX-ACCESS  read-only
    STATUS      current
    DESCRIPTION "Sector index."
    ::= { sectorLnaEntry 1 }

secLnaFilterType OBJECT-TYPE
    SYNTAX      DisplayString
    MAX-ACCESS  read-write
    STATUS      current
    DESCRIPTION "This parameter indicated the type of filter used in the
                LNA/Duplexer unit. It can be simplex (receive only, or duplex
                for transmit and receive)."
    ::= { sectorLnaEntry 2 }

secLnaTowerTop  OBJECT-TYPE
    SYNTAX      TruthValue
    MAX-ACCESS  read-write
    STATUS      current
    DESCRIPTION "Indicates if the LNA is a tower-top mounted type."
    ::= { sectorLnaEntry 3 }


END
