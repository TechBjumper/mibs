-- Teldat, S.A.

                -- Parque Tecnolgico de Madrid

                -- 28760, Tres Cantos (Madrid)

                -- Tlf: +34-918076565

                -- Fax: +34-918076521

                -- e-mail: id@teldat.com


            -- MIB privada de Teldat

            -- Monitorizacin de la calidad de servicio de los interfaces


    -- Historial:
    --      07-02-14    M.A. Pastor     XH 3523. Errors with HP Openview 9.20
    -- 1.2  30-06-10    M.A. Pastor     Compatibilidad con Spectrum
    -- 1.1  05-01-10    N. Moro         Nuevo estadistico 'instant rate'
    -- 1.0  18-06-09    I. Muoz        Implementacin inicial
--------------------------------------------------------------------------------

TELDAT-MON-FEATURES-QOS-MIB DEFINITIONS ::= BEGIN

    IMPORTS
        Counter
            FROM RFC1155-SMI
        OBJECT-TYPE
            FROM RFC-1212
        telProdNpMonFeatures
            FROM TELDAT-SW-STRUCTURE-MIB;


-- Monitorizacin privada de los estadsicos de calidad de servicio de los
-- interfaces del router.

telProdNpMonFeatQos OBJECT IDENTIFIER ::= { telProdNpMonFeatures 9 }


-- Tabla que recoge los estadsicos de calidad de servicio de los interfaces

telProdNpMonFeatQosTable OBJECT-TYPE
    SYNTAX SEQUENCE OF TelProdNpMonFeatQosEntry
    ACCESS not-accessible
    STATUS mandatory
    DESCRIPTION
    "Displays the statistics of traffic for the selected interface. For the
    Frame Relay interface displays statistics of traffic for all circuit classes
    of the interface."
    ::= { telProdNpMonFeatQos 1 }

telProdNpMonFeatQosEntry OBJECT-TYPE
    SYNTAX TelProdNpMonFeatQosEntry
    ACCESS not-accessible
    STATUS mandatory
    DESCRIPTION
    "The table index are: the interface number, the policy map and the class map."
    INDEX { telProdNpMonFeatQosIfc,
            telProdNpMonFeatQosIndexPol,
            telProdNpMonFeatQosIndexClass }
    ::= { telProdNpMonFeatQosTable 1 }

TelProdNpMonFeatQosEntry ::=
    SEQUENCE{
        telProdNpMonFeatQosIfc
            INTEGER,
        telProdNpMonFeatQosIndexPol
            INTEGER,
        telProdNpMonFeatQosIndexClass
            INTEGER,
        telProdNpMonFeatQosClear
            INTEGER,
        telProdNpMonFeatQosAccPkt
            Counter,
        telProdNpMonFeatQosAccByt
            Counter,
        telProdNpMonFeatQosOfferRate
            Counter,
        telProdNpMonFeatQosDropRate
            Counter,
        telProdNpMonFeatQosTime
            Counter,
        telProdNpMonFeatQosInstantRate
            Counter
        }

telProdNpMonFeatQosIfc OBJECT-TYPE
    SYNTAX INTEGER
    ACCESS read-only
    STATUS mandatory
    DESCRIPTION
    "First index: interface number."
    ::= { telProdNpMonFeatQosEntry 1 }

telProdNpMonFeatQosIndexPol OBJECT-TYPE
    SYNTAX INTEGER
    ACCESS read-only
    STATUS mandatory
    DESCRIPTION
    "Second index: policy order within the interface."
    ::= { telProdNpMonFeatQosEntry 2 }

telProdNpMonFeatQosIndexClass OBJECT-TYPE
    SYNTAX INTEGER
    ACCESS read-only
    STATUS mandatory
    DESCRIPTION
    "Third index: class order within the policy."
    ::= { telProdNpMonFeatQosEntry 3 }

telProdNpMonFeatQosClear OBJECT-TYPE
    SYNTAX INTEGER{
        delete(1),
        ok(2),
        error(3),
        undefined(4)
        }
    ACCESS read-write
    STATUS mandatory
    DESCRIPTION
    "Clear command to delete statistics. Enter 1 (delete) to clear
    the counters. In case the counters were correctly deleted, it will
    appear 2 (ok); otherwise it will appear 3 (error). Finally, if the
    counter has been never cleared it will appear 4 (undefined)."
    ::= { telProdNpMonFeatQosEntry 4 }

telProdNpMonFeatQosAccPkt OBJECT-TYPE
    SYNTAX Counter
    ACCESS read-only
    STATUS mandatory
    DESCRIPTION
    "Number of packets accepted on the class map."
    ::= { telProdNpMonFeatQosEntry 5 }

telProdNpMonFeatQosAccByt OBJECT-TYPE
    SYNTAX Counter
    ACCESS read-only
    STATUS mandatory
    DESCRIPTION
    "Number of bytes accepted on the class map."
    ::= { telProdNpMonFeatQosEntry 6 }

telProdNpMonFeatQosOfferRate OBJECT-TYPE
    SYNTAX Counter
    ACCESS read-only
    STATUS mandatory
    DESCRIPTION
    "Rate offered."
    ::= { telProdNpMonFeatQosEntry 7 }

telProdNpMonFeatQosDropRate OBJECT-TYPE
    SYNTAX Counter
    ACCESS read-only
    STATUS mandatory
    DESCRIPTION
    "Discarded packets."
    ::= { telProdNpMonFeatQosEntry 8 }

telProdNpMonFeatQosTime OBJECT-TYPE
    SYNTAX Counter
    ACCESS read-only
    STATUS mandatory
    DESCRIPTION
    "Time for which data is used to compute load statistics."
    ::= { telProdNpMonFeatQosEntry 9 }

telProdNpMonFeatQosInstantRate OBJECT-TYPE
    SYNTAX Counter
    ACCESS read-only
    STATUS mandatory
    DESCRIPTION
    "Instant offered rate."
    ::= { telProdNpMonFeatQosEntry 10 }


END
