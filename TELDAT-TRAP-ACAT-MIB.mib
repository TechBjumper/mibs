-- file automatically created


TELDAT-TRAP-ACAT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


acatTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ACAT event subsystem."
    REVISION "201401200930Z"
    DESCRIPTION "Initial implementation"
        ::= { telEventTraps 225 }


acatEventsGroup	OBJECT IDENTIFIER	::= { acatTrapsMIB 1 }

acatNotifications	OBJECT IDENTIFIER	::= { acatTrapsMIB 2 }
acatNotificationsPrefix	OBJECT IDENTIFIER	::= { acatNotifications 0 }

acatEventObjects1 OBJECT-IDENTITY
    STATUS current
    DESCRIPTION
        "Event ACAT.1
        Group enabled in configuration / has been disabled."
    ::= { acatEventsGroup 1 }

acat1-grp-index OBJECT-TYPE
    SYNTAX Integer32
    MAX-ACCESS accessible-for-notify
    STATUS current
    DESCRIPTION
        "Parameter 'grp-index' in event ACAT.1"
    ::= { acatEventObjects1 1 }

acat1-enable OBJECT-TYPE
    SYNTAX DisplayString
    MAX-ACCESS accessible-for-notify
    STATUS current
    DESCRIPTION
        "Parameter 'enable' in event ACAT.1"
    ::= { acatEventObjects1 2 }

acatEventObjects2 OBJECT-IDENTITY
    STATUS current
    DESCRIPTION
        "Event ACAT.2
        Not enough memory available for reservation."
    ::= { acatEventsGroup 2 }

acat2-module OBJECT-TYPE
    SYNTAX DisplayString
    MAX-ACCESS accessible-for-notify
    STATUS current
    DESCRIPTION
        "Parameter 'module' in event ACAT.2"
    ::= { acatEventObjects2 1 }

acatEventObjects3 OBJECT-IDENTITY
    STATUS current
    DESCRIPTION
        "Event ACAT.3
        An option from a group has been registered/unregistered at an interface to track its state."
    ::= { acatEventsGroup 3 }

acat3-grp-index OBJECT-TYPE
    SYNTAX Integer32
    MAX-ACCESS accessible-for-notify
    STATUS current
    DESCRIPTION
        "Parameter 'grp-index' in event ACAT.3"
    ::= { acatEventObjects3 1 }

acat3-opt-index OBJECT-TYPE
    SYNTAX Integer32
    MAX-ACCESS accessible-for-notify
    STATUS current
    DESCRIPTION
        "Parameter 'opt-index' in event ACAT.3"
    ::= { acatEventObjects3 2 }

acat3-register OBJECT-TYPE
    SYNTAX DisplayString
    MAX-ACCESS accessible-for-notify
    STATUS current
    DESCRIPTION
        "Parameter 'register' in event ACAT.3"
    ::= { acatEventObjects3 3 }

acat3-iface OBJECT-TYPE
    SYNTAX DisplayString
    MAX-ACCESS accessible-for-notify
    STATUS current
    DESCRIPTION
        "Parameter 'iface' in event ACAT.3"
    ::= { acatEventObjects3 4 }

acatEventObjects4 OBJECT-IDENTITY
    STATUS current
    DESCRIPTION
        "Event ACAT.4
        An option from a group has changed its state."
    ::= { acatEventsGroup 4 }

acat4-grp-index OBJECT-TYPE
    SYNTAX Integer32
    MAX-ACCESS accessible-for-notify
    STATUS current
    DESCRIPTION
        "Parameter 'grp-index' in event ACAT.4"
    ::= { acatEventObjects4 1 }

acat4-opt-index OBJECT-TYPE
    SYNTAX Integer32
    MAX-ACCESS accessible-for-notify
    STATUS current
    DESCRIPTION
        "Parameter 'opt-index' in event ACAT.4"
    ::= { acatEventObjects4 2 }

acat4-state OBJECT-TYPE
    SYNTAX DisplayString
    MAX-ACCESS accessible-for-notify
    STATUS current
    DESCRIPTION
        "Parameter 'state' in event ACAT.4"
    ::= { acatEventObjects4 3 }

acatEventObjects5 OBJECT-IDENTITY
    STATUS current
    DESCRIPTION
        "Event ACAT.5
        Consider if a new option should be chosen."
    ::= { acatEventsGroup 5 }

acat5-grp-index OBJECT-TYPE
    SYNTAX Integer32
    MAX-ACCESS accessible-for-notify
    STATUS current
    DESCRIPTION
        "Parameter 'grp-index' in event ACAT.5"
    ::= { acatEventObjects5 1 }

acatEventObjects6 OBJECT-IDENTITY
    STATUS current
    DESCRIPTION
        "Event ACAT.6
        Active priority in a group has been changed."
    ::= { acatEventsGroup 6 }

acat6-grp-index OBJECT-TYPE
    SYNTAX Integer32
    MAX-ACCESS accessible-for-notify
    STATUS current
    DESCRIPTION
        "Parameter 'grp-index' in event ACAT.6"
    ::= { acatEventObjects6 1 }

acat6-active-pri OBJECT-TYPE
    SYNTAX Integer32
    MAX-ACCESS accessible-for-notify
    STATUS current
    DESCRIPTION
        "Parameter 'active-pri' in event ACAT.6"
    ::= { acatEventObjects6 2 }

acatEventObjects7 OBJECT-IDENTITY
    STATUS current
    DESCRIPTION
        "Event ACAT.7
        No option was chosen."
    ::= { acatEventsGroup 7 }

acat7-grp-index OBJECT-TYPE
    SYNTAX Integer32
    MAX-ACCESS accessible-for-notify
    STATUS current
    DESCRIPTION
        "Parameter 'grp-index' in event ACAT.7"
    ::= { acatEventObjects7 1 }

acatEventObjects8 OBJECT-IDENTITY
    STATUS current
    DESCRIPTION
        "Event ACAT.8
        An option from a group has been activated / deactivated."
    ::= { acatEventsGroup 8 }

acat8-grp-index OBJECT-TYPE
    SYNTAX Integer32
    MAX-ACCESS accessible-for-notify
    STATUS current
    DESCRIPTION
        "Parameter 'grp-index' in event ACAT.8"
    ::= { acatEventObjects8 1 }

acat8-opt-index OBJECT-TYPE
    SYNTAX Integer32
    MAX-ACCESS accessible-for-notify
    STATUS current
    DESCRIPTION
        "Parameter 'opt-index' in event ACAT.8"
    ::= { acatEventObjects8 2 }

acat8-activation OBJECT-TYPE
    SYNTAX DisplayString
    MAX-ACCESS accessible-for-notify
    STATUS current
    DESCRIPTION
        "Parameter 'activation' in event ACAT.8"
    ::= { acatEventObjects8 3 }

acatEventObjects9 OBJECT-IDENTITY
    STATUS current
    DESCRIPTION
        "Event ACAT.9
        A group timer has been programmed."
    ::= { acatEventsGroup 9 }

acat9-grp-index OBJECT-TYPE
    SYNTAX Integer32
    MAX-ACCESS accessible-for-notify
    STATUS current
    DESCRIPTION
        "Parameter 'grp-index' in event ACAT.9"
    ::= { acatEventObjects9 1 }

acat9-type OBJECT-TYPE
    SYNTAX DisplayString
    MAX-ACCESS accessible-for-notify
    STATUS current
    DESCRIPTION
        "Parameter 'type' in event ACAT.9"
    ::= { acatEventObjects9 2 }

acat9-seconds OBJECT-TYPE
    SYNTAX Integer32
    MAX-ACCESS accessible-for-notify
    STATUS current
    DESCRIPTION
        "Parameter 'seconds' in event ACAT.9"
    ::= { acatEventObjects9 3 }

acatEventObjects10 OBJECT-IDENTITY
    STATUS current
    DESCRIPTION
        "Event ACAT.10
        A group timer has been stopped."
    ::= { acatEventsGroup 10 }

acat10-grp-index OBJECT-TYPE
    SYNTAX Integer32
    MAX-ACCESS accessible-for-notify
    STATUS current
    DESCRIPTION
        "Parameter 'grp-index' in event ACAT.10"
    ::= { acatEventObjects10 1 }

acat10-type OBJECT-TYPE
    SYNTAX DisplayString
    MAX-ACCESS accessible-for-notify
    STATUS current
    DESCRIPTION
        "Parameter 'type' in event ACAT.10"
    ::= { acatEventObjects10 2 }

acatEventObjects11 OBJECT-IDENTITY
    STATUS current
    DESCRIPTION
        "Event ACAT.11
        A group timer has expired."
    ::= { acatEventsGroup 11 }

acat11-grp-index OBJECT-TYPE
    SYNTAX Integer32
    MAX-ACCESS accessible-for-notify
    STATUS current
    DESCRIPTION
        "Parameter 'grp-index' in event ACAT.11"
    ::= { acatEventObjects11 1 }

acat11-type OBJECT-TYPE
    SYNTAX DisplayString
    MAX-ACCESS accessible-for-notify
    STATUS current
    DESCRIPTION
        "Parameter 'type' in event ACAT.11"
    ::= { acatEventObjects11 2 }

acatEventObjects12 OBJECT-IDENTITY
    STATUS current
    DESCRIPTION
        "Event ACAT.12
        RIP added offset changed / updated at sending/receiving in a group."
    ::= { acatEventsGroup 12 }

acat12-grp-index OBJECT-TYPE
    SYNTAX Integer32
    MAX-ACCESS accessible-for-notify
    STATUS current
    DESCRIPTION
        "Parameter 'grp-index' in event ACAT.12"
    ::= { acatEventObjects12 1 }

acat12-direction OBJECT-TYPE
    SYNTAX DisplayString
    MAX-ACCESS accessible-for-notify
    STATUS current
    DESCRIPTION
        "Parameter 'direction' in event ACAT.12"
    ::= { acatEventObjects12 2 }

acat12-offset OBJECT-TYPE
    SYNTAX Integer32
    MAX-ACCESS accessible-for-notify
    STATUS current
    DESCRIPTION
        "Parameter 'offset' in event ACAT.12"
    ::= { acatEventObjects12 3 }

acatEventObjects13 OBJECT-IDENTITY
    STATUS current
    DESCRIPTION
        "Event ACAT.13
        Default route via gateway has been installed/uninstalled."
    ::= { acatEventsGroup 13 }

acat13-grp-index OBJECT-TYPE
    SYNTAX Integer32
    MAX-ACCESS accessible-for-notify
    STATUS current
    DESCRIPTION
        "Parameter 'grp-index' in event ACAT.13"
    ::= { acatEventObjects13 1 }

acat13-opt-index OBJECT-TYPE
    SYNTAX Integer32
    MAX-ACCESS accessible-for-notify
    STATUS current
    DESCRIPTION
        "Parameter 'opt-index' in event ACAT.13"
    ::= { acatEventObjects13 2 }

acat13-gateway OBJECT-TYPE
    SYNTAX DisplayString
    MAX-ACCESS accessible-for-notify
    STATUS current
    DESCRIPTION
        "Parameter 'gateway' in event ACAT.13"
    ::= { acatEventObjects13 3 }

acat13-installation OBJECT-TYPE
    SYNTAX DisplayString
    MAX-ACCESS accessible-for-notify
    STATUS current
    DESCRIPTION
        "Parameter 'installation' in event ACAT.13"
    ::= { acatEventObjects13 4 }

acatEventObjects14 OBJECT-IDENTITY
    STATUS current
    DESCRIPTION
        "Event ACAT.14
        Dependence of RIP at some IP/iface has been added/removed."
    ::= { acatEventsGroup 14 }

acat14-grp-index OBJECT-TYPE
    SYNTAX Integer32
    MAX-ACCESS accessible-for-notify
    STATUS current
    DESCRIPTION
        "Parameter 'grp-index' in event ACAT.14"
    ::= { acatEventObjects14 1 }

acat14-opt-index OBJECT-TYPE
    SYNTAX Integer32
    MAX-ACCESS accessible-for-notify
    STATUS current
    DESCRIPTION
        "Parameter 'opt-index' in event ACAT.14"
    ::= { acatEventObjects14 2 }

acat14-inia OBJECT-TYPE
    SYNTAX DisplayString
    MAX-ACCESS accessible-for-notify
    STATUS current
    DESCRIPTION
        "Parameter 'inia' in event ACAT.14"
    ::= { acatEventObjects14 3 }

acat14-link OBJECT-TYPE
    SYNTAX DisplayString
    MAX-ACCESS accessible-for-notify
    STATUS current
    DESCRIPTION
        "Parameter 'link' in event ACAT.14"
    ::= { acatEventObjects14 4 }

acatEventObjects15 OBJECT-IDENTITY
    STATUS current
    DESCRIPTION
        "Event ACAT.15
        RIP has been reconfigured from ACAT changing its operation."
    ::= { acatEventsGroup 15 }

acat15-grp-index OBJECT-TYPE
    SYNTAX Integer32
    MAX-ACCESS accessible-for-notify
    STATUS current
    DESCRIPTION
        "Parameter 'grp-index' in event ACAT.15"
    ::= { acatEventObjects15 1 }

acat15-opt-index OBJECT-TYPE
    SYNTAX Integer32
    MAX-ACCESS accessible-for-notify
    STATUS current
    DESCRIPTION
        "Parameter 'opt-index' in event ACAT.15"
    ::= { acatEventObjects15 2 }

acat15-inia OBJECT-TYPE
    SYNTAX DisplayString
    MAX-ACCESS accessible-for-notify
    STATUS current
    DESCRIPTION
        "Parameter 'inia' in event ACAT.15"
    ::= { acatEventObjects15 3 }

acat15-rcv-allow OBJECT-TYPE
    SYNTAX DisplayString
    MAX-ACCESS accessible-for-notify
    STATUS current
    DESCRIPTION
        "Parameter 'rcv-allow' in event ACAT.15"
    ::= { acatEventObjects15 4 }

acat15-rcv-offset OBJECT-TYPE
    SYNTAX Integer32
    MAX-ACCESS accessible-for-notify
    STATUS current
    DESCRIPTION
        "Parameter 'rcv-offset' in event ACAT.15"
    ::= { acatEventObjects15 5 }

acat15-snd-allow OBJECT-TYPE
    SYNTAX DisplayString
    MAX-ACCESS accessible-for-notify
    STATUS current
    DESCRIPTION
        "Parameter 'snd-allow' in event ACAT.15"
    ::= { acatEventObjects15 6 }

acat15-snd-offset OBJECT-TYPE
    SYNTAX Integer32
    MAX-ACCESS accessible-for-notify
    STATUS current
    DESCRIPTION
        "Parameter 'snd-offset' in event ACAT.15"
    ::= { acatEventObjects15 7 }

acatEventObjects16 OBJECT-IDENTITY
    STATUS current
    DESCRIPTION
        "Event ACAT.16
        Cellular related LEDs have been associated to / disassociated from a cellular interface."
    ::= { acatEventsGroup 16 }

acat16-grp-index OBJECT-TYPE
    SYNTAX Integer32
    MAX-ACCESS accessible-for-notify
    STATUS current
    DESCRIPTION
        "Parameter 'grp-index' in event ACAT.16"
    ::= { acatEventObjects16 1 }

acat16-opt-index OBJECT-TYPE
    SYNTAX Integer32
    MAX-ACCESS accessible-for-notify
    STATUS current
    DESCRIPTION
        "Parameter 'opt-index' in event ACAT.16"
    ::= { acatEventObjects16 2 }

acat16-association OBJECT-TYPE
    SYNTAX DisplayString
    MAX-ACCESS accessible-for-notify
    STATUS current
    DESCRIPTION
        "Parameter 'association' in event ACAT.16"
    ::= { acatEventObjects16 3 }

acat16-cell-if OBJECT-TYPE
    SYNTAX DisplayString
    MAX-ACCESS accessible-for-notify
    STATUS current
    DESCRIPTION
        "Parameter 'cell-if' in event ACAT.16"
    ::= { acatEventObjects16 4 }


acatNotification1 NOTIFICATION-TYPE
    OBJECTS { 
              acat1-grp-index, 
              acat1-enable 
            }
    STATUS current
    DESCRIPTION
        "Notification of Event ACAT.1

        Message: 'Group $1 is $2'

        Parameters list:
              $1: acat1-grp-index
              $2: acat1-enable

        Group enabled in configuration / has been disabled."
    ::= { acatNotificationsPrefix 1 }

acatNotification2 NOTIFICATION-TYPE
    OBJECTS { 
              acat2-module 
            }
    STATUS current
    DESCRIPTION
        "Notification of Event ACAT.2

        Message: 'Not enough memory at $1'

        Parameters list:
              $1: acat2-module

        Not enough memory available for reservation."
    ::= { acatNotificationsPrefix 2 }

acatNotification3 NOTIFICATION-TYPE
    OBJECTS { 
              acat3-grp-index, 
              acat3-opt-index,
              acat3-register,
              acat3-iface 
            }
    STATUS current
    DESCRIPTION
        "Notification of Event ACAT.3

        Message: 'Group $1,  option $2. $3 at interface $4 tracking'

        Parameters list:
              $1: acat3-grp-index
              $2: acat3-opt-index
              $3: acat3-register
              $4: acat3-iface

        An option from a group has been registered/unregistered at an interface to track its state."
    ::= { acatNotificationsPrefix 3 }

acatNotification4 NOTIFICATION-TYPE
    OBJECTS { 
              acat4-grp-index, 
              acat4-opt-index,
              acat4-state 
            }
    STATUS current
    DESCRIPTION
        "Notification of Event ACAT.4

        Message: 'Group $1,  option $2. Its state has been set to $3'

        Parameters list:
              $1: acat4-grp-index
              $2: acat4-opt-index
              $3: acat4-state

        An option from a group has changed its state."
    ::= { acatNotificationsPrefix 4 }

acatNotification5 NOTIFICATION-TYPE
    OBJECTS { 
              acat5-grp-index 
            }
    STATUS current
    DESCRIPTION
        "Notification of Event ACAT.5

        Message: 'Group $1. Time to check if a new option should be chosen'

        Parameters list:
              $1: acat5-grp-index

        Consider if a new option should be chosen."
    ::= { acatNotificationsPrefix 5 }

acatNotification6 NOTIFICATION-TYPE
    OBJECTS { 
              acat6-grp-index, 
              acat6-active-pri 
            }
    STATUS current
    DESCRIPTION
        "Notification of Event ACAT.6

        Message: 'Group $1. Active priority set to $2'

        Parameters list:
              $1: acat6-grp-index
              $2: acat6-active-pri

        Active priority in a group has been changed."
    ::= { acatNotificationsPrefix 6 }

acatNotification7 NOTIFICATION-TYPE
    OBJECTS { 
              acat7-grp-index 
            }
    STATUS current
    DESCRIPTION
        "Notification of Event ACAT.7

        Message: 'Group $1. Can not choose any option'

        Parameters list:
              $1: acat7-grp-index

        No option was chosen."
    ::= { acatNotificationsPrefix 7 }

acatNotification8 NOTIFICATION-TYPE
    OBJECTS { 
              acat8-grp-index, 
              acat8-opt-index,
              acat8-activation 
            }
    STATUS current
    DESCRIPTION
        "Notification of Event ACAT.8

        Message: 'Group $1,  option $2. $3'

        Parameters list:
              $1: acat8-grp-index
              $2: acat8-opt-index
              $3: acat8-activation

        An option from a group has been activated / deactivated."
    ::= { acatNotificationsPrefix 8 }

acatNotification9 NOTIFICATION-TYPE
    OBJECTS { 
              acat9-grp-index, 
              acat9-type,
              acat9-seconds 
            }
    STATUS current
    DESCRIPTION
        "Notification of Event ACAT.9

        Message: 'Group $1. Timer of type $2 set to $3 seconds'

        Parameters list:
              $1: acat9-grp-index
              $2: acat9-type
              $3: acat9-seconds

        A group timer has been programmed."
    ::= { acatNotificationsPrefix 9 }

acatNotification10 NOTIFICATION-TYPE
    OBJECTS { 
              acat10-grp-index, 
              acat10-type 
            }
    STATUS current
    DESCRIPTION
        "Notification of Event ACAT.10

        Message: 'Group $1. Timer of type $2 stopped'

        Parameters list:
              $1: acat10-grp-index
              $2: acat10-type

        A group timer has been stopped."
    ::= { acatNotificationsPrefix 10 }

acatNotification11 NOTIFICATION-TYPE
    OBJECTS { 
              acat11-grp-index, 
              acat11-type 
            }
    STATUS current
    DESCRIPTION
        "Notification of Event ACAT.11

        Message: 'Group $1. Timer of type $2 has expired'

        Parameters list:
              $1: acat11-grp-index
              $2: acat11-type

        A group timer has expired."
    ::= { acatNotificationsPrefix 11 }

acatNotification12 NOTIFICATION-TYPE
    OBJECTS { 
              acat12-grp-index, 
              acat12-direction,
              acat12-offset 
            }
    STATUS current
    DESCRIPTION
        "Notification of Event ACAT.12

        Message: 'Group $1. RIP $2 added offset set to $3'

        Parameters list:
              $1: acat12-grp-index
              $2: acat12-direction
              $3: acat12-offset

        RIP added offset changed / updated at sending/receiving in a group."
    ::= { acatNotificationsPrefix 12 }

acatNotification13 NOTIFICATION-TYPE
    OBJECTS { 
              acat13-grp-index, 
              acat13-opt-index,
              acat13-gateway,
              acat13-installation 
            }
    STATUS current
    DESCRIPTION
        "Notification of Event ACAT.13

        Message: 'Group $1, option $2. Default route via gateway at $3 has been $4'

        Parameters list:
              $1: acat13-grp-index
              $2: acat13-opt-index
              $3: acat13-gateway
              $4: acat13-installation

        Default route via gateway has been installed/uninstalled."
    ::= { acatNotificationsPrefix 13 }

acatNotification14 NOTIFICATION-TYPE
    OBJECTS { 
              acat14-grp-index, 
              acat14-opt-index,
              acat14-inia,
              acat14-link 
            }
    STATUS current
    DESCRIPTION
        "Notification of Event ACAT.14

        Message: 'Group $1, option $2. RIP at $3 is $4'

        Parameters list:
              $1: acat14-grp-index
              $2: acat14-opt-index
              $3: acat14-inia
              $4: acat14-link

        Dependence of RIP at some IP/iface has been added/removed."
    ::= { acatNotificationsPrefix 14 }

acatNotification15 NOTIFICATION-TYPE
    OBJECTS { 
              acat15-grp-index, 
              acat15-opt-index,
              acat15-inia,
              acat15-rcv-allow,
              acat15-rcv-offset,
              acat15-snd-allow,
              acat15-snd-offset 
            }
    STATUS current
    DESCRIPTION
        "Notification of Event ACAT.15

        Message: 'Group $1, option $2. RIP at $3 has been reconfigured: receiving $4 (added offset $5), sending $6 (added offset $7)'

        Parameters list:
              $1: acat15-grp-index
              $2: acat15-opt-index
              $3: acat15-inia
              $4: acat15-rcv-allow
              $5: acat15-rcv-offset
              $6: acat15-snd-allow
              $7: acat15-snd-offset

        RIP has been reconfigured from ACAT changing its operation."
    ::= { acatNotificationsPrefix 15 }

acatNotification16 NOTIFICATION-TYPE
    OBJECTS { 
              acat16-grp-index, 
              acat16-opt-index,
              acat16-association,
              acat16-cell-if 
            }
    STATUS current
    DESCRIPTION
        "Notification of Event ACAT.16

        Message: 'Group $1, option $2. Cellular related LEDs have been $3 interface $4'

        Parameters list:
              $1: acat16-grp-index
              $2: acat16-opt-index
              $3: acat16-association
              $4: acat16-cell-if

        Cellular related LEDs have been associated to / disassociated from a cellular interface."
    ::= { acatNotificationsPrefix 16 }


END
