HUAWEI-ETHERNET-OPTICSMODULE-MIB DEFINITIONS ::= BEGIN

		IMPORTS 
			huaweiMgmt			
				FROM HUAWEI-MIB			
			ifIndex, InterfaceIndex
				FROM IF-MIB					
			TimeTicks,OBJECT-TYPE
				FROM SNMPv2-SMI			
			TruthValue, MacAddress, RowStatus, TEXTUAL-CONVENTION
				FROM SNMPv2-TC;

		hwEthernetPort MODULE-IDENTITY
			LAST-UPDATED "200207080900Z"
			ORGANIZATION
				"HAUWEI MIB Standard community
				"
			CONTACT-INFO
				"
			
				"
			DESCRIPTION
				"V01-01-200207080900	
				zengyonggang 26094/huawei, daiyuehua 20365/huawei, tongjian 28021/huawei, yuanminghui 31133/huawei, 
					   qizhenglin 27958/huawei, liwei 24366/huawei, zhoushiyong 10726/huawei lichangcai 28618/huawei, 
					   hebo 16103/huawei, xujinsong 19085/huawei, lvzhenfeng 18230/huawei, fuhongxun 29027/huawei, 
					   dongqing 18889/huawei,lijin 22251/huawei, zhangshilin 28161/huawei, heqingjian 9730/huawei, 
				          liuchenglong 25279/huawei			
			        "
			::= { huaweiMgmt 14 }
		
	
			PortList ::= TEXTUAL-CONVENTION
  				STATUS      current
    				DESCRIPTION
  				"Each octet within this value specifies a set of eight
 				       ports, with the first octet specifying ports 1 through
				       8, the second octet specifying ports 9 through 16, etc.
				        Within each octet, the most significant bit represents
 				       the lowest numbered port, and the least significant bit
 				       represents the highest numbered port.  Thus, each port
 				       of the bridge is represented by a single bit within the
				        value of this object.  If that bit has a value of '1'
				        then that port is included in the set of ports; the port
				        is not included if its bit has a value of '0'."
 			      SYNTAX      OCTET STRING

                hwOpticsModuleInformation OBJECT IDENTIFIER ::= { hwEthernetPort 6 }		
		
		hwOpticsModuleInformationTable OBJECT-TYPE
			SYNTAX SEQUENCE OF HwOpticsModuleInformationEntry
			MAX-ACCESS not-accessible
			STATUS current
			DESCRIPTION
				"   "
			::= { hwOpticsModuleInformation 1 }
			
		hwOpticsModuleInformationEntry OBJECT-TYPE
			SYNTAX HwOpticsModuleInformationEntry
			MAX-ACCESS not-accessible
			STATUS current
			DESCRIPTION
				"    "
			INDEX { ifIndex }
			::= { hwOpticsModuleInformationTable 1 }
			
                HwOpticsModuleInformationEntry ::=
			SEQUENCE { 
				hwOpticsMDIdentifier
					INTEGER,
				hwOpticsMDExtID
					INTEGER,
				hwOpticsMDConnector
					INTEGER,
				hwOpticsMDEncoding
					INTEGER,
				hwOpticsMDBrNominal
					INTEGER,
				hwOpticsMDLength9Micronkm
					INTEGER,
				hwOpticsMDLength9Micron
					INTEGER,
				hwOpticsMDLength50Micron
					INTEGER,
				hwOpticsMDLength62Micron5
					INTEGER,
				hwOpticsMDLengthCopper
					INTEGER,
				hwOpticsMDVendorName
					OCTET STRING,
				hwOpticsMDVendorOUI
					INTEGER,
				hwOpticsMDVendorPN
					OCTET STRING,
			        hwOpticsMDVendorRev
					OCTET STRING,
		                hwOpticsMDWaveLength
					INTEGER,
			        hwOpticsMDCcBase
					INTEGER,
			        hwOpticsMDOptions
					INTEGER,
				hwOpticsMDBrMax
					INTEGER,
				hwOpticsMDBrMin
					INTEGER,
				hwOpticsMDVendorSN
					OCTET STRING,
				hwOpticsMDDateCode
					OCTET STRING,
				hwOpticsMDDiagnosticMonitoringType
					INTEGER,
				hwOpticsMDEnhancedOptions
					INTEGER,
				hwOpticsMDSFF8472Compliance
					INTEGER,
				hwOpticsMDCcExt
					INTEGER,
				hwOpticsMDVendorSpecific
					OCTET STRING
			 }
		
		hwOpticsMDIdentifier OBJECT-TYPE        
			SYNTAX INTEGER
				{
				unknown(1),
				gbic(2),
				solderedtomotherboard(3),
				sfp(4)
				}			          
			MAX-ACCESS read-only                              
			STATUS current                                    
			DESCRIPTION                                       
				" solderedToMotherboard(3):Module/connector soldered to motherboard "     
			::= { hwOpticsModuleInformationEntry 1 }
			
		hwOpticsMDExtID OBJECT-TYPE        
			SYNTAX INTEGER
				{
				notspecifiedornotcompliant(1),
				moddef1(2),
				moddef2(3),
				moddef3(4),
				byserialidonly(5),
				moddef5(6),
				moddef6(7),
				moddef7(8)
				}			          
			MAX-ACCESS read-only                              
			STATUS current                                    
			DESCRIPTION                                       
				" 1 Not specified or not compliant with a defined
                                  MOD-DEF. 
                                  2 GBIC is compliant with MOD-DEF 1
                                  3 GBIC is compliant with MOD-DEF 2
                                  4 GBIC is compliant with MOD-DEF 3
                                  5 GBIC/SFP function is defined by serial ID only
                                  6 GBIC is compliant with MOD-DEF 5
                                  7 GBIC is compliant with MOD-DEF 6
                                  8 GBIC is compliant with MOD-DEF 7
				 "                   
			::= { hwOpticsModuleInformationEntry 2 }
		
		hwOpticsMDConnector OBJECT-TYPE        
			SYNTAX INTEGER
				{
				unknown(1),
				sc(2),
				copperconnector1(3),
				copperconnector2(4),
                                bnctnc(5),
                                coaxialheaders(6),
                                fiberjack(7),
                                lc(8),
                                mtrj(9),
                                mu(10),
                                sg(11),
                                opticalpigtail(12),
                                hssdcii(13),
                                copperpigtail(14),
                                vendorspecific(15)
				}			          
			MAX-ACCESS read-only                              
			STATUS current                                    
			DESCRIPTION                                       
				" 				
				1   Unknown
				2   SC
				3   Fibre Channel Style 1 copper connector
				4   Fibre Channel Style 2 copper connector
                                5   BNC/TNC
                                6   Fibre Channel coaxial headers
                                7   FiberJack
                                8   LC
                                9   MT-RJ
                                10   MU
                                11   SG
                                12   Optical pigtail
                                13   HSSDC II
                                14   Copper Pigtail
                                15   Vendor specific
				 "    
			::= { hwOpticsModuleInformationEntry 3 }

		hwOpticsMDEncoding OBJECT-TYPE        
			SYNTAX INTEGER
				{
				unspecified(1),
				encodingmethod8b10b(2),
				encodingmethod4b5b(3),
				nrz(4),
				manchester(5),
				sonetscrambled(6)
				}			          
			MAX-ACCESS read-only                              
			STATUS current                                    
			DESCRIPTION                                       
				" 	 "           
			::= { hwOpticsModuleInformationEntry 4 }
			
		hwOpticsMDBrNominal OBJECT-TYPE        
			SYNTAX INTEGER							          
			MAX-ACCESS read-only                              
			STATUS current                                    
			DESCRIPTION                                       
				" Nominal bit rate, units of 100 MBits/sec."                   
			::= { hwOpticsModuleInformationEntry 5 }
			
		hwOpticsMDLength9Micronkm OBJECT-TYPE        
			SYNTAX INTEGER							          
			MAX-ACCESS read-only                              
			STATUS current                                    
			DESCRIPTION                                       
				" Link length supported for 9/125 microm fiber, units of km."                   
			::= { hwOpticsModuleInformationEntry 6 }
			
		hwOpticsMDLength9Micron OBJECT-TYPE        
			SYNTAX INTEGER							          
			MAX-ACCESS read-only                              
			STATUS current                                    
			DESCRIPTION                                       
				" Link length supported for 9/125 microm fiber, units of 100 m."                   
			::= { hwOpticsModuleInformationEntry 7 }
			
		hwOpticsMDLength50Micron OBJECT-TYPE        
			SYNTAX INTEGER							          
			MAX-ACCESS read-only                              
			STATUS current                                    
			DESCRIPTION                                       
				" Link length supported for 50/125 microm fiber, units of 10 m."                   
			::= { hwOpticsModuleInformationEntry 8 }
			
		hwOpticsMDLength62Micron5 OBJECT-TYPE        
			SYNTAX INTEGER							          
			MAX-ACCESS read-only                              
			STATUS current                                    
			DESCRIPTION                                       
				" Link length supported for 62.5/125 microm fiber, units of 10 m."                   
			::= { hwOpticsModuleInformationEntry 9 }
			
		hwOpticsMDLengthCopper OBJECT-TYPE        
			SYNTAX INTEGER							          
			MAX-ACCESS read-only                              
			STATUS current                                    
			DESCRIPTION                                       
				" Link length supported for copper, units of meters."                   
			::= { hwOpticsModuleInformationEntry 10 }
			
		hwOpticsMDVendorName OBJECT-TYPE        
			SYNTAX OCTET STRING (SIZE (0..17))							          
			MAX-ACCESS read-only                              
			STATUS current                                    
			DESCRIPTION                                       
				" SFP vendor name (ASCII)."                   
			::= { hwOpticsModuleInformationEntry 11 }
			
		hwOpticsMDVendorOUI OBJECT-TYPE        
			SYNTAX INTEGER							          
			MAX-ACCESS read-only                              
			STATUS current                                    
			DESCRIPTION                                       
				" SFP vendor IEEE company ID."                   
			::= { hwOpticsModuleInformationEntry 12 }
			
		hwOpticsMDVendorPN OBJECT-TYPE        
			SYNTAX OCTET STRING (SIZE (0..17))							          
			MAX-ACCESS read-only                              
			STATUS current                                    
			DESCRIPTION                                       
				" Part number provided by SFP vendor (ASCII)."                   
			::= { hwOpticsModuleInformationEntry 13 }
			
		hwOpticsMDVendorRev OBJECT-TYPE        
			SYNTAX OCTET STRING (SIZE (0..5))							          
			MAX-ACCESS read-only                              
			STATUS current                                    
			DESCRIPTION                                       
				" Revision level for part number provided by vendor (ASCII)."  
			::= { hwOpticsModuleInformationEntry 14 }
			
		hwOpticsMDWaveLength OBJECT-TYPE        
			SYNTAX INTEGER							          
			MAX-ACCESS read-only                              
			STATUS current                                    
			DESCRIPTION                                       
				" Laser wavelength."                   
			::= { hwOpticsModuleInformationEntry 15 }
			
		hwOpticsMDCcBase OBJECT-TYPE        
			SYNTAX INTEGER							          
			MAX-ACCESS read-only                              
			STATUS current                                    
			DESCRIPTION                                       
				" Check code for Base ID Fields (one byte)."                   
			::= { hwOpticsModuleInformationEntry 16 }
			
		hwOpticsMDOptions OBJECT-TYPE        
			SYNTAX INTEGER
				{
                                rateselect(1),
                                txdisableandtheserialoutputdisabled(2),
                                txfault(3),
                                signallossandinvertedfromstandard(4),
                                signallossandasdefined(5)
				}						          
			MAX-ACCESS read-only                              
			STATUS current                                    
			DESCRIPTION                                       
				"                                
				1 RATE-SELECT is implemented
                                2 TX-DISABLE is implemented and disables the serial output.
                                3 TX-FAULT signal implemented. 
                                4 Loss of Signal implemented, signal inverted from standard
                                definition in SFP MSA.
                                5 Loss of Signal implemented, signal as defined in SFP MSA 
				"        
			::= { hwOpticsModuleInformationEntry 17 }
	        
		hwOpticsMDBrMax OBJECT-TYPE        
			SYNTAX INTEGER
			MAX-ACCESS read-only                              
			STATUS current                                    
			DESCRIPTION                                       
				" Upper bit rate margin, units of % "                   
			::= { hwOpticsModuleInformationEntry 18 }
			
		hwOpticsMDBrMin OBJECT-TYPE        
			SYNTAX INTEGER
			MAX-ACCESS read-only                              
			STATUS current                                    
			DESCRIPTION                                       
				"  Lower bit rate margin, units of % "                   
			::= { hwOpticsModuleInformationEntry 19 }
			
		hwOpticsMDVendorSN OBJECT-TYPE        
			SYNTAX OCTET STRING (SIZE (0..17))
			MAX-ACCESS read-only                              
			STATUS current                                    
			DESCRIPTION                                       
				"  Serial number provided by vendor (ASCII) "                   
			::= { hwOpticsModuleInformationEntry 20 }
			
		hwOpticsMDDateCode OBJECT-TYPE        
			SYNTAX OCTET STRING (SIZE (0..9))
			MAX-ACCESS read-only                              
			STATUS current                                    
			DESCRIPTION                                       
				"  Serial number provided by vendor (ASCII) "                   
			::= { hwOpticsModuleInformationEntry 21 }
			
		hwOpticsMDDiagnosticMonitoringType OBJECT-TYPE        
			SYNTAX INTEGER
				{
                                internallycalibrated(1),
                                externallycalibrated(2)
                                }
			MAX-ACCESS read-only                              
			STATUS current                                    
			DESCRIPTION                                       
				" 
				 "     
			::= { hwOpticsModuleInformationEntry 22 }
			
		hwOpticsMDEnhancedOptions OBJECT-TYPE        
			SYNTAX INTEGER
				{
                                forallmonitoredquantities(1), 
                                tx-disable(2),
                                tx-fault(3),
                                rx-los(4),
                                rate-select(5)
                                }
			MAX-ACCESS read-only                              
			STATUS current                                    
			DESCRIPTION                                       
				"
				1 Optional Alarm/warning flags implemented for
                                all monitored quantities 
                                2 Optional Soft TX-DISABLE control and
                                monitoring implemented
                                3 Optional Soft TX-FAULT monitoring
                                implemented
                                4 Optional Soft RX-LOS monitoring
                                implemented
                                5 Optional Soft RATE-SELECT control and
                                monitoring implemented
				  "      
			::= { hwOpticsModuleInformationEntry 23 }
			
		hwOpticsMDSFF8472Compliance OBJECT-TYPE        
			SYNTAX INTEGER
				{
                                undefined(1), 
                                includessff8472(2),
                                tbd(3)
                                }
			MAX-ACCESS read-only                              
			STATUS current                                    
			DESCRIPTION                                       
				"
				1 Not included or undefined.
                                2 ncludes functionality described in Rev 9.3 SFF-8472.
                                3 To Be Determined.
                                	  "
			::= { hwOpticsModuleInformationEntry 24 }
			
		hwOpticsMDCcExt OBJECT-TYPE        
			SYNTAX INTEGER
			MAX-ACCESS read-only                              
			STATUS current                                    
			DESCRIPTION                                       
				"
				Check code for the Extended ID Fields (one byte).
                                	  "
			::= { hwOpticsModuleInformationEntry 25 }
			
		hwOpticsMDVendorSpecific OBJECT-TYPE        
			SYNTAX OCTET STRING (SIZE (0..96))
			MAX-ACCESS read-only                              
			STATUS current                                    
			DESCRIPTION                                       
				"
				32 bytes.
                                	  "
			::= { hwOpticsModuleInformationEntry 26 }

		hwOpticsModuleTransceiverTable OBJECT-TYPE
			SYNTAX SEQUENCE OF HwOpticsModuleTransceiverEntry
			MAX-ACCESS not-accessible
			STATUS current
			DESCRIPTION
				"   "
			::= { hwOpticsModuleInformation 2 }
		
		hwOpticsModuleTransceiverEntry OBJECT-TYPE
			SYNTAX HwOpticsModuleTransceiverEntry
			MAX-ACCESS not-accessible
			STATUS current
			DESCRIPTION
				"    "
			INDEX { ifIndex }
			::= { hwOpticsModuleTransceiverTable 1 }
		
                HwOpticsModuleTransceiverEntry ::=
			SEQUENCE { 
				hwOpticsMDInfinibandComplianceCodes
					INTEGER,
				hwOpticsMDSONETcomplianceCodes
					INTEGER,
				hwOpticsMDGEComplianceCodes
					INTEGER,
				hwOpticsMDLinkLength
					INTEGER,
				hwOpticsMDTransmitterTechnology
					INTEGER,
				hwOpticsMDTransmissionMedia
					INTEGER,
				hwOpticsMDSpeed
					INTEGER
			 }

		hwOpticsMDInfinibandComplianceCodes OBJECT-TYPE
			SYNTAX INTEGER
				{
				sx(1),
				lx(2),
				copperactive(3),
				copperpassive(4)
				}
			MAX-ACCESS read-only
			STATUS current
			DESCRIPTION
				"
				1.1XSX
				2.1XLX
				3.1XCopperActive
				4.1XCopperPassive
     
				"
			::= { hwOpticsModuleTransceiverEntry 1 }
			
		hwOpticsMDSONETcomplianceCodes OBJECT-TYPE
			SYNTAX INTEGER
				{
				oc48longreach(1),
				oc48intermediatereach(2),
				oc48shortreach(3),
				oc12singlemodelongreach(4),
				oc12singlemodeintermediatereach(5),
				oc12multimodeshortreach(6),
				oc3singlemodelongreach(7),
				oc3singlemodeintermediatereach(8),
				oc3multimodeshortreach(9)
				}
			MAX-ACCESS read-only
			STATUS current
			DESCRIPTION
				"     "
			::= { hwOpticsModuleTransceiverEntry 2 }
			
		hwOpticsMDGEComplianceCodes OBJECT-TYPE
			SYNTAX INTEGER
				{
				t(1),
				cx(2),
				lx(3),
				sx(4)
				}
			MAX-ACCESS read-only
			STATUS current
			DESCRIPTION
				"   
				1.1000BASE-T
				2.1000BASE-CX
				3.1000BASE-LX
				4.1000BASE-SX
				  "
			::= { hwOpticsModuleTransceiverEntry 3 }
			
		hwOpticsMDLinkLength OBJECT-TYPE
			SYNTAX INTEGER
				{
				verylongdistance(1),
				shortdistance(2),
				intermediatedistance(3),
				longdistance(4)
				}
			MAX-ACCESS read-only
			STATUS current
			DESCRIPTION
				"     "
			::= { hwOpticsModuleTransceiverEntry 4 }

		hwOpticsMDTransmitterTechnology OBJECT-TYPE
			SYNTAX INTEGER
				{
				longwaveLaser(1),
				electricalInterenclosure(2),
				shortwaveLaser(3)
				}
			MAX-ACCESS read-only
			STATUS current
			DESCRIPTION
				"  
				1.longwave laser
				2.electrical inter-enclosure
				3.shortwave laser 
				   "
			::= { hwOpticsModuleTransceiverEntry 5 }
			
		hwOpticsMDTransmissionMedia OBJECT-TYPE
			SYNTAX INTEGER
				{
				twinaxialpair(1),
				shieldedtwistedpair(2),
				miniaturecoax(3),
				videocoax(4),
				multimode62m5(5),
				multimode50m(6),
				singlemode(7)
				}
			MAX-ACCESS read-only
			STATUS current
			DESCRIPTION
				"    
				1 twin axial pair 
                                2 shielded twisted pair 
                                3 miniature coax 
                                4 video coax 
                                5 multi-mode, 62.5m 
                                6 multi-mode, 50 m 
                                7 single mode 
				 "
			::= { hwOpticsModuleTransceiverEntry 6 }
			
		hwOpticsMDSpeed OBJECT-TYPE
			SYNTAX INTEGER
				{
				speed400mbytespersec(1),
				speed200mbytespersec(2),
				speed100mbytespersec(3)
				}
			MAX-ACCESS read-only
			STATUS current
			DESCRIPTION
				"     "
			::= { hwOpticsModuleTransceiverEntry 7 }
			

			
	END
