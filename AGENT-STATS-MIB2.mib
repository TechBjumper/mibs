AGENT-STATS-MIB2 DEFINITIONS ::= BEGIN

IMPORTS
    enterprises, MODULE-IDENTITY, Integer32, Counter32
        FROM SNMPv2-SMI;

agentStats MODULE-IDENTITY
    LAST-UPDATED "0609201255Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        "The Agent Statistics module monitors the health of the agent installed on the local host."
    ::= { modules 30 }
modules	OBJECT IDENTIFIER ::= { agent 2 }

agent	OBJECT IDENTIFIER ::= { sunsymon 2 }

sunsymon	OBJECT IDENTIFIER ::= { prod 12 }

prod	OBJECT IDENTIFIER ::= { sun 2 }

sun	OBJECT IDENTIFIER ::= { enterprises 42 }


objects	OBJECT IDENTIFIER ::= { agentStats 1 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

toeCount OBJECT-TYPE
    SYNTAX      Integer32
    MAX-ACCESS  read-only
    STATUS      current
    DESCRIPTION
                "The number of toe objects"
    ::= { objects 1 }

bobCount OBJECT-TYPE
    SYNTAX      Integer32
    MAX-ACCESS  read-only
    STATUS      current
    DESCRIPTION
                "The number of binary object buffers"
    ::= { objects 2 }

commands	OBJECT IDENTIFIER ::= { agentStats 2 }

cmdTotal OBJECT-TYPE
    SYNTAX      Counter32
    MAX-ACCESS  read-only
    STATUS      current
    DESCRIPTION
                "The number of commands that have been executed"
    ::= { commands 1 }

cmdRate OBJECT-TYPE
    SYNTAX      DisplayString
    UNITS       "/sec"
    MAX-ACCESS  read-only
    STATUS      current
    DESCRIPTION
                "The number of commands executed per second"
    ::= { commands 2 }

transactions	OBJECT IDENTIFIER ::= { agentStats 3 }

transTotal OBJECT-TYPE
    SYNTAX      Counter32
    MAX-ACCESS  read-only
    STATUS      current
    DESCRIPTION
                "The number of transactions performed by the agent"
    ::= { transactions 1 }

transRate OBJECT-TYPE
    SYNTAX      DisplayString
    UNITS       "/sec"
    MAX-ACCESS  read-only
    STATUS      current
    DESCRIPTION
                "The number of transactions performed by the agent per second"
    ::= { transactions 2 }

procstats	OBJECT IDENTIFIER ::= { agentStats 4 }

pid OBJECT-TYPE
    SYNTAX      Integer32
    MAX-ACCESS  read-only
    STATUS      current
    DESCRIPTION
                "Process ID"
    ::= { procstats 1 }

id OBJECT-TYPE
    SYNTAX      DisplayString
    MAX-ACCESS  read-only
    STATUS      current
    DESCRIPTION
                "The name of the process"
    ::= { procstats 2 }

name OBJECT-TYPE
    SYNTAX      DisplayString
    MAX-ACCESS  read-only
    STATUS      current
    DESCRIPTION
                "The name of the process"
    ::= { procstats 3 }

info OBJECT-TYPE
    SYNTAX      DisplayString
    MAX-ACCESS  read-only
    STATUS      current
    DESCRIPTION
                "The status of the process"
    ::= { procstats 4 }

state OBJECT-TYPE
    SYNTAX      DisplayString
    MAX-ACCESS  read-only
    STATUS      current
    DESCRIPTION
                "The state of the process"
    ::= { procstats 5 }

uid OBJECT-TYPE
    SYNTAX      Integer32
    MAX-ACCESS  read-only
    STATUS      current
    DESCRIPTION
                "The user id of the process"
    ::= { procstats 6 }

size OBJECT-TYPE
    SYNTAX      Integer32
    UNITS       " KB"
    MAX-ACCESS  read-only
    STATUS      current
    DESCRIPTION
                "The total size of the process"
    ::= { procstats 7 }

rss OBJECT-TYPE
    SYNTAX      Integer32
    UNITS       " KB"
    MAX-ACCESS  read-only
    STATUS      current
    DESCRIPTION
                "The resident size of the process"
    ::= { procstats 8 }

starttime OBJECT-TYPE
    SYNTAX      Integer32
    UNITS       "sec"
    MAX-ACCESS  read-only
    STATUS      current
    DESCRIPTION
                "The startup time of the process in seconds since January  1, 1970"
    ::= { procstats 9 }

startdatestring OBJECT-TYPE
    SYNTAX      DisplayString
    MAX-ACCESS  read-only
    STATUS      current
    DESCRIPTION
                "The startup date of the process"
    ::= { procstats 10 }

starttimestring OBJECT-TYPE
    SYNTAX      DisplayString
    MAX-ACCESS  read-only
    STATUS      current
    DESCRIPTION
                "The startup time of the process"
    ::= { procstats 11 }

cputime OBJECT-TYPE
    SYNTAX      Integer32
    UNITS       "sec"
    MAX-ACCESS  read-only
    STATUS      current
    DESCRIPTION
                "The CPU time used by the process"
    ::= { procstats 12 }

pctcputime OBJECT-TYPE
    SYNTAX      DisplayString
    UNITS       "%"
    MAX-ACCESS  read-only
    STATUS      current
    DESCRIPTION
                "The percentage of CPU time used by the process"
    ::= { procstats 13 }

context OBJECT-TYPE
    SYNTAX      Integer32
    MAX-ACCESS  read-only
    STATUS      current
    DESCRIPTION
                "The context switches of the process"
    ::= { procstats 14 }

syscalls OBJECT-TYPE
    SYNTAX      Integer32
    MAX-ACCESS  read-only
    STATUS      current
    DESCRIPTION
                "The system calls made by the process"
    ::= { procstats 15 }

command OBJECT-TYPE
    SYNTAX      DisplayString
    MAX-ACCESS  read-only
    STATUS      current
    DESCRIPTION
                "The command line of the process"
    ::= { procstats 16 }

totalstats	OBJECT IDENTIFIER ::= { agentStats 5 }

totalCount OBJECT-TYPE
    SYNTAX      Integer32
    MAX-ACCESS  read-only
    STATUS      current
    DESCRIPTION
                "The Number of Agent and Child Processes"
    ::= { totalstats 1 }

totalSize OBJECT-TYPE
    SYNTAX      Integer32
    UNITS       " KB"
    MAX-ACCESS  read-only
    STATUS      current
    DESCRIPTION
                "The Total Virtual Size of Agent and Children"
    ::= { totalstats 2 }

totalRss OBJECT-TYPE
    SYNTAX      Integer32
    UNITS       " KB"
    MAX-ACCESS  read-only
    STATUS      current
    DESCRIPTION
                "The Total Res Size of Agent and Children"
    ::= { totalstats 3 }
END
