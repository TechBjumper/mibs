--  =======================================================================
--  File        : rt-cfg.mib
--  Description : Private MIB for Linux Router
--  By          : Yaron, Sharon, Alon & Alex & Yakov
--              :
--  Log         : $Log: rt-cfg.mib,v $
--  Log         : Revision 1.13.16.3  2005/02/22 09:09:15  olga
--  Log         : Support of SNMP MIB for VPLS Table
--  Log         : ======================================
--  Log         : Files:
--  Log         :  common - uid_if.h, ui_comdef.h;
--  Log         :  router - sif.c, ar_int_vif.h, vif_type.h, ui_if.c, ui_if.h;
--  Log         :  zebos5 - if.c, if.h, snmp_misc.c, snmp_misc.h, nsm_interface.c,
--  Log         : 	  nsm_mpls_cli.c, nsm_mpls_snmp.c, nsm_mpls_vc.h, nsm_snmp_priv.h,
--  Log         : 	  nsm_vpls.c, oaVplsConfigGen.c, oaVplsConfigGen.h,
--  Log         : 	  oaVplsPeerTable.c, oaVplsPeerTable.h, oaVplsTable.c,
--  Log         : 	  oaVplsTable.h, oaVplsVifTable.c, oaVplsVifTable.h, cli_vlan.c;
--  Log         : ucd-snmp-2 - build-script, oaSubscriberTable.c, nbRtAccVifPortTable.c,
--  Log         : 	  nbRtAccVifTable.c, nbVifTable.c, vif_snmp.h, mibs/Makefile.in,
--  Log         : 	  oaSubscr.mib, oaVpls.mib, rt-cfg.mib;
--  Log         :
--  Log         : Revision 1.13.16.2  2005/01/10 06:50:18  olga
--  Log         : Support of SNMP MIB forPort Tag outbound Table and for Police Action
--  Log         : =====================================================================
--  Log         : Tables nbRtPortTagTable, nbRtActionListTable, nbRtPoliceActionTable,
--  Log         : nbRtPoliceRateLimitTable, nbRtPoliceActionVifTable are added.
--  Log         :
--  Log         : Revision 1.13.16.1  2005/01/09 08:49:34  olga
--  Log         : Support of SNMP MIB for DiffServ Mapping profiles
--  Log         : =========================================================
--  Log         : Files:
--  Log         :  common - uid_cmd.c, uid_cmd.h, uid_srv_cmd.c, uid_srv_cmd.h;
--  Log         :  zebos5 - cli_system.c;
--  Log         :  router - sif.c, ssys.c;
--  Log         :  ucd-snmp-2 - nbase.h, utility.c, utility.h, rt-cfg.mib,
--  Log         : 	      nbRtDiffServDscpMapPrflTable.c, nbRtDiffServDscpMapPrflTable.h,
--  Log         : 	      nbRtDiffServDscpMapTable.c, nbRtDiffServDscpMapTable.h,
--  Log         : 	      nbRtDiffServVptMapPrflTable.c, nbRtDiffServVptMapPrflTable.h,
--  Log         : 	      nbRtDiffServVptMapTable.c, nbRtDiffServVptMapTable.h,
--  Log         : 	      nbRtDiffServTable.c, nbVifTable.c.
--  Log         :
--  Log         : Revision 1.12  2003/02/19 15:16:28  alex
--  Log         : New objects nbVifDescr & nbVifLastChange in
--  Log         : the nbVifTable
--  Log         :
--  Log         : Revision 1.11  2003/01/07 12:56:56  pavel
--  Log         : Yakov requests.
--  Log         :
--  Log         : Revision 1.10  2002/12/04 09:11:29  alex
--  Log         : Minor changes in nbRtVifDiffServRateLimitTable
--  Log         :
--  Log         : Revision 1.9  2002/12/03 09:34:47  pavel
--  Log         : ADDED: to tables  nbRtAccVifTable and nbRtAccVifPortTable counters in the form: 1. blocks: 1 = 64K bytes; 2. Counters 64 bit are divided to High and Low parts.
--  Log         :
--  Log         : Revision 1.8  2002/12/02 14:40:35  alex
--  Log         : New structure of RateLimitTable
--  Log         :
--  Log         : Revision 1.7  2002/12/02 09:49:13  pavel
--  Log         : New var RED was added.
--  Log         :
--  Log         : Revision 1.6  2002/11/25 15:58:43  pavel
--  Log         : SNMP support of the Accounting per Vif per Port.
--  Log         :
--  Log         : Revision 1.5  2002/11/24 13:20:01  alex
--  Log         : nbRtVifDiffServRateLimitTable has been changed
--  Log         :
--  Log         : Revision 1.4  2002/11/21 13:55:58  alex
--  Log         : 1. AccCounter inseerted
--  Log         : 2. SubcsriberId TEXTUAL CONVERSION has been  deleted
--  Log         : 3. nbRtDiffServEntry indexes have been redisigned
--  Log         :
--  Log         : Revision 1.3  2002/11/17 13:58:10  alex
--  Log         : 1. DiffServ (modes & rate limit)
--  Log         : 2. Accounting
--  Log         :
--  Log         : Revision 1.2  2002/06/18 07:35:31  alex
--  Log         : New possible values for nbVifType: bridge, loopback & dummy
--  Log         :
--  Log         : Revision 1.1.1.1  2002/03/19 13:41:57  alex
--  Log         : Version 4.2.3
--  Log         :
--  Log         : Revision 1.1.1.1  2002/03/10 11:52:44  alex
--  Log         : Version 4.2.3 (For CERT report reasons)
--  Log         :
--  Log         : Revision 1.9  2001/01/10 11:51:52  alex
--  Log         : Merged from branch
--  Log         :
--  Log         : Revision 1.7.6.2  2001/01/08 15:38:07  alex
--  Log         : Description for TAG limits
--  Log         :
--  Log         : Revision 1.8  2001/01/03 11:51:14  alex
--  Log         : Tagging in Vif & Fib tables
--  Log         :
--  =======================================================================
--
--
-- Copyright (c) 1999 NBase-Xyplex.  All Rights Reserved.
--
--
-- Reproduction of this document is authorized on condition that this
-- copyright notice is included.  This NBase-Xyplex SNMP MIB Specification
-- embodies NBase-Xyplex's proprietary intellectual property.  NBase-Xyplex
-- retains all title and ownership in the specification, including any
-- revisions.
--
-- It is NBase-Xyplex's intent to encourage the widespread use of this
-- specification in connection with the management of NBase-Xyplex's
-- products. NBase-Xyplex grants vendor, end-users, and other interested
-- parties a non-exclusive license to use this specification in
-- connection with the management of NBase-Xyplex's products.
--
-- This specification is supplied "AS IS," and NBase-Xyplex makes no
-- warranty, either express or implied, as to the use, operation,
-- condition, or performance of the specification.
--
-- Copyright text courtesy of NBase-Xyplex
--
-- If you have any questions about this MIB, please call NBase-Xyplex
-- Technical Support Center at 1-800-858-7815 from inside USA or
-- 1-818-773-0900 from outside USA.
--
--
-- NBase-Xyplex retains the right to change this MIB without notification.
--

RT-CFG-MIB DEFINITIONS ::= BEGIN

        IMPORTS
                Counter32, Counter64, enterprises,
                IpAddress,TimeTicks     FROM SNMPv2-SMI
                DisplayString,ifIndex   FROM RFC1213-MIB
                OBJECT-TYPE             FROM RFC-1212
                TRAP-TYPE               FROM RFC-1215;


        MacAddress ::=  OCTET STRING(SIZE(6))

        ActionListName ::=  DisplayString(SIZE(1..20))

        DirectionType ::= INTEGER
            {
             other       (1),
             ingress     (2),
             egress      (3)
            }

        AccountCouter ::= Counter32
        AccountCounter64 ::= Counter64

-- ************************************************************
-- NBase Object Identifier Definition
-- ************************************************************

nbase              OBJECT IDENTIFIER ::= { enterprises 629 }
nbSwitchG1         OBJECT IDENTIFIER ::= { nbase 1 }
nbSwitchG1Il       OBJECT IDENTIFIER ::= { nbSwitchG1 50}

-- GROUPS for Layer-3 Interface
nbRouterConfig     OBJECT IDENTIFIER ::= { nbSwitchG1Il 12}

nbRtConfigGen  OBJECT IDENTIFIER ::= { nbRouterConfig 1 }

nbRtDevDiffServMode       OBJECT-TYPE
                SYNTAX  INTEGER
                {
                 other          (1),
                 none           (2),
                 byTOS          (3),
                 byTag          (4)
                }
                ACCESS  read-write
                STATUS  mandatory
                DESCRIPTION
                "The Global DiffServ mode of the Router."
                ::= { nbRtConfigGen 1 }

nbRtDevDiffServMappingSupport       OBJECT-TYPE
                SYNTAX  INTEGER
                {
                 notSupported   (1),
                 supported      (2)
                }
                ACCESS  read-only
                STATUS  mandatory
                DESCRIPTION
                "The DiffServ Mapping feature support."
                ::= { nbRtConfigGen 2 }

-- ***********************************************************************
-- Objects in the Device's Virtual Interfaces Table (old)
-- ***********************************************************************
        
nbRtVifTable OBJECT-TYPE
        SYNTAX  SEQUENCE OF NbRtVifEntry
        ACCESS  not-accessible
        STATUS  mandatory
        DESCRIPTION
        "."
        ::= { nbRouterConfig 2 }

nbRtVifEntry  OBJECT-TYPE
        SYNTAX  NbRtVifEntry
        ACCESS  not-accessible
        STATUS  mandatory
        DESCRIPTION
        "The entries (records)."
        INDEX { nbRtVifId }
        ::= { nbRtVifTable 1 }
        
NbRtVifEntry ::= SEQUENCE {
        nbRtVifId           DisplayString,
        nbRtVifIpAddress    IpAddress,
        nbRtVifMask         IpAddress,
        nbRtVifProtocol     INTEGER,
        nbRtVifName         DisplayString,
        nbRtVifPortList     OCTET STRING,
        nbRtVifMac          MacAddress,
        nbRtVifAdminStatus  INTEGER,
        nbRtVifConfigType   INTEGER,
        nbRtVifSecurity     INTEGER,
        nbRtVifIsTagged     INTEGER,
        nbRtVifTag          INTEGER
        }

nbRtVifId      OBJECT-TYPE
        SYNTAX  DisplayString
        ACCESS  read-only
        STATUS  mandatory
        DESCRIPTION
        "For example 'vif7' or 'vif11:3' (last case if for alias)."
        ::= { nbRtVifEntry 1 }
       
nbRtVifIpAddress   OBJECT-TYPE
        SYNTAX  IpAddress
        ACCESS  read-write
        STATUS  mandatory
        DESCRIPTION
        "."
        ::= { nbRtVifEntry 2 }

nbRtVifMask        OBJECT-TYPE
        SYNTAX  IpAddress
        ACCESS  read-write
        STATUS  mandatory
        DESCRIPTION
        "."
        ::= { nbRtVifEntry 3 }

nbRtVifProtocol    OBJECT-TYPE
        SYNTAX  INTEGER
            {
              other      (1),
              ipV4IF     (2),
              ipxIF      (3),
              portsIF    (4)
            }
        ACCESS  read-write
        STATUS  mandatory
        DESCRIPTION
        "The routing mechanism via which this route was learned."
        ::= { nbRtVifEntry 4 }

nbRtVifName        OBJECT-TYPE
        SYNTAX  DisplayString
        ACCESS  read-write
        STATUS  mandatory
        DESCRIPTION
        "The name of this group (can be setted by the Manager)."
        ::= { nbRtVifEntry 5}
                
nbRtVifPortList    OBJECT-TYPE
        SYNTAX  OCTET STRING
        ACCESS  read-write
        STATUS  mandatory
        DESCRIPTION
        "."
        ::= { nbRtVifEntry 6 }

nbRtVifMac      OBJECT-TYPE
        SYNTAX  MacAddress
        ACCESS  read-write
        STATUS  mandatory
        DESCRIPTION
        "."
        ::= { nbRtVifEntry 7 }

nbRtVifAdminStatus OBJECT-TYPE
        SYNTAX  INTEGER
        {
         valid      (1),
         invalid    (2),
         create     (4)
        }
        ACCESS  read-write
        STATUS  mandatory
        DESCRIPTION
        "Use 'valid' (1) value by
         ADDind new Entry or EDITting of existing Entry.
         Use 'inValid' (2) value by
         DELETting of existing Entry."
        ::= { nbRtVifEntry 8 }

nbRtVifConfigType  OBJECT-TYPE
        SYNTAX  INTEGER
        {
         auto       (1),
         manual     (2)
        }
        ACCESS  read-write
        STATUS  mandatory
        DESCRIPTION
        "Wether we want 'auto' configuration or not."
        ::= { nbRtVifEntry 9 }

nbRtVifSecurity  OBJECT-TYPE
                SYNTAX  INTEGER
                {
                 other      (1),
                 unsecure   (2),
                 secure     (3)
                }
                ACCESS  read-write
                STATUS  mandatory
                DESCRIPTION
                "."
                ::= { nbRtVifEntry 10 }

nbRtVifIsTagged  OBJECT-TYPE
                SYNTAX  INTEGER
                {
                 no       (0),
                 yes      (1)
                }
                ACCESS  read-write
                STATUS  mandatory
                DESCRIPTION
                "."
                ::= { nbRtVifEntry 15 }

nbRtVifTag     OBJECT-TYPE
               SYNTAX  INTEGER ( 0..4080 )
               ACCESS  read-write
               STATUS  mandatory
               DESCRIPTION
               "If nbRtVifIsTagged=yes(1) this field may not be 0;
                else it may have any value.
                Important: actual upper limit is 4080 - 2 * ports_capacity"
               ::= { nbRtVifEntry 16 }

-- ***********************************************************************
-- Device's Virtual Interface Group of Objects (new)
-- ***********************************************************************
        
nbRtVifGroup    OBJECT IDENTIFIER ::= { nbRouterConfig 3 }

nbVifTableSize  OBJECT-TYPE
        SYNTAX  INTEGER 
        ACCESS  read-only
        STATUS  mandatory
        DESCRIPTION
        "The number of Entries in the VIF Table.
         Value = 0 says, that VIF Table is not supported."
        ::= { nbRtVifGroup 1 }

-- ***********************************************************************
-- This table describes the limits for devices number of interafces of all
-- types.
-- ***********************************************************************
        
nbVifDeviceLimitTable OBJECT-TYPE
                SYNTAX  SEQUENCE OF NbVifDeviceLimitEntry
                ACCESS  not-accessible
                STATUS  mandatory
                DESCRIPTION
                "."
                ::= { nbRtVifGroup 2 }

nbVifDeviceLimitEntry OBJECT-TYPE
                SYNTAX  NbVifDeviceLimitEntry
                ACCESS  not-accessible
                STATUS  mandatory
                DESCRIPTION
                "The Entries (records)."
                INDEX { nbVifLimitType }
                ::= { nbVifDeviceLimitTable 1 }

NbVifDeviceLimitEntry   ::= SEQUENCE {
        nbVifLimitType          INTEGER,
        nbVifDevNoMin           INTEGER,
        nbVifDevNoMax           INTEGER,
        nbVifDevNoFirstEmpty    INTEGER
        }

nbVifLimitType   OBJECT-TYPE
                 SYNTAX INTEGER
                   {
                    other         (1),
                    lanEthernet   (2),
                    wanPPP        (3),
                    wanFrameRelay (4)
                   }
                 ACCESS read-only
                 STATUS mandatory
                 DESCRIPTION
                 "Type of the interface; (index # 1 of the Table)."
                 ::= { nbVifDeviceLimitEntry 1 }

nbVifDevNoMin    OBJECT-TYPE
                 SYNTAX INTEGER
                 ACCESS read-only
                 STATUS mandatory
                 DESCRIPTION
                 "Minimum valid Value of [nbVifDevNo] Object for the
                  corresponding Value of the [nbVifType] interface Type."
                 ::= { nbVifDeviceLimitEntry 2 }

nbVifDevNoMax    OBJECT-TYPE
                 SYNTAX INTEGER
                 ACCESS read-only
                 STATUS mandatory
                 DESCRIPTION
                 "Maximum valid Value of [nbVifDevNo] Object for the
                  corresponding Value of the [nbVifType] interface Type."
                 ::= { nbVifDeviceLimitEntry 3 }

nbVifDevNoFirstEmpty    OBJECT-TYPE
                 SYNTAX INTEGER
                 ACCESS read-only
                 STATUS mandatory
                 DESCRIPTION
                 "Valid 'First empty' Value of [nbVifDevNo] Object for the
                  corresponding Value of the [nbVifType] interface Type."
                 ::= { nbVifDeviceLimitEntry 4 }

-- ***********************************************************************
-- This table describes the limits for alias devices number of interafces
-- of all types per primary interface
-- ***********************************************************************
        
nbVifAliasDLimitTable OBJECT-TYPE
                SYNTAX  SEQUENCE OF NbVifAliasDLimitEntry
                ACCESS  not-accessible
                STATUS  mandatory
                DESCRIPTION
                "."
                ::= { nbRtVifGroup 3 }

nbVifAliasDLimitEntry OBJECT-TYPE
                SYNTAX  NbVifAliasDLimitEntry
                ACCESS  not-accessible
                STATUS  mandatory
                DESCRIPTION
                "The Entries (records)."
                INDEX { nbVifAliasLimitType , nbVifAliasLimitDevNo }
                ::= { nbVifAliasDLimitTable 1 }

NbVifAliasDLimitEntry   ::= SEQUENCE {
                nbVifAliasLimitType               INTEGER,
                nbVifAliasLimitDevNo              INTEGER,
                nbVifAliasLimitDevAliasMin        INTEGER,
                nbVifAliasLimitDevAliasMax        INTEGER,
                nbVifAliasLimitDevAliasFirstEmpty INTEGER
                }

nbVifAliasLimitType          OBJECT-TYPE
                SYNTAX INTEGER
                {
                 other          (1),
                 lanEthernet    (2),
                 wanPPP         (3),
                 wanFrameRelay  (4)
                }
                ACCESS read-only
                STATUS mandatory
                DESCRIPTION
                "Type of the interface; (index # 1 of the Table)."
                ::= { nbVifAliasDLimitEntry 1 }

nbVifAliasLimitDevNo           OBJECT-TYPE
                SYNTAX INTEGER
                ACCESS read-only
                STATUS mandatory
                DESCRIPTION
                "VIF Device Number; (index #2 of the table)."
                ::= { nbVifAliasDLimitEntry 2 }

nbVifAliasLimitDevAliasMin           OBJECT-TYPE
                SYNTAX INTEGER
                ACCESS read-only
                STATUS mandatory
                DESCRIPTION
                 "Minimum valid Value of [nbVifAliasDev] Object for the
                  corresponding Values of the [nbVifType] interface Type
                  and [nbVifDevNo] Device Number."
                ::= { nbVifAliasDLimitEntry 3 }

nbVifAliasLimitDevAliasMax           OBJECT-TYPE
                SYNTAX INTEGER
                ACCESS read-only
                STATUS mandatory
                DESCRIPTION
                 "Maximum valid Value of [nbVifAliasDev] Object for the
                  corresponding Values of the [nbVifType] interface Type
                  and [nbVifDevNo] Device Number."
                ::= { nbVifAliasDLimitEntry 4 }

nbVifAliasLimitDevAliasFirstEmpty    OBJECT-TYPE
                SYNTAX INTEGER
                ACCESS read-only
                STATUS mandatory
                DESCRIPTION
                 "Valid 'First empty' Value of [nbVifAliasDev] Object for the
                  corresponding Values of the [nbVifType] interface Type
                  and [nbVifDevNo] Device Number."
                ::= { nbVifAliasDLimitEntry 5 }

--  { nbRtVifGroup 4 ... 10 } Objects are reserved for another features.

-- ***********************************************************************
-- Device's Virtual Interface Table (new)
-- ***********************************************************************

nbVifTable  OBJECT-TYPE
            SYNTAX  SEQUENCE OF NbVifEntry
            ACCESS  not-accessible
            STATUS  mandatory
            DESCRIPTION
            "."
            ::= { nbRtVifGroup 11 }

nbVifEntry  OBJECT-TYPE
            SYNTAX  NbVifEntry
            ACCESS  not-accessible
            STATUS  mandatory
            DESCRIPTION
            "The Entries (records)."
            INDEX { nbVifType, nbVifDevNo, nbVifIsAlias, nbVifAliasDev }
            ::= { nbVifTable 1 }
        
NbVifEntry ::= SEQUENCE {
        nbVifType               INTEGER,
        nbVifDevNo              INTEGER,
        nbVifIsAlias            INTEGER,
        nbVifAliasDev           INTEGER,
        nbVifDevName            DisplayString,
        nbVifIpAddress          IpAddress,
        nbVifMask               IpAddress,
        nbVifPeer               IpAddress,
        nbVifPhysType           INTEGER,
        nbVifProtocol           INTEGER,
        nbVifName               DisplayString,
        nbVifPortList           OCTET STRING,
        nbVifMac                MacAddress,
        nbVifState              INTEGER,
        nbVifAdminStatus        INTEGER,
        nbVifConfigType         INTEGER,
        nbVifSecurity           INTEGER,
        nbVifIsTagged           INTEGER,
        nbVifTag                INTEGER,
        nbVifDescr              DisplayString,
        nbVifLastChange         TimeTicks,
	nbVifL2SwitchingMode    INTEGER,
	nbVifProxyArpMode       INTEGER,
	nbVifIpOnlyMode         INTEGER,
	nbVifIpForwardingMode   INTEGER
        }

nbVifType   OBJECT-TYPE
            SYNTAX INTEGER
            {
              other         (1),
              lanEthernet   (2),
              wanPPP        (3),
              wanFrameRelay (4),
              bridge        (5),
              loopback      (6),
              dummy         (7),
              logical       (8),
              outOfBand     (12)
            }
            ACCESS read-only
            STATUS mandatory
            DESCRIPTION
            "Type of the interface; (index # 1 of the Table)."
            ::= { nbVifEntry 1 }

nbVifDevNo  OBJECT-TYPE
            SYNTAX INTEGER
            ACCESS read-only
            STATUS mandatory
            DESCRIPTION
            "VIF Device Number; (index # 2 of the Table)."
            ::= { nbVifEntry 2 }

nbVifIsAlias OBJECT-TYPE
             SYNTAX INTEGER
             {
               other      (1),
               primary    (2),
               alias      (3)
             }
             ACCESS read-only
             STATUS mandatory
             DESCRIPTION
             "Primary/Alias mode of the VIF Entry;
              (index # 3 of the Table).
              Note : VIF Entry for the corresponding Device Number
              with Alias mode can be created only after
              VIF Entry with Primary mode have been already
              created."
             ::= { nbVifEntry 3 }

nbVifAliasDev  OBJECT-TYPE
               SYNTAX INTEGER
               ACCESS read-only
               STATUS mandatory
               DESCRIPTION
               "VIF Device Alias Number; (index # 4 of the Table).
                If it is a primary interface - [nbVifIsAlias] == 2,
                [nbVifAliasDev] must be zerro."
               ::= { nbVifEntry 4 }

nbVifDevName   OBJECT-TYPE
               SYNTAX DisplayString
               ACCESS read-only
               STATUS mandatory
               DESCRIPTION
               "Name of the VIF Device in the special format.
                For example :
                - 'vif7'    (VIF Device #7  primary Entry.)
                - 'vif11:3' (VIF Device #11 Entry with alias # 3)."
               ::= { nbVifEntry 5 }
       
nbVifIpAddress OBJECT-TYPE
               SYNTAX IpAddress
               ACCESS read-write
               STATUS mandatory
               DESCRIPTION
               "."
               ::= { nbVifEntry 6 }

nbVifMask      OBJECT-TYPE
               SYNTAX IpAddress
               ACCESS read-write
               STATUS mandatory
               DESCRIPTION
               "."
               ::= { nbVifEntry 7 }

nbVifPeer      OBJECT-TYPE
               SYNTAX IpAddress
               ACCESS read-write
               STATUS mandatory
               DESCRIPTION
               "This Object will be used only  for the
                [nbVifType]=3 - wanPPP     or
                [nbVifType]=4 - wanFrameRelay  VIF configuration."
               ::= { nbVifEntry 8 }

nbVifPhysType  OBJECT-TYPE
               SYNTAX INTEGER
               {
                 other      (1),
                 eth0       (2),
                 wp1        (3)
               }
               ACCESS read-only
               STATUS mandatory
               DESCRIPTION
               "The Card Type for the Physical Connection."
               ::= { nbVifEntry 9 }

nbVifProtocol  OBJECT-TYPE
               SYNTAX  INTEGER
               {
                 other      (1),
                 ipV4IF     (2),
                 ipxIF      (3),
                 portsIF    (4)
               }
               ACCESS read-write
               STATUS mandatory
               DESCRIPTION
               "The routing mechanism via which this route was learned."
               ::= { nbVifEntry 10 }

nbVifName      OBJECT-TYPE
               SYNTAX DisplayString
               ACCESS read-write
               STATUS mandatory
               DESCRIPTION
               "The name of this group (can be setted by the Manager)."
               ::= { nbVifEntry 11}
                
nbVifPortList  OBJECT-TYPE
               SYNTAX OCTET STRING
               ACCESS read-write
               STATUS mandatory
               DESCRIPTION
               "."
               ::= { nbVifEntry 12 }

nbVifMac       OBJECT-TYPE
               SYNTAX MacAddress
               ACCESS read-write
               STATUS mandatory
               DESCRIPTION
               "."
               ::= { nbVifEntry 13 }


nbVifState     OBJECT-TYPE
               SYNTAX INTEGER
               {
                 other      (1),
                 up         (2),
                 down       (3),
                 adminDown  (4)
               }
               ACCESS read-write
               STATUS mandatory
               DESCRIPTION
               "This Object will be used only  for the
                [nbVifType]=3 - wanPPP     or
                [nbVifType]=4 - wanFrameRelay  VIF configuration."
               ::= { nbVifEntry 14 }

nbVifAdminStatus OBJECT-TYPE
                 SYNTAX INTEGER
                 {
                  valid      (1),
                  invalid    (2),
                  create     (4)
                 }
                 ACCESS read-write
                 STATUS mandatory
                 DESCRIPTION
                 "Use 'valid' (1) value by
                  ADDind new Entry or EDITting of existing Entry.
                  Use 'inValid' (2) value by
                  DELETting of existing Entry."
                 ::= { nbVifEntry 15 }

nbVifConfigType  OBJECT-TYPE
                 SYNTAX INTEGER
                 {
                  auto       (1),
                  manual     (2)
                 }
                 ACCESS read-write
                 STATUS mandatory
                 DESCRIPTION
                 "Wether we want 'auto' configuration or not."
                 ::= { nbVifEntry 16 }

nbVifSecurity  OBJECT-TYPE
                SYNTAX INTEGER
                {
                 other      (1),
                 unsecure   (2),
                 secure     (3)
                }
                ACCESS  read-write
                STATUS  mandatory
                DESCRIPTION
                "."
                ::= { nbVifEntry 17 }

nbVifIsTagged  OBJECT-TYPE
                SYNTAX  INTEGER
                {
                 no       (0),
                 yes      (1)
                }
                ACCESS  read-write
                STATUS  mandatory
                DESCRIPTION
                "."
                ::= { nbVifEntry 20 }

nbVifTag       OBJECT-TYPE
               SYNTAX  INTEGER ( 0..4080 )
               ACCESS  read-write
               STATUS  mandatory
               DESCRIPTION
               "If nbVifIsTagged=yes(1) this field may not be 0;
                else it may have any value.
                Important: actual upper limit is 4080 - 2 * ports_capacity"
               ::= { nbVifEntry 21 }

nbVifDescr     OBJECT-TYPE
               SYNTAX  DisplayString (SIZE (0..80))
               ACCESS  read-write
               STATUS  mandatory
               DESCRIPTION
               "A textual string containing information about the
                interface."
               ::= { nbVifEntry 22 }

nbVifLastChange  OBJECT-TYPE
               SYNTAX   TimeTicks
               ACCESS read-only
               STATUS mandatory
               DESCRIPTION
               "The value of sysUpTime at the time the interface entered
                its current operational state.  If the current state was
                entered prior to the last re-initialization of the local
                network management subsystem, then this object contains a
                zero value."
               ::= { nbVifEntry 23 }

nbVifL2SwitchingMode  OBJECT-TYPE
	SYNTAX  INTEGER
        {
	 enable	           (1),
         disable           (2),
	 interfaceTagFlood (3),
	 unicastToLinux	   (4)
        }
        ACCESS  read-write
        STATUS  mandatory
        DESCRIPTION
        "Controls the mode of Layer 2 tag switching between subscribers."
        ::= { nbVifEntry 24 }

nbVifProxyArpMode  OBJECT-TYPE
	SYNTAX  INTEGER
        {
	 enable		(1),
         disable	(2),
	 enableAll	(3)
        }
        ACCESS  read-write
        STATUS  mandatory
        DESCRIPTION
        "Controls the enable/disable of proxy-arp for the interface."
        ::= { nbVifEntry 25 }

nbVifIpOnlyMode  OBJECT-TYPE
	SYNTAX  INTEGER
        {
	 enable	       (1),
         disable       (2)
        }
        ACCESS  read-write
        STATUS  mandatory
        DESCRIPTION
        "Controls the enable/disable of only IP packets forwarding for the interface."
        ::= { nbVifEntry 26 }

nbVifIpForwardingMode  OBJECT-TYPE
	SYNTAX  INTEGER
        {
	 enable	       (1),
         disable       (2)
        }
        ACCESS  read-write
        STATUS  mandatory
        DESCRIPTION
        "Controls the enable/disable of IP forwarding for the interface."
        ::= { nbVifEntry 27 }

-- ***********************************************************************
-- Objects in the Device's Forwarding Informational Base (Table)
-- ***********************************************************************

nbRtFib   OBJECT IDENTIFIER ::= { nbRouterConfig 4 }


nbRtFibNumEntries OBJECT-TYPE
                  SYNTAX  INTEGER 
                  ACCESS  read-only
                  STATUS  mandatory
                  DESCRIPTION
                  "The number of entries in this table."
                  ::= { nbRtFib 1 }

nbRtFibTable      OBJECT-TYPE
                  SYNTAX  SEQUENCE OF NbRtFibEntry
                  ACCESS  not-accessible
                  STATUS  mandatory
                  DESCRIPTION
                  "This table shows all the hosts that are attached
                   to the Accelerouter. For each host it shows its
                   port#, IP address, Network Mask and its MAC address."
                  ::= { nbRtFib 2 }

nbRtFibEntry      OBJECT-TYPE
                  SYNTAX  NbRtFibEntry
                  ACCESS  not-accessible
                  STATUS  mandatory
                  DESCRIPTION
                  "The entries (records)."

                  INDEX { nbRtFibEntryIpAddress,  nbRtFibEntryIpMask, nbRtFibEntryProtocol}

                  ::= { nbRtFibTable 1 }


NbRtFibEntry ::= SEQUENCE {

        nbRtFibEntryIpAddress       IpAddress,
        nbRtFibEntryIpMask          IpAddress,
        nbRtFibEntryProtocol        INTEGER,
        nbRtFibEntryNextHop         IpAddress,
        nbRtFibEntryNextPhysAddress MacAddress,
        nbRtFibEntryNextPort        INTEGER,
        nbRtFibEntryLastChTime      INTEGER,
        nbRtFibEntryAge             INTEGER,
        nbRtFibEntryMetric          INTEGER,
        nbRtFibEntryAdminStatus     INTEGER,
        nbRtFibEntryTag             INTEGER
       }

nbRtFibEntryIpAddress  OBJECT-TYPE
        SYNTAX  IpAddress
        ACCESS  read-only
        STATUS  mandatory
        DESCRIPTION
        "The IP address. "
        ::= { nbRtFibEntry 1 }

nbRtFibEntryIpMask OBJECT-TYPE
        SYNTAX  IpAddress
        ACCESS  read-only
        STATUS  mandatory
        DESCRIPTION
        "The IP subnet mask. "
        ::= { nbRtFibEntry 2 }

nbRtFibEntryProtocol   OBJECT-TYPE
        SYNTAX  INTEGER  -- (0..7200)
            {
                 other      (1),
                 direct     (2),
                 netmgmt    (3),
                 icmp       (4),
                 egp        (5),
                 ggp        (6),
                 hello      (7),
                 rip        (8),
                 is-is      (9),
                 es-is      (10),
                 ciscoIgrp  (11),
                 bbnSpfIgp  (12),
                 ospf       (13),
                 bgp        (14),
                 arp        (15),
                 larp       (16)
                }
        ACCESS  read-only
        STATUS  mandatory
        DESCRIPTION
        "The routing mechanism via which this entry was learned."
        ::= { nbRtFibEntry 3 }

nbRtFibEntryNextHop  OBJECT-TYPE
        SYNTAX  IpAddress
        ACCESS  read-write
        STATUS  mandatory
        DESCRIPTION
        "The next hop IP address. "
        ::= { nbRtFibEntry 4 }
        
nbRtFibEntryNextPhysAddress  OBJECT-TYPE
        SYNTAX  MacAddress
        ACCESS  read-write
        STATUS  mandatory
        DESCRIPTION
        "The host or next hop MAC address."
        ::= { nbRtFibEntry 5 }
        
nbRtFibEntryNextPort   OBJECT-TYPE
        SYNTAX  INTEGER
        ACCESS  read-write
        STATUS  mandatory
        DESCRIPTION
        "The port number that the host or next hope is connected to."
        ::= { nbRtFibEntry 6 }

nbRtFibEntryLastChTime   OBJECT-TYPE
        SYNTAX  INTEGER
        ACCESS  read-only
        STATUS  mandatory
        DESCRIPTION
        "The last change time of this entry. "
        ::= { nbRtFibEntry 7 }

nbRtFibEntryAge    OBJECT-TYPE
        SYNTAX  INTEGER
        ACCESS  read-write
        STATUS  mandatory
        DESCRIPTION
        "Age of this entry. "
        ::= { nbRtFibEntry 8 }

nbRtFibEntryMetric   OBJECT-TYPE
        SYNTAX  INTEGER
        ACCESS  read-write
        STATUS  mandatory
        DESCRIPTION
        "Metric of this entry. "
        ::= { nbRtFibEntry 9 }
        
nbRtFibEntryAdminStatus OBJECT-TYPE
        SYNTAX  INTEGER
        {
         valid      (1),
         invalid    (2)
        }
        ACCESS  read-write
        STATUS  mandatory
        DESCRIPTION
        "Controls the Add/Delete of this entry. "
        ::= { nbRtFibEntry 10 }

nbRtFibEntryTag OBJECT-TYPE
                SYNTAX  INTEGER ( 0..4080 )
                ACCESS  read-write
                STATUS  mandatory
                DESCRIPTION
                "Tag 0 means untagged entry."
                DEFVAL { 0 }
                ::= { nbRtFibEntry 15 }

-- ***********************************************************************
-- Diff Services Configuration Group
-- ***********************************************************************

nbRtDiffServ      OBJECT IDENTIFIER ::= { nbRouterConfig 5 }

-- ***********************************************************************
-- Diff Serv Configuration Table
-- ***********************************************************************

nbRtDiffServTable      OBJECT-TYPE
                SYNTAX  SEQUENCE OF NbRtDiffServEntry
                ACCESS  not-accessible
                STATUS  mandatory
                DESCRIPTION
                "The table configures Diff Server for VIF."
                ::= { nbRtDiffServ 2 }

nbRtDiffServEntry      OBJECT-TYPE
                SYNTAX  NbRtDiffServEntry
                ACCESS  not-accessible
                STATUS  mandatory
                DESCRIPTION
                "The Entries (records)."
                INDEX { nbVifType,
                        nbVifDevNo,
                        nbVifIsAlias,
                        nbVifAliasDev }

                ::= { nbRtDiffServTable 1 }

NbRtDiffServEntry ::= SEQUENCE {
                nbRtDiffServMode                 INTEGER,
                nbRtDiffServVptMapNameIndex      INTEGER,
                nbRtDiffServDscpMapNameIndex     INTEGER,
                nbRtDiffServMgmtVptMapNameIndex  INTEGER,
                nbRtDiffServMgmtDscpMapNameIndex INTEGER
                }

nbRtDiffServMode       OBJECT-TYPE
                SYNTAX INTEGER
                {
                 other          (1),
                 none           (2),
                 byTOS          (3),
                 byTag          (4),
                 asGlobal       (10)
                }
                ACCESS read-write
                STATUS mandatory
                DESCRIPTION
                "The Diff Serv mode for VIF or/and Subscriber."
                ::= { nbRtDiffServEntry 2 }

nbRtDiffServVptMapNameIndex   OBJECT-TYPE
                SYNTAX  INTEGER -- (1..8)
                ACCESS  read-write
                STATUS  mandatory
                DESCRIPTION
                "The Index of the Diff Server VPT Mapping Name
                 that is binded to the VIF."
                ::= { nbRtDiffServEntry 3 }

nbRtDiffServDscpMapNameIndex   OBJECT-TYPE
                SYNTAX  INTEGER -- (1..8)
                ACCESS  read-write
                STATUS  mandatory
                DESCRIPTION
                "The Index of the Diff Server DSCP Mapping Name
                 that is binded to the VIF."
                ::= { nbRtDiffServEntry 4 }

nbRtDiffServMgmtVptMapNameIndex   OBJECT-TYPE
                SYNTAX  INTEGER -- (0..8)
                ACCESS  read-write
                STATUS  mandatory
                DESCRIPTION
                "The Index of the Management Diff Server VPT Mapping Name
                 that is binded to the VIF.
		 Value equals to 0 means that this kind of mapping 
		 is not applicable to this kind of Vif."
                ::= { nbRtDiffServEntry 5 }

nbRtDiffServMgmtDscpMapNameIndex   OBJECT-TYPE
                SYNTAX  INTEGER -- (0..8)
                ACCESS  read-write
                STATUS  mandatory
                DESCRIPTION
                "The Index of the Management Diff Server DSCP Mapping Name
                 that is binded to the VIF.
		 Value equals to 0 means that this kind of mapping 
		 is not applicable to this kind of Vif."
                ::= { nbRtDiffServEntry 6 }

-- ***********************************************************************
-- Diff Serv per VIF Rate Limit Configuration Table
-- ***********************************************************************

nbRtVifDiffServRateLimitTable        OBJECT-TYPE
                SYNTAX  SEQUENCE OF NbRtVifDiffServRateLimitEntry
                ACCESS  not-accessible
                STATUS  mandatory
                DESCRIPTION
                "."
                ::= { nbRtDiffServ 4 }

nbRtVifDiffServRateLimitEntry        OBJECT-TYPE
                SYNTAX  NbRtVifDiffServRateLimitEntry
                ACCESS  not-accessible
                STATUS  mandatory
                DESCRIPTION
                "The Entries (records)."
                INDEX { nbVifType,
                        nbVifDevNo,
                        nbVifIsAlias,
                        nbVifAliasDev,
                        ifIndex,
                        nbRtVifDiffServDirect }
                ::= { nbRtVifDiffServRateLimitTable 1 }

NbRtVifDiffServRateLimitEntry ::= SEQUENCE {
                nbRtVifDiffServDirect       DirectionType,
                nbRtVifDiffServBuckRate     INTEGER,
                nbRtVifDiffServBuckSize     INTEGER,
                nbRtVifDiffServREDmode      INTEGER,
                nbRtVifDiffServAdminStatus  INTEGER
                }

nbRtVifDiffServDirect    OBJECT-TYPE
                SYNTAX     DirectionType
                MAX-ACCESS not-accessible
                STATUS     mandatory
                DESCRIPTION
                "The Diff Serv ingress/egress direction."
                ::= { nbRtVifDiffServRateLimitEntry 1 }

nbRtVifDiffServBuckRate   OBJECT-TYPE
                SYNTAX INTEGER -- (26..1048576)
                ACCESS read-write
                STATUS mandatory
                DESCRIPTION
                "The Diff Serv Bucket Rate."
                ::= { nbRtVifDiffServRateLimitEntry 2 }

nbRtVifDiffServBuckSize   OBJECT-TYPE
                SYNTAX INTEGER -- (2048..65535)
                ACCESS read-write
                STATUS mandatory
                DESCRIPTION
                "The Diff Serv Bucket Size.
                The value '0' means - 'optimize'."
                ::= { nbRtVifDiffServRateLimitEntry 3 }

nbRtVifDiffServREDmode    OBJECT-TYPE
                SYNTAX INTEGER
                {
                 other              (1),
                 enable             (2),
                 disable            (3)
                }
                ACCESS read-write
                STATUS mandatory
                DESCRIPTION
                "The Diff Serv Random Early Detection (RED) for Rate Limit Mode."
                ::= { nbRtVifDiffServRateLimitEntry 4 }

nbRtVifDiffServAdminStatus    OBJECT-TYPE
                SYNTAX INTEGER
                {
                 other              (1),
                 createOrModify     (2),
                 delete             (3),
                 exist              (4),
                 absent             (5)
                }
                ACCESS read-write
                STATUS mandatory
                DESCRIPTION
                "The Diff Serv Rate Limit Admin Status."
                ::= { nbRtVifDiffServRateLimitEntry 10 }

-- ***********************************************************************
-- Diff Serv VPT Mapping Table
-- ***********************************************************************

nbRtDiffServVptMapTable      OBJECT-TYPE
                SYNTAX  SEQUENCE OF NbRtDiffServVptMapEntry
                ACCESS  not-accessible
                STATUS  mandatory
                DESCRIPTION
                "The table configures Diff Server VPT Mapping for Device."
                ::= { nbRtDiffServ 6 }

nbRtDiffServVptMapEntry      OBJECT-TYPE
                SYNTAX  NbRtDiffServVptMapEntry
                ACCESS  not-accessible
                STATUS  mandatory
                DESCRIPTION
                "The Entries (records)."
                INDEX { nbRtDiffServVptMapNameId }

                ::= { nbRtDiffServVptMapTable 1 }

NbRtDiffServVptMapEntry ::= SEQUENCE {
                nbRtDiffServVptMapNameId       INTEGER,
                nbRtDiffServVptMapName         DisplayString,
                nbRtDiffServVptMapStatus       INTEGER,
                nbRtDiffServVptMapAdminStatus  INTEGER
                }

nbRtDiffServVptMapNameId   OBJECT-TYPE
                SYNTAX  INTEGER -- (1..8)
                ACCESS  read-only
                STATUS  mandatory
                DESCRIPTION
                "The Diff Server VPT Mapping Name Id."
                ::= { nbRtDiffServVptMapEntry 1 }
        
nbRtDiffServVptMapName    OBJECT-TYPE
                SYNTAX DisplayString (SIZE(1..20))
                ACCESS read-write
                STATUS mandatory
                DESCRIPTION
                "The Diff Server VPT Mapping Name."
                ::= { nbRtDiffServVptMapEntry 2 }

nbRtDiffServVptMapStatus  OBJECT-TYPE
                SYNTAX INTEGER
                {
                 other              (1),
                 active             (2),
                 notActive          (3)
                }
                ACCESS read-only
                STATUS mandatory
                DESCRIPTION
                "The activity Status of the
                 Diff Server VPT Mapping Entry."
                ::= { nbRtDiffServVptMapEntry 3 }

nbRtDiffServVptMapAdminStatus OBJECT-TYPE
                 SYNTAX INTEGER
                 {
                  valid                 (1),
                  invalid               (2),
                  restoreDefaultConfig  (3)
                 }
                 ACCESS read-write
                 STATUS mandatory
                 DESCRIPTION
                 "GET or GET_NEXT Operation :
                  - Responds 'valid' (1) value when the Entry is already exists.
                  - Responds 'inValid' (2) value in case of no existing Entry.
                  SET Operation :
                  - Use 'valid' (1) value for new Entry creation.
                  - Use 'inValid' (2) value for deleting of existing Entry.
                  - Use 'restoreDefaultConfig' (5) value for restoring the
                    default Profile configuration of existing Entry."
                 ::= { nbRtDiffServVptMapEntry 4 }

-- ***********************************************************************
-- Diff Serv VPT Mapping Profiles Table
-- ***********************************************************************

nbRtDiffServVptMapPrflTable      OBJECT-TYPE
                SYNTAX  SEQUENCE OF NbRtDiffServVptMapPrflEntry
                ACCESS  not-accessible
                STATUS  mandatory
                DESCRIPTION
                "The table configures Diff Server VPT Mapping Profiles for Device."
                ::= { nbRtDiffServ 8 }

nbRtDiffServVptMapPrflEntry      OBJECT-TYPE
                SYNTAX  NbRtDiffServVptMapPrflEntry
                ACCESS  not-accessible
                STATUS  mandatory
                DESCRIPTION
                "The Entries (records)."
                INDEX { nbRtDiffServVptMapPrflNameId,
                        nbRtDiffServVptMapPrflInValueId }

                ::= { nbRtDiffServVptMapPrflTable 1 }

NbRtDiffServVptMapPrflEntry ::= SEQUENCE {
                nbRtDiffServVptMapPrflNameId       INTEGER,
                nbRtDiffServVptMapPrflInValueId    INTEGER,
                nbRtDiffServVptMapPrflInValue      INTEGER,
                nbRtDiffServVptMapPrflSl           INTEGER,
                nbRtDiffServVptMapPrflOutValue     INTEGER
                }

nbRtDiffServVptMapPrflNameId   OBJECT-TYPE
                SYNTAX  INTEGER -- (1..8)
                ACCESS  read-only
                STATUS  mandatory
                DESCRIPTION
                "The Diff Server VPT Mapping Profile Name Id."
                ::= { nbRtDiffServVptMapPrflEntry 1 }

nbRtDiffServVptMapPrflInValueId   OBJECT-TYPE
                SYNTAX  INTEGER -- (1..8)
                ACCESS  read-only
                STATUS  mandatory
                DESCRIPTION
                "The Diff Server Mapping Profile Input VPT Value Id."
                ::= { nbRtDiffServVptMapPrflEntry 2 }

nbRtDiffServVptMapPrflInValue   OBJECT-TYPE
                SYNTAX  INTEGER -- (0..7)
                ACCESS  read-only
                STATUS  mandatory
                DESCRIPTION
                "The Diff Server Mapping Profile Input VPT Value."
                ::= { nbRtDiffServVptMapPrflEntry 3 }

nbRtDiffServVptMapPrflSl  OBJECT-TYPE
                SYNTAX INTEGER -- (1..8)
                ACCESS read-write
                STATUS mandatory
                DESCRIPTION
                "The Diff Server VPT Mapping Profile Service Level."
                ::= { nbRtDiffServVptMapPrflEntry 4 }

nbRtDiffServVptMapPrflOutValue  OBJECT-TYPE
                SYNTAX  INTEGER -- (0..7)
                ACCESS  read-write
                STATUS  mandatory
                DESCRIPTION
                "The Diff Server Mapping Profile Output VPT Value."
                ::= { nbRtDiffServVptMapPrflEntry 5 }

-- ***********************************************************************
-- Diff Serv DSCP Mapping Table
-- ***********************************************************************

nbRtDiffServDscpMapTable      OBJECT-TYPE
                SYNTAX  SEQUENCE OF NbRtDiffServDscpMapEntry
                ACCESS  not-accessible
                STATUS  mandatory
                DESCRIPTION
                "The table configures Diff Server DSCP Mapping for Device."
                ::= { nbRtDiffServ 10 }

nbRtDiffServDscpMapEntry      OBJECT-TYPE
                SYNTAX  NbRtDiffServDscpMapEntry
                ACCESS  not-accessible
                STATUS  mandatory
                DESCRIPTION
                "The Entries (records)."
                INDEX { nbRtDiffServDscpMapNameId }

                ::= { nbRtDiffServDscpMapTable 1 }

NbRtDiffServDscpMapEntry ::= SEQUENCE {
                nbRtDiffServDscpMapNameId       INTEGER,
                nbRtDiffServDscpMapName         DisplayString,
                nbRtDiffServDscpMapStatus       INTEGER,
                nbRtDiffServDscpMapAdminStatus  INTEGER
                }

nbRtDiffServDscpMapNameId   OBJECT-TYPE
                SYNTAX  INTEGER -- (1..8)
                ACCESS  read-only
                STATUS  mandatory
                DESCRIPTION
                "The Diff Server Dscp Mapping Name Id."
                ::= { nbRtDiffServDscpMapEntry 1 }
        
nbRtDiffServDscpMapName    OBJECT-TYPE
                SYNTAX DisplayString (SIZE(1..20))
                ACCESS read-write
                STATUS mandatory
                DESCRIPTION
                "The Diff Server DSCP Mapping Name."
                ::= { nbRtDiffServDscpMapEntry 2 }

nbRtDiffServDscpMapStatus  OBJECT-TYPE
                SYNTAX INTEGER
                {
                 other              (1),
                 active             (2),
                 notActive          (3)
                }
                ACCESS read-only
                STATUS mandatory
                DESCRIPTION
                "The Status of the Diff Server DSCP Mapping Entry."
                ::= { nbRtDiffServDscpMapEntry 3 }

nbRtDiffServDscpMapAdminStatus OBJECT-TYPE
                 SYNTAX INTEGER
                 {
                  valid                 (1),
                  invalid               (2),
                  restoreDefaultConfig  (3)
                 }
                 ACCESS read-write
                 STATUS mandatory
                 DESCRIPTION
                 "GET or GET_NEXT Operation :
                  - Responds 'valid' (1) value when the Entry is already exists.
                  - Responds 'inValid' (2) value in case of not existing Entry.
                  SET Operation :
                  - Use 'valid' (1) value for new Entry creation.
                  - Use 'inValid' (2) value for deleting of existing Entry.
                  - Use 'restoreDefaultConfig' (5) value for restoring the
                    default Profile configuration of existing Entry."
                 ::= { nbRtDiffServDscpMapEntry 4 }

-- ***********************************************************************
-- Diff Serv DSCP Mapping Profiles Table
-- ***********************************************************************

nbRtDiffServDscpMapPrflTable      OBJECT-TYPE
                SYNTAX  SEQUENCE OF NbRtDiffServDscpMapPrflEntry
                ACCESS  not-accessible
                STATUS  mandatory
                DESCRIPTION
                "The table configures Diff Server DSCP Mapping Profiles for Device."
                ::= { nbRtDiffServ 12 }

nbRtDiffServDscpMapPrflEntry      OBJECT-TYPE
                SYNTAX  NbRtDiffServDscpMapPrflEntry
                ACCESS  not-accessible
                STATUS  mandatory
                DESCRIPTION
                "The Entries (records)."
                INDEX { nbRtDiffServDscpMapPrflNameId,
                        nbRtDiffServDscpMapPrflInValueId }

                ::= { nbRtDiffServDscpMapPrflTable 1 }

NbRtDiffServDscpMapPrflEntry ::= SEQUENCE {
                nbRtDiffServDscpMapPrflNameId       INTEGER,
                nbRtDiffServDscpMapPrflInValueId    INTEGER,
                nbRtDiffServDscpMapPrflInValue      INTEGER,
                nbRtDiffServDscpMapPrflSl           INTEGER,
                nbRtDiffServDscpMapPrflOutValue     INTEGER
                }

nbRtDiffServDscpMapPrflNameId   OBJECT-TYPE
                SYNTAX  INTEGER -- (1..8)
                ACCESS  read-only
                STATUS  mandatory
                DESCRIPTION
                "The Diff Server DSCP Mapping Profile Name Id."
                ::= { nbRtDiffServDscpMapPrflEntry 1 }

nbRtDiffServDscpMapPrflInValueId   OBJECT-TYPE
                SYNTAX  INTEGER -- (1..64)
                ACCESS  read-only
                STATUS  mandatory
                DESCRIPTION
                "The Diff Server Mapping Profile Input DSCP Value Id."
                ::= { nbRtDiffServDscpMapPrflEntry 2 }

nbRtDiffServDscpMapPrflInValue   OBJECT-TYPE
                SYNTAX  INTEGER -- (0..63)
                ACCESS  read-only
                STATUS  mandatory
                DESCRIPTION
                "The Diff Server Mapping Profile Input DSCP Value."
                ::= { nbRtDiffServDscpMapPrflEntry 3 }

nbRtDiffServDscpMapPrflSl  OBJECT-TYPE
                SYNTAX INTEGER -- (1..8)
                ACCESS read-write
                STATUS mandatory
                DESCRIPTION
                "The Diff Server DSCP Mapping Profile Service Level."
                ::= { nbRtDiffServDscpMapPrflEntry 4 }

nbRtDiffServDscpMapPrflOutValue  OBJECT-TYPE
                SYNTAX  INTEGER -- (0..7)
                ACCESS  read-write
                STATUS  mandatory
                DESCRIPTION
                "The Diff Server Mapping Profile Output DSCP Value."
                ::= { nbRtDiffServDscpMapPrflEntry 5 }

-- ***********************************************************************
-- VIF Accounting Group
-- ***********************************************************************

nbRtAccounting      OBJECT IDENTIFIER ::= { nbRouterConfig 6 }

-- ***********************************************************************
-- VIF Accounting Table
-- ***********************************************************************

nbRtAccVifTable OBJECT-TYPE
                SYNTAX  SEQUENCE OF NbRtAccVifEntry
                ACCESS  not-accessible
                STATUS  mandatory
                DESCRIPTION
                "."
                ::= { nbRtAccounting 10 }

nbRtAccVifEntry OBJECT-TYPE
                SYNTAX  NbRtAccVifEntry
                ACCESS  not-accessible
                STATUS  mandatory
                DESCRIPTION
                "The Entries (records)."
                INDEX { nbVifType,
                        nbVifDevNo,
                        nbVifIsAlias,
                        nbVifAliasDev,
                        nbRtAccVifDirection }

                ::= { nbRtAccVifTable 1 }

NbRtAccVifEntry ::= SEQUENCE {
                nbRtAccVifDirection             DirectionType,
                nbRtAccVifAdminStatus           INTEGER,
                nbRtAccVifOperStatus            INTEGER,
                nbRtAccVifConformingBytes       AccountCouter,
                nbRtAccVifExceedingBytes        AccountCouter,
                nbRtAccVifConformingPackets     AccountCouter,
                nbRtAccVifExceedingPackets      AccountCouter,
                nbRtAccVifHighConformingBytes   Counter32,
                nbRtAccVifHighExceedingBytes    Counter32,
                nbRtAccVifHighConformingPackets Counter32,
                nbRtAccVifHighExceedingPackets  Counter32,
                nbRtAccVifLowConformingBytes    Counter32,
                nbRtAccVifLowExceedingBytes     Counter32,
                nbRtAccVifLowConformingPackets  Counter32,
                nbRtAccVifLowExceedingPackets   Counter32,
                nbRtAccVif64ConformingBytes     AccountCounter64,
                nbRtAccVif64ExceedingBytes      AccountCounter64,
                nbRtAccVifConformingUcastPackets     AccountCouter,
                nbRtAccVifHighConformingUcastPackets Counter32,
                nbRtAccVifLowConformingUcastPackets  Counter32,
                nbRtAccVif64ConformingUcastPackets   AccountCounter64,
                nbRtAccVifConformingMcastPackets     AccountCouter,
                nbRtAccVifHighConformingMcastPackets Counter32,
                nbRtAccVifLowConformingMcastPackets  Counter32,
                nbRtAccVif64ConformingMcastPackets   AccountCounter64,
                nbRtAccVifConformingBcastPackets     AccountCouter,
                nbRtAccVifHighConformingBcastPackets Counter32,
                nbRtAccVifLowConformingBcastPackets  Counter32,
                nbRtAccVif64ConformingBcastPackets   AccountCounter64
                }

nbRtAccVifDirection    OBJECT-TYPE
                SYNTAX DirectionType
                ACCESS read-only
                STATUS mandatory
                DESCRIPTION
                "The ingress/egress direction."
                ::= { nbRtAccVifEntry 1 }

nbRtAccVifAdminStatus    OBJECT-TYPE
                SYNTAX INTEGER
                {
                 other      (1),
                 enable     (2),
                 disable    (3),
                 pause      (4),
                 resume     (5),
                 clear      (6)
                }
                ACCESS read-write
                STATUS mandatory
                DESCRIPTION
                "VIF Accounting Admin Status."
                ::= { nbRtAccVifEntry 3 }


nbRtAccVifOperStatus    OBJECT-TYPE
                SYNTAX INTEGER
                {
                 other      (1),
                 active     (2),
                 paused     (3),
                 disabled   (4)
                }
                ACCESS read-only
                STATUS mandatory
                DESCRIPTION
                "VIF Accounting Oper Status."
                ::= { nbRtAccVifEntry 4 }

nbRtAccVifConformingBytes   OBJECT-TYPE
                SYNTAX  AccountCouter
                ACCESS  read-only
                STATUS  mandatory
                DESCRIPTION
                "The Conforming Bytes Counter in blocks (1 block = 64k bytes) for VIF."
                ::= { nbRtAccVifEntry 6 }

nbRtAccVifExceedingBytes   OBJECT-TYPE
                SYNTAX  AccountCouter
                ACCESS  read-only
                STATUS  mandatory
                DESCRIPTION
                "The Exceeding Bytes Counter in blocks (1 block = 64k bytes) for VIF."
                ::= { nbRtAccVifEntry 7 }

nbRtAccVifConformingPackets   OBJECT-TYPE
                SYNTAX  AccountCouter
                ACCESS  read-only
                STATUS  mandatory
                DESCRIPTION
                "The Conforming Packets Counter in blocks (1 block = 64k bytes) for VIF."
                ::= { nbRtAccVifEntry 8 }

nbRtAccVifExceedingPackets   OBJECT-TYPE
                SYNTAX  AccountCouter
                ACCESS  read-only
                STATUS  mandatory
                DESCRIPTION
                "The Exceeding Packets Counter in blocks (1 block = 64k bytes) for VIF."
                ::= { nbRtAccVifEntry 9 }

nbRtAccVifHighConformingBytes   OBJECT-TYPE
                SYNTAX  Counter32
                ACCESS  read-only
                STATUS  mandatory
                DESCRIPTION
                "The Conforming Bytes Counter (High part) for VIF."
                ::= { nbRtAccVifEntry 11 }

nbRtAccVifHighExceedingBytes   OBJECT-TYPE
                SYNTAX  Counter32
                ACCESS  read-only
                STATUS  mandatory
                DESCRIPTION
                "The Exceeding Bytes Counter (High part) for VIF."
                ::= { nbRtAccVifEntry 12 }

nbRtAccVifHighConformingPackets   OBJECT-TYPE
                SYNTAX  Counter32
                ACCESS  read-only
                STATUS  mandatory
                DESCRIPTION
                "The Conforming Packets Counter (High part) for VIF."
                ::= { nbRtAccVifEntry 13 }

nbRtAccVifHighExceedingPackets   OBJECT-TYPE
                SYNTAX  Counter32
                ACCESS  read-only
                STATUS  mandatory
                DESCRIPTION
                "The Exceeding Packets Counter (High part) for VIF."
                ::= { nbRtAccVifEntry 14 }

nbRtAccVifLowConformingBytes   OBJECT-TYPE
                SYNTAX  Counter32
                ACCESS  read-only
                STATUS  mandatory
                DESCRIPTION
                "The Conforming Bytes Counter (Low part) for VIF."
                ::= { nbRtAccVifEntry 15 }

nbRtAccVifLowExceedingBytes   OBJECT-TYPE
                SYNTAX  Counter32
                ACCESS  read-only
                STATUS  mandatory
                DESCRIPTION
                "The Exceeding Bytes Counter (Low part) for VIF."
                ::= { nbRtAccVifEntry 16 }

nbRtAccVifLowConformingPackets   OBJECT-TYPE
                SYNTAX  Counter32
                ACCESS  read-only
                STATUS  mandatory
                DESCRIPTION
                "The Conforming Packets Counter (Low part) for VIF."
                ::= { nbRtAccVifEntry 17 }

nbRtAccVifLowExceedingPackets   OBJECT-TYPE
                SYNTAX  Counter32
                ACCESS  read-only
                STATUS  mandatory
                DESCRIPTION
                "The Exceeding Packets Counter (Low part) for VIF."
                ::= { nbRtAccVifEntry 18 }

nbRtAccVif64ConformingBytes   OBJECT-TYPE
                SYNTAX  AccountCounter64
                ACCESS  read-only
                STATUS  mandatory
                DESCRIPTION
                "The Conforming Bytes Counter (64 bits) for VIF."
                ::= { nbRtAccVifEntry 19 }

nbRtAccVif64ExceedingBytes   OBJECT-TYPE
                SYNTAX  AccountCounter64
                ACCESS  read-only
                STATUS  mandatory
                DESCRIPTION
                "The Exceeding Bytes Counter (64 bits) for VIF."
                ::= { nbRtAccVifEntry 20 }

nbRtAccVifConformingUcastPackets   OBJECT-TYPE
                SYNTAX  AccountCouter
                ACCESS  read-only
                STATUS  mandatory
                DESCRIPTION
                "The Conforming Unicast Packets Counter
                 in blocks (1 block = 64k bytes) for VIF."
                ::= { nbRtAccVifEntry 21 }

nbRtAccVifHighConformingUcastPackets   OBJECT-TYPE
                SYNTAX  Counter32
                ACCESS  read-only
                STATUS  mandatory
                DESCRIPTION
                "The Conforming Unicast Packets Counter
                 (High part) for VIF."
                ::= { nbRtAccVifEntry 22 }

nbRtAccVifLowConformingUcastPackets   OBJECT-TYPE
                SYNTAX  Counter32
                ACCESS  read-only
                STATUS  mandatory
                DESCRIPTION
                "The Conforming Unicast Packets Counter
                 (Low part) for VIF."
                ::= { nbRtAccVifEntry 23 }

nbRtAccVif64ConformingUcastPackets   OBJECT-TYPE
                SYNTAX  AccountCounter64
                ACCESS  read-only
                STATUS  mandatory
                DESCRIPTION
                "The Conforming Unicast Bytes Counter
                 (64 bits) for VIF."
                ::= { nbRtAccVifEntry 24 }

nbRtAccVifConformingMcastPackets   OBJECT-TYPE
                SYNTAX  AccountCouter
                ACCESS  read-only
                STATUS  mandatory
                DESCRIPTION
                "The Conforming Multicast Packets Counter
                 in blocks (1 block = 64k bytes) for VIF."
                ::= { nbRtAccVifEntry 25 }

nbRtAccVifHighConformingMcastPackets   OBJECT-TYPE
                SYNTAX  Counter32
                ACCESS  read-only
                STATUS  mandatory
                DESCRIPTION
                "The Conforming Multicast Packets Counter
                 (High part) for VIF."
                ::= { nbRtAccVifEntry 26 }

nbRtAccVifLowConformingMcastPackets   OBJECT-TYPE
                SYNTAX  Counter32
                ACCESS  read-only
                STATUS  mandatory
                DESCRIPTION
                "The Conforming Multicast Packets Counter
                 (Low part) for VIF."
                ::= { nbRtAccVifEntry 27 }

nbRtAccVif64ConformingMcastPackets   OBJECT-TYPE
                SYNTAX  AccountCounter64
                ACCESS  read-only
                STATUS  mandatory
                DESCRIPTION
                "The Conforming Multicast Bytes Counter
                 (64 bits) for VIF."
                ::= { nbRtAccVifEntry 28 }

nbRtAccVifConformingBcastPackets   OBJECT-TYPE
                SYNTAX  AccountCouter
                ACCESS  read-only
                STATUS  mandatory
                DESCRIPTION
                "The Conforming Broadcast Packets Counter
                 in blocks (1 block = 64k bytes) for VIF."
                ::= { nbRtAccVifEntry 29 }

nbRtAccVifHighConformingBcastPackets   OBJECT-TYPE
                SYNTAX  Counter32
                ACCESS  read-only
                STATUS  mandatory
                DESCRIPTION
                "The Conforming Broadcast Packets Counter
                 (High part) for VIF."
                ::= { nbRtAccVifEntry 30 }

nbRtAccVifLowConformingBcastPackets   OBJECT-TYPE
                SYNTAX  Counter32
                ACCESS  read-only
                STATUS  mandatory
                DESCRIPTION
                "The Conforming Broadcast Packets Counter
                 (Low part) for VIF."
                ::= { nbRtAccVifEntry 31 }

nbRtAccVif64ConformingBcastPackets   OBJECT-TYPE
                SYNTAX  AccountCounter64
                ACCESS  read-only
                STATUS  mandatory
                DESCRIPTION
                "The Conforming Broadcast Bytes Counter
                 (64 bits) for VIF."
                ::= { nbRtAccVifEntry 32 }

-- ***********************************************************************
-- VIF per Port Accounting Table
-- ***********************************************************************

nbRtAccVifPortTable     OBJECT-TYPE
                SYNTAX  SEQUENCE OF NbRtAccVifPortEntry
                ACCESS  not-accessible
                STATUS  mandatory
                DESCRIPTION
                "."
                ::= { nbRtAccounting 12 }

nbRtAccVifPortEntry     OBJECT-TYPE
                SYNTAX  NbRtAccVifPortEntry
                ACCESS  not-accessible
                STATUS  mandatory
                DESCRIPTION
                "The Entries (records)."
                INDEX { nbVifType,
                        nbVifDevNo,
                        nbVifIsAlias,
                        nbVifAliasDev,
                        nbRtVifPortId,
                        nbRtAccVifDirection}

                ::= { nbRtAccVifPortTable 1 }

NbRtAccVifPortEntry ::= SEQUENCE {
                nbRtVifPortId                    INTEGER,
                nbRtAccPortAdminStatus           INTEGER,
                nbRtAccPortOperStatus            INTEGER,
                nbRtAccPortConformingBytes       AccountCouter,
                nbRtAccPortExceedingBytes        AccountCouter,
                nbRtAccPortConformingPackets     AccountCouter,
                nbRtAccPortExceedingPackets      AccountCouter,
                nbRtAccPortHighConformingBytes   Counter32,
                nbRtAccPortHighExceedingBytes    Counter32,
                nbRtAccPortHighConformingPackets Counter32,
                nbRtAccPortHighExceedingPackets  Counter32,
                nbRtAccPortLowConformingBytes    Counter32,
                nbRtAccPortLowExceedingBytes     Counter32,
                nbRtAccPortLowConformingPackets  Counter32,
                nbRtAccPortLowExceedingPackets   Counter32,
                nbRtAccPortVif64ConformingBytes  AccountCounter64,
                nbRtAccPortVif64ExceedingBytes   AccountCounter64,
                nbRtAccPortConformingUcastPackets     AccountCouter,
                nbRtAccPortHighConformingUcastPackets Counter32,
                nbRtAccPortLowConformingUcastPackets  Counter32,
                nbRtAccPort64ConformingUcastPackets   AccountCounter64,
                nbRtAccPortConformingMcastPackets     AccountCouter,
                nbRtAccPortHighConformingMcastPackets Counter32,
                nbRtAccPortLowConformingMcastPackets  Counter32,
                nbRtAccPort64ConformingMcastPackets   AccountCounter64,
                nbRtAccPortConformingBcastPackets     AccountCouter,
                nbRtAccPortHighConformingBcastPackets Counter32,
                nbRtAccPortLowConformingBcastPackets  Counter32,
                nbRtAccPort64ConformingBcastPackets   AccountCounter64
                }

nbRtVifPortId    OBJECT-TYPE
                SYNTAX INTEGER
                ACCESS read-only
                STATUS mandatory
                DESCRIPTION
                "VIF per Port Accounting Port Id."
                ::= { nbRtAccVifPortEntry 1 }

nbRtAccPortAdminStatus    OBJECT-TYPE
                SYNTAX INTEGER
                {
                 other      (1),
                 enable     (2),
                 disable    (3),
                 pause      (4),
                 resume     (5),
                 clear      (6)
                }
                ACCESS read-write
                STATUS mandatory
                DESCRIPTION
                "VIF per Port Accounting Admin Status."
                ::= { nbRtAccVifPortEntry 2 }

nbRtAccPortOperStatus    OBJECT-TYPE
                SYNTAX INTEGER
                {
                 other      (1),
                 active     (2),
                 paused     (3),
                 disabled   (4)
                }
                ACCESS read-only
                STATUS mandatory
                DESCRIPTION
                "VIF per Port Accounting Oper Status."
                ::= { nbRtAccVifPortEntry 3 }

nbRtAccPortConformingBytes   OBJECT-TYPE
                SYNTAX  AccountCouter
                ACCESS  read-only
                STATUS  mandatory
                DESCRIPTION
                "Port Conforming Bytes Counter in blocks (1 block = 64k bytes) for Port."
                ::= { nbRtAccVifPortEntry 6 }

nbRtAccPortExceedingBytes   OBJECT-TYPE
                SYNTAX  AccountCouter
                ACCESS  read-only
                STATUS  mandatory
                DESCRIPTION
                "Port Exceeding Bytes Counter in blocks (1 block = 64k bytes) for Port."
                ::= { nbRtAccVifPortEntry 7 }

nbRtAccPortConformingPackets   OBJECT-TYPE
                SYNTAX  AccountCouter
                ACCESS  read-only
                STATUS  mandatory
                DESCRIPTION
                "Port Conforming Packets Counter in blocks (1 block = 64k bytes) for Port."
                ::= { nbRtAccVifPortEntry 8 }

nbRtAccPortExceedingPackets   OBJECT-TYPE
                SYNTAX  AccountCouter
                ACCESS  read-only
                STATUS  mandatory
                DESCRIPTION
                "Port Exceeding Packets Counter in blocks (1 block = 64k bytes) for Port."
                ::= { nbRtAccVifPortEntry 9 }

nbRtAccPortHighConformingBytes   OBJECT-TYPE
                SYNTAX  Counter32
                ACCESS  read-only
                STATUS  mandatory
                DESCRIPTION
                "Port Conforming Bytes Counter (High part) for Port."
                ::= { nbRtAccVifPortEntry 11 }

nbRtAccPortHighExceedingBytes   OBJECT-TYPE
                SYNTAX  Counter32
                ACCESS  read-only
                STATUS  mandatory
                DESCRIPTION
                "Port Exceeding Bytes Counter (High part) for Port."
                ::= { nbRtAccVifPortEntry 12 }

nbRtAccPortHighConformingPackets   OBJECT-TYPE
                SYNTAX  Counter32
                ACCESS  read-only
                STATUS  mandatory
                DESCRIPTION
                "Port Conforming Packets Counter (High part) for Port."
                ::= { nbRtAccVifPortEntry 13 }

nbRtAccPortHighExceedingPackets   OBJECT-TYPE
                SYNTAX  Counter32
                ACCESS  read-only
                STATUS  mandatory
                DESCRIPTION
                "Port Exceeding Packets Counter (High part) for Port."
                ::= { nbRtAccVifPortEntry 14 }

nbRtAccPortLowConformingBytes   OBJECT-TYPE
                SYNTAX  Counter32
                ACCESS  read-only
                STATUS  mandatory
                DESCRIPTION
                "Port Conforming Bytes Counter (Low part) for Port."
                ::= { nbRtAccVifPortEntry 15 }

nbRtAccPortLowExceedingBytes   OBJECT-TYPE
                SYNTAX  Counter32
                ACCESS  read-only
                STATUS  mandatory
                DESCRIPTION
                "Port Exceeding Bytes Counter (Low part) for Port."
                ::= { nbRtAccVifPortEntry 16 }

nbRtAccPortLowConformingPackets   OBJECT-TYPE
                SYNTAX  Counter32
                ACCESS  read-only
                STATUS  mandatory
                DESCRIPTION
                "Port Conforming Packets Counter (Low part) for Port."
                ::= { nbRtAccVifPortEntry 17 }

nbRtAccPortLowExceedingPackets   OBJECT-TYPE
                SYNTAX  Counter32
                ACCESS  read-only
                STATUS  mandatory
                DESCRIPTION
                "Port Exceeding Packets Counter (Low part) for Port."
                ::= { nbRtAccVifPortEntry 18 }

nbRtAccPortVif64ConformingBytes   OBJECT-TYPE
                SYNTAX  AccountCounter64
                ACCESS  read-only
                STATUS  mandatory
                DESCRIPTION
                "The Conforming Bytes Counter (64 bits) for Port."
                ::= { nbRtAccVifPortEntry 19 }

nbRtAccPortVif64ExceedingBytes   OBJECT-TYPE
                SYNTAX  AccountCounter64
                ACCESS  read-only
                STATUS  mandatory
                DESCRIPTION
                "The Exceeding Bytes Counter (64 bits) for Port."
                ::= { nbRtAccVifPortEntry 20 }

nbRtAccPortConformingUcastPackets   OBJECT-TYPE
                SYNTAX  AccountCouter
                ACCESS  read-only
                STATUS  mandatory
                DESCRIPTION
                "The Conforming Unicast Packets Counter
                 in blocks (1 block = 64k bytes) for VIF."
                ::= { nbRtAccVifPortEntry 21 }

nbRtAccPortHighConformingUcastPackets   OBJECT-TYPE
                SYNTAX  Counter32
                ACCESS  read-only
                STATUS  mandatory
                DESCRIPTION
                "The Conforming Unicast Packets Counter
                 (High part) for VIF."
                ::= { nbRtAccVifPortEntry 22 }

nbRtAccPortLowConformingUcastPackets   OBJECT-TYPE
                SYNTAX  Counter32
                ACCESS  read-only
                STATUS  mandatory
                DESCRIPTION
                "The Conforming Unicast Packets Counter
                 (Low part) for VIF."
                ::= { nbRtAccVifPortEntry 23 }

nbRtAccPort64ConformingUcastPackets   OBJECT-TYPE
                SYNTAX  AccountCounter64
                ACCESS  read-only
                STATUS  mandatory
                DESCRIPTION
                "The Conforming Unicast Bytes Counter
                 (64 bits) for VIF."
                ::= { nbRtAccVifPortEntry 24 }

nbRtAccPortConformingMcastPackets   OBJECT-TYPE
                SYNTAX  AccountCouter
                ACCESS  read-only
                STATUS  mandatory
                DESCRIPTION
                "The Conforming Multicast Packets Counter
                 in blocks (1 block = 64k bytes) for VIF."
                ::= { nbRtAccVifPortEntry 25 }

nbRtAccPortHighConformingMcastPackets   OBJECT-TYPE
                SYNTAX  Counter32
                ACCESS  read-only
                STATUS  mandatory
                DESCRIPTION
                "The Conforming Multicast Packets Counter
                 (High part) for VIF."
                ::= { nbRtAccVifPortEntry 26 }

nbRtAccPortLowConformingMcastPackets   OBJECT-TYPE
                SYNTAX  Counter32
                ACCESS  read-only
                STATUS  mandatory
                DESCRIPTION
                "The Conforming Multicast Packets Counter
                 (Low part) for VIF."
                ::= { nbRtAccVifPortEntry 27 }

nbRtAccPort64ConformingMcastPackets   OBJECT-TYPE
                SYNTAX  AccountCounter64
                ACCESS  read-only
                STATUS  mandatory
                DESCRIPTION
                "The Conforming Multicast Bytes Counter
                 (64 bits) for VIF."
                ::= { nbRtAccVifPortEntry 28 }

nbRtAccPortConformingBcastPackets   OBJECT-TYPE
                SYNTAX  AccountCouter
                ACCESS  read-only
                STATUS  mandatory
                DESCRIPTION
                "The Conforming Broadcast Packets Counter
                 in blocks (1 block = 64k bytes) for VIF."
                ::= { nbRtAccVifPortEntry 29 }

nbRtAccPortHighConformingBcastPackets   OBJECT-TYPE
                SYNTAX  Counter32
                ACCESS  read-only
                STATUS  mandatory
                DESCRIPTION
                "The Conforming Broadcast Packets Counter
                 (High part) for VIF."
                ::= { nbRtAccVifPortEntry 30 }

nbRtAccPortLowConformingBcastPackets   OBJECT-TYPE
                SYNTAX  Counter32
                ACCESS  read-only
                STATUS  mandatory
                DESCRIPTION
                "The Conforming Broadcast Packets Counter
                 (Low part) for VIF."
                ::= { nbRtAccVifPortEntry 31 }

nbRtAccPort64ConformingBcastPackets   OBJECT-TYPE
                SYNTAX  AccountCounter64
                ACCESS  read-only
                STATUS  mandatory
                DESCRIPTION
                "The Conforming Broadcast Bytes Counter
                 (64 bits) for VIF."
                ::= { nbRtAccVifPortEntry 32 }

-- ***********************************************************************
-- VIF Access Lists Group
-- ***********************************************************************

nbRtAccessLists      OBJECT IDENTIFIER ::= { nbRouterConfig 7 }

-- ***********************************************************************
-- VIF - Access Lists Binding Table
-- ***********************************************************************

nbAclVifTable OBJECT-TYPE
                SYNTAX  SEQUENCE OF NbAclVifEntry
                ACCESS  not-accessible
                STATUS  mandatory
                DESCRIPTION
                "."
                ::= { nbRtAccessLists 5 }

nbAclVifEntry OBJECT-TYPE
                SYNTAX  NbAclVifEntry
                ACCESS  not-accessible
                STATUS  mandatory
                DESCRIPTION
                "The Entries (records)."
                INDEX { nbVifType,
                        nbVifDevNo,
                        nbVifIsAlias,
                        nbVifAliasDev,
                        nbAclVifDirection,
			nbAclVifId }

                ::= { nbAclVifTable 1 }

NbAclVifEntry   ::= SEQUENCE {
		nbAclVifDirection           DirectionType,
		nbAclVifId		    INTEGER,
                nbAclVifAccessListName      DisplayString,
		nbAclVifBindingStatus       INTEGER
                }

nbAclVifDirection    OBJECT-TYPE
                SYNTAX DirectionType
                ACCESS read-only
                STATUS mandatory
                DESCRIPTION
                "The ingress/egress direction."
                ::= { nbAclVifEntry 5 }

nbAclVifId         OBJECT-TYPE
                SYNTAX		    INTEGER
		ACCESS read-only
                STATUS mandatory
                DESCRIPTION
                "The consequent number of the Access List binded to the VIF."
                ::= { nbAclVifEntry 6 }

nbAclVifAccessListName    OBJECT-TYPE
	        SYNTAX DisplayString
                ACCESS read-write
                STATUS mandatory
                DESCRIPTION
                "Access List name corresponding with VIF."
	::= { nbAclVifEntry 7 }

nbAclVifBindingStatus    OBJECT-TYPE
	        SYNTAX INTEGER
		{
                  bind      (1),
                  unbind    (2)
		}
		ACCESS read-write
                STATUS mandatory
                DESCRIPTION
		"Enable or disable the binding of an acl to a VIF entry."
		::= { nbAclVifEntry 8 }

-- ***********************************************************************
-- Port Tag Outbound Group
-- ***********************************************************************

nbRtPortTagGroup      OBJECT IDENTIFIER ::= { nbRouterConfig 8 }

-- ***********************************************************************
-- Port Tag Outbound Table
-- ***********************************************************************

nbRtPortTagTable  OBJECT-TYPE
            SYNTAX  SEQUENCE OF NbRtPortTagEntry
            ACCESS  not-accessible
            STATUS  mandatory
            DESCRIPTION
            "."
            ::= { nbRtPortTagGroup 5 }

nbRtPortTagEntry  OBJECT-TYPE
            SYNTAX  NbRtPortTagEntry
            ACCESS  not-accessible
            STATUS  mandatory
            DESCRIPTION
            "The Entries (records)."
            INDEX { nbRtPortTagId }
            ::= { nbRtPortTagTable 1 }
        
NbRtPortTagEntry ::= SEQUENCE {
	    nbRtPortTagId                INTEGER,
	    nbRtPortTagAwareMode         INTEGER,
	    nbRtPortTagEtherType         INTEGER,
	    nbRtPortTagIpDefTag          INTEGER,
	    nbRtPortTagPortDefTag        INTEGER,
	    nbRtPortTagVmanDefTag        INTEGER,
	    nbRtPortTagNumberOfTags      INTEGER,
	    nbRtPortTagMplsForceMode     INTEGER
	    }

nbRtPortTagId   OBJECT-TYPE
            SYNTAX INTEGER
            ACCESS read-only
            STATUS mandatory
            DESCRIPTION
            "Port Tag Outbound Id."
            ::= { nbRtPortTagEntry 1 }

nbRtPortTagAwareMode   OBJECT-TYPE
            SYNTAX INTEGER
            {
             other             (1),
             tagged            (2),
             untagged          (3),
             hybrid            (4),
             qInQtagged        (5),
             qInQuntagged      (6),
             qInQuntagged2     (7)
            }
            ACCESS read-write
            STATUS mandatory
            DESCRIPTION
            "Port Tag Outbound mode.
             Type 'hybrid' means tagged with defaults.
             VMAN Types 'qInQ...' permit the stack of tags."
            ::= { nbRtPortTagEntry 2 }

nbRtPortTagEtherType   OBJECT-TYPE
            SYNTAX INTEGER ( 1..65535)
            ACCESS read-write
            STATUS mandatory
            DESCRIPTION
            "Ethernet type used for Q in Q packets (hex value)."
            ::= { nbRtPortTagEntry 3 }

nbRtPortTagIpDefTag   OBJECT-TYPE
            SYNTAX INTEGER ( 0..4080 )
            ACCESS read-write
            STATUS mandatory
            DESCRIPTION
            "Tag Default value for IP Interface."
            ::= { nbRtPortTagEntry 4 }

nbRtPortTagPortDefTag   OBJECT-TYPE
            SYNTAX INTEGER ( 0..4080 )
            ACCESS read-write
            STATUS mandatory
            DESCRIPTION
            "Tag Default value for Port Interface."
            ::= { nbRtPortTagEntry 5 }

nbRtPortTagVmanDefTag   OBJECT-TYPE
            SYNTAX INTEGER ( 0..4080 )
            ACCESS read-write
            STATUS mandatory
            DESCRIPTION
            "Tag Default value for VMAN Access Port."
            ::= { nbRtPortTagEntry 6 }

nbRtPortTagNumberOfTags   OBJECT-TYPE
            SYNTAX INTEGER
            ACCESS read-only
            STATUS mandatory
            DESCRIPTION
            "Number of Tags"
            ::= { nbRtPortTagEntry 7 }

nbRtPortTagMplsForceMode   OBJECT-TYPE
            SYNTAX INTEGER
            {
             other             (1),
             mplsForceTag      (2),
             noMplsForceTag    (3)
            }
            ACCESS read-only
            STATUS mandatory
            DESCRIPTION
            "MPLS Force Tag Mode."
            ::= { nbRtPortTagEntry 8 }

-- ***********************************************************************
-- Action Lists Group
-- ***********************************************************************

nbRtActionLists      OBJECT IDENTIFIER ::= { nbRouterConfig 9 }

-- ***********************************************************************

nbRtActionListSupport       OBJECT-TYPE
                SYNTAX  INTEGER
                {
                 notSupported   (1),
                 supported      (2)
                }
                ACCESS  read-only
                STATUS  mandatory
                DESCRIPTION
                "The Action List feature support."
                ::= { nbRtActionLists 1 }

nbRtActionListTable	OBJECT-TYPE
                SYNTAX  SEQUENCE OF NbRtActionListEntry
                ACCESS  not-accessible
                STATUS  mandatory
                DESCRIPTION
                "."
                ::= { nbRtActionLists 2 }

nbRtActionListEntry	OBJECT-TYPE
		SYNTAX  NbRtActionListEntry
                ACCESS  not-accessible
                STATUS  mandatory
                DESCRIPTION
                "The Entries (records)."
                INDEX { nbRtActionListName }
                ::= { nbRtActionListTable 1 }

NbRtActionListEntry ::= SEQUENCE {
                nbRtActionListName              ActionListName,
		nbRtActionListAdminStatus       INTEGER,
		nbRtActionListOperStatus        INTEGER,
		nbRtActionListPoliceType        INTEGER,
		nbRtActionListMplsType          INTEGER
		}

nbRtActionListName    OBJECT-TYPE
	        SYNTAX ActionListName
                ACCESS read-only
                STATUS mandatory
                DESCRIPTION
                "Action List name."
		::= { nbRtActionListEntry 1 }

nbRtActionListAdminStatus    OBJECT-TYPE
                SYNTAX INTEGER
                {
		 valid	 (1),
        	 invalid (2)
                }
                ACCESS read-write
                STATUS mandatory
                DESCRIPTION
                "Controls the Add/Edit/Delete of the Action List."
		::= { nbRtActionListEntry 2 }

nbRtActionListOperStatus    OBJECT-TYPE
                SYNTAX INTEGER
                {
		 active	 (1),
        	 notActive (2)
                }
                ACCESS read-only
                STATUS mandatory
                DESCRIPTION
                "Binding status of the Action List."
		::= { nbRtActionListEntry 3 }

nbRtActionListPoliceType    OBJECT-TYPE
                SYNTAX INTEGER
                {
		 enable		(1),
        	 disable	(2)
                }
                ACCESS read-only
                STATUS mandatory
                DESCRIPTION
                "Police action inside the Action List."
		::= { nbRtActionListEntry 4 }

nbRtActionListMplsType    OBJECT-TYPE
                SYNTAX INTEGER
                {
		 enable		(1),
        	 disable	(2)
                }
                ACCESS read-only
                STATUS mandatory
                DESCRIPTION
                "MPLS action inside the Action List."
		::= { nbRtActionListEntry 5 }


-- ***********************************************************************
-- Police Action Group
-- ***********************************************************************

nbRtPoliceAction      OBJECT IDENTIFIER ::= { nbRtActionLists 3 }

-- ***********************************************************************
-- Police Action Table
-- ***********************************************************************

nbRtPoliceActionTable        OBJECT-TYPE
                SYNTAX  SEQUENCE OF NbRtPoliceActionEntry
                ACCESS  not-accessible
                STATUS  mandatory
                DESCRIPTION
                "."
                ::= { nbRtPoliceAction 1 }

nbRtPoliceActionEntry        OBJECT-TYPE
                SYNTAX  NbRtPoliceActionEntry
                ACCESS  not-accessible
                STATUS  mandatory
                DESCRIPTION
                "The Entries (records)."
                INDEX { nbRtPoliceActionName }
                ::= { nbRtPoliceActionTable 1 }

NbRtPoliceActionEntry ::= SEQUENCE {
                nbRtPoliceActionName                    ActionListName,
		nbRtPoliceActionOperMode                INTEGER,
		nbRtPoliceActionSharingMode             INTEGER,
                nbRtPoliceActionAdminStatus             INTEGER,
		nbRtPoliceActionExceedCntAdminStatus    INTEGER,
                nbRtPoliceActionExceedCntOperStatus     INTEGER,
		nbRtPoliceActionTotalExceedBytesCnt     AccountCounter64,
		nbRtPoliceActionTotalExceedFramesCnt    AccountCounter64,
                nbRtPoliceActionTotalHighExceedBytes32  Counter32,
                nbRtPoliceActionTotalLowExceedBytes32   Counter32,
                nbRtPoliceActionTotalHighExceedFrames32 Counter32,
                nbRtPoliceActionTotalLowExceedFrames32  Counter32
                }

nbRtPoliceActionName    OBJECT-TYPE
	        SYNTAX ActionListName
                ACCESS read-only
                STATUS mandatory
                DESCRIPTION
                "Police Action List name."
		::= { nbRtPoliceActionEntry 1 }

nbRtPoliceActionOperMode    OBJECT-TYPE
                SYNTAX INTEGER
                {
                 other			(1),
		 noREDnoCoS		(2),
		 redTCPnoCoS		(3),
                 redAllnoCoS		(4),
		 coSaware		(5)
                }
                ACCESS read-write
                STATUS mandatory
                DESCRIPTION
                "The Police Action Rate Limit RED Mode."
                ::= { nbRtPoliceActionEntry 2 }

nbRtPoliceActionSharingMode    OBJECT-TYPE
                SYNTAX INTEGER
                {
                 other              (1),
                 enable             (2),
                 disable            (3)
                }
                ACCESS read-write
                STATUS mandatory
                DESCRIPTION
                "The Police Action Sharing Mode."
                ::= { nbRtPoliceActionEntry 3 }

nbRtPoliceActionAdminStatus    OBJECT-TYPE
                SYNTAX INTEGER
                {
		 valid	 (1),
        	 invalid (2)
                }
                ACCESS read-write
                STATUS mandatory
                DESCRIPTION
                "Controls the Add/Edit/Delete of the Police Action."
                ::= { nbRtPoliceActionEntry 4 }

nbRtPoliceActionExceedCntAdminStatus	OBJECT-TYPE
                SYNTAX INTEGER
                {
                 other      (1),
                 enable     (2),
                 disable    (3),
                 pause      (4),
                 resume     (5),
                 clear      (6)
                }
                ACCESS read-write
                STATUS mandatory
                DESCRIPTION
                "Police Exceeding Accounting Admin Status."
                ::= { nbRtPoliceActionEntry 5 }

nbRtPoliceActionExceedCntOperStatus    OBJECT-TYPE
                SYNTAX INTEGER
                {
                 other      (1),
                 active     (2),
                 paused     (3),
                 disabled   (4)
                }
                ACCESS read-only
                STATUS mandatory
                DESCRIPTION
                "Police Exceeding Accounting Oper Status."
                ::= { nbRtPoliceActionEntry 6 }

nbRtPoliceActionTotalExceedBytesCnt   OBJECT-TYPE
                SYNTAX  AccountCounter64
                ACCESS  read-only
                STATUS  mandatory
                DESCRIPTION
                "The Exceeding Bytes Counter (64 bits)
                 for Police Action."
                ::= { nbRtPoliceActionEntry 7 }

nbRtPoliceActionTotalExceedFramesCnt   OBJECT-TYPE
                SYNTAX  AccountCounter64
                ACCESS  read-only
                STATUS  mandatory
                DESCRIPTION
                "The Exceeding Frames Counter (64 bits)
                 for Police Action."
                ::= { nbRtPoliceActionEntry 8 }

nbRtPoliceActionTotalHighExceedBytes32   OBJECT-TYPE
                SYNTAX  Counter32
                ACCESS  read-only
                STATUS  mandatory
                DESCRIPTION
                "The High part of Exceeding Bytes Counter (32 bits)
                 for Police Action."
                ::= { nbRtPoliceActionEntry 9 }

nbRtPoliceActionTotalLowExceedBytes32   OBJECT-TYPE
                SYNTAX  Counter32
                ACCESS  read-only
                STATUS  mandatory
                DESCRIPTION
                "The Low part of Exceeding Bytes Counter (32 bits)
                 for Police Action."
                ::= { nbRtPoliceActionEntry 10 }

nbRtPoliceActionTotalHighExceedFrames32   OBJECT-TYPE
                SYNTAX  Counter32
                ACCESS  read-only
                STATUS  mandatory
                DESCRIPTION
                "The High part of Exceeding Frames Counter (32 bits)
                 for Police Action."
                ::= { nbRtPoliceActionEntry 11 }

nbRtPoliceActionTotalLowExceedFrames32   OBJECT-TYPE
                SYNTAX  Counter32
                ACCESS  read-only
                STATUS  mandatory
                DESCRIPTION
                "The Low part of Exceeding Frames Counter (32 bits)
                 for Police Action."
                ::= { nbRtPoliceActionEntry 12 }

-- ***********************************************************************
-- Police Rate Limit Table
-- ***********************************************************************

nbRtPoliceRateLimitTable        OBJECT-TYPE
                SYNTAX  SEQUENCE OF NbRtPoliceRateLimitEntry
                ACCESS  not-accessible
                STATUS  mandatory
                DESCRIPTION
                "."
                ::= { nbRtPoliceAction 2 }

nbRtPoliceRateLimitEntry        OBJECT-TYPE
                SYNTAX  NbRtPoliceRateLimitEntry
                ACCESS  not-accessible
                STATUS  mandatory
                DESCRIPTION
                "The Entries (records)."
                INDEX { nbRtPoliceRateLimitName,
			nbRtPoliceRateLimitCoSlevel }
                ::= { nbRtPoliceRateLimitTable 1 }

NbRtPoliceRateLimitEntry ::= SEQUENCE {
                nbRtPoliceRateLimitName                 ActionListName,
                nbRtPoliceRateLimitCoSlevel             INTEGER,
                nbRtPoliceRateLimitBuckRate             INTEGER,
                nbRtPoliceRateLimitBuckSize             INTEGER,
		nbRtPoliceRateLimitOperMode             INTEGER,
		nbRtPoliceRateLimitExceedBytesCnt       AccountCounter64,
		nbRtPoliceRateLimitExceedFramesCnt      AccountCounter64,
                nbRtPoliceRateLimitHighExceedBytes32    Counter32,
                nbRtPoliceRateLimitLowExceedBytes32     Counter32,
                nbRtPoliceRateLimitHighExceedFrames32   Counter32,
                nbRtPoliceRateLimitLowExceedFrames32    Counter32
                }

nbRtPoliceRateLimitName    OBJECT-TYPE
	        SYNTAX ActionListName
                ACCESS read-only
                STATUS mandatory
                DESCRIPTION
                "Police Action List name."
		::= { nbRtPoliceRateLimitEntry 1 }

nbRtPoliceRateLimitCoSlevel    OBJECT-TYPE
                SYNTAX INTEGER -- (1..4)
                ACCESS read-only
                STATUS mandatory
                DESCRIPTION
                "The Police Action CoS Level."
                ::= { nbRtPoliceRateLimitEntry 2 }

nbRtPoliceRateLimitBuckRate   OBJECT-TYPE
                SYNTAX INTEGER -- (26..1048576)
                ACCESS read-write
                STATUS mandatory
                DESCRIPTION
                "The Token Bucket Rate parameter (in Kbit/sec)."
                ::= { nbRtPoliceRateLimitEntry 3 }

nbRtPoliceRateLimitBuckSize   OBJECT-TYPE
                SYNTAX INTEGER -- (2048..65535)
                ACCESS read-write
                STATUS mandatory
                DESCRIPTION
                "The Token Bucket burst Size parameter (in bytes).
                The value '0' means - 'optimize'."
                ::= { nbRtPoliceRateLimitEntry 4 }

nbRtPoliceRateLimitOperMode    OBJECT-TYPE
                SYNTAX INTEGER
                {
                 other			(1),
		 noREDnoCoS		(2),
		 redTCPnoCoS		(3),
                 redAllnoCoS		(4),
		 coSnoRED		(5),
                 coSguarantee		(6),
		 coSREDtcp		(7),
		 coSREDall		(8),
		 coSguaranteeREDtcp	(9),
		 coSguaranteeREDall	(10)
                }
                ACCESS read-write
                STATUS mandatory
                DESCRIPTION
                "The Police Action Rate Limit Operation Mode."
                ::= { nbRtPoliceRateLimitEntry 5 }

nbRtPoliceRateLimitExceedBytesCnt   OBJECT-TYPE
                SYNTAX  AccountCounter64
                ACCESS  read-only
                STATUS  mandatory
                DESCRIPTION
                "The Exceeding Bytes Counter (64 bits)
                 for Police Action CoS Level."
                ::= { nbRtPoliceRateLimitEntry 6 }

nbRtPoliceRateLimitExceedFramesCnt   OBJECT-TYPE
                SYNTAX  AccountCounter64
                ACCESS  read-only
                STATUS  mandatory
                DESCRIPTION
                "The Exceeding Frames Counter (64 bits)
                 for Police Action CoS Level."
                ::= { nbRtPoliceRateLimitEntry 7 }

nbRtPoliceRateLimitHighExceedBytes32   OBJECT-TYPE
                SYNTAX  Counter32
                ACCESS  read-only
                STATUS  mandatory
                DESCRIPTION
                "The High part of Exceeding Bytes Counter (32 bits)
                 for Police Action CoS Level."
                ::= { nbRtPoliceRateLimitEntry 8 }

nbRtPoliceRateLimitLowExceedBytes32   OBJECT-TYPE
                SYNTAX  Counter32
                ACCESS  read-only
                STATUS  mandatory
                DESCRIPTION
                "The Low part of Exceeding Bytes Counter (32 bits)
                 for Police Action CoS Level."
                ::= { nbRtPoliceRateLimitEntry 9 }

nbRtPoliceRateLimitHighExceedFrames32   OBJECT-TYPE
                SYNTAX  Counter32
                ACCESS  read-only
                STATUS  mandatory
                DESCRIPTION
                "The High part of Exceeding Frames Counter (32 bits)
                 for Police Action CoS Level."
                ::= { nbRtPoliceRateLimitEntry 10 }

nbRtPoliceRateLimitLowExceedFrames32   OBJECT-TYPE
                SYNTAX  Counter32
                ACCESS  read-only
                STATUS  mandatory
                DESCRIPTION
                "The Low part of Exceeding Frames Counter (32 bits)
                 for Police Action CoS Level."
                ::= { nbRtPoliceRateLimitEntry 11 }

-- ***********************************************************************
-- VIF - Action Lists Binding Table
-- ***********************************************************************

nbRtPoliceActionVifTable OBJECT-TYPE
                SYNTAX  SEQUENCE OF NbRtPoliceActionVifEntry
                ACCESS  not-accessible
                STATUS  mandatory
                DESCRIPTION
                "."
                ::= { nbRtActionLists 4 }

nbRtPoliceActionVifEntry OBJECT-TYPE
                SYNTAX  NbRtPoliceActionVifEntry
                ACCESS  not-accessible
                STATUS  mandatory
                DESCRIPTION
                "The Entries (records)."
                INDEX { nbVifType,
                        nbVifDevNo,
                        nbVifIsAlias,
                        nbVifAliasDev,
			nbRtPoliceActionVifDirection,
			nbRtPoliceActionVifName }

                ::= { nbRtPoliceActionVifTable 1 }

NbRtPoliceActionVifEntry   ::= SEQUENCE {
		nbRtPoliceActionVifDirection            DirectionType,
		nbRtPoliceActionVifName                 ActionListName,
                nbRtPoliceActionVifPortList             OCTET STRING,
		nbRtPoliceActionVifBindingStatus        INTEGER
                }

nbRtPoliceActionVifDirection    OBJECT-TYPE
                SYNTAX DirectionType
                ACCESS read-only
                STATUS mandatory
                DESCRIPTION
                "The ingress/egress direction."
                ::= { nbRtPoliceActionVifEntry 1 }

nbRtPoliceActionVifName    OBJECT-TYPE
	        SYNTAX ActionListName
                ACCESS read-only
                STATUS mandatory
                DESCRIPTION
                "The Name of the Police Action, binded to the VIF."
		::= { nbRtPoliceActionVifEntry 2 }

nbRtPoliceActionVifPortList    OBJECT-TYPE
	        SYNTAX OCTET STRING
                ACCESS read-write
                STATUS mandatory
                DESCRIPTION
                "The list of ports Police Action List is binded to."
		::= { nbRtPoliceActionVifEntry 3 }

nbRtPoliceActionVifBindingStatus    OBJECT-TYPE
	        SYNTAX INTEGER
		{
                  addNewBind       (1),
                  unbind           (2),
                  editExistingBind (3)
		}
		ACCESS read-write
                STATUS mandatory
                DESCRIPTION
		"Add New, Edit Existing, Delete the Binding
                 of an Police Action to a VIF entry."
		::= { nbRtPoliceActionVifEntry 4}

-- ***********************************************************************
-- MPLS Action Group
-- ***********************************************************************
nbRtMplsAction      OBJECT IDENTIFIER ::= { nbRtActionLists 5 }

-- ***********************************************************************
--              T R A P s   D e f i n i t i o n s
-- ***********************************************************************

nbVifModify TRAP-TYPE
          ENTERPRISE nbRouterConfig
          VARIABLES { nbVifDevName,
              nbVifAdminStatus,
              nbVifPhysType,
              nbVifProtocol,
              nbVifState,
              nbVifName,
              nbVifIpAddress,
              nbVifMask,
              nbVifPortList,
              nbVifMac,
              nbVifPeer,
              nbVifConfigType,
              nbVifSecurity}
            DESCRIPTION
          "The SNMP trap that is generated when any VIF
           is created/modified/deleted...
           NOTE: the index fields are :
            - [nbVifType],
            - [nbVifDevNo],
            - [nbVifIsAlias],
            - [nbVifAliasDev]."
                ::= 11

END
