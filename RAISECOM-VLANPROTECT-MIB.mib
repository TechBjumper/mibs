--MibName=rcVlanCfg
-- *****************************************************************
-- RAISECOM-VLAN-MIB.MIB:  Raisecom VLAN MIB file
-- 20121120, shijunfang
--
-- Copyright (c) 2010-2014 by Raisecom, Inc.
-- All rights reserved.
--
-- *****************************************************************
RAISECOM-VLANPROTECT-MIB  DEFINITIONS ::= BEGIN   


IMPORTS
        raisecomAgent                     FROM RAISECOM-BASE-MIB                                             
        RowStatus                         FROM SNMPv2-TC
        Vlanset, PortList                 FROM SWITCH-TC  
        VlanId                            FROM Q-BRIDGE-MIB
        MODULE-IDENTITY, OBJECT-TYPE,
        Integer32                         FROM SNMPv2-SMI 
	    TEXTUAL-CONVENTION                FROM SNMPv2-TC;


	raisecomVlanProtect MODULE-IDENTITY
        LAST-UPDATED    "201209180000Z"
        ORGANIZATION    "Raisecom, Inc."
        CONTACT-INFO
                "       Raise Systems

                Postal: Beijing,
                        China

                   Tel: 86-010-82884499

                E-mail: support@raisecom.com"
        DESCRIPTION
                "description of vlan Protect object."
                ::= { raisecomAgent 82}      

-- -------------------------------------------------------------
-- groups in the SWITCH-VLANCFG MIB
-- -------------------------------------------------------------

raisecomVlanProtectConfig  OBJECT IDENTIFIER ::= { raisecomVlanProtect 1 }
                                              
raisecomVlanProtectGroupTable OBJECT-TYPE
       SYNTAX      SEQUENCE OF RaisecomVlanProtectGroupEntry
       MAX-ACCESS  not-accessible
       STATUS      current
       DESCRIPTION
           "Vlan Protect configuration table."
       ::= { raisecomVlanProtectConfig 1 }
      
raisecomVlanProtectGroupEntry OBJECT-TYPE
       SYNTAX      RaisecomVlanProtectGroupEntry
       MAX-ACCESS  not-accessible
       STATUS      current
       DESCRIPTION
        "Defines an entry in the raisecomVlanProtectGroupTable."
       INDEX   { raisecomVlanProtectGroupId }
       ::= { raisecomVlanProtectGroupTable 1 }  
    
RaisecomVlanProtectGroupEntry ::= SEQUENCE {
       raisecomVlanProtectGroupId                           Integer32,
       raisecomVlanProtectGroupVlanId                     VlanId,
       raisecomVlanProtectGroupPortlist                     PortList,
       raisecomVlanProtectGroupRowStatus                   RowStatus
      } 
     
raisecomVlanProtectGroupId OBJECT-TYPE
       SYNTAX Integer32 
       MAX-ACCESS not-accessible
       STATUS current
       DESCRIPTION
       "This object indicates the protect group id."
       ::= { raisecomVlanProtectGroupEntry 1 }
       
raisecomVlanProtectGroupVlanId OBJECT-TYPE
       SYNTAX      VlanId
       MAX-ACCESS  read-create
       STATUS      current
       DESCRIPTION
       "This object indicates the vlan id of protect group."
        ::= { raisecomVlanProtectGroupEntry 2 } 
        
raisecomVlanProtectGroupPortlist OBJECT-TYPE
       SYNTAX      PortList
       MAX-ACCESS  read-create
       STATUS      current
       DESCRIPTION
       "This object indicates the port list of protect group."
        ::= { raisecomVlanProtectGroupEntry 3 }         
        
raisecomVlanProtectGroupRowStatus OBJECT-TYPE
        SYNTAX  RowStatus
        MAX-ACCESS read-create
        STATUS current
        DESCRIPTION
            "This object indicates protect group status of this table entry. 
            You can set createandgo(4) to create and activate a new entry;
            or set destroy(6) to delete an entry."
        ::= { raisecomVlanProtectGroupEntry 4 }


END
