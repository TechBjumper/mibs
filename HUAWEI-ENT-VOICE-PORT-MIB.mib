-- ============================================================================
-- Copyright (C) 2011 by  HUAWEI TECHNOLOGIES. All rights reserved.
--
-- Description:  
-- Reference:  
-- Version: V1.0
-- History:
-- ============================================================================

 HUAWEI-ENT-VOICE-PORT-MIB DEFINITIONS ::= BEGIN
      IMPORTS
        	MODULE-IDENTITY, OBJECT-TYPE, NOTIFICATION-TYPE, private,Integer32, Unsigned32
        		FROM SNMPv2-SMI
        	MODULE-COMPLIANCE, OBJECT-GROUP, NOTIFICATION-GROUP
        		FROM SNMPv2-CONF
        	TEXTUAL-CONVENTION
        		FROM SNMPv2-TC
        	IpAddress,TimeTicks,Counter32
        		FROM SNMPv2-SMI
        	RowStatus,DisplayString
        		FROM SNMPv2-TC
        	hwDatacomm
        		FROM HUAWEI-MIB;
        
      hwEntVoicePortMIB MODULE-IDENTITY
                LAST-UPDATED "201105050000Z"
      ORGANIZATION 
                "Huawei Technologies Co.,Ltd."
      CONTACT-INFO 
              "Huawei Industrial Base                
              Bantian, Longgang                     
              Shenzhen 518129                       
              People's Republic of China            
              Website: http://www.huawei.com        
              Email: support@huawei.com             
              "   
                DESCRIPTION 
                	            "
                	            huawei VOICE PORT  mib."

								--  Revision history
								
								REVISION     "201105050000Z"
								            DESCRIPTION  "V1.0, create"
								            
                ::= { hwDatacomm 252 }

   hwEntFxsPortConfigTable OBJECT-TYPE
     SYNTAX      SEQUENCE OF HwEntFxsPortConfigEntry
     MAX-ACCESS  not-accessible
     STATUS      current
     DESCRIPTION
       "
       Indicates the attribute configuration table of fxs ports.
       "
     ::= { hwEntVoicePortMIB 1 }
 
   hwEntFxsPortConfigEntry OBJECT-TYPE
     SYNTAX      HwEntFxsPortConfigEntry
     MAX-ACCESS  not-accessible
     STATUS      current
     DESCRIPTION
       " Indicates the attribute configuration entry of fxs ports. "
     INDEX    {  
               hwEntFxsPortIndex
              }
     ::= { hwEntFxsPortConfigTable 1 }
 
   HwEntFxsPortConfigEntry ::=
     SEQUENCE
     {
       hwEntFxsPortIndex	              Integer32,
       hwEntFxsPortSendGain	              Integer32,
       hwEntFxsPortRecvGain 	          Integer32,
       hwEntFxsPortDialMode               INTEGER,
       hwEntFxsPortReversePoleEnable      INTEGER,
       hwEntFxsPortReversePoleLevel       Integer32,
       hwEntFxsPortPolarityReverseMode    INTEGER, 
       hwEntFxsPortLineLock               INTEGER,
       hwEntFxsPortNlpMode                INTEGER,
       hwEntFxsPortClipReversePole        INTEGER,
       hwEntFxsPortImpedance	          Integer32,
       hwEntFxsPortCurrent	              Integer32,
       hwEntFxsPortHighLevel              Integer32,
       hwEntFxsPortLowLevel               Integer32,
       hwEntFxsPortKcType                 INTEGER,
       hwEntFxsPortVoltage                Integer32,
       hwEntFxsPortActualSendGain         Integer32,
       hwEntFxsPortActualRecvGain         Integer32
     }
 
   hwEntFxsPortIndex OBJECT-TYPE
     SYNTAX      Integer32
     MAX-ACCESS  not-accessible
     STATUS      current
     DESCRIPTION
         "
         Indicates the slot/subcard/port index.
         bits 31-24 (8 bits): reserved
         bits 23-16 (8 bits): slot index
         bits 15-8  (8 bits): subcard index
         bits  7-0  (8 bits): port index 
         "
     ::= { hwEntFxsPortConfigEntry 1 }
 
   hwEntFxsPortSendGain OBJECT-TYPE
     SYNTAX      Integer32(0..22)
     MAX-ACCESS  read-write
     STATUS      current
     DESCRIPTION
         "
         Indicates the send gain the fxs port.
          0:    5 dB
          1:  4.5 dB
          2:    4 dB
          3:  3.5 dB
          4:    3 dB
          5:  2.5 dB
          6:    2 dB
          7:  1.5 dB
          8:    1 dB
          9:  0.5 dB
         10:    0 dB
         11: -0.5 dB
         12:   -1 dB
         13: -1.5 dB
         14:   -2 dB
         15: -2.5 dB
         16:   -3 dB
         17: -3.5 dB
         18:   -4 dB
         19: -4.5 dB
         20:   -5 dB
         21: -5.5 dB
         22:   -6 dB
         Default: 10
         "
     ::= { hwEntFxsPortConfigEntry 2 }
         
   hwEntFxsPortRecvGain OBJECT-TYPE
     SYNTAX      Integer32(0..24)
     MAX-ACCESS  read-write
     STATUS      current
     DESCRIPTION
         "
         Indicates the receive gain the fxs port.
          0:     0 dB  
          1:  -0.5 dB   
          2:    -1 dB  
          3:  -1.5 dB  
          4:    -2 dB  
          5:  -2.5 dB  
          6:    -3 dB  
          7:  -3.5 dB  
          8:    -4 dB  
          9:  -4.5 dB 
         10:    -5 dB 
         11:  -5.5 dB 
         12:    -6 dB 
         13:  -6.5 dB 
         14:    -7 dB 
         15:  -7.5 dB 
         16:    -8 dB 
         17:  -8.5 dB 
         18:    -9 dB 
         19:  -9.5 dB 
         20:   -10 dB 
         21: -10.5 dB 
         22:   -11 dB 
         23: -11.5 dB 
         24:   -12 dB
         Default: 14
         "
     ::= { hwEntFxsPortConfigEntry 3 }
          
   hwEntFxsPortDialMode OBJECT-TYPE
     SYNTAX      INTEGER{dtmfPulseBoth(1), dtmfOnly(2), pulseOnly(3)}
     MAX-ACCESS  read-write
     STATUS      current
     DESCRIPTION
         "
         Indicates the dialing mode.
         Options:
         dtmfPulseBoth(1)   -DTMF pulse both
         dtmfOnly(2)        -DTMF only
         pulseOnly(3)       -Pulse only
         Default: dtmfPulseBoth(1)
         "
     ::= { hwEntFxsPortConfigEntry 4 }
     
   hwEntFxsPortReversePoleEnable OBJECT-TYPE
     SYNTAX      INTEGER{enable(1), disable(2)}
     MAX-ACCESS  read-write
     STATUS      current
     DESCRIPTION
         "
         Indicates whether to support the polarity-reversing pulse.
         Options:
         enable(1)
         disable(2)
         Default: enable(1)
         "
     ::= { hwEntFxsPortConfigEntry 5 }
     
   hwEntFxsPortReversePoleLevel OBJECT-TYPE
     SYNTAX      Integer32(20..1270)
     MAX-ACCESS  read-write
     STATUS      current
     DESCRIPTION
         "
         Indicates the level width of the polarity-reversing pulse.
         Default: 100
         Unit: ms
         Step: 10 ms.
         "
     ::= { hwEntFxsPortConfigEntry 6 }
     
   hwEntFxsPortPolarityReverseMode OBJECT-TYPE
     SYNTAX      INTEGER{hard(1), soft(2)}
     MAX-ACCESS  read-write
     STATUS      current
     DESCRIPTION
         "
         Indicates the polarity reversal mode.
         Options:
         hard(1)   -Hard polarity reversal
         soft(2)   -Soft polarity reversal
         Default: hard(1)
         "
     ::= { hwEntFxsPortConfigEntry 7 }     
     
   hwEntFxsPortLineLock OBJECT-TYPE
     SYNTAX      INTEGER{enable(1), disable(2)}
     MAX-ACCESS  read-write
     STATUS      current
     DESCRIPTION
         "
         Indicates whether to support lock port.
         enable(1)
         disable(2)
         Default: enable(1)
         "
     ::= { hwEntFxsPortConfigEntry 8 }
     
   hwEntFxsPortNlpMode OBJECT-TYPE
     SYNTAX      INTEGER{normal(1),ecGainAdjust(2), enhance(3), reduce(4),disable(5)}
     MAX-ACCESS  read-write
     STATUS      current
     DESCRIPTION
         "
         Indicates the Nlp mode of the port.
         normal(1)         -Normal mode
         ecGainAdjust(2)   -Ec gain adjust mode
         enhance(3)        -Enhance mode
         reduce(4)         -Reduce mode
         disable(5):       -Close mode
         Default: normal(1)
         "
     ::= { hwEntFxsPortConfigEntry 9 }
     
   hwEntFxsPortClipReversePole OBJECT-TYPE
     SYNTAX      INTEGER{enable(1), disable(2)}
     MAX-ACCESS  read-write
     STATUS      current
     DESCRIPTION
         "
         Indicates whether to support the polarity-reversing pulse when Clip.
         enable(1)
         disable(2)
         Default: disable(2)
         "
     ::= { hwEntFxsPortConfigEntry 10 }
 
   hwEntFxsPortImpedance OBJECT-TYPE
     SYNTAX      Integer32(0..15)
     MAX-ACCESS  read-write
     STATUS      current
     DESCRIPTION
         " 	
 	     Indicates the port impedance of the board.
 	     Each value corresponds to the required impedance in a specified scenario.
 	      0: Bureau machine in China (200+680|| 100nf)
 	      1: User machine in China (200+560|| 100nf)
 	      2: 600-ohm interface
 	      3: Interface of Russia (150+510|| 47nf)
 	      4: (220+820|| 115nf )
 	      5: (220+820|| 120nf )
 	      6: 900-ohm interface
 	      7: Interface of Brazil (800|| 50nf)
 	      8: BT0(Zin=87+1052||228nF+229||28.4nF, Zload=93+615||471nF+179||495nF+244||32nF)
 	      9: HK-BT3(Zin=370+620|| 310nf,Zload=600)
 	     10: HK-BT5(Zin=270+264|| 357nf+1434|| 265nf,Zload=600)
 	     11: BT1(BT0 without AGC)
 	     12: BT2(Zin=(87 +1052 //228nF+229 //28.4nF),Zload=(270 +264 //357nF+1434 //265nF))
 	     13: BT3(Zin=(87 +1052 //228nF+229 //28.4nF),Zload=(164 +162 //363nF+1227 //350nF))	                      
 	     14: Commonly used in Europe (Zin= 270+750|| 150nf)
 	     15: New zealand (Zin=370+620|| 310nf)                      
 	     Default: 2
         "
         ::= { hwEntFxsPortConfigEntry 11 }
 
   hwEntFxsPortCurrent OBJECT-TYPE
     SYNTAX      Integer32(0..1)
     MAX-ACCESS  read-write
     STATUS      current
     DESCRIPTION
         "
         Port current supported by the board. The value ranges from 0 to 1, which indicates the port current value.
         0: 16mA steady current   
         1: 20mA steady current
 	     Default: 1
         "  
     ::= { hwEntFxsPortConfigEntry 12 }  

   hwEntFxsPortHighLevel OBJECT-TYPE
     SYNTAX      Integer32(20..500)
     MAX-ACCESS  read-write
     STATUS      current
     DESCRIPTION
         "
         Indicates the high power level width.
         Default: 100
         Unit: ms
         "
     ::= { hwEntFxsPortConfigEntry 13 }
     
   hwEntFxsPortLowLevel OBJECT-TYPE
     SYNTAX      Integer32(20..500)
     MAX-ACCESS  read-write
     STATUS      current
     DESCRIPTION
         "
         Indicates the low power level width.
         Default: 300
         Unit: ms
         "
     ::= { hwEntFxsPortConfigEntry 14 }
     
   hwEntFxsPortKcType OBJECT-TYPE
     SYNTAX      INTEGER{type16kc(1), type12kc(2)}
     MAX-ACCESS  read-write
     STATUS      current
     DESCRIPTION
         "
         Indicates the KC type.
         Options:
         1. type16kc(1)
         2. type12kc(2)
         Default: type16kc(1)
         "
     ::= { hwEntFxsPortConfigEntry 15 }
     
   hwEntFxsPortVoltage OBJECT-TYPE
     SYNTAX      Integer32(0..9)
     MAX-ACCESS  read-write
     STATUS      current
     DESCRIPTION
         "
         Indicates the valid voltage value of KC.
         0: 0.45 Vrms   
		 1: 0.775 Vrms  
		 2: 1.0 Vrms    
		 3: 1.5 Vrms    
		 4: 2.0 Vrms    
		 5: 2.5 Vrms    
		 6: 3.0 Vrms    
		 7: 3.5 Vrms    
		 8: 4.0 Vrms    
		 9: 4.5 Vrms    
		 Default: 5
         "
     ::= { hwEntFxsPortConfigEntry 16 }     
             
   hwEntFxsPortActualSendGain OBJECT-TYPE
     SYNTAX      Integer32(0..22|255)
     MAX-ACCESS  read-only
     STATUS      current
     DESCRIPTION
         "
         Indicates the actual send gain of the fxs port.
           0:    5 dB
           1:  4.5 dB
           2:    4 dB
           3:  3.5 dB
           4:    3 dB
           5:  2.5 dB
           6:    2 dB
           7:  1.5 dB
           8:    1 dB
           9:  0.5 dB
          10:    0 dB
          11: -0.5 dB
          12:   -1 dB
          13: -1.5 dB
          14:   -2 dB
          15: -2.5 dB
          16:   -3 dB
          17: -3.5 dB
          18:   -4 dB
          19: -4.5 dB
          20:   -5 dB
          21: -5.5 dB
          22:   -6 dB
         255: null
         "
     ::= { hwEntFxsPortConfigEntry 17 }
         
  hwEntFxsPortActualRecvGain OBJECT-TYPE
     SYNTAX      Integer32(0..24|255)
     MAX-ACCESS  read-only
     STATUS      current
     DESCRIPTION
         "
         Indicates the actual receive gain of the fxs port.
           0:     0 dB  
           1:  -0.5 dB   
           2:    -1 dB  
           3:  -1.5 dB  
           4:    -2 dB  
           5:  -2.5 dB  
           6:    -3 dB  
           7:  -3.5 dB  
           8:    -4 dB  
           9:  -4.5 dB 
          10:    -5 dB 
          11:  -5.5 dB 
          12:    -6 dB 
          13:  -6.5 dB 
          14:    -7 dB 
          15:  -7.5 dB 
          16:    -8 dB 
          17:  -8.5 dB 
          18:    -9 dB 
          19:  -9.5 dB 
          20:   -10 dB 
          21: -10.5 dB 
          22:   -11 dB 
          23: -11.5 dB 
          24:   -12 dB   
         255: null
         "     
     ::= { hwEntFxsPortConfigEntry 18 }
               
--==           
               
   hwEntFxsPortOperTable OBJECT-TYPE
     SYNTAX      SEQUENCE OF HwEntFxsPortOperEntry
     MAX-ACCESS  not-accessible
     STATUS      current
     DESCRIPTION
       "       
       Indicates the operation table (management, maintenance, and status query) of the fxs ports.
       "       
     ::= { hwEntVoicePortMIB 2 }
               
   hwEntFxsPortOperEntry OBJECT-TYPE
     SYNTAX      HwEntFxsPortOperEntry
     MAX-ACCESS  not-accessible
     STATUS      current
     DESCRIPTION
       "Indicates the operation entry (management, maintenance, and status query) of the fxs ports."      
     INDEX    {  
               hwEntFxsPortOperIndex
              }
     ::= { hwEntFxsPortOperTable 1 }
 
   HwEntFxsPortOperEntry ::=
     SEQUENCE
     {  
       hwEntFxsPortOperIndex            Integer32,
       hwEntFxsPortSrvState	            INTEGER,
       hwEntFxsPortAdminState           INTEGER,
       hwEntFxsPortLineState            INTEGER,      
       hwEntFxsPortAdminOper 	        INTEGER
     }     
     
   hwEntFxsPortOperIndex OBJECT-TYPE
     SYNTAX      Integer32
     MAX-ACCESS  not-accessible
     STATUS      current
     DESCRIPTION
         "
         Indicates the FxsPortOper index.
         bits 31-24 (8 bits): reserved
         bits 23-16 (8 bits): slot index
         bits 15-8  (8 bits): subcard index
         bits  7-0  (8 bits): port index 
         "
     ::= { hwEntFxsPortOperEntry 1 }    
     
   hwEntFxsPortSrvState OBJECT-TYPE
     SYNTAX      INTEGER{normal(1), fault(2), deactive(3), powerdeny(4)}
     MAX-ACCESS  read-only
     STATUS      current
     DESCRIPTION
         "
         Indicates state of the fxs port.
         Options:
         normal(1)
         fault(2)
         deactive(3)
         powerdeny(4)
         "
     ::= { hwEntFxsPortOperEntry 2 }
 
   hwEntFxsPortAdminState OBJECT-TYPE
     SYNTAX      INTEGER{noLoopNoTest(1), noLoopTest(2), localLoopNoTest(3), localLoopTest(4),  remoteLoopNoTest(5), remoteLoopTest(6)}
     MAX-ACCESS  read-only
     STATUS      current
     DESCRIPTION
         "
         Indicates admin state of the fxs port.
         Options:
         noLoopNoTest(1)
         noLoopTest(2)
         localLoopNoTest(3)
         localLoopTest(4)
         remoteLoopNoTest(5)
         remoteLoopTest(6)
         "
     ::= { hwEntFxsPortOperEntry 3 }
     
   hwEntFxsPortLineState OBJECT-TYPE
     SYNTAX      INTEGER{normal(1), onEarth(2), unknown(3)}
     MAX-ACCESS  read-only
     STATUS      current
     DESCRIPTION
         "
         Indicates line state of the fxs port.
         Options:
         normal(1)
         onEarth(2)
         unknown(3)
         "
     ::= { hwEntFxsPortOperEntry 4 }  
          
   hwEntFxsPortAdminOper OBJECT-TYPE
     SYNTAX      INTEGER{remoteLoop(1),localLoop(2),cancelLoop(3)}
     MAX-ACCESS  read-write
     STATUS      current
     DESCRIPTION
         "
         Indicates operation type the fxs port.
         Options:
         remoteLoop(1)
         localLoop(2)
         cancelLoop(3)
         "
     ::= { hwEntFxsPortOperEntry 5 }
     
--== 

   hwEntBraPortConfigTable OBJECT-TYPE
     SYNTAX      SEQUENCE OF HwEntBraPortConfigEntry
     MAX-ACCESS  not-accessible
     STATUS      current
     DESCRIPTION
       "
       Indicates the attribute configuration table of the bra port.
       "
     ::= { hwEntVoicePortMIB 3 }
 
   hwEntBraPortConfigEntry OBJECT-TYPE
     SYNTAX      HwEntBraPortConfigEntry
     MAX-ACCESS  not-accessible
     STATUS      current
     DESCRIPTION
       "Indicates the attribute configuration entry of the bra port."
     INDEX    {  
               hwEntBraPortIndex
              }
     ::= { hwEntBraPortConfigTable 1 }
 
   HwEntBraPortConfigEntry ::=
     SEQUENCE
     {
       hwEntBraPortIndex	                Integer32,
       hwEntBraPortRemotePower	            INTEGER,
       hwEntBraPortAutoDeactive	            INTEGER,
       hwEntBraPortAutoDeactiveDelay	    Integer32,
       hwEntBraPortWorkMode	                INTEGER,
       hwEntBraPortL1ActiveMode             INTEGER,
       hwEntBraPortUniAlarmReport           INTEGER,
       hwEntBraPortL2Monitor                INTEGER
     }
  
   hwEntBraPortIndex OBJECT-TYPE
     SYNTAX      Integer32
     MAX-ACCESS  not-accessible
     STATUS      current
     DESCRIPTION
         "
         Indicates the slot/subcard/port index.
         bits 31-24 (8 bits): reserved
         bits 23-16 (8 bits): slot index
         bits 15-8  (8 bits): subcard index
         bits  7-0  (8 bits): port index 
         "
     ::= { hwEntBraPortConfigEntry 1 }
 
   hwEntBraPortRemotePower OBJECT-TYPE
     SYNTAX      INTEGER{enable(1), disable(2)}
     MAX-ACCESS  read-write
     STATUS      current
     DESCRIPTION
         "
         Indicates whether to support remote power supply.
         Options:
         enable(1)   -Supported
         disable(2)  -Not supported
         Default: disable(2)
         "
     ::= { hwEntBraPortConfigEntry 2 }
 
   hwEntBraPortAutoDeactive OBJECT-TYPE
     SYNTAX      INTEGER{enable(1), disable(2)}
     MAX-ACCESS  read-write
     STATUS      current
     DESCRIPTION
         "
         Indicates whether to support automatic deactivation. 
         Options:
         enable(1)   -Supported
         disable(2)  -Not supported
         Default: disable(2)
         "
     ::= { hwEntBraPortConfigEntry 3 }
 
   hwEntBraPortAutoDeactiveDelay OBJECT-TYPE
     SYNTAX      Integer32(10..360) 
     MAX-ACCESS  read-write
     STATUS      current
     DESCRIPTION
         "
         Indicates the automatic deactivation delay of the bra port.
         Default: 30
         Unit: second.
         "
     ::= { hwEntBraPortConfigEntry 4 }
     
  hwEntBraPortWorkMode OBJECT-TYPE
     SYNTAX      INTEGER{p2mp(1), p2p(2)}
     MAX-ACCESS  read-write
     STATUS      current
     DESCRIPTION
         "
         Indicates the bra port working mode.
         p2mp(1)   -Point to multi-point
         p2p(2)    -Point to point
         Default: p2mp(1)
         "
     ::= { hwEntBraPortConfigEntry 5 }
     
  hwEntBraPortL1ActiveMode OBJECT-TYPE
     SYNTAX      INTEGER{stable(1),unstable(2)}
     MAX-ACCESS  read-write
     STATUS      current
     DESCRIPTION
         "
         Indicates layer 1 active mode of the bra port.
         Options:
         stable(1)
         unstable(2)
         Default: unstable(2).
         "
     ::= { hwEntBraPortConfigEntry 6}
     
  hwEntBraPortUniAlarmReport OBJECT-TYPE
     SYNTAX      INTEGER{enable(1),disable(2)}
     MAX-ACCESS  read-write
     STATUS      current
     DESCRIPTION
         "
         Indicates whether to support user network interface fault alarm.
         enable(1)   -Supported
         disable(2)  -Not supported
         Default: disable(2)
         "
     ::= { hwEntBraPortConfigEntry 7}
  
  hwEntBraPortL2Monitor OBJECT-TYPE
     SYNTAX      INTEGER{enable(1),disable(2)}
     MAX-ACCESS  read-write
     STATUS      current
     DESCRIPTION
         "
         Indicates whether to support layer 2 error statistic.
         enable(1)   -Supported
         disable(2)  -Not supported
         Default: enable(1)
         "
     ::= { hwEntBraPortConfigEntry 8}

--==

   hwEntBraPortOperTable OBJECT-TYPE
     SYNTAX      SEQUENCE OF HwEntBraPortOperEntry
     MAX-ACCESS  not-accessible
     STATUS      current
     DESCRIPTION
       "
       Indicates the operation table (management, maintenance, and status query) of the bra ports.
       "
     ::= { hwEntVoicePortMIB 4 }
     
   hwEntBraPortOperEntry OBJECT-TYPE
     SYNTAX      HwEntBraPortOperEntry
     MAX-ACCESS  not-accessible
     STATUS      current
     DESCRIPTION
       "Indicates the operation entry (management, maintenance, and status query) of the bra ports."
     INDEX    {  
              hwEntBraPortOperIndex
              }
     ::= { hwEntBraPortOperTable 1 }
 
   HwEntBraPortOperEntry ::=
     SEQUENCE
     {          
       hwEntBraPortOperIndex              Integer32,
       hwEntBraPortSrvState	              INTEGER,
       hwEntBraPortAdminState             INTEGER,
       hwEntBraPortAlarmState             BITS,
       hwEntBraPortAdminOper              INTEGER
     }
      
    hwEntBraPortOperIndex OBJECT-TYPE
     SYNTAX      Integer32
     MAX-ACCESS  not-accessible
     STATUS      current
     DESCRIPTION
         "
         Indicates the BrPortOper index.
         bits 31-24 (8 bits): reserved
         bits 23-16 (8 bits): slot index
         bits 15-8  (8 bits): subcard index
         bits  7-0  (8 bits): port index 
         "
     ::= { hwEntBraPortOperEntry 1 }      
      
   hwEntBraPortSrvState OBJECT-TYPE
     SYNTAX      INTEGER{normal(1), fault(2), deactive(3), powerdeny(4)}
     MAX-ACCESS  read-only
     STATUS      current
     DESCRIPTION
         "
         Indicates state of the bra port. 
         Options:
         normal(1)
         fault(2)
         deactive(3)         
         powerdeny(4)
         "
     ::= { hwEntBraPortOperEntry 2 }
 
   hwEntBraPortAdminState OBJECT-TYPE
     SYNTAX      INTEGER{noLoopNoTest(1), noLoopTest(2), localLoopNoTest(3), localLoopTest(4),  remoteLoopNoTest(5), remoteLoopTest(6)}
     MAX-ACCESS  read-only
     STATUS      current
     DESCRIPTION
         "  
         Indicates admin state of the bra port. 
         Options:
         noLoopNoTest(1)
         noLoopTest(2)
         localLoopNoTest(3)
         localLoopTest(4)
         remoteLoopNoTest(5)
         remoteLoopTest(6)
         "
     ::= { hwEntBraPortOperEntry 3 }
     
     
   hwEntBraPortAlarmState OBJECT-TYPE
     SYNTAX      BITS{bit0(0),bit1(1),bit2(2),bit3(3),bit4(4)}
     MAX-ACCESS  read-only
     STATUS      current
     DESCRIPTION
         "
         Indicates the alarm state of the bra port, from left to right, each bit represents one alarm state.
         0 means no alarm present,1 means the alarm present.
         bit0: LT overload
         bit1: S port fault(EI2)
         bit2: U port fault(LOS/RSY)
         bit3: S port deactive(SAI)
         bit4: U port deactive(ACT)         
         "
     ::= { hwEntBraPortOperEntry 4}                    
 
   hwEntBraPortAdminOper OBJECT-TYPE
     SYNTAX      INTEGER{remoteLoop(1), localLoop(2), cancelLoop(3)}
     MAX-ACCESS  read-write
     STATUS      current
     DESCRIPTION
         "
         Indicates operation type the bra port. 
         Options:
         remoteLoop(1)
         localLoop(2)
         cancelLoop(3)
         "
     ::= { hwEntBraPortOperEntry 5 }      

--==
     
   hwEntVe1PortConfigTable OBJECT-TYPE
     SYNTAX      SEQUENCE OF HwEntVe1PortConfigEntry
     MAX-ACCESS  not-accessible
     STATUS      current
     DESCRIPTION
       "
       Indicates the attribute configuration table of the ve1 ports.
       "
     ::= { hwEntVoicePortMIB 5 }
   
   hwEntVe1PortConfigEntry OBJECT-TYPE
     SYNTAX      HwEntVe1PortConfigEntry
     MAX-ACCESS  not-accessible
     STATUS      current
     DESCRIPTION
       "Indicates the attribute configuration entry of the ve1 ports."
     INDEX    {  
              hwEntVe1PortIndex
              }
     ::= { hwEntVe1PortConfigTable 1 }
 
   HwEntVe1PortConfigEntry ::=
     SEQUENCE
     {
       hwEntVe1PortIndex  	         Integer32,
       hwEntVe1PortFrameCheckMode    INTEGER,
       hwEntVe1PortImpedance      	 INTEGER,
       hwEntVe1PortSignalType    	 INTEGER,
       hwEntVe1PortAccessMode        INTEGER,
       hwEntVe1PortL2Monitor         INTEGER,
       hwEntVe1PortErrAlarmSwitch    BITS

     }
 
   hwEntVe1PortIndex OBJECT-TYPE
     SYNTAX      Integer32
     MAX-ACCESS  not-accessible
     STATUS      current
     DESCRIPTION
         "
         Indicates the slot/subcard/port index.
         bits 31-24 (8 bits): reserved
         bits 23-16 (8 bits): slot index
         bits 15-8  (8 bits): subcard index
         bits  7-0  (8 bits): port index 
         "
     ::= { hwEntVe1PortConfigEntry 1 }
 
   hwEntVe1PortFrameCheckMode OBJECT-TYPE
     SYNTAX      INTEGER{enable(1), disable(2)}
     MAX-ACCESS  read-write
     STATUS      current
     DESCRIPTION
         "
         Indicates the CRC4 frame check mode of the ve1 port.
         Options:
         enable(1)
         disable(2)
         Default: disable(2)
         "
     ::= { hwEntVe1PortConfigEntry 2 }
 
   hwEntVe1PortImpedance OBJECT-TYPE
     SYNTAX      INTEGER{ohm75(1), ohm120(2)}
     MAX-ACCESS  read-write
     STATUS      current
     DESCRIPTION
         "
         Indicates impedance of the ve1 port.
         Options:
         ohm75(1)
         ohm120(2)
         Default: ohm75(1)
         "
     ::= { hwEntVe1PortConfigEntry 3 }
 
   hwEntVe1PortSignalType OBJECT-TYPE
     SYNTAX      INTEGER{ccs(1), cas(2)}
     MAX-ACCESS  read-write
     STATUS      current
     DESCRIPTION
         "
         Indicates signal type of the ve1 port.
         Options:
         ccs(1)
         cas(2)
         Default: ccs(1)
         "
     ::= { hwEntVe1PortConfigEntry 4 }
         
  hwEntVe1PortAccessMode OBJECT-TYPE
     SYNTAX      INTEGER{digitalAccess(1),directAccess(2)}
     MAX-ACCESS  read-write
     STATUS      current
     DESCRIPTION
         "
         Indicates physical layer digital section access mode of the ve1 port.
         Options:
         digitalAccess(1)
         directAccess(2)
         Default:digitalAccess(1)
         "
     ::= { hwEntVe1PortConfigEntry 5}
  
  hwEntVe1PortL2Monitor OBJECT-TYPE
    SYNTAX      INTEGER{enable(1), disable(2)}
    MAX-ACCESS  read-write
    STATUS      current
    DESCRIPTION
        "
        Indicates whether to support layer 2 error statistic of the ve1 port.
        enable(1)
        disable(2)
        Default: enable(1).
        "
    ::= { hwEntVe1PortConfigEntry 6}

  
  hwEntVe1PortErrAlarmSwitch OBJECT-TYPE
     SYNTAX      BITS{bit0(0),bit1(1),bit2(2),bit3(3),bit4(4),bit5(5)}
     MAX-ACCESS  read-write
     STATUS      current
     DESCRIPTION
         "
         Indicates ve1 error alarm switches, from left to right, each bit respresent a switch.
         0 means disable, 1 means enable.
         bit0: report pcm line fault alarm.
 	     bit1: when error rate reached ULF(Unconditional Line Failure) threshold, report pcm line fault alarm.             
 	     bit2: when error rate reached OLF(Optional Line Failure) threshold, report pcm line fault alarm.
 	     bit3: when error rate reached LDT(Line Disturbance Transient Event) threshold, report ve1 digital line transient event alarm.
 	     bit4: when E1 frame slip frequency exceeded in observation interval reached degraded threshold, report event alarm.
 	     bit5: when any line temporary event occurs, report event alarm.
         Default: 111000
         "
     ::= { hwEntVe1PortConfigEntry 7}
     
--==
      
   hwEntVe1PortOperTable OBJECT-TYPE
     SYNTAX      SEQUENCE OF HwEntVe1PortOperEntry
     MAX-ACCESS  not-accessible
     STATUS      current
     DESCRIPTION
       "
       Indicates the operation table (management, maintenance, and status query) of the ve1 ports.
       "
     ::= { hwEntVoicePortMIB 6 }
 
   hwEntVe1PortOperEntry OBJECT-TYPE
     SYNTAX      HwEntVe1PortOperEntry
     MAX-ACCESS  not-accessible
     STATUS      current
     DESCRIPTION
       "Indicates the operation entry (management, maintenance, and status query) of the ve1 ports."
     INDEX    {  
               hwEntVe1PortOperIndex
              }
     ::= { hwEntVe1PortOperTable 1 }
 
   HwEntVe1PortOperEntry ::=
     SEQUENCE
     {      
       hwEntVe1PortOperIndex          Integer32,
       hwEntVe1PortSrvState	          INTEGER,
       hwEntVe1PortAdminState         INTEGER,
       hwEntVe1PortWarningState	      BITS,
       hwEntVe1PortAdminOper	      INTEGER
     }
                     
   hwEntVe1PortOperIndex OBJECT-TYPE
     SYNTAX      Integer32
     MAX-ACCESS  not-accessible
     STATUS      current
     DESCRIPTION
         "
         Indicates the Ve1PortOper index.
         bits 31-24 (8 bits): reserved
         bits 23-16 (8 bits): slot index
         bits 15-8  (8 bits): subcard index
         bits  7-0  (8 bits): port index 
         "
     ::= { hwEntVe1PortOperEntry 1 }
                          
   hwEntVe1PortSrvState OBJECT-TYPE
     SYNTAX      INTEGER{normal(1), fault(2), lineAbnormal(3), powerdeny(4)}
     MAX-ACCESS  read-only
     STATUS      current
     DESCRIPTION
         "
         Indicates state of the ve1 port.
         Options:
         normal(1)
         fault(2)
         lineAbnormal(3)
         powerdeny(4)
         "
     ::= { hwEntVe1PortOperEntry 2 }
 
   hwEntVe1PortAdminState OBJECT-TYPE
     SYNTAX      INTEGER{noLoopNoTest(1), noLoopTest(2), localLoopNoTest(3), localLoopTest(4),  remoteLoopNoTest(5), remoteLoopTest(6)}
     MAX-ACCESS  read-only
     STATUS      current
     DESCRIPTION
         "
         Indicates admin state  of the ve1 port.
         Options:
         noLoopNoTest(1)
         noLoopTest(2)
         localLoopNoTest(3)
         localLoopTest(4)
         remoteLoopNoTest(5)
         remoteLoopTest(6)
         "
     ::= { hwEntVe1PortOperEntry 3 }
     
     hwEntVe1PortWarningState OBJECT-TYPE
     SYNTAX      BITS{bit0(0), bit1(1), bit2(2), bit3(3), bit4(4), bit5(5), bit6(6), bit7(7),
                      bit8(8), bit9(9), bit10(10), bit11(11), bit12(12), bit13(13), bit14(14), bit15(15)}
     MAX-ACCESS  read-only
     STATUS      current
     DESCRIPTION
         "
         Indicates the alarm status of the ve1 line.
         0 means no alarm present, 1 means the alarm present.
         bit0: LOS alarm
	     bit1: AIS alarm
	     bit2: LFA alarm
	     bit3: LMFA alarm
	     bit4: RRA alarm
	     bit5: CRCER alarm
	     bit6: SCOL alarm
	     bit7: ULF alarm
	     bit8: OLF alarm
	     bit9: LDT alarm
	     bit10: error second alarm,in direction ET/LT to NT1
	     bit11: error second alarm,in direction NT1 to ET/LT 
	     bit12: sequential severe error second alarm,in direction ET/LT to NT1
	     bit13: sequential severe error second alarm,in direction NT1 to ET/LT
	     bit14: degrade minute alarm,in direction ET/LT to NT1
	     bit15: degrade minute alarm,in direction NT1 to ET/LT
         "
     ::= { hwEntVe1PortOperEntry 4 }
                                            
 
   hwEntVe1PortAdminOper OBJECT-TYPE
     SYNTAX      INTEGER{remoteLoop(1), localLoop(2),cancelLoop(3)}
     MAX-ACCESS  read-write
     STATUS      current
     DESCRIPTION
         "
         Indicates operation type of the ve1 port.
         Options:
         remoteLoop(1)
         localLoop(2)
         cancelLoop(3)
         "
     ::= { hwEntVe1PortOperEntry 5 }    

--==

  hwEntVe1PortL1AlarmThresholdTable OBJECT-TYPE
     SYNTAX      SEQUENCE OF HwEntVe1PortL1AlarmThresholdEntry
     MAX-ACCESS  not-accessible
     STATUS      current
     DESCRIPTION
       "
       degrade alarm threshold config table of ve1 port.
       "
     ::= { hwEntVoicePortMIB 7 }
 
   hwEntVe1PortL1AlarmThresholdEntry OBJECT-TYPE
     SYNTAX      HwEntVe1PortL1AlarmThresholdEntry
     MAX-ACCESS  not-accessible
     STATUS      current
     DESCRIPTION
       "degrade alarm threshold config entry of ve1 port."
     INDEX    {  
	          hwEntVe1PortL1AlarmThresholdIndex 
              }
     ::= { hwEntVe1PortL1AlarmThresholdTable 1 }
 
   HwEntVe1PortL1AlarmThresholdEntry ::=
     SEQUENCE
     {
       hwEntVe1PortL1AlarmThresholdIndex        Integer32,
       hwEntVe1PortDmAlarmThreshold             Integer32,
       hwEntVe1PortEsAlarmThreshold      	    Integer32,
       hwEntVe1PortCsesAlarmThreshold           Integer32       
     }
     
  hwEntVe1PortL1AlarmThresholdIndex OBJECT-TYPE
     SYNTAX      Integer32
     MAX-ACCESS  not-accessible
     STATUS      current
     DESCRIPTION
         "
         Indicates the Ve1PortOper index.
         bits 31-24 (8 bits): reserved
         bits 23-16 (8 bits): slot index
         bits 15-8  (8 bits): subcard index
         bits  7-0  (8 bits): port index 
         "
     ::= { hwEntVe1PortL1AlarmThresholdEntry 1 }
     
   hwEntVe1PortDmAlarmThreshold OBJECT-TYPE
     SYNTAX      Integer32(1..60)
     MAX-ACCESS  read-write
     STATUS      current
     DESCRIPTION
         "
         Indicates the degrade minute alarm threshold.
         Default: 8
         "
     ::= { hwEntVe1PortL1AlarmThresholdEntry 2 }
  
   hwEntVe1PortEsAlarmThreshold OBJECT-TYPE
     SYNTAX      Integer32(1..3600)
     MAX-ACCESS  read-write
     STATUS      current
     DESCRIPTION
         "
         Indicates the error second alarm threshold.
         Default: 432
         "
     ::= { hwEntVe1PortL1AlarmThresholdEntry 3 } 

   hwEntVe1PortCsesAlarmThreshold OBJECT-TYPE
     SYNTAX      Integer32(1..60)
     MAX-ACCESS  read-write
     STATUS      current
     DESCRIPTION
         "
         Indicates the sequential severe error second alarm threshold.
         Default: 4
         "
     ::= { hwEntVe1PortL1AlarmThresholdEntry 4 }          

--==

    hwEntFxoPortConfigTable OBJECT-TYPE
     SYNTAX      SEQUENCE OF HwEntFxoPortConfigEntry
     MAX-ACCESS  not-accessible
     STATUS      current
     DESCRIPTION
       "
       Indicates the attribute configuration table of fxo ports.
       "
     ::= { hwEntVoicePortMIB 8 }
 
   hwEntFxoPortConfigEntry OBJECT-TYPE
     SYNTAX      HwEntFxoPortConfigEntry
     MAX-ACCESS  not-accessible
     STATUS      current
     DESCRIPTION
       "Indicates the attribute configuration entry of fxo ports."
     INDEX    {  
               hwEntFxoPortIndex
              }
     ::= { hwEntFxoPortConfigTable 1 }
 
   HwEntFxoPortConfigEntry ::=
     SEQUENCE
     {
       hwEntFxoPortIndex	           Integer32,
       hwEntFxoPortSendGain	           Integer32,
       hwEntFxoPortRecvGain	           Integer32,
       hwEntFxoPortDcImpedance         Integer32,
       hwEntFxoPortAcImpedance         Integer32,       
       hwEntFxoPortRingMinDuration     Integer32,
       hwEntFxoPortRingMaxInterval     Integer32,       
       hwEntFxoPortRingFrequency       Integer32,
       hwEntFxoPortRingAcAmplitude     Integer32,
       hwEntFxoPortRingOffset          Integer32,
       hwEntFxoPortFeedMaxVoltage      Integer32,
       hwEntFxoPortFeedMinVoltage      Integer32,
       hwEntFxoPortFeedMaxCurrent      Integer32,
       hwEntFxoPortFeedMinCurrent      Integer32
    }
 
    hwEntFxoPortIndex OBJECT-TYPE
        SYNTAX      Integer32
        MAX-ACCESS  not-accessible
        STATUS      current
        DESCRIPTION
        "
         Indicates the slot/subcard/port index.
         bits 31-24 (8 bits): reserved
         bits 23-16 (8 bits): slot index
         bits 15-8  (8 bits): subcard index
         bits  7-0  (8 bits): port index 
        "
        ::= { hwEntFxoPortConfigEntry 1 }

    hwEntFxoPortSendGain OBJECT-TYPE
        SYNTAX      Integer32(0..60)
        MAX-ACCESS  read-write
        STATUS      current
        DESCRIPTION
        "
        Indicates send gain of the fxo port.
         0:  13.5dB,   1:  13.0dB,   2:  12.5dB
         3:  12.0dB,   4:  11.5dB,   5:  11.0dB
         6:  10.5dB,   7:  10.0dB,   8:   9.5dB
         9:   9.0dB,  10:   8.5dB,  11:   8.0dB
        12:   7.5dB,  13:   7.0dB,  14:   6.5dB
        15:   6.0dB,  16:   5.5dB,  17:   5.0dB
        18:   4.5dB,  19:   4.0dB,  20:   3.5dB
        21:   3.0dB,  22:   2.5dB,  23:   2.0dB
        24:   1.5dB,  25:   1.0dB,  26:   0.5dB
        27:     0dB,  28:  -0.5dB,  29:  -1.0dB
        30:  -1.5dB,  31:  -2.0dB,  32:  -2.5dB
        33:  -3.0dB,  34:  -3.5dB,  35:  -4.0dB
        36:  -4.5dB,  37:  -5.0dB,  38:  -5.5dB
        39:  -6.0dB,  40:  -6.5dB,  41:  -7.0dB
        42:  -7.5dB,  43:  -8.0dB,  44:  -8.5dB
        45:  -9.0dB,  46:  -9.5dB,  47: -10.0dB
        48: -10.5dB,  49: -11.0dB,  50: -11.5dB
        51: -12.0dB,  52: -12.5dB,  53: -13.0dB
        54: -13.5dB,  55: -14.0dB,  56: -14.5dB
        57: -15.0dB,  58: -15.5dB,  59: -16.0dB
        60: -16.5dB 
        Default: 27
        "
        ::= { hwEntFxoPortConfigEntry 2 }
    
    hwEntFxoPortRecvGain OBJECT-TYPE
        SYNTAX      Integer32(0..60)
        MAX-ACCESS  read-write
        STATUS      current
        DESCRIPTION
        "
        Indicates receive gain of the fxo port.
         0:  13.5dB,   1:  13.0dB,   2:  12.5dB
         3:  12.0dB,   4:  11.5dB,   5:  11.0dB
         6:  10.5dB,   7:  10.0dB,   8:   9.5dB
         9:   9.0dB,  10:   8.5dB,  11:   8.0dB
        12:   7.5dB,  13:   7.0dB,  14:   6.5dB
        15:   6.0dB,  16:   5.5dB,  17:   5.0dB
        18:   4.5dB,  19:   4.0dB,  20:   3.5dB
        21:   3.0dB,  22:   2.5dB,  23:   2.0dB
        24:   1.5dB,  25:   1.0dB,  26:   0.5dB
        27:     0dB,  28:  -0.5dB,  29:  -1.0dB
        30:  -1.5dB,  31:  -2.0dB,  32:  -2.5dB
        33:  -3.0dB,  34:  -3.5dB,  35:  -4.0dB
        36:  -4.5dB,  37:  -5.0dB,  38:  -5.5dB
        39:  -6.0dB,  40:  -6.5dB,  41:  -7.0dB
        42:  -7.5dB,  43:  -8.0dB,  44:  -8.5dB
        45:  -9.0dB,  46:  -9.5dB,  47: -10.0dB
        48: -10.5dB,  49: -11.0dB,  50: -11.5dB
        51: -12.0dB,  52: -12.5dB,  53: -13.0dB
        54: -13.5dB,  55: -14.0dB,  56: -14.5dB
        57: -15.0dB,  58: -15.5dB,  59: -16.0dB
        60: -16.5dB 
        Default: 34    
        "
        ::= { hwEntFxoPortConfigEntry 3 }
        
   hwEntFxoPortDcImpedance OBJECT-TYPE
     SYNTAX      Integer32(0..1)
     MAX-ACCESS  read-write
     STATUS      current
     DESCRIPTION
         "
         Indicates DC impedance of the fxo port.
         0: 50
         1: 800
         Default: 0
         Unit: 
         "
     ::= { hwEntFxoPortConfigEntry 4 }
     
   hwEntFxoPortAcImpedance OBJECT-TYPE
     SYNTAX      Integer32(0..15)
     MAX-ACCESS  read-write
     STATUS      current
     DESCRIPTION
         "
         Indicates AC impedance of the fxo port.
          0: 600
          1: 900 
          2: 270 + (750 || 150 nF) and 275 + (780 || 150 nF)
          3: 220 + (820 || 120 nF) and 220 + (820 || 115 nF)
          4: 370 + (620 || 310 nF)
          5: 320 + (1050 || 230 nF)
          6: 370 + (820 || 110 nF)
          7: 275 + (780 || 115 nF)
          8: 20 + (820 || 110 nF)
          9: 350 + (1000 || 210 nF)
         10: 200 + (680 || 100 nF)
         11: 600 + 2.16 F
         12: 900 + 1 F
         13: 900 + 2.16 F
         14: 600 + 1 F
         15: Global impedance
         Default: 0
         Unit: 
         "
     ::= { hwEntFxoPortConfigEntry 5 }        
       
   hwEntFxoPortRingMinDuration OBJECT-TYPE
     SYNTAX      Integer32(0..7)
     MAX-ACCESS  read-write
     STATUS      current
     DESCRIPTION
         "
         Indicates the min of the ring duration time.
         0: 100ms  
         1: 150ms  
         2: 200ms
         3: 256ms  
         4: 384ms  
         5: 512ms
         6: 640ms  
         7: 1024ms
         Default: 2
         "
     ::= { hwEntFxoPortConfigEntry 6 }
     
   hwEntFxoPortRingMaxInterval OBJECT-TYPE
     SYNTAX      Integer32(0..28)
     MAX-ACCESS  read-write
     STATUS      current
     DESCRIPTION
         "
         Indicates the max of the ring interval time.
          0: not use,   1:  128ms,   2:  256ms,   3:   284ms
          4:   512ms,   5:  640ms,   6:  768ms,   7:   896ms
          8:  1024ms,   9: 1152ms,  10: 1280ms,  11:  1408ms
         12:  1536ms,  13: 1664ms,  14: 1792ms,  15:  1920ms
         16:  2000ms,  17: 2500ms,  18: 3000ms,  19:  3500ms
         20:  4000ms,  21: 4500ms,  22: 5000ms,  23:  6000ms
         24:  7000ms,  25: 8000ms,  26: 9000ms,  27: 10000ms
         28: 15000ms    
         Default: 0     
         "
     ::= { hwEntFxoPortConfigEntry 7 }
     
   hwEntFxoPortRingFrequency OBJECT-TYPE
     SYNTAX      Integer32(0..2)
     MAX-ACCESS  read-write
     STATUS      current
     DESCRIPTION
         "
         Indicates the ring frequency.
         0: 16Hz 
         1: 25Hz
         2: 50Hz   
         Default: 1      
         "
     ::= { hwEntFxoPortConfigEntry 8 }
     
   hwEntFxoPortRingAcAmplitude OBJECT-TYPE
     SYNTAX      Integer32(0..2)
     MAX-ACCESS  read-write
     STATUS      current
     DESCRIPTION
         "
         Indicates the ring of the AC amplitude.
         0: 74V
         1: 65V 
         2: 50V     
         Default: 2      
         "
     ::= { hwEntFxoPortConfigEntry 9 } 
     
     
   hwEntFxoPortRingOffset OBJECT-TYPE
     SYNTAX      Integer32(0..100)
     MAX-ACCESS  read-write
     STATUS      current
     DESCRIPTION
         "
         Indicates the ring offset.
         0-100: -50V ~ 50V
         Default: 70
         "
     ::= { hwEntFxoPortConfigEntry 10 }     
     
   hwEntFxoPortFeedMaxVoltage OBJECT-TYPE
     SYNTAX      Integer32(-100..0)
     MAX-ACCESS  read-write
     STATUS      current
     DESCRIPTION
         "
         Indicates the max feed voltage.
         Default: -20
         Unit:V
         "
     ::= { hwEntFxoPortConfigEntry 11 }
     
     
   hwEntFxoPortFeedMinVoltage OBJECT-TYPE
     SYNTAX      Integer32(-100..0)
     MAX-ACCESS  read-write
     STATUS      current
     DESCRIPTION
         "
         Indicates the min feed voltage.
         Default: -80
         Unit:V
         "
     ::= { hwEntFxoPortConfigEntry 12 }
     
     
   hwEntFxoPortFeedMaxCurrent OBJECT-TYPE
     SYNTAX      Integer32(0..3)
     MAX-ACCESS  read-write
     STATUS      current
     DESCRIPTION
         "
         Indicates the max feed current.
         0: 25mA  
         1: 30mA  
         2: 35mA  
         3: 40mA
         Default: 2
         "
     ::= { hwEntFxoPortConfigEntry 13 }
     
     
   hwEntFxoPortFeedMinCurrent OBJECT-TYPE
     SYNTAX      Integer32(0..4)
     MAX-ACCESS  read-write
     STATUS      current
     DESCRIPTION
         "
         Indicates the min of the PTP feed current.
         0: 16mA  
         1: 17mA  
         2: 18mA  
         3: 19mA  
         4: 20mA
         Default: 0         
         "
     ::= { hwEntFxoPortConfigEntry 14 }       
        
--==

hwEntFxoPortOperTable OBJECT-TYPE
     SYNTAX      SEQUENCE OF HwEntFxoPortOperEntry
     MAX-ACCESS  not-accessible
     STATUS      current
     DESCRIPTION
       "
       Indicates the operation table (management, maintenance, and status query) of the fxo ports.
       "
     ::= { hwEntVoicePortMIB 9 }
 
   hwEntFxoPortOperEntry OBJECT-TYPE
     SYNTAX      HwEntFxoPortOperEntry
     MAX-ACCESS  not-accessible
     STATUS      current
     DESCRIPTION
       "Indicates the operation entry (management, maintenance, and status query) of the fxo ports."
     INDEX    {  
               hwEntFxoPortOperIndex
              }
     ::= { hwEntFxoPortOperTable 1 }
 
   HwEntFxoPortOperEntry ::=
     SEQUENCE
     {        
       hwEntFxoPortOperIndex        Integer32,
       hwEntFxoPortSrvState	        INTEGER,
       hwEntFxoPortAdminState       INTEGER,
       hwEntFxoPortAdminOper        INTEGER,
       hwEntFxoPortLineState        INTEGER
    }

   hwEntFxoPortOperIndex OBJECT-TYPE
     SYNTAX      Integer32
     MAX-ACCESS  not-accessible
     STATUS      current
     DESCRIPTION
         "
         Indicates the FxsPortOper index.
         bits 31-24 (8 bits): reserved
         bits 23-16 (8 bits): slot index
         bits 15-8  (8 bits): subcard index
         bits  7-0  (8 bits): port index 
         "
     ::= { hwEntFxoPortOperEntry 1 }   

    hwEntFxoPortSrvState OBJECT-TYPE
        SYNTAX      INTEGER{normal(1), fault(2), deactive(3), powredeny(4)}
        MAX-ACCESS  read-only
        STATUS      current
        DESCRIPTION
        "
        Indicates state of the fxo port.
        Options:
        normal(1)
        fault(2)
        deactive(3)
        powredeny(4)
        "
        ::= { hwEntFxoPortOperEntry 2 }
        
   hwEntFxoPortAdminState OBJECT-TYPE
		     SYNTAX      INTEGER{noLoopNoTest(1), noLoopTest(2), localLoopNoTest(3), localLoopTest(4),  remoteLoopNoTest(5), remoteLoopTest(6)}
		     MAX-ACCESS  read-only
		     STATUS      current
		     DESCRIPTION
         "
         Indicates the fxo port Admin state.
         Options:
         noLoopNoTest(1)
         noLoopTest(2)
         localLoopNoTest(3)
         localLoopTest(4)
         remoteLoopNoTest(5)
         remoteLoopTest(6)
         "
     ::= { hwEntFxoPortOperEntry 3 }    
        
   hwEntFxoPortLineState OBJECT-TYPE
        SYNTAX      INTEGER{normal(1),fault(2),unknown(3)}
        MAX-ACCESS  read-only
        STATUS      current
        DESCRIPTION
        "
        Indicates line state of the fxo port.
        Options:
        normal(1)
        fault(2)
        unknown(3)
        "
        ::= { hwEntFxoPortOperEntry 4 }

   hwEntFxoPortAdminOper OBJECT-TYPE
        SYNTAX      INTEGER{remoteLoop(1), localLoop(2), cancelLoop(3)}
        MAX-ACCESS  read-write
        STATUS      current
        DESCRIPTION
        "
        Indicates the operate type.
        Options:
        remoteLoop(1)
        localLoop(2)
        cancelLoop(3)
        "
        ::= { hwEntFxoPortOperEntry 5 }
        
    
    --  ============== conformance information ==============
        hwEntVoicePortConformance OBJECT IDENTIFIER ::= { hwEntVoicePortMIB 10 }
        
        
        hwEntVoicePortCompliances OBJECT IDENTIFIER ::= { hwEntVoicePortConformance 1 }
        hwEntVoicePortCompliance MODULE-COMPLIANCE
               STATUS      current
               DESCRIPTION
                   "The compliance statement for systems supporting 
                the this module."

               MODULE      -- this module
               MANDATORY-GROUPS    {hwEntFxsPortConfigGroup, hwEntFxsPortOperGroup, hwEntBraPortConfigGroup,
                              hwEntBraPortOperGroup, hwEntVe1PortConfigGroup, hwEntVe1PortOperGroup,
                              hwEntVe1PortL1AlarmThresholdGroup, hwEntFxoPortConfigGroup, hwEntFxoPortOperGroup}  
                                               
              ::= { hwEntVoicePortCompliances 1 }  
              
          
        --  ============== groups ==============  
        hwEntVoicePortGroups OBJECT IDENTIFIER ::= { hwEntVoicePortConformance 2 } 
        
	   hwEntFxsPortConfigGroup OBJECT-GROUP
	     OBJECTS
	     {
	       hwEntFxsPortIndex,
	       hwEntFxsPortSendGain,
	       hwEntFxsPortRecvGain,
	       hwEntFxsPortDialMode,
	       hwEntFxsPortReversePoleEnable,
	       hwEntFxsPortReversePoleLevel,
	       hwEntFxsPortPolarityReverseMode, 
	       hwEntFxsPortLineLock,
	       hwEntFxsPortNlpMode,
	       hwEntFxsPortClipReversePole,
	       hwEntFxsPortImpedance,
	       hwEntFxsPortCurrent,
	       hwEntFxsPortHighLevel,
	       hwEntFxsPortLowLevel,
	       hwEntFxsPortKcType,
	       hwEntFxsPortVoltage,
	       hwEntFxsPortActualSendGain,
	       hwEntFxsPortActualRecvGain
	     }
	    STATUS current
            DESCRIPTION 
                "The hwEntFxsPortConfig group."
            ::= { hwEntVoicePortGroups 1 }
            
	   hwEntFxsPortOperGroup OBJECT-GROUP
	     OBJECTS
	     {  
	       hwEntFxsPortOperIndex,
	       hwEntFxsPortSrvState,
	       hwEntFxsPortAdminState,
	       hwEntFxsPortLineState,      
	       hwEntFxsPortAdminOper 	        
	     }     
	    STATUS current
            DESCRIPTION 
                "The hwEntFxsPortOper group."
            ::= { hwEntVoicePortGroups 2 }
            
	 
	   hwEntBraPortConfigGroup OBJECT-GROUP
	     OBJECTS
	     {
	       hwEntBraPortIndex,
	       hwEntBraPortRemotePower,
	       hwEntBraPortAutoDeactive,
	       hwEntBraPortAutoDeactiveDelay,
	       hwEntBraPortWorkMode,
	       hwEntBraPortL1ActiveMode,
	       hwEntBraPortUniAlarmReport,
	       hwEntBraPortL2Monitor       
	     }
	    STATUS current
            DESCRIPTION 
                "The HwEntBraPortConfig group."
            ::= { hwEntVoicePortGroups 3 }
            
	 
	   hwEntBraPortOperGroup OBJECT-GROUP
	     OBJECTS
	     { 
	       hwEntBraPortOperIndex,
	       hwEntBraPortSrvState,
	       hwEntBraPortAdminState,
	       hwEntBraPortAlarmState,
	       hwEntBraPortAdminOper     
	     }
	     STATUS current
            DESCRIPTION 
                "The HwEntBraPortOper group."
            ::= { hwEntVoicePortGroups 4 }
             
	   hwEntVe1PortConfigGroup OBJECT-GROUP
	     OBJECTS
	     {
	       hwEntVe1PortIndex,
	       hwEntVe1PortFrameCheckMode,
	       hwEntVe1PortImpedance,
	       hwEntVe1PortSignalType,
	       hwEntVe1PortAccessMode,
	       hwEntVe1PortL2Monitor,
	       hwEntVe1PortErrAlarmSwitch    
	
	     }
	    STATUS current
            DESCRIPTION 
                "The HwEntVe1PortConfig group."
            ::= { hwEntVoicePortGroups 5 }
            
	 
	   hwEntVe1PortOperGroup OBJECT-GROUP
	     OBJECTS
	     {      
	       hwEntVe1PortOperIndex,
	       hwEntVe1PortSrvState,
	       hwEntVe1PortAdminState,
	       hwEntVe1PortWarningState,
	       hwEntVe1PortAdminOper	      
	     }
	   STATUS current
            DESCRIPTION 
                "The HwEntVe1PortOper group."
            ::= { hwEntVoicePortGroups 6 }
            
	 
	   hwEntVe1PortL1AlarmThresholdGroup OBJECT-GROUP
	     OBJECTS
	     {
	       hwEntVe1PortL1AlarmThresholdIndex,
	       hwEntVe1PortDmAlarmThreshold,
	       hwEntVe1PortEsAlarmThreshold,
	       hwEntVe1PortCsesAlarmThreshold
	     }
	     STATUS current
            DESCRIPTION 
                "The HwEntVe1PortL1AlarmThreshold group."
            ::= { hwEntVoicePortGroups 7 }
            
	 
	   hwEntFxoPortConfigGroup OBJECT-GROUP
	     OBJECTS
	     {
	       hwEntFxoPortIndex,
	       hwEntFxoPortSendGain,
	       hwEntFxoPortRecvGain,
	       hwEntFxoPortDcImpedance,
	       hwEntFxoPortAcImpedance,       
	       hwEntFxoPortRingMinDuration,
	       hwEntFxoPortRingMaxInterval,       
	       hwEntFxoPortRingFrequency,
	       hwEntFxoPortRingAcAmplitude,
	       hwEntFxoPortRingOffset,
	       hwEntFxoPortFeedMaxVoltage,
	       hwEntFxoPortFeedMinVoltage,
	       hwEntFxoPortFeedMaxCurrent,
	       hwEntFxoPortFeedMinCurrent      
	    }
	 STATUS current
            DESCRIPTION 
                "The HwEntFxoPortConfig group."
            ::= { hwEntVoicePortGroups 8 }
            
	   hwEntFxoPortOperGroup OBJECT-GROUP
	     OBJECTS
	     {        
	       hwEntFxoPortOperIndex,
	       hwEntFxoPortSrvState,
	       hwEntFxoPortAdminState,
	       hwEntFxoPortAdminOper,
	       hwEntFxoPortLineState        
	    }
	 STATUS current
            DESCRIPTION 
                "The HwEntFxoPortOper group."
            ::= { hwEntVoicePortGroups 9 }
            

        
END
