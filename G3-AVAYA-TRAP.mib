--  The following is the definition of the Traps issued by the 
--  DEFINITY(r) G3 Proxy Agent.  These traps are defined using the
--  TRAP-TYPE macro defined in RFC1215.
 
G3-AVAYA-TRAP DEFINITIONS ::= BEGIN
 
    IMPORTS
        
        g3-products, g3alarmsPort, g3alarmsMaintName, g3alarmsOnBrd,
      g3alarmsAlarmType, g3extdevAltName, g3extdevDescription, g3extdevID,
      g3extdevBuilding, g3extdevAddress, g3clientExternalName,
      g3alarmsAlarmNumber, g3alarmsProductID, g3restartDateTime,
      g3restartLevel, g3restartCarrier, g3restartCraftDemand,
      g3restartEscalated, g3restartInterchange, g3restartUnavailable,
      g3restartCause, g3vintageSpeArelease, g3vintageSpeBrelease,
      g3vintageSpeAupID, g3vintageSpeBupID, g3alarmsIPAddress, 
      g3alarmsCategory, g3alarmsErrorCodes, g3alarmsSrcIPAddr, 
      g3alarmsSrcMACAddr, g3alarmsDestIPAddr, g3alarmsDestPort, 
      g3alarmsProtocol, g3alarmsCount, g3alarmsViolationType,
      g3alarmsCode, g3alarmsData, g3alarmsICMPType, g3alarmsEventID,
      g3alarmsStatus
            FROM G3-AVAYA-MIB
        sysName
            FROM RFC1213-MIB
        TRAP-TYPE
            FROM RFC-1215;
            
    
    alarmClear          TRAP-TYPE
        ENTERPRISE      g3-products
        VARIABLES       { 
g3clientExternalName,g3alarmsProductID,g3alarmsAlarmNumber }
        DESCRIPTION     "A Cleared Alarm Notification has been issued by
                  the switch indicating that all alarms have been
                        cleared."
        ::= 0
 
    alarmCritical       TRAP-TYPE
        ENTERPRISE      g3-products
        VARIABLES       {
      
g3clientExternalName,g3alarmsProductID,g3alarmsAlarmNumber,g3alarmsPort,g3alarmsMaintName,g3alarmsOnBrd,g3alarmsAlarmType,g3alarmsIPAddress,g3alarmsCategory,g3alarmsErrorCodes 
}
        DESCRIPTION     "This trap is defined for future use."
        ::= 1
        
    alarmMajor          TRAP-TYPE
        ENTERPRISE      g3-products
        VARIABLES       {
      
g3clientExternalName,g3alarmsProductID,g3alarmsAlarmNumber,g3alarmsPort,g3alarmsMaintName,g3alarmsOnBrd,g3alarmsAlarmType,g3alarmsIPAddress,g3alarmsCategory,g3alarmsErrorCodes 
}
        DESCRIPTION     "A Major alarm has been issued by the switch. The 
                  MIB variables provide attributes of the alarm. The 
                  information contained in the g3alarmsPort, 
                  g3alarmsMaintName, g3alarmsOnBrd trap variables 
                  differ depending on the kind of alarm. If the 
                  alarm is a voice server alarm these fields 
                  contain, respectively, an equipment location, 
                  maintenance object name, and flag indicating 
                  whether or not the alarm was on-board. For 
                  server platform alarms and messaging alarms these 
                  fields contain, respectively, an alarm description
                  including the source of the alarm, a string 
                  indicating the resource from which the alarm 
                  was generated, and an event ID associated with that 
                  resource. More details on the contents of these 
                  fields can be found in the appropriate product 
                  maintenance documentation."
        ::= 2
 
    alarmMinor          TRAP-TYPE
        ENTERPRISE      g3-products
        VARIABLES       {
      
g3clientExternalName,g3alarmsProductID,g3alarmsAlarmNumber,g3alarmsPort,g3alarmsMaintName,g3alarmsOnBrd,g3alarmsAlarmType,g3alarmsIPAddress,g3alarmsCategory,g3alarmsErrorCodes 
}
        DESCRIPTION     "A Minor alarm has been issued by the switch. 
                  The fields in this trap type has the same 
                  differences, for g3alarmsPort, g3alarmsMaintName, 
                  and g3alarmsOnBrd, as described above for the 
                  alarmMajor trap type."
        ::= 3
 
    alarmWarning        TRAP-TYPE
        ENTERPRISE      g3-products
        VARIABLES       {
      
g3clientExternalName,g3alarmsProductID,g3alarmsAlarmNumber,g3alarmsPort,g3alarmsMaintName,g3alarmsOnBrd,g3alarmsAlarmType,g3alarmsIPAddress,g3alarmsCategory,g3alarmsErrorCodes 
}
        DESCRIPTION     "A Warning alarm has been issued by the switch.
                  The fields in this trap type has the same 
                  differences, for g3alarmsPort, g3alarmsMaintName, 
                  and g3alarmsOnBrd, as described above for the 
                  alarmMajor trap type."
        ::= 4
 
    alarmResolved        TRAP-TYPE
        ENTERPRISE      g3-products
        VARIABLES       {
      
g3clientExternalName,g3alarmsProductID,g3alarmsAlarmNumber,g3alarmsPort,g3alarmsMaintName,g3alarmsOnBrd,g3alarmsAlarmType,g3alarmsIPAddress,g3alarmsCategory,g3alarmsErrorCodes 
}
        DESCRIPTION     "An alarm has been resolved on the switch.
                  The fields in this trap type has the same 
                  differences, for g3alarmsPort, g3alarmsMaintName, 
                  and g3alarmsOnBrd, as described above for the 
                  alarmMajor trap type."
        ::= 12
 
    alarmRMS        TRAP-TYPE
        ENTERPRISE      g3-products
        VARIABLES       {
      
g3clientExternalName,g3alarmsProductID,g3alarmsAlarmNumber,g3alarmsPort,g3alarmsAlarmType,g3alarmsCategory,g3alarmsSrcIPAddr,g3alarmsSrcMACAddr,g3alarmsDestIPAddr,g3alarmsDestPort,g3alarmsProtocol,g3alarmsCount,g3alarmsViolationType,g3alarmsCode,g3alarmsData,g3alarmsICMPType,g3alarmsEventID,g3alarmsStatus 
}
        DESCRIPTION     "An alarm associated with security related events
                  has been issued by the server."
        ::= 13
        
    extalarmMajor       TRAP-TYPE
        ENTERPRISE      g3-products
        VARIABLES       {
      
g3clientExternalName,g3alarmsProductID,g3alarmsAlarmNumber,g3alarmsPort,g3alarmsMaintName,g3alarmsOnBrd,g3alarmsAlarmType,g3extdevAltName,g3extdevDescription,g3extdevID,g3extdevBuilding,g3extdevAddress,g3alarmsIPAddress,g3alarmsCategory,g3alarmsErrorCodes 
}
        DESCRIPTION     "An external device Major alarm has been issued
                  by the switch. The variables describe the location 
                  and nature of the alarm. This trap type only
                  applies to voice server alarms."
        ::= 5
 
    extalarmMinor       TRAP-TYPE
        ENTERPRISE      g3-products
        VARIABLES       {
      
g3clientExternalName,g3alarmsProductID,g3alarmsAlarmNumber,g3alarmsPort,g3alarmsMaintName,g3alarmsOnBrd,g3alarmsAlarmType,g3extdevAltName,g3extdevDescription,g3extdevID,g3extdevBuilding,g3extdevAddress,g3alarmsIPAddress,g3alarmsCategory,g3alarmsErrorCodes 
}
        DESCRIPTION     "An external device Minor alarm has been issued
                  by the switch. The variables describe the location 
                  and nature of the alarm. This trap type only
                  applies to voice server alarms."
        ::= 6
 
    extalarmWarning     TRAP-TYPE
        ENTERPRISE      g3-products
        VARIABLES       {
      
g3clientExternalName,g3alarmsProductID,g3alarmsAlarmNumber,g3alarmsPort,g3alarmsMaintName,g3alarmsOnBrd,g3alarmsAlarmType,g3extdevAltName,g3extdevDescription,g3extdevID,g3extdevBuilding,g3extdevAddress,g3alarmsIPAddress,g3alarmsCategory,g3alarmsErrorCodes 
}
        DESCRIPTION     "An external device Warning alarm has been issued
                  by the switch. The variables describe the location 
                  and nature of the alarm. This trap type only
                  applies to voice server alarms."
        ::= 14
 
    extalarmResolved    TRAP-TYPE
        ENTERPRISE      g3-products
        VARIABLES       {
      
g3clientExternalName,g3alarmsProductID,g3alarmsAlarmNumber,g3alarmsPort,g3alarmsMaintName,g3alarmsOnBrd,g3alarmsAlarmType,g3extdevAltName,g3extdevDescription,g3extdevID,g3extdevBuilding,g3extdevAddress,g3alarmsIPAddress,g3alarmsCategory,g3alarmsErrorCodes 
}
        DESCRIPTION     "An external device alarm has been resolved
                  by the switch. The variables describe the location 
                  and nature of the alarm. This trap type only
                  applies to voice server alarms."
        ::= 15
    
    alarmDispatch       TRAP-TYPE
        ENTERPRISE      g3-products
        VARIABLES       { 
g3clientExternalName,g3alarmsProductID,g3alarmsAlarmNumber }
        DESCRIPTION     "INADS has dispatched the alarm."
        ::= 7
    
    alarmClose          TRAP-TYPE
        ENTERPRISE      g3-products
        VARIABLES       { 
g3clientExternalName,g3alarmsProductID,g3alarmsAlarmNumber }
        DESCRIPTION     "INADS has closed the alarm."
        ::= 8
    
    alarmRestart        TRAP-TYPE
        ENTERPRISE      g3-products
        VARIABLES       { 
g3clientExternalName,g3alarmsProductID,g3alarmsAlarmNumber,g3restartDateTime,g3restartLevel,g3restartCarrier,g3restartCraftDemand,g3restartEscalated,g3restartInterchange,g3restartUnavailable, 
g3restartCause, g3vintageSpeArelease, g3vintageSpeBrelease, g3vintageSpeAupID, 
g3vintageSpeBupID}
        DESCRIPTION     "A system restart has occurred on the switch.
                        The variables describe the location and nature of 
                        the restart."
        ::= 9
            
    alarmNak            TRAP-TYPE
        ENTERPRISE      g3-products
        VARIABLES       { 
g3clientExternalName,g3alarmsProductID,g3alarmsAlarmNumber }
        DESCRIPTION     "A NAK was received in an attempt to forward the
                  alarm to INADS."
        ::= 10
            
    alarmNoAck          TRAP-TYPE
        ENTERPRISE      g3-products
        VARIABLES       { 
g3clientExternalName,g3alarmsProductID,g3alarmsAlarmNumber }
        DESCRIPTION     "A response other than an ACK or NAK was received
                  in an attempt to forward the alarm to INADS."
        ::= 11
 
    connectOther        TRAP-TYPE
        ENTERPRISE      g3-products
        VARIABLES       { g3clientExternalName }
        DESCRIPTION     "The connection status of the PBX/ECS has changed
                        to OTHER. This status indicates that the connect is
                        in an unknown state."
        ::= 101
 
    connectOff          TRAP-TYPE
        ENTERPRISE      g3-products
        VARIABLES       { g3clientExternalName }
        DESCRIPTION     "The connection status of the PBX/ECS has changed
                        to OFF. This status indicates that user set the
                        connection state to off so that the Proxy Agent
                        will not start up a connection with the PBX/ECS."
        ::= 102
 
    connectDown         TRAP-TYPE
        ENTERPRISE      g3-products
        VARIABLES       { g3clientExternalName }
        DESCRIPTION     "The connection status of the PBX/ECS has changed
                        to DOWN. This status indicates that the Proxy
                        Agent attempted to establish a connection with the
                        PBX/ECS and failed."
        ::= 103
 
    connectInit         TRAP-TYPE
        ENTERPRISE      g3-products
        VARIABLES       { g3clientExternalName }
        DESCRIPTION     "The connection status of the PBX/ECS has changed
                  to INIT. This status indicates that the Proxy
                  Agent is in the process of attempting to connect
                  to the PBX/ECS."
        ::= 104
 
    connectUp           TRAP-TYPE
        ENTERPRISE      g3-products
        VARIABLES       { g3clientExternalName }
        DESCRIPTION     "The connection status of the PBX/ECS has changed
                  to UP. This status indicates that the Proxy
                  Agent has a connection established with the PBX/ECS."
        ::= 105
 
    connectIdle         TRAP-TYPE
        ENTERPRISE      g3-products
        VARIABLES       { g3clientExternalName }
        DESCRIPTION     "The connection status of the PBX/ECS has changed
                  to IDLE. This status indicates that a connection
                  with the PBX/ECS is currently inactive due to the 
                  dynamic timeout having been reached without any 
                  activity. The connection will stay in the IDLE state
                  until an SNMP request or alarm is received. This 
                  connection status only applies if the connection 
                  type is 'dynamic'."
        ::= 106
 
    connectMax         TRAP-TYPE
        ENTERPRISE      g3-products
        VARIABLES       { g3clientExternalName }
        DESCRIPTION     "The connection to a PBX/ECS could not be established
                  due to the maximum allowed number of simultaneous
                  connections already being active."
        ::= 110
 
    proxyDown           TRAP-TYPE
        ENTERPRISE      g3-products
        VARIABLES       { sysName }
        DESCRIPTION     "The user has issued a stop proxy-agent command to
                  bring down the Proxy Agent."
        ::= 150
 
    proxyUp             TRAP-TYPE
        ENTERPRISE      g3-products
        VARIABLES       { sysName }
        DESCRIPTION     "The user has issued a start proxy-agent command to
                  bring up the Proxy Agent."
        ::= 151
 
END
