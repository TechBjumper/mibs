-- automatically generated by mosy 7.1 #1 (rathaus), do not edit!

FSC-LOG3-MIB DEFINITIONS ::= BEGIN


IMPORTS
	mib-2, enterprises
		FROM RFC1213-MIB
	SnmpAdminString
		FROM SNMP-FRAMEWORK-MIB
	NOTIFICATION-GROUP
		FROM SNMPv2-CONF
	DateAndTime, DisplayString
		FROM SNMPv2-TC
	Counter64, Counter, Gauge
		FROM SNMPv2-SMI;
-- created from fscLog3MIB (200207171300Z)

sni            OBJECT IDENTIFIER ::= { enterprises 231 }
sniProductMibs OBJECT IDENTIFIER ::= { sni 2 }
fscLog3MIB     OBJECT IDENTIFIER ::= { sniProductMibs 46 }

Gauge32 ::=
     Gauge
DateAndTime ::=
     DisplayString
SnmpAdminString ::=
     DisplayString

Counter16 ::=
    Counter

Unsigned16 ::=
    Gauge

UserID ::=
    Unsigned16

GroupID ::=
    Unsigned16

ProcessID ::=
    Gauge

MessageString ::=
    OCTET STRING

GlobalEntryLimit ::=
    Gauge

log3Objects OBJECT IDENTIFIER ::= { fscLog3MIB  1 }

log3Notifications OBJECT IDENTIFIER ::= { fscLog3MIB  2 }

log3Conformance OBJECT IDENTIFIER ::= { fscLog3MIB  3 }

log3Config OBJECT IDENTIFIER ::= { log3Objects  1 }

log3ConfigSubAgentVersion OBJECT-TYPE
    SYNTAX  SnmpAdminString
    ACCESS  read-only
    STATUS  mandatory
    DESCRIPTION
           "Version of SNMP Agent"
    ::= { log3Config  1 }

log3ConfigNotifyOperScope OBJECT-TYPE
    SYNTAX  INTEGER {
                 unknown(1),
                 other(2),
                 all(3),
                 local(4),
                 no(5)
               }
    ACCESS  read-only
    STATUS  mandatory
    DESCRIPTION
           "Set of Notifications sent by the subagent:
        - unknown:
          The Information cannot be supplied.
        - other:
          The Information does not correspond to the other enumerated
          values.
        - all:
          The subagent sends notifications for all events.
        - local:
          The subagent sends notifications for all events concerning a
          subset of systems including the local node.
        - no:
          The subagent sends no notifications."
    ::= { log3Config  2 }

log3ConfigNotifyAdminScope OBJECT-TYPE
    SYNTAX  INTEGER {
                 all(3),
                 local(4),
                 no(5)
               }
    ACCESS  read-write
    STATUS  mandatory
    DESCRIPTION
           "The desired Scope of Information supplied by the subagent"
    ::= { log3Config  3 }

log3ConfigGlobalEntryLimit OBJECT-TYPE
    SYNTAX  GlobalEntryLimit
    ACCESS  read-write
    STATUS  mandatory
    DESCRIPTION
           "The maximum number of notification entries. A value of 0 means no limit"
    DEFVAL  { 16 }
    ::= { log3Config  4 }

log3Stats OBJECT IDENTIFIER ::= { log3Objects  2 }

log3StatsCurrent OBJECT-TYPE
    SYNTAX  Counter
    ACCESS  read-only
    STATUS  mandatory
    DESCRIPTION
           "The number of event posted by the agent."
    ::= { log3Stats  1 }

log3StatsMemory OBJECT-TYPE
    SYNTAX  Gauge32
    ACCESS  read-only
    STATUS  mandatory
    DESCRIPTION
           "The memory in bytes used by the agent, to hold event informations."
    ::= { log3Stats  2 }

log3StatsReceived OBJECT-TYPE
    SYNTAX  Counter
    ACCESS  read-only
    STATUS  mandatory
    DESCRIPTION
           "The number of event received by the agent."
    ::= { log3Stats  3 }

log3Event OBJECT IDENTIFIER ::= { log3Objects  3 }

log3EventTable OBJECT-TYPE
    SYNTAX  SEQUENCE OF Log3EventEntry
    ACCESS  not-accessible
    STATUS  mandatory
    DESCRIPTION
           "The table of events. "
    ::= { log3Event  1 }

log3EventEntry OBJECT-TYPE
    SYNTAX  Log3EventEntry
    ACCESS  not-accessible
    STATUS  mandatory
    DESCRIPTION
           "log3 event data"
    INDEX   { log3EventIndex }
    ::= { log3EventTable  1 }

Log3EventEntry ::=
    SEQUENCE {
    log3EventIndex
        Gauge,

    log3EventComponentNumber
        Gauge,

    log3EventModuleName
        DisplayString,

    log3EventObjectID
        DisplayString,

    log3EventErrorNumber
        Gauge,

    log3EventErrorWeight
        INTEGER,

    log3EventProcessId
        ProcessID,

    log3EventReleaseVersion
        DisplayString,

    log3EventSystemName
        DisplayString,

    log3EventNodeName
        DisplayString,

    log3EventFirstTime
        DateAndTime,

    log3EventSequence
        Counter16,

    log3EventRepeats
        Counter16,

    log3EventLastTime
        DateAndTime,

    log3EventUserID
        UserID,

    log3EventUserName
        DisplayString,

    log3EventGroupID
        GroupID,

    log3EventGroupName
        DisplayString,

    log3EventMessageText
        DisplayString
    }

log3EventIndex OBJECT-TYPE
    SYNTAX  Gauge
    ACCESS  read-only
    STATUS  mandatory
    DESCRIPTION
           "The index into the event list.

	 MAX-ACCESS is not set to not-accessible, that
	 the agent can send the Index in Notifications.
	 This maybe helpfull for SNMP managers."
    ::= { log3EventEntry  1 }

log3EventComponentNumber OBJECT-TYPE
    SYNTAX  Gauge
    ACCESS  read-only
    STATUS  mandatory
    DESCRIPTION
           "A Number which uniquely identify a log3 Component.
         The Numbers are assigned by log3 number authority
         at FSC."
    ::= { log3EventEntry  2 }

log3EventModuleName OBJECT-TYPE
    SYNTAX  DisplayString
    ACCESS  read-only
    STATUS  mandatory
    DESCRIPTION
           "A string which describes the module, which send
         log3 informations.
         One module may have more then one object.
         E.g. spool module may have objects printer1
         and printer2."
    ::= { log3EventEntry  3 }

log3EventObjectID OBJECT-TYPE
    SYNTAX  DisplayString
    ACCESS  read-only
    STATUS  mandatory
    DESCRIPTION
           "A string which describe the modules object, which send
         log3 informations.
         E.g. printer1."
    ::= { log3EventEntry  4 }

log3EventErrorNumber OBJECT-TYPE
    SYNTAX  Gauge
    ACCESS  read-only
    STATUS  mandatory
    DESCRIPTION
           "A integer which describes the error code."
    ::= { log3EventEntry  5 }

log3EventErrorWeight OBJECT-TYPE
    SYNTAX  INTEGER {
                 emergency(1),
                 alert(2),
                 critical(3),
                 error(4),
                 warning(5),
                 notice(6),
                 informational(7),
                 debug(8),
                 other(9)
               }
    ACCESS  read-only
    STATUS  mandatory
    DESCRIPTION
           "A integer which describes the components error priority.
         Components should use syslog(3) priority.
	 Compoments which use illegal priorities above debug(8) are mapped
	 to other(9).
         A components error priority maybe FATAL, but this does not
         implies that the error is FATAL for the system."
    ::= { log3EventEntry  6 }

log3EventProcessId OBJECT-TYPE
    SYNTAX  ProcessID
    ACCESS  read-only
    STATUS  mandatory
    DESCRIPTION
           "The system OS process ID."
    ::= { log3EventEntry  7 }

log3EventReleaseVersion OBJECT-TYPE
    SYNTAX  DisplayString
    ACCESS  read-only
    STATUS  mandatory
    DESCRIPTION
           "Components release and version number."
    ::= { log3EventEntry  8 }

log3EventSystemName OBJECT-TYPE
    SYNTAX  DisplayString
    ACCESS  read-only
    STATUS  mandatory
    DESCRIPTION
           "Event reporting system name.
         If a system reports log3 events to a other system,
         which collect all log3 events, this is the name of
         the system, where the events occurred."
    ::= { log3EventEntry  9 }

log3EventNodeName OBJECT-TYPE
    SYNTAX  DisplayString
    ACCESS  read-only
    STATUS  mandatory
    DESCRIPTION
           "log3 reporting system name.
         If a system reports log3 events to a other system,
         which collect all log3 events, this is the name of
         the system, which collect events from other systems."
    ::= { log3EventEntry  10 }

log3EventFirstTime OBJECT-TYPE
    SYNTAX  DateAndTime
    ACCESS  read-only
    STATUS  mandatory
    DESCRIPTION
           "Time, where event first occurred."
    ::= { log3EventEntry  11 }

log3EventSequence OBJECT-TYPE
    SYNTAX  Counter16
    ACCESS  read-only
    STATUS  mandatory
    DESCRIPTION
           "a log3 internal sequence number.
         This number could be used to find the sequence of events,
         if more then one events happens in one second.
         log3 is responsible to hold this counter consistent."
    ::= { log3EventEntry  12 }

log3EventRepeats OBJECT-TYPE
    SYNTAX  Counter16
    ACCESS  read-only
    STATUS  mandatory
    DESCRIPTION
           "If a event keep going and no other event happens meanwhile,
         the event will be counted."
    ::= { log3EventEntry  13 }

log3EventLastTime OBJECT-TYPE
    SYNTAX  DateAndTime
    ACCESS  read-only
    STATUS  mandatory
    DESCRIPTION
           "Time, where event last occurred."
    ::= { log3EventEntry  14 }

log3EventUserID OBJECT-TYPE
    SYNTAX  UserID
    ACCESS  read-only
    STATUS  mandatory
    DESCRIPTION
           "The host OS UserID."
    ::= { log3EventEntry  15 }

log3EventUserName OBJECT-TYPE
    SYNTAX  DisplayString
    ACCESS  read-only
    STATUS  mandatory
    DESCRIPTION
           "The user who log the event.
         This is the UserID, decoded by the host OS."
    ::= { log3EventEntry  16 }

log3EventGroupID OBJECT-TYPE
    SYNTAX  GroupID
    ACCESS  read-only
    STATUS  mandatory
    DESCRIPTION
           "The host OS GroupID."
    ::= { log3EventEntry  17 }

log3EventGroupName OBJECT-TYPE
    SYNTAX  DisplayString
    ACCESS  read-only
    STATUS  mandatory
    DESCRIPTION
           "The group, where the user belong to.
         This is the log3GroupID, decoded by the host OS."
    ::= { log3EventEntry  18 }

log3EventMessageText OBJECT-TYPE
    SYNTAX  MessageString
    ACCESS  read-only
    STATUS  mandatory
    DESCRIPTION
           "This is the message, which the component will log.
         This message describe in detail what was happen. The component
         is responsible for the text content."
    ::= { log3EventEntry  19 }

log3Traps OBJECT IDENTIFIER ::= { log3Notifications  0 }

log3EmergencyNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Emergency Event"
	--#SUMMARY	"log3Event: System %s, Module %s, Error %d, Text: %s"
	--#ARGUMENTS	{ 8, 2, 4, 18 }
	--#SEVERITY	CRITICAL
	--#TIMEINDEX	1
	--#STATE	OPERATIONAL
	--
    ::= 1

log3AlertNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Alert Event"
	--#SUMMARY	"log3Event: System %s, Module %s, Error %d, Text: %s"
	--#ARGUMENTS	{ 8, 2, 4, 18 }
	--#SEVERITY	CRITICAL
	--#TIMEINDEX	1
	--#STATE	OPERATIONAL
	--
    ::= 2

log3CriticalNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Critical Event"
	--#SUMMARY	"log3Event: System %s, Module %s, Error %d, Text: %s"
	--#ARGUMENTS	{ 8, 2, 4, 18 }
	--#SEVERITY	CRITICAL
	--#TIMEINDEX	1
	--#STATE	OPERATIONAL
	--
    ::= 3

log3ErrorNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Error Event"
	--#SUMMARY	"log3Event: System %s, Module %s, Error %d, Text: %s"
	--#ARGUMENTS	{ 8, 2, 4, 18 }
	--#SEVERITY	MAJOR
	--#TIMEINDEX	1
	--#STATE	OPERATIONAL
	--
    ::= 4

log3WarningNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Warning Event"
	--#SUMMARY	"log3Event: System %s, Module %s, Error %d, Text: %s"
	--#ARGUMENTS	{ 8, 2, 4, 18 }
	--#SEVERITY	MINOR
	--#TIMEINDEX	1
	--#STATE	OPERATIONAL
	--
    ::= 5

log3NoticeNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Notice Event"
	--#SUMMARY	"log3Event: System %s, Module %s, Error %d, Text: %s"
	--#ARGUMENTS	{ 8, 2, 4, 18 }
	--#SEVERITY	INFORMATIONAL
	--#TIMEINDEX	1
	--#STATE	OPERATIONAL
	--
    ::= 6

log3InformationalNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Informational Event"
	--#SUMMARY	"log3Event: System %s, Module %s, Error %d, Text: %s"
	--#ARGUMENTS	{ 8, 2, 4, 18 }
	--#SEVERITY	INFORMATIONAL
	--#TIMEINDEX	1
	--#STATE	OPERATIONAL
	--
    ::= 7

log3DebugNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Debug Event"
	--#SUMMARY	"log3Event: System %s, Module %s, Error %d, Text: %s"
	--#ARGUMENTS	{ 8, 2, 4, 18 }
	--#SEVERITY	INFORMATIONAL
	--#TIMEINDEX	1
	--#STATE	OPERATIONAL
	--
    ::= 8

log3OtherNotice TRAP-TYPE
     ENTERPRISE { log3Notifications }
    VARIABLES   {                 log3EventIndex,                 log3EventComponentNumber,                 log3EventModuleName,                 log3EventObjectID,                 log3EventErrorNumber,                 log3EventErrorWeight,                 log3EventProcessId,                 log3EventReleaseVersion,                 log3EventSystemName,                 log3EventNodeName,                 log3EventFirstTime,                 log3EventSequence,                 log3EventRepeats,                 log3EventLastTime,                 log3EventUserID,                 log3EventUserName,                 log3EventGroupID,                 log3EventGroupName,                 log3EventMessageText               }
    DESCRIPTION
           "Information send to the management station."
	-- 
	-- FSC Alarm Service
	--
	--#TYPE		"General purpose log3 Event"
	--#SUMMARY	"log3Event: System %s, Module %s, Error %d, Text: %s"
	--#ARGUMENTS	{ 8, 2, 4, 18 }
	--#SEVERITY	INFORMATIONAL
	--#TIMEINDEX	1
	--#STATE	OPERATIONAL
	--
    ::= 9

log3Compliances OBJECT IDENTIFIER ::= { log3Conformance  1 }

log3Groups OBJECT IDENTIFIER ::= { log3Conformance  2 }

log3Compliance OBJECT IDENTIFIER ::= { log3Compliances  1 }

log3ConfigGroup OBJECT IDENTIFIER ::= { log3Groups  1 }

log3StatsGroup OBJECT IDENTIFIER ::= { log3Groups  2 }

log3EventGroup OBJECT IDENTIFIER ::= { log3Groups  3 }

log3NoticeGroup OBJECT IDENTIFIER ::= { log3Groups  4 }

END
