ZXR10-TCP-MIB DEFINITIONS ::= BEGIN    

IMPORTS
    MODULE-IDENTITY,
    OBJECT-TYPE,
    enterprises,
    Counter32
        FROM SNMPv2-SMI;        

 
 zte MODULE-IDENTITY
    LAST-UPDATED "201502270000Z"  
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS SMI MIB"

    REVISION "201502270000Z"  
    DESCRIPTION
       "modify:    tcpSendBufOver
                   tcpRecvBufOver
                   tcpAppSndRst
                   tcpRcvErrToSndRst
                   tcpSndFinSegs
                   tcpRcvFinSegs"
    REVISION "200504120000Z"  
    DESCRIPTION
       ""
  ::= { enterprises 3902 }

 zxr10 OBJECT IDENTIFIER ::= { zte 3}
 zxr10TCP OBJECT IDENTIFIER ::= { zxr10 68}
  

 -- the TCP general group

   
 tcpSendBufOver OBJECT-TYPE
     SYNTAX       Counter32
     MAX-ACCESS   read-only
     STATUS       obsolete
     DESCRIPTION
         "The total times of sending datagrams failure caused by
          spilled buffer. "
     ::= { zxr10TCP 1} 
     

 tcpRecvBufOver OBJECT-TYPE
   SYNTAX       Counter32
   MAX-ACCESS   read-only
   STATUS       obsolete
   DESCRIPTION
       "The total times of receiving datagrams failure caused by
        spilled buffer. "
   ::= { zxr10TCP 2}  
   
   
  tcpAppSndRst OBJECT-TYPE
     SYNTAX       Counter32
     MAX-ACCESS   read-only
     STATUS       obsolete
     DESCRIPTION
         "The total times of sending RST datagrams by app. "
     ::= { zxr10TCP 3}   
     
  tcpRcvErrToSndRst OBJECT-TYPE
     SYNTAX       Counter32
     MAX-ACCESS   read-only
     STATUS       obsolete
     DESCRIPTION
         "The total times of sending datagrams containing RST flag as recving error datagrams. "
     ::= { zxr10TCP 4} 
     

  tcpSndFinSegs OBJECT-TYPE
   SYNTAX       Counter32
   MAX-ACCESS   read-only
   STATUS       obsolete
   DESCRIPTION
       "The total times of sending datagrams containing FIN flag."
   ::= { zxr10TCP 5}  
   
   
   tcpRcvFinSegs OBJECT-TYPE
     SYNTAX       Counter32
     MAX-ACCESS   read-only
     STATUS       obsolete
     DESCRIPTION
         "The total times of receiving datagrams containing FIN flag. "
     ::= { zxr10TCP 6}        
END
