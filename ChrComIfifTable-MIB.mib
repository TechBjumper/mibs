ChrComIfifTable-MIB

--FORCE-INCLUDE	
--FORCE-INCLUDE	
--FORCE-INCLUDE	"mibhand.h"

	DEFINITIONS  ::=  BEGIN

IMPORTS
	OBJECT-TYPE, Counter32			FROM  SNMPv2-SMI
	Integer32, Unsigned32			FROM  SNMPv2-SMI
	chrComIf				FROM  Chromatis-MIB
	DisplayString			FROM  RFC1213-MIB
	AdminStatus				FROM  ChrTyp-MIB
	OperStatus				FROM  ChrTyp-MIB;

-- chrComIfifTable Table

chrComIfifTableTable		OBJECT-TYPE
	SYNTAX		SEQUENCE OF ChrComIfifTableEntry
	MAX-ACCESS	not-accessible
	STATUS		current
	DESCRIPTION
	"Chromatis Interface Table"
	::= { chrComIf 10}

chrComIfifTableEntry		OBJECT-TYPE
	SYNTAX		ChrComIfifTableEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "ifTable"
	::= { chrComIfifTableTable  1 }

ChrComIfifTableEntry  ::=
	SEQUENCE  {
	chrComIfifIndex			Unsigned32	(0..4294967295),
	chrComIfifName			DisplayString	(SIZE (0..32)),
	chrComIfifAdminStatus		AdminStatus,
	chrComIfifOperStatus		OperStatus,
	chrComIfvirtualIfIndex		Unsigned32	(0..4294967295),
	chrComIfreal1IfIndex		Unsigned32	(0..4294967295),
	chrComIfreal2IfIndex		Unsigned32	(0..4294967295)
}

chrComIfifIndex 	OBJECT-TYPE
	SYNTAX		Unsigned32	(0..4294967295)
	MAX-ACCESS 	read-only
	STATUS 		current
	DESCRIPTION
	"1.Index referring to the equipment table (Shelf, Slot) (9 bits)
2. Index containing MPHY port number in card.
For OC3 trib 0-3 
For TC&ATM If's we also have:
* SAR if.  = SAR_FIFO_IF (FE)
* APS FIFO = ASP_FIFO_IF (FF)
Note that these new interfaces have no 'low layers' bellow, i.e. there are no SONET layers on these virtual supports (6 bits).
3. Index containing sub-port number, e.g., 0-3 OC12's in OC48 frame (6 bits).
4. 
(2^6-1)-Null	(all bits are 1) reserved for NULL interface, NullVCPeerID, etc.
	1-OTS'SRC Optical Transmission Section Source (OPA,ADOM,OMDM) 
2-OTS-SNK Optical Transmission Section Sink. (OPA,ADOM,OMDM)
3-OMS-SRC Optical Multiplex Section Source (ADOM, OMDM)
4-OMS-SNK Optical Multiplex Section Sink (ADOM, OMDM)
5-OCH Optical Channel (OCM/Trib)
6-SNT-S Sonet Section (OCM/Trib)
7-SNT-L Sonet Line (OCM/Trib)
8-SNT-P Sonet Path (OCM/Trib)
9-TC&ATM  C and ATM general cell layer (OCM/Trib)
10-Ethernet
11-IP
12-Synchronization 
(6 bits)
5. Virtual interface represent a whole protection peer, out of which some members are working and the rest are protecting.
SAR and Egress FIFO are real interfaces (5 bits).

"
	::= { chrComIfifTableEntry  1 }

chrComIfifName 	OBJECT-TYPE
	SYNTAX		DisplayString	(SIZE (0..32))
	MAX-ACCESS 	read-write
	STATUS 		current
	DESCRIPTION
	"String of text defining the name of the port given by the user."
	::= { chrComIfifTableEntry  2 }

chrComIfifAdminStatus 	OBJECT-TYPE
	SYNTAX		AdminStatus
	MAX-ACCESS 	read-write
	STATUS 		current
	DESCRIPTION
	"The desired state of the interface.  The testing(3) state indicates that no operational packets can be passed.  When a managed system initializes, all interfaces start with ifAdminStatus in the down(2)state. As a result of either explicit management action or per configuration information retained by the managed system, ifAdminStatus is then changed to either the up(1) or testing(3) states (or remains in the down(2) state)."
	::= { chrComIfifTableEntry  3 }

chrComIfifOperStatus 	OBJECT-TYPE
	SYNTAX		OperStatus
	MAX-ACCESS 	read-only
	STATUS 		current
	DESCRIPTION
	"The down state of ifOperStatus has two meanings, depending on the value of ifAdminStatus.
(1) if ifAdminStatus is not down and ifOperStatus is down then a fault condition is presumed to exist on the interface.
2) if ifAdminStatus is down, then ifOperStatus will normally also be down (or notPresent) i.e.,there is not (necessarily) a fault condition on the interface.
"
	::= { chrComIfifTableEntry  4 }

chrComIfvirtualIfIndex 	OBJECT-TYPE
	SYNTAX		Unsigned32	(0..4294967295)
	MAX-ACCESS 	read-only
	STATUS 		current
	DESCRIPTION
	"This attribute is an outcome of the card/Path Protection attribute of the equipment table. The peer ID is a virtual card ID (which is the higher of the two peers).
Note that we do not reflect peering of VSP (real path protection) in this field!
"
	::= { chrComIfifTableEntry  5 }

chrComIfreal1IfIndex 	OBJECT-TYPE
	SYNTAX		Unsigned32	(0..4294967295)
	MAX-ACCESS 	read-only
	STATUS 		current
	DESCRIPTION
	"This field represents the first real IfIndex , if IfIndex is virtual. "
	::= { chrComIfifTableEntry  6 }

chrComIfreal2IfIndex 	OBJECT-TYPE
	SYNTAX		Unsigned32	(0..4294967295)
	MAX-ACCESS 	read-only
	STATUS 		current
	DESCRIPTION
	"This field represents the second real IfIndex , if IfIndex is virtual."
	::= { chrComIfifTableEntry  7 }


END
