-- Teldat, S.A.

                -- Parque Tecnolgico de Madrid

                -- 28760, Tres Cantos (Madrid)

                -- Tlf: +34-918076565

                -- Fax: +34-918076521

                -- e-mail: id@teldat.com


            -- MIB privada de Teldat


            -- Protocolo RIP


    -- Historial:
    --      07/02/14    M.A. Pastor     XH 3523. Errors with HP Openview 9.20
    -- 1.2  11-01-13    E. Amorena      XH 2610. MIBs compilation.
    -- 1.1 04-08-09   I. Muoz      Autenticacin MD5 en RIP
    -- 1.0  01/07/04  J. Molina     Cambio de nombre del fichero de RIP.mib
    --          a TELDAT-MON-PROTOCOL-RIP-MIB.mib
    -- 05/10/01  M. Meseguer    Traduccin a ingles
    -- 14/11/00  J. Alvarez     Implementacion inicial
-------------------------------------------------------------------------------

TELDAT-MON-PROTOCOL-RIP-MIB DEFINITIONS ::= BEGIN

    IMPORTS
            Counter, IpAddress
        FROM RFC1155-SMI
            OBJECT-TYPE
        FROM RFC-1212
            telProdNpMonProtocols
        FROM TELDAT-SW-STRUCTURE-MIB;


    -- Protocolo RIP

    telProdNpMonProtRip             OBJECT IDENTIFIER ::= { telProdNpMonProtocols 5 }

    -- Parametros globales de Rip

    telProdNpMonProtRipGlobalgroup  OBJECT IDENTIFIER ::= { telProdNpMonProtRip 1 }

    telProdNpMonProtRipGloRouchanges OBJECT-TYPE
        SYNTAX Counter
        ACCESS read-only
        STATUS mandatory
        DESCRIPTION
            "Number of routes modified by the RIP protocol."
        ::={ telProdNpMonProtRipGlobalgroup 1 }

    telProdNpMonProtRipGloResponsesent OBJECT-TYPE
        SYNTAX Counter
        ACCESS read-only
        STATUS mandatory
        DESCRIPTION
            "Number of responses sent to RIP requests."
        ::={ telProdNpMonProtRipGlobalgroup 2 }


    -- Tabla con los estadsicos del protocolo.

    telProdNpMonProtRipStatsTable OBJECT-TYPE
        SYNTAX SEQUENCE OF TelProdNpMonProtRipStatsEntry
        ACCESS not-accessible
        STATUS mandatory
        DESCRIPTION
            "Table with protocol statistics."
        ::={ telProdNpMonProtRip 2 }

    telProdNpMonProtRipStatsEntry OBJECT-TYPE
        SYNTAX TelProdNpMonProtRipStatsEntry
        ACCESS not-accessible
        STATUS mandatory
        DESCRIPTION
            "There are two indexes. One for interface and another one for
            different IP addresses assigned to that interface."
        INDEX {telProdNpMonProtRipStatsIfcindex, telProdNpMonProtRipStatsOrderindex}
        ::={ telProdNpMonProtRipStatsTable 1 }

    TelProdNpMonProtRipStatsEntry ::=
        SEQUENCE {
            telProdNpMonProtRipStatsIfcindex
                INTEGER,
            telProdNpMonProtRipStatsOrderindex
                INTEGER,
            telProdNpMonProtRipStatsIpadddres
                IpAddress,
            telProdNpMonProtRipStatsPackrxerrors
                Counter,
            telProdNpMonProtRipStatsRourxerrors
                Counter,
            telProdNpMonProtRipStatsTriggupdatestx
                Counter,
            telProdNpMonProtRipStatsDisMd5Pkts
                Counter,
            telProdNpMonProtRipStatsDisMd5Seqnum
                Counter
            }

    telProdNpMonProtRipStatsIfcindex OBJECT-TYPE
        SYNTAX INTEGER
        ACCESS read-only
        STATUS mandatory
        DESCRIPTION
            "Interface number. It is the first index of the table."
        ::={ telProdNpMonProtRipStatsEntry 1 }

    telProdNpMonProtRipStatsOrderindex OBJECT-TYPE
        SYNTAX INTEGER
        ACCESS read-only
        STATUS mandatory
        DESCRIPTION
            "Order of entry within an interface. It is the second index."
        ::={ telProdNpMonProtRipStatsEntry 2 }

    telProdNpMonProtRipStatsIpadddres OBJECT-TYPE
        SYNTAX IpAddress
        ACCESS read-only
        STATUS mandatory
        DESCRIPTION
            "IP addresses of the interface."
        ::={ telProdNpMonProtRipStatsEntry 3 }

    telProdNpMonProtRipStatsPackrxerrors OBJECT-TYPE
        SYNTAX Counter
        ACCESS read-only
        STATUS mandatory
        DESCRIPTION
            "It counts the number of packets with error received."
        ::={ telProdNpMonProtRipStatsEntry 4 }

    telProdNpMonProtRipStatsRourxerrors OBJECT-TYPE
        SYNTAX Counter
        ACCESS read-only
        STATUS mandatory
        DESCRIPTION
            "It counts the number of wrong routes received."
        ::={ telProdNpMonProtRipStatsEntry 5 }

    telProdNpMonProtRipStatsTriggupdatestx OBJECT-TYPE
        SYNTAX Counter
        ACCESS read-only
        STATUS mandatory
        DESCRIPTION
            "It counts the updates sent by change of route."
        ::={ telProdNpMonProtRipStatsEntry 6 }

    telProdNpMonProtRipStatsDisMd5Pkts OBJECT-TYPE
        SYNTAX Counter
        ACCESS read-only
        STATUS mandatory
        DESCRIPTION
            "It counts the number of discarded packets with bad authentication."
        ::={ telProdNpMonProtRipStatsEntry 7 }

    telProdNpMonProtRipStatsDisMd5Seqnum OBJECT-TYPE
        SYNTAX Counter
        ACCESS read-only
        STATUS mandatory
        DESCRIPTION
            "It counts the numbre of packets with wrong sequence number."
        ::={ telProdNpMonProtRipStatsEntry 8 }

END
