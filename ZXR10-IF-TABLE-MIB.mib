--  ************************************************
--  $Id: ZXR10-ETH-MGT.mib 12 2005-07-13 01:01:17Z taowq $
--
--  ZXR10-ETH-MGT.mib: ZXR10 ethnet query and  configuration MIB file
--  
--  Jun. 2005, Tao wenqiang
--   
--  Copyright(c) 2005 by ZTE Corporaton
--  All rights reservered
--
--  ************************************************

ZXR10-IF-TABLE-MIB DEFINITIONS ::= BEGIN

IMPORTS
    MODULE-IDENTITY,OBJECT-TYPE,Integer32,Unsigned32
        FROM SNMPv2-SMI
   zxr10interfaces
        FROM ZXR10-SMI
   TimeStamp,DisplayString,TruthValue,MacAddress,TEXTUAL-CONVENTION   
        FROM SNMPv2-TC
   Ipv6Address  
        FROM IPV6-TC 
   RowStatus                           
        FROM SNMPv2-TC;
    
    zxr10IfTableMgtMIB MODULE-IDENTITY
    LAST-UPDATED "201805160900Z"
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS v4.6.03 ethnet query and configuration MIB"
     
    REVISION "201805160900Z"
    DESCRIPTION
     "Change the SYNTAX of node zxr10IfCfgDescr from DisplayString(SIZE(0..104) to DisplayString(SIZE(0..238)."

    REVISION "201802060900Z"
    DESCRIPTION
     "Add TruthValue of node zxr10IfCfgMacAddressAnycast to the Zxr10IfEntry mib table." 
      
    REVISION "201606010900Z"
    DESCRIPTION
     "Change the SYNTAX of node zxr10IfCfgMtu from Unsigned32(1500..9600) to Unsigned32(0..9600).
      Change the SYNTAX of node zxr10IfEffectiveMtu from Unsigned32(1500..9600) to Unsigned32(0..9600).
      Change the SYNTAX of node zxr10IfCfgIpMtu from Unsigned32(68..9600) to Unsigned32(0..9600).
      Change the SYNTAX of node zxr10IfEffectiveIpMtu from Unsigned32(68..9600) to Unsigned32(0..9600)."

    REVISION "201601180900Z"
    DESCRIPTION
     "Change the SYNTAX of node zxr10IfCfgUnnumberName from DisplayString(SIZE(1..31)) to DisplayString(SIZE(0..31)).
      Change the SYNTAX of node zxr10IfCfgDescr from DisplayString(SIZE(1..104)) to DisplayString(SIZE(0..104))."

    REVISION "201507151521Z"
    DESCRIPTION
     "Add SYNTAX of node zxr10IfTriggerTrackTrigger with the value reverse(4) in zxr10IfTriggerTable."

    REVISION "201503141650Z"
    DESCRIPTION
     "Add node zxr10IfCfgDescr in zxr10IfTable.
     Change MAX-ACCESS of node zxr10IfCfgMtu from read-only to read-create.
     Change MAX-ACCESS of node zxr10IfCfgIpMtu from read-only to read-create.
     Change MAX-ACCESS of node zxr10IfCfgMplsMtu from read-only to read-create.
     Change SYNTAX of node zxr10IfCfgMtu and zxr10IfEffectiveMtu from Unsigned32(1500..9216) to Unsigned32(1500..9600).
     Change SYNTAX of node zxr10IfCfgIpMtu and zxr10IfEffectiveIpMtu from Unsigned32(68..9216) to Unsigned32(68..9600).
     Change SYNTAX of node zxr10IfCfgIpv6Mtu and zxr10IfEffectiveIpv6Mtu from Unsigned32(1280..9216) to Unsigned32(1280..9600).
     Change SYNTAX of node zxr10IfCfgMplsMtu and zxr10IfEffectiveMplsMtu from Unsigned32(68..9216) to Unsigned32(68..9600)."
     
    REVISION "201403200900Z"
    DESCRIPTION
     "Add node zxr10IfTriggerShutDownPeriod in zxr10IfTriggerTable."

    REVISION "201402190900Z"
    DESCRIPTION
     "IP unnumbered support set operation for SNMP"
 
    REVISION "201402111600Z"
    DESCRIPTION
     "Add a enum value for node zxr10IfAttrIfL2L3Attr in zxr10IfAttrTable."

    REVISION "201401130900Z"
    DESCRIPTION
     "Change the description of zxr10IPv6AddrType."
  
    REVISION "201312090900Z"
    DESCRIPTION
     "Add zxr10IPv6AddrTable."

    REVISION "201311080900Z"
    DESCRIPTION
     "Add interface trigger for SNMP according with CLI. 
      Add zxr10IfCommonMIB."
      
    REVISION "201305031600Z"
    DESCRIPTION
     "Change syntax value for some nodes in zxr10IfTable.
      Add units for some nodes in zxr10IfTable."
    
    REVISION "201304160900Z"
    DESCRIPTION
     "Changes zxr10IfTrackTable index.Our equipments now support 
      track instances with different types on the same interface."

    REVISION "201304091600Z"
    DESCRIPTION
     "Add a enum value for node zxr10IfCfgIpLdshPolicy in zxr10IfTable 
      and change the default value from {2} to {per_destination}.
      Add a enum value for node zxr10IfCfgGateWay in  zxr10IfTable and
      set the value as default value."

    REVISION "201304020900Z"
    DESCRIPTION
     "Add interface items for SNMP according with CLI.
      Add zxr10IfGroupBindTable and zxr10IfCipBindTable 
      and correct the non-compliant description."
    
    REVISION "201303151140Z"
    DESCRIPTION
     "Index of zxr10IfTable is changed from zxr10IfIfName to zxr10IfName."
   
    REVISION "200504120000Z"
    DESCRIPTION
       ""
    ::= { zxr10interfaces 4 }
    --=============================
    --Defined Data type  
    --============================= 
    --=============================
    --1.zxr10IfTableMgtMIBObjects 
    --============================= 
    zxr10IfTableMgtMIBObjects        
      OBJECT IDENTIFIER ::= { zxr10IfTableMgtMIB 1 }                                                       
        zxr10IfTableLastChange OBJECT-TYPE
             SYNTAX      TimeStamp
             MAX-ACCESS  read-only
             STATUS      current
             DESCRIPTION
               "The value of sysUpTime on the most recent occasion at which 
                interface table changed"
             ::= { zxr10IfTableMgtMIBObjects 1 }

        zxr10EthSubIfTableLastChange OBJECT-TYPE
             SYNTAX      TimeStamp
             MAX-ACCESS  read-only
             STATUS      current
             DESCRIPTION
               "The value of sysUpTime on the most recent occasion at which 
                ethernet sub-interface table changed"
             ::= { zxr10IfTableMgtMIBObjects 2 }  
        
        zxr10EthPhyIfTableLastChange OBJECT-TYPE
             SYNTAX      TimeStamp
             MAX-ACCESS  read-only
             STATUS      current
             DESCRIPTION
               "The value of sysUpTime on the most recent occasion at which  
                ethernet interface table changed"
             ::={ zxr10IfTableMgtMIBObjects 3 }      
        
        zxr10PosPhyIfTableLastChange OBJECT-TYPE
             SYNTAX      TimeStamp
             MAX-ACCESS  read-only
             STATUS      current
             DESCRIPTION
               "The value of sysUpTime on the most recent occasion at which  
                pos interface table changed"
             ::= { zxr10IfTableMgtMIBObjects 4 }
     --=============================
     --2.zxr10IfAttrTable 
     --============================= 
     zxr10IfAttrTable  OBJECT-TYPE
        SYNTAX  SEQUENCE OF Zxr10IfAttrEntry
        MAX-ACCESS  not-accessible
        STATUS  current
        DESCRIPTION
            "Interface attribute table"
        ::= { zxr10IfTableMgtMIB 2 }

    zxr10IfAttrEntry  OBJECT-TYPE
        SYNTAX  Zxr10IfAttrEntry
        MAX-ACCESS  not-accessible
        STATUS  current
        DESCRIPTION
            ""
        INDEX  { zxr10IfAttrIfName }
        ::= { zxr10IfAttrTable 1 }

    Zxr10IfAttrEntry ::=
        SEQUENCE {
            zxr10IfAttrIfName
                DisplayString,
            zxr10IfAttrIfIndex
                Integer32,
            zxr10IfAttrIfL2L3Attr
                INTEGER                             
                                                                                                                                                 
    }

    zxr10IfAttrIfName  OBJECT-TYPE
        SYNTAX  DisplayString(SIZE(0..32))
        MAX-ACCESS  read-only 
        STATUS  current
        DESCRIPTION
            "Interface name"
        ::= { zxr10IfAttrEntry 1 }    


    zxr10IfAttrIfIndex OBJECT-TYPE
        SYNTAX   Integer32
        MAX-ACCESS  read-only
        STATUS  current
        DESCRIPTION
            "Interface index"
        ::= { zxr10IfAttrEntry 2 }          

    zxr10IfAttrIfL2L3Attr OBJECT-TYPE
        SYNTAX  INTEGER{none(1),l2(2),l3(3),l2andl3(4)}  
        MAX-ACCESS  read-only
        STATUS  current
        DESCRIPTION
            "Interface L2/L3 attribute"
        ::= { zxr10IfAttrEntry 3 } 
        
     --=============================
     --3.zxr10IfTable 
     --============================= 
    --
    -- Textual Conventions
    --
    BwType ::= TEXTUAL-CONVENTION
        DISPLAY-HINT "d-3"
        STATUS       current
        DESCRIPTION
                     " A BwType value of 1234 be rendered as '1.234'.It needs
                       webmaster software parse the clause 'DISPLAY-HINT' to 
                       render 1234 as 1.234."
        SYNTAX       Unsigned32

    zxr10IfTable  OBJECT-TYPE
        SYNTAX  SEQUENCE OF Zxr10IfEntry
        MAX-ACCESS  not-accessible
        STATUS  current
        DESCRIPTION
            "Interface table"
        ::= { zxr10IfTableMgtMIB 3 }

    zxr10IfEntry  OBJECT-TYPE
        SYNTAX  Zxr10IfEntry
        MAX-ACCESS  not-accessible
        STATUS  current
        DESCRIPTION
            ""
        INDEX  { zxr10IfName }
        ::= { zxr10IfTable 1 }

    Zxr10IfEntry ::=
        SEQUENCE {
            zxr10IfName
                DisplayString,
            zxr10IfIndex
                Unsigned32,
            zxr10IfCfgMtu
                Unsigned32,
            zxr10IfEffectiveMtu
                Unsigned32,
            zxr10IfCfgIpMtu
                Unsigned32,
            zxr10IfEffectiveIpMtu
                Unsigned32,
            zxr10IfCfgIpv6Mtu
                Unsigned32,
            zxr10IfEffectiveIpv6Mtu
                Unsigned32,
            zxr10IfCfgMplsMtu
                Unsigned32,
            zxr10IfEffectiveMplsMtu
                Unsigned32,
            zxr10IfCfgMacAddress
                MacAddress,
            zxr10IfEffectiveMacAddress
                MacAddress,
            zxr10IfCfgMacOffset
                Unsigned32,
            zxr10IfCfgVrfName
                DisplayString,
            zxr10IfCfgUnnumberName
                DisplayString,
            zxr10IfCfgLdshPriority
                Integer32,
            zxr10IfCfgLdshWaterLine
                Integer32,
            zxr10IfCfgLdshBw
                BwType,
            zxr10IfEffectiveLdshBw
                BwType,
            zxr10IfCfgIpLdshPolicy
                INTEGER,
            zxr10IfCfgMultiShareCost
                Integer32,
            zxr10IfCfgGateWay
                INTEGER,
            zxr10IfCfgDescr
                DisplayString,
            zxr10IfCfgMacAddressAnycast
                TruthValue,
            zxr10IfCfgRowStatus
                RowStatus
    }

    zxr10IfName  OBJECT-TYPE
        SYNTAX  DisplayString(SIZE(0..32))
        MAX-ACCESS  read-only 
        STATUS  current
        DESCRIPTION
            "Interface name"
        ::= { zxr10IfEntry 1 }    

    zxr10IfIndex OBJECT-TYPE
        SYNTAX   Unsigned32
        MAX-ACCESS  read-only
        STATUS  current
        DESCRIPTION
            "Interface index"
        ::= { zxr10IfEntry 2 }      
    
    zxr10IfCfgMtu OBJECT-TYPE
        SYNTAX   Unsigned32(0..9600)
        UNITS    "bytes"
        MAX-ACCESS  read-create
        STATUS  current
        DESCRIPTION
            "Interface configured card mtu.
             Different configuration ranges in different interfaces."
        ::= { zxr10IfEntry 3 } 
    
    zxr10IfEffectiveMtu OBJECT-TYPE
        SYNTAX  Unsigned32(0..9600)
        UNITS    "bytes"
        MAX-ACCESS  read-only
        STATUS  current
        DESCRIPTION
            "Interface effective card mtu.
             Different effective ranges in different interfaces."
        ::= { zxr10IfEntry 4 }

    zxr10IfCfgIpMtu OBJECT-TYPE
        SYNTAX   Unsigned32(0..9600)
        UNITS    "bytes"
        MAX-ACCESS  read-create
        STATUS  current
        DESCRIPTION
            "Interface configured ip mtu.
             Different configuration ranges in different interfaces."
        ::= { zxr10IfEntry 5 } 
    
    zxr10IfEffectiveIpMtu OBJECT-TYPE
        SYNTAX  Unsigned32(0..9600)
        UNITS    "bytes"
        MAX-ACCESS  read-only
        STATUS  current
        DESCRIPTION
            "Interface effective ip mtu.
             Different effective ranges in different interfaces."
        ::= { zxr10IfEntry 6 }

    zxr10IfCfgIpv6Mtu OBJECT-TYPE
        SYNTAX   Unsigned32(1280..9600)
        UNITS    "bytes"
        MAX-ACCESS  read-only
        STATUS  current
        DESCRIPTION
            "Interface configured ipv6 mtu.
             Different configuration ranges in different interfaces."
        ::= { zxr10IfEntry 7 } 
    
    zxr10IfEffectiveIpv6Mtu OBJECT-TYPE
        SYNTAX  Unsigned32(1280..9600)
        UNITS    "bytes"
        MAX-ACCESS  read-only
        STATUS  current
        DESCRIPTION
            "Interface effective ipv6 mtu.
             Different effective ranges in different interfaces."
        ::= { zxr10IfEntry 8 }

    zxr10IfCfgMplsMtu OBJECT-TYPE
        SYNTAX   Unsigned32(68..9600)
        UNITS    "bytes"
        MAX-ACCESS  read-create
        STATUS  current
        DESCRIPTION
            "Interface configured mpls mtu.
             Different configuration ranges in different interfaces."
        ::= { zxr10IfEntry 9 }         
    
    zxr10IfEffectiveMplsMtu OBJECT-TYPE
        SYNTAX  Unsigned32(68..9600)
        UNITS    "bytes"
        MAX-ACCESS  read-only
        STATUS  current
        DESCRIPTION
            "Interface effective mpls mtu.
             Different effective ranges in different interfaces."
        ::= { zxr10IfEntry 10 }
    
    zxr10IfCfgMacAddress OBJECT-TYPE
        SYNTAX   MacAddress
        MAX-ACCESS  read-only
        STATUS  current
        DESCRIPTION
            "Interface configured mac-address."
        ::= { zxr10IfEntry 11 }
    
    zxr10IfEffectiveMacAddress OBJECT-TYPE
        SYNTAX  MacAddress
        MAX-ACCESS  read-only
        STATUS  current
        DESCRIPTION
            "Interface effective mac-address."
        ::= { zxr10IfEntry 12}    
    
    zxr10IfCfgMacOffset OBJECT-TYPE
        SYNTAX   Unsigned32
        MAX-ACCESS  read-only
        STATUS  current
        DESCRIPTION
            "Interface configured mac offset.
             The range of macoffset is alterable,it is decided by pm."
        ::= { zxr10IfEntry 13 }
    
    zxr10IfCfgVrfName  OBJECT-TYPE
        SYNTAX  DisplayString(SIZE(1..32))
        MAX-ACCESS  read-only 
        STATUS  current
        DESCRIPTION
            "Interface vrf name."
        ::= { zxr10IfEntry 14 } 

    zxr10IfCfgUnnumberName  OBJECT-TYPE
        SYNTAX  DisplayString(SIZE(0..31))
        MAX-ACCESS  read-create 
        STATUS  current
        DESCRIPTION
            "Interface ip unnumber name."
        ::= { zxr10IfEntry 15 }         
                                  
    zxr10IfCfgLdshPriority OBJECT-TYPE
        SYNTAX   Integer32(1..7)
        MAX-ACCESS  read-only
        STATUS  current
        DESCRIPTION
            "Interface configured load sharing priority."
        ::= { zxr10IfEntry 16 }
    
    zxr10IfCfgLdshWaterLine OBJECT-TYPE
        SYNTAX   Integer32(50..95)
        MAX-ACCESS  read-only
        STATUS  current
        DESCRIPTION
            "Interface configured load sharing waterline.
             The waterline is an option attribute,
             if only when you have set the attribute priority 
             then you can set waterline."
        DEFVAL    {90}
        ::= { zxr10IfEntry 17 }

    zxr10IfCfgLdshBw OBJECT-TYPE
        SYNTAX   BwType
        UNITS    "kbps"
        MAX-ACCESS  read-only
        STATUS  current
        DESCRIPTION
            "Interface configured load sharing bandwidth."
        ::= { zxr10IfEntry 18 }

    zxr10IfEffectiveLdshBw OBJECT-TYPE
        SYNTAX  BwType
        UNITS    "kbps"
        MAX-ACCESS  read-only
        STATUS  current
        DESCRIPTION
            "Interface effective load sharing bandwidth."
        ::= { zxr10IfEntry 19 }

    zxr10IfCfgIpLdshPolicy OBJECT-TYPE
        SYNTAX   INTEGER{per-destination(1),per-packet(2),nonsupport(3)}
        MAX-ACCESS  read-only
        STATUS  current
        DESCRIPTION
            "Interface configured ip load sharing policy."
        DEFVAL    {per-destination}
        ::= { zxr10IfEntry 20 }

    zxr10IfCfgMultiShareCost OBJECT-TYPE
        SYNTAX   Integer32(1..8)
        MAX-ACCESS  read-only
        STATUS  current
        DESCRIPTION
            "Interface configured mulitpule sharing cost."
        DEFVAL    {1}
        ::= { zxr10IfEntry 21 }

    zxr10IfCfgGateWay OBJECT-TYPE
        SYNTAX   INTEGER{bGateWay(1),notGateWay(2),nonsupport(3)}
        MAX-ACCESS  read-only
        STATUS  current
        DESCRIPTION
            "Interface configured whether it's gateway interface."
        DEFVAL    {notGateWay}
        ::= { zxr10IfEntry 22 }        
       
    zxr10IfCfgDescr OBJECT-TYPE
        SYNTAX  DisplayString(SIZE(0..238))
        MAX-ACCESS  read-create
        STATUS  current
        DESCRIPTION
            "A textual string containing information about the
             interface.  This string may be set by the network
             management system."
        ::= { zxr10IfEntry 23 }  
        
    zxr10IfCfgMacAddressAnycast OBJECT-TYPE
        SYNTAX   TruthValue
        MAX-ACCESS  read-only
        STATUS  current
        DESCRIPTION
            "The flag of the interface effective mac-address is anycast or not."
        DEFVAL  { false }
        ::= { zxr10IfEntry 24 }

    zxr10IfCfgRowStatus OBJECT-TYPE
        SYNTAX   RowStatus
        MAX-ACCESS  read-create
        STATUS  current
        DESCRIPTION
            "Row status.active(1),notInService(2),notReady(3),createAndGo(4),
             createAndWait(5),destroy(6)."
        ::= { zxr10IfEntry 100 }                                                                     
     --=============================
     --4.zxr10IfTrackTable 
     --=============================   
    zxr10IfTrackTable  OBJECT-TYPE
        SYNTAX  SEQUENCE OF Zxr10IfTrackEntry
        MAX-ACCESS  not-accessible
        STATUS  current
        DESCRIPTION
            "Interface track table"
        ::= { zxr10IfTableMgtMIB 4 }

    zxr10IfTrackEntry  OBJECT-TYPE
        SYNTAX  Zxr10IfTrackEntry
        MAX-ACCESS  not-accessible
        STATUS  current
        DESCRIPTION
            "A list of interface track entries."
        INDEX  { zxr10IfTrackIfName,  
                 zxr10IfTrackTrackName,  
                 zxr10IfTrackTrackType}
        ::= { zxr10IfTrackTable 1 }

    Zxr10IfTrackEntry ::=
        SEQUENCE {
            zxr10IfTrackIfName
                DisplayString,  
            zxr10IfTrackTrackName
                DisplayString,    
            zxr10IfTrackIfIndex
                Integer32, 
            zxr10IfTrackTrackType
                INTEGER,
            zxr10IfTrackIsGrpTrack
                INTEGER
                                                                                                                                   
    }
        
    zxr10IfTrackIfName  OBJECT-TYPE
        SYNTAX  DisplayString(SIZE(1..31))
        MAX-ACCESS  not-accessible 
        STATUS  current
        DESCRIPTION
            "Interface name"
        ::= { zxr10IfTrackEntry 1 }  
       
    zxr10IfTrackTrackName  OBJECT-TYPE
        SYNTAX  DisplayString(SIZE(1..31))
        MAX-ACCESS  not-accessible 
        STATUS  current
        DESCRIPTION
            "Track name"
        ::= { zxr10IfTrackEntry 2 } 
        
    zxr10IfTrackIfIndex  OBJECT-TYPE
        SYNTAX  Integer32
        MAX-ACCESS  read-only 
        STATUS  current
        DESCRIPTION
            "Interface index"
        ::= { zxr10IfTrackEntry 3 }  
        
    zxr10IfTrackTrackType  OBJECT-TYPE
        SYNTAX  INTEGER{
                        l2(1),    --l2 track
                        ipv4(2),  --ipv4 track
                        ipv6(3)   --ipv6 track     
                       }                        
        MAX-ACCESS  not-accessible 
        STATUS  current
        DESCRIPTION
            "Track type: 
            l2(1)   --zxr10IfTrackTrackName is l2 track 
            ipv4(2) --zxr10IfTrackTrackName is ipv4 track
            ipv6(3) --zxr10IfTrackTrackName is ipv6 track
            "
        ::= { zxr10IfTrackEntry 4 }       
        
    zxr10IfTrackIsGrpTrack  OBJECT-TYPE
        SYNTAX  INTEGER{false(0), true(1)}
        MAX-ACCESS  read-only 
        STATUS  current
        DESCRIPTION
            "Group track flag:
            false(0) --zxr10IfTrackTrackName is not group track 
             true(1) --zxr10IfTrackTrackName is group track
             "
        ::= { zxr10IfTrackEntry 5 }
    --=============================
    --5.zxr10IfTableMgtObjects 
    --=============================       
    zxr10IfTableMgtObjects         
      OBJECT IDENTIFIER ::= { zxr10IfTableMgtMIB 5 } 
    --=============================
    --5.1 zxr10PortRelationMIB 
    --=============================
    zxr10PortRelationMIB           
      OBJECT IDENTIFIER ::= { zxr10IfTableMgtObjects 1 } 
    --=============================
    --5.1.1 zxr10PortRelationGlobalObjects 
    --=============================
    zxr10PortRelationGlobalObjects 
      OBJECT IDENTIFIER ::= { zxr10PortRelationMIB 1 }  
    --=============================
    --5.1.2 zxr10PortRelationObjects 
    --=============================
    zxr10PortRelationObjects       
      OBJECT IDENTIFIER ::= { zxr10PortRelationMIB 2 }
    --=============================
    --5.1.2.1 zxr10IfGroup 
    --=============================
    zxr10IfGroup                   
      OBJECT IDENTIFIER ::= { zxr10PortRelationObjects 1 } 
    --=============================
    --5.1.2.1.1 zxr10IfGroupStatGroup 
    --=============================
    zxr10IfGroupStatGroup          
      OBJECT IDENTIFIER ::= { zxr10IfGroup 1 } 
    --=============================
    --5.1.2.1.2 zxr10IfGroupTable 
    --=============================
    --zxr10IfGroupTable OBJECT-TYPE 
    --    SYNTAX       SEQUENCE OF Zxr10IfGroupEntry 
    --    MAX-ACCESS   not-accessible 
    --    STATUS       current
    --    DESCRIPTION
    --        "A list of interface group entries." 
    --    ::= { zxr10IfGroup 2 }
    --
    --zxr10IfGroupEntry OBJECT-TYPE 
    --    SYNTAX       Zxr10IfGroupEntry
    --    MAX-ACCESS   not-accessible 
    --    STATUS       current
    --    DESCRIPTION
    --        "An entry containing management information applicable to a
    --        particular interface group." 
    --    INDEX { zxr10IfGroupName } 
    --    ::= { zxr10IfGroupTable 1 }
    --
    --Zxr10IfGroupEntry ::=  
    --    SEQUENCE {
    --        zxr10IfGroupName           DisplayString
    --        }
    --
    --zxr10IfGroupName OBJECT-TYPE
    --    SYNTAX        DisplayString(SIZE(1..31))
    --    MAX-ACCESS    not-accessible 
    --    STATUS        current
    --    DESCRIPTION
    --       "The textual name of the interface group."
    --        ::= { zxr10IfGroupEntry 1 }
    --=============================
    --5.1.2.1.3 zxr10IfGroupBindTable 
    --=============================
    zxr10IfGroupBindTable OBJECT-TYPE 
        SYNTAX       SEQUENCE OF Zxr10IfGroupBindEntry 
        MAX-ACCESS   not-accessible 
        STATUS       current
        DESCRIPTION
            "A list of interface group binding entries." 
        ::= { zxr10IfGroup 3 }
  
    zxr10IfGroupBindEntry OBJECT-TYPE 
        SYNTAX       Zxr10IfGroupBindEntry
        MAX-ACCESS   not-accessible 
        STATUS       current
        DESCRIPTION
            "An entry containing management information applicable to a
            particular interface binded group." 
        INDEX { zxr10IfGroupBindMemName } 
        ::= { zxr10IfGroupBindTable 1 }

    Zxr10IfGroupBindEntry ::=  
        SEQUENCE {
            zxr10IfGroupBindMemName           DisplayString,
            zxr10IfGroupBindGroupName         DisplayString
            }
  
    zxr10IfGroupBindMemName OBJECT-TYPE
        SYNTAX        DisplayString(SIZE(1..31))
        MAX-ACCESS    not-accessible 
        STATUS        current
        DESCRIPTION
           "The textual name of the member interface."
            ::= { zxr10IfGroupBindEntry 1 }
   
    zxr10IfGroupBindGroupName OBJECT-TYPE
        SYNTAX        DisplayString(SIZE(1..31))
        MAX-ACCESS    read-create 
        STATUS        current
        DESCRIPTION
           "The textual name of the interface group."
            ::= { zxr10IfGroupBindEntry 2 }
    --=============================
    --5.1.2.2 zxr10CipRelation  
    --=============================
    zxr10CipRelation               
      OBJECT IDENTIFIER ::= { zxr10PortRelationObjects 2 } 
    --=============================
    --5.1.2.2.1 zxr10CipRelation  
    --=============================
    zxr10IfCipBindStatGroup        
      OBJECT IDENTIFIER ::= { zxr10CipRelation 1 } 
    --=============================
    --5.1.2.2.2 zxr10IfCipBindTable   
    --=============================
     zxr10IfCipBindTable OBJECT-TYPE 
        SYNTAX       SEQUENCE OF Zxr10IfCipBindEntry 
        MAX-ACCESS   not-accessible 
        STATUS       current
        DESCRIPTION
            "A list of cip binding entries." 
        ::= { zxr10CipRelation 2 }
  
    zxr10IfCipBindEntry OBJECT-TYPE 
        SYNTAX       Zxr10IfCipBindEntry
        MAX-ACCESS   not-accessible 
        STATUS       current
        DESCRIPTION
            "An entry containing objects for binding interface on a cip
            interface." 
        INDEX { zxr10IfCipBindCipName } 
        ::= { zxr10IfCipBindTable 1 }

    Zxr10IfCipBindEntry ::=  
        SEQUENCE {
            zxr10IfCipBindCipName      DisplayString,
            zxr10IfCipBindPhyName      DisplayString
            }
  
    zxr10IfCipBindCipName OBJECT-TYPE
        SYNTAX        DisplayString(SIZE(1..31))
        MAX-ACCESS    not-accessible 
        STATUS        current
        DESCRIPTION
           "The textual name of the cip interface."
            ::= { zxr10IfCipBindEntry 1 }

    zxr10IfCipBindPhyName OBJECT-TYPE
        SYNTAX        DisplayString(SIZE(1..31))
        MAX-ACCESS    read-create  
        STATUS        current
        DESCRIPTION
           "The textual name of the cip binding interface."
            ::= { zxr10IfCipBindEntry 2 }                       
    --=============================
    --5.1.3 zxr10PortRelationNotifications 
    --=============================
    zxr10PortRelationNotifications 
      OBJECT IDENTIFIER ::= { zxr10PortRelationMIB 3 } 
    --=============================
    --5.1.4 zxr10PortRelationConformance 
    --=============================
    zxr10PortRelationConformance   
      OBJECT IDENTIFIER ::= { zxr10PortRelationMIB 4 } 
  ------------------------------------------  
    --=============================
    --5.2 zxr10IfCommonMIB 
    --=============================
    zxr10IfCommonMIB           
      OBJECT IDENTIFIER ::= { zxr10IfTableMgtObjects 2 } 
    --=============================
    --5.2.1 zxr10IfCommonGlobalObjects 
    --=============================
    zxr10IfCommonGlobalObjects 
      OBJECT IDENTIFIER ::= { zxr10IfCommonMIB 1 }  
    --=============================
    --5.2.2 zxr10IfCommonObjects 
    --=============================
    zxr10IfCommonObjects       
      OBJECT IDENTIFIER ::= { zxr10IfCommonMIB 2 }
    --=============================
    --5.2.2.1 zxr10IfTrigger 
    --=============================
    zxr10IfTrigger                   
      OBJECT IDENTIFIER ::= { zxr10IfCommonObjects 1 } 
    --=============================
    --5.2.2.1.1 zxr10IfTriggerStatGroup 
    --=============================
    zxr10IfTriggerStatGroup          
      OBJECT IDENTIFIER ::= { zxr10IfTrigger 1 } 
    --=============================
    --5.2.2.1.2 zxr10IfTriggerTable 
    --=============================
    zxr10IfTriggerTable  OBJECT-TYPE
        SYNTAX  SEQUENCE OF Zxr10IfTriggerEntry
        MAX-ACCESS  not-accessible
        STATUS  current
        DESCRIPTION
            "Interface trigger table"
        ::= { zxr10IfTrigger 2 }

    zxr10IfTriggerEntry  OBJECT-TYPE
        SYNTAX  Zxr10IfTriggerEntry
        MAX-ACCESS  not-accessible
        STATUS  current
        DESCRIPTION
            "A list of interface trigger entries."
        INDEX  { zxr10IfTriggerIfName }
        ::= { zxr10IfTriggerTable 1 }

    Zxr10IfTriggerEntry ::=
        SEQUENCE {
            zxr10IfTriggerIfName
                DisplayString,  
            zxr10IfTriggerTrackName
                DisplayString,    
            zxr10IfTriggerIfIndex
                Integer32, 
            zxr10IfTriggerTrackTrigger
                INTEGER,
            zxr10IfTriggerIsGrpTrack
                INTEGER,
            zxr10IfTriggerShutDownPeriod
                Integer32    
    }
        
    zxr10IfTriggerIfName  OBJECT-TYPE
        SYNTAX  DisplayString(SIZE(1..31))
        MAX-ACCESS  not-accessible 
        STATUS  current
        DESCRIPTION
            "Interface name"
        ::= { zxr10IfTriggerEntry 1 }  
       
    zxr10IfTriggerTrackName  OBJECT-TYPE
        SYNTAX  DisplayString(SIZE(1..31))
        MAX-ACCESS  read-only 
        STATUS  current
        DESCRIPTION
            "Track name"
        ::= { zxr10IfTriggerEntry 2 } 
        
    zxr10IfTriggerIfIndex  OBJECT-TYPE
        SYNTAX  Integer32
        MAX-ACCESS  read-only 
        STATUS  current
        DESCRIPTION
            "Interface index"
        ::= { zxr10IfTriggerEntry 3 }  
        
    zxr10IfTriggerTrackTrigger  OBJECT-TYPE
        SYNTAX  INTEGER{
                        block(1),      --whether or not to block the interface 
                                       --according to track status
                        shutdown(2),   --whether or not to shutdown the  
                                       --interface according to track status
                        none(3),        --no configuration of track trigger   
                        reverse(4)     --whether or not to make the  
                                       --interface physical down according to track status
                       }                        
        MAX-ACCESS  read-only 
        STATUS  current
        DESCRIPTION
            "Track trigger: 
            block(1)       --whether or not to block the interface according  
                             to track status.
            shutdown(2)    --whether or not to shutdown the interface according 
                             to track status.
            none(3)        --no configuration of track trigger.  
            reverse(4)     ----whether or not to make the  
                           --interface physical down according to track status
            "
        ::= { zxr10IfTriggerEntry 4 }       
        
    zxr10IfTriggerIsGrpTrack  OBJECT-TYPE
        SYNTAX  INTEGER{true(1), false(2)}
        MAX-ACCESS  read-only 
        STATUS  current
        DESCRIPTION
            "Group track flag:
            true(1)  --zxr10IfTriggerTrackName is group track.
            false(2) --zxr10IfTriggerTrackName is not group track. 
            "
        ::= { zxr10IfTriggerEntry 5 }
    
    zxr10IfTriggerShutDownPeriod  OBJECT-TYPE
        SYNTAX  Integer32  
        UNITS    "second"
        MAX-ACCESS  read-only 
        STATUS  current
        DESCRIPTION
            "The time of keeping the port shutdown. "
        ::= { zxr10IfTriggerEntry 6 }
      
                                   
    --=============================
    --5.2.2.3 zxr10IPv6Addr 
    --=============================
    zxr10IPv6Addr                   
      OBJECT IDENTIFIER ::= { zxr10IfCommonObjects 2 } 
    --=============================
    --5.2.2.3.1 zxr10IPv6AddrStatGroup 
    --=============================
    zxr10IPv6AddrStatGroup          
      OBJECT IDENTIFIER ::= { zxr10IPv6Addr 1 } 
    --=============================
    --5.2.2.3.2 zxr10IPv6AddrTable 
    --=============================
    zxr10IPv6AddrTable  OBJECT-TYPE
        SYNTAX  SEQUENCE OF Zxr10IPv6AddrEntry
        MAX-ACCESS  not-accessible
        STATUS  current
        DESCRIPTION
        "Ipv6 address config table."
        ::= { zxr10IPv6Addr 2 }
        
    zxr10IPv6AddrEntry  OBJECT-TYPE
        SYNTAX  Zxr10IPv6AddrEntry
        MAX-ACCESS  not-accessible
        STATUS  current
        DESCRIPTION
        
        ""
        INDEX  {zxr10IPv6Index}
        ::= { zxr10IPv6AddrTable 1 }

    Zxr10IPv6AddrEntry ::=
        SEQUENCE {
            zxr10IPv6Index
                Integer32,
            zxr10IPv6AddrIfName
                DisplayString,
            zxr10IPv6Address
                Ipv6Address,
            zxr10IPv6AddrPrefixLength
                Integer32,
            zxr10IPv6AddrType
                INTEGER
    }      
    
    zxr10IPv6Index  OBJECT-TYPE
        SYNTAX   Integer32
        MAX-ACCESS  not-accessible  
        STATUS  current
        DESCRIPTION
        "Interface Index"
        ::= { zxr10IPv6AddrEntry 1}

    zxr10IPv6AddrIfName    OBJECT-TYPE
        SYNTAX   DisplayString(SIZE(1..31))
        MAX-ACCESS  read-only
        STATUS  current
        DESCRIPTION
        "Interface name"
        ::= { zxr10IPv6AddrEntry 2}
        
    zxr10IPv6Address  OBJECT-TYPE
        SYNTAX  Ipv6Address
        MAX-ACCESS  read-only
        STATUS  current
        DESCRIPTION
        "The ipv6 address on this interface "
        ::= { zxr10IPv6AddrEntry 3 }
    
    zxr10IPv6AddrPrefixLength  OBJECT-TYPE
        SYNTAX   Integer32
        MAX-ACCESS  read-only
        STATUS  current
        DESCRIPTION
        "The length of the ipv6 address prefix" 
        ::= { zxr10IPv6AddrEntry 4 }
    
    zxr10IPv6AddrType    OBJECT-TYPE
        SYNTAX   INTEGER{
                        linklocal(1),  --linklocal address
                        eui64(2),     --eui-64 address
                        anycast(3),    --anycast address
                        unicast(4)    --unicast address
                       }  
        MAX-ACCESS  read-only
        STATUS  current
        DESCRIPTION
        "The type of the ipv6 address:
            linklocal(1)  --linklocal address
            eui-64(2)     --eui-64 address
            anycast(3)    --anycast address
            unicast(4)    --unicast address
         If the result is 0,interface exist and support this node,
         but configuration is empty."
        ::= { zxr10IPv6AddrEntry 5}

    --=============================
    --6 zxr10IfTableMgtNotifications 
    --=============================
    zxr10IfTableMgtNotifications   
      OBJECT IDENTIFIER ::= { zxr10IfTableMgtMIB 6 } 
    --=============================
    --7 zxr10IfTableMgtConformance 
    --=============================
    zxr10IfTableMgtConformance     
      OBJECT IDENTIFIER ::= { zxr10IfTableMgtMIB 7 }
    
 END
