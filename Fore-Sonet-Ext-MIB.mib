-- 
-- Copyright 1999 by Fore Systems, Inc. 
-- Converted to SMIv2 rfc 2578,2579,2580 - STD 58
--
-- Copyright 1999 by Fore Systems, Inc.
-- All Rights Reserved
--
-- This mib implements extensions to the standard SONET
-- mib to support extra configuration and statistics
-- that are supported by Fore Systems

Fore-Sonet-Ext-MIB DEFINITIONS ::= BEGIN

IMPORTS
         Integer32,
	 Counter32,
	 OBJECT-TYPE,
	 NOTIFICATION-TYPE,
	 MODULE-IDENTITY		FROM	SNMPv2-SMI
	 asx		      		FROM	Fore-Common-MIB
	 ifIndex,ifName       		FROM	IF-MIB
	 trapLogIndex			FROM	Fore-TrapLog-MIB
	 sonetSectionIntervalNumber,
	 sonetLineIntervalNumber,
	 sonetFarEndLineIntervalNumber,
	 sonetPathIntervalNumber,
	 sonetFarEndPathIntervalNumber,
	 sonetVTIntervalNumber,
	 sonetFarEndVTIntervalNumber	FROM    SONET-MIB;

foreSonetMib  MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
	      This mib implements extensions to the standard SONET
	      mib to support extra configuration and statistics
	      that are supported by Fore Systems."
    ::= { asx 14 }

foreSonetMedium   	OBJECT IDENTIFIER ::= { foreSonetMib 1 }

foreSonetSection  	OBJECT IDENTIFIER ::= { foreSonetMib 2 }

foreSonetLine     	OBJECT IDENTIFIER ::= { foreSonetMib 3 }

foreSonetPath     	OBJECT IDENTIFIER ::= { foreSonetMib 4 }

foreSonetVT       	OBJECT IDENTIFIER ::= { foreSonetMib 5 }

foreSonetSPE      	OBJECT IDENTIFIER ::= { foreSonetMib 6 }

foreSonetFarEndLine     OBJECT IDENTIFIER ::= { foreSonetMib 7 }

foreSonetFarEndPath     OBJECT IDENTIFIER ::= { foreSonetMib 8 }

foreSonetFarEndVT       OBJECT IDENTIFIER ::= { foreSonetMib 9 }

-- Sonet Medium Tables

foreSonetMediumConfigTable OBJECT-TYPE
	SYNTAX SEQUENCE OF ForeSonetMediumConfigEntry
	MAX-ACCESS	not-accessible
	STATUS	current
	DESCRIPTION
		"A table of configuration options and statistics that
		 extend the Sonet Medium Group in the Standard SONET MIB."
	::= { foreSonetMedium 1 }

foreSonetMediumConfigEntry OBJECT-TYPE
	SYNTAX ForeSonetMediumConfigEntry
	MAX-ACCESS not-accessible
	STATUS current
	DESCRIPTION
		"A table entry containing Fore specific extensions to
		 the standard SONET Medium Group Tables."
	INDEX { ifIndex }
	::= { foreSonetMediumConfigTable 1 }

ForeSonetMediumConfigEntry ::=
	SEQUENCE {
		foreSonetMediumConfigLoopbackMode	INTEGER,
		foreSonetMediumConfigTxClockSource	INTEGER
	}

foreSonetMediumConfigLoopbackMode OBJECT-TYPE
	SYNTAX	INTEGER {
		sonetNoLoop(1), 
		sonetLineLoop(2),
		sonetDiagLoop(3),
		sonetOtherLoop(4)
		}
	MAX-ACCESS	read-write
	STATUS	current
	DESCRIPTION
		"This variable represents the current loopback status of the 
		SONET interface.
		The possible values are: 
		sonetNoLoop (1) means that the interface is not in a loopback 
		state.
		sonetLineLoop (2) means that the receive data and clock are 
		connected to the transmit data and clock.
		sonetDiagLoop (3) means that the transmit data stream and clock
		are looped back to the receiver.
		sonetOtherLoop (4) means that the interface is in a loopback 
		that is not defined here."
	DEFVAL { sonetNoLoop }
	::= { foreSonetMediumConfigEntry 1 }

foreSonetMediumConfigTxClockSource OBJECT-TYPE
	SYNTAX	INTEGER {
		rxTiming(1), 
		localTiming(2)
		}
	MAX-ACCESS	read-write
	STATUS	current
	DESCRIPTION
		"The source of the transmit clock."
	DEFVAL { localTiming }
	::= { foreSonetMediumConfigEntry 2 }


-- foreSonetMediumTotalTable OBJECT-TYPE
--	SYNTAX SEQUENCE OF ForeSonetMediumTotalEntry
--	MAX-ACCESS	not-accessible
--	STATUS	current
--	DESCRIPTION
--		"A table of configuration options and statistics that
--		 extend the Sonet Medium Group in the Standard SONET MIB."
--	::= { foreSonetMedium 2 }

--foreSonetMediumTotalEntry OBJECT-TYPE
--	SYNTAX ForeSonetMediumTotalEntry
--	MAX-ACCESS not-accessible
--	STATUS current
--	DESCRIPTION
--		"A table entry containing Fore specific extensions to
--		 the standard SONET Medium Group Tables."
--	INDEX { ifIndex }
--	::= { foreSonetMediumTotalTable 1 }

--ForeSonetMediumTotalEntry ::=
--	SEQUENCE {
--	}

-- foreSonetMediumDiagnosticsTable OBJECT-TYPE
--	SYNTAX SEQUENCE OF ForeSonetMediumDiagnosticsEntry
--	MAX-ACCESS	not-accessible
--	STATUS	current
--	DESCRIPTION
--		"A table of configuration options and statistics that
--		 extend the Sonet Medium Group in the Standard SONET MIB."
--	::= { foreSonetMedium 3 }

--foreSonetMediumDiagnosticsEntry OBJECT-TYPE
--	SYNTAX ForeSonetMediumDiagnosticsEntry
--	MAX-ACCESS not-accessible
--	STATUS current
--	DESCRIPTION
--		"A table entry containing Fore specific extensions to
--		 the standard SONET Medium Group Tables."
--	INDEX { ifIndex }
--	::= { foreSonetMediumDiagnosticsTable 1 }

--ForeSonetMediumDiagnosticsEntry ::=
--	SEQUENCE {
--	}

-- Extensions to the Sonet Section Level

-- foreSonetSectionConfigTable OBJECT-TYPE
--	SYNTAX SEQUENCE OF ForeSonetSectionEntry
--	MAX-ACCESS	not-accessible
--	STATUS		current
--	DESCRIPTION
--		"A table of configuration options and statistics
--		 that extend the standard Sonet Section Tables."
--	::= { foreSonetSection 1 }

--foreSonetSectionConfigEntry OBJECT-TYPE
--	SYNTAX ForeSonetSectionConfigEntry
--	MAX-ACCESS	not-accessible
--	STATUS		current
--	DESCRIPTION
--		"A table entry containing Fore specific extensions
--		 to the standard SONET section table."
--	INDEX { ifIndex }
--	::= { foreSonetSectionConfigTable 1 }
--
--ForeSonetSectionConfigEntry ::=
--	SEQUENCE {
--	}

foreSonetSectionTotalTable OBJECT-TYPE
	SYNTAX SEQUENCE OF ForeSonetSectionTotalEntry
	MAX-ACCESS	not-accessible
	STATUS		current
	DESCRIPTION
		"A table of configuration options and statistics
		 that extend the standard Sonet section tables."
	::= { foreSonetSection 2 }

foreSonetSectionTotalEntry OBJECT-TYPE
	SYNTAX ForeSonetSectionTotalEntry
	MAX-ACCESS	not-accessible
	STATUS		current
	DESCRIPTION
		"A table entry containing Fore specific extensions
		 to the standard SONET section table statistics."
	INDEX { ifIndex }
	::= { foreSonetSectionTotalTable 1 }

ForeSonetSectionTotalEntry ::=
	SEQUENCE {
		foreSonetSectionTotalBIPs		Counter32,
		foreSonetSectionTotalLOSs		Counter32,
		foreSonetSectionTotalLOFs		Counter32
	}

foreSonetSectionTotalBIPs OBJECT-TYPE
	SYNTAX	Counter32
	MAX-ACCESS	read-only
	STATUS	current
	DESCRIPTION
		"The number of Section BIP-8 (Bit Interleaved Parity) errors that have been 
		detected since the last time the port has been reset. The calculated BIP-8 
		code is compared with the BIP-8 code extracted from the B1 byte of the 
		following frame. Differences indicate that a section level bit error has 
		occurred."
	::= { foreSonetSectionTotalEntry 1 }

foreSonetSectionTotalLOSs OBJECT-TYPE
	SYNTAX	Counter32
	MAX-ACCESS	read-only
	STATUS	current
	DESCRIPTION
		"The number of seconds in which Loss Of Signal (LOS) has occurred. A LOS 
		is declared when 20 +/- 3us of all zeros patterns is detected. LOS is cleared 
		when two valid framing words are detected and during the intervening time no 
		LOS condition is detected."
	::= { foreSonetSectionTotalEntry 2 }

foreSonetSectionTotalLOFs OBJECT-TYPE
	SYNTAX	Counter32
	MAX-ACCESS	read-only
	STATUS	current
	DESCRIPTION
		"The number of seconds in which Loss Of Frame (LOF) has occurred. A LOF 
		is declared when an out-of-frame (OOF) condition persists for 3ms. The LOF 
		is cleared when an in-frame condition persists for 3ms. While in-frame the 
		framing bytes (A1, A2) in each frame are compared against the expected 
		pattern. Out-of-frame is declared when four consecutive frames containing 
		one or more framing pattern errors have been received."
	::= { foreSonetSectionTotalEntry 3 }


foreSonetSectionDiagnosticsTable OBJECT-TYPE
	SYNTAX SEQUENCE OF ForeSonetSectionDiagnosticsEntry
	MAX-ACCESS	not-accessible
	STATUS		current
	DESCRIPTION
		"A table of configuration options and statistics
		 that extend the standard Sonet Section tables."
	::= { foreSonetSection 3 }


foreSonetSectionDiagnosticsEntry OBJECT-TYPE
 	SYNTAX ForeSonetSectionDiagnosticsEntry
 	MAX-ACCESS	not-accessible
 	STATUS		current
 	DESCRIPTION
 		"A table entry containing Fore specific extensions
 		 to the standard SONET Section tables."
 	INDEX { ifIndex }
 	::= { foreSonetSectionDiagnosticsTable 1 }
 
ForeSonetSectionDiagnosticsEntry ::=
 	SEQUENCE {
 		foreSonetSectionDiagnosticsFraming		 INTEGER,
		foreSonetSectionDiagnosticsB1			 INTEGER,
		foreSonetSectionDiagnosticsDisableTxScrambling	 INTEGER,
		foreSonetSectionDiagnosticsDisableRxDescrambling INTEGER,
		foreSonetSectionDiagnosticsLOS			 INTEGER
 	}

foreSonetSectionDiagnosticsFraming OBJECT-TYPE
 	SYNTAX	INTEGER {
		on(1),
		off(2),
		momentary(3)
		}
 	MAX-ACCESS	read-write
 	STATUS	current
 	DESCRIPTION
		"Controls the insertion of framing (A1 A2 byte) errors. 

		off 	   When set to off, transmit Sonet frames 
			   continously with no A1A2 errors (framing errors).
		on 	   When set to on, transmit Sonet frames 
			   continously with bad A1A2 values.
		momentary  When set to momentary, transmit a chip dependent 
			   number of Sonet frames with A1A2 errors."
	DEFVAL { off }	
 	::= { foreSonetSectionDiagnosticsEntry 1 }


foreSonetSectionDiagnosticsB1 OBJECT-TYPE
 	SYNTAX	INTEGER {
		on(1),
		off(2),
		momentary(3)
		}
 	MAX-ACCESS	read-write
 	STATUS	current
 	DESCRIPTION
		"Controls the insertion of BIP errors in the sonet section 
		 B1 byte overhead. 
		off		When set to off, do not generate section
				BIP errors. 
		on		When set to on, generate section BIP errors. 
		momentary	When set to momentary, transmit a chip dependent
				number of Sonet frames with section BIP errors."
	DEFVAL { off }
 	::= { foreSonetSectionDiagnosticsEntry 2 }


foreSonetSectionDiagnosticsDisableTxScrambling OBJECT-TYPE
 	SYNTAX	INTEGER {
		on(1),
		off(2)
		}
 	MAX-ACCESS	read-write
 	STATUS	current
 	DESCRIPTION
		"Controls the scrambling of sonet overhead and SPE of the
		 transmitted Sonet frame.  

		off	When set to off, transmitted Sonet frames are
			scrambled.
		on	When set to on, transmitted Sonet frames are NOT
			scrambled."
	DEFVAL { off }
 	::= { foreSonetSectionDiagnosticsEntry 3 }


foreSonetSectionDiagnosticsDisableRxDescrambling OBJECT-TYPE
 	SYNTAX	INTEGER {
		on(1),
		off(2)
		}
 	MAX-ACCESS	read-write
 	STATUS	current
 	DESCRIPTION
		"Controls the descrambling of sonet overhead and SPE of the
		 received Sonet frame. 

		off	When set to off, received Sonet frames are 
			descrambled.
		on	When set to on, received Sonet frames are NOT 
			descrambled."
	DEFVAL { off }
 	::= { foreSonetSectionDiagnosticsEntry 4 }


foreSonetSectionDiagnosticsLOS OBJECT-TYPE
 	SYNTAX	INTEGER {
		on(1),
		off(2)
		}
 	MAX-ACCESS	read-write
 	STATUS	current
 	DESCRIPTION
		"Controls the insertion of Loss of Signal (LOS) errors in 
		 the transmitted Sonet frame. 

		off	When set to off, do not generate LOS errors.
		on	When set to on, generate LOS errors."

	DEFVAL { off }
 	::= { foreSonetSectionDiagnosticsEntry 5 }

-- Fore extensions to the standard SONET Section Current table
foreSonetSectionCurrentTable OBJECT-TYPE
	SYNTAX SEQUENCE OF ForeSonetSectionCurrentEntry
	MAX-ACCESS  not-accessible
        STATUS current
        DESCRIPTION
                 "The Fore's extension to SONET/SDH Section Current table."
               ::= { foreSonetSection 4 }

foreSonetSectionCurrentEntry OBJECT-TYPE
        SYNTAX  ForeSonetSectionCurrentEntry
        MAX-ACCESS  not-accessible
        STATUS current
        DESCRIPTION
                 "An entry in the SONET/SDH Section Current table."
	INDEX   { ifIndex }
               ::= { foreSonetSectionCurrentTable 1 }

          ForeSonetSectionCurrentEntry ::=
              SEQUENCE {
                  foreSonetSectionCurrentBBEs     Integer32
              }

foreSonetSectionCurrentBBEs OBJECT-TYPE
        SYNTAX  Integer32
        MAX-ACCESS  read-only
        STATUS current
        DESCRIPTION
                "The counter associated with the number of Background
                 Errors encountered by a
                 SONET/SDH Section in the current 15 minute interval."
               ::= { foreSonetSectionCurrentEntry 1 }

-- Fore extensions to the standard SONET Section Interval table
foreSonetSectionIntervalTable OBJECT-TYPE
	SYNTAX SEQUENCE OF ForeSonetSectionIntervalEntry
	MAX-ACCESS  not-accessible
        STATUS current
        DESCRIPTION
                 "The Fore's extension to SONET/SDH Section Interval table."
               ::= { foreSonetSection 5 }

foreSonetSectionIntervalEntry OBJECT-TYPE
        SYNTAX  ForeSonetSectionIntervalEntry
        MAX-ACCESS  not-accessible
        STATUS current
        DESCRIPTION
                 "An entry in the SONET/SDH Section Interval table."
	INDEX   { ifIndex, 
		  sonetSectionIntervalNumber }
               ::= { foreSonetSectionIntervalTable 1 }

          ForeSonetSectionIntervalEntry ::=
              SEQUENCE {
                  foreSonetSectionIntervalBBEs     Integer32,
                  foreSonetSectionIntervalESR      Integer32,
                  foreSonetSectionIntervalSESR     Integer32,
                  foreSonetSectionIntervalBBER     Integer32
              }

foreSonetSectionIntervalBBEs OBJECT-TYPE
        SYNTAX  Integer32 
        MAX-ACCESS  read-only
        STATUS current
        DESCRIPTION
                "The counter associated with the number of Background
                 Errors encountered by a
                 SONET/SDH Section in  a particular
                 15-minute interval in the past 24 hours."
               ::= { foreSonetSectionIntervalEntry 1 }

foreSonetSectionIntervalESR OBJECT-TYPE
        SYNTAX  Integer32
        MAX-ACCESS  read-only
        STATUS current
        DESCRIPTION
                 "The ratio of Errored seconds encountered by a
                 SONET/SDH Section to time in a particular
                 15-minute interval in the past 24 hours."
              ::= { foreSonetSectionIntervalEntry 2 }

foreSonetSectionIntervalSESR OBJECT-TYPE
        SYNTAX  Integer32
        MAX-ACCESS  read-only
        STATUS current
        DESCRIPTION
                 "The ratio of Sev Errored seconds encountered by a
                 SONET/SDH Section to time in a particular
                 15-minute interval in the past 24 hours."
              ::= { foreSonetSectionIntervalEntry 3 }

foreSonetSectionIntervalBBER OBJECT-TYPE
        SYNTAX  Integer32
        MAX-ACCESS  read-only
        STATUS current
        DESCRIPTION
                 "The ratio of Background blk errors encountered by a
                 SONET/SDH Section to time in a particular
                 15-minute interval in the past 24 hours."
              ::= { foreSonetSectionIntervalEntry 4 }

-- Fore extensions to the standard SONET Line Current table
foreSonetLineCurrentTable OBJECT-TYPE
	SYNTAX SEQUENCE OF ForeSonetLineCurrentEntry
	MAX-ACCESS  not-accessible
        STATUS current
        DESCRIPTION
                 "The Fore's extension to SONET/SDH Line Current table."
               ::= { foreSonetLine 4 }

foreSonetLineCurrentEntry OBJECT-TYPE
        SYNTAX  ForeSonetLineCurrentEntry
        MAX-ACCESS  not-accessible
        STATUS current
        DESCRIPTION
                 "An entry in the SONET/SDH Line Current table."
	INDEX   { ifIndex }
               ::= { foreSonetLineCurrentTable 1 }

          ForeSonetLineCurrentEntry ::=
              SEQUENCE {
                  foreSonetLineCurrentBBEs     Integer32
              }

foreSonetLineCurrentBBEs OBJECT-TYPE
        SYNTAX  Integer32
        MAX-ACCESS  read-only
        STATUS current
        DESCRIPTION
                "The counter associated with the number of Background
                 Errors encountered by a
                 SONET/SDH Line in the current 15 minute interval."
               ::= { foreSonetLineCurrentEntry 1 }

-- Fore extensions to the standard SONET Line Interval table
foreSonetLineIntervalTable OBJECT-TYPE
        SYNTAX SEQUENCE OF ForeSonetLineIntervalEntry
        MAX-ACCESS  not-accessible
        STATUS current
        DESCRIPTION
                 "The Fore's extension to SONET/SDH Line Interval table."
               ::= { foreSonetLine 5 }

foreSonetLineIntervalEntry OBJECT-TYPE
        SYNTAX  ForeSonetLineIntervalEntry
        MAX-ACCESS  not-accessible
        STATUS current
        DESCRIPTION
                 "An entry in the SONET/SDH Line Interval table."
        INDEX   { ifIndex,
                  sonetLineIntervalNumber }
               ::= { foreSonetLineIntervalTable 1 }

          ForeSonetLineIntervalEntry ::=
              SEQUENCE {
                  foreSonetLineIntervalBBEs     Integer32,
                  foreSonetLineIntervalESR      Integer32,
                  foreSonetLineIntervalSESR     Integer32,
                  foreSonetLineIntervalBBER     Integer32
              }

foreSonetLineIntervalBBEs OBJECT-TYPE
        SYNTAX  Integer32
        MAX-ACCESS  read-only
        STATUS current
        DESCRIPTION
                "The counter associated with the number of Background
                 Errors encountered by a
                 SONET/SDH Line in  a particular
                 15-minute interval in the past 24 hours."
               ::= { foreSonetLineIntervalEntry 1 }

foreSonetLineIntervalESR OBJECT-TYPE
        SYNTAX  Integer32
        MAX-ACCESS  read-only
        STATUS current
        DESCRIPTION
                 "The ratio of Errored seconds encountered by a
                 SONET/SDH Line to time in a particular
                 15-minute interval in the past 24 hours."
              ::= { foreSonetLineIntervalEntry 2 }

foreSonetLineIntervalSESR OBJECT-TYPE
        SYNTAX  Integer32
        MAX-ACCESS  read-only
        STATUS current
        DESCRIPTION
                 "The ratio of Sev Errored seconds encountered by a
                 SONET/SDH Line to time in a particular
                 15-minute interval in the past 24 hours."
              ::= { foreSonetLineIntervalEntry 3 }

foreSonetLineIntervalBBER OBJECT-TYPE
        SYNTAX  Integer32
        MAX-ACCESS  read-only
        STATUS current
        DESCRIPTION
                 "The ratio of Background blk errors encountered by a
                 SONET/SDH Line to time in a particular
                 15-minute interval in the past 24 hours."
              ::= { foreSonetLineIntervalEntry 4 }

-- Fore extensions to the standard SONET Far End Line Current table
foreSonetFarEndLineCurrentTable OBJECT-TYPE
	SYNTAX SEQUENCE OF ForeSonetFarEndLineCurrentEntry
	MAX-ACCESS  not-accessible
        STATUS current
        DESCRIPTION
                 "The Fore's extension to SONET/SDH Farend Line Current table."
               ::= { foreSonetFarEndLine 1 }

foreSonetFarEndLineCurrentEntry OBJECT-TYPE
        SYNTAX  ForeSonetFarEndLineCurrentEntry
        MAX-ACCESS  not-accessible
        STATUS current
        DESCRIPTION
                 "An entry in the SONET/SDH FarEnd Line Current table."
	INDEX   { ifIndex }
               ::= { foreSonetFarEndLineCurrentTable 1 }

          ForeSonetFarEndLineCurrentEntry ::=
              SEQUENCE {
                  foreSonetFarEndLineCurrentBBEs     Integer32
              }

foreSonetFarEndLineCurrentBBEs OBJECT-TYPE
        SYNTAX  Integer32
        MAX-ACCESS  read-only
        STATUS current
        DESCRIPTION
                "The counter associated with the number of Background
                 Errors encountered by a
                 SONET/SDH FarEnd Line in the current 15 minute interval."
               ::= { foreSonetFarEndLineCurrentEntry 1 }

-- Fore extensions to the standard SONET FarEnd Line Interval table
foreSonetFarEndLineIntervalTable OBJECT-TYPE
        SYNTAX SEQUENCE OF ForeSonetFarEndLineIntervalEntry
        MAX-ACCESS  not-accessible
        STATUS current
        DESCRIPTION
                 "The Fore's extension to SONET/SDH FarEndLine Interval table."
               ::= { foreSonetFarEndLine 2 }

foreSonetFarEndLineIntervalEntry OBJECT-TYPE
        SYNTAX  ForeSonetFarEndLineIntervalEntry
        MAX-ACCESS  not-accessible
        STATUS current
        DESCRIPTION
                 "An entry in the SONET/SDH FarEndLine Interval table."
        INDEX   { ifIndex,
                  sonetFarEndLineIntervalNumber }
               ::= { foreSonetFarEndLineIntervalTable 1 }

          ForeSonetFarEndLineIntervalEntry ::=
              SEQUENCE {
                  foreSonetFarEndLineIntervalBBEs     Integer32,
                  foreSonetFarEndLineIntervalESR      Integer32,
                  foreSonetFarEndLineIntervalSESR     Integer32,
                  foreSonetFarEndLineIntervalBBER     Integer32
              }

foreSonetFarEndLineIntervalBBEs OBJECT-TYPE
        SYNTAX  Integer32
        MAX-ACCESS  read-only
        STATUS current
        DESCRIPTION
                "The counter associated with the number of Background
                 Errors encountered by a
                 SONET/SDH FarEndLine in  a particular
                 15-minute interval in the past 24 hours."
               ::= { foreSonetFarEndLineIntervalEntry 1 }

foreSonetFarEndLineIntervalESR OBJECT-TYPE
        SYNTAX  Integer32
        MAX-ACCESS  read-only
        STATUS current
        DESCRIPTION
                 "The ratio of Errored seconds encountered by a
                 SONET/SDH FarEndLine to time in a particular
                 15-minute interval in the past 24 hours."
              ::= { foreSonetFarEndLineIntervalEntry 2 }

foreSonetFarEndLineIntervalSESR OBJECT-TYPE
        SYNTAX  Integer32
        MAX-ACCESS  read-only
        STATUS current
        DESCRIPTION
                 "The ratio of Sev Errored seconds encountered by a
                 SONET/SDH FarEndLine to time in a particular
                 15-minute interval in the past 24 hours."
              ::= { foreSonetFarEndLineIntervalEntry 3 }

foreSonetFarEndLineIntervalBBER OBJECT-TYPE
        SYNTAX  Integer32
        MAX-ACCESS  read-only
        STATUS current
        DESCRIPTION
                 "The ratio of Background blk errors encountered by a
                 SONET/SDH FarEndLine to time in a particular
                 15-minute interval in the past 24 hours."
              ::= { foreSonetFarEndLineIntervalEntry 4 }

-- Fore extensions to the standard SONET Path Interval table
foreSonetPathIntervalTable OBJECT-TYPE
        SYNTAX SEQUENCE OF ForeSonetPathIntervalEntry
        MAX-ACCESS  not-accessible
        STATUS current
        DESCRIPTION
                 "The Fore's extension to SONET/SDH Path Interval table."
               ::= { foreSonetPath 6 }

foreSonetPathIntervalEntry OBJECT-TYPE
        SYNTAX  ForeSonetPathIntervalEntry
        MAX-ACCESS  not-accessible
        STATUS current
        DESCRIPTION
                 "An entry in the SONET/SDH Path Interval table."
        INDEX   { ifIndex,
                  sonetPathIntervalNumber }
               ::= { foreSonetPathIntervalTable 1 }

          ForeSonetPathIntervalEntry ::=
              SEQUENCE {
                  foreSonetPathIntervalBBEs     Integer32,
                  foreSonetPathIntervalESR      Integer32,
                  foreSonetPathIntervalSESR     Integer32,
                  foreSonetPathIntervalBBER     Integer32
              }

foreSonetPathIntervalBBEs OBJECT-TYPE
        SYNTAX  Integer32
        MAX-ACCESS  read-only
        STATUS current
        DESCRIPTION
                "The counter associated with the number of Background
                 Errors encountered by a
                 SONET/SDH Path in  a particular
                 15-minute interval in the past 24 hours."
               ::= { foreSonetPathIntervalEntry 1 }

foreSonetPathIntervalESR OBJECT-TYPE
        SYNTAX  Integer32
        MAX-ACCESS  read-only
        STATUS current
        DESCRIPTION
                 "The ratio of Errored seconds encountered by a
                 SONET/SDH Path to time in a particular
                 15-minute interval in the past 24 hours."
              ::= { foreSonetPathIntervalEntry 2 }

foreSonetPathIntervalSESR OBJECT-TYPE
        SYNTAX  Integer32
        MAX-ACCESS  read-only
        STATUS current
        DESCRIPTION
                 "The ratio of Sev Errored seconds encountered by a
                 SONET/SDH Path to time in a particular
                 15-minute interval in the past 24 hours."
              ::= { foreSonetPathIntervalEntry 3 }

foreSonetPathIntervalBBER OBJECT-TYPE
        SYNTAX  Integer32
        MAX-ACCESS  read-only
        STATUS current
        DESCRIPTION
                 "The ratio of Background blk errors encountered by a
                 SONET/SDH Path to time in a particular
                 15-minute interval in the past 24 hours."
              ::= { foreSonetPathIntervalEntry 4 }


-- Fore extensions to the standard SONET Far End Path Current table
foreSonetFarEndPathCurrentTable OBJECT-TYPE
	SYNTAX SEQUENCE OF ForeSonetFarEndPathCurrentEntry
	MAX-ACCESS  not-accessible
        STATUS current
        DESCRIPTION
                 "The Fore's extension to SONET/SDH FarEnd Path Current table."
               ::= { foreSonetFarEndPath 1 }

foreSonetFarEndPathCurrentEntry OBJECT-TYPE
        SYNTAX  ForeSonetFarEndPathCurrentEntry
        MAX-ACCESS  not-accessible
        STATUS current
        DESCRIPTION
                 "An entry in the SONET/SDH FarEnd Path Current table."
	INDEX   { ifIndex }
               ::= { foreSonetFarEndPathCurrentTable 1 }

          ForeSonetFarEndPathCurrentEntry ::=
              SEQUENCE {
                  foreSonetFarEndPathCurrentBBEs     Integer32
              }

foreSonetFarEndPathCurrentBBEs OBJECT-TYPE
        SYNTAX  Integer32
        MAX-ACCESS  read-only
        STATUS current
        DESCRIPTION
                "The counter associated with the number of Background
                 Errors encountered by a
                 SONET/SDH FarEnd Path in the current 15 minute interval."
               ::= { foreSonetFarEndPathCurrentEntry 1 }

-- Fore extensions to the standard SONET FarEndPath Interval table
foreSonetFarEndPathIntervalTable OBJECT-TYPE
        SYNTAX SEQUENCE OF ForeSonetFarEndPathIntervalEntry
        MAX-ACCESS  not-accessible
        STATUS current
        DESCRIPTION
                 "The Fore's extension to SONET/SDH FarEndPath Interval table."
               ::= { foreSonetFarEndPath 2 }

foreSonetFarEndPathIntervalEntry OBJECT-TYPE
        SYNTAX  ForeSonetFarEndPathIntervalEntry
        MAX-ACCESS  not-accessible
        STATUS current
        DESCRIPTION
                 "An entry in the SONET/SDH FarEndPath Interval table."
        INDEX   { ifIndex,
                  sonetFarEndPathIntervalNumber }
               ::= { foreSonetFarEndPathIntervalTable 1 }

          ForeSonetFarEndPathIntervalEntry ::=
              SEQUENCE {
                  foreSonetFarEndPathIntervalBBEs     Integer32,
                  foreSonetFarEndPathIntervalESR      Integer32,
                  foreSonetFarEndPathIntervalSESR     Integer32,
                  foreSonetFarEndPathIntervalBBER     Integer32
              }

foreSonetFarEndPathIntervalBBEs OBJECT-TYPE
        SYNTAX  Integer32
        MAX-ACCESS  read-only
        STATUS current
        DESCRIPTION
                "The counter associated with the number of Background
                 Errors encountered by a
                 SONET/SDH FarEndPath in  a particular
                 15-minute interval in the past 24 hours."
               ::= { foreSonetFarEndPathIntervalEntry 1 }

foreSonetFarEndPathIntervalESR OBJECT-TYPE
        SYNTAX  Integer32
        MAX-ACCESS  read-only
        STATUS current
        DESCRIPTION
                 "The ratio of Errored seconds encountered by a
                 SONET/SDH FarEndPath to time in a particular
                 15-minute interval in the past 24 hours."
              ::= { foreSonetFarEndPathIntervalEntry 2 }

foreSonetFarEndPathIntervalSESR OBJECT-TYPE
        SYNTAX  Integer32
        MAX-ACCESS  read-only
        STATUS current
        DESCRIPTION
                 "The ratio of Sev Errored seconds encountered by a
                 SONET/SDH FarEndPath to time in a particular
                 15-minute interval in the past 24 hours."
              ::= { foreSonetFarEndPathIntervalEntry 3 }

foreSonetFarEndPathIntervalBBER OBJECT-TYPE
        SYNTAX  Integer32
        MAX-ACCESS  read-only
        STATUS current
        DESCRIPTION
                 "The ratio of Background blk errors encountered by a
                 SONET/SDH FarEndPath to time in a particular
                 15-minute interval in the past 24 hours."
              ::= { foreSonetFarEndPathIntervalEntry 4 }

-- Fore extensions to the standard SONET VT Current table
foreSonetVTCurrentTable OBJECT-TYPE
	SYNTAX SEQUENCE OF ForeSonetVTCurrentEntry
	MAX-ACCESS  not-accessible
        STATUS current
        DESCRIPTION
                 "The Fore's extension to SONET/SDH VT Current table."
               ::= { foreSonetVT 4 }

foreSonetVTCurrentEntry OBJECT-TYPE
        SYNTAX  ForeSonetVTCurrentEntry
        MAX-ACCESS  not-accessible
        STATUS current
        DESCRIPTION
                 "An entry in the SONET/SDH VT Current table."
	INDEX   { ifIndex }
               ::= { foreSonetVTCurrentTable 1 }

          ForeSonetVTCurrentEntry ::=
              SEQUENCE {
                  foreSonetVTCurrentBBEs     Integer32
              }

foreSonetVTCurrentBBEs OBJECT-TYPE
        SYNTAX  Integer32
        MAX-ACCESS  read-only
        STATUS current
        DESCRIPTION
                "The counter associated with the number of Background
                 Errors encountered by a
                 SONET/SDH VT in the current 15 minute interval."
               ::= { foreSonetVTCurrentEntry 1 }

-- Fore extensions to the standard SONET VT Interval table
foreSonetVTIntervalTable OBJECT-TYPE
        SYNTAX SEQUENCE OF ForeSonetVTIntervalEntry
        MAX-ACCESS  not-accessible
        STATUS current
        DESCRIPTION
                 "The Fore's extension to SONET/SDH VT Interval table."
               ::= { foreSonetVT 5 }

foreSonetVTIntervalEntry OBJECT-TYPE
        SYNTAX  ForeSonetVTIntervalEntry
        MAX-ACCESS  not-accessible
        STATUS current
        DESCRIPTION
                 "An entry in the SONET/SDH VT Interval table."
        INDEX   { ifIndex,
                  sonetVTIntervalNumber }
               ::= { foreSonetVTIntervalTable 1 }

          ForeSonetVTIntervalEntry ::=
              SEQUENCE {
                  foreSonetVTIntervalBBEs     Integer32,
                  foreSonetVTIntervalESR      Integer32,
                  foreSonetVTIntervalSESR     Integer32,
                  foreSonetVTIntervalBBER     Integer32
              }

foreSonetVTIntervalBBEs OBJECT-TYPE
        SYNTAX  Integer32
        MAX-ACCESS  read-only
        STATUS current
        DESCRIPTION
                "The counter associated with the number of Background
                 Errors encountered by a
                 SONET/SDH VT in  a particular
                 15-minute interval in the past 24 hours."
               ::= { foreSonetVTIntervalEntry 1 }

foreSonetVTIntervalESR OBJECT-TYPE
        SYNTAX  Integer32
        MAX-ACCESS  read-only
        STATUS current
        DESCRIPTION
                 "The ratio of Errored seconds encountered by a
                 SONET/SDH Section to time in a particular
                 15-minute interval in the past 24 hours."
              ::= { foreSonetVTIntervalEntry 2 }

foreSonetVTIntervalSESR OBJECT-TYPE
        SYNTAX  Integer32
        MAX-ACCESS  read-only
        STATUS current
        DESCRIPTION
                 "The ratio of Sev Errored seconds encountered by a
                 SONET/SDH Section to time in a particular
                 15-minute interval in the past 24 hours."
              ::= { foreSonetVTIntervalEntry 3 }

foreSonetVTIntervalBBER OBJECT-TYPE
        SYNTAX  Integer32
        MAX-ACCESS  read-only
        STATUS current
        DESCRIPTION
                 "The ratio of Background blk errors encountered by a
                 SONET/SDH Section to time in a particular
                 15-minute interval in the past 24 hours."
              ::= { foreSonetVTIntervalEntry 4 }


-- Fore extensions to the standard SONET Far End VT Current table
foreSonetFarEndVTCurrentTable OBJECT-TYPE
	SYNTAX SEQUENCE OF ForeSonetFarEndVTCurrentEntry
	MAX-ACCESS  not-accessible
        STATUS current
        DESCRIPTION
                 "The Fore's extension to SONET/SDH Farend VT Current table."
               ::= { foreSonetFarEndVT 1 }

foreSonetFarEndVTCurrentEntry OBJECT-TYPE
        SYNTAX  ForeSonetFarEndVTCurrentEntry
        MAX-ACCESS  not-accessible
        STATUS current
        DESCRIPTION
                 "An entry in the SONET/SDH FarEnd VT Current table."
	INDEX   { ifIndex }
               ::= { foreSonetFarEndVTCurrentTable 1 }

          ForeSonetFarEndVTCurrentEntry ::=
              SEQUENCE {
                  foreSonetFarEndVTCurrentBBEs     Integer32
              }

foreSonetFarEndVTCurrentBBEs OBJECT-TYPE
        SYNTAX  Integer32
        MAX-ACCESS  read-only
        STATUS current
        DESCRIPTION
                "The counter associated with the number of Background
                 Errors encountered by a
                 SONET/SDH FarEnd VT in the current 15 minute interval."
               ::= { foreSonetFarEndVTCurrentEntry 1 }

-- Fore extensions to the standard SONET FarEndVT Interval table
foreSonetFarEndVTIntervalTable OBJECT-TYPE
        SYNTAX SEQUENCE OF ForeSonetFarEndVTIntervalEntry
        MAX-ACCESS  not-accessible
        STATUS current
        DESCRIPTION
                 "The Fore's extension to SONET/SDH FarEndVT Interval table."
               ::= { foreSonetFarEndVT 2 }

foreSonetFarEndVTIntervalEntry OBJECT-TYPE
        SYNTAX  ForeSonetFarEndVTIntervalEntry
        MAX-ACCESS  not-accessible
        STATUS current
        DESCRIPTION
                 "An entry in the SONET/SDH FarEndVT Interval table."
        INDEX   { ifIndex,
                  sonetFarEndVTIntervalNumber }
               ::= { foreSonetFarEndVTIntervalTable 1 }

          ForeSonetFarEndVTIntervalEntry ::=
              SEQUENCE {
                  foreSonetFarEndVTIntervalBBEs     Integer32,
                  foreSonetFarEndVTIntervalESR      Integer32,
                  foreSonetFarEndVTIntervalSESR     Integer32,
                  foreSonetFarEndVTIntervalBBER     Integer32
              }

foreSonetFarEndVTIntervalBBEs OBJECT-TYPE
        SYNTAX  Integer32
        MAX-ACCESS  read-only
        STATUS current
        DESCRIPTION
                "The counter associated with the number of Background
                 Errors encountered by a
                 SONET/SDH FarEndVT in  a particular
                 15-minute interval in the past 24 hours."
               ::= { foreSonetFarEndVTIntervalEntry 1 }

foreSonetFarEndVTIntervalESR OBJECT-TYPE
        SYNTAX  Integer32
        MAX-ACCESS  read-only
        STATUS current
        DESCRIPTION
                 "The ratio of Errored seconds encountered by a
                 SONET/SDH FarEndVT to time in a particular
                 15-minute interval in the past 24 hours."
              ::= { foreSonetFarEndVTIntervalEntry 2 }

foreSonetFarEndVTIntervalSESR OBJECT-TYPE
        SYNTAX  Integer32
        MAX-ACCESS  read-only
        STATUS current
        DESCRIPTION
                 "The ratio of Sev Errored seconds encountered by a
                 SONET/SDH FarEndVT to time in a particular
                 15-minute interval in the past 24 hours."
              ::= { foreSonetFarEndVTIntervalEntry 3 }

foreSonetFarEndVTIntervalBBER OBJECT-TYPE
        SYNTAX  Integer32
        MAX-ACCESS  read-only
        STATUS current
        DESCRIPTION
                 "The ratio of Background blk errors encountered by a
                 SONET/SDH FarEndVT to time in a particular
                 15-minute interval in the past 24 hours."
              ::= { foreSonetFarEndVTIntervalEntry 4 }

-- foreSonetSectionDiagnosticsEntry OBJECT-TYPE
-- 	SYNTAX ForeSonetSectionDiagnosticsEntry
-- 	MAX-ACCESS	not-accessible
-- 	STATUS		current
-- 	DESCRIPTION
-- 		"A table entry containing Fore specific extensions
-- 		 to the standard SONET Section tables."
-- 	INDEX { ifIndex }
-- 	::= { foreSonetSectionDiagnosticsTable 1 }
-- 
-- ForeSonetSectionDiagnosticsEntry ::=
-- 	SEQUENCE {
-- 		foreSonetSectionDiagnosticsMode		INTEGER
-- 	}
-- 
-- foreSonetSectionDiagnosticsMode OBJECT-TYPE
-- 	SYNTAX	INTEGER
-- 	MAX-ACCESS	read-write
-- 	STATUS	current
-- 	DESCRIPTION
-- 		"This variable controls the insertion of various types
-- 		of section diagnostic bit patterns in the transmit
-- 		stream.  
-- 
-- 		Under normal operation it should be set to 1
-- 
-- 		1 None : No diagnostics
-- 
-- 		2 DFP : Controls the insertion of single bit errors
-- 		continuously in the most significant bit (bit 1) of
-- 		the A1 section overhead framing byte.  When DFP is on
-- 		the A1 bytes are set to 0x76 instaed of 0xF6
-- 
-- 		4 DBIP8 : Controls the insertion of bit errors
-- 		continuously in the section BIP-8 byte (B1).  When
-- 		DBIB8 is on the B1 byte is inverted.
-- 
-- 		8 DLOS : Controls the insertion of all zeros in the
-- 		stream.  When DLOST is on the transmit stream is
-- 		forced to 0x00.
-- 
-- 		Note that not all section interfaces support all
-- 		diagnostics.
-- 		"
-- 	DEFVAL { 1 }
-- 	::= { foreSonetSectionDiagnosticsEntry 2 }
-- 
-- Fore extensions to the standard SONET Line Tables

foreSonetLineConfigTable OBJECT-TYPE
	SYNTAX SEQUENCE OF ForeSonetLineConfigEntry
	MAX-ACCESS	not-accessible
	STATUS	current
	DESCRIPTION
		"A table of configuration options and statistics that
		 extend the Sonet Line Group in the Standard SONET MIB."
	::= { foreSonetLine 1 }

foreSonetLineConfigEntry OBJECT-TYPE
	SYNTAX ForeSonetLineConfigEntry
	MAX-ACCESS not-accessible
	STATUS current
	DESCRIPTION
		"A table entry containing Fore specific extensions to
		 the standard SONET Line Group Tables."
	INDEX { ifIndex }
	::= { foreSonetLineConfigTable 1 }

ForeSonetLineConfigEntry ::=
	SEQUENCE {
		foreSonetLineBipThrSeconds	Integer32,
		foreSonetLineBipThrErrors	Integer32,
		foreSonetLineBipFailEnable	INTEGER,
		foreSonetLineSignalDegradeBer   Integer32,
		foreSonetLineSignalFailBer      Integer32,
		foreSonetLineBerErrorModel      INTEGER,
		foreSonetLineBerState		INTEGER
	}

foreSonetLineBipThrSeconds OBJECT-TYPE
	SYNTAX	Integer32
	MAX-ACCESS	read-write
	STATUS	current
	DESCRIPTION
		"This variable represents the consecutive number of
		 BAD/GOOD seconds to detect/clear a B2 byte Line Bit
		 Interleaved Parity (BIP) Defect. The range of the 
		 values it can take is between 2 and 10 inclusive."
         DEFVAL { 10 }
	 ::= { foreSonetLineConfigEntry 2 }

foreSonetLineBipThrErrors OBJECT-TYPE
	SYNTAX	Integer32
	MAX-ACCESS	read-write
	STATUS	current
	DESCRIPTION
		"This variable is a threshold for the number of B2 byte
		 Line Bit Interleaved Parity (BIP) Errors per second
		 and is used as a parameter to the Line BIP Defect. If
		 the number of errors exceeds the threshold, the 
		 particular second is declared BAD, otherwise it is
		 declared GOOD."
	DEFVAL { 1 }
	::= { foreSonetLineConfigEntry 3 }

foreSonetLineBipFailEnable OBJECT-TYPE
	SYNTAX	INTEGER {
		enabled(1),
		disabled(2)
		}
	MAX-ACCESS	read-write
	STATUS	current
	DESCRIPTION
		"This variable controls whether declaration of a
		 Line BIP Defect forces the port's operState to Down."
	::= { foreSonetLineConfigEntry 4 }
	
foreSonetLineSignalDegradeBer OBJECT-TYPE
	SYNTAX  Integer32
	MAX-ACCESS  read-write
	STATUS  current
	DESCRIPTION
		"This is the exponent of 10 for the current signal
		 degrade bit error rate (BER) threshold for this port.
		 The value -7, for example, represents a BER of 1E-7.
		 This variable is only applicable when sonetLineBerErrorModel
		 is set to errorModelRandom."
	::= { foreSonetLineConfigEntry 5 }

foreSonetLineSignalFailBer OBJECT-TYPE
	SYNTAX  Integer32
	MAX-ACCESS  read-write
	STATUS  current
	DESCRIPTION
		"This is the exponent of 10 for the current signal
		 fail bit error rate (BER) threshold for this port.
		 The value -4, for example, represents a BER of 1E-4.
		 This variable is only applicable when sonetLineBerErrorModel
		 is set to errorModelRandom."
	::= { foreSonetLineConfigEntry 6 }


foreSonetLineBerErrorModel OBJECT-TYPE
	SYNTAX  INTEGER {
		errorModelNone(0),
		errorModelRandom(1),
		errorModelBurst(2)
		}
	MAX-ACCESS	read-write
	STATUS		current
	DESCRIPTION
		"This is the error distribution model to be used to
		 identify signal degrade and signal fail conditions.
		 errorModelRandom selects a random error distribution
		 and declares signal conditions based on the thresholds
		 set in sonetLineSignalDegradeBer and sonetLineSignalFailBer.
		 errorModelBurst selects a burst error model and declares
		 signal degrade conditions based on the thresholds set in
		 sonetLineBipThrSeconds and sonetLineBipThrErrors.
		 errorModelNone disables detection of signal conditions."
	DEFVAL	{ errorModelRandom }
	::= { foreSonetLineConfigEntry 7 }

foreSonetLineBerState OBJECT-TYPE
	SYNTAX	INTEGER {
		berStateOk(0),
		berStateSigDegrade(1),
		berStateSigFail(2)
		}
	MAX-ACCESS read-only
	STATUS	   current
	DESCRIPTION
		"This value describes the current state of the port as 
		 determined through bit error rate analysis."
	::= { foreSonetLineConfigEntry 8 }

foreSonetLineTotalTable OBJECT-TYPE
	SYNTAX SEQUENCE OF ForeSonetLineTotalEntry
	MAX-ACCESS	not-accessible
	STATUS	current
	DESCRIPTION
		"A table of configuration options and statistics that
		 extend the Sonet Line Group in the Standard SONET MIB."
	::= { foreSonetLine 2 }

foreSonetLineTotalEntry OBJECT-TYPE
	SYNTAX ForeSonetLineTotalEntry
	MAX-ACCESS not-accessible
	STATUS current
	DESCRIPTION
		"A table entry containing Fore specific extensions to
		 the standard SONET Line Group Tables."
	INDEX { ifIndex }
	::= { foreSonetLineTotalTable 1 }

ForeSonetLineTotalEntry ::=
	SEQUENCE {
		foreSonetLineTotalBIPs		Counter32,
		foreSonetLineTotalFEBEs		Counter32,
		foreSonetLineTotalAISs		Counter32,
		foreSonetLineTotalRDIs		Counter32
	}

foreSonetLineTotalBIPs OBJECT-TYPE
	SYNTAX	Counter32
	MAX-ACCESS	read-only
	STATUS	current
	DESCRIPTION
		"The number of Line BIP-24 (Bit Interleaved Parity)
		errors that have been detected since the last time the
		port has been reset. The calculated BIP-24 code is
		based on the line overhead and synchronous payload
		envelope (SPE) of the STS-3c stream. The line BIP-24
		code is a bit interleaved parity calculation using
		even parity. The calculated code is compared with the
		BIP-24 code extracted from the B2 bytes of the
		following frame. Differences indicate that a line
		layer bit error has occurred."
	::= { foreSonetLineTotalEntry 1 }

foreSonetLineTotalFEBEs OBJECT-TYPE
	SYNTAX	Counter32
	MAX-ACCESS	read-only
	STATUS	current
	DESCRIPTION
		"The number of line Far End Block Errors (FEBE) that have been detected since 
		the last time the port has been reset."
	::= { foreSonetLineTotalEntry 2 }

foreSonetLineTotalAISs OBJECT-TYPE
	SYNTAX	Counter32
	MAX-ACCESS	read-only
	STATUS	current
	DESCRIPTION
		"The number of seconds in which line Alarm Indication
		Signal (AIS) has occurred.  A line AIS is asserted
		when a 111 binary pattern is detected in bits 6,7,8 of
		the K2 byte for five consecutive frames. A line AIS is
		removed when any pattern other than 111 is detected in
		these bits for five consecutive frames."
	::= { foreSonetLineTotalEntry 3 }

foreSonetLineTotalRDIs OBJECT-TYPE
	SYNTAX	Counter32
	MAX-ACCESS	read-only
	STATUS	current
	DESCRIPTION
		"The number of seconds in which line Far End Receive
		Failure (RDI) has occurred.  A line RDI is asserted
		when a 110 binary pattern is detected in bits 6,7,8 of
		the K2 byte for five consecutive frames. A line RDI is
		removed when any pattern other than 110 is detected in
		these bits for five consecutive frames."
	::= { foreSonetLineTotalEntry 4 }


foreSonetLineDiagnosticsTable OBJECT-TYPE
	SYNTAX SEQUENCE OF ForeSonetLineDiagnosticsEntry
	MAX-ACCESS	not-accessible
	STATUS	current
	DESCRIPTION
		"A table of configuration options and statistics that
		 extend the Sonet Line Group in the Standard SONET MIB."
	::= { foreSonetLine 3 }


foreSonetLineDiagnosticsEntry OBJECT-TYPE
 	SYNTAX ForeSonetLineDiagnosticsEntry
 	MAX-ACCESS not-accessible
 	STATUS current
 	DESCRIPTION
 		"A table entry containing Fore specific extensions to
 		 the standard SONET Line Group Tables."
 	INDEX { ifIndex }
 	::= { foreSonetLineDiagnosticsTable 1 }


ForeSonetLineDiagnosticsEntry ::=
 	SEQUENCE {
		foreSonetLineDiagnosticsLAIS		INTEGER,
		foreSonetLineDiagnosticsB2		INTEGER,
		foreSonetLineDiagnosticsAPS		INTEGER,
		foreSonetLineDiagnosticsK1channel	INTEGER,
		foreSonetLineDiagnosticsK1request	INTEGER,
		foreSonetLineDiagnosticsK2channel	INTEGER,
		foreSonetLineDiagnosticsK2Architecture	INTEGER,
		foreSonetLineDiagnosticsK2Mode		INTEGER,
		foreSonetLineDiagnosticsLRDI		INTEGER,
		foreSonetLineDiagnosticsLREI		INTEGER
 	}


foreSonetLineDiagnosticsLAIS OBJECT-TYPE
 	SYNTAX	INTEGER {
 		on(1),
 		off(2)
		}
 	MAX-ACCESS	read-write
 	STATUS	current
 	DESCRIPTION
		"Controls the insertion of line alarm indication signal
		 (AIS_L). 

		on	When set to on, all bits of the SONET frame are 
			set to 1 except for the section overhead.
		off	resume normal operation"
	DEFVAL { off }
 	::= { foreSonetLineDiagnosticsEntry 1 }


foreSonetLineDiagnosticsB2 OBJECT-TYPE
 	SYNTAX	INTEGER {
		on(1),
		off(2),
		momentary(3)
		}
 	MAX-ACCESS	read-write
 	STATUS	current
 	DESCRIPTION
		"Controls the insertion of BIP errors in the sonet line 
	         B2 byte overhead. 

		off		When set to off, do not generate line BIP 
				errors.
		on		When set to on, generate line BIP errors.
		momentary	When set to momentary, transmit a chip dependent  
				number of Sonet frame with line BIP errors."
	DEFVAL { off }
 	::= { foreSonetLineDiagnosticsEntry 2 }

 
foreSonetLineDiagnosticsAPS OBJECT-TYPE
 	SYNTAX	INTEGER {
 		on(1),
 		off(2)
		}
 	MAX-ACCESS	read-write
 	STATUS	current
 	DESCRIPTION
 		"Controls the insertion of line APS bytes (K1 and K2)
		that are determined by normal operating rules or by
		diagnostic mibs.

		off	When set to off, resume normal operation.
		on	When set to on, K1 and K2 bytes are calculated
			by contents of diagnostic mibs."
 	DEFVAL { off }
 	::= { foreSonetLineDiagnosticsEntry 3 }


foreSonetLineDiagnosticsK1channel OBJECT-TYPE
 	SYNTAX	INTEGER {
 		null(0),
 		working1(1),
		working2(2),
		working3(3),
		working4(4),
		working5(5),
		working6(6),
		working7(7),
		working8(8),
		working9(9),
		working10(10),
		working11(11),
		working12(12),
		working13(13),
		working14(14),
		extraTraffic(15)
		}
 	MAX-ACCESS	read-write
 	STATUS	current
 	DESCRIPTION
		"Specifies the channel number code, k1 bits 5 to 8.

		* null(0) -  null channel
		Code 0 is used with the Lockout of Protection request.

		* working(1..14) - Working channels
		Codes 1 through n apply in a 1:n architecture
		Only code 1 applies in a 1+1 architecture

		*extraTraffic(15) - Extra traffic channel
		May exist only when provisioned in a 1:n architecture
		NOTE: Refer to GR-253-CORE for more details"
 	DEFVAL { null }
 	::= { foreSonetLineDiagnosticsEntry 4}


foreSonetLineDiagnosticsK1request OBJECT-TYPE
 	SYNTAX	INTEGER {
		lockout(15),
		forcedsw(14),
		sfhp(13),
		sflp(12),
		sdhp(11),
		sdlp(10),
		manualsw(8),
		wtr(6),
		exercise(4),
		rr(2),
		donotrevert(1),
		noreq(0)
		}
 	MAX-ACCESS	read-write
 	STATUS	current
 	DESCRIPTION
		"Defines the various values for K1 byte (1-4) for the 
		 type of request

		 For 1+1 systems, Forced and Manual switch request apply.

	 	 SD and SF requests apply to conditions detected on the 
		 protection line."
 	DEFVAL { noreq }
 	::= { foreSonetLineDiagnosticsEntry 5 }


foreSonetLineDiagnosticsK2channel OBJECT-TYPE
 	SYNTAX	INTEGER {
 		null(0),
 		working1(1),
		working2(2),
		working3(3),
		working4(4),
		working5(5),
		working6(6),
		working7(7),
		working8(8),
		working9(9),
		working10(10),
		working11(11),
		working12(12),
		working13(13),
		working14(14),
		extraTraffic(15)
		}
 	MAX-ACCESS	read-write
 	STATUS	current
 	DESCRIPTION
		"Specifies the channel number code, k2 bits 1 to 4
		* null - null channel
		Code 0 is used with the Lockout of Protection request.

		* working(1..14) - Working channels
		Codes 1 through n apply in a 1:n architecture
		Only code1 applies in a 1+1 architecture

		* extraTraffic(15) - Extra traffic channel
		May exist only when provisioned in a 1:n architecture
                NOTE: Refer to GR-253-CORE for more details"
 	DEFVAL { null }
 	::= { foreSonetLineDiagnosticsEntry 6 }


foreSonetLineDiagnosticsK2Architecture OBJECT-TYPE
 	SYNTAX	INTEGER {
	oneplusone(0),
	onen(1)
	}
 	MAX-ACCESS	read-write
 	STATUS	current
 	DESCRIPTION
		"Bit 5 of the K2 byte shall be set to indicate:
		
		* Code '0' if the provisioned (or only supported) 
		  architecture is 1+1
		* Code '1' if the provisioned (or only supported) 
		  architecture is 1:n"
 	DEFVAL { oneplusone }
 	::= { foreSonetLineDiagnosticsEntry 7 }


foreSonetLineDiagnosticsK2Mode OBJECT-TYPE
 	SYNTAX	INTEGER {
	unidirectional(4),
	bidirectional(5)
	}
 	MAX-ACCESS	read-write
 	STATUS	current
 	DESCRIPTION
		"Bits 6 through 8 of the K2 byte shall be set to indicate:
		* Code '101' if the provisioned mode is bidirectional
		* Code '100' if the provisioned mode is unidirectional
		The codes '011', '010', '001' and '000' in K2 bites 6-8 
		are reserved for future use in 1:n drop and insert(nested) 
		protection switching, and the code '111' is used in 
		detecting an incoming AIS_L."
 	DEFVAL { unidirectional }
 	::= { foreSonetLineDiagnosticsEntry 8 }


foreSonetLineDiagnosticsLRDI OBJECT-TYPE
 	SYNTAX	INTEGER {
 		on(1),
 		off(2),
		auto(4)
		}
 	MAX-ACCESS	read-write
 	STATUS	current
	DESCRIPTION
		"Controls the insertion of line Remote Defect Indication 
		 (Line RDI). Line RDI is inserted by transmitting the code 
		 110 (binary) in bit positions 6, 7 and 8 of the K2 byte 
		 contained in the transmit stream.

		off	When set to off, Line RDI is NOT inserted in the 
			transmit stream even if LOS/LOF is received
		on	When set to on, Line RDI is inserted continuously 
			in the transmit stream.
		auto	When set to auto, Line RDI is inserted as under 
			normal operation"
 	DEFVAL { auto }
 	::= { foreSonetLineDiagnosticsEntry 9 }


foreSonetLineDiagnosticsLREI OBJECT-TYPE
 	SYNTAX	INTEGER {
		on(1),
		off(2),
		auto(4)
 		}
 	MAX-ACCESS	read-write
 	STATUS	current
 	DESCRIPTION
		"Controls the insertion of Line Remote Error Indication
		 (REI_L). The number of BIP errors (B2) detected are encoded
		 in the transmit REI_L (M0/M1) byte. REI_L was previously
		 called Line FEBE (Far End Block Error). 

		off	When set to off, insert 0 for M0/M1 bytes,
			irrespective of the number of B2 errors received.
		on	When set to on, insert 8/8N for M0/M1 bytes 
			continuously.
		auto	When set to auto, resume normal operation."
 	DEFVAL { auto }
 	::= { foreSonetLineDiagnosticsEntry 10 }


-- Fore extensions to the Sonet Path Tables

foreSonetPathConfigTable OBJECT-TYPE
	SYNTAX SEQUENCE OF ForeSonetPathConfigEntry
	MAX-ACCESS	not-accessible
	STATUS		current
	DESCRIPTION
		"A table of configuration options and statistics
		 that extend the standard SONET Path Tables"
	::= { foreSonetPath 1 }

foreSonetPathConfigEntry OBJECT-TYPE
	SYNTAX 		ForeSonetPathConfigEntry
	MAX-ACCESS	not-accessible
	STATUS		current
	DESCRIPTION
		"A table entry containing Fore specific extensions
		 to the standard SONET path tables"
	INDEX { ifIndex }
	::= { foreSonetPathConfigTable 1 }

ForeSonetPathConfigEntry ::=
	SEQUENCE {
		foreSonetPathRxSignalLabel	Integer32,
		foreSonetPathTxSignalLabel	Integer32,
		foreSonetPathLoopbackMode	INTEGER
	}

foreSonetPathRxSignalLabel OBJECT-TYPE
	SYNTAX	Integer32
	MAX-ACCESS	read-only
	STATUS	current
	DESCRIPTION
		"This variable contains the path signal label byte
		(C2).  The value in this variable is updated to a new
		path signal label value if the same new value is
		observed for two consecutive frames."
	DEFVAL { 19 }
	::= { foreSonetPathConfigEntry 2 }

foreSonetPathTxSignalLabel OBJECT-TYPE
	SYNTAX	Integer32
	MAX-ACCESS	read-write
	STATUS	current
	DESCRIPTION
		"This variable controls the transmit path payload.
		The default value for ATM is 0x13 (19 decimal). Changing
		the value of this variable attempts to change the payload
		and if successfull will change the transmitted C2 label
		to reflect the new payload.  Use the C2 variable in the
		diagnostics table if you wish to change the C2 value for
		diagnostic purposes without actually changing the
		transmitted payload type."
	DEFVAL { 19 }
	::= { foreSonetPathConfigEntry 3 }
 
foreSonetPathLoopbackMode OBJECT-TYPE
	SYNTAX	INTEGER {
		sonetPathNoLoop(1), 
		sonetPathLineLoop(2),
		sonetPathDiagLoop(3),
		sonetPathOtherLoop(4)
		}
	MAX-ACCESS	read-write
	STATUS	current
	DESCRIPTION
		"This variable represents the current loopback status of the 
		SONET interface.
		The possible values are: 
		sonetPathNoLoop (1) means that the interface is not in a 
		loopback state.
		sonetPathLineLoop (2) means that the receive data 
		is connected to the transmit data.
		sonetPathDiagLoop (3) means that the transmit data 
		stream is looped back to the receiver.
		sonetPathOtherLoop (4) means that the interface is in a 
		loopback that is not defined here."
	DEFVAL { sonetPathNoLoop }
	::= { foreSonetPathConfigEntry 5 }


-- Fore Sonet Path Total Table

foreSonetPathTotalTable OBJECT-TYPE
	SYNTAX SEQUENCE OF ForeSonetPathTotalEntry
	MAX-ACCESS	not-accessible
	STATUS		current
	DESCRIPTION
		"A table of configuration options and statistics
		 that extend the standard SONET Path Tables"
	::= { foreSonetPath 2 }

foreSonetPathTotalEntry OBJECT-TYPE
	SYNTAX 		ForeSonetPathTotalEntry
	MAX-ACCESS	not-accessible
	STATUS		current
	DESCRIPTION
		"A table entry containing Fore specific extensions
		 to the standard SONET path tables"
	INDEX { ifIndex }
	::= { foreSonetPathTotalTable 1 }

ForeSonetPathTotalEntry ::=
	SEQUENCE {
		foreSonetPathTotalBIPs		Counter32,
		foreSonetPathTotalLOPs		Counter32,
		foreSonetPathTotalAISs		Counter32,
		foreSonetPathTotalRDIs		Counter32,
		foreSonetPathTotalUNEQs		Counter32,
		foreSonetPathTotalPLMs		Counter32,
		foreSonetPathTotalFEBEs		Counter32
	}

foreSonetPathTotalBIPs OBJECT-TYPE
	SYNTAX	Counter32
	MAX-ACCESS	read-only
	STATUS	current
	DESCRIPTION
		"The number of Path BIP-8 (Bit Interleaved Parity) errors that have been 
		detected since the last time the port has been reset. A path BIP-8 error is 
		detected by comparing the path BIP-8 byte (B3) extracted from the current 
		frame, to the path BIP-8 computed for the previous frame."
	::= { foreSonetPathTotalEntry 1 }

foreSonetPathTotalLOPs OBJECT-TYPE
	SYNTAX	Counter32
	MAX-ACCESS	read-only
	STATUS	current
	DESCRIPTION
		"The number of seconds in which path Loss Of Pointer (LOP) has occurred. A path
		LOP is detected when a 'normal pointer value' is not found in eight consecutive 
		frames. The LOP is cleared when a 'normal pointer value' is detected for three 
		consecutive frames."
	::= { foreSonetPathTotalEntry 2 }

foreSonetPathTotalAISs OBJECT-TYPE
	SYNTAX	Counter32
	MAX-ACCESS	read-only
	STATUS	current
	DESCRIPTION
		"The number of seconds in which path Alarm Indication Signal (AIS) has occurred. 
		A path AIS is asserted when an all-ones pattern is detected in the pointer bytes 
		(H1 and H2) for three consecutive frames. It is cleared when a valid pointer is 
		detected for three consecutive frames. AIS indicates that an upstream failure 
		has been detected."
	::= { foreSonetPathTotalEntry 3 }


foreSonetPathTotalRDIs OBJECT-TYPE
	SYNTAX	Counter32
	MAX-ACCESS	read-only
	STATUS	current
	DESCRIPTION
		"The number of seconds in which path RDI alarm has occurred. A path RDI 
		alarm is detected by extracting bit 5 of the path status byte. If bit 5 is 
		high for ten consecutive frames, a RDI alarm is declared. A RDI alarm 
		is cleared when bit 5 is low for ten consecutive frames. RDI signals are 
		used to alert upstream terminals of a downstream failure in order to initiate 
		trunk conditioning on the failure circuit."
	::= { foreSonetPathTotalEntry 4 }


foreSonetPathTotalUNEQs OBJECT-TYPE
	SYNTAX	Counter32
	MAX-ACCESS	read-only
	STATUS	current
	DESCRIPTION
		"The number of seconds in which a path UNEQ defect has occurred.  A path UNEQ
		defect is detected when the STS Signal label (C2 byte) == 0x00"
	::= { foreSonetPathTotalEntry 5 }


foreSonetPathTotalPLMs OBJECT-TYPE
	SYNTAX	Counter32
	MAX-ACCESS	read-only
	STATUS	current
	DESCRIPTION
		"The number of seconds in which a path PLM defect has occrred.  A path PLM
		defect is detected when the STS Signal lable (C2 bytes) != 0x00, 0x01, 0x13,
		0xFC or 0xFF."
	::= { foreSonetPathTotalEntry 6 }

foreSonetPathTotalFEBEs OBJECT-TYPE
	SYNTAX Counter32
	MAX-ACCESS	read-only
	STATUS	current
	DESCRIPTION
		"The number of path Far End Block Errors (FEBE) that have been detected since 
		the last time the port has been reset. FEBEs are detected by extracting the 
		4-bit FEBE field from the path status byte (G1). The legal range for the 4 bit 
		field is between 0000 and 1000, representing zero to eight errors. Any other 
		value is interpreted as zero errors."
	::= { foreSonetPathTotalEntry 7 } 

-- Fore Sonet Path Current Table
foreSonetPathCurrentTable OBJECT-TYPE
        SYNTAX SEQUENCE OF ForeSonetPathCurrentEntry
        MAX-ACCESS          not-accessible
        STATUS          current
        DESCRIPTION
               "A table of configuration options and statistics
                that extend the standard SONET Path table."
        ::= { foreSonetPath 3 }

foreSonetPathCurrentEntry OBJECT-TYPE
	SYNTAX		ForeSonetPathCurrentEntry
	MAX-ACCESS	not-accessible
	STATUS		current
	DESCRIPTION
		"A table entry containing fore specific extensions
		 to the current status table for SONET paths."
	INDEX  { ifIndex }
	::= { foreSonetPathCurrentTable 1 }

ForeSonetPathCurrentEntry ::=
	SEQUENCE {
		foreSonetPathCurrentStatus      Integer32,
		foreSonetPathCurrentBBEs	Integer32
        }

foreSonetPathCurrentStatus      OBJECT-TYPE
	SYNTAX Integer32
	MAX-ACCESS read-only
	STATUS current
	DESCRIPTION
		"This variable indicates information about the
	         current status of the sonet path.  This variable
                 is encoded as a bit vector so it can represent
                 multiple conditions simultaneously.

                 The various bit positions are:
			1       pathPDI-P detected

				pathPDI-P is set when the incoming
				path C2 byte is set to a value in
				the range 0xe1..0xfc.
		"
	::= { foreSonetPathCurrentEntry 1}

foreSonetPathCurrentBBEs OBJECT-TYPE
        SYNTAX  Integer32
        MAX-ACCESS  read-only
        STATUS current
        DESCRIPTION
                "The counter associated with the number of Background
                 Errors encountered by a
                 SONET/SDH Path in the current 15 minute interval."
        ::= { foreSonetPathCurrentEntry 2 }

-- Fore Sonet Path Diagnostics Table

foreSonetPathDiagnosticsTable OBJECT-TYPE
	SYNTAX SEQUENCE OF ForeSonetPathDiagnosticsEntry
	MAX-ACCESS	not-accessible
	STATUS		current
	DESCRIPTION
		"A table of diagnostics tests that extend the 
		 standard SONET Path Tables"
	::= { foreSonetPath 4 }


foreSonetPathDiagnosticsEntry OBJECT-TYPE
 	SYNTAX 		ForeSonetPathDiagnosticsEntry
 	MAX-ACCESS	not-accessible
 	STATUS		current
 	DESCRIPTION
 		"A table entry containing Fore specific extensions
 		 to the standard SONET path tables"
 	INDEX { ifIndex }
 	::= { foreSonetPathDiagnosticsTable 1 }
 
ForeSonetPathDiagnosticsEntry ::=
	SEQUENCE {
		foreSonetPathDiagnosticsC2		INTEGER,
		foreSonetPathDiagnosticsC2Value		INTEGER,
		foreSonetPathDiagnosticsB3		INTEGER,
 		foreSonetPathDiagnosticsPREI		INTEGER,
		foreSonetPathDiagnosticsPAIS		INTEGER,
		foreSonetPathDiagnosticsPERDI		INTEGER,
		foreSonetPathDiagnosticsERDIValue	INTEGER,
		foreSonetPathDiagnosticsLOP		INTEGER
	}
 
foreSonetPathDiagnosticsC2 OBJECT-TYPE
 	SYNTAX	INTEGER {
		on(1),
 		off(2)
		}
 	MAX-ACCESS	read-write
 	STATUS	current
 	DESCRIPTION
		"Controls the insertion of Signal label/Payload Defect
		 Indication (PDI_P) into the C2 byte of the Sonet path
		 overhead. The various values for Signal label/PDI_P are
		 defined in GR-253-CORE.

		off	When set to off, the C2 byte is set to previously
			configured C2 value.
		on	When set to on, the foreSonetPathDiagnosticsC2Value
			is inserted in the C2 byte of the tranmsit stream."
 	DEFVAL { off }
 	::= { foreSonetPathDiagnosticsEntry 1 }

foreSonetPathDiagnosticsC2Value OBJECT-TYPE
 	SYNTAX	INTEGER  {
		unequipped(0),
		equippednonspecPL(1),
		vtstructSTSSPE(2),
		lockedVTmode(3),
		asyncDS3mapping(4),
		asyncDS4na(18),
		atmmapping(19),
		dqdbmapping(20),
		asyncfddimapping(21),
		hdlcwithscrambling(22),
		sts1with1vtxPD(225),
		sts1with2vtxPD(226),
		sts1with3vtxPD(227),
		sts1with4vtxPD(228),
		sts1with5vtxPD(229),
		sts1with6vtxPD(230),
		sts1with7vtxPD(231),
		sts1with8vtxPD(232),
		sts1with9vtxPD(233),
		sts1with10vtxPD(234),
		sts1with11vtxPD(235),
		sts1with12vtxPD(236),
		sts1with13vtxPD(237),
		sts1with14vtxPD(238),
		sts1with15vtxPD(239),
		sts1with16vtxPD(240),
		sts1with17vtxPD(241),
		sts1with18vtxPD(242),
		sts1with19vtxPD(243),
		sts1with20vtxPD(244),
		sts1with21vtxPD(245),
		sts1with22vtxPD(246),
		sts1with23vtxPD(247),
		sts1with24vtxPD(248),
		sts1with25vtxPD(249),
		sts1with26vtxPD(250),
		sts1with27vtxPD(251),
		payloaddefect(252)	
		}
 	MAX-ACCESS	read-write
 	STATUS	current
 	DESCRIPTION
		"Contains C2 byte value of the transmit stream"
 	DEFVAL { equippednonspecPL }
 	::= { foreSonetPathDiagnosticsEntry 2 }

foreSonetPathDiagnosticsB3 OBJECT-TYPE
 	SYNTAX	INTEGER {
		on(1),
 		off(2),
		momentary(3)
		}		
 	MAX-ACCESS	read-write
 	STATUS	current
 	DESCRIPTION
		"Controls the insertion of Path BIP errors in the sonet path B3
		 byte overhead. 

		off		When set to off, do not generate path BIP errors.
		on		When set to on, generate path BIP errors.
		momentary	When set to momentary, transmit a chip dependent
			        number of Sonet frames with path BIP errors."
	DEFVAL { off }
 	::= { foreSonetPathDiagnosticsEntry 3 }

foreSonetPathDiagnosticsPREI OBJECT-TYPE
 	SYNTAX	INTEGER {
		on(1),
 		off(2),
		auto(4)
 		}
 	MAX-ACCESS	read-write
 	STATUS	current
 	DESCRIPTION
		"Controls the insertion of Sonet Path Remote Error
		 Indication (REI_P) (previously called Far End Block Error 
		 (FEBE)).

					G1 byte
			 1    2    3    4    5     6    7    8	
			----|----|----|----|----|----|----|----|
		 	|     REI_P        |    RDI_P     | uu |
			----------------------------------------

		REI_P 		Path Remote Error Indication
		RDI_P		Path Remote Defect Indication
		uu  		Unused

		off	When set to off, the value 0 is inserted in bits 
		 	1:4 of G1 byte.
		on 	When set to on, the value 0x8 is inserted in bits 
			1:4 of G1 byte.
		auto	When set to auto, resume normal operation."
	DEFVAL { auto }
 	::= { foreSonetPathDiagnosticsEntry 4 }


foreSonetPathDiagnosticsPAIS OBJECT-TYPE
 	SYNTAX	INTEGER {
		on(1),
 		off(2)
		}
 	MAX-ACCESS	read-write
 	STATUS	current
 	DESCRIPTION
 		"Controls the insertion of STS Path Alarm Indication Signal
		 (AIS_P).  

		off	When set to off, AIS_P is not generated under any
			circumstances.
		on	When set to on, AIS_P is generated."
	DEFVAL { off }
 	::= { foreSonetPathDiagnosticsEntry  5 }


foreSonetPathDiagnosticsPERDI OBJECT-TYPE
 	SYNTAX	INTEGER {
		on(1),
		auto(4)
		}
 	MAX-ACCESS	read-write
 	STATUS	current
 	DESCRIPTION
		"Controls the insertion of Enhanced Remote Defect
		 Indication. Bits 5,6, and 7 of G1 byte is used for the
		 inserting ERDI.

					G1 byte
			 1    2    3    4    5     6    7    8	
			----|----|----|----|----|----|----|----|
		 	|     REI_P        |    RDI_P     | uu |
			----------------------------------------

		REI_P 		Path Remote Error Indication
		RDI_P		Path Remote Defect Indication
		uu  		Unused

		on 	When set to on, foreSonetPathDiagnosticsERDIValue
			is inserted in the bits 5,6,7 of G1 byte.
		auto	When set to auto, resume normal operation using
		        single bit RDI."
 	DEFVAL { auto }
	::= { foreSonetPathDiagnosticsEntry 6 }

foreSonetPathDiagnosticsERDIValue OBJECT-TYPE
 	SYNTAX	INTEGER {
		sonetPathERDIOnebitRDI(4),
		sonetPathERDIserverDefect(5),
		sonetPathERDIconnDefect(6),
		sonetPathERDIpayloadDefect(2),
		sonetPathERDInoDefect(1),
		sonetPathERDInoPrionoDefect(0)
		}
 	MAX-ACCESS	read-write
 	STATUS	current
 	DESCRIPTION
		"Defines the values that may be inserted in the bits
		 5,6 and 7 of G1 byte.

		1xx - One bit RDI
		000 - No RDI_P defect with no priority
		001 - No RDI_P defect
		010 - ERDI_P payload defect
		101 - ERDI_P server defect
		110 - ERDI_P connectivity defect"
 	DEFVAL { sonetPathERDInoDefect }
 	::= { foreSonetPathDiagnosticsEntry 7 }

foreSonetPathDiagnosticsLOP OBJECT-TYPE
 	SYNTAX	INTEGER {
		on(1),
 		off(2)
		}		
 	MAX-ACCESS	read-write
 	STATUS	current
 	DESCRIPTION
		"Controls the insertion of Loss of pointer for path level.

		off	When set to off, loss of pointer is not
			generated.
		on	When set to on, loss of pointer is generated
			in the transmit direction."
	DEFVAL { off }
 	::= { foreSonetPathDiagnosticsEntry 8 }



-- Fore Sonet Path Group Configuration Table

foreSonetPathGroupConfigTable OBJECT-TYPE
    SYNTAX SEQUENCE OF ForeSonetPathGroupConfigEntry
    MAX-ACCESS not-accessible
    STATUS current
    DESCRIPTION
	"A table of configuration options for Sonet Path VT Groups that extend
	 the standard SONET Path tables."
	::= { foreSonetPath 5 }

foreSonetPathGroupConfigEntry OBJECT-TYPE
    SYNTAX ForeSonetPathGroupConfigEntry
    MAX-ACCESS not-accessible
    STATUS current
    DESCRIPTION
	"A table entry containing Marconi specific extensions to the SONET Path
	 configuration table."
	INDEX  { ifIndex, foreVTGroup }
	::= { foreSonetPathGroupConfigTable 1 }

ForeSonetPathGroupConfigEntry ::=
    SEQUENCE {
	foreVTGroup	Integer32,
	foreVTWidth	INTEGER
    }

foreVTGroup OBJECT-TYPE
    SYNTAX Integer32
    MAX-ACCESS read-only
    STATUS current
    DESCRIPTION
	"This variable indicates the sonet VT group number within the sonet
	 path. It can range from 0 to 6. "
	::= { foreSonetPathGroupConfigEntry 1}

foreVTWidth OBJECT-TYPE
    SYNTAX INTEGER {
	vtWidth15VC11(1),
	vtWidth2VC12(2),
	vtWidth3(3),
	vtWidth6VC2(4),
	vtWidth6c(5)
    }
    MAX-ACCESS read-write
    STATUS current
    DESCRIPTION
	"This variable indicates the sonet VT width."
    DEFVAL { vtWidth15VC11 }
	::= { foreSonetPathGroupConfigEntry 2}





-- ************************ Fore Sonet VT Tables ***************************

-- Fore Sonet VT Configuration Table

foreSonetVTConfigTable OBJECT-TYPE
    SYNTAX SEQUENCE OF ForeSonetVTConfigEntry
    MAX-ACCESS not-accessible
    STATUS current
    DESCRIPTION
	"A table of sonet VT configuration options that extend the standard
	 sonet VT tables"
	::= { foreSonetVT 1 }

foreSonetVTConfigEntry OBJECT-TYPE
    SYNTAX ForeSonetVTConfigEntry
    MAX-ACCESS not-accessible
    STATUS current
    DESCRIPTION
	"A table entry containing Fore specific extensions to the standard
	 sonet VT tables"
	INDEX { ifIndex }
	::= { foreSonetVTConfigTable 1 }

ForeSonetVTConfigEntry ::=
    SEQUENCE {
	foreSonetVTLoopbackMode	INTEGER
    }

foreSonetVTLoopbackMode OBJECT-TYPE
    SYNTAX INTEGER {
	sonetVTNoLoop(1), 
	sonetVTLineLoop(2),
	sonetVTDiagLoop(3),
	sonetVTOtherLoop(4)
    }
    MAX-ACCESS read-write
    STATUS current
    DESCRIPTION
	"This variable represents the current loopback status of the sonet
	 interface.  The possible values are: 
	    sonetVTNoLoop(1):    interface is not in a loopback state.
	    sonetVTLineLoop(2):  data on the receive path is looped back on to
				 the transmit path.
	    sonetVTDiagLoop(3):  data to be transmitted on the transmit path is
				 looped back on to the receive path.
	    sonetVTOtherLoop(4): the loopback mode is not defined here."
	DEFVAL { sonetVTNoLoop }
	::= { foreSonetVTConfigEntry 1 }



-- Fore Sonet VT Total Table

foreSonetVTTotalTable OBJECT-TYPE
    SYNTAX SEQUENCE OF ForeSonetVTTotalEntry
    MAX-ACCESS not-accessible
    STATUS current
    DESCRIPTION
	"A table of statistics that extend the standard sonet VT Tables"
	::= { foreSonetVT 2 }

foreSonetVTTotalEntry OBJECT-TYPE
    SYNTAX ForeSonetVTTotalEntry
    MAX-ACCESS not-accessible
    STATUS current
    DESCRIPTION
	"A table entry containing Fore specific extensions to the standard
	 sonet VT tables"
    INDEX { ifIndex }
    ::= { foreSonetVTTotalTable 1 }

ForeSonetVTTotalEntry ::=
    SEQUENCE {
	foreSonetVTTotalBIPs		Counter32,
	foreSonetVTTotalREIs		Counter32,
	foreSonetVTTotalLOPs		Counter32,
	foreSonetVTTotalAISs		Counter32,
	foreSonetVTTotalRDIs		Counter32,
	foreSonetVTTotalUNEQs		Counter32,
	foreSonetVTTotalPLMs		Counter32
    }

foreSonetVTTotalBIPs OBJECT-TYPE
    SYNTAX Counter32
    MAX-ACCESS read-only
    STATUS current
    DESCRIPTION
	"The number of VT BIP-2 errors that have been detected since the last
	 time this interface has been reset."
	::= { foreSonetVTTotalEntry 1 }

foreSonetVTTotalREIs OBJECT-TYPE
    SYNTAX Counter32
    MAX-ACCESS read-only
    STATUS current
    DESCRIPTION
	"The number of REIs that have been detected since the last time this
	 interface has been reset."
	::= { foreSonetVTTotalEntry 2 } 

foreSonetVTTotalLOPs OBJECT-TYPE
    SYNTAX Counter32
    MAX-ACCESS read-only
    STATUS current
    DESCRIPTION
	"The number of seconds in which VT LOP has occurred since the last time
	 this interface has been reset."
	::= { foreSonetVTTotalEntry 3 }

foreSonetVTTotalAISs OBJECT-TYPE
    SYNTAX Counter32
    MAX-ACCESS read-only
    STATUS current
    DESCRIPTION
	"The number of seconds in which VT AIS has occurred since the last time
	 this interface has been reset."
	::= { foreSonetVTTotalEntry 4 }

foreSonetVTTotalRDIs OBJECT-TYPE
    SYNTAX Counter32
    MAX-ACCESS read-only
    STATUS current
    DESCRIPTION
	"The number of seconds in which VT RDI has occurred since the last time
	 this interface has been reset."
	::= { foreSonetVTTotalEntry 5 }

foreSonetVTTotalUNEQs OBJECT-TYPE
    SYNTAX Counter32
    MAX-ACCESS read-only
    STATUS current
    DESCRIPTION
	"The number of seconds in which VT UNEQ has occurred since the last
	 time this interface has been reset."
    ::= { foreSonetVTTotalEntry 6 }

foreSonetVTTotalPLMs OBJECT-TYPE
    SYNTAX Counter32
    MAX-ACCESS read-only
    STATUS current
    DESCRIPTION
	"The number of seconds in which VT PLM has occrred since the last time
	 this interface has been reset."
	::= { foreSonetVTTotalEntry 7 }



-- Fore Sonet VT Diagnostics Table

foreSonetVTDiagnosticsTable OBJECT-TYPE
        SYNTAX SEQUENCE OF ForeSonetVTDiagnosticsEntry
        MAX-ACCESS not-accessible
        STATUS current
        DESCRIPTION
	       "A table of diagnostic controls that are used
	        to manipulate Sonet virtual tributaries."
	::= { foreSonetVT 3 }

foreSonetVTDiagnosticsEntry OBJECT-TYPE
        SYNTAX ForeSonetVTDiagnosticsEntry
        MAX-ACCESS not-accessible
        STATUS current
        DESCRIPTION
               "A table entry containing Marconi specific extensions
                to the standard Sonet VT Tables."
        INDEX { ifIndex }
        ::= { foreSonetVTDiagnosticsTable 1 }

ForeSonetVTDiagnosticsEntry ::=
        SEQUENCE {
	        foreSonetVtDiagnosticsBIP           INTEGER,
	        foreSonetVtDiagnosticsRDI           INTEGER,
		foreSonetVtDiagnosticsRFI           INTEGER,
		foreSonetVtDiagnosticsAIS           INTEGER,
		foreSonetVtDiagnosticsLOP           INTEGER,
		foreSonetVtDiagnosticsLabel         INTEGER,
		foreSonetVtDiagnosticsLabelValue    INTEGER,
		foreSonetVtDiagnosticsREI 	    INTEGER
        }

foreSonetVtDiagnosticsBIP OBJECT-TYPE
    SYNTAX INTEGER {
	on(1),
	off(2),
	momentary(3)
    }		
    MAX-ACCESS read-write
    STATUS current
    DESCRIPTION
	"Controls the insertion of VT BIP errors in the sonet VT V5 byte
	 overhead. 
	    on:		Generate sonet VT BIP errors continuously.
	    off:	Do not generate sonet VT BIP errors.
	    momentary:	Generate a chip dependent number of sonet frames with
			sonet VT BIP errors."
	DEFVAL { off }
 	::= { foreSonetVTDiagnosticsEntry 1 }

foreSonetVtDiagnosticsRDI OBJECT-TYPE
        SYNTAX  INTEGER {
	        on(1),
		off(2),
		momentary(3),
		auto(4)
		}
	MAX-ACCESS  read-write
	STATUS  current
	DESCRIPTION
	        "Controls the generation of VT RDI defects on the selected
		 interface.

		 Value		Description
		 on(1)          RDI is continually tramsmitted
		 off(2)         RDI is never transmitted
		 momentary(3)   RDI is transmitted for a short period of time.
		 auto(4)        RDI is generated according to the sonet specification"
	DEFVAL { auto }
	::= { foreSonetVTDiagnosticsEntry 2 }


foreSonetVtDiagnosticsRFI OBJECT-TYPE
        SYNTAX  INTEGER {
	        on(1),
		off(2),
		momentary(3),
		auto(4)
		}
	MAX-ACCESS  read-write
	STATUS  current
	DESCRIPTION
	        "Controls the generation of VT RFI defects on the selected
		 interface.

		 Value		Description
		 on(1)          RFI is continually tramsmitted
		 off(2)         RFI is never transmitted
		 momentary(3)   RFI is transmitted for a short period of time.
		 auto(4)        RFI is generated according to the sonet specification"
	DEFVAL { auto }
	::= { foreSonetVTDiagnosticsEntry 3 }

foreSonetVtDiagnosticsAIS OBJECT-TYPE
        SYNTAX  INTEGER {
	        on(1),
		off(2),
		momentary(3),
		auto(4)
		}
	MAX-ACCESS  read-write
	STATUS  current
	DESCRIPTION
	        "Controls the generation of VT AIS on the selected
		 interface.

		 Value		Description
		 on(1)          AIS is continually tramsmitted
		 off(2)         AIS is never transmitted
		 momentary(3)   AIS is transmitted for a short period of time.
		 auto(4)        AIS is generated according to the sonet specification"
	DEFVAL { auto }
	::= { foreSonetVTDiagnosticsEntry 4 }

foreSonetVtDiagnosticsLOP OBJECT-TYPE
        SYNTAX  INTEGER {
	        on(1),
		off(2),
		momentary(3)
		}
	MAX-ACCESS  read-write
	STATUS  current
	DESCRIPTION
	        "Controls the generation of VT LOP on the selected
		 interface.

		 Value		Description
		 on(1)          LOP is continually tramsmitted
		 off(2)         LOP is never transmitted
		 momentary(3)   LOP is transmitted for a short period of time."
	DEFVAL { off }
	::= { foreSonetVTDiagnosticsEntry 5 }

foreSonetVtDiagnosticsLabel OBJECT-TYPE
        SYNTAX  INTEGER {
	        on(1),
		off(2)
		}
	MAX-ACCESS  read-write
	STATUS  current
	DESCRIPTION
	        "Controls the transmission of generated label values to
		 force PLM-V failures on the remote system.

		 Value		Description
		 on(1)          Use label value in foreSonetVtDiagnosticsLableValue
		 off(2)         Transmit label appropriate for VT type"
	DEFVAL { off }
	::= { foreSonetVTDiagnosticsEntry 6 }

foreSonetVtDiagnosticsLabelValue OBJECT-TYPE
	SYNTAX	INTEGER  {
		unequipped(0),
		equippednonspec(1),
		asynchronous(2),
		bitsynchronous(3),
		bytesynchronous(4)
	}
	MAX-ACCESS  read-write
	STATUS  current
	DESCRIPTION
	        "Selects the  label value to be transmitted in order to
		 force PLM-V failures on the remote system."
	DEFVAL { 1 }
	::= { foreSonetVTDiagnosticsEntry 7 }

foreSonetVtDiagnosticsREI OBJECT-TYPE
        SYNTAX  INTEGER {
	        on(1),
		off(2),
		auto(4)
		}
	MAX-ACCESS  read-write
	STATUS  current
	DESCRIPTION
	        "Controls the generation of VT REI on the selected
		 interface.  REI indicates to the far end that a BIP-2
		 error check failed.

		 Value		Description
		 on(1)          REI is continually tramsmitted
		 off(2)         REI is never transmitted
		 auto(4)        REI is transmitted according to the BIP-2"
	DEFVAL { auto }
	::= { foreSonetVTDiagnosticsEntry 8 }



-- Fore SONET Traps

foreSonetLOSDetected NOTIFICATION-TYPE
	OBJECTS { ifIndex, ifName, trapLogIndex }
	STATUS      current
	DESCRIPTION
		"This trap indicates that the specified SONET port is
		experiencing Loss Of Signal. Bellcore Document
		TA-NWT-000253 Section 6.3.1.1.1 states that... A SONET
		NE shall declare a LOS failure when the LOS defect
		persists for 2.5 (+- .5) seconds, or when a LOS defect
		is present and the criteria for LOF failure
		declaration have been met."
	::= { foreSonetMib 0 1 }

foreSonetLOSCleared NOTIFICATION-TYPE
	OBJECTS { ifIndex, ifName, trapLogIndex }
	STATUS      current
	DESCRIPTION
		"This trap indicates that the LOS condition identified
		by trap foreSonetLOSDetected has been cleared."
	::= { foreSonetMib 0 2 }

foreSonetPathLabelDetected NOTIFICATION-TYPE
	OBJECTS { ifIndex, ifName, trapLogIndex }
	STATUS      current
	DESCRIPTION
		"This trap indicates that the specified SONET port is
		receiving and errored C2 Path Label byte. Reference
		Bellcore Document TA-NWT-000253 Section 3.3.2.3 and
		6.3.1.1.8 the Path Label (C2) byte should have the
		value 0x13 or 0x01."
	::= { foreSonetMib 0 3 }

foreSonetPathLabelCleared NOTIFICATION-TYPE
	OBJECTS { ifIndex,  ifName, trapLogIndex }
	STATUS      current
	DESCRIPTION
		"This trap indicates that the Errored Path Label (C2)
		byte error condition signaled by the
		foreSonetPathLabelDetected trap has been cleared."
	::= { foreSonetMib 0 4 }

foreSonetLineAISDetected NOTIFICATION-TYPE
	OBJECTS { ifIndex, ifName, trapLogIndex }
	STATUS      current
	DESCRIPTION
		"This trap indicates that the specified SONET port is
		receiving a Line level Alarm Indication Signal from the
		far-end equipment."
	::= { foreSonetMib 0 5 }

foreSonetLineAISCleared NOTIFICATION-TYPE
	OBJECTS {  ifIndex, ifName, trapLogIndex }
	STATUS      current
	DESCRIPTION
		"This trap indicates that the Line AIS error condition
		signaled by the foreSonetLineAISDetected trap has been
		cleared."
	::= { foreSonetMib 0 6 }

foreSonetLOFDetected NOTIFICATION-TYPE
	OBJECTS { ifIndex, ifName, trapLogIndex }
	STATUS      current
	DESCRIPTION
		"This trap indicates that the specified SONET port is
		experiencing Loss Of Frame (LOF) failure. An LOF
		failure is declared when the LOF defect persists fore
		a period of 2.5 +/- 0.5 seconds, except when an LOS
		defect or failure is present."
	::= { foreSonetMib 0 7 }

foreSonetLOFCleared NOTIFICATION-TYPE
	OBJECTS { ifIndex, ifName, trapLogIndex }
	STATUS      current
	DESCRIPTION
		"This trap indicates that the LOF failure identified
		by trap foreSonetLOFDetected has been cleared. The LOF
		failure is cleared when the LOS failure is declared,
		or when the LOF defect is absent for 10 +/- 0.5
		seconds."
	::= { foreSonetMib 0 8 }

foreSonetLineRDIDetected NOTIFICATION-TYPE
	OBJECTS { ifIndex, ifName, trapLogIndex }
	STATUS      current
	DESCRIPTION
		"This trap indicates that the specified SONET port is
		experiencing Line Remote Defect Indication (LRDI). A
		Line RDI failure is declared when the incoming Line
		RDI defects lasts for 2.5 +/- 0.5 seconds."
	::= { foreSonetMib 0 9 }

foreSonetLineRDICleared NOTIFICATION-TYPE
	OBJECTS { ifIndex, ifName,  trapLogIndex }
	STATUS      current
	DESCRIPTION
		"This trap indicates that the Line RDI failure
		identified by trap foreSonetLineRDIDetected has been
		cleared.  The Line RDI failure is cleared when no Line
		RDI defects are detected for 10 +/- 0.5 seconds."
	::= { foreSonetMib 0 10 }

foreSonetPathAISDetected NOTIFICATION-TYPE
	OBJECTS { ifIndex, ifName, trapLogIndex }
	STATUS      current
	DESCRIPTION
		"This trap indicates that the specified SONET port is
		experiencing Path Alarm Inidication Signal (PAIS). A Path
		AIS failure is declared when the Path AIS defect
		persists for 2.5 +/- 0.5 seconds."
	::= { foreSonetMib 0 11 }

foreSonetPathAISCleared NOTIFICATION-TYPE
	OBJECTS { ifIndex,  ifName, trapLogIndex }
	STATUS      current
	DESCRIPTION
		"This trap indicates that the PathAIS failure
		identified by trap foreSonetPathAISDetected has been
		cleared.  A PAIS failure is cleared when the PAIS
		defect is absent for 10 +/- 0.5 seconds."
	::= { foreSonetMib 0 12 }

foreSonetPathLOPDetected NOTIFICATION-TYPE
	OBJECTS { ifIndex,  ifName, trapLogIndex }
	STATUS      current
	DESCRIPTION
		"This trap indicates that the specified SONET port is
		experiencing Loss Of Pointer (LOP). A LOP failure is
		declared when the LOP defect persists for a period of
		2.5 +/- 0.5 seconds."
	::= { foreSonetMib 0 13 }

foreSonetPathLOPCleared NOTIFICATION-TYPE
	OBJECTS { ifIndex,  ifName, trapLogIndex }
	STATUS      current
	DESCRIPTION
		"This trap indicates that the LOP failure identified
		by trap foreSonetLOPDetected has been cleared. A LOP
		failure is cleared when the LOP defect is absent for
		10 +/- 0.5 seconds."
	::= { foreSonetMib 0 14 }

foreSonetPathUNEQDetected NOTIFICATION-TYPE
	OBJECTS { ifIndex,  ifName, trapLogIndex }
	STATUS      current
	DESCRIPTION
		"This trap indicates that the specified SONET port is
		experiencing unequiped (UNEQ). A UNEQ failure is
		declared when the UNEQ defect persists for a period of
		2.5 +/- 0.5 seconds."
	::= { foreSonetMib 0 15 }

foreSonetPathUNEQCleared NOTIFICATION-TYPE
	OBJECTS { ifIndex, ifName, trapLogIndex }
	STATUS      current
	DESCRIPTION
		"This trap indicates that the UNEQ failure identified
		by trap foreSonetUNEQDetected has been cleared. A UNEQ
		failure is cleared when the UNEQ defect is absent for
		10 +/- 0.5 seconds."
	::= { foreSonetMib 0 16 }

foreSonetPathRDIDetected NOTIFICATION-TYPE
	OBJECTS { ifIndex, ifName, trapLogIndex }
	STATUS      current
	DESCRIPTION
		"This trap indicates that the specified SONET port is
		experiencing Path Remote Defect Indication (PRDI). A
		Path RDI failure is declared when the incoming Path
		RDI defects lasts for 2.5 +/- 0.5 seconds."
	::= { foreSonetMib 0 17 }

foreSonetPathRDICleared NOTIFICATION-TYPE
	OBJECTS { ifIndex,  ifName, trapLogIndex }
	STATUS      current
	DESCRIPTION
		"This trap indicates that the Path RDI failure
		identified by trap foreSonetPathRDIDetected has been
		cleared.  The Path RDI failure is cleared when no Path
		RDI defects are detected for 10 +/- 0.5 seconds."
	::= { foreSonetMib 0 18 }

foreSonetPathPDIDetected NOTIFICATION-TYPE
	OBJECTS { ifIndex,  ifName, trapLogIndex }
	STATUS      current
	DESCRIPTION
		"This trap indicates that the specified SONET path
		 is experiencing a PDI-P ( Path Defect Indication)
		 condition.  A PDI-P indication is signalled by 
		 a value in the C2 ( path label ) byte in the range
		 0xe0..0xfc."
	::= { foreSonetMib 0 19 }

foreSonetPathPDICleared NOTIFICATION-TYPE
	OBJECTS { ifIndex,  ifName, trapLogIndex }
	STATUS      current
	DESCRIPTION
		"This trap indicates that the PDI falure
		 identified by trap foreSonetPathPDIDetected
		 has been cleared."
	::= { foreSonetMib 0 20 }

foreSonetLineBIPDetected NOTIFICATION-TYPE
	OBJECTS { ifIndex, ifName, trapLogIndex }
	STATUS      current
	DESCRIPTION
		"This trap indicates that the specified SONET port is
		 experiencing Bit Interleaved Parity (BIP) errors. A
		 Line BIP failure is declared when the Line BIP defect
		 persists for a period of 2.5 +/- 0.5 seconds."
	::= { foreSonetMib 0 21 }

foreSonetLineBIPCleared NOTIFICATION-TYPE
	OBJECTS { ifIndex, ifName, trapLogIndex }
	STATUS      current
	DESCRIPTION
		"This trap indicates that the Line BIP failure identified
		 by trap asxSonetAtmLineBIPDetected has been cleared. A Line
		 BIP failure is cleared when the Line BIP defect is absent
		 for 10 +/- 0.5 seconds."
	::= { foreSonetMib 0 22 }

foreSonetVtAISDetected NOTIFICATION-TYPE
        OBJECTS { ifIndex, ifName, trapLogIndex }
	STATUS      current
        DESCRIPTION
                "This trap indicates that the specified Sonet virtual
		 tributary is receiving an AIS indication from the far
		 end.  An AIS-V failure is declared when the AIS-V defect
                 persists for 2.5 +/- 0.5 seconds."
	::= { foreSonetMib 0 23 }

foreSonetVtAISCleared NOTIFICATION-TYPE
        OBJECTS { ifIndex, ifName, trapLogIndex }
	STATUS      current
        DESCRIPTION
                "This trap indicates that the virtual tributary AIS
		 failure condition has been cleared.  An AIS-V failure
		 is cleared when the AIS-V defect is absent for
		 10 +/- 0.5 seconds."
	::= { foreSonetMib 0 24 }

foreSonetVtLOPDetected NOTIFICATION-TYPE
        OBJECTS { ifIndex, ifName, trapLogIndex }
	STATUS      current
        DESCRIPTION
                "This trap indicates that the specified virtual tributary
		 is receiving an LOP-V failure.  An LOP-V failure is declared
		 when an LOP-V defect persists for 2.5 +/- 0.5 seconds."
	::= { foreSonetMib 0 25 }

foreSonetVtLOPCleared NOTIFICATION-TYPE
        OBJECTS { ifIndex, ifName, trapLogIndex }
	STATUS      current
        DESCRIPTION
                "This trap indicates that the specified virtual tributary
		 is no longer experiencing loss-of-pointer failure.  An LOP-V
		 failure is cleared when the LOP-V defect is absent for 10
		 +/- 0.5 seconds"
	::= { foreSonetMib 0 26 }

foreSonetVtUNEQDetected NOTIFICATION-TYPE
        OBJECTS { ifIndex, ifName, trapLogIndex }
	STATUS      current
        DESCRIPTION
                "This trap indicates that the specified virtual tributary
		 is receiving an UNEQ virtual tributary. (V5 byte is 0 )."
	::= { foreSonetMib 0 27 }

foreSonetVtUNEQCleared NOTIFICATION-TYPE
        OBJECTS { ifIndex, ifName, trapLogIndex }
	STATUS      current
        DESCRIPTION
                "This trap indicates that the specified virtual tributary
		 is no longer receving an UNEQ virtual tributary."
	::= { foreSonetMib 0 28 }

foreSonetVtVILMDetected NOTIFICATION-TYPE
        OBJECTS { ifIndex, ifName, trapLogIndex }
	STATUS      current
        DESCRIPTION
                "This trap indicates that the specified virtual tributary
		 is experiencing a VT path label mismatch failure, PLM-V."
	::= { foreSonetMib 0 29 }

foreSonetVtVILMCleared NOTIFICATION-TYPE
        OBJECTS { ifIndex, ifName, trapLogIndex }
	STATUS      current
        DESCRIPTION
                "This trap indicates that the specified virtual tributary
		 is no longer experiencing a PLM-V failure."
	::= { foreSonetMib 0 30 }

foreSonetVtRDIDetected NOTIFICATION-TYPE
        OBJECTS { ifIndex, ifName, trapLogIndex }
	STATUS      current
        DESCRIPTION
                "This trap indicates that the specified virtual tributary
		is experiencing an RDI failure.  An RDI-V failure is declared
		after the interface receives RDI-V defects for 2.5 +/- 0.5
		seconds."
	::= { foreSonetMib 0 31 }

foreSonetVtRDICleared NOTIFICATION-TYPE
        OBJECTS { ifIndex, ifName, trapLogIndex }
	STATUS      current
        DESCRIPTION
                "This trap indicates that the specified virtual tributary
		is no longer experiencing an RDI failure.  An RDI-V failure
		is cleared after the interface receives no RDI-V defects for
		10 +/- 0.5 seconds."
	::= { foreSonetMib 0 32 }

foreSonetVtRFIDetected NOTIFICATION-TYPE
        OBJECTS { ifIndex, ifName, trapLogIndex }
	STATUS      current
        DESCRIPTION
                "This trap indicates that the specified virtual tributary
		 is experiencing an RFI-V failure.  An RFI-V failure is
		 declared within 5 milliseconds of the detection of an
		 incoming RFI-V indication."
	::= { foreSonetMib 0 33 }

foreSonetVtRFICleared NOTIFICATION-TYPE
        OBJECTS { ifIndex, ifName, trapLogIndex }
	STATUS      current
        DESCRIPTION
                "This trap indicates that the specified virtual tributary
		 is no longer experiencing an RFI-V failure.  An RFI-V failure
		 is cleared within 50 milliseconds of the removal of an
		 incoming RFI-V indication."
	::= { foreSonetMib 0 34 }

END
