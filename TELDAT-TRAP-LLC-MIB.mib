-- file automatically created


TELDAT-TRAP-LLC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


llcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LLC event subsystem."
    REVISION "201401200930Z"
    DESCRIPTION "Initial implementation"
        ::= { telEventTraps 103 }


llcEventsGroup	OBJECT IDENTIFIER	::= { llcTrapsMIB 1 }

llcNotifications	OBJECT IDENTIFIER	::= { llcTrapsMIB 2 }
llcNotificationsPrefix	OBJECT IDENTIFIER	::= { llcNotifications 0 }

llcEventObjects1 OBJECT-IDENTITY
    STATUS current
    DESCRIPTION
        "Event LLC.1
        LLC is sending a frame. Possible frame types are:
        SABME-C0 or SABME-C1 (Set Asynchronous Balanced Mode Extended),
        DM-R0 or DM-R1 (Disconnected Mode), DISC-C0 or DISC-C1 (Disconnect),
        RR-C0 or RR-C1 or RR-R0 or RR-R1 (Receiver Ready),
        RNR-C0 or RNR-C1 or RNR-R0 or RNR-R1 (Receiver Not Ready),
        REJ-C0 or REJ-C1 or REJ-R0 or REJ-R1 (Reject),
        UA-R0 or UA-R1 (Unnumbered Acknowledgement),
        FRMR-R0 or FRMR-R1 (Frame Reject), and
        I-C0 or I-C1 or I-R0 or I-R1 (Information Frame).
        The abbrevation suffixes are C0 (command, poll bit off),
        C1 (command, poll bit on), R0 (response, final bit off) and
        R1 (response, final bit on)."
    ::= { llcEventsGroup 1 }

llc1-frame-type OBJECT-TYPE
    SYNTAX DisplayString
    MAX-ACCESS accessible-for-notify
    STATUS current
    DESCRIPTION
        "Parameter 'frame-type' in event LLC.1"
    ::= { llcEventObjects1 1 }

llc1-src-mac OBJECT-TYPE
    SYNTAX DisplayString
    MAX-ACCESS accessible-for-notify
    STATUS current
    DESCRIPTION
        "Parameter 'src-mac' in event LLC.1"
    ::= { llcEventObjects1 2 }

llc1-dst-mac OBJECT-TYPE
    SYNTAX DisplayString
    MAX-ACCESS accessible-for-notify
    STATUS current
    DESCRIPTION
        "Parameter 'dst-mac' in event LLC.1"
    ::= { llcEventObjects1 3 }

llc1-rif OBJECT-TYPE
    SYNTAX DisplayString
    MAX-ACCESS accessible-for-notify
    STATUS current
    DESCRIPTION
        "Parameter 'rif' in event LLC.1"
    ::= { llcEventObjects1 4 }

llc1-src-sap OBJECT-TYPE
    SYNTAX Integer32
    MAX-ACCESS accessible-for-notify
    STATUS current
    DESCRIPTION
        "Parameter 'src-sap' in event LLC.1"
    ::= { llcEventObjects1 5 }

llc1-dst-sap OBJECT-TYPE
    SYNTAX Integer32
    MAX-ACCESS accessible-for-notify
    STATUS current
    DESCRIPTION
        "Parameter 'dst-sap' in event LLC.1"
    ::= { llcEventObjects1 6 }

llc1-interface OBJECT-TYPE
    SYNTAX DisplayString
    MAX-ACCESS accessible-for-notify
    STATUS current
    DESCRIPTION
        "Parameter 'interface' in event LLC.1"
    ::= { llcEventObjects1 7 }

llcEventObjects2 OBJECT-IDENTITY
    STATUS current
    DESCRIPTION
        "Event LLC.2
        An event occurred on an llc2 connection. The LLC2 FSM (Finite State
        Machine) has been called to process the event.
        The LLC2 connection is uniquely identified by the combination
        destination MAC address, source MAC address, destination sap and
        source sap on a particular interface.
        The possible events are:
        SET-ABME (user request to connect to remote),
        SET-ADM (user request to disconnect from remote),
        SEND-BTU (user request to send data),
        FLOW-REQ-ON (user request to turn off local busy condition),
        FLOW-REQ-OFF (user request to turn on local busy condition),
        T1-EXP (T1 timer expiration), T2-EXP (T2 timer expiration),
        Ti-EXP (Ti timer epiration), OS-I-C0 or OS-I-C1 or OS-I-R0 or OS-I-R1
        (Ns on I-frame is out of sequence), I-C0 or I-C1 or I-R0 or I-R1
        (valid I-frame received), RR-C0 or RR-C1 or RR-R0 or RR-R1
        (RR frame received), RNR-C0 or RNR-C1 or RNR-R0 or RNR-R1
        (RNR frame received), REJ-C0 or REJ-C1 or REJ-R0 or REJ-R1
        (REJ frame received), UA-R0 or UA-R1 (UA frame received),
        DISC-C0 or DISC-C1 (DISC frame received), DM-R0 or DM-R1
        (DM frame received), FRMR-R0 or FRMR-R1 (FRMR  frame received),
        BAD-FRAME-0 or BAD-FRAME-1 (received frame will generate FRMR),
        SABME-C0 or SABME-C1 (SABME frame received), and
        SEND-I-POLL (Sending I frame with Poll bit on).
        The abbrevation suffixes are C0 (command, poll bit off),
        C1 (command, poll bit on), R0 (response, final bit off) and
        R1 (response, final bit on)."
    ::= { llcEventsGroup 2 }

llc2-llc-event OBJECT-TYPE
    SYNTAX DisplayString
    MAX-ACCESS accessible-for-notify
    STATUS current
    DESCRIPTION
        "Parameter 'llc-event' in event LLC.2"
    ::= { llcEventObjects2 1 }

llc2-llc-state OBJECT-TYPE
    SYNTAX DisplayString
    MAX-ACCESS accessible-for-notify
    STATUS current
    DESCRIPTION
        "Parameter 'llc-state' in event LLC.2"
    ::= { llcEventObjects2 2 }

llc2-llc2-connection OBJECT-TYPE
    SYNTAX DisplayString
    MAX-ACCESS accessible-for-notify
    STATUS current
    DESCRIPTION
        "Parameter 'llc2-connection' in event LLC.2"
    ::= { llcEventObjects2 3 }

llc2-llc2-sap OBJECT-TYPE
    SYNTAX Integer32
    MAX-ACCESS accessible-for-notify
    STATUS current
    DESCRIPTION
        "Parameter 'llc2-sap' in event LLC.2"
    ::= { llcEventObjects2 4 }

llc2-interface OBJECT-TYPE
    SYNTAX DisplayString
    MAX-ACCESS accessible-for-notify
    STATUS current
    DESCRIPTION
        "Parameter 'interface' in event LLC.2"
    ::= { llcEventObjects2 5 }

llcEventObjects3 OBJECT-IDENTITY
    STATUS current
    DESCRIPTION
        "Event LLC.3
        There is LLC2 state change.
        The possible states are:
        DISCONNECTED (initial state),
        LINK-OPENING (link establishment in progress),
        DISCONNECTING (DISC sent, awaiting DM),
        FRMR-SENT (frmr sent),
        LINK-OPENED (normal state),
        LOCAL-BUSY (local is busy),
        REJECTION (remote sent an out of sequence frame),
        CHECKPOINTING (poll sent, awaiting response sending of data supended),
        CKPT-LB (combination state),
        CKPT-REJ (combination state),
        RESETTING (awaiting user response to reset),
        REMOTE-BUSY (remote is busy),
        LB-RB (combination state),
        REJ-LB (combination state),
        REJ-RB (combination state),
        CKPT-REJ-LB (combination state),
        CKPT-CLR (clearing from CKPT-LB state),
        CKPT-REJ-CLR (clearing from CKPT-REJ-LB state),
        REJ-LB-RB (combination state),
        FRMR-RECEIVED (received frmr).
        The abbreviations above are: CKPT=CHECKPOINTING, CLR=CLEARING,
        LB=LOCAL BUSY, RB=REMOTE BUSY, and REJ=REJECTION."
    ::= { llcEventsGroup 3 }

llc3-llc-old-state OBJECT-TYPE
    SYNTAX DisplayString
    MAX-ACCESS accessible-for-notify
    STATUS current
    DESCRIPTION
        "Parameter 'llc-old-state' in event LLC.3"
    ::= { llcEventObjects3 1 }

llc3-llc-new-state OBJECT-TYPE
    SYNTAX DisplayString
    MAX-ACCESS accessible-for-notify
    STATUS current
    DESCRIPTION
        "Parameter 'llc-new-state' in event LLC.3"
    ::= { llcEventObjects3 2 }

llc3-llc2-connection OBJECT-TYPE
    SYNTAX DisplayString
    MAX-ACCESS accessible-for-notify
    STATUS current
    DESCRIPTION
        "Parameter 'llc2-connection' in event LLC.3"
    ::= { llcEventObjects3 3 }

llc3-llc2-sap OBJECT-TYPE
    SYNTAX Integer32
    MAX-ACCESS accessible-for-notify
    STATUS current
    DESCRIPTION
        "Parameter 'llc2-sap' in event LLC.3"
    ::= { llcEventObjects3 4 }

llc3-interface OBJECT-TYPE
    SYNTAX DisplayString
    MAX-ACCESS accessible-for-notify
    STATUS current
    DESCRIPTION
        "Parameter 'interface' in event LLC.3"
    ::= { llcEventObjects3 5 }

llcEventObjects4 OBJECT-IDENTITY
    STATUS current
    DESCRIPTION
        "Event LLC.4
        LLC2 event upcall is occuring.
        Some of the arguments on the upcall are shown.
        User Cookie is meaningful to the router software running over
        the LLC subsystem.
        Event reason sometimes further specifies the event.
        The possible upcall events are:
        CONN-IND (cookie=session, reason=none),
        CONN-IND-PASS (cookie=sap, reason=none),
        CONN-CONFIRM (cookie=session, reason=none),
        DISC-IND (cookie=session, possible reasons: local term (disconnecting),
        remote term, conn refused, local term (disconnected)),
        RESET-IND (cookie=session, possible reasons: local reset,
        remote reset, frmr rcvd, frmr sent),
        RESET-CONF (cookie=session, reason=none),
        FLOW-IND (cookie=session, possible reasons: flow off, flow on), and
        DISC-CONFIRM (cookie=session, reason=none)."
    ::= { llcEventsGroup 4 }

llc4-user-event OBJECT-TYPE
    SYNTAX DisplayString
    MAX-ACCESS accessible-for-notify
    STATUS current
    DESCRIPTION
        "Parameter 'user-event' in event LLC.4"
    ::= { llcEventObjects4 1 }

llc4-user-value OBJECT-TYPE
    SYNTAX Integer32
    MAX-ACCESS accessible-for-notify
    STATUS current
    DESCRIPTION
        "Parameter 'user-value' in event LLC.4"
    ::= { llcEventObjects4 2 }

llc4-event-reason OBJECT-TYPE
    SYNTAX DisplayString
    MAX-ACCESS accessible-for-notify
    STATUS current
    DESCRIPTION
        "Parameter 'event-reason' in event LLC.4"
    ::= { llcEventObjects4 3 }

llc4-llc2-connection OBJECT-TYPE
    SYNTAX DisplayString
    MAX-ACCESS accessible-for-notify
    STATUS current
    DESCRIPTION
        "Parameter 'llc2-connection' in event LLC.4"
    ::= { llcEventObjects4 4 }

llc4-llc2-sap OBJECT-TYPE
    SYNTAX Integer32
    MAX-ACCESS accessible-for-notify
    STATUS current
    DESCRIPTION
        "Parameter 'llc2-sap' in event LLC.4"
    ::= { llcEventObjects4 5 }

llc4-interface OBJECT-TYPE
    SYNTAX DisplayString
    MAX-ACCESS accessible-for-notify
    STATUS current
    DESCRIPTION
        "Parameter 'interface' in event LLC.4"
    ::= { llcEventObjects4 6 }

llcEventObjects5 OBJECT-IDENTITY
    STATUS current
    DESCRIPTION
        "Event LLC.5
        A sap-releated LLC user-primitive was called.
        The possible SAP primitives are:
        OPEN-SAP,
        CLOSE-SAP,
        CLOSE-SAP-FORCED,
        MODIFY-SAP,
        OPEN-STATION, and
        UNITDATA."
    ::= { llcEventsGroup 5 }

llc5-user-primitive OBJECT-TYPE
    SYNTAX DisplayString
    MAX-ACCESS accessible-for-notify
    STATUS current
    DESCRIPTION
        "Parameter 'user-primitive' in event LLC.5"
    ::= { llcEventObjects5 1 }

llc5-SAP-value OBJECT-TYPE
    SYNTAX Integer32
    MAX-ACCESS accessible-for-notify
    STATUS current
    DESCRIPTION
        "Parameter 'SAP-value' in event LLC.5"
    ::= { llcEventObjects5 2 }

llc5-interface OBJECT-TYPE
    SYNTAX DisplayString
    MAX-ACCESS accessible-for-notify
    STATUS current
    DESCRIPTION
        "Parameter 'interface' in event LLC.5"
    ::= { llcEventObjects5 3 }

llcEventObjects6 OBJECT-IDENTITY
    STATUS current
    DESCRIPTION
        "Event LLC.6
        A llc2 connection non-data user-primitive was called.
        The possible primitives are:
        CLOSE-STATION,
        CLOSE-STATION-FORCED,
        CONNECT-REQUEST,
        CONNECT-RESPONSE,
        DISCONNECT-REQUEST,
        RESET-REQUEST,
        RESET-RESPONSE,
        FLOW-REQ."
    ::= { llcEventsGroup 6 }

llc6-user-primitive OBJECT-TYPE
    SYNTAX DisplayString
    MAX-ACCESS accessible-for-notify
    STATUS current
    DESCRIPTION
        "Parameter 'user-primitive' in event LLC.6"
    ::= { llcEventObjects6 1 }

llc6-llc2-connection OBJECT-TYPE
    SYNTAX DisplayString
    MAX-ACCESS accessible-for-notify
    STATUS current
    DESCRIPTION
        "Parameter 'llc2-connection' in event LLC.6"
    ::= { llcEventObjects6 2 }

llc6-llc2-sap OBJECT-TYPE
    SYNTAX Integer32
    MAX-ACCESS accessible-for-notify
    STATUS current
    DESCRIPTION
        "Parameter 'llc2-sap' in event LLC.6"
    ::= { llcEventObjects6 3 }

llc6-interface OBJECT-TYPE
    SYNTAX DisplayString
    MAX-ACCESS accessible-for-notify
    STATUS current
    DESCRIPTION
        "Parameter 'interface' in event LLC.6"
    ::= { llcEventObjects6 4 }

llcEventObjects7 OBJECT-IDENTITY
    STATUS current
    DESCRIPTION
        "Event LLC.7
        A DATA-REQUEST data primitive was called. DATA-REQUEST passes the data
        in buffer memory."
    ::= { llcEventsGroup 7 }

llc7-llc2-connection OBJECT-TYPE
    SYNTAX DisplayString
    MAX-ACCESS accessible-for-notify
    STATUS current
    DESCRIPTION
        "Parameter 'llc2-connection' in event LLC.7"
    ::= { llcEventObjects7 1 }

llc7-llc2-sap OBJECT-TYPE
    SYNTAX Integer32
    MAX-ACCESS accessible-for-notify
    STATUS current
    DESCRIPTION
        "Parameter 'llc2-sap' in event LLC.7"
    ::= { llcEventObjects7 2 }

llc7-interface OBJECT-TYPE
    SYNTAX DisplayString
    MAX-ACCESS accessible-for-notify
    STATUS current
    DESCRIPTION
        "Parameter 'interface' in event LLC.7"
    ::= { llcEventObjects7 3 }

llcEventObjects8 OBJECT-IDENTITY
    STATUS current
    DESCRIPTION
        "Event LLC.8
        A DATA-LOCAL data primitive was called. DATA-LOCAL passes the data
        in data memory."
    ::= { llcEventsGroup 8 }

llc8-llc2-connection OBJECT-TYPE
    SYNTAX DisplayString
    MAX-ACCESS accessible-for-notify
    STATUS current
    DESCRIPTION
        "Parameter 'llc2-connection' in event LLC.8"
    ::= { llcEventObjects8 1 }

llc8-llc2-sap OBJECT-TYPE
    SYNTAX Integer32
    MAX-ACCESS accessible-for-notify
    STATUS current
    DESCRIPTION
        "Parameter 'llc2-sap' in event LLC.8"
    ::= { llcEventObjects8 2 }

llc8-interface OBJECT-TYPE
    SYNTAX DisplayString
    MAX-ACCESS accessible-for-notify
    STATUS current
    DESCRIPTION
        "Parameter 'interface' in event LLC.8"
    ::= { llcEventObjects8 3 }

llcEventObjects9 OBJECT-IDENTITY
    STATUS current
    DESCRIPTION
        "Event LLC.9
        A UNITDATA llc1 data primitive was called."
    ::= { llcEventsGroup 9 }

llc9-SAP-value OBJECT-TYPE
    SYNTAX Integer32
    MAX-ACCESS accessible-for-notify
    STATUS current
    DESCRIPTION
        "Parameter 'SAP-value' in event LLC.9"
    ::= { llcEventObjects9 1 }

llc9-interface OBJECT-TYPE
    SYNTAX DisplayString
    MAX-ACCESS accessible-for-notify
    STATUS current
    DESCRIPTION
        "Parameter 'interface' in event LLC.9"
    ::= { llcEventObjects9 2 }

llcEventObjects10 OBJECT-IDENTITY
    STATUS current
    DESCRIPTION
        "Event LLC.10
        The oubound queue has grown grossly large. The llc2 connection is being
        automatically terminated."
    ::= { llcEventsGroup 10 }

llc10-llc2-connection OBJECT-TYPE
    SYNTAX DisplayString
    MAX-ACCESS accessible-for-notify
    STATUS current
    DESCRIPTION
        "Parameter 'llc2-connection' in event LLC.10"
    ::= { llcEventObjects10 1 }

llc10-llc2-sap OBJECT-TYPE
    SYNTAX Integer32
    MAX-ACCESS accessible-for-notify
    STATUS current
    DESCRIPTION
        "Parameter 'llc2-sap' in event LLC.10"
    ::= { llcEventObjects10 2 }

llc10-interface OBJECT-TYPE
    SYNTAX DisplayString
    MAX-ACCESS accessible-for-notify
    STATUS current
    DESCRIPTION
        "Parameter 'interface' in event LLC.10"
    ::= { llcEventObjects10 3 }

llcEventObjects11 OBJECT-IDENTITY
    STATUS current
    DESCRIPTION
        "Event LLC.11
        No buffer available to duplicate I-frame."
    ::= { llcEventsGroup 11 }

llc11-llc2-connection OBJECT-TYPE
    SYNTAX DisplayString
    MAX-ACCESS accessible-for-notify
    STATUS current
    DESCRIPTION
        "Parameter 'llc2-connection' in event LLC.11"
    ::= { llcEventObjects11 1 }

llc11-llc2-sap OBJECT-TYPE
    SYNTAX Integer32
    MAX-ACCESS accessible-for-notify
    STATUS current
    DESCRIPTION
        "Parameter 'llc2-sap' in event LLC.11"
    ::= { llcEventObjects11 2 }

llc11-interface OBJECT-TYPE
    SYNTAX DisplayString
    MAX-ACCESS accessible-for-notify
    STATUS current
    DESCRIPTION
        "Parameter 'interface' in event LLC.11"
    ::= { llcEventObjects11 3 }

llcEventObjects12 OBJECT-IDENTITY
    STATUS current
    DESCRIPTION
        "Event LLC.12
        No memory to duplicate I-frame."
    ::= { llcEventsGroup 12 }

llc12-llc2-connection OBJECT-TYPE
    SYNTAX DisplayString
    MAX-ACCESS accessible-for-notify
    STATUS current
    DESCRIPTION
        "Parameter 'llc2-connection' in event LLC.12"
    ::= { llcEventObjects12 1 }

llc12-llc2-sap OBJECT-TYPE
    SYNTAX Integer32
    MAX-ACCESS accessible-for-notify
    STATUS current
    DESCRIPTION
        "Parameter 'llc2-sap' in event LLC.12"
    ::= { llcEventObjects12 2 }

llc12-interface OBJECT-TYPE
    SYNTAX DisplayString
    MAX-ACCESS accessible-for-notify
    STATUS current
    DESCRIPTION
        "Parameter 'interface' in event LLC.12"
    ::= { llcEventObjects12 3 }

llcEventObjects13 OBJECT-IDENTITY
    STATUS current
    DESCRIPTION
        "Event LLC.13
        A buffer could not be obtained to to build an LLC Supervisory or
        Unnumbered frame. No loss of data integrity has occurred yet, but
        unless buffers for this purpose become available within a few seconds,
        the other end of the LLC2 connection will most likely terminate
        this LLC connection as part of the normal LLC2 protocol."
    ::= { llcEventsGroup 13 }

llc13-llc2-connection OBJECT-TYPE
    SYNTAX DisplayString
    MAX-ACCESS accessible-for-notify
    STATUS current
    DESCRIPTION
        "Parameter 'llc2-connection' in event LLC.13"
    ::= { llcEventObjects13 1 }

llc13-llc2-sap OBJECT-TYPE
    SYNTAX Integer32
    MAX-ACCESS accessible-for-notify
    STATUS current
    DESCRIPTION
        "Parameter 'llc2-sap' in event LLC.13"
    ::= { llcEventObjects13 2 }

llc13-interface OBJECT-TYPE
    SYNTAX DisplayString
    MAX-ACCESS accessible-for-notify
    STATUS current
    DESCRIPTION
        "Parameter 'interface' in event LLC.13"
    ::= { llcEventObjects13 3 }

llcEventObjects14 OBJECT-IDENTITY
    STATUS current
    DESCRIPTION
        "Event LLC.14
        The frame type the LLC is trying to build is invalid."
    ::= { llcEventsGroup 14 }

llc14-llc2-connection OBJECT-TYPE
    SYNTAX DisplayString
    MAX-ACCESS accessible-for-notify
    STATUS current
    DESCRIPTION
        "Parameter 'llc2-connection' in event LLC.14"
    ::= { llcEventObjects14 1 }

llc14-llc2-sap OBJECT-TYPE
    SYNTAX Integer32
    MAX-ACCESS accessible-for-notify
    STATUS current
    DESCRIPTION
        "Parameter 'llc2-sap' in event LLC.14"
    ::= { llcEventObjects14 2 }

llc14-interface OBJECT-TYPE
    SYNTAX DisplayString
    MAX-ACCESS accessible-for-notify
    STATUS current
    DESCRIPTION
        "Parameter 'interface' in event LLC.14"
    ::= { llcEventObjects14 3 }

llcEventObjects15 OBJECT-IDENTITY
    STATUS current
    DESCRIPTION
        "Event LLC.15
        The LLC2 Finite State Machine (FSM) was called with an event that was
        out of range."
    ::= { llcEventsGroup 15 }

llc15-event-code-number OBJECT-TYPE
    SYNTAX Integer32
    MAX-ACCESS accessible-for-notify
    STATUS current
    DESCRIPTION
        "Parameter 'event-code-number' in event LLC.15"
    ::= { llcEventObjects15 1 }

llcEventObjects16 OBJECT-IDENTITY
    STATUS current
    DESCRIPTION
        "Event LLC.16
        An OPEN SAP operation was tried on a network type that LLC does not
        support. Network types Token-Ring, Ethernet, and FDDI are supported."
    ::= { llcEventsGroup 16 }

llc16-network-type OBJECT-TYPE
    SYNTAX Integer32
    MAX-ACCESS accessible-for-notify
    STATUS current
    DESCRIPTION
        "Parameter 'network-type' in event LLC.16"
    ::= { llcEventObjects16 1 }

llc16-interface OBJECT-TYPE
    SYNTAX DisplayString
    MAX-ACCESS accessible-for-notify
    STATUS current
    DESCRIPTION
        "Parameter 'interface' in event LLC.16"
    ::= { llcEventObjects16 2 }

llcEventObjects17 OBJECT-IDENTITY
    STATUS current
    DESCRIPTION
        "Event LLC.17
        A OPEN SAP operation was tried on a sap that has already been opened."
    ::= { llcEventsGroup 17 }

llc17-SAP-value OBJECT-TYPE
    SYNTAX Integer32
    MAX-ACCESS accessible-for-notify
    STATUS current
    DESCRIPTION
        "Parameter 'SAP-value' in event LLC.17"
    ::= { llcEventObjects17 1 }

llc17-interface OBJECT-TYPE
    SYNTAX DisplayString
    MAX-ACCESS accessible-for-notify
    STATUS current
    DESCRIPTION
        "Parameter 'interface' in event LLC.17"
    ::= { llcEventObjects17 2 }

llcEventObjects18 OBJECT-IDENTITY
    STATUS current
    DESCRIPTION
        "Event LLC.18
        Unable to allocate memory for SAP control block."
    ::= { llcEventsGroup 18 }

llc18-interface OBJECT-TYPE
    SYNTAX DisplayString
    MAX-ACCESS accessible-for-notify
    STATUS current
    DESCRIPTION
        "Parameter 'interface' in event LLC.18"
    ::= { llcEventObjects18 1 }

llcEventObjects19 OBJECT-IDENTITY
    STATUS current
    DESCRIPTION
        "Event LLC.19
        Unable to allocate memory for station control block."
    ::= { llcEventsGroup 19 }

llc19-interface OBJECT-TYPE
    SYNTAX DisplayString
    MAX-ACCESS accessible-for-notify
    STATUS current
    DESCRIPTION
        "Parameter 'interface' in event LLC.19"
    ::= { llcEventObjects19 1 }

llcEventObjects20 OBJECT-IDENTITY
    STATUS current
    DESCRIPTION
        "Event LLC.20
        UI frame refused by the local application within the router."
    ::= { llcEventsGroup 20 }

llc20-llc2-connection OBJECT-TYPE
    SYNTAX DisplayString
    MAX-ACCESS accessible-for-notify
    STATUS current
    DESCRIPTION
        "Parameter 'llc2-connection' in event LLC.20"
    ::= { llcEventObjects20 1 }

llc20-llc2-sap OBJECT-TYPE
    SYNTAX Integer32
    MAX-ACCESS accessible-for-notify
    STATUS current
    DESCRIPTION
        "Parameter 'llc2-sap' in event LLC.20"
    ::= { llcEventObjects20 2 }

llc20-interface OBJECT-TYPE
    SYNTAX DisplayString
    MAX-ACCESS accessible-for-notify
    STATUS current
    DESCRIPTION
        "Parameter 'interface' in event LLC.20"
    ::= { llcEventObjects20 3 }

llcEventObjects21 OBJECT-IDENTITY
    STATUS current
    DESCRIPTION
        "Event LLC.21
        TEST frame refused by the local application within the router.
        The frame is passed on to the bridge code, etc."
    ::= { llcEventsGroup 21 }

llc21-llc2-connection OBJECT-TYPE
    SYNTAX DisplayString
    MAX-ACCESS accessible-for-notify
    STATUS current
    DESCRIPTION
        "Parameter 'llc2-connection' in event LLC.21"
    ::= { llcEventObjects21 1 }

llc21-llc2-sap OBJECT-TYPE
    SYNTAX Integer32
    MAX-ACCESS accessible-for-notify
    STATUS current
    DESCRIPTION
        "Parameter 'llc2-sap' in event LLC.21"
    ::= { llcEventObjects21 2 }

llc21-interface OBJECT-TYPE
    SYNTAX DisplayString
    MAX-ACCESS accessible-for-notify
    STATUS current
    DESCRIPTION
        "Parameter 'interface' in event LLC.21"
    ::= { llcEventObjects21 3 }

llcEventObjects22 OBJECT-IDENTITY
    STATUS current
    DESCRIPTION
        "Event LLC.22
        XID frame refused by the local application within the router.
        The frame is passed on to the bridge code, etc."
    ::= { llcEventsGroup 22 }

llc22-llc2-connection OBJECT-TYPE
    SYNTAX DisplayString
    MAX-ACCESS accessible-for-notify
    STATUS current
    DESCRIPTION
        "Parameter 'llc2-connection' in event LLC.22"
    ::= { llcEventObjects22 1 }

llc22-llc2-sap OBJECT-TYPE
    SYNTAX Integer32
    MAX-ACCESS accessible-for-notify
    STATUS current
    DESCRIPTION
        "Parameter 'llc2-sap' in event LLC.22"
    ::= { llcEventObjects22 2 }

llc22-interface OBJECT-TYPE
    SYNTAX DisplayString
    MAX-ACCESS accessible-for-notify
    STATUS current
    DESCRIPTION
        "Parameter 'interface' in event LLC.22"
    ::= { llcEventObjects22 3 }

llcEventObjects23 OBJECT-IDENTITY
    STATUS current
    DESCRIPTION
        "Event LLC.23
        LLC makes an upcall providing the LLC with a unitdata frame.
        The possible unitdata frames are:
        TEST-C0 or TEST-C1 or TEST-R0 or TEST-R1 (TEST frame),
        XID-C0 or XID-C1 or XID-R0 or XID-R1 (Exchange Identification frame),
        UI-C0 or UI-R0 (Unnumbered Information).
        The abbrevation suffixes are C0 (command, poll bit off),
        C1 (command, poll bit on), R0 (response, final bit off) and
        R1 (response, final bit on)."
    ::= { llcEventsGroup 23 }

llc23-frame-type OBJECT-TYPE
    SYNTAX DisplayString
    MAX-ACCESS accessible-for-notify
    STATUS current
    DESCRIPTION
        "Parameter 'frame-type' in event LLC.23"
    ::= { llcEventObjects23 1 }

llc23-src-mac OBJECT-TYPE
    SYNTAX DisplayString
    MAX-ACCESS accessible-for-notify
    STATUS current
    DESCRIPTION
        "Parameter 'src-mac' in event LLC.23"
    ::= { llcEventObjects23 2 }

llc23-dst-mac OBJECT-TYPE
    SYNTAX DisplayString
    MAX-ACCESS accessible-for-notify
    STATUS current
    DESCRIPTION
        "Parameter 'dst-mac' in event LLC.23"
    ::= { llcEventObjects23 3 }

llc23-rif OBJECT-TYPE
    SYNTAX DisplayString
    MAX-ACCESS accessible-for-notify
    STATUS current
    DESCRIPTION
        "Parameter 'rif' in event LLC.23"
    ::= { llcEventObjects23 4 }

llc23-src-sap OBJECT-TYPE
    SYNTAX Integer32
    MAX-ACCESS accessible-for-notify
    STATUS current
    DESCRIPTION
        "Parameter 'src-sap' in event LLC.23"
    ::= { llcEventObjects23 5 }

llc23-dst-sap OBJECT-TYPE
    SYNTAX Integer32
    MAX-ACCESS accessible-for-notify
    STATUS current
    DESCRIPTION
        "Parameter 'dst-sap' in event LLC.23"
    ::= { llcEventObjects23 6 }

llc23-interface OBJECT-TYPE
    SYNTAX DisplayString
    MAX-ACCESS accessible-for-notify
    STATUS current
    DESCRIPTION
        "Parameter 'interface' in event LLC.23"
    ::= { llcEventObjects23 7 }

llcEventObjects24 OBJECT-IDENTITY
    STATUS current
    DESCRIPTION
        "Event LLC.24
        The sending of an LLC2 related outbound frame failed.
        The reason-code is the internal error code for the failure."
    ::= { llcEventsGroup 24 }

llc24-reason-code OBJECT-TYPE
    SYNTAX Integer32
    MAX-ACCESS accessible-for-notify
    STATUS current
    DESCRIPTION
        "Parameter 'reason-code' in event LLC.24"
    ::= { llcEventObjects24 1 }

llc24-llc2-connection OBJECT-TYPE
    SYNTAX DisplayString
    MAX-ACCESS accessible-for-notify
    STATUS current
    DESCRIPTION
        "Parameter 'llc2-connection' in event LLC.24"
    ::= { llcEventObjects24 2 }

llc24-llc2-sap OBJECT-TYPE
    SYNTAX Integer32
    MAX-ACCESS accessible-for-notify
    STATUS current
    DESCRIPTION
        "Parameter 'llc2-sap' in event LLC.24"
    ::= { llcEventObjects24 3 }

llc24-interface-name OBJECT-TYPE
    SYNTAX DisplayString
    MAX-ACCESS accessible-for-notify
    STATUS current
    DESCRIPTION
        "Parameter 'interface-name' in event LLC.24"
    ::= { llcEventObjects24 4 }

llcEventObjects25 OBJECT-IDENTITY
    STATUS current
    DESCRIPTION
        "Event LLC.25
        The sending of the user's UNITDATA or an LLC-generated XID or TEST
        response outbound frame failed.
        The possible frame test are:
        TEST-C0 or TEST-C1 or TEST-R0 or TEST-R1 (TEST frame),
        XID-C0 or XID-C1 or XID-R0 or XID-R1 (Exchange Identification frame),
        UI-C0 or UI-R0 (Unnumbered Information frame) and
        unexpected (not one of the above types).
        The abbrevation suffixes are C0 (command, poll bit off),
        C1 (command, poll bit on),
        R0 (response, final bit off), and R1 (response, final bit on)."
    ::= { llcEventsGroup 25 }

llc25-frame-type OBJECT-TYPE
    SYNTAX DisplayString
    MAX-ACCESS accessible-for-notify
    STATUS current
    DESCRIPTION
        "Parameter 'frame-type' in event LLC.25"
    ::= { llcEventObjects25 1 }

llc25-reason-code OBJECT-TYPE
    SYNTAX Integer32
    MAX-ACCESS accessible-for-notify
    STATUS current
    DESCRIPTION
        "Parameter 'reason-code' in event LLC.25"
    ::= { llcEventObjects25 2 }

llc25-llc2-connection OBJECT-TYPE
    SYNTAX DisplayString
    MAX-ACCESS accessible-for-notify
    STATUS current
    DESCRIPTION
        "Parameter 'llc2-connection' in event LLC.25"
    ::= { llcEventObjects25 3 }

llc25-llc2-sap OBJECT-TYPE
    SYNTAX Integer32
    MAX-ACCESS accessible-for-notify
    STATUS current
    DESCRIPTION
        "Parameter 'llc2-sap' in event LLC.25"
    ::= { llcEventObjects25 4 }

llc25-interface OBJECT-TYPE
    SYNTAX DisplayString
    MAX-ACCESS accessible-for-notify
    STATUS current
    DESCRIPTION
        "Parameter 'interface' in event LLC.25"
    ::= { llcEventObjects25 5 }

llcEventObjects26 OBJECT-IDENTITY
    STATUS current
    DESCRIPTION
        "Event LLC.26
        Unable to allocate memory for an LLC-CONF-BLOCK at initialization time.
        LLC configuration defaults are used."
    ::= { llcEventsGroup 26 }

llc26-interface OBJECT-TYPE
    SYNTAX DisplayString
    MAX-ACCESS accessible-for-notify
    STATUS current
    DESCRIPTION
        "Parameter 'interface' in event LLC.26"
    ::= { llcEventObjects26 1 }

llcEventObjects27 OBJECT-IDENTITY
    STATUS current
    DESCRIPTION
        "Event LLC.27
        LLC Configuration record read for this network. This only occurs
        at initialization time. The values in the LLC configuration record
        are used as default value on the interface."
    ::= { llcEventsGroup 27 }

llc27-interface OBJECT-TYPE
    SYNTAX DisplayString
    MAX-ACCESS accessible-for-notify
    STATUS current
    DESCRIPTION
        "Parameter 'interface' in event LLC.27"
    ::= { llcEventObjects27 1 }

llcEventObjects28 OBJECT-IDENTITY
    STATUS current
    DESCRIPTION
        "Event LLC.28
        access-priority, on an interface that is not a token ring must be
        zero because it is not used."
    ::= { llcEventsGroup 28 }

llc28-access-priority OBJECT-TYPE
    SYNTAX Integer32
    MAX-ACCESS accessible-for-notify
    STATUS current
    DESCRIPTION
        "Parameter 'access-priority' in event LLC.28"
    ::= { llcEventObjects28 1 }

llc28-interface OBJECT-TYPE
    SYNTAX DisplayString
    MAX-ACCESS accessible-for-notify
    STATUS current
    DESCRIPTION
        "Parameter 'interface' in event LLC.28"
    ::= { llcEventObjects28 2 }

llcEventObjects29 OBJECT-IDENTITY
    STATUS current
    DESCRIPTION
        "Event LLC.29
        The access priority is greater than 7. A default of 0 is used."
    ::= { llcEventsGroup 29 }

llc29-access-priority OBJECT-TYPE
    SYNTAX Integer32
    MAX-ACCESS accessible-for-notify
    STATUS current
    DESCRIPTION
        "Parameter 'access-priority' in event LLC.29"
    ::= { llcEventObjects29 1 }

llc29-interface OBJECT-TYPE
    SYNTAX DisplayString
    MAX-ACCESS accessible-for-notify
    STATUS current
    DESCRIPTION
        "Parameter 'interface' in event LLC.29"
    ::= { llcEventObjects29 2 }

llcEventObjects30 OBJECT-IDENTITY
    STATUS current
    DESCRIPTION
        "Event LLC.30
        An LLC config record exists for an interface that does not have a
        LAN hardware type."
    ::= { llcEventsGroup 30 }

llc30-hardware-type OBJECT-TYPE
    SYNTAX Integer32
    MAX-ACCESS accessible-for-notify
    STATUS current
    DESCRIPTION
        "Parameter 'hardware-type' in event LLC.30"
    ::= { llcEventObjects30 1 }

llc30-interface OBJECT-TYPE
    SYNTAX DisplayString
    MAX-ACCESS accessible-for-notify
    STATUS current
    DESCRIPTION
        "Parameter 'interface' in event LLC.30"
    ::= { llcEventObjects30 2 }

llcEventObjects31 OBJECT-IDENTITY
    STATUS current
    DESCRIPTION
        "Event LLC.31
        An LLC config record exists for an interface that does not exist."
    ::= { llcEventsGroup 31 }

llc31-interface-number OBJECT-TYPE
    SYNTAX Integer32
    MAX-ACCESS accessible-for-notify
    STATUS current
    DESCRIPTION
        "Parameter 'interface-number' in event LLC.31"
    ::= { llcEventObjects31 1 }

llcEventObjects32 OBJECT-IDENTITY
    STATUS current
    DESCRIPTION
        "Event LLC.32
        LLC user is sending a frame, or LLC itself is sending a
        TEST or XID response frame.
        The possible frame types are:
        TEST-C0 or TEST-C1 or TEST-R0 or TEST-R1 (TEST frame),
        XID-C0 or XID-C1 or XID-R0 or XID-R1 (Exchange Identification frame),
        UI-C0 or UI-R0 (Unnumbered Information frame).
        The abbrevation suffixes are C0 (command, poll bit off),
        C1 (command, poll bit on), R0 (response, final bit off) and
        R1 (response, final bit on)."
    ::= { llcEventsGroup 32 }

llc32-frame-type OBJECT-TYPE
    SYNTAX DisplayString
    MAX-ACCESS accessible-for-notify
    STATUS current
    DESCRIPTION
        "Parameter 'frame-type' in event LLC.32"
    ::= { llcEventObjects32 1 }

llc32-src-mac OBJECT-TYPE
    SYNTAX DisplayString
    MAX-ACCESS accessible-for-notify
    STATUS current
    DESCRIPTION
        "Parameter 'src-mac' in event LLC.32"
    ::= { llcEventObjects32 2 }

llc32-dst-mac OBJECT-TYPE
    SYNTAX DisplayString
    MAX-ACCESS accessible-for-notify
    STATUS current
    DESCRIPTION
        "Parameter 'dst-mac' in event LLC.32"
    ::= { llcEventObjects32 3 }

llc32-rif OBJECT-TYPE
    SYNTAX DisplayString
    MAX-ACCESS accessible-for-notify
    STATUS current
    DESCRIPTION
        "Parameter 'rif' in event LLC.32"
    ::= { llcEventObjects32 4 }

llc32-src-sap OBJECT-TYPE
    SYNTAX Integer32
    MAX-ACCESS accessible-for-notify
    STATUS current
    DESCRIPTION
        "Parameter 'src-sap' in event LLC.32"
    ::= { llcEventObjects32 5 }

llc32-dst-sap OBJECT-TYPE
    SYNTAX Integer32
    MAX-ACCESS accessible-for-notify
    STATUS current
    DESCRIPTION
        "Parameter 'dst-sap' in event LLC.32"
    ::= { llcEventObjects32 6 }

llc32-interface OBJECT-TYPE
    SYNTAX DisplayString
    MAX-ACCESS accessible-for-notify
    STATUS current
    DESCRIPTION
        "Parameter 'interface' in event LLC.32"
    ::= { llcEventObjects32 7 }

llcEventObjects33 OBJECT-IDENTITY
    STATUS current
    DESCRIPTION
        "Event LLC.33
        LLC subsystem itself is responding to a TEST or XID frame.
        The possible frame types are:
        TEST-C0 or TEST-C1 (TEST frame), and
        XID-C0 or XID-C1 (Exchange Identification frame).
        The abbrevation suffixes are:
        C0=(command, poll  bit off) and
        C1=(command, poll  bit on)."
    ::= { llcEventsGroup 33 }

llc33-frame-type OBJECT-TYPE
    SYNTAX DisplayString
    MAX-ACCESS accessible-for-notify
    STATUS current
    DESCRIPTION
        "Parameter 'frame-type' in event LLC.33"
    ::= { llcEventObjects33 1 }

llc33-src-mac OBJECT-TYPE
    SYNTAX DisplayString
    MAX-ACCESS accessible-for-notify
    STATUS current
    DESCRIPTION
        "Parameter 'src-mac' in event LLC.33"
    ::= { llcEventObjects33 2 }

llc33-dst-mac OBJECT-TYPE
    SYNTAX DisplayString
    MAX-ACCESS accessible-for-notify
    STATUS current
    DESCRIPTION
        "Parameter 'dst-mac' in event LLC.33"
    ::= { llcEventObjects33 3 }

llc33-rif OBJECT-TYPE
    SYNTAX DisplayString
    MAX-ACCESS accessible-for-notify
    STATUS current
    DESCRIPTION
        "Parameter 'rif' in event LLC.33"
    ::= { llcEventObjects33 4 }

llc33-src-sap OBJECT-TYPE
    SYNTAX Integer32
    MAX-ACCESS accessible-for-notify
    STATUS current
    DESCRIPTION
        "Parameter 'src-sap' in event LLC.33"
    ::= { llcEventObjects33 5 }

llc33-dst-sap OBJECT-TYPE
    SYNTAX Integer32
    MAX-ACCESS accessible-for-notify
    STATUS current
    DESCRIPTION
        "Parameter 'dst-sap' in event LLC.33"
    ::= { llcEventObjects33 6 }

llc33-interface OBJECT-TYPE
    SYNTAX DisplayString
    MAX-ACCESS accessible-for-notify
    STATUS current
    DESCRIPTION
        "Parameter 'interface' in event LLC.33"
    ::= { llcEventObjects33 7 }


llcNotification1 NOTIFICATION-TYPE
    OBJECTS { 
              llc1-frame-type, 
              llc1-src-mac,
              llc1-dst-mac,
              llc1-rif,
              llc1-src-sap,
              llc1-dst-sap,
              llc1-interface 
            }
    STATUS current
    DESCRIPTION
        "Notification of Event LLC.1

        Message: 'Sent $1, $2->$3, $4 saps $5->$6, interface $7'

        Parameters list:
              $1: llc1-frame-type
              $2: llc1-src-mac
              $3: llc1-dst-mac
              $4: llc1-rif
              $5: llc1-src-sap
              $6: llc1-dst-sap
              $7: llc1-interface

        LLC is sending a frame. Possible frame types are:
        SABME-C0 or SABME-C1 (Set Asynchronous Balanced Mode Extended),
        DM-R0 or DM-R1 (Disconnected Mode), DISC-C0 or DISC-C1 (Disconnect),
        RR-C0 or RR-C1 or RR-R0 or RR-R1 (Receiver Ready),
        RNR-C0 or RNR-C1 or RNR-R0 or RNR-R1 (Receiver Not Ready),
        REJ-C0 or REJ-C1 or REJ-R0 or REJ-R1 (Reject),
        UA-R0 or UA-R1 (Unnumbered Acknowledgement),
        FRMR-R0 or FRMR-R1 (Frame Reject), and
        I-C0 or I-C1 or I-R0 or I-R1 (Information Frame).
        The abbrevation suffixes are C0 (command, poll bit off),
        C1 (command, poll bit on), R0 (response, final bit off) and
        R1 (response, final bit on)."
    ::= { llcNotificationsPrefix 1 }

llcNotification2 NOTIFICATION-TYPE
    OBJECTS { 
              llc2-llc-event, 
              llc2-llc-state,
              llc2-llc2-connection,
              llc2-llc2-connection,
              llc2-llc2-sap,
              llc2-llc2-sap,
              llc2-interface 
            }
    STATUS current
    DESCRIPTION
        "Notification of Event LLC.2

        Message: 'event=$1 in state=$2, $3->$4, saps $5->$6, interface $7'

        Parameters list:
              $1: llc2-llc-event
              $2: llc2-llc-state
              $3: llc2-llc2-connection
              $4: llc2-llc2-connection
              $5: llc2-llc2-sap
              $6: llc2-llc2-sap
              $7: llc2-interface

        An event occurred on an llc2 connection. The LLC2 FSM (Finite State
        Machine) has been called to process the event.
        The LLC2 connection is uniquely identified by the combination
        destination MAC address, source MAC address, destination sap and
        source sap on a particular interface.
        The possible events are:
        SET-ABME (user request to connect to remote),
        SET-ADM (user request to disconnect from remote),
        SEND-BTU (user request to send data),
        FLOW-REQ-ON (user request to turn off local busy condition),
        FLOW-REQ-OFF (user request to turn on local busy condition),
        T1-EXP (T1 timer expiration), T2-EXP (T2 timer expiration),
        Ti-EXP (Ti timer epiration), OS-I-C0 or OS-I-C1 or OS-I-R0 or OS-I-R1
        (Ns on I-frame is out of sequence), I-C0 or I-C1 or I-R0 or I-R1
        (valid I-frame received), RR-C0 or RR-C1 or RR-R0 or RR-R1
        (RR frame received), RNR-C0 or RNR-C1 or RNR-R0 or RNR-R1
        (RNR frame received), REJ-C0 or REJ-C1 or REJ-R0 or REJ-R1
        (REJ frame received), UA-R0 or UA-R1 (UA frame received),
        DISC-C0 or DISC-C1 (DISC frame received), DM-R0 or DM-R1
        (DM frame received), FRMR-R0 or FRMR-R1 (FRMR  frame received),
        BAD-FRAME-0 or BAD-FRAME-1 (received frame will generate FRMR),
        SABME-C0 or SABME-C1 (SABME frame received), and
        SEND-I-POLL (Sending I frame with Poll bit on).
        The abbrevation suffixes are C0 (command, poll bit off),
        C1 (command, poll bit on), R0 (response, final bit off) and
        R1 (response, final bit on)."
    ::= { llcNotificationsPrefix 2 }

llcNotification3 NOTIFICATION-TYPE
    OBJECTS { 
              llc3-llc-old-state, 
              llc3-llc-new-state,
              llc3-llc2-connection,
              llc3-llc2-connection,
              llc3-llc2-sap,
              llc3-llc2-sap,
              llc3-interface 
            }
    STATUS current
    DESCRIPTION
        "Notification of Event LLC.3

        Message: '$1 to $2, $3->$4, saps $5->$6, interface $7'

        Parameters list:
              $1: llc3-llc-old-state
              $2: llc3-llc-new-state
              $3: llc3-llc2-connection
              $4: llc3-llc2-connection
              $5: llc3-llc2-sap
              $6: llc3-llc2-sap
              $7: llc3-interface

        There is LLC2 state change.
        The possible states are:
        DISCONNECTED (initial state),
        LINK-OPENING (link establishment in progress),
        DISCONNECTING (DISC sent, awaiting DM),
        FRMR-SENT (frmr sent),
        LINK-OPENED (normal state),
        LOCAL-BUSY (local is busy),
        REJECTION (remote sent an out of sequence frame),
        CHECKPOINTING (poll sent, awaiting response sending of data supended),
        CKPT-LB (combination state),
        CKPT-REJ (combination state),
        RESETTING (awaiting user response to reset),
        REMOTE-BUSY (remote is busy),
        LB-RB (combination state),
        REJ-LB (combination state),
        REJ-RB (combination state),
        CKPT-REJ-LB (combination state),
        CKPT-CLR (clearing from CKPT-LB state),
        CKPT-REJ-CLR (clearing from CKPT-REJ-LB state),
        REJ-LB-RB (combination state),
        FRMR-RECEIVED (received frmr).
        The abbreviations above are: CKPT=CHECKPOINTING, CLR=CLEARING,
        LB=LOCAL BUSY, RB=REMOTE BUSY, and REJ=REJECTION."
    ::= { llcNotificationsPrefix 3 }

llcNotification4 NOTIFICATION-TYPE
    OBJECTS { 
              llc4-user-event, 
              llc4-user-value,
              llc4-event-reason,
              llc4-llc2-connection,
              llc4-llc2-connection,
              llc4-llc2-sap,
              llc4-llc2-sap,
              llc4-interface 
            }
    STATUS current
    DESCRIPTION
        "Notification of Event LLC.4

        Message: 'Upcall user event $1 args $2/$3 on $4->$5, saps $6->$7, interface $8'

        Parameters list:
              $1: llc4-user-event
              $2: llc4-user-value
              $3: llc4-event-reason
              $4: llc4-llc2-connection
              $5: llc4-llc2-connection
              $6: llc4-llc2-sap
              $7: llc4-llc2-sap
              $8: llc4-interface

        LLC2 event upcall is occuring.
        Some of the arguments on the upcall are shown.
        User Cookie is meaningful to the router software running over
        the LLC subsystem.
        Event reason sometimes further specifies the event.
        The possible upcall events are:
        CONN-IND (cookie=session, reason=none),
        CONN-IND-PASS (cookie=sap, reason=none),
        CONN-CONFIRM (cookie=session, reason=none),
        DISC-IND (cookie=session, possible reasons: local term (disconnecting),
        remote term, conn refused, local term (disconnected)),
        RESET-IND (cookie=session, possible reasons: local reset,
        remote reset, frmr rcvd, frmr sent),
        RESET-CONF (cookie=session, reason=none),
        FLOW-IND (cookie=session, possible reasons: flow off, flow on), and
        DISC-CONFIRM (cookie=session, reason=none)."
    ::= { llcNotificationsPrefix 4 }

llcNotification5 NOTIFICATION-TYPE
    OBJECTS { 
              llc5-user-primitive, 
              llc5-SAP-value,
              llc5-interface 
            }
    STATUS current
    DESCRIPTION
        "Notification of Event LLC.5

        Message: 'user primitive $1 sap $2 on interface $3'

        Parameters list:
              $1: llc5-user-primitive
              $2: llc5-SAP-value
              $3: llc5-interface

        A sap-releated LLC user-primitive was called.
        The possible SAP primitives are:
        OPEN-SAP,
        CLOSE-SAP,
        CLOSE-SAP-FORCED,
        MODIFY-SAP,
        OPEN-STATION, and
        UNITDATA."
    ::= { llcNotificationsPrefix 5 }

llcNotification6 NOTIFICATION-TYPE
    OBJECTS { 
              llc6-user-primitive, 
              llc6-llc2-connection,
              llc6-llc2-connection,
              llc6-llc2-sap,
              llc6-llc2-sap,
              llc6-interface 
            }
    STATUS current
    DESCRIPTION
        "Notification of Event LLC.6

        Message: 'primitive $1, $2->$3, saps $4->$5, interface $6'

        Parameters list:
              $1: llc6-user-primitive
              $2: llc6-llc2-connection
              $3: llc6-llc2-connection
              $4: llc6-llc2-sap
              $5: llc6-llc2-sap
              $6: llc6-interface

        A llc2 connection non-data user-primitive was called.
        The possible primitives are:
        CLOSE-STATION,
        CLOSE-STATION-FORCED,
        CONNECT-REQUEST,
        CONNECT-RESPONSE,
        DISCONNECT-REQUEST,
        RESET-REQUEST,
        RESET-RESPONSE,
        FLOW-REQ."
    ::= { llcNotificationsPrefix 6 }

llcNotification7 NOTIFICATION-TYPE
    OBJECTS { 
              llc7-llc2-connection, 
              llc7-llc2-connection,
              llc7-llc2-sap,
              llc7-llc2-sap,
              llc7-interface 
            }
    STATUS current
    DESCRIPTION
        "Notification of Event LLC.7

        Message: 'data primitive, $1->$2, saps $3->$4, interface $5'

        Parameters list:
              $1: llc7-llc2-connection
              $2: llc7-llc2-connection
              $3: llc7-llc2-sap
              $4: llc7-llc2-sap
              $5: llc7-interface

        A DATA-REQUEST data primitive was called. DATA-REQUEST passes the data
        in buffer memory."
    ::= { llcNotificationsPrefix 7 }

llcNotification8 NOTIFICATION-TYPE
    OBJECTS { 
              llc8-llc2-connection, 
              llc8-llc2-connection,
              llc8-llc2-sap,
              llc8-llc2-sap,
              llc8-interface 
            }
    STATUS current
    DESCRIPTION
        "Notification of Event LLC.8

        Message: 'data primitive, $1->$2, saps $3->$4, interface $5'

        Parameters list:
              $1: llc8-llc2-connection
              $2: llc8-llc2-connection
              $3: llc8-llc2-sap
              $4: llc8-llc2-sap
              $5: llc8-interface

        A DATA-LOCAL data primitive was called. DATA-LOCAL passes the data
        in data memory."
    ::= { llcNotificationsPrefix 8 }

llcNotification9 NOTIFICATION-TYPE
    OBJECTS { 
              llc9-SAP-value, 
              llc9-interface 
            }
    STATUS current
    DESCRIPTION
        "Notification of Event LLC.9

        Message: 'unitdata primitive, sap $1 interface $2'

        Parameters list:
              $1: llc9-SAP-value
              $2: llc9-interface

        A UNITDATA llc1 data primitive was called."
    ::= { llcNotificationsPrefix 9 }

llcNotification10 NOTIFICATION-TYPE
    OBJECTS { 
              llc10-llc2-connection, 
              llc10-llc2-connection,
              llc10-llc2-sap,
              llc10-llc2-sap,
              llc10-interface 
            }
    STATUS current
    DESCRIPTION
        "Notification of Event LLC.10

        Message: 'outbound queue too big, $1->$2, saps $3->$4, interface $5'

        Parameters list:
              $1: llc10-llc2-connection
              $2: llc10-llc2-connection
              $3: llc10-llc2-sap
              $4: llc10-llc2-sap
              $5: llc10-interface

        The oubound queue has grown grossly large. The llc2 connection is being
        automatically terminated."
    ::= { llcNotificationsPrefix 10 }

llcNotification11 NOTIFICATION-TYPE
    OBJECTS { 
              llc11-llc2-connection, 
              llc11-llc2-connection,
              llc11-llc2-sap,
              llc11-llc2-sap,
              llc11-interface 
            }
    STATUS current
    DESCRIPTION
        "Notification of Event LLC.11

        Message: 'No buffer available to duplicate I-frame, $1->$2, saps $3->$4, interface $5'

        Parameters list:
              $1: llc11-llc2-connection
              $2: llc11-llc2-connection
              $3: llc11-llc2-sap
              $4: llc11-llc2-sap
              $5: llc11-interface

        No buffer available to duplicate I-frame."
    ::= { llcNotificationsPrefix 11 }

llcNotification12 NOTIFICATION-TYPE
    OBJECTS { 
              llc12-llc2-connection, 
              llc12-llc2-connection,
              llc12-llc2-sap,
              llc12-llc2-sap,
              llc12-interface 
            }
    STATUS current
    DESCRIPTION
        "Notification of Event LLC.12

        Message: 'No memory available to duplicate I-frame, $1->$2, saps $3->$4, interface $5'

        Parameters list:
              $1: llc12-llc2-connection
              $2: llc12-llc2-connection
              $3: llc12-llc2-sap
              $4: llc12-llc2-sap
              $5: llc12-interface

        No memory to duplicate I-frame."
    ::= { llcNotificationsPrefix 12 }

llcNotification13 NOTIFICATION-TYPE
    OBJECTS { 
              llc13-llc2-connection, 
              llc13-llc2-connection,
              llc13-llc2-sap,
              llc13-llc2-sap,
              llc13-interface 
            }
    STATUS current
    DESCRIPTION
        "Notification of Event LLC.13

        Message: 'No buffer for LLC frame, $1->$2, saps $3->$4, interface $5'

        Parameters list:
              $1: llc13-llc2-connection
              $2: llc13-llc2-connection
              $3: llc13-llc2-sap
              $4: llc13-llc2-sap
              $5: llc13-interface

        A buffer could not be obtained to to build an LLC Supervisory or
        Unnumbered frame. No loss of data integrity has occurred yet, but
        unless buffers for this purpose become available within a few seconds,
        the other end of the LLC2 connection will most likely terminate
        this LLC connection as part of the normal LLC2 protocol."
    ::= { llcNotificationsPrefix 13 }

llcNotification14 NOTIFICATION-TYPE
    OBJECTS { 
              llc14-llc2-connection, 
              llc14-llc2-connection,
              llc14-llc2-sap,
              llc14-llc2-sap,
              llc14-interface 
            }
    STATUS current
    DESCRIPTION
        "Notification of Event LLC.14

        Message: 'frame type invalid, $1->$2, saps $3->$4, interface $5'

        Parameters list:
              $1: llc14-llc2-connection
              $2: llc14-llc2-connection
              $3: llc14-llc2-sap
              $4: llc14-llc2-sap
              $5: llc14-interface

        The frame type the LLC is trying to build is invalid."
    ::= { llcNotificationsPrefix 14 }

llcNotification15 NOTIFICATION-TYPE
    OBJECTS { 
              llc15-event-code-number 
            }
    STATUS current
    DESCRIPTION
        "Notification of Event LLC.15

        Message: 'Invalid LLC2 FSM event $1'

        Parameters list:
              $1: llc15-event-code-number

        The LLC2 Finite State Machine (FSM) was called with an event that was
        out of range."
    ::= { llcNotificationsPrefix 15 }

llcNotification16 NOTIFICATION-TYPE
    OBJECTS { 
              llc16-network-type, 
              llc16-interface 
            }
    STATUS current
    DESCRIPTION
        "Notification of Event LLC.16

        Message: 'invalid network type $1 on interface $2'

        Parameters list:
              $1: llc16-network-type
              $2: llc16-interface

        An OPEN SAP operation was tried on a network type that LLC does not
        support. Network types Token-Ring, Ethernet, and FDDI are supported."
    ::= { llcNotificationsPrefix 16 }

llcNotification17 NOTIFICATION-TYPE
    OBJECTS { 
              llc17-SAP-value, 
              llc17-interface 
            }
    STATUS current
    DESCRIPTION
        "Notification of Event LLC.17

        Message: 'duplicate sap $1 on interface $2'

        Parameters list:
              $1: llc17-SAP-value
              $2: llc17-interface

        A OPEN SAP operation was tried on a sap that has already been opened."
    ::= { llcNotificationsPrefix 17 }

llcNotification18 NOTIFICATION-TYPE
    OBJECTS { 
              llc18-interface 
            }
    STATUS current
    DESCRIPTION
        "Notification of Event LLC.18

        Message: 'No memory for SAP control block on interface $1'

        Parameters list:
              $1: llc18-interface

        Unable to allocate memory for SAP control block."
    ::= { llcNotificationsPrefix 18 }

llcNotification19 NOTIFICATION-TYPE
    OBJECTS { 
              llc19-interface 
            }
    STATUS current
    DESCRIPTION
        "Notification of Event LLC.19

        Message: 'No memory for station control block on interface $1'

        Parameters list:
              $1: llc19-interface

        Unable to allocate memory for station control block."
    ::= { llcNotificationsPrefix 19 }

llcNotification20 NOTIFICATION-TYPE
    OBJECTS { 
              llc20-llc2-connection, 
              llc20-llc2-connection,
              llc20-llc2-sap,
              llc20-llc2-sap,
              llc20-interface 
            }
    STATUS current
    DESCRIPTION
        "Notification of Event LLC.20

        Message: 'UI frame dropped, $1->$2, saps $3->$4, interface $5'

        Parameters list:
              $1: llc20-llc2-connection
              $2: llc20-llc2-connection
              $3: llc20-llc2-sap
              $4: llc20-llc2-sap
              $5: llc20-interface

        UI frame refused by the local application within the router."
    ::= { llcNotificationsPrefix 20 }

llcNotification21 NOTIFICATION-TYPE
    OBJECTS { 
              llc21-llc2-connection, 
              llc21-llc2-connection,
              llc21-llc2-sap,
              llc21-llc2-sap,
              llc21-interface 
            }
    STATUS current
    DESCRIPTION
        "Notification of Event LLC.21

        Message: 'TEST frame refused, $1->$2, saps $3->$4, interface $5'

        Parameters list:
              $1: llc21-llc2-connection
              $2: llc21-llc2-connection
              $3: llc21-llc2-sap
              $4: llc21-llc2-sap
              $5: llc21-interface

        TEST frame refused by the local application within the router.
        The frame is passed on to the bridge code, etc."
    ::= { llcNotificationsPrefix 21 }

llcNotification22 NOTIFICATION-TYPE
    OBJECTS { 
              llc22-llc2-connection, 
              llc22-llc2-connection,
              llc22-llc2-sap,
              llc22-llc2-sap,
              llc22-interface 
            }
    STATUS current
    DESCRIPTION
        "Notification of Event LLC.22

        Message: 'XID frame refused, $1->$2, saps $3->$4, interface $5'

        Parameters list:
              $1: llc22-llc2-connection
              $2: llc22-llc2-connection
              $3: llc22-llc2-sap
              $4: llc22-llc2-sap
              $5: llc22-interface

        XID frame refused by the local application within the router.
        The frame is passed on to the bridge code, etc."
    ::= { llcNotificationsPrefix 22 }

llcNotification23 NOTIFICATION-TYPE
    OBJECTS { 
              llc23-frame-type, 
              llc23-src-mac,
              llc23-dst-mac,
              llc23-rif,
              llc23-src-sap,
              llc23-dst-sap,
              llc23-interface 
            }
    STATUS current
    DESCRIPTION
        "Notification of Event LLC.23

        Message: 'Upcall frame $1, $2->$3, $4 saps $5->$6, interface $7'

        Parameters list:
              $1: llc23-frame-type
              $2: llc23-src-mac
              $3: llc23-dst-mac
              $4: llc23-rif
              $5: llc23-src-sap
              $6: llc23-dst-sap
              $7: llc23-interface

        LLC makes an upcall providing the LLC with a unitdata frame.
        The possible unitdata frames are:
        TEST-C0 or TEST-C1 or TEST-R0 or TEST-R1 (TEST frame),
        XID-C0 or XID-C1 or XID-R0 or XID-R1 (Exchange Identification frame),
        UI-C0 or UI-R0 (Unnumbered Information).
        The abbrevation suffixes are C0 (command, poll bit off),
        C1 (command, poll bit on), R0 (response, final bit off) and
        R1 (response, final bit on)."
    ::= { llcNotificationsPrefix 23 }

llcNotification24 NOTIFICATION-TYPE
    OBJECTS { 
              llc24-reason-code, 
              llc24-llc2-connection,
              llc24-llc2-connection,
              llc24-llc2-sap,
              llc24-llc2-sap,
              llc24-interface-name 
            }
    STATUS current
    DESCRIPTION
        "Notification of Event LLC.24

        Message: 'llc2 outbound frame dropped, reason $1, $2->$3, saps $4->$5, interface $6'

        Parameters list:
              $1: llc24-reason-code
              $2: llc24-llc2-connection
              $3: llc24-llc2-connection
              $4: llc24-llc2-sap
              $5: llc24-llc2-sap
              $6: llc24-interface-name

        The sending of an LLC2 related outbound frame failed.
        The reason-code is the internal error code for the failure."
    ::= { llcNotificationsPrefix 24 }

llcNotification25 NOTIFICATION-TYPE
    OBJECTS { 
              llc25-frame-type, 
              llc25-reason-code,
              llc25-llc2-connection,
              llc25-llc2-connection,
              llc25-llc2-sap,
              llc25-llc2-sap,
              llc25-interface 
            }
    STATUS current
    DESCRIPTION
        "Notification of Event LLC.25

        Message: '$1 outbound frame dropped, reason $2, $3->$4, saps $5->$6, interface $7'

        Parameters list:
              $1: llc25-frame-type
              $2: llc25-reason-code
              $3: llc25-llc2-connection
              $4: llc25-llc2-connection
              $5: llc25-llc2-sap
              $6: llc25-llc2-sap
              $7: llc25-interface

        The sending of the user's UNITDATA or an LLC-generated XID or TEST
        response outbound frame failed.
        The possible frame test are:
        TEST-C0 or TEST-C1 or TEST-R0 or TEST-R1 (TEST frame),
        XID-C0 or XID-C1 or XID-R0 or XID-R1 (Exchange Identification frame),
        UI-C0 or UI-R0 (Unnumbered Information frame) and
        unexpected (not one of the above types).
        The abbrevation suffixes are C0 (command, poll bit off),
        C1 (command, poll bit on),
        R0 (response, final bit off), and R1 (response, final bit on)."
    ::= { llcNotificationsPrefix 25 }

llcNotification26 NOTIFICATION-TYPE
    OBJECTS { 
              llc26-interface 
            }
    STATUS current
    DESCRIPTION
        "Notification of Event LLC.26

        Message: 'No memory for LLC CONF BLOCK on interface $1'

        Parameters list:
              $1: llc26-interface

        Unable to allocate memory for an LLC-CONF-BLOCK at initialization time.
        LLC configuration defaults are used."
    ::= { llcNotificationsPrefix 26 }

llcNotification27 NOTIFICATION-TYPE
    OBJECTS { 
              llc27-interface 
            }
    STATUS current
    DESCRIPTION
        "Notification of Event LLC.27

        Message: 'Read LLC Configuration record for interface $1'

        Parameters list:
              $1: llc27-interface

        LLC Configuration record read for this network. This only occurs
        at initialization time. The values in the LLC configuration record
        are used as default value on the interface."
    ::= { llcNotificationsPrefix 27 }

llcNotification28 NOTIFICATION-TYPE
    OBJECTS { 
              llc28-access-priority, 
              llc28-interface 
            }
    STATUS current
    DESCRIPTION
        "Notification of Event LLC.28

        Message: 'Inv access priority $1 for interface $2'

        Parameters list:
              $1: llc28-access-priority
              $2: llc28-interface

        access-priority, on an interface that is not a token ring must be
        zero because it is not used."
    ::= { llcNotificationsPrefix 28 }

llcNotification29 NOTIFICATION-TYPE
    OBJECTS { 
              llc29-access-priority, 
              llc29-interface 
            }
    STATUS current
    DESCRIPTION
        "Notification of Event LLC.29

        Message: 'Inv acc $1 for interface $2'

        Parameters list:
              $1: llc29-access-priority
              $2: llc29-interface

        The access priority is greater than 7. A default of 0 is used."
    ::= { llcNotificationsPrefix 29 }

llcNotification30 NOTIFICATION-TYPE
    OBJECTS { 
              llc30-hardware-type, 
              llc30-interface 
            }
    STATUS current
    DESCRIPTION
        "Notification of Event LLC.30

        Message: 'Invalid hardware type $1 for interface $2'

        Parameters list:
              $1: llc30-hardware-type
              $2: llc30-interface

        An LLC config record exists for an interface that does not have a
        LAN hardware type."
    ::= { llcNotificationsPrefix 30 }

llcNotification31 NOTIFICATION-TYPE
    OBJECTS { 
              llc31-interface-number 
            }
    STATUS current
    DESCRIPTION
        "Notification of Event LLC.31

        Message: 'Invalid interface $1 in config'

        Parameters list:
              $1: llc31-interface-number

        An LLC config record exists for an interface that does not exist."
    ::= { llcNotificationsPrefix 31 }

llcNotification32 NOTIFICATION-TYPE
    OBJECTS { 
              llc32-frame-type, 
              llc32-src-mac,
              llc32-dst-mac,
              llc32-rif,
              llc32-src-sap,
              llc32-dst-sap,
              llc32-interface 
            }
    STATUS current
    DESCRIPTION
        "Notification of Event LLC.32

        Message: 'Sent $1, $2->$3, $4 saps $5->$6, interface $7'

        Parameters list:
              $1: llc32-frame-type
              $2: llc32-src-mac
              $3: llc32-dst-mac
              $4: llc32-rif
              $5: llc32-src-sap
              $6: llc32-dst-sap
              $7: llc32-interface

        LLC user is sending a frame, or LLC itself is sending a
        TEST or XID response frame.
        The possible frame types are:
        TEST-C0 or TEST-C1 or TEST-R0 or TEST-R1 (TEST frame),
        XID-C0 or XID-C1 or XID-R0 or XID-R1 (Exchange Identification frame),
        UI-C0 or UI-R0 (Unnumbered Information frame).
        The abbrevation suffixes are C0 (command, poll bit off),
        C1 (command, poll bit on), R0 (response, final bit off) and
        R1 (response, final bit on)."
    ::= { llcNotificationsPrefix 32 }

llcNotification33 NOTIFICATION-TYPE
    OBJECTS { 
              llc33-frame-type, 
              llc33-src-mac,
              llc33-dst-mac,
              llc33-rif,
              llc33-src-sap,
              llc33-dst-sap,
              llc33-interface 
            }
    STATUS current
    DESCRIPTION
        "Notification of Event LLC.33

        Message: 'frm to LLC, frm $1, $2->$3, $4 saps $5->$6, interface $7'

        Parameters list:
              $1: llc33-frame-type
              $2: llc33-src-mac
              $3: llc33-dst-mac
              $4: llc33-rif
              $5: llc33-src-sap
              $6: llc33-dst-sap
              $7: llc33-interface

        LLC subsystem itself is responding to a TEST or XID frame.
        The possible frame types are:
        TEST-C0 or TEST-C1 (TEST frame), and
        XID-C0 or XID-C1 (Exchange Identification frame).
        The abbrevation suffixes are:
        C0=(command, poll  bit off) and
        C1=(command, poll  bit on)."
    ::= { llcNotificationsPrefix 33 }


END
