-- *****************************************************************
-- Codan.mib:  Codan's 8800 DMR product MIB
--
-- Created by Kjell Genborg
--
-- Copyright (c) 2005 by Codan Ltd.
-- All rights reserved.
--
-- *****************************************************************

CODAN-MIB DEFINITIONS ::= BEGIN

IMPORTS
   MODULE-IDENTITY, OBJECT-TYPE,
   NOTIFICATION-TYPE,
   Integer32, TimeTicks,
   IpAddress, Gauge32, Counter32           FROM SNMPv2-SMI
   DisplayString, DateAndTime,
   TEXTUAL-CONVENTION,
   TestAndIncr,TimeInterval                FROM SNMPv2-TC
   codanMibs                               FROM CODAN-SMI;



minetMIB MODULE-IDENTITY
   LAST-UPDATED "0906260645Z"
   ORGANIZATION "Codan Limited"
   CONTACT-INFO
        "       Andrew Burton
        Postal: Codan
                81 Graves St.
                Newton 5074
                Australia
        Tel:    +61-8-83050311
        Fax:    +61-8-83050411
                http//codan.com.au"
    DESCRIPTION
        "
        This is the MIB module for objects necessary to manage the
        Codan 8800 DMR device.
        Also NOTIFICATION-TYPEs (traps) are defined at the end of this
        document.

        Its position in the internet tree and its general structure
        are as follows:

                          iso(1).org(3).dod(6).internet(1)
                                       :
                                   private(4)
                                       :
                                  enterprises(1)
                                       :
                                   codan(23304)
                                       :
                                  codanMibs(1)
                                       :
                                  minetMIB(1)
                                       :
          ..........................................................
          :              :             :             :             :
          :              :             :             :             :
          :       wvStatusAndGauges(2) :         wvTests(4)        :
  wvConfiguration(1)            wvPerformance(3)               wvTraps(10)
          :
          :........................................................
           :                 :         :         :                :
           :                 :         :         :                :
    wvLinkSettings(1)  wvInterfaces(2) :   wvManagement(3)  wvRelayTable(4)
                                       :
          .......................................................
          :                            :                        :
          :                            :                        :
 wvExternalInputTable(5)       wvAlarmControl(6)   wvComponentsRevisions(7)



        Note that in addition to the objects defined in this module,
        the Codan 8800 DMR supports the following objects from standard
        MIBs:

     MIB NAME                   GROUP                OBJECT
     ========                   =====                ======

     MIB-II (RFC 1213)          system               sysName
                                                     sysLocation
                                                     sysContact
                                                     sysObjectId
                                                     sysDescr
                                                     sysUpTime

                                ipAddrTable          ipAdEntAddr
                                                     ipAdEntIfIndex
                                                     ipAdEntNetMask

     Interfaces MIB (RFC 1573)  interfaces           ifNumber
                                                     ifIndex
                                                     ifDescr
                                                     ifType
                                                     ifMtu
                                                     ifSpeed
                                                     ifPhysAddress
                                                     ifAdminStatus
                                                     ifOperStatus
                                                     ifLastChange
                                                     ifInOctets
                                                     ifInUcastPkts
                                                     ifInNUcastPkts
                                                     ifInDiscards
                                                     ifInErrors
                                                     ifInUnknownProtos
                                                     ifOutOctets
                                                     ifOutUcastPkts
                                                     ifOutNUcastPkts
                                                     ifOutDiscards
                                                     ifOutErrors
						     ifOutQLen
						     ifSpecific
                                snmpTraps            linkUp
                                                     linkDown

     DS1/E1 MIB (RFC 1406)      dsx1ConfigTable      dsx1LineIndex
                                                     dsx1IfIndex
                                                     dsx1LineType
                                                     dsx1LineCoding
                                                     dsx1LoopbackConfig
                                                     dsx1TransmitClockSource
                                                     dsx1LineStatus
                                                     dsx1TimeElapsed
                                                     dsx1CurrentESs
                                                     dsx1CurrentSESs
                                                     dsx1CurrentUASs
                                                     dsx1CurrentDMs
                                                     dsx1TotalESs
                                                     dsx1TotalSESs
                                                     dsx1TotalUASs
                                                     dsx1TotalDMs

     DS3/E3 MIB (RFC 1407)      dsx3ConfigTable      dsx3LineIndex
                                                     dsx3IfIndex
                                                     dsx3LineCoding
                                                     dsx3TransmitClockSource
                                                     dsx3LineStatus
                                                     dsx3CurrentUASs
                                                     dsx3TotalUASs

     RS-232-like MIB (RFC 1659) rs232PortTable       rs232PortIndex
                                                     rs232PortInSpeed
                                                     rs232PortOutSpeed
                                                     rs232PortInFlowType
                                                     rs232PortOutFlowType
                                                     rs232PortType

                                rs232AsyncPortTable  rs232AsyncPortIndex
                                                     rs232AsyncPortBits
                                                     rs232AsyncPortStopBits
                                                     rs232AsyncPortParity

     RFC 1907                   snmpTraps            authenticationFailure

     ETH-Like MIB (RFC 1643)	dot3StatsTable	     dot3StatsIndex
            					     dot3StatsAlignmentErrors
            					     dot3StatsFCSErrors
            					     dot3StatsSingleCollisionFrames
            					     dot3StatsMultipleCollisionFrames
            					     dot3StatsSQETestErrors
            					     dot3StatsDeferredTransmissions
            					     dot3StatsLateCollisions
            					     dot3StatsExcessiveCollisions
            					     dot3StatsInternalMacTransmitErrors
            					     dot3StatsCarrierSenseErrors
            					     dot3StatsFrameTooLongs
            					     dot3StatsInternalMacReceiveErrors
            					     dot3StatsEtherChipSet


NOTE:   Codan 8800 DMR supports an STS-1 interface. For the purposes of this MIB, it behaves
        like E3/T3. Since it doesn't have a specific ifType, it's type will be
        'other'.
        "

    REVISION    "9708261800Z"
    DESCRIPTION
           "Release Version of this MIB."
    ::= { codanMibs 1 }

-- ***##############################################################***
--              CodanMIB Textual Convention Definitions
-- ***##############################################################***

WvAlarmsList ::= TEXTUAL-CONVENTION
    STATUS       current
    DESCRIPTION
        "Describes all the possible alarms in the system as a bit pattern,
        taken directly from the various statuses (see wvStatusAndGauges group).
        The alarms are sorted in a descending severity order
        (fatal/error/warning), thus automatically defining their severity
        level."
    SYNTAX      BITS {
                    -- *** Fatal Severity Alarms ***
                    filler0(0),
                    wvTelemetrynotOperational(1), -- wvTelemetryStatus
                    wvIduOduCableFault(2),     -- wvIduOduCableStatus
                    wvOperatingSystemFailure(3),-- wvOperatingSystemStatus
                    iduPowerSupplyLowValue(4), -- wvIduStatus
                    iduTxSynthesizerOutOfLock(5), -- wvIduStatus
                    iduRxSynthesizerOutOfLock(6), -- wvIduStatus
                    iduNotOperational(7),      -- wvIduStatus
                    oduPowerSupplyOutOfRange(8),-- wvOduStatus
                    txFailure(9),             -- wvOduStatus
                    oduTxSynthesizerOutOfLock(10), -- wvOduStatus
                    oduRxSynthesizerOutOfLock(11), -- wvOduStatus
                    oduRfSynthesizerOutOfLock(12), -- wvOduStatus
                    remoteTerminalNotResponding(13), -- wvRemoteTerminalStatus
                    linkDown(14),		   -- ifOperStatus of the LINK
                    filler15(15),
                    filler16(16),
                    filler17(17),
                    filler18(18),
                    filler19(19),
                    -- *** Error Severity Alarms ***
                    selfTestFault(20),         -- wvIduStatus
                    rxFailure(21),             -- wvOduStatus
                    wvTelemetryFailure(22),     -- wvTelemetryStatus
                    oduTemperatureViolation(23),   -- wvOduStatus
                    anyOtherOduFault(24),      -- wvOduStatus
                    oduNotResponding(25),      -- wvOduStatus
                    wvSlipModemFailure(26),    -- wvSlipModemStatus
                    linkIdViolation(27),       -- wvSecurityStatus
                    wvTftpDwnlFailure(28),     -- wvTftpDwnlStatus
                    wvLinkESAlarm(29),         -- wvLinkPerformanceAlarmsStatus
                    wvLinkSESAlarm(30),        -- wvLinkPerformanceAlarmsStatus
                    wvLinkUASAlarm(31),        -- wvLinkPerformanceAlarmsStatus
                    wvLinkDMAlarm(32),         -- wvLinkPerformanceAlarmsStatus
                    wvLinkBERFailureAlarm(33), -- wvLinkPerformanceAlarmsStatus
                    wvLinkBLERAlarm(34),       -- wvLinkPerformanceAlarmsStatus
                    wvLinkBBERAlarm(35),       -- wvLinkPerformanceAlarmsStatus
                    wvLinkNCBLERAlarm(36),     -- wvLinkPerformanceAlarmsStatus
                    dwnlGeneralError(37),            -- wvTftpDwnlStatus
                    dwnlNoResponseFromServer(38),    -- wvTftpDwnlStatus
                    dwnlChecksumError(39),           -- wvTftpDwnlStatus
                    dwnlSwIncompatibleImage(40),     -- wvTftpDwnlStatus
                    dwnlConfigIncompatibleImage(41), -- wvTftpDwnlStatus
                    dwnlTftpFileNotFound(42),        -- wvTftpDwnlStatus
                    dwnlTftpAccessViolation(43),     -- wvTftpDwnlStatus
                    remoteTerminalFailure(44), -- wvRemoteTerminalStatus
                    filler45(45),
                    filler46(46),
                    filler47(47),
                    filler48(48),
                    filler49(49),
                    -- *** Warning Severity Alarms ***
                    txOnMuteState(50),         -- wvOduStatus
                    rxOnMuteState(51),         -- wvOduStatus
                    remoteTerminalWarning(52), -- wvRemoteTerminalStatus
                    passwordBypass(53),        -- wvSecurityStatus
                    wvLinkBERWarningAlarm(54), -- wvLinkPerformanceAlarmsStatus
                    rslLow(55),                -- wvOduStatus
                    averageRSLLow(56),         -- wvOduStatus
                    ds1Line-1-AIS(57),
                    ds1Line-2-AIS(58),
                    ds1Line-3-AIS(59),
                    ds1Line-4-AIS(60),
                    ds1Line-5-AIS(61),
                    ds1Line-6-AIS(62),
                    ds1Line-7-AIS(63),
                    ds1Line-8-AIS(64),
                    ds1Line-9-AIS(65),
                    ds1Line-10-AIS(66),
                    ds1Line-11-AIS(67),
                    ds1Line-12-AIS(68),
                    ds1Line-13-AIS(69),
                    ds1Line-14-AIS(70),
                    ds1Line-15-AIS(71),
                    ds1Line-16-AIS(72),
                    ds3Sts1Line-AIS(73),
                    ds1Line-1-LOS(74),
                    ds1Line-2-LOS(75),
                    ds1Line-3-LOS(76),
                    ds1Line-4-LOS(77),
                    ds1Line-5-LOS(78),
                    ds1Line-6-LOS(79),
                    ds1Line-7-LOS(80),
                    ds1Line-8-LOS(81),
                    ds1Line-9-LOS(82),
                    ds1Line-10-LOS(83),
                    ds1Line-11-LOS(84),
                    ds1Line-12-LOS(85),
                    ds1Line-13-LOS(86),
                    ds1Line-14-LOS(87),
                    ds1Line-15-LOS(88),
                    ds1Line-16-LOS(89),
                    ds3Sts1Line-LOS(90),
                    ds1Line-1-USD(91),
                    ds1Line-2-USD(92),
                    ds1Line-3-USD(93),
                    ds1Line-4-USD(94),
                    ds1Line-5-USD(95),
                    ds1Line-6-USD(96),
                    ds1Line-7-USD(97),
                    ds1Line-8-USD(98),
                    ds1Line-9-USD(99),
                    ds1Line-10-USD(100),
                    ds1Line-11-USD(101),
                    ds1Line-12-USD(102),
                    ds1Line-13-USD(103),
                    ds1Line-14-USD(104),
                    ds1Line-15-USD(105),
                    ds1Line-16-USD(106),
                    ds3Sts1Line-USD(107),
                    ds1Line-1-LOOP(108),
                    ds1Line-2-LOOP(109),
                    ds1Line-3-LOOP(110),
                    ds1Line-4-LOOP(111),
                    ds1Line-5-LOOP(112),
                    ds1Line-6-LOOP(113),
                    ds1Line-7-LOOP(114),
                    ds1Line-8-LOOP(115),
                    ds1Line-9-LOOP(116),
                    ds1Line-10-LOOP(117),
                    ds1Line-11-LOOP(118),
                    ds1Line-12-LOOP(119),
                    ds1Line-13-LOOP(120),
                    ds1Line-14-LOOP(121),
                    ds1Line-15-LOOP(122),
                    ds1Line-16-LOOP(123),
                    ds3Sts1Line-LOOP(124),
                    dwnlStatusUnknown(125),
                    dwnlInProcess(126),
                    dwnlSuccess(127),
                    ifLinkDown(128),           	-- ifOperStatus
                    wvTelemetryWarning(129), 	-- wvTelemetryStatus
                    filler130(130),
                    eth10-100Port-1-CSL(131),	-- wvEth10-100PortStatus
                    eth10-100Port-2-CSL(132),   -- wvEth10-100PortStatus
                    eth10-100Port-3-CSL(133),	-- wvEth10-100PortStatus
                    eth10-100Port-4-CSL(134),   -- wvEth10-100PortStatus
                    eth10-100Port-1-EC(135),	-- wvEth10-100PortStatus
                    eth10-100Port-2-EC(136),	-- wvEth10-100PortStatus
                    eth10-100Port-3-EC(137),	-- wvEth10-100PortStatus
                    eth10-100Port-4-EC(138),	-- wvEth10-100PortStatus
                    eth10-100Port-1-IMTE(139),  -- wvEth10-100PortStatus
                    eth10-100Port-2-IMTE(140),	-- wvEth10-100PortStatus
                    eth10-100Port-3-IMTE(141),  -- wvEth10-100PortStatus
                    eth10-100Port-4-IMTE(142),	-- wvEth10-100PortStatus
                    eth10-100Port-1-IMRE(143),	-- wvEth10-100PortStatus
                    eth10-100Port-2-IMRE(144),	-- wvEth10-100PortStatus
                    eth10-100Port-3-IMRE(145),	-- wvEth10-100PortStatus
                    eth10-100Port-4-IMRE(146),	-- wvEth10-100PortStatus
                    filler147(147),
                    -- *** User-Defined Severity Alarms ***
                    externalInput1Active(148),  -- wvExternalInputStatus
                    externalInput2Active(149),  -- wvExternalInputStatus
                    externalInput3Active(150),  -- wvExternalInputStatus
                    externalInput4Active(151),  -- wvExternalInputStatus
                    externalInput5Active(152),  -- wvExternalInputStatus
                    externalInput6Active(153),  -- wvExternalInputStatus
                    externalInput7Active(154),  -- wvExternalInputStatus
                    externalInput8Active(155),  -- wvExternalInputStatus
                    eth10-100RxLinkUsageLow(156) , -- wvLinkPerformanceAlarmsStatus
                    eth10-100RxLinkUsageHigh(157), -- wvLinkPerformanceAlarmsStatus
                    eth10-100TxLinkUsageLow(158),  -- wvLinkPerformanceAlarmsStatus
                    eth10-100TxLinkUsageHigh(159)  -- wvLinkPerformanceAlarmsStatus
                                    
                    
                    -- ??? to be checked what about interfaces alarms: ifDown
                    --     for all i/fs
                    }

ComponentRevision ::= TEXTUAL-CONVENTION
    DISPLAY-HINT "Vxx.yy"
    STATUS      current
    DESCRIPTION
        "The hex value in the first octet - xx - represent the major revision no.
        and the hex value in the second octet - yy - the minor revision no."
    SYNTAX      OCTET STRING(SIZE(2))

FrontPanelPassword ::= TEXTUAL-CONVENTION
    STATUS      current
    DESCRIPTION
        "Describes a Front Panel Password key sequence, in the following convention:
         0 - end of password string
         1 - ESC key
         2 - SEL/SAVE key
         3 - Arrow Right key
         4 - Arrow Left key
         5 - LOCAL/REMOTE key"
    SYNTAX      OCTET STRING (SIZE(0..5))

FloatingPoint ::= TEXTUAL-CONVENTION
    DISPLAY-HINT "a.bcdE-n"
    STATUS      current
    DESCRIPTION
        "The hex value in the first 2 octets specify the mantissa*1000
        (1000 =< value <= 9999) and the hex value in the 3rd octet
        specify the 10th power (1 =< n <= 15).
        Example: For user input of 1.025E-7 the hex value should be
        '040107'h."
    SYNTAX      OCTET STRING(SIZE(3))

WvLoopbacksList ::= TEXTUAL-CONVENTION
    STATUS      current
    DESCRIPTION
        "Describes the type of loopbacks that can be performed on the terminal.
        Local restrictions may dictate how many and which loopbacks can be
        performed simultaneously."
    SYNTAX      BITS {
                    filler0(0),
                    localIduInputdsx1-1(1),     	-- e1/t1 port 1
                    localIduInputdsx1-2(2),     	-- e1/t1 port 2
                    localIduInputdsx1-3(3),     	-- e1/t1 port 3
                    localIduInputdsx1-4(4),     	-- e1/t1 port 4
                    localIduInputdsx1-5(5),     	-- e1/t1 port 5
                    localIduInputdsx1-6(6),     	-- e1/t1 port 6
                    localIduInputdsx1-7(7),     	-- e1/t1 port 7
                    localIduInputdsx1-8(8),     	-- e1/t1 port 8
                    localIduInputdsx1-9(9),     	-- e1/t1 port 9
                    localIduInputdsx1-10(10),   	-- e1/t1 port 10
                    localIduInputdsx1-11(11),   	-- e1/t1 port 11
                    localIduInputdsx1-12(12),   	-- e1/t1 port 12
                    localIduInputdsx1-13(13),   	-- e1/t1 port 13
                    localIduInputdsx1-14(14),   	-- e1/t1 port 14
                    localIduInputdsx1-15(15),   	-- e1/t1 port 15
                    localIduInputdsx1-16(16),   	-- e1/t1 port 16
                    localIduInputdsx3sts1(17),  	-- e3/t3 or sts1 port
                    localIduOutput(18),
                    localOdu(19),
		    localIduInput(20),
                    remoteIdudsx1-1(21),   		-- e1/t1 port 1
                    remoteIdudsx1-2(22),   		-- e1/t1 port 2
                    remoteIdudsx1-3(23),   		-- e1/t1 port 3
                    remoteIdudsx1-4(24),   		-- e1/t1 port 4
                    remoteIdudsx1-5(25),   		-- e1/t1 port 5
                    remoteIdudsx1-6(26),   		-- e1/t1 port 6
                    remoteIdudsx1-7(27),   		-- e1/t1 port 7
                    remoteIdudsx1-8(28),   		-- e1/t1 port 8
                    remoteIdudsx1-9(29),   		-- e1/t1 port 9
                    remoteIdudsx1-10(30),  		-- e1/t1 port 10
                    remoteIdudsx1-11(31),  		-- e1/t1 port 11
                    remoteIdudsx1-12(32),  		-- e1/t1 port 12
                    remoteIdudsx1-13(33),  		-- e1/t1 port 13
                    remoteIdudsx1-14(34),  		-- e1/t1 port 14
                    remoteIdudsx1-15(35),  		-- e1/t1 port 15
                    remoteIdudsx1-16(36),  		-- e1/t1 port 16
                    remoteIdudsx3sts1(37), 		-- e3/t3 or sts1 port
		    filler38(38),
                    filler39(39),
                    filler40(40),
                    localIduInputEth10-100-1(41),	-- ETH 10/100 port 1
                    localIduInputEth10-100-2(42),       -- ETH 10/100 port 2
                    remoteIduEth10-100-1(43),   	-- ETH 10/100 port 1
                    remoteIduEth10-100-2(44)            -- ETH 10/100 port 2
                    }


-- ***##############################################################***
--              Groups within the minetMIB
-- ***##############################################################***

wvConfiguration         OBJECT IDENTIFIER ::= { minetMIB 1 }
wvStatusAndGauges       OBJECT IDENTIFIER ::= { minetMIB 2 }
wvPerformance           OBJECT IDENTIFIER ::= { minetMIB 3 }
wvTests                 OBJECT IDENTIFIER ::= { minetMIB 4 }
wvTraps                 OBJECT IDENTIFIER ::= { minetMIB 10 }

-- *** Configuration groups ***
wvLinkSettings          OBJECT IDENTIFIER ::= { wvConfiguration 1 }
wvInterfaces            OBJECT IDENTIFIER ::= { wvConfiguration 2 }
wvManagement            OBJECT IDENTIFIER ::= { wvConfiguration 3 }
wvRelays                OBJECT IDENTIFIER ::= { wvConfiguration 4 }
wvExternalInputs        OBJECT IDENTIFIER ::= { wvConfiguration 5 }
wvAlarmControl          OBJECT IDENTIFIER ::= { wvConfiguration 6 }
wvComponentsRevisions   OBJECT IDENTIFIER ::= { wvConfiguration 7 }


-- ####################################################################
-- *** Link Settings Configuration Group ***
-- ####################################################################

wvLinkId OBJECT-TYPE
    SYNTAX      INTEGER (1..99999)
    MAX-ACCESS  read-write
    STATUS      current
    DESCRIPTION
        "Radio Link ID. The 2 terminals of the link must have the same linkId
        in order to communicate.
        This value should be encrypted when carried accross the network."
    DEFVAL { 1 }
    ::= { wvLinkSettings 1 }

wvLinkName OBJECT-TYPE
    SYNTAX      DisplayString (SIZE(0..16))
    MAX-ACCESS  read-write
    STATUS      current
    DESCRIPTION
        "Radio Link Name. Limited to above size and [a-z, 0-9,-,*] because of
        the LCD."
    DEFVAL { "Codan" }
    ::= { wvLinkSettings 2 }

wvLinkRouteDescription OBJECT-TYPE
    SYNTAX      DisplayString (SIZE(0..16))
    MAX-ACCESS  read-write
    STATUS      current
    DESCRIPTION
        "Radio Link Route. Limited to above size and [a-z, 0-9,-,*]
        because of the LCD."
    DEFVAL { "siteA-siteB" }
    ::= { wvLinkSettings 3 }

wvTxPowerSetting OBJECT-TYPE
    SYNTAX      INTEGER (-10..29)
    UNITS      "dBm"
    MAX-ACCESS  read-write
    STATUS      current
    DESCRIPTION
        "The transmit power value set for this terminal, in 1dBm steps."
    DEFVAL { 10 }
    ::= { wvLinkSettings 4 }

wvChannelNo OBJECT-TYPE
    SYNTAX      INTEGER (0..2400)
    MAX-ACCESS  read-write
    STATUS      current
    DESCRIPTION
        "The frequency channel to work on. Each channel corresponds to a given
        pair of transmit and receive frequencies, depending on the ODU's
	Standard (US/European), Spectrum Range Allocation (38 Ghz, 23 Ghz,
	18 Ghz, etc...), Duplex	Spacing (700 Mhz, 1200 Mhz, 1010 Mhz, etc...)
	and Frequency Band (1, 2, 3 or 4) (see wvOduPartNo below).

        The channel nos. spacing follow the h/w resolution, that is 0.25 Mhz.

        According to the FCC standard, each chosen frequency has a minimum spacing
        of 2.5 Mhz, therefore on FCC allocations the first and last allowed frequency
        centers are 1.25 Mhz from the start/end of the below specified bands, leaving
        5 channels on start side and 4 on the end side not selectable (maybe more,
        depending on additional restrictions specific to each Duplex Spacing).

        According to the ETSI standard, each chosen frequency has a minimum spacing
        of 3.5 Mhz, therefore on ETSI allocations the first and last allowed frequency
        centers are 1.75 Mhz from the start/end of the below specified bands, leaving
        7 channels on start side and 6 on the end side not selectable (maybe more,
        depending on additional restrictions specific to each Duplex Spacing).


        *******************************************************
	*** For 38 Ghz, according to ITU-R F.749.1 standard ***
	*******************************************************

	### In the American (FCC) model ###

	=== Duplex Spacing: 700 Mhz ===

	The 38600-40000 Mhz frequency space is divided into 4 350 Mhz bands:

	1. 38600-38950
	2. 38950-39300
	3. 39300-39650
	4. 39650-40000

        Since the h/w resolution is 0.25 Mhz, we have the 350 Mhz on each band
	sub-divided into 0 - 1399 channels (with 0 sitting on the START
	of each band).

	The corresponding Operating Frequencies (center point) are calculated by:
	TxBand = 38600.00 + (Band - 1) * 350 + wvChannelNo * 0.25
	for Band = 1,2,3,4

	Since the spacing between Tx and Rx is 700 Mhz, the Rx frequency
	is deduced from the Tx frequency as follows:
	Rx1 = Tx1 + 700
	Rx2 = Tx2 + 700
	Rx3 = Tx3 - 700
	Rx4 = Tx4 - 700

	The first/last allowed wvChannelNo depends on the used channel spacing and
	is calculated as follows:

	first = wvChannelSpacing*10/5
	last  = 1400-first

	### In the European (ETSI) model ###

	=== Duplex Spacing: 1260 Mhz ===

        The 37000-39500 Mhz frequency space is divided into 4 560 Mhz bands
	(after subtracting 260 MHz guard bands):

	1. 37058-37618
	2. 37618-38178
	3. 38318-38878
	4. 38878-39438

        Since the h/w resolution is 0.25 Mhz, we have the 560 Mhz on each band
	sub-divided into 0 - 2239 channels (with 0 sitting on the START of
	each band).

	The corresponding Operating frequencies (center point) are calculated by:
        TxBand = 37058.00 + (Band - 1) * 630 + wvChannelNo * 0.25
	for Band = 1,3
	and
        TxBand = 37618.00 + (Band - 2) * 630 + wvChannelNo * 0.25
	for Band = 2,4

	Since the spacing between Tx and Rx is 1260 Mhz, the Rx frequency
	is deduced from the Tx frequency as follows:
	Rx1 = Tx1 + 1260
	Rx2 = Tx2 + 1260
	Rx3 = Tx3 - 1260
	Rx4 = Tx4 - 1260

	The first/last allowed wvChannelNo depends on the used channel spacing and
	is calculated as follows:

	first = wvChannelSpacing*10/5
	last  = 2240-first.

	********************************************************
	*** For 23 Ghz, according to ITU-R 637.2 standard ***
	********************************************************

	### In the American (FCC) model ###

	=== Duplex Spacing: 1200 Mhz ===

	The 21200-23600 Mhz frequency space is divided into 4 600 Mhz bands:

	1. 21200-21800
	2. 21800-22400
	3. 22400-23000
	4. 23000-23600

        Since the h/w resolution is 0.25 Mhz, we have the 600 Mhz on each band
	sub-divided into 0 - 2399 channels (with 0 sitting on the START
	of each band).

	The corresponding Operating Frequencies (center point) are calculated by:
	TxBand = 21200.00 + (Band - 1) * 600 + wvChannelNo * 0.25
	for Band = 1,2,3,4

	Since the spacing between Tx and Rx is 1200 Mhz, the Rx frequency
	is deduced from the Tx frequency as follows:
        Rx1 = Tx1 + 1200
	Rx2 = Tx2 + 1200
	Rx3 = Tx3 - 1200
	Rx4 = Tx4 - 1200

	The first/last allowed wvChannelNo depends on the used channel spacing and
	is calculated as follows:

	first = wvChannelSpacing*10/5
	last  = 2400-first


	### In the European (ETSI) model ###

	=== Duplex Spacing: 1008 Mhz ===

        On the 22000-23600 Mhz frequency space there are 2 592 Mhz bands
	(named bands 1 and 3 for compatibility), with a not used
	'hole' of 400 Mhz in the middle, and additional guards on start and
	end of each band, depending on the channel spacing used (note that
        not all the 592 Mhz space is used):

        1. 22000-22592
        3. 23008-23600

        Since the h/w resolution is 0.25 Mhz, we have the 592 Mhz on each band
        sub-divided into 0 - 2367 channels (with 0 sitting on the START
	of each band).

	The corresponding Operating Frequencies (center point) are calculated by:
        TxBand = 22000.00 + (Band - 1) * 504 + wvChannelNo * 0.25
        for Band = 1,3

	Since the spacing between Tx and Rx is 1008 Mhz, the Rx frequency
	is deduced from the Tx frequency as follows:
	Rx1 = Tx1 + 1008
	Rx3 = Tx3 - 1008

	The first/last allowed wvChannelNo depends on the used channel spacing
	and is given in the following table:

        wvChannelSpacing      First     Last
        ================      =====     ====

           3.5 Mhz              18      2356
           7.0 Mhz              46      2342
          14.0 Mhz              60      2300
          28.0 Mhz              88      2216
          56.0 Mhz             312      2104


	=== Duplex Spacing: 1200 Mhz ===

	The 21200-23600 Mhz frequency space is divided into 4 600 Mhz bands:

	1. 21200-21800
	2. 21800-22400
	3. 22400-23000
	4. 23000-23600

        Since the h/w resolution is 0.25 Mhz, we have the 600 Mhz on each band
	sub-divided into 0 - 2399 channels (with 0 sitting on the START
	of each band).

	The corresponding Operating Frequencies (center point) are calculated by:
	TxBand = 21200.00 + (Band - 1) * 600 + wvChannelNo * 0.25
	for Band = 1,2,3,4

	Since the spacing between Tx and Rx is 1200 Mhz, the the Rx frequency
	is deduced from the Tx frequency as follows:
	Rx1 = Tx1 + 1200
	Rx2 = Tx2 + 1200
	Rx3 = Tx3 - 1200
	Rx4 = Tx4 - 1200

	The first/last allowed wvChannelNo depends on the used channel spacing and
	is calculated as follows:

	first = wvChannelSpacing*10/5
	last  = 2400-first

        === Duplex Spacing: 1232 Mhz ===

        The 21200-23600 Mhz frequency space is divided into 4 560 Mhz bands, with
        not used 'holes' of 24 Mhz in the beginning and end of the range and 112 Mhz
        in the middle:

        1. 21224-21784
        2. 21784-22344
        3. 22456-23016
        4. 23016-23576

        Since the h/w resolution is 0.25 Mhz, we have the 560 Mhz on each band
	sub-divided into 0 - 2239 channels (with 0 sitting on the START of
	each band).

	The corresponding Operating frequencies (center point) are calculated by:
        TxBand = 21224.00 + (Band - 1) * 616 + wvChannelNo * 0.25
	for Band = 1,3
	and
        TxBand = 21784.00 + (Band - 2) * 616 + wvChannelNo * 0.25
	for Band = 2,4

        Since the spacing between Tx and Rx is 1232 Mhz, the Rx frequency
	is deduced from the Tx frequency as follows:
        Rx1 = Tx1 + 1232
        Rx2 = Tx2 + 1232
        Rx3 = Tx3 - 1232
        Rx4 = Tx4 - 1232

	The first/last allowed wvChannelNo depends on the used channel spacing and
	is calculated as follows:

	first = wvChannelSpacing*10/5
	last  = 2240-first.


	********************************************************
	*** For 18 Ghz, according to ITU-R F.595-5 standard ***
	********************************************************

	### In the American (FCC) model ###

	=== Duplex Spacing: 1560 Mhz ===

        On the 17700-19700 Mhz frequency space there are 2 440 Mhz bands (named
        bands 1 and 3 for compatibility), with a not used 'hole' of 1120 Mhz
        in the middle:

	1. 17700-18140
	3. 19260-19700

        Since the h/w resolution is 0.25 Mhz, we have the 440 Mhz on each band
	sub-divided into 0 - 1759 channels (with 0 sitting on the START
	of each band).

	The corresponding Operating Frequencies (center point) are calculated by:
	TxBand = 17700.00 + (Band - 1) * 780 + wvChannelNo * 0.25
	for Band = 1,3

	Since the spacing between Tx and Rx is 1560 Mhz, the Rx frequency
	is deduced from the Tx frequency as follows:
	Rx1 = Tx1 + 1560
	Rx3 = Tx3 - 1560

        The first/last allowed wvChannelNo depends on the used channel spacing
        and is calculated as follows:

	first = wvChannelSpacing*10/5
	last  = 1760-first

	### In the European (ETSI) model ###

	=== Duplex Spacing: 1010 Mhz ===

        The 17700-19700 Mhz frequency space is divided into 2 522.5 Mhz bands
        (Bands 1 and 3) and 2 467.5 Mhz bands (Bands 2 and 4) with a not used
	'hole' of 20 Mhz in the middle, and additional guards (proportionally
	to the channel spacing used) on start of bands 1/3 and on end of
	bands 2/4:

        1. 17700.0-18222.5
        2. 18208.75-18690.0
        3. 18710.0-19232.5
        4. 19218.75-19700.0

        Since the h/w resolution is 0.25 Mhz, we have the 522.5 Mhz on bands 1,3
        sub-divided into 0 - 2090 channels and the 481.25 Mhz on bands 2,4
        sub-divided into 0 - 1925 channels (with 0 sitting on the START of
	each band).

	The corresponding Operating frequencies (center point) are calculated by:
        TxBand = 17700.00 + (Band - 1) * 505 + wvChannelNo * 0.25
        for Band = 1,3
	and
        TxBand = 18208.75 + (Band - 2) * 505 + wvChannelNo * 0.25
        for Band = 2,4

	Since the spacing between Tx and Rx is 1010 Mhz, the Rx frequency
	is deduced from the Tx frequency as follows:
	Rx1 = Tx1 + 1010
	Rx2 = Tx2 + 1010
	Rx3 = Tx3 - 1010
	Rx4 = Tx4 - 1010

        The first/last allowed wvChannelNo depends on the used channel spacing
        and is calculated as follows:

        first = wvChannelSpacing*4 - wvChannelSpacing/14 for Bands 1,3
        first = wvChannelSpacing*2 - wvChannelSpacing/28 for Bands 2,4
        last  = 2090 - first(2,4)  for Bands 1,3
        last  = 1925 - first(1,3)  for Bands 2,4

        ***********************************************************
        *** For 26 Ghz, according to EN 300 431 v1.3.1 standard ***
        ***********************************************************

        ### In the European (ETSI) model ###

        === Duplex Spacing: 1008 Mhz ===

        The 24500-26500 Mhz frequency space is divided into 4 448 Mhz bands:

        1. 24549-24997
        2. 24997-25445
        3. 25557-26005
        4. 26005-26453

        Since the h/w resolution is 0.25 Mhz, we have the 448 Mhz on each band
        sub-divided into 0 - 1791 channels (with 0 sitting on the START
	of each band).

	The corresponding Operating Frequencies (center point) are calculated by:
        TxBand = 24549.00 + (Band - 1) * 504 + wvChannelNo * 0.25
        for Band = 1,3
        TxBand = 24597.00 + (Band - 2) * 504 + wvChannelNo * 0.25
        for Band = 2,4

        Since the spacing between Tx and Rx is 1008 Mhz, the Rx frequency
	is deduced from the Tx frequency as follows:
        Rx1 = Tx1 + 1008
        Rx2 = Tx2 + 1008
        Rx3 = Tx3 - 1008
        Rx4 = Tx4 - 1008

	The first/last allowed wvChannelNo depends on the used channel spacing and
	is calculated as follows:

	first = wvChannelSpacing*10/5
        last  = 1792-first

        **************************************************************
        *** For 15 Ghz, according to CEPT/ERC/REC 12-07 E standard ***
        **************************************************************

        ### In the European (ETSI) model ###

        === Duplex Spacing: 728 Mhz ===

        The 14500-15350 Mhz frequency space is divided into 2 112+7 Mhz bands:

        1. 14508-14620
        3. 15229-15348

        Since the h/w resolution is 0.25 Mhz, we have the 119 Mhz on each band
        sub-divided into 0 - 475 channels (with 0 sitting on the START
	of each band).

	The corresponding Operating Frequencies (center point) are calculated by:
        TxBand = 14501.00 + (Band - 1) * 364 + wvChannelNo * 0.25
        for Band = 1,3

        Since the spacing between Tx and Rx is 728 Mhz, the Rx frequency
	is deduced from the Tx frequency as follows:
        Rx1 = Tx1 + 728
        Rx3 = Tx3 - 728

	The first/last allowed wvChannelNo depends on the used channel spacing and
	is calculated as follows:

        wvChannelSpacing      First     Last
        ================      =====     ====

           3.5 Mhz               7      441
           7.0 Mhz              14      434
          14.0 Mhz              56      448
          28.0 Mhz              56      392
          56.0 Mhz             112      336

        **************************************************************
        *** For 15 Ghz, according to ITU-R F.636-3 standard        ***
        **************************************************************
	### In the European (ETSI) model ###

        === Duplex Spacing: 420 Mhz ===

        The 14500-15350 Mhz frequency space is divided into 2 224 Mhz bands
        (Bands 1 and 3) and 2 210 Mhz bands (Bands 2 and 4) :

        1. 14501-14725
        2. 14718-14928
        3. 14921-15145
        4. 15138-15348

        Since the h/w resolution is 0.25 Mhz, we have the 224 Mhz on bands 1,3
        sub-divided into 0 - 895 channels and the 210 Mhz on bands 2,4
        sub-divided into 0 - 839 channels (with 0 sitting on the START of
	each band).

	The corresponding Operating frequencies (center point) are calculated by:
        TxBand = 14501 + (Band - 1) * 210 + wvChannelNo * 0.25
        for Band = 1,3
	and
        TxBand = 14718 + (Band - 2) * 210 + wvChannelNo * 0.25
        for Band = 2,4

        Since the spacing between Tx and Rx is 420 Mhz, the Rx frequency
	is deduced from the Tx frequency as follows:
        Rx1 = Tx1 + 420
        Rx2 = Tx2 + 420
        Rx3 = Tx3 - 420
        Rx4 = Tx4 - 420

        The first/last allowed wvChannelNo depends on the used channel spacing
        and is calculated as follows:

                                Band 1,3             Band 2,4
        wvChannelSpacing      First     Last       First     Last
        ================      =====     ====       =====     ====

           3.5 Mhz               7      861           7      805
           7.0 Mhz              14      854          14      798
          14.0 Mhz              56      840          28      812
          28.0 Mhz              56      840          84      756
          56.0 Mhz             112      784         140      700

        **************************************************************
        *** For 15 Ghz,             ???                            ***
        **************************************************************
	### In the European (ETSI) model ###

        === Duplex Spacing: 315 Mhz ===

        The 14628-15228 Mhz frequency space is divided into 2 139 Mhz bands
        (Bands 1 and 3) and 2 151 Mhz bands (Bands 2 and 4) :

        1. 14628-14767
        2. 14760-14911
        3. 14943-15082
        4. 15075-15226

        Since the h/w resolution is 0.25 Mhz, we have the 139 Mhz on bands 1,3
        sub-divided into 0 - 555 channels and the 151 Mhz on bands 2,4
        sub-divided into 0 - 603 channels (with 0 sitting on the START of
	each band).

	The corresponding Operating frequencies (center point) are calculated by:
        TxBand = 14628 + (Band - 1) * 157.5 + wvChannelNo * 0.25
        for Band = 1,3
	and
        TxBand = 14760 + (Band - 2) * 157.5 + wvChannelNo * 0.25
        for Band = 2,4

        Since the spacing between Tx and Rx is 315 Mhz, the Rx frequency
	is deduced from the Tx frequency as follows:
        Rx1 = Tx1 + 315
        Rx2 = Tx2 + 315
        Rx3 = Tx3 - 315
        Rx4 = Tx4 - 315

        The first/last allowed wvChannelNo depends on the used channel spacing
        and is calculated as follows:

                                Band 1,3             Band 2,4
        wvChannelSpacing      First     Last       First     Last
        ================      =====     ====       =====     ====

           3.5 Mhz              10      528          14      588
           7.0 Mhz              24      528          28      588
          14.0 Mhz              80      472          56      560
          28.0 Mhz             136      472          56      504
          56.0 Mhz             192      416         112      448

        **************************************************************
        *** For 13 Ghz, according to CEPT/ERC/REC 12-02 E standard ***
        **************************************************************

        ### In the European (ETSI) model ###

        === Duplex Spacing: 266 Mhz ===

        The 12750-13250 Mhz frequency space is divided into 4 112 Mhz bands:

        1. 12751-12863
        2. 12863-12975
        3. 13017-13129
        4. 13129-13241

        Since the h/w resolution is 0.25 Mhz, we have the 112 Mhz on each band
        sub-divided into 0 - 447 channels (with 0 sitting on the START
	of each band).

	The corresponding Operating Frequencies (center point) are calculated by:
        TxBand = 12751.00 + (Band - 1) * 133 + wvChannelNo * 0.25
        for Band = 1,3
        TxBand = 12863.00 + (Band - 2) * 133 + wvChannelNo * 0.25
        for Band = 2,4

        Since the spacing between Tx and Rx is 266 Mhz, the Rx frequency
	is deduced from the Tx frequency as follows:
        Rx1 = Tx1 + 266
        Rx2 = Tx2 + 266
        Rx3 = Tx3 - 266
        Rx4 = Tx4 - 266

	The first/last allowed wvChannelNo depends on the used channel spacing and
	is calculated as follows:

	first = wvChannelSpacing*10/5
        last  = 448-first

        **************************************************************
        *** For 8 Ghz, according to ITU-R F.386-6 standard ***
        **************************************************************

        ### In the European (ETSI) model ###

        === Duplex Spacing: 126 Mhz ===

        The 8275-8500 Mhz frequency space is divided into 4 49 Mhz bands:

        1. 8279-8328
        2. 8321-8370
        3. 8405-8454
        4. 8447-8496

        Since the h/w resolution is 0.25 Mhz, we have the 49 Mhz on each band
        sub-divided into 0 - 195 channels (with 0 sitting on the START
	of each band).

	The corresponding Operating Frequencies (center point) are calculated by:
        TxBand = 8279.00 + (Band - 1) * 63 + wvChannelNo * 0.25
        for Band = 1,3
        TxBand = 8321.00 + (Band - 2) * 63 + wvChannelNo * 0.25
        for Band = 2,4

        Since the spacing between Tx and Rx is 126 Mhz, the Rx frequency
	is deduced from the Tx frequency as follows:
        Rx1 = Tx1 + 126
        Rx2 = Tx2 + 126
        Rx3 = Tx3 - 126
        Rx4 = Tx4 - 126

	The first/last allowed wvChannelNo depends on the used channel spacing and
	is calculated as follows:

	first = wvChannelSpacing*10/5
        last  = 196-first
	Valid wvChannelSpacing are 3.5MHz,7MHz & 14MHz.

        **************************************************************
        *** For 8 Ghz, according to ITU-R F.386-6 standard ***
        **************************************************************

        ### In the European (ETSI) model ###

        === Duplex Spacing: 119 Mhz ===

        The 8275-8500 Mhz frequency space is divided into 4 56 Mhz bands:

        1. 8279-8335
        2. 8321-8377
        3. 8398-8454
        4. 8440-8496

        Since the h/w resolution is 0.25 Mhz, we have the 56 Mhz on each band
        sub-divided into 0 - 223 channels (with 0 sitting on the START
	of each band).

	The corresponding Operating Frequencies (center point) are calculated by:
        TxBand = 8279.00 + (Band - 1) * 59.5 + wvChannelNo * 0.25
        for Band = 1,3
        TxBand = 8321.00 + (Band - 2) * 59.5 + wvChannelNo * 0.25
        for Band = 2,4

        Since the spacing between Tx and Rx is 119 Mhz, the Rx frequency
	is deduced from the Tx frequency as follows:
        Rx1 = Tx1 + 119
        Rx2 = Tx2 + 119
        Rx3 = Tx3 - 119
        Rx4 = Tx4 - 119

	The first/last allowed wvChannelNo depends on the used channel spacing and
	is calculated as follows:

	first = wvChannelSpacing*10/5
        last  = 224-first
	Valid wvChannelSpacing are 14MHz & 28MHz.

        **************************************************************
        *** For 8 Ghz, according to ITU-R F.386-6 standard ***
        **************************************************************

        ### In the European (ETSI) model ###

        === Duplex Spacing: 311.32 Mhz ===

        The 7725-8275 Mhz frequency space is divided into 4 127 Mhz bands:

        1. 7725.00-7852.00
        2. 7844.00-8971.00
        3. 8036.25-8163.25
        4. 8155.25-8282.25

	The channel number set from the following table:
      ( The numbers are transmit center frequency in MHz )

	Ch #      Band 1      Band 2      Band 3      Band 4
          0      7725.4625   7844.0625   8036.7825   8155.3825
         15      7729.1687   7847.7687   8040.4887   8159.0887
         30      7732.8750   7851.4750   8044.1950   8162.7950
         45      7736.5812   7855.1812   8047.9012   8166.5012
         60      7740.2875   7858.8875   8051.6075   8170.2075
         75      7743.9937   7862.5937   8055.3137   8173.9137
         90      7747.7000   7866.3000   8059.0200   8177.6200
        105      7751.4062   7870.0062   8062.7262   8181.3262
        120      7755.1125   7873.7125   8066.4325   8185.0325
        135      7758.8187   7877.4187   8070.1387   8188.7387
        150      7762.5250   7881.1250   8073.8450   8192.4450
        165      7766.2312   7884.8312   8077.5512   8196.1512
        180      7769.9375   7888.5375   8081.2575   8199.8575
        195      7773.6437   7892.2437   8084.9637   8203.5637
        210      7777.3500   7895.9500   8088.6700   8207.2700
        225      7781.0562   7899.6562   8092.3762   8210.9762
        240      7784.7625   7903.3625   8096.0825   8214.6825
        255      7788.4687   7907.0687   8099.7887   8218.3887
        270      7792.1750   7910.7750   8103.4950   8222.0950
        285      7795.8812   7914.4812   8107.2012   8225.8012
        300      7799.5875   7918.1875   8110.9075   8229.5075
        315      7803.2937   7921.8937   8114.6137   8233.2137
        330      7807.0000   7925.6000   8118.3200   8236.9200
        345      7810.7062   7929.3062   8122.0262   8240.6262
        360      7814.4125   7933.0125   8125.7325   8244.3325
        375      7818.1187   7936.7187   8129.4387   8248.0387
        390      7821.8250   7940.4250   8133.1450   8251.7450
        405      7825.5312   7944.1312   8136.8512   8255.4512
        420      7829.2375   7947.8375   8140.5575   8259.1575
        435      7832.9437   7951.5437   8144.2637   8262.8637
        450      7836.6500   7955.2500   8147.9700   8266.5700
        465      7840.3562   7958.9562   8151.6762   8270.2762
        480      7844.0625   7962.6625   8155.3825   8273.9825
        495      7847.7687   7966.3687   8159.0887   8277.6887

        Since the spacing between Tx and Rx is 311.32 Mhz, the Rx frequency
	is deduced from the Tx frequency as follows:
        Rx1 = Tx1 + 311.32
        Rx2 = Tx2 + 311.32
        Rx3 = Tx3 - 311.32
        Rx4 = Tx4 - 311.32

	The first/last allowed wvChannelNo depends on the used channel spacing and
	is calculated as follows:

        first = 15 for 7MHz, 30 for 14MHz , 60 for 28MHa
        last  = 510 - first
	Valid wvChannelSpacing are 14MHz & 28MHz

	NOTES:
        1. Valid channel numbers are n*15  n= 1,2,3...,32
	2. When we display the transmit frequency the format is MMMM.KK and we
           trunk the least significant numbers.


        **************************************************************
        *** For 7 Ghz, according to ITU-R F.385-6 standard ***
        **************************************************************

        ### In the European (ETSI) model ###

        === Duplex Spacing: 245 Mhz ===

        The 7425-7900 Mhz frequency space is divided into 4 112 Mhz bands:

        1. 7428-7540
        2. 7540-7652
        3. 7673-7785
        4. 7785-7897

        Since the h/w resolution is 0.25 Mhz, we have the 56 Mhz on each band
        sub-divided into 0 - 447 channels (with 0 sitting on the START
	of each band).

	The corresponding Operating Frequencies (center point) are calculated by:
        TxBand = 7428.00 + (Band - 1) * 122.5 + wvChannelNo * 0.25
        for Band = 1,3
        TxBand = 7540.00 + (Band - 2) * 122.5 + wvChannelNo * 0.25
        for Band = 2,4

        Since the spacing between Tx and Rx is 245 Mhz, the Rx frequency
	is deduced from the Tx frequency as follows:
        Rx1 = Tx1 + 245
        Rx2 = Tx2 + 245
        Rx3 = Tx3 - 245
        Rx4 = Tx4 - 245

	The first/last allowed wvChannelNo depends on the used channel spacing and
	is calculated as follows:

	first = wvChannelSpacing*10/5
        last  = 448-first

        **************************************************************
        *** For 7 Ghz, according to ITU-R F.385-6 standard ***
        **************************************************************

        ### In the European (ETSI) model ###

        === Duplex Spacing: 154 Mhz ===

        The 7125-7425 or 7425-7725 or  7250-7558  or  7550-7850 Mhz frequency space
        is divided into 2 84 Mhz bands (Bands 1 and 3)
        and 2 56 Mhz bands (Bands 2 and 4) :

        1. 7128-7212  or  7428-7512  or  7253-7337  or  7553-7637
        2. 7212-7268  or  7512-7568  or  7337-7393  or  7637-7693
        3. 7282-7366  or  7582-7666  or  7407-7491  or  7707-7791
        4. 7366-7422  or  7666-7722  or  7491-7547  or  7791-7847

        Since the h/w resolution is 0.25 Mhz, we have the 84 Mhz on bands 1,3
        sub-divided into 0 - 335 channels and the 56 Mhz on bands 2,4
        sub-divided into 0 - 223 channels (with 0 sitting on the START of
	each band).

	The corresponding Operating Frequencies (center point) are calculated by:
        TxBand = (7128.00 or 7428.00 or 7253 or 7553) +
                          (Band - 1) * 77.0 + wvChannelNo * 0.25
        for Band = 1,3
        TxBand = (7212.00 or 7512.00 or 7337 or 7637) +
                          (Band - 2) * 77.0 + wvChannelNo * 0.25
        for Band = 2,4

        Since the spacing between Tx and Rx is 154 Mhz, the Rx frequency
	is deduced from the Tx frequency as follows:
        Rx1 = Tx1 + 154
        Rx2 = Tx2 + 154
        Rx3 = Tx3 - 154
        Rx4 = Tx4 - 154

	The first/last allowed wvChannelNo depends on the used channel spacing and
	is calculated as follows:

	first = wvChannelSpacing*10/5
        last  = 336-first    for  bands 1,3
        last  = 224-first    for  bands 2,4


        **************************************************************
        *** For 7 Ghz, according to ITU-R F.385-6 standard ***
        **************************************************************

        ### In the European (ETSI) model ###

        === Duplex Spacing: 161 Mhz ===

        The 7124.5-7425.5 or 7424.5-7725.5 Mhz or 7249.5-7550.5
        frequency space is divided into 2 84 Mhz bands (Bands 1 and 3)
        and 2 56 Mhz bands (Bands 2 and 4) :

        1. 7124.5-7208.5  or  7424.5-7508.5  or  7249.5-7333.5
        2. 7208.5-7264.5  or  7508.5-7564.5  or  7333.5-7389.5
        3. 7285.5-7369.5  or  7585.5-7669.5  or  7410.5-7494.5
        4. 7369.5-7425.5  or  7669.5-7725.5  or  7494.5-7550.5

        Since the h/w resolution is 0.25 Mhz, we have the 84 Mhz on bands 1,3
        sub-divided into 0 - 335 channels and the 56 Mhz on bands 2,4
        sub-divided into 0 - 223 channels (with 0 sitting on the START of
	each band).

	The corresponding Operating Frequencies (center point) are calculated by:
        TxBand = (7124.50 or 7424.50 or 7249.50) +
                          (Band - 1) * 80.5 + wvChannelNo * 0.25
        for Band = 1,3
        TxBand = (7208.50 or 7508.50 or 7333.50) +
                          (Band - 2) * 80.5 + wvChannelNo * 0.25
        for Band = 2,4

        Since the spacing between Tx and Rx is 161 Mhz, the Rx frequency
	is deduced from the Tx frequency as follows:
        Rx1 = Tx1 + 161
        Rx2 = Tx2 + 161
        Rx3 = Tx3 - 161
        Rx4 = Tx4 - 161

	The first/last allowed wvChannelNo depends on the used channel spacing and
	is calculated as follows:

	first = wvChannelSpacing*10/5
        last  = 336-first    for  bands 1,3
        last  = 224-first    for  bands 2,4

	### In the European (ETSI) model 15GHz Australia ITU-R F.636-3###

	=== Duplex Spacing: 644 Mhz ===

        On the 14500-15350 Mhz frequency space there are 2 196 Mhz bands
	(named bands 1 and 3 for compatibility), with a not used
	'hole' of 448 Mhz in the middle, and additional guards on start and
	end of each band, depending on the channel spacing used :

        1. 14501-14697
        3. 15145-15341

        Since the h/w resolution is 0.25 Mhz, we have the 196 Mhz on each band
        sub-divided into 0 - 783 channels (with 0 sitting on the START
	of each band).

	The corresponding Operating Frequencies (center point) are calculated by:
        TxBand = 14501.00 + (Band - 1) * 98 + wvChannelNo * 0.25
        for Band = 1,3

	Since the spacing between Tx and Rx is 644 Mhz, the Rx frequency
	is deduced from the Tx frequency as follows:
	Rx1 = Tx1 + 644
	Rx3 = Tx3 - 644

	The first/last allowed wvChannelNo depends on the used channel spacing
	and is given in the following table:

	first = wvChannelSpacing*10/5
        last  = 784-first


	### In the European (ETSI) model 15GHz Australia ###

	=== Duplex Spacing: 490 Mhz ===

        On the 14403-15348 Mhz frequency space there are 4 224 Mhz bands
	(named bands 1 to 4 for compatibility):

        1. 14403-14627
        2. 14627-14821
        3. 14893-15117
        4. 15117-15341

        Since the h/w resolution is 0.25 Mhz, we have the 224 Mhz on each band
        sub-divided into 0 - 895 channels (with 0 sitting on the START
	of each band).

	The corresponding Operating Frequencies (center point) are calculated by:
        TxBand = 14403.00 + (Band - 1) * 112 + wvChannelNo * 0.25
        for Band = 1,3
    and
        TxBand = 14627.00 + (Band - 2) * 112 + wvChannelNo * 0.25
        for Band = 2,4

	Since the spacing between Tx and Rx is 490 Mhz, the Rx frequency
	is deduced from the Tx frequency as follows:
	Rx1 = Tx1 + 490
	Rx2 = Tx2 + 490
	Rx3 = Tx3 - 490
	Rx4 = Tx4 - 490

	The first/last allowed wvChannelNo depends on the used channel spacing
	and is given in the following table:

	first = wvChannelSpacing*10/5
        last  = 896-first


	### In the European (ETSI) model 15GHz Australia ###

    === Duplex Spacing: 322 Mhz ===

    The 14634-15229 Mhz frequency space is divided into 2 126 Mhz bands
    (Bands 1 and 3) and 2 140 Mhz bands (Bands 2 and 4) :

        1. 14634-14760
        2. 14767-14907
        3. 14956-15082
        4. 15089-15229

        Since the h/w resolution is 0.25 Mhz, we have the 126 Mhz on bands 1,3
        sub-divided into 0 - 504 channels and the 140 Mhz on bands 2,4
        sub-divided into 0 - 560 channels (with 0 sitting on the START of
	each band).

	The corresponding Operating frequencies (center point) are calculated by:
        TxBand = 14634 + (Band - 1) * 63 + wvChannelNo * 0.25
        for Band = 1,3
	and
        TxBand = 14760 + (Band - 2) * 70 + wvChannelNo * 0.25
        for Band = 2,4

        Since the spacing between Tx and Rx is 322 Mhz, the Rx frequency
	is deduced from the Tx frequency as follows:
        Rx1 = Tx1 + 322
        Rx2 = Tx2 + 322
        Rx3 = Tx3 - 322
        Rx4 = Tx4 - 322

    The first/last allowed wvChannelNo depends on the used channel spacing
    and is calculated as follows:

	first = wvChannelSpacing*10/5
        last  = 504-first (for band 1,3)
        last  = 560-first (for band 2,4)


    ### In the European (ETSI) model 10GHz Australia ITU-R F.747###

        === Duplex Spacing: 65 Mhz ===

        On the 10550-10680 Mhz frequency space is divided into 2 35 Mhz bands
        (Bands 1 and 3) and 2 30 Mhz bands (Bands 2 and 4) ::

        1. 10550-10585
        2. 10582.5-10615
        3. 10615-10650
        4. 10647.5-10680

        Since the h/w resolution is 0.25 Mhz, we have the 35 Mhz on bands 1,3
        sub-divided into 0 - 139 channels and the 32.5 Mhz on bands 2,4
        sub-divided into 0 - 129 channels (with 0 sitting on the START of
        each band).

	The corresponding Operating Frequencies (center point) are calculated by:
        TxBand = 10550 + (Band - 1) * 32.5 + wvChannelNo * 0.25
        for Band = 1,3
        TxBand = 10582.5 + (Band - 2) * 32.5 + wvChannelNo * 0.25
        for Band = 2,4

        Since the spacing between Tx and Rx is 65 Mhz, the Rx frequency
	is deduced from the Tx frequency as follows:
        Rx1 = Tx1 + 65
        Rx2 = Tx2 + 65
        Rx3 = Tx3 - 65
        Rx4 = Tx4 - 65

	The first/last allowed wvChannelNo depends on the used channel spacing and
	is calculated as follows:

	first = wvChannelSpacing*10/5
        last  = 140-first    for  bands 1,3
        last  = 130-first    for  bands 2,4

    ### In the European (ETSI) model 10GHz Australia ITU-R F.747###

        === Duplex Spacing: 91 Mhz ===

        On the 10500-10680 Mhz frequency space is divided into 4 42 Mhz bands:

        1. 10500.5-10542.5
        2. 10542.5-10584.5
        3. 10591.5-10633.5
        4. 10633.5-10675.5

        Since the h/w resolution is 0.25 Mhz, we have the 42 Mhz on each band
        sub-divided into 0 - 167 channels (with 0 sitting on the START
	of each band).

	The corresponding Operating Frequencies (center point) are calculated by:
        TxBand = 10500.5 + (Band - 1) * 45.5 + wvChannelNo * 0.25
        for Band = 1,3
        TxBand = 10542.5 + (Band - 2) * 45.5 + wvChannelNo * 0.25
        for Band = 2,4

        Since the spacing between Tx and Rx is 119 Mhz, the Rx frequency
	is deduced from the Tx frequency as follows:
        Rx1 = Tx1 + 91
        Rx2 = Tx2 + 91
        Rx3 = Tx3 - 91
        Rx4 = Tx4 - 91

	The first/last allowed wvChannelNo depends on the used channel spacing and
	is calculated as follows:

	first = wvChannelSpacing*10/5
        last  = 168-first


	### In the European (ETSI) model 18GHz ###

	=== Duplex Spacing: 1008 Mhz ===

        The 17720.5-19680.5 Mhz frequency space is divided into 2 500.5 Mhz bands
        (Bands 1 and 3) and 2 451.5 Mhz bands (Bands 2 and 4) with a not used
		'hole' of 56 Mhz in the middle.

        1. 17702.5-18221.0
        2. 18221.0-18672.5
        3. 18728.5-19229.0
        4. 19229.0-19700.5

        Since the h/w resolution is 0.25 Mhz, we have the 500.5 Mhz on bands 1,3
        sub-divided into 0 - 2002 channels and the 451.5 Mhz on bands 2,4
        sub-divided into 0 - 1806 channels (with 0 sitting on the START of
	each band).

	The corresponding Operating frequencies (center point) are calculated by:
        TxBand = 17702.5 + (Band - 1) * 500.5 + wvChannelNo * 0.25
        for Band = 1,3
	and
        TxBand = 18221.0 + (Band - 2) * 451.5 + wvChannelNo * 0.25
        for Band = 2,4

	Since the spacing between Tx and Rx is 1010 Mhz, the Rx frequency
	is deduced from the Tx frequency as follows:
	Rx1 = Tx1 + 1008
	Rx2 = Tx2 + 1008
	Rx3 = Tx3 - 1008
	Rx4 = Tx4 - 1008

        The first/last allowed wvChannelNo depends on the used channel spacing
        and is calculated as follows:

        first = wvChannelSpacing*4 - wvChannelSpacing/14 for Bands 1,3
        first = wvChannelSpacing*2 - wvChannelSpacing/28 for Bands 2,4
        last  = 2002 - first(2,4)  for Bands 1,3
        last  = 1806 - first(1,3)  for Bands 2,4



	wvChannelNo's default is the first allowed Channel No, according to
	the chosen channel spacing."
    ::= { wvLinkSettings 5 }

wvLinkCapacity OBJECT-TYPE
    SYNTAX      INTEGER {
                    oneE1(1),
                    twoE1(2),
                    fourE1(3),
                    eightE1(4),
                    sixteenE1(5),
                    e3(6),
                    e3PlusOneE1(7),
                    e3PlusTwoE1(8),
                    oneT1(9),
                    twoT1(10),
                    fourT1(11),
                    eightT1(12),
                    sixteenT1(13),
                    t3(14),
                    t3PlusTwoT1(15),
                    t3PlusFourT1(16),
                    sts1(17),
		    eth10-100Only(18),
		    eth10-100PlusOneE1(19),
		    eth10-100PlusTwoE1(20),
		    eth10-100PlusFourE1(21),
		    eth10-100PlusOneT1(22),
		    eth10-100PlusTwoT1(23),
		    eth10-100PlusFourT1(24)
                    }
    MAX-ACCESS  read-write
    STATUS      current
    DESCRIPTION
        "Terminal Link chosen bit rate. Enables reduced capacity work for
        a given installed plug-in (according to wvInstalledPlugInPartNo).
        All subsets of a given plug-in are allowed.
        Its default is the installed plug-in full capacity."
    ::= { wvLinkSettings 6 }

wvTransmitterMute OBJECT-TYPE
    SYNTAX      INTEGER {
                    on(1),
                    off(2)
                    }
    MAX-ACCESS  read-write
    STATUS      current
    DESCRIPTION
        "When 'on', disables this terminal's transmission to the link.
        Note that disabling transmission sets off an alarm."
    DEFVAL { off }
    ::= { wvLinkSettings 7 }

wvReceiverMute OBJECT-TYPE
    SYNTAX      INTEGER {
                    on(1),
                    off(2)
                    }
    MAX-ACCESS  read-write
    STATUS      current
    DESCRIPTION
        "When 'on', disables this terminal's reception from the link.
        Since disabling reception is regarded as a kind of alarm, setting
        of this variable causes a trap."
    DEFVAL { off }
    ::= { wvLinkSettings 8 }

wvModulation OBJECT-TYPE
    SYNTAX      INTEGER {
                    cp4fsk(2),
                    qam4(3),
                    qam8(4),
                    qam16(5),
                    qam32(6),
                    qam64(7),
                    qam128(8)
                    }
    MAX-ACCESS  read-write
    STATUS      current
    DESCRIPTION
        "Sets the terminal radio modulation.
        Not all values apply to all models."
    DEFVAL { cp4fsk }
    ::= { wvLinkSettings 9 }

wvForceAis OBJECT-TYPE
    SYNTAX      INTEGER {
                    never(1),
                    onBerWarning(2),
                    onBerError(3),
                    always(4)
                    }
    MAX-ACCESS  read-write
    STATUS      current
    DESCRIPTION
        "Defines whether to force Alarm Indication Signal (all 1's) on the
        link upon either occurence of a link BER Warning or BER Error alarm or
        unconditionally."
    DEFVAL { never }
    ::= { wvLinkSettings 10 }

wvFecEnabled OBJECT-TYPE
    SYNTAX      INTEGER {
                    on(1),
                    off(2)
                    }
    MAX-ACCESS  read-write
    STATUS      deprecated
    DESCRIPTION
        "Enables/disables the Forward Error Correction option."
    DEFVAL { on }
    ::= { wvLinkSettings 11 }

wvFecReceiveCorrection OBJECT-TYPE
    SYNTAX      INTEGER {
                    on(1),
                    off(2)
                    }
    MAX-ACCESS  read-write
    STATUS      current
    DESCRIPTION
        "Enables/disables Automatic Error Correction on receive."
    DEFVAL { on }
    ::= { wvLinkSettings 12 }

wvFecNoOfCorrectableBytes OBJECT-TYPE
    SYNTAX      INTEGER (1..20)
    MAX-ACCESS  read-write
    STATUS      current
    DESCRIPTION
        "Specifies the Forward Error Correction level on transmit.
         - for LAN plug-in the values are 10 or 20.
         - for PDH plug-in the values are read only. "
    DEFVAL { 10 }
    ::= { wvLinkSettings 13 }

wvEth10-100ChannelSpacing  OBJECT-TYPE
    SYNTAX      INTEGER {
		    -- American ODU standard --
                    twoAndAHalf(1),	-- for eth10-100Only
                    five(2),		-- *** 2.5 Mhz on the 18 Ghz Spectrum Range ***
					-- for eth10-100Only, eth10-100PlusOneT1
                    sevenAndAHalf(3),	-- *** 5 Mhz on the 18 Ghz Spectrum Range ***
					-- for eth10-100Only, eth10-100PlusOneE1,
					--     eth10-100PlusTwoE1, eth10-100PlusOneT1,
					--     eth10-100PlusTwoT1
                    twelveAndAHalf(4),  -- *** 10 Mhz on the 18 Ghz Spectrum Range ***
					-- for all ETH 10/100 capacities
                    twentyFive(5),	-- *** 20 Mhz on the 18 Ghz Spectrum Range ***
					-- for all ETH 10/100 capacities
                    fifty(6),		-- *** 40 Mhz on the 18 Ghz Spectrum Range ***
					-- for all ETH 10/100 capacities

		    -- European ODU standard --
                    threeAndAHalf(7),	-- *** 3.5 Mhz on the 18 Ghz Spectrum Range ***
					-- for eth10-100Only
                    seven(8),		-- *** 7 Mhz on the 18 Ghz Spectrum Range ***
					-- for eth10-100Only, eth10-100PlusOneE1,
					--     eth10-100PlusTwoE1,eth10-100PlusOneT1,
					--     eth10-100PlusTwoT1,eth10-100PlusFourT1
                    fourteen(9),        -- *** 13.75 Mhz on the 18 Ghz Spectrum Range ***
					-- for eth10-100Only, eth10-100PlusOneE1,
					--     eth10-100PlusTwoE1, eth10-100PlusFourE1
					--     eth10-100PlusOneT1, eth10-100PlusTwoT1,
					--     eth10-100PlusFourT1
                    twentyEight(10),    -- *** 27.5 Mhz on the 18 Ghz Spectrum Range ***
					-- for all ETH 10/100 capacities
		    fiftySix(11) 	-- *** 55 Mhz on the 18 Ghz Spectrum Range ***
					-- for all ETH 10/100 capacities
                    }
    UNITS      "MHz"
    MAX-ACCESS  read-write
    STATUS      current
    DESCRIPTION
        "Specifies the allowed frequency spacing between adjacent channels for the
	ETH 10/100 plug-in, as a function of the ODU standard (American vs. European)
	and chosen wvLinkCapacity.
	The user may specify a given spacing only if the chosen wvLinkCapacity is
	one of the specified on its right.
	Note that on the 18 Ghz Spectrum Range the actual values may be different than
	on the other ranges, and those are specifically mentioned where applicable.
	When working with ETH 10/100 plug-in, wvChannelSpacing reflects this
	object's value."
    ::= { wvLinkSettings 14 }


-- *** the Automatic Transmission Power Control (ATPC) sub-group ***

wvAtpcControl OBJECT-TYPE
    SYNTAX      INTEGER {
                    enabled(1),
                    disabled(2)
                    }
    MAX-ACCESS  read-write
    STATUS      current
    DESCRIPTION
        "Enables/disables the ATPC feature."
    DEFVAL { disabled }
    ::= { wvLinkSettings 30 }

wvAtpcRslOptimalValue OBJECT-TYPE
    SYNTAX      INTEGER (-90..-15)
    UNITS       "dBm"
    MAX-ACCESS  read-write
    STATUS      current
    DESCRIPTION
        "Defines the targeted working RSL value, for ATPC."
-- DEFVAL { -45 }
    ::= { wvLinkSettings 31 }

wvAtpcRslUpperThreshold OBJECT-TYPE
    SYNTAX      INTEGER (-90..-15)
    UNITS       "dBm"
    MAX-ACCESS  read-write
    STATUS      current
    DESCRIPTION
        "Defines the upper threshold for which, if the RSL value is greater than it
	 for more than 10 seconds, the ATPC mechanism (if enabled) will decrease
	 the remote TX power to get the RSL to wvAtpcRslOptimalValue."
-- DEFVAL { -40 }
    ::= { wvLinkSettings 32 }

wvAtpcRslLowerThreshold OBJECT-TYPE
    SYNTAX      INTEGER (-90..-15)
    UNITS       "dBm"
    MAX-ACCESS  read-write
    STATUS      current
    DESCRIPTION
        "Defines the lower threshold for which, if the RSL value is less than it
	 for more than 10 seconds, the ATPC mechanism (if enabled) will increase
	 the remote TX power to get the RSL to wvAtpcRslOptimalValue."
-- DEFVAL { -50 }
    ::= { wvLinkSettings 33 }


wvPauseTransmitterControl OBJECT-TYPE
    SYNTAX      INTEGER {
                    enabled(1),
                    disabled(2)
                    }
    MAX-ACCESS  read-write
    STATUS      current
    DESCRIPTION
        "Enables/disables the Pause Transmitter feature."
    DEFVAL { disabled }
    ::= { wvLinkSettings 34 }

wvPauseTransmitterTime OBJECT-TYPE
    SYNTAX      INTEGER (30..36000)
    UNITS       "seconds"
    MAX-ACCESS  read-write
    STATUS      current
    DESCRIPTION
        "Defines the time in seconds to hold the pause for the transmitter in mute state."
    ::= { wvLinkSettings 35 }

wvE1BNC75ohm OBJECT-TYPE
    SYNTAX      INTEGER {
                    on(1),
                    off(2)
                    }
    MAX-ACCESS  read-write
    STATUS      current
    DESCRIPTION
        "set E1 port to 75ohm."
    DEFVAL { off }
    ::= { wvLinkSettings 36 }


wvAtpcTimeOutControl OBJECT-TYPE
    SYNTAX      INTEGER {
                    enabled(1),
                    disabled(2)
                    }
    MAX-ACCESS  read-write
    STATUS      current
    DESCRIPTION
        "Enables/disables the ATPC TimeOut feature."
    DEFVAL { disabled }
    ::= { wvLinkSettings 37 }
    
wvAtpcTimeOutTimer OBJECT-TYPE
    SYNTAX      INTEGER (1..60)
    UNITS      "minutes"
    MAX-ACCESS  read-write
    STATUS      current
    DESCRIPTION
        "Atpc TimeOut timer feature."
    DEFVAL { 5 }
    ::= { wvLinkSettings 38 }

wvAtpcTimeOutAlarm OBJECT-TYPE
    SYNTAX      INTEGER {
                    enabled(1),
                    disabled(2)
                    }
    MAX-ACCESS  read-write
    STATUS      current
    DESCRIPTION
        "Enables/disables the ATPC TimeOut alarm."
    DEFVAL { disabled }
    ::= { wvLinkSettings 39 }
    
wvAtpcTimeOutAlarmLevel OBJECT-TYPE
    SYNTAX      INTEGER {
                    message(1),
                    error(2),
                    fatal(3)
                    }
    MAX-ACCESS  read-write
    STATUS      current
    DESCRIPTION
        "declare the ATPC TimeOut alarm level."
    DEFVAL { fatal }
    ::= { wvLinkSettings 40 }

wvDisableAtpcInTimeOutAlarm OBJECT-TYPE
    SYNTAX      INTEGER {
                        on(1),                       
                        off(2) 
                        }   
    MAX-ACCESS  read-write
    STATUS      current
    DESCRIPTION
        "Disable the ATPC if TimeOut alarm in active."
    DEFVAL { off }
    ::= { wvLinkSettings 41 }

wvEnableSpaceDiversity OBJECT-TYPE
    SYNTAX      INTEGER {
                        on(1),                       
                        off(2) 
                        }   
    MAX-ACCESS  read-write
    STATUS      current
    DESCRIPTION
        "Enable the Space Diversity feature in 1+1 mode."
    DEFVAL { off }
    ::= { wvLinkSettings 42 }

-- ####################################################################
-- *** Interfaces Configuration Group ***
-- ####################################################################

-- *** Interfaces Tributary ***

wvTributaryPortConnectionsMode OBJECT-TYPE
    SYNTAX      INTEGER {
                     manual(1),
                     autoSensing(2)
                     }
    MAX-ACCESS  read-write
    STATUS      current
    DESCRIPTION
        "Defines the data ports connections mode.
        In Auto Sensing mode the system automatically detects which ports are
        connected. In Manual mode user choices are reflected through
        the interfaces wvTributaryPortConnection settings (see below)."
    DEFVAL { manual }
    ::= { wvInterfaces 1 }

wvTributaryPortTable OBJECT-TYPE
    SYNTAX      SEQUENCE OF WvTributaryPortEntry
    MAX-ACCESS  not-accessible
    STATUS      current
    DESCRIPTION
        "A table for private extensions to standard interface MIBs (like
        dsx1/dsx3)."
    ::= { wvInterfaces 2 }

wvTributaryPortEntry OBJECT-TYPE
    SYNTAX      WvTributaryPortEntry
    MAX-ACCESS  not-accessible
    STATUS      current
    DESCRIPTION
        "Entry in the wvTributaryPortTable."
    INDEX       { wvTributaryPortIfIndex }
    ::= { wvTributaryPortTable 1 }

WvTributaryPortEntry ::= SEQUENCE {
    wvTributaryPortIfIndex        Integer32,
    wvTributaryPortConnection     INTEGER,
    wvTributaryPortInvertedAlarm  INTEGER,
    wvTributaryPortName           DisplayString
    }

wvTributaryPortIfIndex OBJECT-TYPE
    SYNTAX      Integer32
    MAX-ACCESS  read-only
    STATUS      current
    DESCRIPTION
        "The value of this object is equal to the value of ifIndex for the
        corresponding interface on the Interfaces table of MIB-II.
        Note that the possible wvTributaryPortIfIndex values depend on the
        available interfaces, according to wvInstalledPlugInPartNo."
    ::= { wvTributaryPortEntry 1 }

wvTributaryPortConnection OBJECT-TYPE
    SYNTAX      INTEGER {
                    enabled(0),
                    disabled(1)
                    }
    MAX-ACCESS  read-write
    STATUS      current
    DESCRIPTION
        "Determines if this port is connected or not.
        Note that the maximum number of connected ports is a subset of the
        available data ports (according to wvInstalledPlugInPartNo), and
        can not exceed the chosen wvLinkCapacity.
        The default connections are the first ones available.
        Applicable only when wvTributaryPortConnectionsMode is set to manual."
    ::= { wvTributaryPortEntry 2 }

wvTributaryPortInvertedAlarm OBJECT-TYPE
    SYNTAX      INTEGER {
                    enabled(1),
                    disabled(2)
                    }
    MAX-ACCESS  read-write
    STATUS      current
    DESCRIPTION
        "Determines if this line has inverted alarm enabled.
        A line with inverted alarm enabled will report an alarm if either
        'no LOS' or 'AIS' is detected (meaning that the line is alive).
        This condition is indicated as Unexpected Signal Detection alarm.
        The default is disabled (not inverted)."
    ::= { wvTributaryPortEntry 3 }


wvTributaryPortName OBJECT-TYPE
    SYNTAX      DisplayString (SIZE(0..16))
    MAX-ACCESS  read-write
    STATUS      current
    DESCRIPTION
        "Specifies the prefix string for Tributary Port."
    ::= { wvTributaryPortEntry 4 }



wvDsx3CableLengthRange OBJECT-TYPE
    SYNTAX      INTEGER {
                    upTo225Feet(1),
                    moreThan225Feet(2)
                    }
    MAX-ACCESS  read-write
    STATUS      current
    DESCRIPTION
        "Defines the cable length range of the DS3/E3 line, for proper
        interface support."
    DEFVAL { upTo225Feet }
    ::= { wvInterfaces 3 }


-- *** Interfaces IDU SLIP ***

wvSlipConnection OBJECT-TYPE
    SYNTAX      INTEGER {
                    direct(1),
                    modem(2)
                    }
    MAX-ACCESS  read-write
    STATUS      current
    DESCRIPTION
        "Defines the type of SLIP connection to the IDU.
        ??? Couldn't this be self detectable ???"
    DEFVAL { direct }
    ::= { wvInterfaces 4 }

wvTelephoneNumber OBJECT-TYPE
    SYNTAX      DisplayString (SIZE(0..30))
    MAX-ACCESS  read-write
    STATUS      current
    DESCRIPTION
        "Specifies the telephone number for dial-back purposes (e.g., for
        TFTP connection)."
    ::= { wvInterfaces 5 }

wvDialPrefixString OBJECT-TYPE
    SYNTAX      DisplayString (SIZE(0..16))
    MAX-ACCESS  read-write
    STATUS      current
    DESCRIPTION
        "Specifies the prefix string for modem dial up ."
    DEFVAL { "ATDT" }
    ::= { wvInterfaces 6 }

wvInitString OBJECT-TYPE
    SYNTAX      DisplayString (SIZE(0..32))
    MAX-ACCESS  read-write
    STATUS      current
    DESCRIPTION
        "Specifies the string to be sent to the modem for initialization ."
    DEFVAL { "ATZ" }
    ::= { wvInterfaces 7 }

-- *** Interfaces ETH 10/100 ***

wvEth10-100SysCtrl OBJECT-TYPE
    SYNTAX      BITS {
                    aging(0),
                    crcCheck(1),
                    flowCtrl(2)
                    }
    MAX-ACCESS  read-write
    STATUS      current
    DESCRIPTION
        "Specifies General ETH 10/100 Board controls."
    ::= { wvInterfaces 20 }

wvEth10-100SysAgingTime OBJECT-TYPE
    SYNTAX      INTEGER (0..524280)
    UNITS       "seconds"
    MAX-ACCESS  read-write
    STATUS      current
    DESCRIPTION
        "Specifies ETH 10/100 Board Aging Time.
	 Given value will be rounded down to highest multiple of 8."
    DEFVAL { 80 }
    ::= { wvInterfaces 21 }

wvEth10-100PortTable OBJECT-TYPE
    SYNTAX      SEQUENCE OF WvEth10-100PortEntry
    MAX-ACCESS  not-accessible
    STATUS      current
    DESCRIPTION
        "A table for ETH 10/100 ports."
    ::= { wvInterfaces 22 }

wvEth10-100PortEntry OBJECT-TYPE
    SYNTAX      WvEth10-100PortEntry
    MAX-ACCESS  not-accessible
    STATUS      current
    DESCRIPTION
        "Entry in the wvEth10-100PortTable."
    INDEX       { wvEth10-100PortIfIndex }
    ::= { wvEth10-100PortTable 1 }

WvEth10-100PortEntry ::= SEQUENCE {
    wvEth10-100PortIfIndex	Integer32,
    wvEth10-100PortCtrl     	BITS,
    wvEth10-100PortStatus     	BITS,
    wvEth10-100PortClearStats   Integer32,
    wvEth10-100PortThroughputCtrl INTEGER 
    }

wvEth10-100PortIfIndex OBJECT-TYPE
    SYNTAX      Integer32
    MAX-ACCESS  read-only
    STATUS      current
    DESCRIPTION
        "The value of this object is equal to the value of ifIndex for the
        corresponding interface on the Interfaces table of MIB-II.
        Note that the possible wvEth10-100PortIfIndex values depend on the
        available interfaces, according to wvInstalledPlugInPartNo."
    ::= { wvEth10-100PortEntry 1 }

wvEth10-100PortCtrl OBJECT-TYPE
    SYNTAX      BITS {
                    fastSpeed(0),
                    fullDuplex(1),
                    autoNegotiation(2),
                    forceDisconnectOnLinkDown(3)
                    }
    MAX-ACCESS  read-write
    STATUS      current
    DESCRIPTION
        "Specifies specific ETH 10/100 Port controls."
    ::= { wvEth10-100PortEntry 2 }

wvEth10-100PortStatus OBJECT-TYPE
    SYNTAX      BITS {
                    fastSpeedOn(0),
                    fullDuplexOn(1),
		    cslAlarm(2),	-- Carrier Sense Lost
		    ecAlarm(3),		-- Excessive Collisions
		    imteAlarm(4),	-- Internal Mac Transmit Errors
		    imreAlarm(5)        -- Internal Mac Receive Errors
                    }
    MAX-ACCESS  read-only
    STATUS      current
    DESCRIPTION
        "Keeps the specific ETH 10/100 Port status."
    ::= { wvEth10-100PortEntry 3 }

wvEth10-100PortClearStats OBJECT-TYPE
    SYNTAX      Integer32
    MAX-ACCESS  read-write
    STATUS      current
    DESCRIPTION
        "Setting of this object clears the specific ETH 10/100 port statistics.
	The value given with the object is not relevant and it's not checked."
    ::= { wvEth10-100PortEntry 4 }


wvEth10-100PortThroughputCtrl OBJECT-TYPE  
    SYNTAX      INTEGER {     
                    unlimited(1),
                    limit128K(2),
                    limit256K(3),
                    limit512K(4),
                    limit1M  (5),
                    limit2M  (6),
                    limit4M  (7),
                    limit8M  (8)
                    }
    MAX-ACCESS  read-write
    STATUS      current
    DESCRIPTION
        "Specifies specific ETH 10/100 Port Throughput controls."
    DEFVAL { unlimited }
    ::= { wvEth10-100PortEntry 5 }

wvEth10-100AvailCapacity OBJECT-TYPE
    SYNTAX      Integer32
    UNITS       "Bits/sec"
    MAX-ACCESS  read-only
    STATUS      current
    DESCRIPTION
        "Shows the link capacity available for the ETH 10/100, after deducting the
	 capacity used by the DS1s from the total available spectrum."
    ::= { wvInterfaces 23 }


-- *** Interfaces RS-232 ***

-- RS-232-like General Port Table objects supported on Codan 8800 DMR.
-- Also the corresponding standard objects from Rs232PortTable and rs232AsyncPortTable
-- are supported and reflect below objects' values.

wvRs232PortTable OBJECT-TYPE
    SYNTAX SEQUENCE OF WvRs232PortEntry
    MAX-ACCESS not-accessible
    STATUS current
    DESCRIPTION
        "A list of port entries.  The number of entries is
        given by the value of rs232Number."
    ::= { wvInterfaces 30 }

wvRs232PortEntry OBJECT-TYPE
    SYNTAX WvRs232PortEntry
    MAX-ACCESS not-accessible
    STATUS current
    DESCRIPTION
        "Status and parameter values for a port."
    INDEX { wvRs232PortIndex }
    ::= { wvRs232PortTable 1 }

WvRs232PortEntry ::=
    SEQUENCE {
        wvRs232PortIndex
            Integer32,
        wvRs232PortType
            INTEGER,
	wvRs232PortSpeed
    	    Integer32,
	wvRs232PortFlowType
            INTEGER,
	wvRs232AsyncPortBits
            INTEGER,
	wvRs232AsyncPortStopBits
            INTEGER,
	wvRs232AsyncPortParity
            INTEGER
    }

wvRs232PortIndex OBJECT-TYPE
    SYNTAX Integer32
    MAX-ACCESS read-only
    STATUS current
    DESCRIPTION
        "Same as original rs232PortIndex:
	The value of ifIndex for the port.  By convention
        and if possible, hardware port numbers map directly
        to external connectors.  The value for each port must
        remain constant at least from one re-initialization
        of the network management agent to the next."
    ::= { wvRs232PortEntry 1 }

wvRs232PortType OBJECT-TYPE
    SYNTAX INTEGER { rs232(2), rs422(3) }
    MAX-ACCESS read-write
    STATUS current
    DESCRIPTION
	"The port's hardware type.
        Same as original rs232PortType, but read-write and with restricted values."
    ::= { wvRs232PortEntry 2 }

wvRs232PortSpeed OBJECT-TYPE
    SYNTAX Integer32
    MAX-ACCESS read-write
    STATUS current
    DESCRIPTION
	"The port's input/output speed in bits per second.  Note that
        non-standard values, such as 9612, are probably not allowed
        on most implementations.
        Same as original rs232PortInSpeed and rs232PortOutSpeed."
    ::= { wvRs232PortEntry 3 }

wvRs232PortFlowType OBJECT-TYPE
    SYNTAX INTEGER { none(1), xonXoff(2) }
    MAX-ACCESS read-write
    STATUS current
    DESCRIPTION
        "The port's type of input flow control.  'none'
        indicates no flow control at this level.
        Same as original rs232PortInFlowType and rs232PortOutFlowType,
	but with different values."
    ::= { wvRs232PortEntry 4 }

wvRs232AsyncPortBits OBJECT-TYPE
    SYNTAX INTEGER (7..8)
    MAX-ACCESS read-write
    STATUS current
    DESCRIPTION
        "The port's number of bits in a character.
        Same as original rs232AsyncPortBits, but with restricted values."
    ::= { wvRs232PortEntry 5 }

wvRs232AsyncPortStopBits OBJECT-TYPE
    SYNTAX INTEGER { one(1), two(2) }
    MAX-ACCESS read-write
    STATUS current
    DESCRIPTION
        "The port's number of stop bits.
        Same as original rs232AsyncPortStopBits, but with restricted values."
    ::= { wvRs232PortEntry 6 }

wvRs232AsyncPortParity OBJECT-TYPE
    SYNTAX INTEGER { none(1), odd(2), even(3) }
    MAX-ACCESS read-write
    STATUS current
    DESCRIPTION
        "The port's sense of a character parity bit.
        Same as original rs232AsyncPortParity, but with restricted values."
    ::= { wvRs232PortEntry 7 }


-- ####################################################################
-- *** Configuration Management Group ***
-- ####################################################################

-- *** Management General ***

wvUpdateTerminalConfiguration OBJECT-TYPE
    SYNTAX      Integer32
    MAX-ACCESS  read-write
    STATUS      current
    DESCRIPTION
        "Initializes a configuration update process from the manager to either the
	Active or one of the Saved Configurations on the terminal.
	The actual updated configuration is specified through the community in the request,
	as explained below on the wvCommunityTable Description.
        If the Update is to one of the Saved Configurations then it is saved on
	non-volatile memory.
        If the Update is to the Active Configuration then the changed parameters are
	activated.
	The value given with the object is not relevant and it's not checked."
    ::= { wvManagement 2 }

wvActivateTerminalConfiguration OBJECT-TYPE
    SYNTAX      Integer32
    MAX-ACCESS  read-write
    STATUS      current
    DESCRIPTION
        "Initializes a configuration transfer process on the terminal from
	one of the Saved Configurations to the Active Configuration, according
	to wvActivateTerminalConfigurationTime (see below).
	The actual activated configuration is specified through the community
	in the request, as explained below on the wvCommunityTable Description.
	The value given with the object is not relevant and it's not checked."
    ::= { wvManagement 3 }

wvResetTerminal OBJECT-TYPE
    SYNTAX      INTEGER {
                    cold(1),
                    warm(2),            -- IDU only!!!
                    coldSwitchOver(3),	-- IDU switchover only!!!
                    terminalSwitchOver(4), -- IDU + ODU switchover
                    running(5),
                    oduSwitchOver(6) -- ODU switchover only!!!
                    }
    MAX-ACCESS  read-write
    STATUS      current
    DESCRIPTION
        "Activates a cold/warm reset at the terminal.
        A cold reset is performed at both the IDU and the ODU and stops all
	communications with the device.
        A warm reset affects only IDU NMS operation and doesn't interrupt data
        communications.
        A cold switch-over reset, in addition to performing a cold reset,
	causes the IDU to restart with the stand-by software (see wvSwModuleTable)
	becoming the active one, and the active software becoming the stand-by one."
    DEFVAL { warm }
    ::= { wvManagement 4 }

wvActivateTerminalConfigurationTime OBJECT-TYPE
    SYNTAX      TimeTicks
    MAX-ACCESS  read-write
    STATUS      current
    DESCRIPTION
        "Defines the time, relative to sysUpTime, when the wvActivateTerminalConfiguration
        request should be performed.
        If when set this value is 0 then the the activation is performed immediately."
    ::= { wvManagement 5 }

wvSavedActiveConfiguration OBJECT-TYPE
    SYNTAX      INTEGER {
                    savedConfiguration1(1),
                    savedConfiguration2(2),
                    savedConfiguration3(3),
                    factoryDefault(4),
		    none(5)
                    }
    MAX-ACCESS  read-only
    STATUS      deprecated
    DESCRIPTION
        "Specifies which of the Saved Configurations currently reflects the
	Active Configuration.
	It is set to 'none' following a successful wvUpdateTerminalConfiguration
	to the Active Configuration.
	It is set to any of the other values following a successful
	wvActivateTerminalConfiguration request, according to the specified
	configuration."
    ::= { wvManagement 6 }

-- 1+1 Operations

wvOnePlusOneRequestSwitchOut OBJECT-TYPE
    SYNTAX      Integer32
    MAX-ACCESS  read-write
    STATUS      current
    DESCRIPTION
        "For 1+1 systems only:
	Simulates a 'Switch-Out' request on the current unit.
	If not a 1+1 system, the request is rejected.
	The value given with the object is not relevant and it's not checked."
    ::= { wvManagement 7 }


-- *** Management Security Parameters ***

wvFrontPanelUserPassword OBJECT-TYPE
    SYNTAX      FrontPanelPassword
    MAX-ACCESS  read-write
    STATUS      current
    DESCRIPTION
        "Specifies the Password for User privilege Front Panel access."
    DEFVAL { '0101010101'h }
    ::= { wvManagement 10 }

wvFrontPanelAdminPassword OBJECT-TYPE
    SYNTAX      FrontPanelPassword
    MAX-ACCESS  read-write
    STATUS      current
    DESCRIPTION
        "Specifies the Password for Admin privilege Front Panel access."
    DEFVAL { '0101020202'h }
    ::= { wvManagement 11 }

wvFrontPanelSupervisorPassword OBJECT-TYPE
    SYNTAX      FrontPanelPassword
    MAX-ACCESS  read-write
    STATUS      current
    DESCRIPTION
        "Specifies the Password for Supervisor privilege Front Panel access."
    DEFVAL { '0101030304'h }
    ::= { wvManagement 12 }


-- *** ODU Operations ***

wvResetOdu OBJECT-TYPE
    SYNTAX      INTEGER {
                    cold(1),
                    coldSwitchOver(2),
                    running(3)
                    }
    MAX-ACCESS  read-write
    STATUS      current
    DESCRIPTION
        "Activates an ODU only cold reset.
        This will cause the link to be restarted.
        A cold switch-over reset, in addition to performing a cold reset,
	causes the ODU to restart with the stand-by software (see wvSwModuleTable)
	becoming the active one, and the active software becoming the stand-by one."
    DEFVAL { cold }
    ::= { wvManagement 15 }


-- *** Management IP Parameters ***
-- Local Terminal
-- The terminal's IP parameters are defined as per the MIB-II IP address
-- table as read-only, therefore we need read-write entries for our service
-- interfaces.
-- They're individually defined as scalars and not as a table, and their ifIndex
-- are pre-defined in the agent.

wvSlipInIPAddress OBJECT-TYPE
    SYNTAX  IpAddress
    MAX-ACCESS  read-write
    STATUS  current
    DESCRIPTION
            "The terminals' Slip-In IP address."
    ::= { wvManagement 20 }

wvSlipInIPSubnetMask OBJECT-TYPE
    SYNTAX  IpAddress
    MAX-ACCESS  read-write
    STATUS  current
    DESCRIPTION
            "The subnet mask associated with wvSlipInIPAddress.
            The value of the mask is an IP address with all the network
            bits set to 1 and all the hosts bits set to 0."
    ::= { wvManagement 21 }

wvSlipOutIPAddress OBJECT-TYPE
    SYNTAX  IpAddress
    MAX-ACCESS  read-write
    STATUS  current
    DESCRIPTION
            "The terminals' Slip-Out IP address."
    ::= { wvManagement 22 }

wvSlipOutIPSubnetMask OBJECT-TYPE
    SYNTAX  IpAddress
    MAX-ACCESS  read-write
    STATUS  current
    DESCRIPTION
            "The subnet mask associated with wvSlipOutIPAddress.
            The value of the mask is an IP address with all the network
            bits set to 1 and all the hosts bits set to 0."
    ::= { wvManagement 23 }

wvLanIPAddress OBJECT-TYPE
    SYNTAX  IpAddress
    MAX-ACCESS  read-write
    STATUS  current
    DESCRIPTION
            "The terminals' LAN IP address."
    ::= { wvManagement 24 }

wvLanIPSubnetMask OBJECT-TYPE
    SYNTAX  IpAddress
    MAX-ACCESS  read-write
    STATUS  current
    DESCRIPTION
            "The subnet mask associated with wvLanIPAddress.
            The value of the mask is an IP  address with all the network
            bits set to 1 and all the hosts bits set to 0."
    ::= { wvManagement 25 }

wvLinkIPAddress OBJECT-TYPE
    SYNTAX  IpAddress
    MAX-ACCESS  read-write
    STATUS  current
    DESCRIPTION
            "The terminals' link IP address."
    ::= { wvManagement 26 }

wvLinkIPSubnetMask OBJECT-TYPE
    SYNTAX  IpAddress
    MAX-ACCESS  read-write
    STATUS  current
    DESCRIPTION
            "The subnet mask associated with wvLinkIPAddress.
            The value of the mask is an IP  address with all the network
            bits set to 1 and all the hosts bits set to 0."
    ::= { wvManagement 27 }

wvEth10-100ManIPAddress OBJECT-TYPE
    SYNTAX  IpAddress
    MAX-ACCESS  read-write
    STATUS  current
    DESCRIPTION
            "The terminals' ETH 10/100 IP address."
    ::= { wvManagement 28 }

wvEth10-100ManIPSubnetMask OBJECT-TYPE
    SYNTAX  IpAddress
    MAX-ACCESS  read-write
    STATUS  current
    DESCRIPTION
            "The subnet mask associated with wvEth10-100ManIPAddress.
            The value of the mask is an IP  address with all the network
            bits set to 1 and all the hosts bits set to 0."
    ::= { wvManagement 29 }


-- Peer Terminal
-- Since the peer terminal interface can not be defined here, it's IP parameters
-- are defined so that they can be reached through the local terminal.

wvPeerSlipInIPAddress OBJECT-TYPE
    SYNTAX  IpAddress
    MAX-ACCESS  read-only
    STATUS  current
    DESCRIPTION
            "The peer terminals' Slip-In IP address."
    ::= { wvManagement 30 }

wvPeerSlipInIPSubnetMask OBJECT-TYPE
    SYNTAX  IpAddress
    MAX-ACCESS  read-only
    STATUS  current
    DESCRIPTION
            "The subnet mask associated with wvPeerSlipInIPAddress.
            The value of the mask is an IP address with all the network
            bits set to 1 and all the hosts bits set to 0."
    ::= { wvManagement 31 }

wvPeerSlipOutIPAddress OBJECT-TYPE
    SYNTAX  IpAddress
    MAX-ACCESS  read-only
    STATUS  current
    DESCRIPTION
            "The peer terminals' Slip-Out IP address."
    ::= { wvManagement 32 }

wvPeerSlipOutIPSubnetMask OBJECT-TYPE
    SYNTAX  IpAddress
    MAX-ACCESS  read-only
    STATUS  current
    DESCRIPTION
            "The subnet mask associated with wvPeerSlipOutIPAddress.
            The value of the mask is an IP address with all the network
            bits set to 1 and all the hosts bits set to 0."
    ::= { wvManagement 33 }

wvPeerLanIPAddress OBJECT-TYPE
    SYNTAX  IpAddress
    MAX-ACCESS  read-only
    STATUS  current
    DESCRIPTION
            "The peer terminals' LAN IP address."
    ::= { wvManagement 34 }

wvPeerLanIPSubnetMask OBJECT-TYPE
    SYNTAX  IpAddress
    MAX-ACCESS  read-only
    STATUS  current
    DESCRIPTION
            "The subnet mask associated with wvPeerLanIPAddress.
            The value of the mask is an IP  address with all the network
            bits set to 1 and all the hosts bits set to 0."
    ::= { wvManagement 35 }

wvPeerLinkIPAddress OBJECT-TYPE
    SYNTAX  IpAddress
    MAX-ACCESS  read-only
    STATUS  current
    DESCRIPTION
            "The peer terminals' link IP address."
    ::= { wvManagement 36 }

wvPeerLinkIPSubnetMask OBJECT-TYPE
    SYNTAX  IpAddress
    MAX-ACCESS  read-only
    STATUS  current
    DESCRIPTION
            "The subnet mask associated with wvPeerLinkIPAddress.
            The value of the mask is an IP  address with all the network
            bits set to 1 and all the hosts bits set to 0."
    ::= { wvManagement 37 }

wvPeerEth10-100ManIPAddress OBJECT-TYPE
    SYNTAX  IpAddress
    MAX-ACCESS  read-only
    STATUS  current
    DESCRIPTION
            "The peer terminals' ETH 10/100  IP address."
    ::= { wvManagement 38 }

wvPeerEth10-100ManIPSubnetMask OBJECT-TYPE
    SYNTAX  IpAddress
    MAX-ACCESS  read-only
    STATUS  current
    DESCRIPTION
            "The subnet mask associated with wvPeerEth10-100ManIPAddress.
            The value of the mask is an IP  address with all the network
            bits set to 1 and all the hosts bits set to 0."
    ::= { wvManagement 39 }


-- Slip Destination Terminals
-- The SLIP protocol requires the address of the terminal's counterpart
-- to be pre-known.

wvSlipInDestIPAddress OBJECT-TYPE
    SYNTAX  IpAddress
    MAX-ACCESS  read-write
    STATUS  current
    DESCRIPTION
            "The IP address of the destination connected to the Slip-In port."
    ::= { wvManagement 40 }

wvSlipInDestIPSubnetMask OBJECT-TYPE
    SYNTAX  IpAddress
    MAX-ACCESS  read-write
    STATUS      deprecated
    DESCRIPTION
            "The subnet mask associated with wvSlipInDestIPAddress.
            The value of the mask is an IP address with all the network
            bits set to 1 and all the hosts bits set to 0."
    ::= { wvManagement 41 }

wvSlipOutDestIPAddress OBJECT-TYPE
    SYNTAX  IpAddress
    MAX-ACCESS  read-write
    STATUS  current
    DESCRIPTION
            "The IP address of the destination connected to the Slip-Out port."
    ::= { wvManagement 42 }

wvSlipOutDestIPSubnetMask OBJECT-TYPE
    SYNTAX  IpAddress
    MAX-ACCESS  read-write
    STATUS      deprecated
    DESCRIPTION
            "The subnet mask associated with wvSlipOutDestIPAddress.
            The value of the mask is an IP address with all the network
            bits set to 1 and all the hosts bits set to 0."
    ::= { wvManagement 43 }


-- 1+1 Companion Slip Addresses
-- IP addresses of the other unit on a "1+1" system

wvOnePlusOneCompanionLinkIPAddress OBJECT-TYPE
    SYNTAX  IpAddress
    MAX-ACCESS  read-only
    STATUS  current
    DESCRIPTION
            "The companion terminals' link IP address.
	     VAlid only if system is a '1+1', according to wvOnePlusOneStatus."
    ::= { wvManagement 44 }

wvOnePlusOneCompanionEthIPAddress OBJECT-TYPE
    SYNTAX  IpAddress
    MAX-ACCESS  read-write
    STATUS  current
    DESCRIPTION
            "The Companion Eth(LAN)IP address in '1+1' system."
    ::= { wvManagement 45 }


wvUserRoutesManagement            OBJECT IDENTIFIER ::= { wvManagement 50 }
-- *** User Routes Table ***
-- The NMS user has no rights to update the System Routing (Forwarding) Table.
-- On the other hand - the user should have possibility to add his own static routes
-- by updating the User Routes Table: add update or delete static routes
-- The updated User Routes Table will be flushed to the System Routing Table on activation phase
-- No syntax or semantic checking will be done on that phase -
-- the user is in charge to define static routes correctly




wvUserRoutesTable OBJECT-TYPE
    SYNTAX      SEQUENCE OF WvUserRoutesEntry
    MAX-ACCESS  not-accessible
    STATUS      current
    DESCRIPTION
        "A table of the user defined static routes."
    ::= { wvUserRoutesManagement 1 }

wvUserRoutesCount OBJECT-TYPE
    SYNTAX      INTEGER(0..10)       -- limited to 10 entries
    MAX-ACCESS  read-only
    STATUS      current
    DESCRIPTION
        "The number of entries in User Routes Table."
    ::= { wvUserRoutesManagement 2 }

wvUserRoutesEntry OBJECT-TYPE
    SYNTAX      WvUserRoutesEntry
    MAX-ACCESS  not-accessible
    STATUS      current
    DESCRIPTION
        "Entry in the wvUserRoutesTable. The table has a variable size, limited
	to the range specified by wvUserRoutesIndex below.
	Deletion of a row is achieved by setting wvUserRoutesType to  value.
	Creation of a new route is achieved by setting any of the read-write fields with a
	index = Current-Last-Index + 1. "
    INDEX       { wvUserRoutesIndex }
    ::= { wvUserRoutesTable 1 }

WvUserRoutesEntry ::= SEQUENCE {
    wvUserRoutesIndex           INTEGER,
    wvUserRoutesDest            IpAddress,
    wvUserRoutesHop             IpAddress,
    wvUserRoutesMask            IpAddress,
    wvUserRoutesIf              INTEGER,
    wvUserRoutesType            INTEGER
    }

wvUserRoutesIndex OBJECT-TYPE
    SYNTAX      INTEGER(1..10)       -- limited to 10 entries
    MAX-ACCESS  read-only
    STATUS      current
    DESCRIPTION
        "The entry index."
    ::= { wvUserRoutesEntry 1 }

wvUserRoutesDest OBJECT-TYPE
    SYNTAX      IpAddress
    MAX-ACCESS  read-write
    STATUS      current
    DESCRIPTION
        "The route destination."
    ::= { wvUserRoutesEntry 2 }

wvUserRoutesHop OBJECT-TYPE
    SYNTAX      IpAddress
    MAX-ACCESS  read-write
    STATUS      current
    DESCRIPTION
        "The route hop."
    ::= { wvUserRoutesEntry 3 }

wvUserRoutesMask OBJECT-TYPE
    SYNTAX      IpAddress
    MAX-ACCESS  read-write
    STATUS      current
    DESCRIPTION
        "The route mask."
    ::= { wvUserRoutesEntry 4 }

wvUserRoutesIf OBJECT-TYPE
    SYNTAX      INTEGER{
                    eth        (1),
                    eth10-100  (2),
		    link       (3),
		    nms-in     (4),
		    nms-out    (5),
		    sys-choice (6)
                    }
    MAX-ACCESS  read-write
    STATUS      current
    DESCRIPTION
        " Set requested interface for the route ."
    ::= { wvUserRoutesEntry 5 }

wvUserRoutesType OBJECT-TYPE
    SYNTAX      INTEGER{
                    valid    (1),
                    invalid  (2)
                    }
    MAX-ACCESS  read-write
    STATUS      current
    DESCRIPTION
        " Set  for route deleting ."
    ::= { wvUserRoutesEntry 6 }




-- *** Management SNMP Parameters ***

-- Set operations synchronization objects:
-- Since only one manager is allowed to perform set operations at a given time,
-- before starting a set operation, a manager must first obtain 'ownership' of
-- set operation. This is accomplished with the wvSetOperationId and
-- wvSetOperationCtrl objects as follows:
--
-- A manager station first retrieves the value of the wvSetOperationId and
-- wvSetOperationCtrl, periodically repeating the retrieval if necessary,
-- until the value of wvSetOperationCtrl is 'setDisabled'.  The manager
-- station then tries to set the wvSetOperationId object to the value just
-- retrieved, the wvSetOperationCtrl object to 'setEnabled', and the
-- wvSetOperationOwner object to some unique identity value. If the set
-- operation succeeds then the manager has obtained ownership of the set
-- operations, and the value of wvSetOperationId object is incremented by
-- the agent (per the semantics of TestAndIncr).
-- Failure of the set operation indicates that some other manager has
-- obtained ownership of the set operations.
-- Once ownership is obtained, set operations can be performed by this manager,
-- and only it, according to normal access control policies.
-- When the manager is finished with the set operations, it should set
-- wvSetOperationCtrl back to 'setDisabled'.
-- To prevent lock of the set operations by an inactive manager station,
-- if no set operation is performed for 10 minutes, the agent times-out the
-- manager, and resets the value of the wvSetOperationCtrl back to
-- 'setDisabled'."
--

wvSetOperationId OBJECT-TYPE
    SYNTAX       TestAndIncr
    MAX-ACCESS   read-write
    STATUS       current
    DESCRIPTION
         "This object identifies the current successful invocation of the
         set operation."
    ::= { wvManagement 100 }

wvSetOperationCtrl OBJECT-TYPE
    SYNTAX      INTEGER {
                    setEnabled(1),
                    setDisabled(2)
                    }
    MAX-ACCESS  read-write
    STATUS      current
    DESCRIPTION
        "This object synchronizes between several cooperating manager stations,
        to coordinate their use of the set operation.
        If it is set to 'setDisabled' no SNMP set operations are performed by
        the agent."
    ::= { wvManagement 101 }

wvSetOperationOwner OBJECT-TYPE
    SYNTAX      DisplayString (SIZE(0..80))
    MAX-ACCESS  read-write
    STATUS      current
    DESCRIPTION
        "The entity which currently has the 'ownership'
        required to perform set operations."
    ::= { wvManagement 102 }

wvConfigurationChangedStatus OBJECT-TYPE
    SYNTAX      BITS {
                   filler(0),
                   wvLinkSettings(1),        -- on this MIB
                   wvInterfaces(2),          -- on this MIB
                   interfaces(3),            -- on Interfaces MIB
                   ifTestTable(4),           -- on Interfaces MIB
                   ipAddrTable(5),           -- on MIB-II
                   dsx1ConfigTable(6),       -- on DS1/E1 MIB
                   dsx3ConfigTable(7),       -- on DS3/E3 MIB
                   rs232(8),                 -- on RS-232-like MIB
                   wvManagement(9),          -- on this MIB
                   system(10),               -- on MIB-II
                   wvRelayTable(11),         -- on this MIB
                   wvExternalInputTable(12), -- on this MIB
                   wvAlarmControl(13),       -- on this MIB
                   wvTests(14)               -- on this MIB
                    }
    MAX-ACCESS  read-write
    STATUS      deprecated
    DESCRIPTION
        "A bit is set for a family by the agent to indicate that a
        configuration parameter in the corresponding family has been changed.
        It is the manager's responsibility to reset set bits."
    ::= { wvManagement 103 }


-- *** SNMP Communities Table ***
-- The choice of the terminal configuration to be worked on depend on the community given.
-- Every get or set request (pdu) to any of the configurations (that is, read-write parameters)
-- is sent with a read or write community, that is derived from one of the original read/write
-- communities defined below by the user, as follows (for more details, see "Configurations
-- Handling Concept" document, from Sep. 23, 1998, by Y. Roitman):
-- Active Configuration (get request or set to be activated only on the
--   wvUpdateTerminalConfiguration request) -
--	original read/write community string, as in the table.
-- Active Configuration (set to be activated immediately - "on-the-fly") -
--      original write community string prefixed and suffixed by #A#
-- Saved Configuration n -
--      original read/write community string prefixed and suffixed by #n# (n = 1,2, ...N)
-- Default Configuration -
--      original read community string prefixed and suffixed by #0#
-- For example, if the user defined a read community of public and a write community of the 8800 DMR then:
--  *  a get from Saved Configuration 2 will use community string "#2#public#2#"
--  *  a set of not on-the-fly parameters to Active Configuration  will use community string "codan"
--  *  a set of on-the-fly parameters to Active Configuration  will use community string "#A#codan#A#"
--  *  a get from Default Configuration will use community string "#0#public#0#"
--  *  a set to Saved Configuration 3 will use community string "#3#codan#3#"
-- Requests to non-configurable parameters (read-only) can be given with any (or none)
-- of the above additions.



wvCommunityTable OBJECT-TYPE
    SYNTAX      SEQUENCE OF WvCommunityEntry
    MAX-ACCESS  not-accessible
    STATUS      current
    DESCRIPTION
        "A table of SNMP community settings."
    ::= { wvManagement 110 }

wvCommunityEntry OBJECT-TYPE
    SYNTAX      WvCommunityEntry
    MAX-ACCESS  not-accessible
    STATUS      current
    DESCRIPTION
        "Entry in the wvCommunityTable. The table has a variable size, limited
	to the range specified by wvCommunityId below.
	Deletion of a row is achieved by setting wvCommunityName to the
	NULL string.
	Creation of a new row is achieved by setting wvCommunityName with a
	non-existing index to a non-NULL string.
	Setting of wvCommunityPrivilege with a non-existing index is rejected."
    INDEX       { wvCommunityId }
    ::= { wvCommunityTable 1 }

WvCommunityEntry ::= SEQUENCE {
    wvCommunityId               INTEGER,
    wvCommunityName             DisplayString,
    wvCommunityPrivilege        INTEGER
    }

wvCommunityId OBJECT-TYPE
    SYNTAX      INTEGER(1..5)       -- limited to 5 entries
    MAX-ACCESS  read-only
    STATUS      current
    DESCRIPTION
        "The entry index."
    ::= { wvCommunityEntry 1 }

wvCommunityName OBJECT-TYPE
    SYNTAX      DisplayString (SIZE(0..32))
    MAX-ACCESS  read-write
    STATUS      current
    DESCRIPTION
        "The name of the community."
    ::= { wvCommunityEntry 2 }

wvCommunityPrivilege OBJECT-TYPE
    SYNTAX      INTEGER{
                    readOnly(1),
                    readWrite(2)
                    }
    MAX-ACCESS  read-write
    STATUS      current
    DESCRIPTION
        "Sets the privilege of the community which name is given by
        wvCommunityName ."
    ::= { wvCommunityEntry 3 }

-- SNMP Trap Recipients Table

wvTrapRecipientsTable OBJECT-TYPE
    SYNTAX      SEQUENCE OF WvTrapRecipientsEntry
    MAX-ACCESS  not-accessible
    STATUS      current
    DESCRIPTION
        "A table of SNMP trap managers IP addresses."
    ::= { wvManagement 111 }

wvTrapRecipientsEntry OBJECT-TYPE
    SYNTAX      WvTrapRecipientsEntry
    MAX-ACCESS  not-accessible
    STATUS      current
    DESCRIPTION
        "Entry in the wvTrapRecipientsTable. The table has a variable size,
	limited	to the range specified by wvTrapRecipientsId below.
	Deletion of a row is achieved by setting wvTrapRecipientsId to 0.0.0.0.
	Creation of a new row is achieved by setting wvTrapRecipientsId
	with a non-existing index to any value different than 0.0.0.0."
    INDEX       { wvTrapRecipientsId }
    ::= { wvTrapRecipientsTable 1 }

WvTrapRecipientsEntry ::= SEQUENCE {
    wvTrapRecipientsId          INTEGER,
    wvTrapRecipientsIp          IpAddress
    }

wvTrapRecipientsId OBJECT-TYPE
    SYNTAX      INTEGER(1..5)       -- limited to 5 entries
    MAX-ACCESS  read-only
    STATUS      current
    DESCRIPTION
        "The entry index."
    ::= { wvTrapRecipientsEntry 1 }

wvTrapRecipientsIp OBJECT-TYPE
    SYNTAX      IpAddress
    MAX-ACCESS  read-write
    STATUS      current
    DESCRIPTION
        "The IP Address of the manager to receive the trap."
    ::= { wvTrapRecipientsEntry 2 }

-- *** Management TFTP (Software/Configuration Download) ***

wvTftpServerIpAddress OBJECT-TYPE
    SYNTAX      IpAddress
    MAX-ACCESS  read-write
    STATUS      current
    DESCRIPTION
        "Defines the IP Address of the TFTP server."
    ::= { wvManagement 200 }

wvTftpOperationCtrl OBJECT-TYPE
    SYNTAX      INTEGER {
                    enabled(1),
                    disabled(2)
                    }
    MAX-ACCESS  read-write
    STATUS      current
    DESCRIPTION
        "When disabled no TFTP can be performed.
        This allows a high privilege authority to disallow lower privilege
        managers to initialize TFTP from this terminal.
        Note that since the agent has no notion of privilege levels
        (user/admin/supervisor) it has no means to check authentication of
        the entity setting this object, and the privilege distinctions are made
        at the managers' level."
    ::= { wvManagement 201 }

wvTftpNoOfRetries OBJECT-TYPE
    SYNTAX      INTEGER (0..30)
    MAX-ACCESS  read-write
    STATUS      current
    DESCRIPTION
        "Determines the no. of retries to be performed by the terminal upon
        TFTP failures. A value of 0 means to try forever until successful or
        deliberately stopped."
    ::= { wvManagement 202 }

wvTftpFileName OBJECT-TYPE
    SYNTAX      DisplayString (SIZE(0..128))
    MAX-ACCESS  read-write
    STATUS      current
    DESCRIPTION
        "Defines the full name of the file to be TFTP'ed."
    DEFVAL { "\codan.lst" }
    ::= { wvManagement 203 }

wvTftpStartTime OBJECT-TYPE
    SYNTAX      TimeTicks
    MAX-ACCESS  read-write
    STATUS      current
    DESCRIPTION
        "Defines the desired delay time, in time-ticks, before the TFTP is started.
        When TFTP is on, either on delay or started, setting wvTftpStartTime to 0
	forces a premature stop."
    ::= { wvManagement 204 }

wvTftpRemainingStartTime OBJECT-TYPE
    SYNTAX      TimeTicks
    MAX-ACCESS  read-only
    STATUS      current
    DESCRIPTION
        "Defines the ongoing remaining time before the TFTP starts."
    ::= { wvManagement 205 }


-- *** Management Software Modules Table ***

--     The Software Modules Table is used to provide information regarding the
--     active software versions and the standby software versions.
--     The active version for each module is the currently running version.
--     Performing reset of the terminal with the switchOver option (see
--     wvResetTerminal) causes the stand-by version to become active, and the
--     active version to become stand-by.
--

wvSwModuleTable OBJECT-TYPE
    SYNTAX      SEQUENCE OF WvSwModuleEntry
    MAX-ACCESS  not-accessible
    STATUS      current
    DESCRIPTION
    "The Terminal Software Modules table."
    ::= { wvManagement 210 }


wvResetPerformance OBJECT-TYPE
    SYNTAX      INTEGER {
                    on(1),
                    off(2)
                    }
    MAX-ACCESS  read-write
    STATUS      current
    DESCRIPTION
        "When setting to 'on' it will Reset the Performance parameters. 
        Reading this object will return allways 'off'."
    DEFVAL { off }
    ::= { wvManagement 215 }

wvSwModuleEntry OBJECT-TYPE
    SYNTAX      WvSwModuleEntry
    MAX-ACCESS  not-accessible
    STATUS      current
    DESCRIPTION
    "Entry in the wvSwModuleTable."
    INDEX   { wvSwModuleIndex }
    ::= { wvSwModuleTable 1 }

WvSwModuleEntry ::= SEQUENCE {
    wvSwModuleIndex             INTEGER,
    wvSwModuleName              DisplayString,
    wvSwModuleActiveRev         ComponentRevision,
    wvSwModuleActiveCS          INTEGER,
    wvSwModuleStandByRev        ComponentRevision,
    wvSwModuleStandByCS         INTEGER
    }

wvSwModuleIndex OBJECT-TYPE
    SYNTAX      INTEGER(1..65535)
    MAX-ACCESS  read-only
    STATUS      current
    DESCRIPTION
    "An index to the Software Modules Table."
    ::= { wvSwModuleEntry 1 }


wvSwModuleName  OBJECT-TYPE
    SYNTAX     DisplayString (SIZE(0..15))
    MAX-ACCESS read-only
    STATUS     current
    DESCRIPTION
    "The software module name. For example: Kernel, Agent."
    ::= { wvSwModuleEntry 2 }

wvSwModuleActiveRev  OBJECT-TYPE
    SYNTAX     ComponentRevision
    MAX-ACCESS read-only
    STATUS     current
    DESCRIPTION
    "The module active software revision. This string
    will have a zero length if the revision is unknown."
    ::= { wvSwModuleEntry 3 }

wvSwModuleActiveCS OBJECT-TYPE
    SYNTAX      INTEGER(0..65535)
    MAX-ACCESS  read-only
    STATUS      current
    DESCRIPTION
    "The module active software check-sum."
    ::= { wvSwModuleEntry 4 }

wvSwModuleStandByRev  OBJECT-TYPE
    SYNTAX     ComponentRevision
    MAX-ACCESS read-only
    STATUS     current
    DESCRIPTION
    "The module stand-by software revision. This string
    will have a zero length if the revision is unknown."
    ::= { wvSwModuleEntry 5 }

wvSwModuleStandByCS OBJECT-TYPE
    SYNTAX      INTEGER(0..65535)
    MAX-ACCESS  read-only
    STATUS      current
    DESCRIPTION
    "The module stand-by software check-sum."
    ::= { wvSwModuleEntry 6 }


-- ####################################################################
-- *** Relays Configuration Group ***
-- ####################################################################

wvRelayTable OBJECT-TYPE
    SYNTAX      SEQUENCE OF WvRelayEntry
    MAX-ACCESS  not-accessible
    STATUS      current
    DESCRIPTION
        "A table of relays settings.
        There are 7 entries in the table: 5 actual relays, a buzzer as 6th
        entry and a general purpose external TTL output as 7th entry."
    ::= { wvRelays 1 }

wvRelayEntry OBJECT-TYPE
    SYNTAX      WvRelayEntry
    MAX-ACCESS  not-accessible
    STATUS      current
    DESCRIPTION
        "Entry in the wvRelayTable."
    INDEX       { wvRelayId }
    ::= { wvRelayTable 1 }

WvRelayEntry ::= SEQUENCE {
    wvRelayId                   INTEGER,
    wvRelayOperation            INTEGER,
    wvRelayNormalState          INTEGER,
    wvRelayActivate             INTEGER,
    wvRelayToLocalAlarmMapping  WvAlarmsList,
    wvRelayToRemoteAlarmMapping WvAlarmsList,
    wvRelayStatus               INTEGER
    }

wvRelayId OBJECT-TYPE
    SYNTAX      INTEGER(1..7)
    MAX-ACCESS  read-only
    STATUS      current
    DESCRIPTION
        "The entry index."
    ::= { wvRelayEntry 1 }

wvRelayOperation OBJECT-TYPE
    SYNTAX      INTEGER {
                    enabled(1),
                    disabled(2)
                    }
    MAX-ACCESS  read-write
    STATUS      current
    DESCRIPTION
        "Enables/disables given relay."
    DEFVAL { enabled }
    ::= { wvRelayEntry 2 }

wvRelayNormalState OBJECT-TYPE
    SYNTAX      INTEGER {
                    open(1),        -- for TTL it means Low
                    closed(2)       -- for TTL it means High
                    }
    MAX-ACCESS  read-write
    STATUS      current
    DESCRIPTION
        "Defines the normal state of the relay or TTL out.
        Buzzer normal state is always off, and can not be chosen."
    DEFVAL { open }
    ::= { wvRelayEntry 3 }

wvRelayActivate OBJECT-TYPE
    SYNTAX      INTEGER {
                    off(1),
                    on(2)
                    }
    MAX-ACCESS  read-write
    STATUS      current
    DESCRIPTION
        "Manually activates the relay."
    DEFVAL { off }
    ::= { wvRelayEntry 4 }

wvRelayToLocalAlarmMapping OBJECT-TYPE
    SYNTAX      WvAlarmsList
    MAX-ACCESS  read-write
    STATUS      current
    DESCRIPTION
        "Bits in the list set to on will cause the given relay to be activated
        when any of the corresponding local alarms occur."
    ::= { wvRelayEntry 5 }

wvRelayToRemoteAlarmMapping OBJECT-TYPE
    SYNTAX      WvAlarmsList
    MAX-ACCESS  read-write
    STATUS      current
    DESCRIPTION
        "Bits in the list set to on will cause the given relay to be activated
        when any of the corresponding remote alarms occur."
    ::= { wvRelayEntry 6 }

wvRelayStatus OBJECT-TYPE
    SYNTAX      INTEGER {
                    open(1),        -- for TTL it means Low
                    closed(2)       -- for TTL it means High
                    }
    MAX-ACCESS  read-only
    STATUS      current
    DESCRIPTION
        "Describes the current state of the given relay."
    ::= { wvRelayEntry 7 }


-- ####################################################################
-- *** External Inputs Configuration Group ***
-- ####################################################################

wvExternalInputTable OBJECT-TYPE
    SYNTAX      SEQUENCE OF WvExternalInputEntry
    MAX-ACCESS  not-accessible
    STATUS      current
    DESCRIPTION
        "A table of external inputs settings."
    ::= { wvExternalInputs 1 }

wvExternalInputEntry OBJECT-TYPE
    SYNTAX      WvExternalInputEntry
    MAX-ACCESS  not-accessible
    STATUS      current
    DESCRIPTION
        "Entry in the wvExternalInputTable."
    INDEX       { wvExternalInputId }
    ::= { wvExternalInputTable 1 }

WvExternalInputEntry ::= SEQUENCE {
    wvExternalInputId               INTEGER,
    wvExternalInputSetting          INTEGER,
    wvExternalInputSense            INTEGER,
    wvExternalInputAlarmSeverity    INTEGER,
    wvExternalInputStatus           INTEGER
    }

wvExternalInputId OBJECT-TYPE
    SYNTAX      INTEGER(1..8)       -- there are 8 external inputs
    MAX-ACCESS  read-only
    STATUS      current
    DESCRIPTION
        "The entry index."
    ::= { wvExternalInputEntry 1 }

wvExternalInputSetting OBJECT-TYPE
    SYNTAX      INTEGER {
                    enabled(1),
                    disabled(2)
                    }
    MAX-ACCESS  read-write
    STATUS      current
    DESCRIPTION
        "Enables/disables given external input."
    DEFVAL { enabled }
    ::= { wvExternalInputEntry 2 }

wvExternalInputSense OBJECT-TYPE
    SYNTAX      INTEGER {
                    low(1),
                    high(2),
                    anyChange(3)
                    }
    MAX-ACCESS  read-write
    STATUS      current
    DESCRIPTION
        "Sets the sense on which the input alarm is defined as active."
    DEFVAL { high }
    ::= { wvExternalInputEntry 3 }

wvExternalInputAlarmSeverity OBJECT-TYPE
    SYNTAX      INTEGER {
                    warning(1),
                    error(2),
                    fatal(3)
                    }
    MAX-ACCESS  read-write
    STATUS      current
    DESCRIPTION
        "Defines the alarm severity of given input."
    DEFVAL { error }
    ::= { wvExternalInputEntry 4 }

wvExternalInputStatus OBJECT-TYPE
    SYNTAX      INTEGER {
                    active(1),
                    notActive(2)
                    }
    MAX-ACCESS  read-only
    STATUS      current
    DESCRIPTION
        "Describes the current state of the given input."
    ::= { wvExternalInputEntry 5 }


-- ####################################################################
-- *** Alarm Control Configuration Group ***
-- ####################################################################

wvAlarmsReportToNMSCtrl OBJECT-TYPE
    SYNTAX      INTEGER {
                    all(1),
                    errorAndFatal(2),
                    fatalOnly(3),
                    none(4)
                    }
    MAX-ACCESS  read-write
    STATUS      current
    DESCRIPTION
        "Defines the severity level of the alarms to be asynchronoulsy
        reported by the agent to the managers specified in the
        wvTrapRecepientsIpTable."
    DEFVAL { errorAndFatal }
    ::= { wvAlarmControl 1 }

wvAlarmsReportToLCDCtrl OBJECT-TYPE
    SYNTAX      INTEGER {
                    all(1),
                    errorAndFatal(2),
                    fatalOnly(3),
                    none(4)
                    }
    MAX-ACCESS  read-write
    STATUS      current
    DESCRIPTION
        "Defines the severity level of the alarms to be displayed at the
        front panel LCD."
    DEFVAL { fatalOnly }
    ::= { wvAlarmControl 2 }

wvNoOfAlertsOnLCD OBJECT-TYPE
    SYNTAX      INTEGER (1..50)
    MAX-ACCESS  read-write
    STATUS      current
    DESCRIPTION
        "Limits the number of alarms to be displayed at the front panel LCD."
    DEFVAL { 15 }
    ::= { wvAlarmControl 3 }

-- Performance Alarms Threshold Parameters

wvLinkBERWarningThresholdHigh OBJECT-TYPE
    SYNTAX      FloatingPoint
    MAX-ACCESS  read-write
    STATUS      current
    DESCRIPTION
        "Defines the high water mark above which the terminal enters the link
        BER warning alarm state.
        If wvLinkxxxBER in a given wvLinkThresholdMeasurementInterval
        gets above this value a wvlinkBERWarningAlarm is set, to be
        canceled if the value gets below wvLinkBERWarningThresholdLow
        (see below)."
    DEFVAL { '03e805'h }        -- 1.000E-5
    ::= { wvAlarmControl 4 }

wvLinkBERWarningThresholdLow OBJECT-TYPE
    SYNTAX      FloatingPoint
    MAX-ACCESS  read-write
    STATUS      current
    DESCRIPTION
        "Defines the low water mark below which the terminal exits the
        link BER warning alarm state."
    DEFVAL { '03e806'h }        -- 1.000E-6
    ::= { wvAlarmControl 5 }

wvLinkBERErrorThresholdHigh OBJECT-TYPE
    SYNTAX      FloatingPoint
    MAX-ACCESS  read-write
    STATUS      current
    DESCRIPTION
        "Defines the high water mark above which the terminal enters the
        link BER error alarm state.
        If wvxxxlinkBER in a given wvLinkThresholdMeasurementInterval gets
        above this value a wvlinkBERFailureAlarm is set, to be canceled
        if the value gets below wvLinkBERErrorThresholdLow (see below)."
    DEFVAL { '03e802'h }        -- 1.000E-2
    ::= { wvAlarmControl 6 }

wvLinkBERErrorThresholdLow OBJECT-TYPE
    SYNTAX      FloatingPoint
    MAX-ACCESS  read-write
    STATUS      current
    DESCRIPTION
        "Defines the low water mark below which the terminal exits the
        link BER error alarm state."
    DEFVAL { '03e803'h }        -- 1.000E-3
    ::= { wvAlarmControl 7 }

  wvLinkBLERAlarmThresholdHigh OBJECT-TYPE
    SYNTAX      FloatingPoint
    MAX-ACCESS  read-write
    STATUS      current
    DESCRIPTION
        "Defines the high water mark above which the terminal enters the
        link Blocks Error Rate alarm state.
        If wvLinkxxxBLER in a given wvLinkThresholdMeasurementInterval gets
        above this value a wvlinkBLERAlarm is set, to be canceled if the value
        gets below wvLinkBLERAlarmThresholdLow (see below)."
    DEFVAL { '03e802'h }        -- 1.000E-2
    ::= { wvAlarmControl 8 }

wvLinkBLERAlarmThresholdLow OBJECT-TYPE
    SYNTAX      FloatingPoint
    MAX-ACCESS  read-write
    STATUS      current
    DESCRIPTION
        "Defines the low water mark below which the terminal exits the
        link Blocks Error Rate alarm state."
    DEFVAL { '03e803'h }        -- 1.000E-3
    ::= { wvAlarmControl 9 }

  wvLinkBBERAlarmThresholdHigh OBJECT-TYPE
    SYNTAX      FloatingPoint
    MAX-ACCESS  read-write
    STATUS      current
    DESCRIPTION
        "Defines the high water mark above which the terminal enters the
        link Blocks Background Error Rate alarm state.
        If wvLinkxxxBBER in a given wvLinkThresholdMeasurementInterval gets
        above this value a wvlinkBBERAlarm is set, to be canceled if the value
        gets below wvLinkBBERAlarmThresholdLow (see below)."
    DEFVAL { '03e802'h }        -- 1.000E-2
    ::= { wvAlarmControl 10 }

wvLinkBBERAlarmThresholdLow OBJECT-TYPE
    SYNTAX      FloatingPoint
    MAX-ACCESS  read-write
    STATUS      current
    DESCRIPTION
        "Defines the low water mark below which the terminal exits the
        link Blocks Error Rate alarm state."
    DEFVAL { '03e803'h }        -- 1.000E-3
    ::= { wvAlarmControl 11 }

wvLinkNCBLERAlarmThresholdHigh OBJECT-TYPE
    SYNTAX      FloatingPoint
    MAX-ACCESS  read-write
    STATUS      current
    DESCRIPTION
        "Defines the high water mark above which the terminal enters the
        link Not Corrected Blocks Error Rate alarm state.
        If wvLinkxxxNCBLER in a given wvLinkThresholdMeasurementInterval gets
        above this value a wvLinkNCBLERAlarm is set, to be canceled
        if the value gets below wvLinkNCBLERAlarmThresholdLow (see below)."
    DEFVAL { '03e802'h }        -- 1.000E-2
    ::= { wvAlarmControl 12 }

wvLinkNCBLERAlarmThresholdLow OBJECT-TYPE
    SYNTAX      FloatingPoint
    MAX-ACCESS  read-write
    STATUS      current
    DESCRIPTION
        "Defines the low water mark below which the terminal exits the
        link Not Corrected Blocks Error Rate alarm state."
    DEFVAL { '03e803'h }        -- 1.000E-3
    ::= { wvAlarmControl 13 }

wvLinkESAlarmThresholdHigh OBJECT-TYPE
    SYNTAX      INTEGER (0..10000)
    MAX-ACCESS  read-write
    STATUS      current
    DESCRIPTION
        "Defines the high water mark above which the terminal enters the
        link Errored Seconds alarm state.
        If wvLinkxxxESs in a given wvLinkThresholdMeasurementInterval gets above
        this value a wvLinkESAlarm is set, to be canceled
        if the value gets below wvLinkESAlarmThresholdLow (see below).
        The value is expressed as a percentage x 100 of the elapsed time
        specified by wvLinkThresholdMeasurementInterval."
    DEFVAL { 1000 }
    ::= { wvAlarmControl 14 }

wvLinkESAlarmThresholdLow OBJECT-TYPE
    SYNTAX      INTEGER (0..10000)
    MAX-ACCESS  read-write
    STATUS      current
    DESCRIPTION
        "Defines the low water mark below which the terminal exits the
        link Errored Seconds alarm state.
        The value is expressed as a percentage x 100 of the elapsed time
        specified by wvLinkThresholdMeasurementInterval."
    DEFVAL { 900 }
    ::= { wvAlarmControl 15 }

wvLinkSESAlarmThresholdHigh OBJECT-TYPE
    SYNTAX      INTEGER (0..10000)
    MAX-ACCESS  read-write
    STATUS      current
    DESCRIPTION
        "Defines the high water mark above which the terminal enters the
        link Severely Errored Seconds alarm state.
        If wvLinkxxxSESs in a given wvLinkThresholdMeasurementInterval gets
        above this value a wvLinkSESAlarm is set, to be canceled
        if the value gets below wvLinkSESAlarmThresholdLow (see below).
        The value is expressed as a percentage x 100 of the elapsed time
        specified by wvLinkThresholdMeasurementInterval."
    DEFVAL { 1000 }
    ::= { wvAlarmControl 16 }

wvLinkSESAlarmThresholdLow OBJECT-TYPE
    SYNTAX      INTEGER (0..10000)
    MAX-ACCESS  read-write
    STATUS      current
    DESCRIPTION
        "Defines the low water mark below which the terminal exits the
        link Severely Errored Seconds alarm state.
        The value is expressed as a percentage x 100 of the elapsed time
        specified by wvLinkThresholdMeasurementInterval."
    DEFVAL { 900 }
    ::= { wvAlarmControl 17 }

wvLinkDMAlarmThresholdHigh OBJECT-TYPE
    SYNTAX      INTEGER (0..10000)
    MAX-ACCESS  read-write
    STATUS      current
    DESCRIPTION
        "Defines the high water mark above which the terminal enters the
        link Degraded Minutes alarm state.
        If wvLinkxxxDMs in a given wvLinkThresholdMeasurementInterval gets above
        this value a wvLinkDMAlarm is set, to be canceled
        if the value gets below wvLinkDMAlarmThresholdLow (see below).
        The value is expressed as a percentage x 100 of the elapsed time
        specified by wvLinkThresholdMeasurementInterval."
    DEFVAL { 1000 }
    ::= { wvAlarmControl 18 }

wvLinkDMAlarmThresholdLow OBJECT-TYPE
    SYNTAX      INTEGER (0..10000)
    MAX-ACCESS  read-write
    STATUS      current
    DESCRIPTION
        "Defines the low water mark below which the terminal exits the
        link Degraded Minutes alarm state.
        The value is expressed as a percentage x 100 of the elapsed time
        specified by wvLinkThresholdMeasurementInterval."
    DEFVAL { 900 }
    ::= { wvAlarmControl 19 }

wvLinkUASAlarmThresholdHigh OBJECT-TYPE
    SYNTAX      INTEGER (0..10000)
    MAX-ACCESS  read-write
    STATUS      current
    DESCRIPTION
        "Defines the high water mark above which the terminal enters the
        link Unavailable Seconds alarm state.
        If wvLinkxxxUASs in a given wvLinkThresholdMeasurementInterval gets
        above this value a wvLinkUASAlarm is set, to be canceled
        if the value gets below wvLinkUASAlarmThresholdLow (see below).
        The value is expressed as a percentage x 100 of the elapsed time
        specified by wvLinkThresholdMeasurementInterval."
    DEFVAL { 1000 }
    ::= { wvAlarmControl 20 }

wvLinkUASAlarmThresholdLow OBJECT-TYPE
    SYNTAX      INTEGER (0..10000)
    MAX-ACCESS  read-write
    STATUS      current
    DESCRIPTION
        "Defines the low water mark below which the terminal exits the
        link Unavailable Seconds alarm state.
        The value is expressed as a percentage x 100 of the elapsed time
        specified by wvLinkThresholdMeasurementInterval."
    DEFVAL { 900 }
    ::= { wvAlarmControl 21 }

wvlinkRSLLowAlarmThresholdhHigh OBJECT-TYPE
    SYNTAX      INTEGER (-100..-10)
    UNITS       "dBm"
    MAX-ACCESS  read-write
    STATUS      current
    DESCRIPTION
        "Defines the high water mark above which the terminal enters the
        link rslLow alarm state.
        If wvLinkxxxRSL in a given wvLinkThresholdMeasurementInterval gets
        above this value a rslLow is set, to be canceled
        if the value gets below wvlinkRSLLowAlarmThresholdLow (see below)."
-- DEFVAL { -70 }
    ::= { wvAlarmControl 22 }

wvlinkRSLLowAlarmThresholdhLow OBJECT-TYPE
    SYNTAX      INTEGER (-100..-10)
    UNITS       "dBm"
    MAX-ACCESS  read-write
    STATUS      current
    DESCRIPTION
        "Defines the low water mark below which the terminal exits the
        link rslLow alarm state."
--  DEFVAL { -65 }
    ::= { wvAlarmControl 23 }

wvlinkAverageRSLLowAlarmThresholdhHigh OBJECT-TYPE
    SYNTAX      INTEGER (-100..-10)
    UNITS       "dBm"
    MAX-ACCESS  read-write
    STATUS      current
    DESCRIPTION
        "Defines the high water mark above which the terminal enters the
        link averageRSLLow alarm state.
        If wvLinkxxxAverageRSL in a given wvLinkThresholdMeasurementInterval
        gets above this value a averageRSLLow is set, to be canceled
        if the value gets below wvlinkAverageRSLLowAlarmThresholdLow
        (see below)."
-- DEFVAL { -60 }
    ::= { wvAlarmControl 24 }

wvlinkAverageRSLLowAlarmThresholdhLow OBJECT-TYPE
    SYNTAX      INTEGER (-100..-10)
    UNITS       "dBm"
    MAX-ACCESS  read-write
    STATUS      current
    DESCRIPTION
        "Defines the low water mark below which the terminal exits the
        link averageRSLLow alarm state."
--  DEFVAL { -55 }
    ::= { wvAlarmControl 25 }

wvLinkThresholdMeasurementInterval OBJECT-TYPE
    SYNTAX      INTEGER (0..900)      -- up to 15 minutes
    UNITS       "seconds"
    MAX-ACCESS  read-write
    STATUS      current
    DESCRIPTION
        "Defines the periodical interval against which the link performance
        alarm thresholds are to be checked.
        A value of zero means no link performance alarms should be issued."
    DEFVAL { 30 }
  ::= { wvAlarmControl 26 }

-- *** ETH 10/100 ***

wvEth10-100CSLAlarmThresholdhHigh OBJECT-TYPE
    SYNTAX      INTEGER (0..50)
    MAX-ACCESS  read-write
    STATUS      current
    DESCRIPTION
        "Defines the high water mark above which the terminal enters the
        ETH 10/100 Carrier Sense Lost alarm state.
        If dot3StatsCarrierSenseErrors for any ETH 10-100 port gets above this value
	in a given wvEth10-100ThresholdMeasurementInterval, a eth10-100PortCSLAlarm
	is set, to be canceled if the value gets below wvEth10-100CSLAlarmThresholdhLow
        (see below)."
    DEFVAL { 5 }
    ::= { wvAlarmControl 50 }

wvEth10-100CSLAlarmThresholdhLow OBJECT-TYPE
    SYNTAX      INTEGER (0..50)
    MAX-ACCESS  read-write
    STATUS      current
    DESCRIPTION
        "Defines the low water mark below which the terminal exits the
        ETH 10/100 Carrier Sense Lost alarm state."
    DEFVAL { 0 }
    ::= { wvAlarmControl 51 }

wvEth10-100ECAlarmThresholdhHigh OBJECT-TYPE
    SYNTAX      INTEGER (0..50)
    MAX-ACCESS  read-write
    STATUS      current
    DESCRIPTION
        "Defines the high water mark above which the terminal enters the
        ETH 10/100 Excessive Collisions alarm state.
        If dot3StatsExcessiveCollisions for any ETH 10-100 port gets above this value
	in a given wvEth10-100ThresholdMeasurementInterval, a eth10-100PortECAlarm
	is set, to be canceled if the value gets below wvEth10-100ECAlarmThresholdhLow
        (see below)."
    DEFVAL { 5 }
    ::= { wvAlarmControl 52 }

wvEth10-100ECAlarmThresholdhLow OBJECT-TYPE
    SYNTAX      INTEGER (0..50)
    MAX-ACCESS  read-write
    STATUS      current
    DESCRIPTION
        "Defines the low water mark below which the terminal exits the
        ETH 10/100 Excessive Collisions alarm state."
    DEFVAL { 0 }
    ::= { wvAlarmControl 53 }

wvEth10-100IMTEAlarmThresholdhHigh OBJECT-TYPE
    SYNTAX      INTEGER (0..50)
    MAX-ACCESS  read-write
    STATUS      current
    DESCRIPTION
        "Defines the high water mark above which the terminal enters the
        ETH 10/100 Internal MAC Transmit Errors alarm state.
        If dot3StatsInternalMacTransmitErrors for any ETH 10-100 port gets above this value
	in a given wvEth10-100ThresholdMeasurementInterval, a eth10-100PortIMTEAlarm
	is set, to be canceled if the value gets below wvEth10-100IMTEAlarmThresholdhLow
        (see below)."
    DEFVAL { 20 }
    ::= { wvAlarmControl 54 }

wvEth10-100IMTEAlarmThresholdhLow OBJECT-TYPE
    SYNTAX      INTEGER (0..50)
    MAX-ACCESS  read-write
    STATUS      current
    DESCRIPTION
        "Defines the low water mark below which the terminal exits the
        ETH 10/100 Internal MAC Transmit Errors alarm state."
    DEFVAL { 5 }
    ::= { wvAlarmControl 55 }

wvEth10-100IMREAlarmThresholdhHigh OBJECT-TYPE
    SYNTAX      INTEGER (0..50)
    MAX-ACCESS  read-write
    STATUS      current
    DESCRIPTION
        "Defines the high water mark above which the terminal enters the
        ETH 10/100 Internal MAC Receive Errors alarm state.
        If dot3StatsInternalMacReceiveErrors for any ETH 10-100 port gets above this value
	in a given wvEth10-100ThresholdMeasurementInterval, a eth10-100PortIMREAlarm
	is set, to be canceled if the value gets below wvEth10-100IMREAlarmThresholdhLow
        (see below)."
    DEFVAL { 20 }
    ::= { wvAlarmControl 56 }

wvEth10-100IMREAlarmThresholdhLow OBJECT-TYPE
    SYNTAX      INTEGER (0..50)
    MAX-ACCESS  read-write
    STATUS      current
    DESCRIPTION
        "Defines the low water mark below which the terminal exits the
        ETH 10/100 Internal MAC Receive Errors alarm state."
    DEFVAL { 5 }
    ::= { wvAlarmControl 57 }

wvEth10-100TxLinkUsageAlarmThresholdLow OBJECT-TYPE
    SYNTAX      INTEGER (0..50)
    UNITS       "MBits/sec"
    MAX-ACCESS  read-write
    STATUS      current
    DESCRIPTION
         "Low threshold of the actual no. of bits being transmitted by the ETH 10/100 ports to
	 the Link interface."
    DEFVAL { 0 }
    ::= { wvAlarmControl 58 }

wvEth10-100TxLinkUsageAlarmThresholdHigh OBJECT-TYPE
    SYNTAX      INTEGER (0..50)
    UNITS       "MBits/sec"
    MAX-ACCESS  read-write
    STATUS      current
    DESCRIPTION
         "High threshold of the actual no. of bits being transmitted by the ETH 10/100 ports to
	 the Link interface."
    DEFVAL { 0 }
    ::= { wvAlarmControl 59 }

wvEth10-100RxLinkUsageAlarmThresholdLow OBJECT-TYPE
    SYNTAX      INTEGER (0..50)
    UNITS       "MBits/sec"
    MAX-ACCESS  read-write
    STATUS      current
    DESCRIPTION
         "Low threshold of the actual no. of bits being received by the ETH 10/100 ports from
	 the Link interface."
    DEFVAL { 0 }
    ::= { wvAlarmControl 60 }

wvEth10-100RxLinkUsageAlarmThresholdHigh OBJECT-TYPE
    SYNTAX      INTEGER (0..50)
    UNITS       "MBits/sec"
    MAX-ACCESS  read-write
    STATUS      current
    DESCRIPTION
         "High threshold of the actual no. of bits being received by the ETH 10/100 ports from
	 the Link interface."
    DEFVAL { 0 }
    ::= { wvAlarmControl 61 }




wvEth10-100ThresholdMeasurementInterval OBJECT-TYPE
    SYNTAX      INTEGER (0..900)      -- up to 15 minutes
    UNITS       "seconds"
    MAX-ACCESS  read-write
    STATUS      current
    DESCRIPTION
        "Defines the periodical interval against which the ETH 10/100
        alarm thresholds are to be checked.
        A value of zero means no link performance alarms should be issued."
    DEFVAL { 30 }
  ::= { wvAlarmControl 70 }

wvClearAlarmLog OBJECT-TYPE
    SYNTAX      Integer32
    MAX-ACCESS  read-write
    STATUS      current
    DESCRIPTION
        "use SET wvClearAlarmLog to Clear the alarm log and insert alarm that 'Alarm log was cleared by user'
         and GET wvClearAlarmLog to get the number of entries in the alarm log."
  ::= { wvAlarmControl 71 }

-- ####################################################################
-- *** Components Revisions Configuration Group ***
-- ####################################################################

wvInstalledPlugInPartNo OBJECT-TYPE
    SYNTAX      DisplayString(SIZE(5))
    MAX-ACCESS  read-only
    STATUS      current
    DESCRIPTION
        "The 8800 DMR Plug-In Part No. is defined as PIN-'xyztu', as follows:
        x - interface type:
		 	x=1 - T1/T3,
			x=2 - E1/E3,
			x=3 - STS1,
			x=4 - 10/100Base-T + T1s,
			x=5 - 10/100Base-T + E1s,
			x=6, 7, ...- reserved.

        y - connector type:
		for x=1/2, T1/E1 connector type -
			y=1 - BNC, 
			y=2 - RJ48,  
			y=7 - SCSI, 
			y=8 - SCSI + T3/E3 - BNC
		for x=4/5, 10/100Base-T + T1/E1 connectors types
			y=1 - 10/100Base-T - RJ45 + T1/E1 - BNC,
			y=2 - 10/100Base-T - RJ45 + T1/E1 - RJ48,
			if no T1/E1s available then y=1
			y=3 - 10/100Base-FX - (FIBER) + T1/E1 - BNC,
			y=4 - 10/100Base-FX - (FIBER) + T1/E1 - RJ48,
			if no T1/E1s available then y=3

        zt- # of T1/E1 interfaces:
		for x=1/2/3
			zt = 00, 01, 02, 04, 08 or 16
		for x=4/5
			zt =  00, 01, 02, or 04

        u - # of high band interfaces:
		for x=1/2/3, # of T3/E3 interfaces -
			u = 0 or 1.
		for x=4/5, # of 10/100Base-T ports -
			u = 1, 2 or 4."
    ::= { wvComponentsRevisions 1 }

wvInstalledPlugInHwRevision OBJECT-TYPE
    SYNTAX      ComponentRevision
    MAX-ACCESS  read-only
    STATUS      current
    DESCRIPTION
        "Plug-In Hardware Revision."
    ::= { wvComponentsRevisions 2 }

wvIduPartNo OBJECT-TYPE
    SYNTAX      DisplayString(SIZE(4))
    MAX-ACCESS  read-only
    STATUS      current
    DESCRIPTION
        "The 8800 DMR DIU Part No. is defined as IDU-'xyzt'
        (exact definition of xyzt TBD)."
    ::= { wvComponentsRevisions 3 }

wvIduHwRevision OBJECT-TYPE
    SYNTAX      ComponentRevision
    MAX-ACCESS  read-only
    STATUS      current
    DESCRIPTION
        "IDU Hardware Revision (in fact reflects the ICB - IDU Control Board -
	revision)."
    ::= { wvComponentsRevisions 4 }

wvIduSwRevision OBJECT-TYPE
    SYNTAX      ComponentRevision
    MAX-ACCESS  read-only
    STATUS      current
    DESCRIPTION
        "IDU Software Revision."
    ::= { wvComponentsRevisions 5 }

wvIduLastSwUpdateTime OBJECT-TYPE
    SYNTAX      DateAndTime
    MAX-ACCESS  read-only
    STATUS      current
    DESCRIPTION
        "Sent together with the software being updated."
    ::= { wvComponentsRevisions 6 }

wvOduPartNo OBJECT-TYPE
    SYNTAX      DisplayString(SIZE(5))
    MAX-ACCESS  read-only
    STATUS      current
    DESCRIPTION
        "The Codan 8800 DMR ODU Part No. is defined as ODU-'xwyzt', as follows:
        x - Standard: x=1 - FCC(US), x=2 - ETSI(European)
        w - Duplex Spacing:
                standard    frequency    left digit value                 duplex
                FCC             38                1                         700
                FCC             23                1                        1200
                FCC             18                1                        1560
                ETSI            38                1                        1260
                ETSI            26                1                        1008
                ETSI            23                1                        1200
                ETSI            23                2                        1008
                ETSI            23                3                        1232
                ETSI            18                1                        1010
                ETSI            18                2                        1008
                ETSI            15                1                         315
                ETSI            15                2                         420
                ETSI            15                3                         728
                ETSI            15                4                         644
                ETSI            15                5                         490
                ETSI            15                6                         322
                ETSI            13                1                         266
                ETSI            10                1                         65 
                ETSI            10                2                         91 
                ETSI            10                3                         65 
                ETSI            10                4                         65 
                ETSI            10                5                         91 
                ETSI            10                6                         91 
                ETSI            10                7                         91 
                ETSI             8                1                         311.32
                ETSI             8                2                         126
                ETSI             8                3                         119
                ETSI             7                1                         154 (7125-7425)
                ETSI             7                2                         154 (7425-7725)
                ETSI             7                3                         161 (7125-7425)
                ETSI             7                4                         161 (7425-7725)
                ETSI             7                5                         245
                ETSI             7                6                         161 (7250-7550)


        y - Frequency Band: y=1-4 -  Band 1-4
	zt- Spectrum Range Allocation (in Ghz): 38, 23, 18, etc...

        Example:  ODU-2-1-4-23 = ETSI, duplex spacing 1200MHz / band 4, 23GHz.

	The rules governing the Frequency Band correlation of the 2 terminals
	usage of a given link depend on the Spectrum Range of the link."
    ::= { wvComponentsRevisions 7 }

wvOduHwRevision OBJECT-TYPE
    SYNTAX      ComponentRevision
    MAX-ACCESS  read-only
    STATUS      current
    DESCRIPTION
        "ODU Hardware Revision."
    ::= { wvComponentsRevisions 8 }

wvOduSwRevision OBJECT-TYPE
    SYNTAX      ComponentRevision
    MAX-ACCESS  read-only
    STATUS      current
    DESCRIPTION
        "ODU Software Revision."
    ::= { wvComponentsRevisions 9 }

wvOduLastSwUpdateTime OBJECT-TYPE
    SYNTAX      DateAndTime
    MAX-ACCESS  read-only
    STATUS      current
    DESCRIPTION
        "Sent together with the software being updated."
    ::= { wvComponentsRevisions 10 }

wvIpbHwRevision OBJECT-TYPE
    SYNTAX      ComponentRevision
    MAX-ACCESS  read-only
    STATUS      current
    DESCRIPTION
        "The IPB (IDU Panel Board) Hardware Revision."
    ::= { wvComponentsRevisions 11 }

wvBootSwRevision OBJECT-TYPE
    SYNTAX      ComponentRevision
    MAX-ACCESS  read-only
    STATUS      current
    DESCRIPTION
        "BOOT Software Revision."
    ::= { wvComponentsRevisions 12 }

wvIduAlternetSwRevision OBJECT-TYPE
    SYNTAX      ComponentRevision
    MAX-ACCESS  read-only
    STATUS      current
    DESCRIPTION
        "IDU Alternate Software Revision."
    ::= { wvComponentsRevisions 13 }

wvOemId OBJECT-TYPE
    SYNTAX      INTEGER (0..255)
    MAX-ACCESS  read-only
    STATUS      current
    DESCRIPTION
        "Describe the manufacture of this system.
        '1' - Codan.
        ... future OEM."
    ::= { wvComponentsRevisions 14 }

wvOemIduPartNo OBJECT-TYPE
    SYNTAX      DisplayString(SIZE(12))
    MAX-ACCESS  read-only
    STATUS      current
    DESCRIPTION
        "The OEM IDU Part No. is defined as IDU-'xx-xxxxx-xxx'."
    ::= { wvComponentsRevisions 15 }
    
wvOemOduPartNo OBJECT-TYPE
    SYNTAX      DisplayString(SIZE(12))
    MAX-ACCESS  read-only
    STATUS      current
    DESCRIPTION
        "The OEM ODU Part No. is defined as ODU-'xx-xxxxx-xxx'."
    ::= { wvComponentsRevisions 16 }

wvInstalledOemPlugInPartNo OBJECT-TYPE
    SYNTAX      DisplayString(SIZE(12))
    MAX-ACCESS  read-only
    STATUS      current
    DESCRIPTION
        "The OEM Plug-in Part No. is defined as Plug-in-'xx-xxxxx-xxx'."
    ::= { wvComponentsRevisions 17 }


-- ####################################################################
-- *** Status and Gauges Group ***
-- ####################################################################

-- *** Statuses ***

wvTelemetryStatus OBJECT-TYPE
    SYNTAX      INTEGER {
                    ok(1),
                    warning(2),
                    fault(3),
                    notOperational(4)
                    }
    MAX-ACCESS  read-only
    STATUS      current
    DESCRIPTION
        "Keeps the status of the Idu-Odu communication."
    ::= { wvStatusAndGauges 1 }

wvOperatingSystemStatus OBJECT-TYPE
    SYNTAX      INTEGER {
                    ok(1),
                    systemFailure(2)    --  TBD what to be presented here ???
                    }
    MAX-ACCESS  read-only
    STATUS      current
    DESCRIPTION
        "Keeps the state of the system from the firmware point-of-view."
    ::= { wvStatusAndGauges 2 }

wvIduOduCableStatus OBJECT-TYPE
    SYNTAX      INTEGER {           -- not sure we can detect below cases ???
                    ok(1),
                    warning(2),     -- TBD
                    short(3),
                    open(4)
                    }
    MAX-ACCESS  read-only
    STATUS      current
    DESCRIPTION
        "Keeps the current status of the Idu-Odu cable."
    ::= { wvStatusAndGauges 3 }

wvIduStatus OBJECT-TYPE
    SYNTAX      BITS {
                    filler0(0),
                    iduPowerSupplyLowValue(1),
                    iduTxSynthesizerOutOfLock(2),
                    iduRxSynthesizerOutOfLock(3),
                    externalInputsActive(4),    -- at least one external input
                    selfTestFault(5),           -- details at wvLastSelfTestStatus
                    iduNotOperational(6)
                    }
    MAX-ACCESS  read-only
    STATUS      current
    DESCRIPTION
        "Reports the current status of the IDU."
    ::= { wvStatusAndGauges 4 }

wvOduStatus OBJECT-TYPE
    SYNTAX      BITS {
                    filler0(0),
                    oduPowerSupplyOutOfRange(1),
                    txOnMuteState(2),
                    rxOnMuteState(3),
                    txFailure(4),
                    rxFailure(5),
                    rslLow(6),                         -- RSL momentary value
                    averageRSLLow(7),                  -- RSL average value
                    oduTxSynthesizerOutOfLock(8),
                    oduRxSynthesizerOutOfLock(9),
                    oduRfSynthesizerOutOfLock(10),
                    oduTemperatureViolation(11),
                    anyOtherOduFault(12),              -- TBD ???
                    oduNotResponding(13)
                    }
    MAX-ACCESS  read-only
    STATUS      current
    DESCRIPTION
        "Reports the current status of the ODU."
    ::= { wvStatusAndGauges 5 }

wvRemoteTerminalStatus OBJECT-TYPE
    SYNTAX      BITS {
                    remoteTerminalWarning(0),
                    remoteTerminalFailure(1),
                    remoteTerminalNotResponding(2)
                    }
    MAX-ACCESS  read-only
    STATUS      current
    DESCRIPTION
        "Reports the general current status of the remote terminal."
     ::= { wvStatusAndGauges 6 }

wvSlipModemStatus OBJECT-TYPE
    SYNTAX      INTEGER {
                    ok(1),
                    notResponding(2),   -- no response to init sequence
                    noDialTone(3),
                    lineBusy(4),
                    connected(5),
                    anyOtherFault(6),   -- TBD ???
		    noAnswer(7)		-- no answer from remote modem
                    }
    MAX-ACCESS  read-only
    STATUS      current
    DESCRIPTION
        "Keeps the modem current status."
     ::= { wvStatusAndGauges 7 }

wvSecurityStatus OBJECT-TYPE
    SYNTAX      BITS {
                    filler0(0),
                    linkIdViolation(1), -- the last received Link Id doesn't
                                        --  match wvLinkId - the modem is
                                        --  resynchronized. If not successful,
                                        --  sets a remoteNotResponding alarm.
                    passwordBypass(2)   -- front panel supervisor password has
                                        --  bypassed through jumpers
                                        -- ?? TBD how to reset this event
                    }
    MAX-ACCESS  read-only
    STATUS      current
    DESCRIPTION
        "Reports the current security status."
    ::= { wvStatusAndGauges 8 }

    wvTftpDwnlStatus OBJECT-TYPE
    SYNTAX      INTEGER {
                    dwnlStatusUnknown(1),
                    dwnlInProcess(2),
                    dwnlSuccess(3),
                    dwnlGeneralError(4),
                    dwnlNoResponseFromServer(5),
                    dwnlChecksumError(6),
                    dwnlSwIncompatibleImage(7),
                    dwnlConfigIncompatibleImage(8),
                    dwnlTftpProtocolError(9),
                    dwnlTftpFilePasswordError(10),
                    dwnlCancelByUser(11)
                    }
    MAX-ACCESS  read-only
    STATUS      current
    DESCRIPTION
        "Describes the status of last TFTP operation.
        If no TFTP has been performed its status is dwnlStatusUnknown."
    ::= { wvStatusAndGauges 9 }

wvLinkPerformanceAlarmsStatus OBJECT-TYPE
    SYNTAX      BITS {
                    filler0(0),
                    wvLinkESAlarm(1),
                    wvLinkSESAlarm(2),
                    wvLinkUASAlarm(3),
                    wvLinkDMAlarm(4),
                    wvLinkBERWarningAlarm(5),
                    wvLinkBERFailureAlarm(6),
                    wvLinkBLERAlarm(7),
                    wvLinkBBERAlarm(8),
                    wvLinkNCBLERAlarm(9),
                    eth10-100RxLinkUsageLow(10),
                    eth10-100RxLinkUsageHigh(11),
                    eth10-100TxLinkUsageLow(12),
                    eth10-100TxLinkUsageHigh(13)
                    }
    MAX-ACCESS  read-only
    STATUS      current
    DESCRIPTION
        "Reports the status of link performance related alarms."
    ::= { wvStatusAndGauges 10 }

-- *** Gauges and Information ***

wvOperatingFrequency OBJECT-TYPE
    SYNTAX      Integer32
    UNITS      "MHz*100"
    MAX-ACCESS  read-only
    STATUS      current
    DESCRIPTION
        "Specifies the current Spectrum Range Allocation x 100, in Mhz
	(3800000, 2300000, 1800000, etc...)
        The value is extracted from the terminal's wvOduPartNo."
    ::= { wvStatusAndGauges 11 }

wvFrequencyBand OBJECT-TYPE
    SYNTAX      INTEGER {
                    bandOne(1),
                    bandTwo(2),
                    bandThree(3),
                    bandFour(4)
                    }
    MAX-ACCESS  read-only
    STATUS      current
    DESCRIPTION
        "Specifies the current frequency band, as read from preset jumpers at
	the ODU.
        The value read should be compatible with the peer's Link Terminal,
	so that if one side has 1 or 3 the other side must have 2 or 4,
	accordingly."
    ::= { wvStatusAndGauges 12 }

wvChannelSpacing OBJECT-TYPE
    SYNTAX      INTEGER {
		    -- American ODU standard --
                    twoAndAHalf(1),	-- for oneT1
                    five(2),		-- for twoT1 and oneE1
                    sevenAndAHalf(3),	-- for fourT1 and twoE1
                    twelveAndAHalf(4),  -- *** 10 Mhz on the 18 Ghz Spectrum Range ***
                    			-- for eightT1 and fourE1
                    twentyFive(5),	-- *** 20 Mhz on the 18 Ghz Spectrum Range ***
                    			-- for sixteenT1 and eightE1
                    fifty(6),		-- *** 40 Mhz on the 18 Ghz Spectrum Range ***
                    			-- for t3, t3PlusTwoT1, t3PlusFourT1, sts1,
					--     sixteenE1, e3, e3PlusOneE1 and e3PlusTwoE1
		    -- European ODU standard --
                    threeAndAHalf(7),	-- for twoE1 and twoT1
                    seven(8),		-- for fourE1 and fourT1
                    fourteen(9),        -- *** 13.75 Mhz on the 18 Ghz Spectrum Range ***
                    			-- for eightE1 and eightT1
                    twentyEight(10),    -- *** 27.5 Mhz on the 18 Ghz Spectrum Range ***
                    			-- for sixteenE1, sixteenT1, e3, e3PlusOneE1
					--     and e3PlusTwoE1
		    fiftySix(11) 	-- *** 55 Mhz on the 18 Ghz Spectrum Range ***
		    			-- for t3, t3PlusTwoT1, t3PlusFourT1, sts1
                    }
    UNITS      "MHz"
    MAX-ACCESS  read-only
    STATUS      current
    DESCRIPTION
        "Specifies the frequency spacing between adjacent channels, as a function
        of the ODU standard (American vs. European) and chosen wvLinkCapacity.
	Note that on the 18 Ghz Spectrum Range the actual values may be different than
	on the other ranges, and those are specifically mentioned where applicable."
    ::= { wvStatusAndGauges 13 }

wvTxPowerLevel OBJECT-TYPE
    SYNTAX      INTEGER (-70..30)
    UNITS      "dBm"
    MAX-ACCESS  read-only
    STATUS      current
    DESCRIPTION
        "The transmit power value read at this terminal's ODU output."
    ::= { wvStatusAndGauges 14 }

wvRxSignalLevel OBJECT-TYPE
    SYNTAX      INTEGER (-100..-10)
    UNITS      "dBm"
    MAX-ACCESS  read-only
    STATUS      current
    DESCRIPTION
        "The receive signal value read on this terminal."
    ::= { wvStatusAndGauges 15 }

wvFadeMargin OBJECT-TYPE
    SYNTAX      INTEGER (0..90)
    UNITS      "dB"
    MAX-ACCESS  read-only
    STATUS      current
    DESCRIPTION
        "The margin on the receive signal level, as a function of the
        Automatic Gain Control read( min(wvRxSignalLevel) - wvRxSignalLevel )."
    ::= { wvStatusAndGauges 16 }

wvOduTemperature OBJECT-TYPE
    SYNTAX      INTEGER (-58..212)
    MAX-ACCESS  read-only
    STATUS      current
    DESCRIPTION
        "The measured ODU temperature.
        The units and possible values depend on the ODU model.
        The shown range is American Fahreneit.
        The European range is -50..100 Centigrades."
    ::= { wvStatusAndGauges 17 }

wvLedState OBJECT-TYPE
    SYNTAX      BITS {
                    filler0(0),
                    powerOn(1),
                    linkOperational(2),
                    relay1On(3),
                    relay2On(4),
                    relay3On(5),
                    relay4On(6),
                    relay5On(7),
                    localCableFault(8),
                    remoteCableFault(9),
                    localIduFault(10),
                    remoteIduFault(11),
                    localOduFault(12),
                    remoteOduFault(13),
                    localFrontPanelDisplay(14),
                    remoteFrontPanelDisplay(15)
                    }
    MAX-ACCESS  read-only
    STATUS      current
    DESCRIPTION
        "The current state of the IDU LEDs."
    ::= { wvStatusAndGauges 18 }

wvModemAfc OBJECT-TYPE
    SYNTAX      INTEGER (-128..127)
    MAX-ACCESS  read-only
    STATUS      current
    DESCRIPTION
        "The measured Modem Automatic Frequency Control.
	This is an implementation specific value, mainly for diagnostic
	purposes."
    ::= { wvStatusAndGauges 19 }

wvRxPllFrequency OBJECT-TYPE
    SYNTAX      Integer32
    MAX-ACCESS  read-only
    STATUS      current
    DESCRIPTION
        "The measured Receive Pll Frequency.
	This is an implementation specific value, mainly for diagnostic
	purposes."
    ::= { wvStatusAndGauges 20 }

wvWorkingFrequency OBJECT-TYPE
    SYNTAX      Integer32
    UNITS      "MHz*100"
    MAX-ACCESS  read-only
    STATUS      current
    DESCRIPTION
        "Specifies the actual working frequency x 100, in Mhz
	(3897875, 2122550, 1873875, etc...)
        The value depends on the chosen wvChannelNo, the terminal's
	wvOduPartNo and wvFrequencyBand."
    ::= { wvStatusAndGauges 21 }

wvMaxTxPowerSetting OBJECT-TYPE
    SYNTAX      INTEGER (-10..29)
    UNITS      "dBm"
    MAX-ACCESS  read-only
    STATUS      current
    DESCRIPTION
        "This value present the maximum Tx power that can be achieved by the system
        (this parameter is the maximum value that the user can set for the 'wvTxPowerSetting'). "
    DEFVAL { 29 }
    ::= { wvStatusAndGauges 22 }

wvMinTxPowerSetting OBJECT-TYPE
    SYNTAX      INTEGER (-10..29)
    UNITS      "dBm"
    MAX-ACCESS  read-only
    STATUS      current
    DESCRIPTION
        "This value present the minimum Tx power that can be achieved by the system
        (this parameter is the minimum value that the user can set for the 'wvTxPowerSetting'). "
    DEFVAL { -10 }
    ::= { wvStatusAndGauges 23 }

wvOduSerialNumber OBJECT-TYPE
    SYNTAX      Integer32
    MAX-ACCESS  read-only
    STATUS      current
    DESCRIPTION
        "The serial number of ODU."
    ::= { wvStatusAndGauges 24 }

wvIduSerialNumber OBJECT-TYPE
    SYNTAX      Integer32
    MAX-ACCESS  read-only
    STATUS      current
    DESCRIPTION
        "The serial number of IDU."
    ::= { wvStatusAndGauges 25 }



-- *** 1+1 Information ***

wvOnePlusOneStatus OBJECT-TYPE
    SYNTAX      BITS {
                    filler0(0),
                    onePlusOneOn(1),         -- set if unit is installed on a "1+1" configuration;
					     -- if not set, all other signals are ignored
                    primaryUnit(2),	     -- set if unit is Primary, reset if Secondary
                    manualModeOn(3),	     -- set if unit is in MANUAL state
                    alternateIduOk(4),	     -- set if other unit is OK
                    unitActive(5),	     -- set if unit assumed the "active" role
                    frequencyDiversityOn(6), -- set if Backup Mode is Frequency Diversity,
					     -- reset if mode is Hot StandBy
                    swIduFail(7),            -- set if the s/w detected conditions for switching
                    upperUnit(8)	     -- set if unit is the upper, reset if the lower
                    }
    MAX-ACCESS  read-only
    STATUS      current
    DESCRIPTION
        "Reports the current status of various 1+1 related signals and s/w
	 detected conditions."
    ::= { wvStatusAndGauges 30 }

wvSupport2T1and2E1Status OBJECT-TYPE
    SYNTAX      INTEGER {
                        support2T1and2E1Enable(0),
                        support2T1and2E1Disable(1)
                        }
    MAX-ACCESS  read-only
    STATUS      current
    DESCRIPTION
        "Reports the current status of support 2T1 and 2E1 capacity."
     ::= { wvStatusAndGauges 31 }

wvLastUpdateConfigurationTimestamp OBJECT-TYPE
    SYNTAX      Integer32
    MAX-ACCESS  read-only
    STATUS      current
    DESCRIPTION
        "The Last Update Configuration Timestamp in system ticks"
    ::= { wvStatusAndGauges 32 }
    
wvOemIduSerialNumber OBJECT-TYPE
    SYNTAX      DisplayString(SIZE(12))
    MAX-ACCESS  read-only
    STATUS      current
    DESCRIPTION
        "The IDU serial number for OEM manufacture."
    ::= { wvStatusAndGauges 33 }

wvOemOduSerialNumber OBJECT-TYPE
    SYNTAX      DisplayString(SIZE(12))
    MAX-ACCESS  read-only
    STATUS      current
    DESCRIPTION
        "The ODU serial number for OEM manufacture."
    ::= { wvStatusAndGauges 34 }

wvOnePlusOneConnectorType OBJECT-TYPE
    SYNTAX      INTEGER {
                        yCable(0),
                        iauDb25(1),
                        iau75(2)
                        }
    MAX-ACCESS  read-only
    STATUS      current
    DESCRIPTION
        "Reports the current connector type that connected to the plug-in's in the new 1+1 system."
     ::= { wvStatusAndGauges 35 }


-- *** Log Event ***
wvLog         OBJECT IDENTIFIER ::= { wvStatusAndGauges 40 }

wvLogEventsElapsed OBJECT-TYPE
    SYNTAX      Gauge32
    MAX-ACCESS  read-only
    STATUS      current
    DESCRIPTION
       "The number of events from last reset"
    ::= { wvLog 1 }



-- *** the Log Events Table ***

-- The Log Events Table contains various events
-- collected by the local system.

wvLogEventTable OBJECT-TYPE
    SYNTAX      SEQUENCE OF WvLogEventEntry
    MAX-ACCESS  not-accessible
    STATUS      current
    DESCRIPTION
       "The Log Event table."
    ::= { wvLog 2  }

wvLogEventEntry OBJECT-TYPE
    SYNTAX      WvLogEventEntry
    MAX-ACCESS  not-accessible
    STATUS      current
    DESCRIPTION
       "An entry in the Log Event table."
    INDEX   { wvLogEventLock }
    ::= { wvLogEventTable 1 }

WvLogEventEntry ::= SEQUENCE {
    wvLogEventLock           INTEGER,
    wvLogEventTime           TimeTicks,
    wvLogEventStatus         INTEGER,
    wvLogEventDescription    DisplayString
    }

wvLogEventLock OBJECT-TYPE
    SYNTAX      INTEGER (0..64)
    MAX-ACCESS  read-only
    STATUS      current
    DESCRIPTION
       "A number between 1 and 64, where 1 is the last (new) event in queue
       and 64 is the first (old) event in queue.
       (assuming   that  all  64  events  are valid)."
    ::= { wvLogEventEntry 1 }

wvLogEventTime OBJECT-TYPE
    SYNTAX      TimeTicks
    MAX-ACCESS  read-only
    STATUS      current
    DESCRIPTION
       "Defines the event time, relative to sysUpTime"
    ::= { wvLogEventEntry 2 }

wvLogEventStatus OBJECT-TYPE
    SYNTAX      INTEGER {
                    messageStart(1),
                    warningStart(2),
                    fatalStart(3),
                    messageEnd(4),
                    warningEnd(5),
                    fatalEnd(6)
                    }
    MAX-ACCESS  read-only
    STATUS      current
    DESCRIPTION
        "Defines the alarm severity."
    ::= { wvLogEventEntry 3 }

wvLogEventDescription  OBJECT-TYPE
    SYNTAX     DisplayString (SIZE(0..32))
    MAX-ACCESS read-only
    STATUS     current
    DESCRIPTION
    "The event description. For example: IDU Tx synt. Fail."
    ::= { wvLogEventEntry 4 }


-- ####################################################################
-- *** Performance Monitoring Group ***
-- ####################################################################

-- All errors measurements start 1 second after system start-up, to allow
-- for proper stabilization.

-- *** Link ***

-- Cummulative values

wvlinkBER OBJECT-TYPE
    SYNTAX      FloatingPoint
    MAX-ACCESS  read-only
    STATUS      current
    DESCRIPTION
        "Specifies the terminal's cummulative Bit Error Rate since link last
        start-up."
    ::= { wvPerformance 1 }

wvlinkBLER OBJECT-TYPE
    SYNTAX      FloatingPoint
    MAX-ACCESS  read-only
    STATUS      current
    DESCRIPTION
        "Specifies the terminal's cummulative Corrected Blocks Rate
	since link last start-up."
    ::= { wvPerformance 2 }

wvlinkBBER OBJECT-TYPE
    SYNTAX      FloatingPoint
    MAX-ACCESS  read-only
    STATUS      current
    DESCRIPTION
        "Specifies the terminal's cummulative Background Blocks Error Rate
        since link last start-up."
    ::= { wvPerformance 3 }

wvlinkNCBLER OBJECT-TYPE
    SYNTAX      FloatingPoint
    MAX-ACCESS  read-only
    STATUS      current
    DESCRIPTION
        "Specifies the terminal's cummulative Not Corrected Blocks Error Rate
	since link last start-up."
    ::= { wvPerformance 4 }

wvLinkESs OBJECT-TYPE
    SYNTAX      Gauge32
    UNITS       "seconds"
    MAX-ACCESS  read-only
    STATUS      current
    DESCRIPTION
        "Specifies the number of Errored Seconds, encountered by the interface
        Link since link last start-up."
    ::= { wvPerformance 5 }

wvLinkSESs OBJECT-TYPE
    SYNTAX      Gauge32
    UNITS       "seconds"
    MAX-ACCESS  read-only
    STATUS      current
    DESCRIPTION
        "Specifies the number of Severely Errored Seconds, encountered by the
        interface Link since link last start-up."
    ::= { wvPerformance 6 }

wvLinkUAs OBJECT-TYPE
    SYNTAX      Gauge32
    UNITS       "seconds"
    MAX-ACCESS  read-only
    STATUS      current
    DESCRIPTION
        "Specifies the number of Unavailable Seconds, encountered by the
        interface Link since link last start-up."
    ::= { wvPerformance 7 }

wvLinkDMs OBJECT-TYPE
    SYNTAX      Gauge32
    UNITS       "minutes"
    MAX-ACCESS  read-only
    STATUS      current
    DESCRIPTION
        "Specifies the number of Degraded Minutes, encountered by the
        interface Link since link last start-up."
    ::= { wvPerformance 8 }

wvlinkAverageRSL OBJECT-TYPE
    SYNTAX      Integer32
    UNITS       "dBm"
    MAX-ACCESS  read-only
    STATUS      current
    DESCRIPTION
        "Specifies the average Receive Signal Level, encountered by the
        interface Link since link last start-up."
    ::= { wvPerformance 9 }

wvlinkMaximumRSL OBJECT-TYPE
    SYNTAX      Integer32
    UNITS       "dBm"
    MAX-ACCESS  read-only
    STATUS      current
    DESCRIPTION
        "Specifies the maximum Receive Signal Level, encountered by the
        interface Link since link last start-up."
    ::= { wvPerformance 10 }

wvlinkMinimumRSL OBJECT-TYPE
    SYNTAX      Integer32
    UNITS       "dBm"
    MAX-ACCESS  read-only
    STATUS      current
    DESCRIPTION
        "Specifies the minimum Receive Signal Level, encountered by the
        interface Link since link last start-up."
    ::= { wvPerformance 11 }


-- Following objects follow the "current, interval and total" performance
-- monitoring concepts of the DS1/E1 and DS3/E3 MIBs.
-- Refer to RFCS 1406 and 1407 for further details.
-- ??? The exact definition of the various below error conditions TBD ???

wvLinkValidIntervals OBJECT-TYPE
    SYNTAX      INTEGER (0..96)
    MAX-ACCESS  read-only
    STATUS      current
    DESCRIPTION
        "The number of  previous  intervals  for  which valid data was
        collected.  The value will be 96 unless the interface was brought
        on-line within the last 24 hours, in which case the value will
        be the number of complete 15  minute intervals since the interface
        has been online."
    ::= { wvPerformance 12 }


-- *** the Link Current sub-group ***

-- The Link current sub-group contains various statistics being
-- collected for the current 15 minute interval.

wvLinkCurrentESs OBJECT-TYPE
    SYNTAX      Gauge32
    UNITS       "seconds"
    MAX-ACCESS  read-only
    STATUS      current
    DESCRIPTION
        "The number of Errored Seconds, encountered  by
        the interface Link in the current 15 minute interval."
    ::= { wvPerformance 13 }

wvLinkCurrentSESs OBJECT-TYPE
    SYNTAX      Gauge32
    UNITS       "seconds"
    MAX-ACCESS  read-only
    STATUS      current
    DESCRIPTION
        "The number of Severely Errored Seconds, encountered  by
        the interface Link in the current 15 minute interval."
    ::= { wvPerformance 14 }

wvLinkCurrentUASs OBJECT-TYPE
    SYNTAX      Gauge32
    UNITS       "seconds"
    MAX-ACCESS  read-only
    STATUS      current
    DESCRIPTION
        "The number of Unavailable Seconds, encountered  by
        the interface Link in the current 15 minute interval."
    ::= { wvPerformance 15 }

wvLinkCurrentDMs OBJECT-TYPE
    SYNTAX      Gauge32
    UNITS       "seconds"
    MAX-ACCESS  read-only
    STATUS      current
    DESCRIPTION
        "The number of Degraded Minutes, encountered  by
        the interface Link in the current 15 minute interval."
    ::= { wvPerformance 16 }

wvLinkCurrentBER OBJECT-TYPE
    SYNTAX      FloatingPoint
    MAX-ACCESS  read-only
    STATUS      current
    DESCRIPTION
        "The Bit Error Rate encountered by the interface Link in the current
        15 minute interval."
    ::= { wvPerformance 17 }

wvLinkCurrentBLER OBJECT-TYPE
    SYNTAX      FloatingPoint
    MAX-ACCESS  read-only
    STATUS      current
    DESCRIPTION
        "The Corrected Blocks Rate encountered by the interface Link in the
        current 15 minute interval."
    ::= { wvPerformance 18 }

wvLinkCurrentBBER OBJECT-TYPE
    SYNTAX      FloatingPoint
    MAX-ACCESS  read-only
    STATUS      current
    DESCRIPTION
        "The Background Blocks Error Rate encountered by the interface Link in
        the current 15 minute interval."
    ::= { wvPerformance 19 }

wvLinkCurrentNCBLER OBJECT-TYPE
    SYNTAX      FloatingPoint
    MAX-ACCESS  read-only
    STATUS      current
    DESCRIPTION
        "The Not Corrected Blocks Error Rate encountered by the interface Link in the
        current 15 minute interval."
    ::= { wvPerformance 20 }

wvlinkCurrentAverageRSL OBJECT-TYPE
    SYNTAX      Integer32
    UNITS       "dBm"
    MAX-ACCESS  read-only
    STATUS      current
    DESCRIPTION
        "Specifies the average Receive Signal Level,
        encountered by the Link interface in the current 15 minute interval."
    ::= { wvPerformance 21 }

wvlinkCurrentMaximumRSL OBJECT-TYPE
    SYNTAX      Integer32
    UNITS       "dBm"
    MAX-ACCESS  read-only
    STATUS      current
    DESCRIPTION
        "Specifies the maximum Receive Signal Level,
        encountered by the Link interface in the current 15 minute interval."
    ::= { wvPerformance 22 }

wvlinkCurrentMinimumRSL OBJECT-TYPE
    SYNTAX      Integer32
    UNITS       "dBm"
    MAX-ACCESS  read-only
    STATUS      current
    DESCRIPTION
        "Specifies the minimum Receive Signal Level,
        encountered by the Link interface in the current 15 minute interval."
    ::= { wvPerformance 23 }

wvlinkCurrentTimeElapsed OBJECT-TYPE
    SYNTAX      INTEGER (0..899)
    UNITS       "seconds"
    MAX-ACCESS  read-only
    STATUS      current
    DESCRIPTION
        "Specifies the no. of seconds elapsed since the beginning of the current 15
        minute interval."
    ::= { wvPerformance 24 }


-- *** the Link Interval Table ***

-- The Link Interval Table contains various statistics
-- collected by the Link Interface over the previous 24 hours of
-- operation.  The past 24 hours are broken into 96 completed
-- 15 minute intervals.

wvLinkIntervalTable OBJECT-TYPE
    SYNTAX      SEQUENCE OF WvLinkIntervalEntry
    MAX-ACCESS  not-accessible
    STATUS      current
    DESCRIPTION
       "The Link Interval table."
    ::= { wvPerformance 25 }

wvLinkIntervalEntry OBJECT-TYPE
    SYNTAX      WvLinkIntervalEntry
    MAX-ACCESS  not-accessible
    STATUS      current
    DESCRIPTION
       "An entry in the Link Interval table."
    INDEX   { wvLinkIntervalNumber }
    ::= { wvLinkIntervalTable 1 }

WvLinkIntervalEntry ::= SEQUENCE {
    wvLinkIntervalNumber        INTEGER,
    wvLinkIntervalESs           Gauge32,
    wvLinkIntervalSESs          Gauge32,
    wvLinkIntervalUASs          Gauge32,
    wvLinkIntervalDMs           Gauge32,
    wvLinkIntervalBER           FloatingPoint,
    wvLinkIntervalBLER          FloatingPoint,
    wvLinkIntervalBBER          FloatingPoint,
    wvLinkIntervalNCBLER        FloatingPoint,
    wvlinkIntervalAverageRSL    Integer32,
    wvlinkIntervalMaximumRSL    Integer32,
    wvlinkIntervalMinimumRSL    Integer32
    }

wvLinkIntervalNumber OBJECT-TYPE
    SYNTAX      INTEGER (1..96)
    MAX-ACCESS  read-only
    STATUS      current
    DESCRIPTION
       "A number between 1 and 96, where 1 is the most recently completed 15
       minute interval and 96 is the least recently completed 15 minutes
       interval (assuming   that  all  96  intervals  are valid)."
    ::= { wvLinkIntervalEntry 1 }

wvLinkIntervalESs OBJECT-TYPE
    SYNTAX      Gauge32
    MAX-ACCESS  read-only
    STATUS      current
    DESCRIPTION
       "The number of Errored Seconds encountered by the Link interface in
       one of the previous 96, individual 15 minute, intervals."
    ::= { wvLinkIntervalEntry 2 }

wvLinkIntervalSESs OBJECT-TYPE
    SYNTAX      Gauge32
    MAX-ACCESS  read-only
    STATUS      current
    DESCRIPTION
       "The number of Severely Errored Seconds encountered by the Link
       interface in one of the previous 96, individual 15 minute, intervals."
    ::= { wvLinkIntervalEntry 3 }

wvLinkIntervalUASs OBJECT-TYPE
    SYNTAX      Gauge32
    MAX-ACCESS  read-only
    STATUS      current
    DESCRIPTION
       "The number of Unavailable Seconds encountered by the Link interface
       in one of the previous 96, individual 15 minute, intervals."
    ::= { wvLinkIntervalEntry 4 }

wvLinkIntervalDMs OBJECT-TYPE
    SYNTAX      Gauge32
    MAX-ACCESS  read-only
    STATUS      current
    DESCRIPTION
       "The number of Degraded Minutes (DMs) encountered by the Link
       interface in one of the previous 96, individual 15 minute, intervals."
    ::= { wvLinkIntervalEntry 5 }

wvLinkIntervalBER OBJECT-TYPE
    SYNTAX      FloatingPoint
    MAX-ACCESS  read-only
    STATUS      current
    DESCRIPTION
        "The Bit Error Rate encountered by the Link interface in one of the
        previous 96, individual 15 minute, intervals."
    ::= { wvLinkIntervalEntry 6 }

wvLinkIntervalBLER OBJECT-TYPE
    SYNTAX      FloatingPoint
    MAX-ACCESS  read-only
    STATUS      current
    DESCRIPTION
        "The Corrected Blocks Rate encountered by the Link interface in
	one of the previous 96, individual 15 minute, intervals."
    ::= { wvLinkIntervalEntry 7 }

wvLinkIntervalBBER OBJECT-TYPE
    SYNTAX      FloatingPoint
    MAX-ACCESS  read-only
    STATUS      current
    DESCRIPTION
        "The Background Blocks Error Rate encountered by the Link interface in
        one of the previous 96, individual 15 minute, intervals."
    ::= { wvLinkIntervalEntry 8 }

wvLinkIntervalNCBLER OBJECT-TYPE
    SYNTAX      FloatingPoint
    MAX-ACCESS  read-only
    STATUS      current
    DESCRIPTION
        "The Not Corrected Blocks Error Rate encountered by the Link interface in
	one of the previous 96, individual 15 minute, intervals."
    ::= { wvLinkIntervalEntry 9 }

wvlinkIntervalAverageRSL OBJECT-TYPE
    SYNTAX      Integer32
    UNITS       "dBm"
    MAX-ACCESS  read-only
    STATUS      current
    DESCRIPTION
        "Specifies the average Receive Signal Level,
        encountered by the Link interface in one of the previous 96, individual
        15 minute, intervals."
    ::= { wvLinkIntervalEntry 10 }

wvlinkIntervalMaximumRSL OBJECT-TYPE
    SYNTAX      Integer32
    UNITS       "dBm"
    MAX-ACCESS  read-only
    STATUS      current
    DESCRIPTION
        "Specifies the maximum Receive Signal Level,
        encountered by the Link interface in one of the previous 96, individual
        15 minute, intervals."
    ::= { wvLinkIntervalEntry 11 }

wvlinkIntervalMinimumRSL OBJECT-TYPE
    SYNTAX      Integer32
    UNITS       "dBm"
    MAX-ACCESS  read-only
    STATUS      current
    DESCRIPTION
        "Specifies the minimum Receive Signal Level,
        encountered by the Link interface in one of the previous 96, individual
        15 minute, intervals."
    ::= { wvLinkIntervalEntry 12 }


-- *** the Link Total sub-group ***

-- The Link Total sub-group contains the cumulative sum of the
-- various statistics for the 24 hour period preceding the
-- current interval.

wvLinkTotalESs OBJECT-TYPE
    SYNTAX      Gauge32
    MAX-ACCESS  read-only
    STATUS      current
    DESCRIPTION
       "The number of Errored Seconds encountered by the Link interface in
       the previous 24 hour interval."
    ::= { wvPerformance 26 }

wvLinkTotalSESs OBJECT-TYPE
    SYNTAX      Gauge32
    MAX-ACCESS  read-only
    STATUS      current
    DESCRIPTION
       "The number of Severely Errored Seconds encountered by the Link
       interface in the previous 24 hour interval."
    ::= { wvPerformance 27 }

wvLinkTotalUASs OBJECT-TYPE
    SYNTAX      Gauge32
    MAX-ACCESS  read-only
    STATUS      current
    DESCRIPTION
       "The number of Unavailable Seconds encountered by the Link interface
       the previous 24 hour interval."
    ::= { wvPerformance 28 }

wvLinkTotalDMs OBJECT-TYPE
    SYNTAX      Gauge32
    MAX-ACCESS  read-only
    STATUS      current
    DESCRIPTION
       "The number of Degraded Minutes (DMs) encountered by the Link
       interface in the previous 24 hour interval."
    ::= { wvPerformance 29 }

wvLinkTotalBER OBJECT-TYPE
    SYNTAX      FloatingPoint
    MAX-ACCESS  read-only
    STATUS      current
    DESCRIPTION
        "The Bit Error Rate encountered by the Link interface in the
        previous 24 hour interval."
    ::= { wvPerformance 30 }

wvLinkTotalBLER OBJECT-TYPE
    SYNTAX      FloatingPoint
    MAX-ACCESS  read-only
    STATUS      current
    DESCRIPTION
        "The Corrected Blocks Rate encountered by the Link interface in the
        previous 24 hour interval."
    ::= { wvPerformance 31 }

wvLinkTotalBBER OBJECT-TYPE
    SYNTAX      FloatingPoint
    MAX-ACCESS  read-only
    STATUS      current
    DESCRIPTION
        "The Background Blocks Error Rate encountered by the Link interface in
        the previous 24 hour interval."
    ::= { wvPerformance 32 }

wvLinkTotalNCBLER OBJECT-TYPE
    SYNTAX      FloatingPoint
    MAX-ACCESS  read-only
    STATUS      current
    DESCRIPTION
        "The Not Corrected Blocks Rate encountered by the Link interface in the
        previous 24 hour interval."
    ::= { wvPerformance 33 }

wvlinkTotalAverageRSL OBJECT-TYPE
    SYNTAX      Integer32
    UNITS       "dBm"
    MAX-ACCESS  read-only
    STATUS      current
    DESCRIPTION
        "Specifies the average Receive Signal Level,
        encountered by the Link interface in the previous 24 hour interval."
    ::= { wvPerformance 34 }

wvlinkTotalMaximumRSL OBJECT-TYPE
    SYNTAX      Integer32
    UNITS       "dBm"
    MAX-ACCESS  read-only
    STATUS      current
    DESCRIPTION
        "Specifies the maximum Receive Signal Level,
        encountered by the Link interface in the previous 24 hour interval."
    ::= { wvPerformance 35 }

wvlinkTotalMinimumRSL OBJECT-TYPE
    SYNTAX      Integer32
    UNITS       "dBm"
    MAX-ACCESS  read-only
    STATUS      current
    DESCRIPTION
        "Specifies the minimum Receive Signal Level,
        encountered by the Link interface in the previous 24 hour interval."
    ::= { wvPerformance 36 }


-- *** the Link Absolute Counters sub-group ***

-- The Link Absolute Counters sub-group	contains absolute counters that
-- monotonically increase until they reaches a maximum value of 2^32-1
-- (4294967295 decimal), when it wraps around and starts increasing
-- again from zero.
-- These allow the user to calculate various rates based on deltas of his
-- choice.

wvlinkNoOfReceivedKBits OBJECT-TYPE
    SYNTAX      Counter32
    UNITS       "Kilobits"
    MAX-ACCESS  read-only
    STATUS      current
    DESCRIPTION
        "Specifies the total number of kilobits received by the Link interface."
    ::= { wvPerformance 40 }

wvlinkNoOfErrors OBJECT-TYPE
    SYNTAX      Counter32
    MAX-ACCESS  read-only
    STATUS      current
    DESCRIPTION
        "Specifies the total number of errors received by the Link interface, before
	FEC Correction."
    ::= { wvPerformance 41 }

wvlinkErroredBlocks OBJECT-TYPE
    SYNTAX      Counter32
    MAX-ACCESS  read-only
    STATUS      current
    DESCRIPTION
        "Specifies the total number of errored blocks received by the Link interface, before
	FEC Correction."
    ::= { wvPerformance 42 }

wvlinkNotCorrectedErroredBlocks OBJECT-TYPE
    SYNTAX      Counter32
    MAX-ACCESS  read-only
    STATUS      current
    DESCRIPTION
        "Specifies the total number of blocks that could not be corrected by the FEC,
	received by the Link interface."
    ::= { wvPerformance 43 }

wvLinkPerformanceCountTime OBJECT-TYPE
    SYNTAX  TimeTicks
    MAX-ACCESS  read-only
    STATUS      current
    DESCRIPTION
            "The time (in hundredths of a second) since when Link related
	    performance is calculated.
	    It behaves like sysUpTime and is reset to 0 whenever Link
	    characteristics (Capacity, Modulation, etc...) is changed."
    ::= { wvPerformance 50 }


-- *** the Link Instantaneous sub-group ***

-- The Link Total sub-group contains the cumulative sum of the
-- various statistics for the 24 hour period preceding the
-- current interval.

wvlinkInstantaneousBER  OBJECT-TYPE
    SYNTAX      FloatingPoint
    MAX-ACCESS  read-only
    STATUS      current
    DESCRIPTION
        "The Instantaneous Bit Error Rate encountered by the Link interface.
		 This is the value adaptively calculated to reach a 1% measurement precision."
    ::= { wvPerformance 60 }



-- *** ETH 10/100 ***
-- Below objects are in addition to dot3 standard statistics

wvEth10-100TxLinkUsage OBJECT-TYPE
    SYNTAX      Integer32
    UNITS       "Bits/sec"
    MAX-ACCESS  read-only
    STATUS      current
    DESCRIPTION
        "Shows the actual no. of bits being transmitted by the ETH 10/100 ports to
	 the Link interface."
    ::= { wvPerformance 100 }

wvEth10-100RxLinkUsage OBJECT-TYPE
    SYNTAX      Integer32
    UNITS       "Bits/sec"
    MAX-ACCESS  read-only
    STATUS      current
    DESCRIPTION
        "Shows the actual no. of bits being received by the ETH 10/100 ports from
	 the Link interface."
    ::= { wvPerformance 101 }

wvEth10-100TxLinkUtilization OBJECT-TYPE
    SYNTAX      Integer32
    UNITS       "%"
    MAX-ACCESS  read-only
    STATUS      current
    DESCRIPTION
        "Shows the calculated ETH 10/100 Link percentage Tx usage
	 (100 X wvEth10-100TxLinkUsage / total channel capacity)."
    ::= { wvPerformance 102 }

wvEth10-100RxLinkUtilization OBJECT-TYPE
    SYNTAX      Integer32
    UNITS       "%"
    MAX-ACCESS  read-only
    STATUS      current
    DESCRIPTION
        "Shows the calculated ETH 10/100 Link percentage Rx usage
	 (100 X wvEth10-100RxLinkUsage / total channel capacity)."
    ::= { wvPerformance 103 }


-- ####################################################################
-- *** Tests Group ***
-- ####################################################################

-- *** Loopback Parameters ***

wvLoopbackType OBJECT-TYPE
    SYNTAX      WvLoopbacksList
    MAX-ACCESS  read-write
    STATUS      current
    DESCRIPTION
        "Defines the type of loopback to be performed on the terminal."
    ::= { wvTests 1 }

wvLoopbackStartTime OBJECT-TYPE
    SYNTAX      TimeTicks
    MAX-ACCESS  read-write
    STATUS      current
    DESCRIPTION
        "Defines the desired delay time, in time-ticks, before the loopbacks
	specified by wvLoopbackType are activated.
        When any loopback is on, either on delay or started, 0 forces a
	premature stop."
    ::= { wvTests 2 }

wvLoopbackTimePeriod OBJECT-TYPE
    SYNTAX      TimeInterval (0..3600000)   -- up to 10 hours
    MAX-ACCESS  read-write
    STATUS      current
    DESCRIPTION
        "Defines the desired duration of the loopback.
        Setting a value of 0 means it should run until deliberately stopped."
    DEFVAL { 60000 }    -- 10 minutes
    ::= { wvTests 3 }

wvLoopbackRemainingStartTime OBJECT-TYPE
    SYNTAX      TimeTicks
    MAX-ACCESS  read-only
    STATUS      current
    DESCRIPTION
        "Defines the ongoing remaining time before the loopbacks specified
        by wvLoopbackType are activated."
    ::= { wvTests 4 }

wvLoopbackRemainingTimePeriod OBJECT-TYPE
    SYNTAX      TimeInterval
    MAX-ACCESS  read-only
    STATUS      current
    DESCRIPTION
        "Defines the ongoing remaining duration of the loopback activation."
    ::= { wvTests 5 }


-- *** Self-Test (Built-In-Tests) Parameters ***

wvSelfTestType OBJECT-TYPE
    SYNTAX      BITS {
                        noTest(0),
                        ramTest(1),
                        flashTest(2),
                        epromTest(3),
                        fpTest(4),
                        modemTest(5),
                        fecTest(6),
                        muxTest(7),
                        ibTest(8),
                        bertTest(9),
                        sccTest(10)
                    -- ??? TBD tests ???
                    }
    MAX-ACCESS  read-write
    STATUS      deprecated
    DESCRIPTION
        "Defines the type of next self-tests to be performed on the terminal.
        Local restrictions may limit the tests that can be performed
        simultaneously."
    ::= { wvTests 100 }

wvSelfTestStartTime OBJECT-TYPE
    SYNTAX      TimeTicks
    MAX-ACCESS  read-write
    STATUS      deprecated
    DESCRIPTION
        "Defines the desired delay time, in time-ticks, before the tests specified
        by wvSelfTestType are started.
        When any test is running, 0 forces a premature stop."
    ::= { wvTests 101 }

wvLastSelfTestStartTime OBJECT-TYPE
    SYNTAX      TimeTicks
    MAX-ACCESS  read-only
    STATUS      current
    DESCRIPTION
        "Keeps the time, relative to sysUpTime, when the tests in the
         wvLastSelfTestTable were last performed."
    ::= { wvTests 102 }

wvLastSelfTestTable OBJECT-TYPE
    SYNTAX      SEQUENCE OF WvLastSelfTestEntry
    MAX-ACCESS  not-accessible
    STATUS      current
    DESCRIPTION
        "A table of last self tests."
    ::= { wvTests 103 }

wvLastSelfTestEntry OBJECT-TYPE
    SYNTAX      WvLastSelfTestEntry
    MAX-ACCESS  not-accessible
    STATUS      current
    DESCRIPTION
        "Entry in the wvLastSelfTestTable.
        There is one for each of the last run self-tests."
    INDEX       { wvLastSelfTestType }
    ::= { wvLastSelfTestTable 1 }

WvLastSelfTestEntry ::= SEQUENCE {
    wvLastSelfTestType             INTEGER,
    wvLastSelfTestStatus           INTEGER
    }

wvLastSelfTestType OBJECT-TYPE
    SYNTAX      INTEGER {
                        noTest(0),
                        ramTest(1),
                        flashTest(2),
                        epromTest(3),
                        fpTest(4),
                        modemTest(5),
                        fecTest(6),
                        muxTest(7),
                        ibTest(8),
                        bertTest(9),
                        sccTest(10)
                    }
    MAX-ACCESS  read-only
    STATUS      current
    DESCRIPTION
        "The self-test type for this entry."
    ::= { wvLastSelfTestEntry 1 }

wvLastSelfTestStatus OBJECT-TYPE
    SYNTAX      INTEGER {
                    failed(1),
                    passed(2)
                    }
    MAX-ACCESS  read-only
    STATUS      current
    DESCRIPTION
        "The status of the test specified in wvLastSelfTestType."
    ::= { wvLastSelfTestEntry 2 }


wvSelfTestRemainingStartTime OBJECT-TYPE
    SYNTAX      TimeTicks
    MAX-ACCESS  read-only
    STATUS      deprecated
    DESCRIPTION
        "Defines the ongoing remaining time before the tests specified
        by wvSelfTestType start."
    ::= { wvTests 104 }


-- *** Line Test Signal Parameters ***

wvInsertTestSignalLine OBJECT-TYPE
    SYNTAX      BITS {
                    filler0(0),
                    dsx1-1(1),     -- e1/t1 port 1
                    dsx1-2(2),     -- e1/t1 port 2
                    dsx1-3(3),     -- e1/t1 port 3
                    dsx1-4(4),     -- e1/t1 port 4
                    dsx1-5(5),     -- e1/t1 port 5
                    dsx1-6(6),     -- e1/t1 port 6
                    dsx1-7(7),     -- e1/t1 port 7
                    dsx1-8(8),     -- e1/t1 port 8
                    dsx1-9(9),     -- e1/t1 port 9
                    dsx1-10(10),   -- e1/t1 port 10
                    dsx1-11(11),   -- e1/t1 port 11
                    dsx1-12(12),   -- e1/t1 port 12
                    dsx1-13(13),   -- e1/t1 port 13
                    dsx1-14(14),   -- e1/t1 port 14
                    dsx1-15(15),   -- e1/t1 port 15
                    dsx1-16(16),   -- e1/t1 port 16
                    dsx3(17),      -- e3/t3 port
		    eth10-100(18)  -- ETH 10/100
                    }
    MAX-ACCESS  read-write
    STATUS      current
    DESCRIPTION
        "Defines the line(s) on which a special BER test signal is inserted.
        Proper loopbacks are assumed to be previously set for the test to succeed.
	If no loopback is selected, the test results are checked at the peer terminal.
        The actual lines applicable depend on wvLinkCapacity.
        In addition, only the following combinations can be simultaneously tested:
        - 1 T1/E1 line
        - T3/E3 line
	- the eth10-100 board (both ports)
        - all existing lines/ports (full capacity)."
    ::= { wvTests 200 }

wvInsertTestSignalStartTime OBJECT-TYPE
    SYNTAX      TimeTicks
    MAX-ACCESS  read-write
    STATUS      current
    DESCRIPTION
        "Defines the desired delay time, in time-ticks, before the tests on the lines
        specified by wvInsertTestSignalLine are started.
        When any test is on, 0 forces a premature stop."
    ::= { wvTests 201 }

wvInsertTestSignalTimePeriod OBJECT-TYPE
    SYNTAX      TimeInterval (0..3600000)   -- up to 10 hours
    MAX-ACCESS  read-write
    STATUS      current
    DESCRIPTION
        "Defines the desired duration of the tests.
        Setting a value of 0 means it should run until deliberately stopped."
    ::= { wvTests 202 }

wvLastTestSignalTime OBJECT-TYPE
    SYNTAX      TimeTicks
    MAX-ACCESS  read-only
    STATUS      current
    DESCRIPTION
        "Defines the time, relative to sysUpTime, when the insert test signal
        was last performed."
    ::= { wvTests 203 }

wvLastTestSignalBER OBJECT-TYPE
    SYNTAX      FloatingPoint
    MAX-ACCESS  read-only
    STATUS      current
    DESCRIPTION
        "Specifies the Bit Error Rate from last test signal activation."
    ::= { wvTests 204 }

wvInsertTestSignalRemainingStartTime OBJECT-TYPE
    SYNTAX      TimeTicks
    MAX-ACCESS  read-only
    STATUS      current
    DESCRIPTION
        "Defines the ongoing remaining time before the tests on the lines
        specified by wvInsertTestSignalLine start."
    ::= { wvTests 205 }

wvInsertTestSignalRemainingTimePeriod OBJECT-TYPE
    SYNTAX      TimeInterval
    MAX-ACCESS  read-only
    STATUS      current
    DESCRIPTION
        "Defines the ongoing remaining duration of the tests."
    ::= { wvTests 206 }


-- *** Parameters for Diagnostic usage ***
-- This is for authorized personnel use only, since the details of
-- these objects contents are not of general knowledge

wvGenericDiagnosticsParameterAddress OBJECT-TYPE
    SYNTAX      Integer32
    MAX-ACCESS  read-write
    STATUS      current
    DESCRIPTION
        "This object defines the address on the IDU physical memory
	from which wvGenericDiagnosticsParameterValue below is read.
	The given address will be aligned to long, if needed.
	Attempt to set it to a non-valid address will be rejected."
    ::= { wvTests 300 }

wvGenericDiagnosticsParameterValue OBJECT-TYPE
    SYNTAX      Integer32
    MAX-ACCESS  read-only
    STATUS      current
    DESCRIPTION
        "Reading of this object returns the 4 bytes (long) value on the address
	specified by wvGenericDiagnosticsParameterAddress above."
    ::= { wvTests 301 }




-- ***##############################################################***
--              Traps Definitions Group
-- ***##############################################################***

-- define next to overcome some compilers objections to advance directly 2 levels
wvTraps0                OBJECT IDENTIFIER ::= { wvTraps 0 }
wvTrapVars              OBJECT IDENTIFIER ::= { wvTraps 1 }


wvTrapKeepAlivePeriod OBJECT-TYPE
    SYNTAX      Integer32
    MAX-ACCESS  read-write
    STATUS      current
    DESCRIPTION
        "This object defines the keep alive traps period in minutes."
    ::= { wvTrapVars 1 }


wvAisPortTrap OBJECT-TYPE
    SYNTAX      Integer32
    MAX-ACCESS  read-only
    STATUS      current
    DESCRIPTION
        "This object defines the port munber that refers to wvLineAisStart/wvLineAisStop
        /wvAisReceiveStart/wvAisReceiveStop, this number should be used as wvTributaryPortIfIndex in the wvTributaryPortTable."
    ::= { wvTrapVars 2 }


wvLosPortTrap OBJECT-TYPE
    SYNTAX      Integer32
    MAX-ACCESS  read-only
    STATUS      current
    DESCRIPTION
        "This object defines the port munber that refers to wvLineLosStart/wvLineLosStop,
        this number should be used as wvTributaryPortIfIndex in the wvTributaryPortTable."
    ::= { wvTrapVars 3 }


wvExternalInputTrap OBJECT-TYPE
    SYNTAX      INTEGER (0..5)
    MAX-ACCESS  read-only
    STATUS      current
    DESCRIPTION
        "This object defines the external input munber that refers to wvExternalInputsStart/wvExternalInputsStop."
    ::= { wvTrapVars 4 }


wvRelayIdTrap OBJECT-TYPE
    SYNTAX      Integer32
    MAX-ACCESS  read-only
    STATUS      current
    DESCRIPTION
        "This object defines the relay id munber that refers to wvRelayStart\wvRelayStop,
        this number should be used as wvRelayId in the wvRelayTable."
    ::= { wvTrapVars 5 }


wvSelectTrapVector OBJECT-TYPE
    SYNTAX      BITS {
                    -- *** Fatal Severity Alarms ***
             wlOduCableFaultStart          (0) ,
             wlOduCableFaultStop           (1) ,
             wlIduIntnlFaultStart          (2) ,
             wlIduIntnlFaultStop           (3) ,
             wlOduIntnlFaultStart          (4) ,
             wlOduIntnlFaultStop           (5) ,
             wlLinkDownStart               (6) ,
             wlLinkDownStop                (7) ,
             wlIdViolationtStart           (8) ,
             wlIdViolationStop             (9) ,
             wlRmtTermAccsStart            (10),
             wlRmtTermAccsStop             (11),
             wlLoclOduAccsStart            (12),
             wlLoclOduAccsStop             (13),
             wlRcvSignLowLevlStart         (14),
             wlRcvSignLowLevlStop          (15),
             wlRelayStart                  (16),
             wlRelayStop                   (17),
             wlAisStart                    (18),
             wlAisStop                     (19),
             wlLosStart                    (20),
             wlLosStop                     (21),
             wlBerWarnStart                (22),
             wlBerWarnStop                 (23),
             wlBerErrStart                 (24),
             wlBerErrStop                  (25),
             wlExtInputsStart              (26),
             wlExtInputsStop               (27),
             wlUasStart                    (28),
             wlUasStop                     (29),
             wlTftpFail                    (30),
             wlTftpSuss                    (31),
             wlOduTempStart                (32),
             wlOduTempStop                 (33),
             wlTxMuteStart                 (34),
             wlTxMuteStop                  (35),
             wlPwrSupplyStart              (36),
             wlPwrSupplyStop               (37),
             wlCfgMismatch                 (38),
             wlBankSw                      (39),
             wlPortLoopBckStart            (40),
             wlPortLoopBckStop             (41),
             wlPortBertStart               (42),
             wlPortBertStop                (43),
             wlHeartBit                    (44),
             wlAisReceiveStart             (45),
             wlAisReceiveStop              (46),
             wlEth10x100RxLinkUsageLowStart  (47),
             wlEth10x100RxLinkUsageLowStop   (48),
             wlEth10x100RxLinkUsageHighStart (49),
             wlEth10x100RxLinkUsageHighStop  (50),
             wlEth10x100TxLinkUsageLowStart  (51),
             wlEth10x100TxLinkUsageLowStop   (52),
             wlEth10x100TxLinkUsageHighStart (53),
             wlEth10x100TxLinkUsageHighStop  (54),
             wlEnd                         (55) -- END OF TRAPS
               }

    MAX-ACCESS  read-write
    STATUS      current
    DESCRIPTION
        "Private traps mapping."
    ::= { wvTrapVars 6 }

wvTrapKeepAliveVarsSelect OBJECT-TYPE
    SYNTAX      BITS {
             vRSL          (0) ,
             vBER          (1) ,
             vUAS          (2) ,
             vEnd          (3)  -- END OF VARS
               }

    MAX-ACCESS  read-write
    STATUS      current
    DESCRIPTION
        "Keep Alive trap variables mapping."
    ::= { wvTrapVars 7 }


wvTrapKeepAliveString OBJECT-TYPE
    SYNTAX  DisplayString (SIZE (0..255))
    MAX-ACCESS  read-only
    STATUS      current
    DESCRIPTION
        "A verbal string send with the wvIduHeartBit trap
	 Has the following format:
	 Serial Numbers:   \
	                 [RSL = ] [BER = ] [UAS = ]"
    ::= { wvTrapVars 8 }




wvIduOduCableFaultStart NOTIFICATION-TYPE
                OBJECTS {
                        wvIduOduCableStatus
                        }
    STATUS      current
    DESCRIPTION
        "A trap indicating Idu or Odu cable fail"
    ::= { wvTraps0 1 }

wvIduOduCableFaultStop NOTIFICATION-TYPE
                OBJECTS {
                        wvIduOduCableStatus
                        }
    STATUS      current
    DESCRIPTION
        "A trap indicating restoring from wvIduOduCableFaultStart"
    ::= { wvTraps0 2 }


wvIduInternalFaultStart NOTIFICATION-TYPE
                OBJECTS {
                        wvIduStatus
                        }
    STATUS      current
    DESCRIPTION
        "A trap indicating Idu internal fail: RX or TX synthesizer out of lock
	 or power supply fail"
    ::= { wvTraps0 3 }

wvIduInternalFaultStop NOTIFICATION-TYPE
                OBJECTS {
                        wvIduStatus
                        }
    STATUS      current
    DESCRIPTION
        "A trap indicating restoring from wvIduInternalFaultStart"
    ::= { wvTraps0 4 }


wvOduInternalFaultStart NOTIFICATION-TYPE
                OBJECTS {
                        wvOduStatus
                        }
    STATUS      current
    DESCRIPTION
        "A trap indicating Odu internal fail: RX or TX synthesizer out of lock
	 or power supply fail"
    ::= { wvTraps0 5 }

wvOduInternalFaultStop NOTIFICATION-TYPE
                OBJECTS {
                        wvOduStatus
                        }
    STATUS      current
    DESCRIPTION
        "A trap indicating restoring from wvOduInternalFaultStart"
    ::= { wvTraps0 6 }


wvLinkDownStart NOTIFICATION-TYPE
                OBJECTS {
                        wvLinkPerformanceAlarmsStatus
                        }
    STATUS      current
    DESCRIPTION
        "A trap indicating that MUX or MODEM is not synchronized "
    ::= { wvTraps0 7 }

wvLinkDownStop NOTIFICATION-TYPE
                OBJECTS {
                        wvLinkPerformanceAlarmsStatus
                        }
    STATUS      current
    DESCRIPTION
        "A trap indicating restoring from wvLinkDownStart"
    ::= { wvTraps0 8 }


wvIdViolationStart NOTIFICATION-TYPE
                OBJECTS {
                        wvSecurityStatus
                        }
    STATUS      current
    DESCRIPTION
        "A trap indicating that the last received peer Link ID does not
	 match the local Link ID"
    ::= { wvTraps0 9 }

wvIdViolationStop NOTIFICATION-TYPE
                OBJECTS {
                        wvSecurityStatus
                        }
    STATUS      current
    DESCRIPTION
        "A trap indicating restoring from wvIdViolationStart"
    ::= { wvTraps0 10 }


wvRemoteAccessStart NOTIFICATION-TYPE
                OBJECTS {
                        wvRemoteTerminalStatus
                        }
    STATUS      current
    DESCRIPTION
        "A trap indicating that the remote terminal is not accessable"
    ::= { wvTraps0 11 }

wvRemoteAccessStop NOTIFICATION-TYPE
                OBJECTS {
                        wvRemoteTerminalStatus
                        }
    STATUS      current
    DESCRIPTION
        "A trap indicating restoring from wvRemoteAccessStart"
    ::= { wvTraps0 12 }



wvLocalOduAccessStart NOTIFICATION-TYPE
                OBJECTS {
                        wvOduStatus
                        }
    STATUS      current
    DESCRIPTION
        "A trap indicating that the local Odu is not responding"
    ::= { wvTraps0 13 }

wvLocalOduAccessStop NOTIFICATION-TYPE
                OBJECTS {
                        wvOduStatus
                        }
    STATUS      current
    DESCRIPTION
        "A trap indicating restoring from wvLocalOduAccessStart"
    ::= { wvTraps0 14 }

wvReceiveSignalLowerLevelStart NOTIFICATION-TYPE
                OBJECTS {
		        wvRxSignalLevel,
                        wvAtpcRslLowerThreshold
                        }
    STATUS      current
    DESCRIPTION
        "A trap indicating that the local RSL is out of the lower range"
    ::= { wvTraps0 15 }

wvReceiveSignalLowerLevelStop NOTIFICATION-TYPE
                OBJECTS {
		        wvRxSignalLevel,
                        wvAtpcRslLowerThreshold
                        }
    STATUS      current
    DESCRIPTION
        "A trap indicating restoring from wvReceiveSignalLowerLevelStart"
    ::= { wvTraps0 16 }

wvRelayStart NOTIFICATION-TYPE
                OBJECTS {
		        wvRelayIdTrap
                        }
    STATUS      current
    DESCRIPTION
        "A trap indicating that the relay was switched to on"
    ::= { wvTraps0 17 }

wvRelayStop NOTIFICATION-TYPE
                OBJECTS {
                        wvRelayIdTrap
                        }
    STATUS      current
    DESCRIPTION
        "A trap indicating that the relay was switched to off "
    ::= { wvTraps0 18 }



wvLineAisStart NOTIFICATION-TYPE
                OBJECTS {
			wvAisPortTrap
                        }
    STATUS      current
    DESCRIPTION
        "A trap indicating that the port transmit AIS"
    ::= { wvTraps0 19 }

wvLineAisStop NOTIFICATION-TYPE
                OBJECTS {
			wvAisPortTrap
                        }
    STATUS      current
    DESCRIPTION
        "A trap indicating restoring from wvLineAisStart"
    ::= { wvTraps0 20 }


wvLineLosStart NOTIFICATION-TYPE
                OBJECTS {
			wvLosPortTrap
                        }
    STATUS      current
    DESCRIPTION
        "A trap indicating that there is an LOS on the specified line"
    ::= { wvTraps0 21 }

wvLineLosStop NOTIFICATION-TYPE
                OBJECTS {
			wvLosPortTrap
                        }
    STATUS      current
    DESCRIPTION
        "A trap indicating restoring from wvLineLosStart"
    ::= { wvTraps0 22 }


wvBerWarningStart NOTIFICATION-TYPE
                OBJECTS {
		        wvlinkBER,
                        wvLinkBERWarningThresholdLow,
			wvLinkBERWarningThresholdHigh
                        }
    STATUS      current
    DESCRIPTION
        "A trap indicating that the local BER is out of range"
    ::= { wvTraps0 23 }

wvBerWarningStop NOTIFICATION-TYPE
                OBJECTS {
		        wvlinkBER,
                        wvLinkBERWarningThresholdLow,
			wvLinkBERWarningThresholdHigh
                        }
    STATUS      current
    DESCRIPTION
        "A trap indicating restoring from wvBerStart"
    ::= { wvTraps0 24 }

wvBerFatalStart NOTIFICATION-TYPE
                OBJECTS {
		        wvlinkBER,
                        wvLinkBERErrorThresholdLow,
			wvLinkBERErrorThresholdHigh
                        }
    STATUS      current
    DESCRIPTION
        "A trap indicating that the local BER is out of range"
    ::= { wvTraps0 25 }

wvBerFatalStop NOTIFICATION-TYPE
                OBJECTS {
		        wvlinkBER,
                        wvLinkBERErrorThresholdLow,
			wvLinkBERErrorThresholdHigh
                        }
    STATUS      current
    DESCRIPTION
        "A trap indicating restoring from wvBerStart"
    ::= { wvTraps0 26 }



wvExternalInputsStart NOTIFICATION-TYPE
                OBJECTS {
			wvExternalInputTrap
                        }
    STATUS      current
    DESCRIPTION
        "A trap indicating that the external input is active"
    ::= { wvTraps0 27 }

wvExternalInputsStop NOTIFICATION-TYPE
                OBJECTS {
			wvExternalInputTrap
                        }
    STATUS      current
    DESCRIPTION
        "A trap indicating restoring from wvExternalInputsStart"
    ::= { wvTraps0 28 }

wvLinkUasStart NOTIFICATION-TYPE
                OBJECTS {
		        wvLinkUAs,
                        wvLinkUASAlarmThresholdLow,
			wvLinkUASAlarmThresholdHigh
                        }
    STATUS      current
    DESCRIPTION
        "A trap indicating that the link UAS is out of range"
    ::= { wvTraps0 29 }


wvLinkUasStop NOTIFICATION-TYPE
                OBJECTS {
		        wvLinkUAs,
                        wvLinkUASAlarmThresholdLow,
			wvLinkUASAlarmThresholdHigh
                        }
    STATUS      current
    DESCRIPTION
        "A trap indicating restoring from wvLinkUasStart"
    ::= { wvTraps0 30 }


wvTftpFail NOTIFICATION-TYPE
                OBJECTS {
                        wvTftpServerIpAddress,
			wvTftpOperationCtrl,
			wvTftpFileName,
			wvTftpDwnlStatus
                        }
    STATUS      current
    DESCRIPTION
        "A trap indicating that there was TFTP operation fault"
    ::= { wvTraps0 31 }


wvTftpSuccess NOTIFICATION-TYPE
                OBJECTS {
                        wvTftpServerIpAddress,
			wvTftpOperationCtrl,
			wvTftpFileName,
			wvTftpDwnlStatus
                        }
    STATUS      current
    DESCRIPTION
        "A trap indicating that the last TFTP operation was successful"
    ::= { wvTraps0 32 }

wvOduTempViolationStart NOTIFICATION-TYPE
                OBJECTS {
			wvOduTemperature
                        }
    STATUS      current
    DESCRIPTION
        "A trap indicating that the ODU temperature is out of range"
    ::= { wvTraps0 33 }

wvOduTempViolationStop NOTIFICATION-TYPE
                OBJECTS {
			wvOduTemperature
                        }
    STATUS      current
    DESCRIPTION
        "A trap indicating restoring from wvOduTempViolationStart"
    ::= { wvTraps0 34 }


wvOduTxMuteStart NOTIFICATION-TYPE
                OBJECTS {
			wvOduStatus
                        }
    STATUS      current
    DESCRIPTION
        "A trap indicating that the ODU transmitter is in mute state"
    ::= { wvTraps0 35 }

wvOduTxMuteStop NOTIFICATION-TYPE
                OBJECTS {
			wvOduStatus
                        }
    STATUS      current
    DESCRIPTION
        "A trap indicating restoring from wvOduTxMuteStart"
    ::= { wvTraps0 36 }

wvIduPowerSupplyStart NOTIFICATION-TYPE
                OBJECTS {
			wvIduStatus
                        }
    STATUS      current
    DESCRIPTION
        "A trap indicating that theIDU ha power supply problems"
    ::= { wvTraps0 37 }


wvIduPowerSupplyStop NOTIFICATION-TYPE
                OBJECTS {
			wvIduStatus
                        }
    STATUS      current
    DESCRIPTION
        "A trap indicating restoring from wvIduPowerSupplyStart"
    ::= { wvTraps0 38 }

wvIduConfigurationMismatch NOTIFICATION-TYPE
    STATUS      current
    DESCRIPTION
        "A trap indicating that the IDU's configuration does not match the current hardware"
    ::= { wvTraps0 39 }


wvIduBankSwitchover NOTIFICATION-TYPE
    STATUS      current
    DESCRIPTION
        "A trap indicating that the bank switchover had occured"
    ::= { wvTraps0 40 }

wvIduPortLoopbackStart NOTIFICATION-TYPE
                OBJECTS {
			wvIduStatus
                        }
    STATUS      current
    DESCRIPTION
        "A trap indicating that the corresponding poer is in loopback state"
    ::= { wvTraps0 41 }

wvIduPortLoopbackStop NOTIFICATION-TYPE
                OBJECTS {
			wvIduStatus
                        }
    STATUS      current
    DESCRIPTION
        "A trap indicating restoring from wvIduPortLoopbackStart"
    ::= { wvTraps0 42 }


wvIduPortBertStart NOTIFICATION-TYPE
                OBJECTS {
			wvIduStatus
                        }
    STATUS      current
    DESCRIPTION
        "A trap indicating that the corresponding poer is in loopback state"
    ::= { wvTraps0 43 }

wvIduPortBertStop NOTIFICATION-TYPE
                OBJECTS {
			wvIduStatus
                        }
    STATUS      current
    DESCRIPTION
        "A trap indicating restoring from wvIduPortBertStart"
    ::= { wvTraps0 44 }

wvIduHeartBit NOTIFICATION-TYPE
                OBJECTS {
			wvTrapKeepAliveString
                        }
    STATUS      current
    DESCRIPTION
        " Serial Numbers: Odu, Idu;
	  HeartBit Values ( string): 
	  A HeartBit trap "
    ::= { wvTraps0 45 }

wvAisReceiveStart NOTIFICATION-TYPE
                OBJECTS {
			wvAisPortTrap
                        }
    STATUS      current
    DESCRIPTION
        "A trap indicating that the port receives AIS"
    ::= { wvTraps0 46 }

wvAisReceiveStop NOTIFICATION-TYPE
                OBJECTS {
			wvAisPortTrap
                        }
    STATUS      current
    DESCRIPTION
        "A trap indicating restoring from wvAisReceiveStart"
    ::= { wvTraps0 47 }


wlEth10x100RxLinkUsageLowStart NOTIFICATION-TYPE
                OBJECTS {
		        wvEth10-100RxLinkUsage,
                        wvEth10-100RxLinkUsageAlarmThresholdLow
                        }
    STATUS      current
    DESCRIPTION
        "A trap indicating that the Rx Link Usage  is out of low range"
    ::= { wvTraps0 48 }


wlEth10x100RxLinkUsageLowStop NOTIFICATION-TYPE
                OBJECTS {
		        wvEth10-100RxLinkUsage,
                        wvEth10-100RxLinkUsageAlarmThresholdLow
                        }
    STATUS      current
    DESCRIPTION
        "A trap indicating that the Rx Link Usage  is in low range"
    ::= { wvTraps0 49 }

wlEth10x100RxLinkUsageHighStart NOTIFICATION-TYPE
                OBJECTS {
		        wvEth10-100RxLinkUsage,
			wvEth10-100RxLinkUsageAlarmThresholdHigh
                        }
    STATUS      current
    DESCRIPTION
        "A trap indicating that the Rx Link Usage is out of High range"
    ::= { wvTraps0 50 }


wlEth10x100RxLinkUsageHighStop NOTIFICATION-TYPE
                OBJECTS {
		        wvEth10-100RxLinkUsage,
			wvEth10-100RxLinkUsageAlarmThresholdHigh
                        }
    STATUS      current
    DESCRIPTION
        "A trap indicating that the Rx Link Usage is in High range"
    ::= { wvTraps0 51 }

wlEth10x100TxLinkUsageLowStart NOTIFICATION-TYPE
                OBJECTS {
		        wvEth10-100TxLinkUsage,
                        wvEth10-100TxLinkUsageAlarmThresholdLow
                        }
    STATUS      current
    DESCRIPTION
        "A trap indicating that the Tx Link Usage is out of Low range"
    ::= { wvTraps0 52 }


wlEth10x100TxLinkUsageLowStop NOTIFICATION-TYPE
                OBJECTS {
		        wvEth10-100TxLinkUsage,
                        wvEth10-100TxLinkUsageAlarmThresholdLow
                        }
    STATUS      current
    DESCRIPTION
        "A trap indicating that the Tx Link Usage is in Low range"
    ::= { wvTraps0 53 }

wlEth10x100TxLinkUsageHighStart NOTIFICATION-TYPE
                OBJECTS {
		        wvEth10-100TxLinkUsage,
			wvEth10-100TxLinkUsageAlarmThresholdHigh
                        }
    STATUS      current
    DESCRIPTION
        "A trap indicating that the Tx Link Usage is out of High range"
    ::= { wvTraps0 54 }


wlEth10x100TxLinkUsageHighStop NOTIFICATION-TYPE
                OBJECTS {
		        wvEth10-100TxLinkUsage,
			wvEth10-100TxLinkUsageAlarmThresholdHigh
                        }
    STATUS      current
    DESCRIPTION
        "A trap indicating that the Tx Link Usage is in High range"
    ::= { wvTraps0 55 }











END
