-- file automatically created


TELDAT-TRAP-NTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ntpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NTP event subsystem."
    REVISION "201401200930Z"
    DESCRIPTION "Initial implementation"
        ::= { telEventTraps 139 }


ntpEventsGroup	OBJECT IDENTIFIER	::= { ntpTrapsMIB 1 }

ntpNotifications	OBJECT IDENTIFIER	::= { ntpTrapsMIB 2 }
ntpNotificationsPrefix	OBJECT IDENTIFIER	::= { ntpNotifications 0 }

ntpEventObjects1 OBJECT-IDENTITY
    STATUS current
    DESCRIPTION
        "Event NTP.1
        This message is generated when a packet is received from port 123."
    ::= { ntpEventsGroup 1 }

ntp1-ntpsourceadd OBJECT-TYPE
    SYNTAX IpAddress
    MAX-ACCESS accessible-for-notify
    STATUS current
    DESCRIPTION
        "Parameter 'ntpsourceadd' in event NTP.1"
    ::= { ntpEventObjects1 1 }

ntp1-refTime OBJECT-TYPE
    SYNTAX DisplayString
    MAX-ACCESS accessible-for-notify
    STATUS current
    DESCRIPTION
        "Parameter 'refTime' in event NTP.1"
    ::= { ntpEventObjects1 2 }

ntp1-orgTime OBJECT-TYPE
    SYNTAX DisplayString
    MAX-ACCESS accessible-for-notify
    STATUS current
    DESCRIPTION
        "Parameter 'orgTime' in event NTP.1"
    ::= { ntpEventObjects1 3 }

ntp1-recvTime OBJECT-TYPE
    SYNTAX DisplayString
    MAX-ACCESS accessible-for-notify
    STATUS current
    DESCRIPTION
        "Parameter 'recvTime' in event NTP.1"
    ::= { ntpEventObjects1 4 }

ntp1-txTime OBJECT-TYPE
    SYNTAX DisplayString
    MAX-ACCESS accessible-for-notify
    STATUS current
    DESCRIPTION
        "Parameter 'txTime' in event NTP.1"
    ::= { ntpEventObjects1 5 }

ntpEventObjects2 OBJECT-IDENTITY
    STATUS current
    DESCRIPTION
        "Event NTP.2
        This message is generated when a packet is sent to a remote host."
    ::= { ntpEventsGroup 2 }

ntp2-ntpdestadd OBJECT-TYPE
    SYNTAX IpAddress
    MAX-ACCESS accessible-for-notify
    STATUS current
    DESCRIPTION
        "Parameter 'ntpdestadd' in event NTP.2"
    ::= { ntpEventObjects2 1 }

ntp2-refTime OBJECT-TYPE
    SYNTAX DisplayString
    MAX-ACCESS accessible-for-notify
    STATUS current
    DESCRIPTION
        "Parameter 'refTime' in event NTP.2"
    ::= { ntpEventObjects2 2 }

ntp2-orgTime OBJECT-TYPE
    SYNTAX DisplayString
    MAX-ACCESS accessible-for-notify
    STATUS current
    DESCRIPTION
        "Parameter 'orgTime' in event NTP.2"
    ::= { ntpEventObjects2 3 }

ntp2-recvTime OBJECT-TYPE
    SYNTAX DisplayString
    MAX-ACCESS accessible-for-notify
    STATUS current
    DESCRIPTION
        "Parameter 'recvTime' in event NTP.2"
    ::= { ntpEventObjects2 4 }

ntp2-txTime OBJECT-TYPE
    SYNTAX DisplayString
    MAX-ACCESS accessible-for-notify
    STATUS current
    DESCRIPTION
        "Parameter 'txTime' in event NTP.2"
    ::= { ntpEventObjects2 5 }

ntpEventObjects3 OBJECT-IDENTITY
    STATUS current
    DESCRIPTION
        "Event NTP.3
        This message is generated after checking the input packet. Error codes
        are shown below:
        TEST1		0x0001		Duplicate packet received.
        TEST2		0x0002		Bogus packet received.
        TEST3		0x0004		Protocol unsynchronized.
        TEST4		0x0008		Peer delay/dispersion bounds check.
        TEST5		0x0010		Peer authentication failed.
        TEST6       0x0020		Peer clock unsynchronized.
        TEST7		0x0040		Peer stratum out of bounds.
        TEST8		0x0080		Root delay/dispersion bounds check."
    ::= { ntpEventsGroup 3 }

ntp3-ntpsourceadd OBJECT-TYPE
    SYNTAX IpAddress
    MAX-ACCESS accessible-for-notify
    STATUS current
    DESCRIPTION
        "Parameter 'ntpsourceadd' in event NTP.3"
    ::= { ntpEventObjects3 1 }

ntp3-errorcode OBJECT-TYPE
    SYNTAX Integer32
    MAX-ACCESS accessible-for-notify
    STATUS current
    DESCRIPTION
        "Parameter 'errorcode' in event NTP.3"
    ::= { ntpEventObjects3 2 }

ntpEventObjects4 OBJECT-IDENTITY
    STATUS current
    DESCRIPTION
        "Event NTP.4
        This message indicates a wrong NTP version."
    ::= { ntpEventsGroup 4 }

ntp4-versnumber OBJECT-TYPE
    SYNTAX Integer32
    MAX-ACCESS accessible-for-notify
    STATUS current
    DESCRIPTION
        "Parameter 'versnumber' in event NTP.4"
    ::= { ntpEventObjects4 1 }

ntp4-ntpsourceadd OBJECT-TYPE
    SYNTAX IpAddress
    MAX-ACCESS accessible-for-notify
    STATUS current
    DESCRIPTION
        "Parameter 'ntpsourceadd' in event NTP.4"
    ::= { ntpEventObjects4 2 }

ntpEventObjects5 OBJECT-IDENTITY
    STATUS current
    DESCRIPTION
        "Event NTP.5
        This message indicates the received packet is a control packet."
    ::= { ntpEventsGroup 5 }

ntp5-ntpsourceadd OBJECT-TYPE
    SYNTAX IpAddress
    MAX-ACCESS accessible-for-notify
    STATUS current
    DESCRIPTION
        "Parameter 'ntpsourceadd' in event NTP.5"
    ::= { ntpEventObjects5 1 }

ntpEventObjects6 OBJECT-IDENTITY
    STATUS current
    DESCRIPTION
        "Event NTP.6
        This message indicates the received packet is a Broadcast packet."
    ::= { ntpEventsGroup 6 }

ntp6-ntpsourceadd OBJECT-TYPE
    SYNTAX IpAddress
    MAX-ACCESS accessible-for-notify
    STATUS current
    DESCRIPTION
        "Parameter 'ntpsourceadd' in event NTP.6"
    ::= { ntpEventObjects6 1 }

ntpEventObjects8 OBJECT-IDENTITY
    STATUS current
    DESCRIPTION
        "Event NTP.8
        This message indicates the received packet is private packet."
    ::= { ntpEventsGroup 8 }

ntp8-ntpsourceadd OBJECT-TYPE
    SYNTAX IpAddress
    MAX-ACCESS accessible-for-notify
    STATUS current
    DESCRIPTION
        "Parameter 'ntpsourceadd' in event NTP.8"
    ::= { ntpEventObjects8 1 }

ntpEventObjects9 OBJECT-IDENTITY
    STATUS current
    DESCRIPTION
        "Event NTP.9
        This message indicates the received packet is client packet."
    ::= { ntpEventsGroup 9 }

ntp9-ntpsourceadd OBJECT-TYPE
    SYNTAX IpAddress
    MAX-ACCESS accessible-for-notify
    STATUS current
    DESCRIPTION
        "Parameter 'ntpsourceadd' in event NTP.9"
    ::= { ntpEventObjects9 1 }

ntpEventObjects10 OBJECT-IDENTITY
    STATUS current
    DESCRIPTION
        "Event NTP.10
        This message is generated by NTP Fake-Out routine."
    ::= { ntpEventsGroup 10 }

ntp10-ntpsourceadd OBJECT-TYPE
    SYNTAX IpAddress
    MAX-ACCESS accessible-for-notify
    STATUS current
    DESCRIPTION
        "Parameter 'ntpsourceadd' in event NTP.10"
    ::= { ntpEventObjects10 1 }

ntpEventObjects11 OBJECT-IDENTITY
    STATUS current
    DESCRIPTION
        "Event NTP.11
        This message is generated when a packet arrived from an unknown peer."
    ::= { ntpEventsGroup 11 }

ntp11-ntpsourceadd OBJECT-TYPE
    SYNTAX IpAddress
    MAX-ACCESS accessible-for-notify
    STATUS current
    DESCRIPTION
        "Parameter 'ntpsourceadd' in event NTP.11"
    ::= { ntpEventObjects11 1 }

ntpEventObjects12 OBJECT-IDENTITY
    STATUS current
    DESCRIPTION
        "Event NTP.12
        This message indicates the received packet is active mode packet."
    ::= { ntpEventsGroup 12 }

ntp12-ntpsourceadd OBJECT-TYPE
    SYNTAX IpAddress
    MAX-ACCESS accessible-for-notify
    STATUS current
    DESCRIPTION
        "Parameter 'ntpsourceadd' in event NTP.12"
    ::= { ntpEventObjects12 1 }

ntpEventObjects13 OBJECT-IDENTITY
    STATUS current
    DESCRIPTION
        "Event NTP.13
        This message indicates the received packet is passive mode packet."
    ::= { ntpEventsGroup 13 }

ntp13-ntpsourceadd OBJECT-TYPE
    SYNTAX IpAddress
    MAX-ACCESS accessible-for-notify
    STATUS current
    DESCRIPTION
        "Parameter 'ntpsourceadd' in event NTP.13"
    ::= { ntpEventObjects13 1 }

ntpEventObjects14 OBJECT-IDENTITY
    STATUS current
    DESCRIPTION
        "Event NTP.14
        This message indicates the received packet is server mode packet."
    ::= { ntpEventsGroup 14 }

ntp14-ntpsourceadd OBJECT-TYPE
    SYNTAX IpAddress
    MAX-ACCESS accessible-for-notify
    STATUS current
    DESCRIPTION
        "Parameter 'ntpsourceadd' in event NTP.14"
    ::= { ntpEventObjects14 1 }

ntpEventObjects15 OBJECT-IDENTITY
    STATUS current
    DESCRIPTION
        "Event NTP.15
        This message is shown when a clock update has been done."
    ::= { ntpEventsGroup 15 }

ntp15-Delay OBJECT-TYPE
    SYNTAX Integer32
    MAX-ACCESS accessible-for-notify
    STATUS current
    DESCRIPTION
        "Parameter 'Delay' in event NTP.15"
    ::= { ntpEventObjects15 1 }

ntp15-OffsetSign OBJECT-TYPE
    SYNTAX DisplayString
    MAX-ACCESS accessible-for-notify
    STATUS current
    DESCRIPTION
        "Parameter 'OffsetSign' in event NTP.15"
    ::= { ntpEventObjects15 2 }

ntp15-OffsetSeconds OBJECT-TYPE
    SYNTAX Integer32
    MAX-ACCESS accessible-for-notify
    STATUS current
    DESCRIPTION
        "Parameter 'OffsetSeconds' in event NTP.15"
    ::= { ntpEventObjects15 3 }

ntp15-OffsetMillSeconds OBJECT-TYPE
    SYNTAX Integer32
    MAX-ACCESS accessible-for-notify
    STATUS current
    DESCRIPTION
        "Parameter 'OffsetMillSeconds' in event NTP.15"
    ::= { ntpEventObjects15 4 }

ntpEventObjects16 OBJECT-IDENTITY
    STATUS current
    DESCRIPTION
        "Event NTP.16
        This message is shown when a date has been established."
    ::= { ntpEventsGroup 16 }

ntp16-datetostab OBJECT-TYPE
    SYNTAX DisplayString
    MAX-ACCESS accessible-for-notify
    STATUS current
    DESCRIPTION
        "Parameter 'datetostab' in event NTP.16"
    ::= { ntpEventObjects16 1 }

ntp16-stabdate OBJECT-TYPE
    SYNTAX DisplayString
    MAX-ACCESS accessible-for-notify
    STATUS current
    DESCRIPTION
        "Parameter 'stabdate' in event NTP.16"
    ::= { ntpEventObjects16 2 }

ntpEventObjects17 OBJECT-IDENTITY
    STATUS current
    DESCRIPTION
        "Event NTP.17
        This is a debugging message used to know the time since the timer
        was thrown."
    ::= { ntpEventsGroup 17 }

ntp17-secTimer OBJECT-TYPE
    SYNTAX Integer32
    MAX-ACCESS accessible-for-notify
    STATUS current
    DESCRIPTION
        "Parameter 'secTimer' in event NTP.17"
    ::= { ntpEventObjects17 1 }

ntpEventObjects18 OBJECT-IDENTITY
    STATUS current
    DESCRIPTION
        "Event NTP.18
        This message is used to know the clock precision."
    ::= { ntpEventsGroup 18 }

ntp18-millisec OBJECT-TYPE
    SYNTAX Integer32
    MAX-ACCESS accessible-for-notify
    STATUS current
    DESCRIPTION
        "Parameter 'millisec' in event NTP.18"
    ::= { ntpEventObjects18 1 }

ntpEventObjects19 OBJECT-IDENTITY
    STATUS current
    DESCRIPTION
        "Event NTP.19
        Device exact date and time."
    ::= { ntpEventsGroup 19 }

ntp19-datetime OBJECT-TYPE
    SYNTAX DisplayString
    MAX-ACCESS accessible-for-notify
    STATUS current
    DESCRIPTION
        "Parameter 'datetime' in event NTP.19"
    ::= { ntpEventObjects19 1 }

ntp19-millisec OBJECT-TYPE
    SYNTAX Integer32
    MAX-ACCESS accessible-for-notify
    STATUS current
    DESCRIPTION
        "Parameter 'millisec' in event NTP.19"
    ::= { ntpEventObjects19 2 }

ntpEventObjects20 OBJECT-IDENTITY
    STATUS current
    DESCRIPTION
        "Event NTP.20
        This message is generated when NTP client doesn't accept
        NTP broadcast messages from packet source host."
    ::= { ntpEventsGroup 20 }

ntp20-ntpsourceadd OBJECT-TYPE
    SYNTAX IpAddress
    MAX-ACCESS accessible-for-notify
    STATUS current
    DESCRIPTION
        "Parameter 'ntpsourceadd' in event NTP.20"
    ::= { ntpEventObjects20 1 }

ntpEventObjects21 OBJECT-IDENTITY
    STATUS current
    DESCRIPTION
        "Event NTP.21
        NTP transmission date/time."
    ::= { ntpEventsGroup 21 }

ntp21-datetime OBJECT-TYPE
    SYNTAX DisplayString
    MAX-ACCESS accessible-for-notify
    STATUS current
    DESCRIPTION
        "Parameter 'datetime' in event NTP.21"
    ::= { ntpEventObjects21 1 }

ntp21-millisec OBJECT-TYPE
    SYNTAX Integer32
    MAX-ACCESS accessible-for-notify
    STATUS current
    DESCRIPTION
        "Parameter 'millisec' in event NTP.21"
    ::= { ntpEventObjects21 2 }

ntp21-timeticks OBJECT-TYPE
    SYNTAX Integer32
    MAX-ACCESS accessible-for-notify
    STATUS current
    DESCRIPTION
        "Parameter 'timeticks' in event NTP.21"
    ::= { ntpEventObjects21 3 }

ntpEventObjects22 OBJECT-IDENTITY
    STATUS current
    DESCRIPTION
        "Event NTP.22
        NTP reception date/time."
    ::= { ntpEventsGroup 22 }

ntp22-datetime OBJECT-TYPE
    SYNTAX DisplayString
    MAX-ACCESS accessible-for-notify
    STATUS current
    DESCRIPTION
        "Parameter 'datetime' in event NTP.22"
    ::= { ntpEventObjects22 1 }

ntp22-millisec OBJECT-TYPE
    SYNTAX Integer32
    MAX-ACCESS accessible-for-notify
    STATUS current
    DESCRIPTION
        "Parameter 'millisec' in event NTP.22"
    ::= { ntpEventObjects22 2 }

ntp22-timeticks OBJECT-TYPE
    SYNTAX Integer32
    MAX-ACCESS accessible-for-notify
    STATUS current
    DESCRIPTION
        "Parameter 'timeticks' in event NTP.22"
    ::= { ntpEventObjects22 3 }

ntpEventObjects24 OBJECT-IDENTITY
    STATUS current
    DESCRIPTION
        "Event NTP.24
        NTP packets are discarded because NTP client is stopped."
    ::= { ntpEventsGroup 24 }

ntp24-ntpsourceadd OBJECT-TYPE
    SYNTAX IpAddress
    MAX-ACCESS accessible-for-notify
    STATUS current
    DESCRIPTION
        "Parameter 'ntpsourceadd' in event NTP.24"
    ::= { ntpEventObjects24 1 }

ntpEventObjects26 OBJECT-IDENTITY
    STATUS current
    DESCRIPTION
        "Event NTP.26
        This message is generated when a local packet arrived. NTP only accepts
        packets from other hosts."
    ::= { ntpEventsGroup 26 }

ntp26-ntpsourceadd OBJECT-TYPE
    SYNTAX IpAddress
    MAX-ACCESS accessible-for-notify
    STATUS current
    DESCRIPTION
        "Parameter 'ntpsourceadd' in event NTP.26"
    ::= { ntpEventObjects26 1 }

ntpEventObjects27 OBJECT-IDENTITY
    STATUS current
    DESCRIPTION
        "Event NTP.27
        A NTP packet has been received from the specified host, but it was wrong
        because it failed the specidifed test (number, error code and
        description)."
    ::= { ntpEventsGroup 27 }

ntp27-ntpsourceadd OBJECT-TYPE
    SYNTAX IpAddress
    MAX-ACCESS accessible-for-notify
    STATUS current
    DESCRIPTION
        "Parameter 'ntpsourceadd' in event NTP.27"
    ::= { ntpEventObjects27 1 }

ntp27-testnumber OBJECT-TYPE
    SYNTAX Integer32
    MAX-ACCESS accessible-for-notify
    STATUS current
    DESCRIPTION
        "Parameter 'testnumber' in event NTP.27"
    ::= { ntpEventObjects27 2 }

ntp27-testerrorcode OBJECT-TYPE
    SYNTAX Integer32
    MAX-ACCESS accessible-for-notify
    STATUS current
    DESCRIPTION
        "Parameter 'testerrorcode' in event NTP.27"
    ::= { ntpEventObjects27 3 }

ntp27-testdescription OBJECT-TYPE
    SYNTAX DisplayString
    MAX-ACCESS accessible-for-notify
    STATUS current
    DESCRIPTION
        "Parameter 'testdescription' in event NTP.27"
    ::= { ntpEventObjects27 4 }

ntpEventObjects28 OBJECT-IDENTITY
    STATUS current
    DESCRIPTION
        "Event NTP.28
        NTP peer host clock data has been updated by the clock-filter prodedure,
        producing new values for delay, offset and dispersion, as shown in the
        trace."
    ::= { ntpEventsGroup 28 }

ntp28-ntpsourceadd OBJECT-TYPE
    SYNTAX IpAddress
    MAX-ACCESS accessible-for-notify
    STATUS current
    DESCRIPTION
        "Parameter 'ntpsourceadd' in event NTP.28"
    ::= { ntpEventObjects28 1 }

ntp28-delay OBJECT-TYPE
    SYNTAX Integer32
    MAX-ACCESS accessible-for-notify
    STATUS current
    DESCRIPTION
        "Parameter 'delay' in event NTP.28"
    ::= { ntpEventObjects28 2 }

ntp28-offset OBJECT-TYPE
    SYNTAX Integer32
    MAX-ACCESS accessible-for-notify
    STATUS current
    DESCRIPTION
        "Parameter 'offset' in event NTP.28"
    ::= { ntpEventObjects28 3 }

ntp28-dispersion OBJECT-TYPE
    SYNTAX Integer32
    MAX-ACCESS accessible-for-notify
    STATUS current
    DESCRIPTION
        "Parameter 'dispersion' in event NTP.28"
    ::= { ntpEventObjects28 4 }

ntpEventObjects29 OBJECT-IDENTITY
    STATUS current
    DESCRIPTION
        "Event NTP.29
        NTP peer host clock data has been discarded by the clock-selection
        prodedure, and the cause is shown."
    ::= { ntpEventsGroup 29 }

ntp29-ntpsourceadd OBJECT-TYPE
    SYNTAX IpAddress
    MAX-ACCESS accessible-for-notify
    STATUS current
    DESCRIPTION
        "Parameter 'ntpsourceadd' in event NTP.29"
    ::= { ntpEventObjects29 1 }

ntp29-discardcause OBJECT-TYPE
    SYNTAX DisplayString
    MAX-ACCESS accessible-for-notify
    STATUS current
    DESCRIPTION
        "Parameter 'discardcause' in event NTP.29"
    ::= { ntpEventObjects29 2 }

ntpEventObjects30 OBJECT-IDENTITY
    STATUS current
    DESCRIPTION
        "Event NTP.30
        NTP peer host clock data has been selected by the clock-selection
        prodedure."
    ::= { ntpEventsGroup 30 }

ntp30-ntpsourceadd OBJECT-TYPE
    SYNTAX IpAddress
    MAX-ACCESS accessible-for-notify
    STATUS current
    DESCRIPTION
        "Parameter 'ntpsourceadd' in event NTP.30"
    ::= { ntpEventObjects30 1 }

ntpEventObjects32 OBJECT-IDENTITY
    STATUS current
    DESCRIPTION
        "Event NTP.32
        An NTP packet is received or transmitted from or to the given host. Some
        message data is shown. More information is available in other events."
    ::= { ntpEventsGroup 32 }

ntp32-rxtx OBJECT-TYPE
    SYNTAX DisplayString
    MAX-ACCESS accessible-for-notify
    STATUS current
    DESCRIPTION
        "Parameter 'rxtx' in event NTP.32"
    ::= { ntpEventObjects32 1 }

ntp32-peeraddr OBJECT-TYPE
    SYNTAX IpAddress
    MAX-ACCESS accessible-for-notify
    STATUS current
    DESCRIPTION
        "Parameter 'peeraddr' in event NTP.32"
    ::= { ntpEventObjects32 2 }

ntp32-lihigh OBJECT-TYPE
    SYNTAX Integer32
    MAX-ACCESS accessible-for-notify
    STATUS current
    DESCRIPTION
        "Parameter 'lihigh' in event NTP.32"
    ::= { ntpEventObjects32 3 }

ntp32-lilow OBJECT-TYPE
    SYNTAX Integer32
    MAX-ACCESS accessible-for-notify
    STATUS current
    DESCRIPTION
        "Parameter 'lilow' in event NTP.32"
    ::= { ntpEventObjects32 4 }

ntp32-litxt OBJECT-TYPE
    SYNTAX DisplayString
    MAX-ACCESS accessible-for-notify
    STATUS current
    DESCRIPTION
        "Parameter 'litxt' in event NTP.32"
    ::= { ntpEventObjects32 5 }

ntp32-versionnum OBJECT-TYPE
    SYNTAX Integer32
    MAX-ACCESS accessible-for-notify
    STATUS current
    DESCRIPTION
        "Parameter 'versionnum' in event NTP.32"
    ::= { ntpEventObjects32 6 }

ntp32-mode OBJECT-TYPE
    SYNTAX Integer32
    MAX-ACCESS accessible-for-notify
    STATUS current
    DESCRIPTION
        "Parameter 'mode' in event NTP.32"
    ::= { ntpEventObjects32 7 }

ntp32-modetxt OBJECT-TYPE
    SYNTAX DisplayString
    MAX-ACCESS accessible-for-notify
    STATUS current
    DESCRIPTION
        "Parameter 'modetxt' in event NTP.32"
    ::= { ntpEventObjects32 8 }

ntp32-stratum OBJECT-TYPE
    SYNTAX Integer32
    MAX-ACCESS accessible-for-notify
    STATUS current
    DESCRIPTION
        "Parameter 'stratum' in event NTP.32"
    ::= { ntpEventObjects32 9 }

ntp32-poll OBJECT-TYPE
    SYNTAX Integer32
    MAX-ACCESS accessible-for-notify
    STATUS current
    DESCRIPTION
        "Parameter 'poll' in event NTP.32"
    ::= { ntpEventObjects32 10 }

ntp32-polltxt OBJECT-TYPE
    SYNTAX DisplayString
    MAX-ACCESS accessible-for-notify
    STATUS current
    DESCRIPTION
        "Parameter 'polltxt' in event NTP.32"
    ::= { ntpEventObjects32 11 }

ntp32-prec OBJECT-TYPE
    SYNTAX Integer32
    MAX-ACCESS accessible-for-notify
    STATUS current
    DESCRIPTION
        "Parameter 'prec' in event NTP.32"
    ::= { ntpEventObjects32 12 }

ntp32-prectxt OBJECT-TYPE
    SYNTAX DisplayString
    MAX-ACCESS accessible-for-notify
    STATUS current
    DESCRIPTION
        "Parameter 'prectxt' in event NTP.32"
    ::= { ntpEventObjects32 13 }

ntpEventObjects33 OBJECT-IDENTITY
    STATUS current
    DESCRIPTION
        "Event NTP.33
        An NTP packet is received or transmitted from or to the given host. Some
        message data is shown. More information is available in other events."
    ::= { ntpEventsGroup 33 }

ntp33-rxtx OBJECT-TYPE
    SYNTAX DisplayString
    MAX-ACCESS accessible-for-notify
    STATUS current
    DESCRIPTION
        "Parameter 'rxtx' in event NTP.33"
    ::= { ntpEventObjects33 1 }

ntp33-peeraddr OBJECT-TYPE
    SYNTAX IpAddress
    MAX-ACCESS accessible-for-notify
    STATUS current
    DESCRIPTION
        "Parameter 'peeraddr' in event NTP.33"
    ::= { ntpEventObjects33 2 }

ntp33-rootdelay OBJECT-TYPE
    SYNTAX DisplayString
    MAX-ACCESS accessible-for-notify
    STATUS current
    DESCRIPTION
        "Parameter 'rootdelay' in event NTP.33"
    ::= { ntpEventObjects33 3 }

ntp33-rootdispersion OBJECT-TYPE
    SYNTAX DisplayString
    MAX-ACCESS accessible-for-notify
    STATUS current
    DESCRIPTION
        "Parameter 'rootdispersion' in event NTP.33"
    ::= { ntpEventObjects33 4 }

ntp33-referenceid OBJECT-TYPE
    SYNTAX Integer32
    MAX-ACCESS accessible-for-notify
    STATUS current
    DESCRIPTION
        "Parameter 'referenceid' in event NTP.33"
    ::= { ntpEventObjects33 5 }

ntpEventObjects34 OBJECT-IDENTITY
    STATUS current
    DESCRIPTION
        "Event NTP.34
        An NTP packet is received or transmitted from or to the given host. Some
        message data is shown. More information is available in other events."
    ::= { ntpEventsGroup 34 }

ntp34-rxtx OBJECT-TYPE
    SYNTAX DisplayString
    MAX-ACCESS accessible-for-notify
    STATUS current
    DESCRIPTION
        "Parameter 'rxtx' in event NTP.34"
    ::= { ntpEventObjects34 1 }

ntp34-peeraddr OBJECT-TYPE
    SYNTAX IpAddress
    MAX-ACCESS accessible-for-notify
    STATUS current
    DESCRIPTION
        "Parameter 'peeraddr' in event NTP.34"
    ::= { ntpEventObjects34 2 }

ntp34-referencets OBJECT-TYPE
    SYNTAX DisplayString
    MAX-ACCESS accessible-for-notify
    STATUS current
    DESCRIPTION
        "Parameter 'referencets' in event NTP.34"
    ::= { ntpEventObjects34 3 }

ntpEventObjects35 OBJECT-IDENTITY
    STATUS current
    DESCRIPTION
        "Event NTP.35
        An NTP packet is received or transmitted from or to the given host. Some
        message data is shown. More information is available in other events."
    ::= { ntpEventsGroup 35 }

ntp35-rxtx OBJECT-TYPE
    SYNTAX DisplayString
    MAX-ACCESS accessible-for-notify
    STATUS current
    DESCRIPTION
        "Parameter 'rxtx' in event NTP.35"
    ::= { ntpEventObjects35 1 }

ntp35-peeraddr OBJECT-TYPE
    SYNTAX IpAddress
    MAX-ACCESS accessible-for-notify
    STATUS current
    DESCRIPTION
        "Parameter 'peeraddr' in event NTP.35"
    ::= { ntpEventObjects35 2 }

ntp35-originatets OBJECT-TYPE
    SYNTAX DisplayString
    MAX-ACCESS accessible-for-notify
    STATUS current
    DESCRIPTION
        "Parameter 'originatets' in event NTP.35"
    ::= { ntpEventObjects35 3 }

ntpEventObjects36 OBJECT-IDENTITY
    STATUS current
    DESCRIPTION
        "Event NTP.36
        An NTP packet is received or transmitted from or to the given host. Some
        message data is shown. More information is available in other events."
    ::= { ntpEventsGroup 36 }

ntp36-rxtx OBJECT-TYPE
    SYNTAX DisplayString
    MAX-ACCESS accessible-for-notify
    STATUS current
    DESCRIPTION
        "Parameter 'rxtx' in event NTP.36"
    ::= { ntpEventObjects36 1 }

ntp36-peeraddr OBJECT-TYPE
    SYNTAX IpAddress
    MAX-ACCESS accessible-for-notify
    STATUS current
    DESCRIPTION
        "Parameter 'peeraddr' in event NTP.36"
    ::= { ntpEventObjects36 2 }

ntp36-receivets OBJECT-TYPE
    SYNTAX DisplayString
    MAX-ACCESS accessible-for-notify
    STATUS current
    DESCRIPTION
        "Parameter 'receivets' in event NTP.36"
    ::= { ntpEventObjects36 3 }

ntpEventObjects37 OBJECT-IDENTITY
    STATUS current
    DESCRIPTION
        "Event NTP.37
        An NTP packet is received or transmitted from or to the given host. Some
        message data is shown. More information is available in other events."
    ::= { ntpEventsGroup 37 }

ntp37-rxtx OBJECT-TYPE
    SYNTAX DisplayString
    MAX-ACCESS accessible-for-notify
    STATUS current
    DESCRIPTION
        "Parameter 'rxtx' in event NTP.37"
    ::= { ntpEventObjects37 1 }

ntp37-peeraddr OBJECT-TYPE
    SYNTAX IpAddress
    MAX-ACCESS accessible-for-notify
    STATUS current
    DESCRIPTION
        "Parameter 'peeraddr' in event NTP.37"
    ::= { ntpEventObjects37 2 }

ntp37-transmitts OBJECT-TYPE
    SYNTAX DisplayString
    MAX-ACCESS accessible-for-notify
    STATUS current
    DESCRIPTION
        "Parameter 'transmitts' in event NTP.37"
    ::= { ntpEventObjects37 3 }


ntpNotification1 NOTIFICATION-TYPE
    OBJECTS { 
              ntp1-ntpsourceadd, 
              ntp1-refTime,
              ntp1-orgTime,
              ntp1-recvTime,
              ntp1-txTime 
            }
    STATUS current
    DESCRIPTION
        "Notification of Event NTP.1

        Message: 'possible NTP packet received from host $1 ref time $2 org time $3 recv time $4 tx time $5'

        Parameters list:
              $1: ntp1-ntpsourceadd
              $2: ntp1-refTime
              $3: ntp1-orgTime
              $4: ntp1-recvTime
              $5: ntp1-txTime

        This message is generated when a packet is received from port 123."
    ::= { ntpNotificationsPrefix 1 }

ntpNotification2 NOTIFICATION-TYPE
    OBJECTS { 
              ntp2-ntpdestadd, 
              ntp2-refTime,
              ntp2-orgTime,
              ntp2-recvTime,
              ntp2-txTime 
            }
    STATUS current
    DESCRIPTION
        "Notification of Event NTP.2

        Message: 'Sent NTP packet to host $1 ref time $2 org time $3 recv time $4 tx time $5'

        Parameters list:
              $1: ntp2-ntpdestadd
              $2: ntp2-refTime
              $3: ntp2-orgTime
              $4: ntp2-recvTime
              $5: ntp2-txTime

        This message is generated when a packet is sent to a remote host."
    ::= { ntpNotificationsPrefix 2 }

ntpNotification3 NOTIFICATION-TYPE
    OBJECTS { 
              ntp3-ntpsourceadd, 
              ntp3-errorcode 
            }
    STATUS current
    DESCRIPTION
        "Notification of Event NTP.3

        Message: 'Wrong NTP packet received from host $1 (Error Code = $2)'

        Parameters list:
              $1: ntp3-ntpsourceadd
              $2: ntp3-errorcode

        This message is generated after checking the input packet. Error codes
        are shown below:
        TEST1		0x0001		Duplicate packet received.
        TEST2		0x0002		Bogus packet received.
        TEST3		0x0004		Protocol unsynchronized.
        TEST4		0x0008		Peer delay/dispersion bounds check.
        TEST5		0x0010		Peer authentication failed.
        TEST6       0x0020		Peer clock unsynchronized.
        TEST7		0x0040		Peer stratum out of bounds.
        TEST8		0x0080		Root delay/dispersion bounds check."
    ::= { ntpNotificationsPrefix 3 }

ntpNotification4 NOTIFICATION-TYPE
    OBJECTS { 
              ntp4-versnumber, 
              ntp4-ntpsourceadd 
            }
    STATUS current
    DESCRIPTION
        "Notification of Event NTP.4

        Message: 'Packet with version not supported $1 from host $2'

        Parameters list:
              $1: ntp4-versnumber
              $2: ntp4-ntpsourceadd

        This message indicates a wrong NTP version."
    ::= { ntpNotificationsPrefix 4 }

ntpNotification5 NOTIFICATION-TYPE
    OBJECTS { 
              ntp5-ntpsourceadd 
            }
    STATUS current
    DESCRIPTION
        "Notification of Event NTP.5

        Message: 'control packet received from host $1'

        Parameters list:
              $1: ntp5-ntpsourceadd

        This message indicates the received packet is a control packet."
    ::= { ntpNotificationsPrefix 5 }

ntpNotification6 NOTIFICATION-TYPE
    OBJECTS { 
              ntp6-ntpsourceadd 
            }
    STATUS current
    DESCRIPTION
        "Notification of Event NTP.6

        Message: 'Broadcast packet received from host $1'

        Parameters list:
              $1: ntp6-ntpsourceadd

        This message indicates the received packet is a Broadcast packet."
    ::= { ntpNotificationsPrefix 6 }

ntpNotification7 NOTIFICATION-TYPE
    STATUS current
    DESCRIPTION
        "Notification of Event NTP.7

        Message: 'There is no free buffers to store packet'

        This message is generated when NTP protocol handler hasn't enough memory
        to store the packet."
    ::= { ntpNotificationsPrefix 7 }

ntpNotification8 NOTIFICATION-TYPE
    OBJECTS { 
              ntp8-ntpsourceadd 
            }
    STATUS current
    DESCRIPTION
        "Notification of Event NTP.8

        Message: 'Private packet received from host $1'

        Parameters list:
              $1: ntp8-ntpsourceadd

        This message indicates the received packet is private packet."
    ::= { ntpNotificationsPrefix 8 }

ntpNotification9 NOTIFICATION-TYPE
    OBJECTS { 
              ntp9-ntpsourceadd 
            }
    STATUS current
    DESCRIPTION
        "Notification of Event NTP.9

        Message: 'Client packet received from host $1'

        Parameters list:
              $1: ntp9-ntpsourceadd

        This message indicates the received packet is client packet."
    ::= { ntpNotificationsPrefix 9 }

ntpNotification10 NOTIFICATION-TYPE
    OBJECTS { 
              ntp10-ntpsourceadd 
            }
    STATUS current
    DESCRIPTION
        "Notification of Event NTP.10

        Message: 'NULL: packet from host $1 discarded'

        Parameters list:
              $1: ntp10-ntpsourceadd

        This message is generated by NTP Fake-Out routine."
    ::= { ntpNotificationsPrefix 10 }

ntpNotification11 NOTIFICATION-TYPE
    OBJECTS { 
              ntp11-ntpsourceadd 
            }
    STATUS current
    DESCRIPTION
        "Notification of Event NTP.11

        Message: 'NTP packet discarded from host $1 Cause: Unknown peer'

        Parameters list:
              $1: ntp11-ntpsourceadd

        This message is generated when a packet arrived from an unknown peer."
    ::= { ntpNotificationsPrefix 11 }

ntpNotification12 NOTIFICATION-TYPE
    OBJECTS { 
              ntp12-ntpsourceadd 
            }
    STATUS current
    DESCRIPTION
        "Notification of Event NTP.12

        Message: 'NTP Active mode Packet received from host $1'

        Parameters list:
              $1: ntp12-ntpsourceadd

        This message indicates the received packet is active mode packet."
    ::= { ntpNotificationsPrefix 12 }

ntpNotification13 NOTIFICATION-TYPE
    OBJECTS { 
              ntp13-ntpsourceadd 
            }
    STATUS current
    DESCRIPTION
        "Notification of Event NTP.13

        Message: 'NTP Passive mode Packet received from host $1'

        Parameters list:
              $1: ntp13-ntpsourceadd

        This message indicates the received packet is passive mode packet."
    ::= { ntpNotificationsPrefix 13 }

ntpNotification14 NOTIFICATION-TYPE
    OBJECTS { 
              ntp14-ntpsourceadd 
            }
    STATUS current
    DESCRIPTION
        "Notification of Event NTP.14

        Message: 'NTP Server mode Packet received from host $1'

        Parameters list:
              $1: ntp14-ntpsourceadd

        This message indicates the received packet is server mode packet."
    ::= { ntpNotificationsPrefix 14 }

ntpNotification15 NOTIFICATION-TYPE
    OBJECTS { 
              ntp15-Delay, 
              ntp15-OffsetSign,
              ntp15-OffsetSeconds,
              ntp15-OffsetMillSeconds 
            }
    STATUS current
    DESCRIPTION
        "Notification of Event NTP.15

        Message: 'Clock Update   Delay  $1 ms - Offset $2$3.$4 seconds'

        Parameters list:
              $1: ntp15-Delay
              $2: ntp15-OffsetSign
              $3: ntp15-OffsetSeconds
              $4: ntp15-OffsetMillSeconds

        This message is shown when a clock update has been done."
    ::= { ntpNotificationsPrefix 15 }

ntpNotification16 NOTIFICATION-TYPE
    OBJECTS { 
              ntp16-datetostab, 
              ntp16-stabdate 
            }
    STATUS current
    DESCRIPTION
        "Notification of Event NTP.16

        Message: 'Date to Stablish $1 Stablished Date $2'

        Parameters list:
              $1: ntp16-datetostab
              $2: ntp16-stabdate

        This message is shown when a date has been established."
    ::= { ntpNotificationsPrefix 16 }

ntpNotification17 NOTIFICATION-TYPE
    OBJECTS { 
              ntp17-secTimer 
            }
    STATUS current
    DESCRIPTION
        "Notification of Event NTP.17

        Message: 'Time since updating timer was thrown $1 ms'

        Parameters list:
              $1: ntp17-secTimer

        This is a debugging message used to know the time since the timer
        was thrown."
    ::= { ntpNotificationsPrefix 17 }

ntpNotification18 NOTIFICATION-TYPE
    OBJECTS { 
              ntp18-millisec 
            }
    STATUS current
    DESCRIPTION
        "Notification of Event NTP.18

        Message: 'Device Clock Milliseconds Value $1'

        Parameters list:
              $1: ntp18-millisec

        This message is used to know the clock precision."
    ::= { ntpNotificationsPrefix 18 }

ntpNotification19 NOTIFICATION-TYPE
    OBJECTS { 
              ntp19-datetime, 
              ntp19-millisec 
            }
    STATUS current
    DESCRIPTION
        "Notification of Event NTP.19

        Message: 'Device Exact Date/Time $1 $2'

        Parameters list:
              $1: ntp19-datetime
              $2: ntp19-millisec

        Device exact date and time."
    ::= { ntpNotificationsPrefix 19 }

ntpNotification20 NOTIFICATION-TYPE
    OBJECTS { 
              ntp20-ntpsourceadd 
            }
    STATUS current
    DESCRIPTION
        "Notification of Event NTP.20

        Message: 'NTP client doesn't accept NTP Broadcasts from host $1'

        Parameters list:
              $1: ntp20-ntpsourceadd

        This message is generated when NTP client doesn't accept
        NTP broadcast messages from packet source host."
    ::= { ntpNotificationsPrefix 20 }

ntpNotification21 NOTIFICATION-TYPE
    OBJECTS { 
              ntp21-datetime, 
              ntp21-millisec,
              ntp21-timeticks 
            }
    STATUS current
    DESCRIPTION
        "Notification of Event NTP.21

        Message: 'NTP Transmission Date/Time  $1 $2 ms $3 ticks'

        Parameters list:
              $1: ntp21-datetime
              $2: ntp21-millisec
              $3: ntp21-timeticks

        NTP transmission date/time."
    ::= { ntpNotificationsPrefix 21 }

ntpNotification22 NOTIFICATION-TYPE
    OBJECTS { 
              ntp22-datetime, 
              ntp22-millisec,
              ntp22-timeticks 
            }
    STATUS current
    DESCRIPTION
        "Notification of Event NTP.22

        Message: 'NTP Reception Date/Time  $1 $2 ms $3 ticks'

        Parameters list:
              $1: ntp22-datetime
              $2: ntp22-millisec
              $3: ntp22-timeticks

        NTP reception date/time."
    ::= { ntpNotificationsPrefix 22 }

ntpNotification23 NOTIFICATION-TYPE
    STATUS current
    DESCRIPTION
        "Notification of Event NTP.23

        Message: 'Clt NTP Stopped- Skew Time too large'

        Clt NTP Stopped- Skew Time too large."
    ::= { ntpNotificationsPrefix 23 }

ntpNotification24 NOTIFICATION-TYPE
    OBJECTS { 
              ntp24-ntpsourceadd 
            }
    STATUS current
    DESCRIPTION
        "Notification of Event NTP.24

        Message: 'Discarded NTP packet from host $1 Stopped NTP Client'

        Parameters list:
              $1: ntp24-ntpsourceadd

        NTP packets are discarded because NTP client is stopped."
    ::= { ntpNotificationsPrefix 24 }

ntpNotification25 NOTIFICATION-TYPE
    STATUS current
    DESCRIPTION
        "Notification of Event NTP.25

        Message: 'NTP Client stopped : IP not enabled'

        NTP Client stopped while IP disabled."
    ::= { ntpNotificationsPrefix 25 }

ntpNotification26 NOTIFICATION-TYPE
    OBJECTS { 
              ntp26-ntpsourceadd 
            }
    STATUS current
    DESCRIPTION
        "Notification of Event NTP.26

        Message: 'NTP packet discarded from host $1 Cause: local packet'

        Parameters list:
              $1: ntp26-ntpsourceadd

        This message is generated when a local packet arrived. NTP only accepts
        packets from other hosts."
    ::= { ntpNotificationsPrefix 26 }

ntpNotification27 NOTIFICATION-TYPE
    OBJECTS { 
              ntp27-ntpsourceadd, 
              ntp27-testnumber,
              ntp27-testerrorcode,
              ntp27-testdescription 
            }
    STATUS current
    DESCRIPTION
        "Notification of Event NTP.27

        Message: 'Wrong NTP packet received from host $1, failed test $2 code $3: $4'

        Parameters list:
              $1: ntp27-ntpsourceadd
              $2: ntp27-testnumber
              $3: ntp27-testerrorcode
              $4: ntp27-testdescription

        A NTP packet has been received from the specified host, but it was wrong
        because it failed the specidifed test (number, error code and
        description)."
    ::= { ntpNotificationsPrefix 27 }

ntpNotification28 NOTIFICATION-TYPE
    OBJECTS { 
              ntp28-ntpsourceadd, 
              ntp28-delay,
              ntp28-offset,
              ntp28-dispersion 
            }
    STATUS current
    DESCRIPTION
        "Notification of Event NTP.28

        Message: 'NTP host $1 clock filter: new delay $2, offset $3, dispersion $4'

        Parameters list:
              $1: ntp28-ntpsourceadd
              $2: ntp28-delay
              $3: ntp28-offset
              $4: ntp28-dispersion

        NTP peer host clock data has been updated by the clock-filter prodedure,
        producing new values for delay, offset and dispersion, as shown in the
        trace."
    ::= { ntpNotificationsPrefix 28 }

ntpNotification29 NOTIFICATION-TYPE
    OBJECTS { 
              ntp29-ntpsourceadd, 
              ntp29-discardcause 
            }
    STATUS current
    DESCRIPTION
        "Notification of Event NTP.29

        Message: 'NTP host $1 clock selection discarded: $2'

        Parameters list:
              $1: ntp29-ntpsourceadd
              $2: ntp29-discardcause

        NTP peer host clock data has been discarded by the clock-selection
        prodedure, and the cause is shown."
    ::= { ntpNotificationsPrefix 29 }

ntpNotification30 NOTIFICATION-TYPE
    OBJECTS { 
              ntp30-ntpsourceadd 
            }
    STATUS current
    DESCRIPTION
        "Notification of Event NTP.30

        Message: 'NTP host $1 clock selected'

        Parameters list:
              $1: ntp30-ntpsourceadd

        NTP peer host clock data has been selected by the clock-selection
        prodedure."
    ::= { ntpNotificationsPrefix 30 }

ntpNotification31 NOTIFICATION-TYPE
    STATUS current
    DESCRIPTION
        "Notification of Event NTP.31

        Message: 'NTP no host selected'

        NTP clock-selection prodedure has found no suitable time server from any
        known host."
    ::= { ntpNotificationsPrefix 31 }

ntpNotification32 NOTIFICATION-TYPE
    OBJECTS { 
              ntp32-rxtx, 
              ntp32-peeraddr,
              ntp32-lihigh,
              ntp32-lilow,
              ntp32-litxt,
              ntp32-versionnum,
              ntp32-mode,
              ntp32-modetxt,
              ntp32-stratum,
              ntp32-poll,
              ntp32-polltxt,
              ntp32-prec,
              ntp32-prectxt 
            }
    STATUS current
    DESCRIPTION
        "Notification of Event NTP.32

        Message: '$1 host $2: LI $3$4 ($5) VN $6 Mode $7 ($8), Stratum $9, Poll Interval $10 ($11), Precision $12 ($13)'

        Parameters list:
              $1: ntp32-rxtx
              $2: ntp32-peeraddr
              $3: ntp32-lihigh
              $4: ntp32-lilow
              $5: ntp32-litxt
              $6: ntp32-versionnum
              $7: ntp32-mode
              $8: ntp32-modetxt
              $9: ntp32-stratum
              $10: ntp32-poll
              $11: ntp32-polltxt
              $12: ntp32-prec
              $13: ntp32-prectxt

        An NTP packet is received or transmitted from or to the given host. Some
        message data is shown. More information is available in other events."
    ::= { ntpNotificationsPrefix 32 }

ntpNotification33 NOTIFICATION-TYPE
    OBJECTS { 
              ntp33-rxtx, 
              ntp33-peeraddr,
              ntp33-rootdelay,
              ntp33-rootdispersion,
              ntp33-referenceid 
            }
    STATUS current
    DESCRIPTION
        "Notification of Event NTP.33

        Message: '$1 host $2: Root Delay $3, Root Dispersion $4, Reference Identifier $5'

        Parameters list:
              $1: ntp33-rxtx
              $2: ntp33-peeraddr
              $3: ntp33-rootdelay
              $4: ntp33-rootdispersion
              $5: ntp33-referenceid

        An NTP packet is received or transmitted from or to the given host. Some
        message data is shown. More information is available in other events."
    ::= { ntpNotificationsPrefix 33 }

ntpNotification34 NOTIFICATION-TYPE
    OBJECTS { 
              ntp34-rxtx, 
              ntp34-peeraddr,
              ntp34-referencets 
            }
    STATUS current
    DESCRIPTION
        "Notification of Event NTP.34

        Message: '$1 host $2: Reference Timestamp $3'

        Parameters list:
              $1: ntp34-rxtx
              $2: ntp34-peeraddr
              $3: ntp34-referencets

        An NTP packet is received or transmitted from or to the given host. Some
        message data is shown. More information is available in other events."
    ::= { ntpNotificationsPrefix 34 }

ntpNotification35 NOTIFICATION-TYPE
    OBJECTS { 
              ntp35-rxtx, 
              ntp35-peeraddr,
              ntp35-originatets 
            }
    STATUS current
    DESCRIPTION
        "Notification of Event NTP.35

        Message: '$1 host $2: Originate Timestamp $3'

        Parameters list:
              $1: ntp35-rxtx
              $2: ntp35-peeraddr
              $3: ntp35-originatets

        An NTP packet is received or transmitted from or to the given host. Some
        message data is shown. More information is available in other events."
    ::= { ntpNotificationsPrefix 35 }

ntpNotification36 NOTIFICATION-TYPE
    OBJECTS { 
              ntp36-rxtx, 
              ntp36-peeraddr,
              ntp36-receivets 
            }
    STATUS current
    DESCRIPTION
        "Notification of Event NTP.36

        Message: '$1 host $2: Receive Timestamp $3'

        Parameters list:
              $1: ntp36-rxtx
              $2: ntp36-peeraddr
              $3: ntp36-receivets

        An NTP packet is received or transmitted from or to the given host. Some
        message data is shown. More information is available in other events."
    ::= { ntpNotificationsPrefix 36 }

ntpNotification37 NOTIFICATION-TYPE
    OBJECTS { 
              ntp37-rxtx, 
              ntp37-peeraddr,
              ntp37-transmitts 
            }
    STATUS current
    DESCRIPTION
        "Notification of Event NTP.37

        Message: '$1 host $2: Transmit Timestamp $3'

        Parameters list:
              $1: ntp37-rxtx
              $2: ntp37-peeraddr
              $3: ntp37-transmitts

        An NTP packet is received or transmitted from or to the given host. Some
        message data is shown. More information is available in other events."
    ::= { ntpNotificationsPrefix 37 }


END
