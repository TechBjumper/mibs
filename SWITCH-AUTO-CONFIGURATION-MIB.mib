--MibName=rcAutoConfig
  -- *****************************************************************
-- switch-autoconfig-mib.mi2:  Raisecom Auto Configuration MIB file
-- Nov 2011,yangfan, change size list of the version of upgrade file
--
-- Jun 2009, tangyoucan, enhance autoconfig module
--
-- Oct 2007, zhangliwei     
--
-- Copyright (c) 1994-2007 by Raisecom Technology Co., Ltd. 
-- All rights reserved.
-- 
-- *****************************************************************

  
  
  SWITCH-AUTO-CONFIGURATION-MIB DEFINITIONS ::= BEGIN 
 
    IMPORTS
    MODULE-IDENTITY,
    NOTIFICATION-TYPE,
    IpAddress, Unsigned32,
    OBJECT-TYPE                         FROM SNMPv2-SMI
        
    MODULE-COMPLIANCE,
    NOTIFICATION-GROUP,
    OBJECT-GROUP                        FROM SNMPv2-CONF     
    EnableVar        			        FROM SWITCH-TC      
    iscomSwitch                         FROM RAISECOM-BASE-MIB;   
    
 	
 	rcAutoConfig MODULE-IDENTITY
        LAST-UPDATED    "200906110000Z"
        ORGANIZATION    "Raisecom, Inc."
        CONTACT-INFO
                		"Raise Systems
                        
               			 Postal: Beijing,China

                         Tel: 86-010-82884499

                		 E-mail: support@raisecom.com"
        DESCRIPTION
                        "The MIB module for Auto Config upgrade service."
                ::= { iscomSwitch 28}
    
------------------------------------------------------------------------------
--  define groups in AUTO-CONFIGURATION-MIB 
------------------------------------------------------------------------------
    rcAutoConfigTraps         OBJECT IDENTIFIER ::= { rcAutoConfig 9 }
    -- End of define groups
 
              
	rcAutoConfigTftpServerAddress OBJECT-TYPE							
	  	SYNTAX   IpAddress
    	MAX-ACCESS  read-write                      
    	STATUS      current
    	DESCRIPTION					
    	    "The object indicates the tftp server address requested
    	     of auto upgrade. The configuration of this object
    	     would not have effect on the tftp server address obtained
    	     from DHCP server."
    	DEFVAL  {""}                     
    	::= { rcAutoConfig 1 } 
    	
	rcAutoConfigFileName OBJECT-TYPE							
    	SYNTAX	OCTET STRING (SIZE(0..80))   
    	MAX-ACCESS  read-write                      
    	STATUS      current
    	DESCRIPTION					
    	    "The object indicates the configuration file name requested
    	     of auto upgrade. The configuration of this object would
    	     not have effect on the configuration file name obtained from 
    	     DHCP server."
    	DEFVAL  {""}                     
    	::= { rcAutoConfig 2 }   
    	                    
     rcAutoConfigStartupEnable OBJECT-TYPE							
    	SYNTAX	EnableVar
    	MAX-ACCESS  read-only                      
    	STATUS      current
    	DESCRIPTION					
    	    "The object indicates whether the auto configuration will
    	     start while startup."
    	                         
    	::= { rcAutoConfig 3 } 
    	
    rcAutoConfigOverwriteEnable OBJECT-TYPE							
    	SYNTAX	EnableVar
    	MAX-ACCESS  read-write                      
    	STATUS      current
    	DESCRIPTION					
    	    "The object indicates whether overwrite the local 
    	     configuration file using the server configuration file."
    	DEFVAL  {disable}                     
    	::= { rcAutoConfig 4 } 
    	
    rcAutoConfigTrapEnable OBJECT-TYPE							
    	SYNTAX	EnableVar
    	MAX-ACCESS  read-write                      
    	STATUS      current
    	DESCRIPTION					
    	    "The object indicates whether sending the trap
    	     information or not."
    	DEFVAL  {disable}                     
    	::= { rcAutoConfig 5 } 
    	
    rcAutoConfigCommand OBJECT-TYPE							
    	SYNTAX	INTEGER{                             
                 start(1),
                 stop(2)
                    }
    	MAX-ACCESS  read-write                      
    	STATUS      deprecated
    	DESCRIPTION					
    	    "The object indicates the request type of 
    	     auto upgrade."
    	DEFVAL  {start}                     
    	::= { rcAutoConfig 6 } 
    	
    rcAutoConfigOperationStates OBJECT-TYPE							
    	SYNTAX	INTEGER{  
                 waiting(1),
                 getting(2),
                 loading(3),
                 writing(4),
                 done(5)
    			}
    	MAX-ACCESS  read-only                      
    	STATUS      current
    	DESCRIPTION					
    	    "The object indicates the running states of 
    	    auto upgrade."
    	DEFVAL  {done}                     
    	::= { rcAutoConfig 7 } 
    	
    rcAutoConfigResult OBJECT-TYPE							
    	SYNTAX	INTEGER{                             
         none(1),
		 succeeded(2),
		 ipAddressUnavailable(3),
		 acquireFailed(4), 
		 getFailed(5), 
		 writeFailed(6),  
		 notEnoughMemory(7), 
		 other(8),  
		 stopped(9)  
    	}
    	MAX-ACCESS  read-only                      
    	STATUS      current
    	DESCRIPTION					
    	    "The object indicates the result states of 
    	     auto upgrade."
    	DEFVAL  {none}                     
    	::= { rcAutoConfig 8 }     
    	 
     rcAutoConfigFilenameRule OBJECT-TYPE							
    	SYNTAX	Unsigned32 (80000..89999)                            
        MAX-ACCESS  read-write                      
    	STATUS      current
    	DESCRIPTION					
    	    "The filename rule number "     
    	    
    	::= { rcAutoConfig 10 }  
 
    	 
------------------------------------------------------------------------------
--
--  Auto Configuration Trap
--
--  This trap used to inform the result states of auto configuration.
--
------------------------------------------------------------------------------
--  
     rcAutoConfigCompletionTrap NOTIFICATION-TYPE
        OBJECTS {rcAutoConfigCurrentFileType, rcAutoConfigResult }
        STATUS  current
        DESCRIPTION
             "Auto Configuration Completion."
        ::= { rcAutoConfigTraps 1 }
  
------------------------------------------------------------------------------
-- define version of upgrade file
------------------------------------------------------------------------------
rcAutoConfigSystemBootVersion OBJECT-TYPE
       SYNTAX  OCTET STRING (SIZE(7))
       MAX-ACCESS  read-write
       STATUS  current
       DESCRIPTION
       "version of systerm boot file, format is year-month-day-number.such as 0906031"                  
       ::= { rcAutoConfig 11 }


rcAutoConfigBootstrapVersion OBJECT-TYPE
       SYNTAX  OCTET STRING (SIZE(7))
       MAX-ACCESS  read-write
       STATUS  current
       DESCRIPTION
       "version of bootstrap file, format is year-month-day-number.such as 0906031"                  
       ::= { rcAutoConfig 12 }

rcAutoConfigStartupConfigVersion OBJECT-TYPE
       SYNTAX  OCTET STRING (SIZE(7))
       MAX-ACCESS  read-write
       STATUS  current
       DESCRIPTION
       "name of startup config file, format is year-month-day-number.such as 0906031"                  
       ::= { rcAutoConfig 13 }   

rcAutoConfigEnable OBJECT-TYPE							
    	SYNTAX	EnableVar
    	MAX-ACCESS  read-write                      
    	STATUS  current     
    	DESCRIPTION					
    	    "Auto upgrade disable or enable."
    	DEFVAL  {enable}                     
    	::= { rcAutoConfig 14 } 

rcAutoConfigCurrentFileType OBJECT-TYPE							
    	SYNTAX	INTEGER{                             
         none(1),
         startup-config(2),
         system-boot(3),
         bootstrap(4)
    	}
    	MAX-ACCESS  read-only                      
    	STATUS      current
    	DESCRIPTION					
    	    "The object indicates the current operate file."
    	DEFVAL  {none}                     
    	::= { rcAutoConfig 15 } 
--
-- end-rcAutoConfig
--	
END
