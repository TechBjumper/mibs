-- ============================================================================
-- Copyright (C) 2009 by H3C Technologies. All rights reserved.
--
-- Description: Huawei-3COM Product OID MIB
-- Reference: HUAWEI-3COM-OID-MIB
-- Version: V1.19
-- History:
--   V1.00 2006-02-23 Initial Version, created by haobin.
--     The product sysObjectID are all included in this mib.
--     Add OID from 175 to 181 under h3cProductId by gaolong
--   V1.01 2006-05-09
--     Add OID from 182 to 188 under h3cProductId by gaolong
--   V1.02 2006-05-31
--     Add OID from 189 to 191 under h3cProductId by gaolong
--   V1.03 2006-06-08
--     Add OID from 192 to 196 under h3cProductId by gaolong
--   V1.04 2006-08-23
--     Add OID 197 under h3cProductId by gaolong
--   V1.05 2006-11-29
--     Add OID from 198 to 204 under h3cProductId by gaolong
--   V1.06 2006-12-25
--     Add OID from 205 to 209 under h3cProductId by gaolong
--   V1.07 2007-02-01
--     Add OID from 210 to 214 under h3cProductId by gaolong
--   V1.08 2007-03-28
--     Add OID 215 under h3cProductId by gaolong
--   V1.09 2007-04-24
--     Add OID from 216 to 219 under h3cProductId by gaolong
--   V1.10 2007-05-28
--     Add OID 220 under h3cProductId by gaolong
--   V1.11 2007-07-02
--     Add OID from 221 to 223 under h3cProductId by gaolong
--   V1.12 2007-10-27
--     Add OID from 224 to 226 under h3cProductId by longyin
--   V1.13 2007-11-26
--     Add OID from 227 to 234 under h3cProductId by longyin
--   V1.14 2008-02-27
--     Add OID from 235 to 236 under h3cProductId by longyin
--   V1.15 2008-04-30
--     Add OID 237 under h3cProductId by songhao
--   V1.16 2008-05-31
--     Add OID from 238 to 240 under h3cProductId by songhao
--   V1.17 2008-07-25
--     Add OID from 241 to 242 under h3cProductId by songhao
--   V1.18 2008-10-10
--     Add OID 243 under h3cProductId by songhao
--   V1.19 2009-02-27
--     Add OID 244 under h3cProductId by songhao
-- ============================================================================
HUAWEI-PRODUCT-ID-MIB DEFINITIONS ::= BEGIN
    IMPORTS
        products,quidway,h3cProductId,lanSw,mlsr
            FROM HUAWEI-3COM-OID-MIB;

-- under h3cProductId
        s2008-EI     OBJECT IDENTIFIER ::= { h3cProductId 1 }   -- 2003/12/29, xiejianping added
                                                                -- 2004/07/05, xjp modify name s2008Z to s2008-EI
        s2016-EI     OBJECT IDENTIFIER ::= { h3cProductId 2 }   -- 2003/12/29, xiejianping added
                                                                -- 2004/07/05, xjp modify name s2016C to s2016-EI
        s2403H-EI    OBJECT IDENTIFIER ::= { h3cProductId 3 }   -- 2003/12/29, xiejianping added
                                                                -- 2004/07/05, xjp modify name s2403I to s2403H-EI
        s3026PWR     OBJECT IDENTIFIER ::= { h3cProductId 4 }   -- 2003/12/29, xiejianping added
        secpath1000  OBJECT IDENTIFIER ::= { h3cProductId 5 }   -- 2003/12/31, xiejianping added
        ar18-35      OBJECT IDENTIFIER ::= { h3cProductId 6 }   -- 2004/02/17, xiejianping added
        s3552F-HI    OBJECT IDENTIFIER ::= { h3cProductId 7 }   -- 2004/07/1, xiejianping changend
        secpath10    OBJECT IDENTIFIER ::= { h3cProductId 8 }   -- 2003/12/31, xiejianping added
        s3924-SI     OBJECT IDENTIFIER ::= { h3cProductId 9 }   -- 2004/06/1, xiejianping added
        s3928P-SI    OBJECT IDENTIFIER ::= { h3cProductId 10 }  -- 2004/06/1, xiejianping added
        s3952P-SI    OBJECT IDENTIFIER ::= { h3cProductId 11 }  -- 2004/06/1, xiejianping added
        s3928TP-SI   OBJECT IDENTIFIER ::= { h3cProductId 12 }  -- 2004/06/1, xiejianping added
        s3928P-EI    OBJECT IDENTIFIER ::= { h3cProductId 13 }  -- 2004/06/1, xiejianping added
        s3952P-EI    OBJECT IDENTIFIER ::= { h3cProductId 14 }  -- 2004/06/1, xiejianping added
        s3928P-PWR-EI   OBJECT IDENTIFIER ::= { h3cProductId 15 }       -- 2004/06/1, xiejianping added
        s3952P-PWR-EI   OBJECT IDENTIFIER ::= { h3cProductId 16 }       -- 2004/06/1, xiejianping added
        s3928F-EI       OBJECT IDENTIFIER ::= { h3cProductId 17 }       -- 2004/06/1, xiejianping added
        s5600M          OBJECT IDENTIFIER ::= { h3cProductId 18 }       -- 2004/06/1, xiejianping added
        ar18-50         OBJECT IDENTIFIER ::= { h3cProductId 19 }       -- 2004/06/2, xiejianping added
        ar18-33E        OBJECT IDENTIFIER ::= { h3cProductId 20 }       -- 2004/08/25, chenjianhui modify node name
        ar18-34E        OBJECT IDENTIFIER ::= { h3cProductId 21 }       -- 2004/08/25, chenjianhui modify node name
        s8508           OBJECT IDENTIFIER ::= { h3cProductId 22 }       -- 2004/06/25, xiejianping added
        secpath100N      OBJECT IDENTIFIER ::= { h3cProductId 23 }      -- 2004/06/29, xiejianping added
        secpath100V      OBJECT IDENTIFIER ::= { h3cProductId 24 }      -- 2004/06/29, xiejianping added
        secpath100F      OBJECT IDENTIFIER ::= { h3cProductId 25 }      -- 2004/06/29, xiejianping added
        secpath1000F     OBJECT IDENTIFIER ::= { h3cProductId 26 }      -- 2004/12/21, xiejianping added
        secpath500F  OBJECT IDENTIFIER ::= { h3cProductId 27 }  -- 2005/5/25, gaolong added
        secpath10F   OBJECT IDENTIFIER ::= { h3cProductId 28 }  -- 2005/6/12, gaolong added
        secpath100FS  OBJECT IDENTIFIER ::= { h3cProductId 29 } -- 2005/10/29, longyin added
        secpath100FE  OBJECT IDENTIFIER ::= { h3cProductId 30 } -- 2005/10/29, longyin added
        secpath100FW  OBJECT IDENTIFIER ::= { h3cProductId 31 } -- 2006/03/05, longyin added
        secpath1800FS  OBJECT IDENTIFIER ::= { h3cProductId 32 } -- 2006/03/05, longyin added
        secpath1800FE  OBJECT IDENTIFIER ::= { h3cProductId 33 } -- 2006/03/05, longyin added
        --  34-39 reserve for secpath
        --
        sr8805   OBJECT IDENTIFIER ::= { h3cProductId 40 }      -- 2004/07/1, xiejianping added
        sr8808   OBJECT IDENTIFIER ::= { h3cProductId 41 }      -- 2004/07/1, xiejianping added
        sr8812   OBJECT IDENTIFIER ::= { h3cProductId 42 }      -- 2004/07/1, xiejianping added
        s5624P      OBJECT IDENTIFIER ::= { h3cProductId 43 }   -- 2004/07/2, xiejianping added
        s5624P-PWR  OBJECT IDENTIFIER ::= { h3cProductId 44 }   -- 2004/07/2, xiejianping added
        s5648P      OBJECT IDENTIFIER ::= { h3cProductId 45 }   -- 2004/07/2, xiejianping added
        s5648P-PWR  OBJECT IDENTIFIER ::= { h3cProductId 46 }   -- 2004/07/2, xiejianping added
        s2008C  OBJECT IDENTIFIER ::= { h3cProductId 47 }       -- 2004/07/7, xiejianping added
        s2016C  OBJECT IDENTIFIER ::= { h3cProductId 48 }       -- 2004/07/7, xiejianping added
        s2024C  OBJECT IDENTIFIER ::= { h3cProductId 49 }       -- 2004/07/7, xiejianping added
        ar18-13V  OBJECT IDENTIFIER ::= { h3cProductId 50 }     -- 2004/07/7, xiejianping added
        ar18-18V  OBJECT IDENTIFIER ::= { h3cProductId 51 }     -- 2004/07/7, xiejianping added
        isPath1000 OBJECT IDENTIFIER ::= { h3cProductId 52 }    -- 2004/07/13, xiejianping added
        ar18-20S  OBJECT IDENTIFIER ::= { h3cProductId 53 }     -- 2004/07/19, xiejianping added

        -- for Wellhope OEM
        wellhope  OBJECT IDENTIFIER ::= { h3cProductId 54 }     -- 2004/08/16, xiejianping added
        tph12616  OBJECT IDENTIFIER ::= { wellhope 1 }          -- NE80
        tph10408  OBJECT IDENTIFIER ::= { wellhope 2 }          -- NE40-8
        tph10404  OBJECT IDENTIFIER ::= { wellhope 3 }          -- NE40-4
        tph10402  OBJECT IDENTIFIER ::= { wellhope 4 }          -- NE40-2
        trt7554  OBJECT IDENTIFIER ::= { wellhope 5 }           -- NE05
        tab3740  OBJECT IDENTIFIER ::= { wellhope 6 }           -- AR46-40
        tab3680  OBJECT IDENTIFIER ::= { wellhope 7 }           -- AR28-80
        tab2609  OBJECT IDENTIFIER ::= { wellhope 8 }           -- AR28-09
        tab2611  OBJECT IDENTIFIER ::= { wellhope 9 }           -- AR28-11
        tab2631  OBJECT IDENTIFIER ::= { wellhope 10 }          -- AR28-31
        ts6061r  OBJECT IDENTIFIER ::= { wellhope 11 }          -- S6506R
        ts3262  OBJECT IDENTIFIER ::= { wellhope 12 }           -- S3526C
        ts2502  OBJECT IDENTIFIER ::= { wellhope 13 }           -- S3050C
        ts2262  OBJECT IDENTIFIER ::= { wellhope 14 }           -- S3026C

        xe200  OBJECT IDENTIFIER ::= { h3cProductId 55 }        -- 2004/08/31, xiejianping added
        xe2000 OBJECT IDENTIFIER ::= { h3cProductId 56 }        -- 2004/08/31, xiejianping added
        e026T   OBJECT IDENTIFIER ::= { h3cProductId 57 }       -- 2004/10/15, xiejianping added
        e008-FE OBJECT IDENTIFIER ::= { h3cProductId 58 }       -- 2004/10/15, xiejianping added
        e017-FE OBJECT IDENTIFIER ::= { h3cProductId 59 }       -- 2004/10/15, xiejianping added
        e026-FE OBJECT IDENTIFIER ::= { h3cProductId 60 }       -- 2004/10/15, xiejianping added
        ar28-12 OBJECT IDENTIFIER ::= { h3cProductId 61 }       -- 2004/10/29, xiejianping added
        ar28-13 OBJECT IDENTIFIER ::= { h3cProductId 62 }       -- 2004/10/29, xiejianping added
        ar28-14 OBJECT IDENTIFIER ::= { h3cProductId 63 }       -- 2004/10/29, xiejianping added
        ar18-10 OBJECT IDENTIFIER ::= { h3cProductId 64 }       -- 2004/11/18, xiejianping added
        ar18-21 OBJECT IDENTIFIER ::= { h3cProductId 65 }       -- 2004/11/18, xiejianping added
        ar18-21A OBJECT IDENTIFIER ::= { h3cProductId 66 }      -- 2004/11/18, xiejianping added
        ar18-21B OBJECT IDENTIFIER ::= { h3cProductId 67 }      -- 2004/11/18, xiejianping added
        ar18-21C OBJECT IDENTIFIER ::= { h3cProductId 68 }      -- 2004/11/18, xiejianping added
        ar18-22 OBJECT IDENTIFIER ::= { h3cProductId 69 }       -- 2004/11/18, xiejianping added
        ar18-22-8 OBJECT IDENTIFIER ::= { h3cProductId 70 }     -- 2004/11/18, xiejianping added
        ar18-22-24 OBJECT IDENTIFIER ::= { h3cProductId 71 }    -- 2004/11/18, xiejianping added
        ar18-23-1 OBJECT IDENTIFIER ::= { h3cProductId 72 }     -- 2004/11/18, xiejianping added
        ar18-30E OBJECT IDENTIFIER ::= { h3cProductId 73 }      -- 2004/11/18, xiejianping added
        ar18-31E OBJECT IDENTIFIER ::= { h3cProductId 74 }      -- 2004/11/18, xiejianping added
        ar18-32E OBJECT IDENTIFIER ::= { h3cProductId 75 }      -- 2004/11/18, xiejianping added
        ar18-35E OBJECT IDENTIFIER ::= { h3cProductId 76 }      -- 2004/11/18, xiejianping added
        ar18-36E OBJECT IDENTIFIER ::= { h3cProductId 77 }      -- 2004/11/18, xiejianping added
        ar18-37E OBJECT IDENTIFIER ::= { h3cProductId 78 }      -- 2004/11/18, xiejianping added
        ar18-52 OBJECT IDENTIFIER ::= { h3cProductId 79 }       -- 2004/11/18, xiejianping added
        s6502 OBJECT IDENTIFIER ::= { h3cProductId 80 }         -- 2004/11/23, xiejianping added
        s5124P-EI OBJECT IDENTIFIER ::= { h3cProductId 81 }     -- 2004/12/2, xiejianping added
        s5126C-EI OBJECT IDENTIFIER ::= { h3cProductId 82 }     -- 2004/12/2, xiejianping added
        s5148P-EI OBJECT IDENTIFIER ::= { h3cProductId 83 }     -- 2004/12/2, xiejianping added
        s5150C-EI OBJECT IDENTIFIER ::= { h3cProductId 84 }     -- 2004/12/2, xiejianping added
        s5116P-SI OBJECT IDENTIFIER ::= { h3cProductId 85 }     -- 2004/12/2, xiejianping added
        s5124P-SI OBJECT IDENTIFIER ::= { h3cProductId 86 }     -- 2004/12/2, xiejianping added
        s5148P-SI OBJECT IDENTIFIER ::= { h3cProductId 87 }     -- 2004/12/2, xiejianping added
        ar4620E OBJECT IDENTIFIER ::= { h3cProductId 88 }       -- 2004/12/6, xiejianping added
        ar4640E OBJECT IDENTIFIER ::= { h3cProductId 89 }       -- 2004/12/6, xiejianping added
        ar4680E OBJECT IDENTIFIER ::= { h3cProductId 90 }       -- 2004/12/6, xiejianping added
        ar18-22s-8 OBJECT IDENTIFIER ::= { h3cProductId 91 }    -- 2004/12/24, xiejianping added
        ar18-23s-1 OBJECT IDENTIFIER ::= { h3cProductId 92 }    -- 2004/12/24, xiejianping added
        secEngineP500 OBJECT IDENTIFIER ::= { h3cProductId 93 } -- 2004/12/29, xiejianping added
        s2108-SI OBJECT IDENTIFIER ::= { h3cProductId 94 }      -- 2005/1/6, xiejianping added
        s2116-SI OBJECT IDENTIFIER ::= { h3cProductId 95 }      -- 2005/1/6, xiejianping added
        s2126-SI OBJECT IDENTIFIER ::= { h3cProductId 96 }      -- 2005/1/6, xiejianping added
        s2108-EI OBJECT IDENTIFIER ::= { h3cProductId 97 }      -- 2005/1/6, xiejianping added
        s2116-EI OBJECT IDENTIFIER ::= { h3cProductId 98 }      -- 2005/1/6, xiejianping added
        s2126-EI OBJECT IDENTIFIER ::= { h3cProductId 99 }      -- 2005/1/6, xiejianping added
        s5624F OBJECT IDENTIFIER ::= { h3cProductId 100 }       -- 2005/1/6, xiejianping added
        s3224P OBJECT IDENTIFIER ::= { h3cProductId 101 }       -- 2005/1/17, xiejianping added
        s3226T OBJECT IDENTIFIER ::= { h3cProductId 102 }       -- 2005/1/17, xiejianping added
        s3226P OBJECT IDENTIFIER ::= { h3cProductId 103 }       -- 2005/1/17, xiejianping added
        s3250T OBJECT IDENTIFIER ::= { h3cProductId 104 }       -- 2005/1/17, xiejianping added
        s3250P OBJECT IDENTIFIER ::= { h3cProductId 105 }       -- 2005/1/17, xiejianping added
        s3108T OBJECT IDENTIFIER ::= { h3cProductId 106 }       -- 2005/2/5, gaolong added
        s3116T OBJECT IDENTIFIER ::= { h3cProductId 107 }       -- 2005/2/5, gaolong added
        s3126T OBJECT IDENTIFIER ::= { h3cProductId 108 }       -- 2005/2/5, gaolong added
        s3108C OBJECT IDENTIFIER ::= { h3cProductId 109 }       -- 2005/2/5, gaolong added
        s3116C OBJECT IDENTIFIER ::= { h3cProductId 110 }       -- 2005/2/5, gaolong added
        s3126C OBJECT IDENTIFIER ::= { h3cProductId 111 }       -- 2005/2/5, gaolong added
        ar28-12B OBJECT IDENTIFIER ::= { h3cProductId 112 }     -- 2005/3/25, xiejianping added
        secBladeIDS OBJECT IDENTIFIER ::= { h3cProductId 113 }  -- 2005/3/25, gaolong added
        secBladeIPS OBJECT IDENTIFIER ::= { h3cProductId 114 }  -- 2005/3/25, gaolong added
        secEngineD500 OBJECT IDENTIFIER ::= { h3cProductId 115 }-- 2005/4/1, xiejianping added
        s3928TP-V6 OBJECT IDENTIFIER ::= { h3cProductId 116 }   -- 2005/4/14, xiejianping added
        s3928P-V6 OBJECT IDENTIFIER ::= { h3cProductId 117 }    -- 2005/4/14, xiejianping added
        s3952P-V6 OBJECT IDENTIFIER ::= { h3cProductId 118 }    -- 2005/4/14, xiejianping added
        s3928F-V6 OBJECT IDENTIFIER ::= { h3cProductId 119 }    -- 2005/4/14, xiejianping added
        s5524P OBJECT IDENTIFIER ::= { h3cProductId 120 }       -- 2005/4/14, xiejianping added
        s5524F OBJECT IDENTIFIER ::= { h3cProductId 121 }       -- 2005/4/14, xiejianping added
        xE7000 OBJECT IDENTIFIER ::= { h3cProductId 122 }       -- 2005/4/15, gaolong added
        vg10-40 OBJECT IDENTIFIER ::= { h3cProductId 123 }      -- 2005/4/15, gaolong added
        vg10-41 OBJECT IDENTIFIER ::= { h3cProductId 124 }      -- 2005/4/15, gaolong added
        vg20-16 OBJECT IDENTIFIER ::= { h3cProductId 125 }      -- 2005/4/15, gaolong added
        vg20-32 OBJECT IDENTIFIER ::= { h3cProductId 126 }      -- 2005/4/15, gaolong added
        vg20-08L OBJECT IDENTIFIER ::= { h3cProductId 127 }     -- 2005/4/15, gaolong added
        vg80-20 OBJECT IDENTIFIER ::= { h3cProductId 128 }      -- 2005/4/15, gaolong added
        vg80-20T OBJECT IDENTIFIER ::= { h3cProductId 129 }     -- 2005/4/15, gaolong added
        s2008CT OBJECT IDENTIFIER ::= { h3cProductId 130 }      -- 2005/5/13, xiejianping added
        s2008CP OBJECT IDENTIFIER ::= { h3cProductId 131 }      -- 2005/5/13, xiejianping added
        secBladeFW OBJECT IDENTIFIER ::= { h3cProductId 132 }   -- 2005/5/20, xiejianping added
        secBladeVPN OBJECT IDENTIFIER ::= { h3cProductId 133 }  -- 2005/5/20, xiejianping added
        secEngineD200 OBJECT IDENTIFIER ::= { h3cProductId 134 }-- 2005/6/20, gaolong added
-- subidentifier {h3cProductId 135} is reserved for OEM.
        sJW59 OBJECT IDENTIFIER ::= { h3cProductId 136 }        -- 2005/8/2, gaolong added
        vg21-08 OBJECT IDENTIFIER ::= { h3cProductId 137 }      -- 2005/8/2, gaolong added
        ar19-61 OBJECT IDENTIFIER ::= { h3cProductId 138 }      -- 2005/8/2, gaolong added
        ar19-62 OBJECT IDENTIFIER ::= { h3cProductId 139 }      -- 2005/8/2, gaolong added
        ar29-01 OBJECT IDENTIFIER ::= { h3cProductId 140}       -- 2005/8/2, gaolong added
        ar29-21 OBJECT IDENTIFIER ::= { h3cProductId 141 }      -- 2005/8/2, gaolong added
        ar29-41 OBJECT IDENTIFIER ::= { h3cProductId 142 }      -- 2005/8/2, gaolong added
        ar29-61 OBJECT IDENTIFIER ::= { h3cProductId 143 }      -- 2005/8/2, gaolong added
        ar49-45 OBJECT IDENTIFIER ::= { h3cProductId 144 }      -- 2005/8/2, gaolong added
        ar49-65 OBJECT IDENTIFIER ::= { h3cProductId 145 }      -- 2005/8/2, gaolong added
        s5112P-EI OBJECT IDENTIFIER ::= { h3cProductId 146 }    -- 2005/8/2, gaolong added
        s5112C-EI OBJECT IDENTIFIER ::= { h3cProductId 147 }    -- 2005/8/2, gaolong added
        s5228C OBJECT IDENTIFIER ::= { h3cProductId 148 }       -- 2005/9/20, gaolong added
        s5252C OBJECT IDENTIFIER ::= { h3cProductId 149 }       -- 2005/9/20, gaolong added
        s5228C-PWR OBJECT IDENTIFIER ::= { h3cProductId 150 }   -- 2005/9/20, gaolong added
        s5252C-PWR OBJECT IDENTIFIER ::= { h3cProductId 151 }   -- 2005/9/20, gaolong added
        s2008-HI OBJECT IDENTIFIER ::= { h3cProductId 152 }     -- 2005/10/29, longyin added
        s2016-HI OBJECT IDENTIFIER ::= { h3cProductId 153 }     -- 2005/10/29, longyin added
        s2403H-HI OBJECT IDENTIFIER ::= { h3cProductId 154 }    -- 2005/10/29, longyin added
        vg31-08 OBJECT IDENTIFIER ::= { h3cProductId 155 }      -- 2005/11/24, longyin added
        s8508V OBJECT IDENTIFIER ::= { h3cProductId 156 }       -- 2005/11/24, longyin added
        e126 OBJECT IDENTIFIER ::= { h3cProductId 157 }         -- 2005/11/24, longyin added
        s3126TP OBJECT IDENTIFIER ::= { h3cProductId 158 }      -- 2005/11/24, longyin added
        e328 OBJECT IDENTIFIER ::= { h3cProductId 159 }         -- 2005/11/24, longyin added
        e352 OBJECT IDENTIFIER ::= { h3cProductId 160 }         -- 2005/11/24, longyin added
        s3928P-PWR-SI OBJECT IDENTIFIER ::= { h3cProductId 161 }   -- 2005/11/24, longyin added
-- subidentifier {h3cProductId 162} is reserved for OEM.
        s8502 OBJECT IDENTIFIER ::= { h3cProductId 163 }        -- 2005/11/28, longyin added
-- for Intransa OEM
        intransa  OBJECT IDENTIFIER ::= { h3cProductId 135 }    -- 2005/06/25, gaolong added
        ix5000  OBJECT IDENTIFIER ::= { intransa 1 }            -- 2005/06/25, gaolong added
-- for Falcon OEM
        falcon  OBJECT IDENTIFIER ::= { h3cProductId 162 }      -- 2005/11/26, longyin added
        ix1000  OBJECT IDENTIFIER ::= { falcon 1 }              -- 2005/11/26, longyin added

        sr8802 OBJECT IDENTIFIER ::= { h3cProductId 164 }       -- 2006/01/09, longyin added
        s3328P-SI OBJECT IDENTIFIER ::= { h3cProductId 165 }    -- 2006/01/09, longyin added
        s3352P-SI OBJECT IDENTIFIER ::= { h3cProductId 166 }    -- 2006/01/09, longyin added
        s3328TP-SI OBJECT IDENTIFIER ::= { h3cProductId 167 }   -- 2006/01/09, longyin added
        s3328P-PWR-SI OBJECT IDENTIFIER ::= { h3cProductId 168 }-- 2006/01/09, longyin added
        s3328P-EI OBJECT IDENTIFIER ::= { h3cProductId 169 }    -- 2006/01/09, longyin added
        s3352P-EI OBJECT IDENTIFIER ::= { h3cProductId 170 }    -- 2006/01/09, longyin added
        s3328P-PWR-EI OBJECT IDENTIFIER ::= { h3cProductId 171 }-- 2006/01/09, longyin added
        s3352P-PWR-EI OBJECT IDENTIFIER ::= { h3cProductId 172 }-- 2006/01/09, longyin added
        s3328F-EI OBJECT IDENTIFIER ::= { h3cProductId 173 }    -- 2006/01/09, longyin added
        s6502ME OBJECT IDENTIFIER ::= { h3cProductId 174 }      -- 2006/01/21, longyin added

        s5528C-EI OBJECT IDENTIFIER ::= { h3cProductId 175 }      -- 2006/04/13, gaolong added
        s5552C-EI OBJECT IDENTIFIER ::= { h3cProductId 176 }      -- 2006/04/13, gaolong added
        s5528C-PWR-EI OBJECT IDENTIFIER ::= { h3cProductId 177 }      -- 2006/04/13, gaolong added
        s5552C-PWR-EI OBJECT IDENTIFIER ::= { h3cProductId 178 }      -- 2006/04/13, gaolong added
        s5528F-EI OBJECT IDENTIFIER ::= { h3cProductId 179 }      -- 2006/04/13, gaolong added
        s5528C-EI-DC OBJECT IDENTIFIER ::= { h3cProductId 180 }      -- 2006/04/13, gaolong added

        e126-SI OBJECT IDENTIFIER ::= { h3cProductId 181 }      -- 2006/04/13, gaolong added

        dr814                       OBJECT IDENTIFIER ::= { h3cProductId 182 }
        dr814q                      OBJECT IDENTIFIER ::= { h3cProductId 183 }
        wdr854g                     OBJECT IDENTIFIER ::= { h3cProductId 184 }
        vdr824g                     OBJECT IDENTIFIER ::= { h3cProductId 185 }
        vdr824                      OBJECT IDENTIFIER ::= { h3cProductId 186 }
        vdr744                      OBJECT IDENTIFIER ::= { h3cProductId 187 }
        dr744                       OBJECT IDENTIFIER ::= { h3cProductId 188 }
        s6502M                      OBJECT IDENTIFIER ::= { h3cProductId 189 }
        s6501M-GT                   OBJECT IDENTIFIER ::= { h3cProductId 190 }
        s6501M-GP                   OBJECT IDENTIFIER ::= { h3cProductId 191 }
        s8505-V5                    OBJECT IDENTIFIER ::= { h3cProductId 192 }
        s8512-V5                    OBJECT IDENTIFIER ::= { h3cProductId 193 }
        s8508-V5                    OBJECT IDENTIFIER ::= { h3cProductId 194 }
        s8508V-V5                   OBJECT IDENTIFIER ::= { h3cProductId 195 }
        s8502-V5                    OBJECT IDENTIFIER ::= { h3cProductId 196 }
        s6502-V5                    OBJECT IDENTIFIER ::= { h3cProductId 197 }

        s2008TP-EA                  OBJECT IDENTIFIER ::= { h3cProductId 198 }
        s2016TP-EA                  OBJECT IDENTIFIER ::= { h3cProductId 199 }
        s2403TP-EA                  OBJECT IDENTIFIER ::= { h3cProductId 200 }
        s2403TP-PWR-EA              OBJECT IDENTIFIER ::= { h3cProductId 201 }
        s2008TP-MI                  OBJECT IDENTIFIER ::= { h3cProductId 202 }
        s2016TP-MI                  OBJECT IDENTIFIER ::= { h3cProductId 203 }
        s2403TP-MI                  OBJECT IDENTIFIER ::= { h3cProductId 204 }

        s7802                       OBJECT IDENTIFIER ::= { h3cProductId 205 }
        s7803                       OBJECT IDENTIFIER ::= { h3cProductId 206 }
        s7806                       OBJECT IDENTIFIER ::= { h3cProductId 207 }
        s7806-V                     OBJECT IDENTIFIER ::= { h3cProductId 208 }
        s7810                       OBJECT IDENTIFIER ::= { h3cProductId 209 }

        s2016TP-PWR-EA              OBJECT IDENTIFIER ::= { h3cProductId 210 }
        s3552P-EA                   OBJECT IDENTIFIER ::= { h3cProductId 211 }
        s3528P-EA                   OBJECT IDENTIFIER ::= { h3cProductId 212 }
        s3528TP-EA                  OBJECT IDENTIFIER ::= { h3cProductId 213 }
        s3528F-EA                   OBJECT IDENTIFIER ::= { h3cProductId 214 }
        s3552f-ea                   OBJECT IDENTIFIER ::= { h3cProductId 215 }

        s6902                       OBJECT IDENTIFIER ::= { h3cProductId 216 }
        s6903                       OBJECT IDENTIFIER ::= { h3cProductId 217 }
        s6906                       OBJECT IDENTIFIER ::= { h3cProductId 218 }
        s6906R                      OBJECT IDENTIFIER ::= { h3cProductId 219 }
        s3928P-SI-ACDC              OBJECT IDENTIFIER ::= { h3cProductId 220 }

        s5540F                      OBJECT IDENTIFIER ::= { h3cProductId 221 }
        s5540C                      OBJECT IDENTIFIER ::= { h3cProductId 222 }
        s5556C                      OBJECT IDENTIFIER ::= { h3cProductId 223 }

        ar19-10                     OBJECT IDENTIFIER ::= { h3cProductId 224 }
        ar19-13                     OBJECT IDENTIFIER ::= { h3cProductId 225 }
        ar19-15                     OBJECT IDENTIFIER ::= { h3cProductId 226 }

        s3552P-SI                   OBJECT IDENTIFIER ::= { h3cProductId 227 }
        s3528P-SI                   OBJECT IDENTIFIER ::= { h3cProductId 228 }
        s5628C-HI-AC                OBJECT IDENTIFIER ::= { h3cProductId 229 }
        s5628C-HI-DC                OBJECT IDENTIFIER ::= { h3cProductId 230 }
        s5652C-HI-AC                OBJECT IDENTIFIER ::= { h3cProductId 231 }
        s5628F-HI                   OBJECT IDENTIFIER ::= { h3cProductId 232 }
        s5628C-PWR-HI               OBJECT IDENTIFIER ::= { h3cProductId 233 }
        s5652C-PWR-HI               OBJECT IDENTIFIER ::= { h3cProductId 234 }
        secBlade-LSQ1FWBSC1         OBJECT IDENTIFIER ::= { h3cProductId 235 }
        secBlade-LSQ1NSMSC1         OBJECT IDENTIFIER ::= { h3cProductId 236 }
        s7803-L                     OBJECT IDENTIFIER ::= { h3cProductId 237 }
        s6503-v5                    OBJECT IDENTIFIER ::= { h3cProductId 238 }
        s6506-v5                    OBJECT IDENTIFIER ::= { h3cProductId 239 }
        s6506R-v5                   OBJECT IDENTIFIER ::= { h3cProductId 240 }
        ar19-03                     OBJECT IDENTIFIER ::= { h3cProductId 241 }
        ar19-05                     OBJECT IDENTIFIER ::= { h3cProductId 242 }
        s7806-L                     OBJECT IDENTIFIER ::= { h3cProductId 243 }
        ar29-11                     OBJECT IDENTIFIER ::= { h3cProductId 244 }

-- under .huawei.hwLocal.quidway
        quidwayRouter OBJECT IDENTIFIER ::= { quidway 1 }
        hwRouter OBJECT IDENTIFIER ::= { quidwayRouter 1 }
        quidway1600 OBJECT IDENTIFIER ::= { quidwayRouter 1600 }
        quidway1602 OBJECT IDENTIFIER ::= { quidwayRouter 1602 }  -- May 07,2003,yubo added
        quidway1612 OBJECT IDENTIFIER ::= { quidwayRouter 1612 }  -- May 07,2003,yubo added
        quidway1613 OBJECT IDENTIFIER ::= { quidwayRouter 1613 }  -- May 07,2003,yubo added
        quidway1614 OBJECT IDENTIFIER ::= { quidwayRouter 1614 }  -- May 07,2003,yubo added
        quidway1615 OBJECT IDENTIFIER ::= { quidwayRouter 1615 }  -- May 07,2003,yubo added
        quidway1760 OBJECT IDENTIFIER ::= { quidwayRouter 1760 }  -- May 07,2003,yubo added
        quidway1760B OBJECT IDENTIFIER ::= { quidwayRouter 1761 } -- April 21,2003,yubo added
        quidway2501 OBJECT IDENTIFIER ::= { quidwayRouter 2501 }
        quidway2509 OBJECT IDENTIFIER ::= { quidwayRouter 2509 }
        quidway2511 OBJECT IDENTIFIER ::= { quidwayRouter 2511 }   -- May 07,2003,yubo added
        quidway2501E OBJECT IDENTIFIER ::= { quidwayRouter 2601 }  -- May 07,2003,yubo added
        quidway4001E OBJECT IDENTIFIER ::= { quidwayRouter 2606 }  -- May 07,2003,yubo added
        quidway2509E OBJECT IDENTIFIER ::= { quidwayRouter 2608 }  -- May 07,2003,yubo added
        quidway2511E OBJECT IDENTIFIER ::= { quidwayRouter 2609 }  -- May 07,2003,yubo added
        quidway2610 OBJECT IDENTIFIER ::= { quidwayRouter 2610 }  -- May 07,2003,yubo added
        quidway2611 OBJECT IDENTIFIER ::= { quidwayRouter 2611 }  -- May 07,2003,yubo added
        quidway2620 OBJECT IDENTIFIER ::= { quidwayRouter 2620 }  -- May 07,2003,yubo added
        quidway2621 OBJECT IDENTIFIER ::= { quidwayRouter 2621 }  -- May 07,2003,yubo added
        quidway2630 OBJECT IDENTIFIER ::= { quidwayRouter 2630 }  -- May 07,2003,yubo added
        quidway2631 OBJECT IDENTIFIER ::= { quidwayRouter 2631 }  -- May 07,2003,yubo added
        quidway3640 OBJECT IDENTIFIER ::= { quidwayRouter 3640 }
        quidway3680 OBJECT IDENTIFIER ::= { quidwayRouter 3680 }  -- May 07,2003,yubo added
        quidway4001 OBJECT IDENTIFIER ::= { quidwayRouter 4001 }
        eudemon OBJECT IDENTIFIER ::= { quidwayRouter 100 }    -- May 07,2003,yubo added
        ar28-80 OBJECT IDENTIFIER ::= { quidwayRouter 12880 }  -- May 19,2003,yubo added rename 3680E
        ar28-10 OBJECT IDENTIFIER ::= { quidwayRouter 12810 }  -- May 19,2003,yubo added rename 2610
        ar28-11 OBJECT IDENTIFIER ::= { quidwayRouter 12811 }  -- May 19,2003,yubo added rename 2611
        ar18-12 OBJECT IDENTIFIER ::= { quidwayRouter 11812 }  -- May 19,2003,yubo added rename 1612
        ar18-13 OBJECT IDENTIFIER ::= { quidwayRouter 11813 }  -- May 19,2003,yubo added rename 1613
        ar18-15 OBJECT IDENTIFIER ::= { quidwayRouter 11815 }  -- May 19,2003,yubo added rename 1615
        ar18-16 OBJECT IDENTIFIER ::= { quidwayRouter 11816 }  -- May 19,2003,yubo added rename 1616
        ar28-40 OBJECT IDENTIFIER ::= { quidwayRouter 12840 }  -- May 19,2003,yubo added rename 3640E
        ar28-09 OBJECT IDENTIFIER ::= { quidwayRouter 12809 }  -- May 19,2003,yubo added rename 1760
        ar28-30 OBJECT IDENTIFIER ::= { quidwayRouter 12830 }  -- May 19,2003,yubo added rename 2630
        ar28-31 OBJECT IDENTIFIER ::= { quidwayRouter 12831 }  -- May 19,2003,yubo added rename 2631

-- under .huawei.products
        ar46-20 OBJECT IDENTIFIER ::= { products 44 }  -- June 16, 2003, yubo added
        ar46-40 OBJECT IDENTIFIER ::= { products 45 }  -- June 16, 2003, yubo added
        ar46-80 OBJECT IDENTIFIER ::= { products 46 }  -- June 16, 2003, yubo added
        vdg10-40 OBJECT IDENTIFIER ::= { products 52 } -- June 24, 2003, yubo added
        vdg10-41 OBJECT IDENTIFIER ::= { products 53 } -- June 24, 2003, yubo added
        ar18-18 OBJECT IDENTIFIER ::= { products 55 }  -- August 12,2003,yubo added
        ar18-20 OBJECT IDENTIFIER ::= { products 56 }  -- August 12,2003,yubo added
        ar18-30 OBJECT IDENTIFIER ::= { products 57 }  -- August 12,2003,yubo added
        ar18-31 OBJECT IDENTIFIER ::= { products 58 }  -- August 12,2003,yubo added
        ar18-32 OBJECT IDENTIFIER ::= { products 59 }  -- August 12,2003,yubo added
        ar18-33 OBJECT IDENTIFIER ::= { products 60 }  -- August 12,2003,yubo added
        ar18-34 OBJECT IDENTIFIER ::= { products 61 }  -- August 12,2003,yubo added
        ne5000 OBJECT IDENTIFIER ::= { products 62 }   -- August 29,2003,xiejianping added

-- under .huawei.products.lanSw
        s8016 OBJECT IDENTIFIER ::= { lanSw 11 }
        s8016Common OBJECT IDENTIFIER ::= { s8016 1 }
        s8016A OBJECT IDENTIFIER ::= { s8016 2 }
        s8016B OBJECT IDENTIFIER ::= { s8016 3 }
        s3526 OBJECT IDENTIFIER ::= { lanSw 12 }
        s3026 OBJECT IDENTIFIER ::= { lanSw 13 }
        s3026V OBJECT IDENTIFIER ::= { lanSw 14 }
        s2008 OBJECT IDENTIFIER ::= { lanSw 15 }
        s2016 OBJECT IDENTIFIER ::= { lanSw 16 }
        s3526F OBJECT IDENTIFIER ::= { lanSw 17 }       -- May 07,2003,yubo modify name
        s5516 OBJECT IDENTIFIER ::= { lanSw 18 }
        s6506 OBJECT IDENTIFIER ::= { lanSw 19 }
        s3026F OBJECT IDENTIFIER ::= { lanSw 20 }
        s3526E OBJECT IDENTIFIER ::= { lanSw 21 }
        s2026 OBJECT IDENTIFIER ::= { lanSw 22 }
        s2403H OBJECT IDENTIFIER ::= { lanSw 23 }
        s3026E OBJECT IDENTIFIER ::= { lanSw 24 }
        s3026E-FM OBJECT IDENTIFIER ::= { lanSw 25 }
        s3026E-FS OBJECT IDENTIFIER ::= { lanSw 26 }
        s3526E-FM OBJECT IDENTIFIER ::= { lanSw 27 }
        s3526E-FS OBJECT IDENTIFIER ::= { lanSw 28 }
        s3050C OBJECT IDENTIFIER ::= { lanSw 29 }       -- May 07,2003,yubo added
        s6503 OBJECT IDENTIFIER ::= { lanSw 30 }        -- May 07,2003,yubo added
        s8512 OBJECT IDENTIFIER ::= { lanSw 31 }        -- April 08,2003,yubo added
        s8505 OBJECT IDENTIFIER ::= { lanSw 32 }        -- May 07,2003,yubo added
        s6506R OBJECT IDENTIFIER ::= { lanSw 33 }       -- May 07,2003,yubo added
        s3026c OBJECT IDENTIFIER ::= { lanSw 34 }       -- May 14,2003,yubo added
        s3026g OBJECT IDENTIFIER ::= { lanSw 35 }       -- May 14,2003,yubo added
        s3026t OBJECT IDENTIFIER ::= { lanSw 36 }       -- May 14,2003,yubo added
        s3552G OBJECT IDENTIFIER ::= { lanSw 37 }       -- May 19,2003,yubo added
        s3552P OBJECT IDENTIFIER ::= { lanSw 38 }       -- May 19,2003,yubo added
        s3528G OBJECT IDENTIFIER ::= { lanSw 39 }       -- May 19,2003,yubo added
        s3528P OBJECT IDENTIFIER ::= { lanSw 40 }       -- May 19,2003,yubo added
        s3526c OBJECT IDENTIFIER ::= { lanSw 41 }       -- May 23,2003,yubo added
        s3026c-24-12fs OBJECT IDENTIFIER ::= { lanSw 42 }          -- May 23,2003,yubo added
        s3026c-24-12fm OBJECT IDENTIFIER ::= { lanSw 43 }          -- May 23,2003,yubo added
        s3526c-24-12fs OBJECT IDENTIFIER ::= { lanSw 44 }          -- May 23,2003,yubo added
        s3526c-24-12fm OBJECT IDENTIFIER ::= { lanSw 45 }          -- May 23,2003,yubo added
        s5012G  OBJECT IDENTIFIER ::= { lanSw 46 }                 -- July 03,2003,yubo added
        s5012G-DC       OBJECT IDENTIFIER ::= { lanSw 47 }         -- July 03,2003,yubo added
        s5012T-12-10GBC         OBJECT IDENTIFIER ::= { lanSw 48 } -- July 03,2003,yubo added
        s5012T-12-10GBC-DC      OBJECT IDENTIFIER ::= { lanSw 49 } -- July 03,2003,yubo added
        s5024G-24-20TP  OBJECT IDENTIFIER ::= { lanSw 50 }         -- July 03,2003,yubo added
        s5024G-24-20TP-DC       OBJECT IDENTIFIER ::= { lanSw 51 } -- July 03,2003,yubo added
        s2026Z          OBJECT IDENTIFIER ::= { lanSw 52 }      -- August 12,2003,yubo added
        s2026C          OBJECT IDENTIFIER ::= { lanSw 53 }      -- August 12,2003,yubo added
        s3026G-SI       OBJECT IDENTIFIER ::= { lanSw 54 }      -- August 12,2003,yubo added
        s3026C-SI       OBJECT IDENTIFIER ::= { lanSw 55 }      -- August 12,2003,yubo added
        s3026S-SI       OBJECT IDENTIFIER ::= { lanSw 56 }      -- August 12,2003,yubo added
        s8505e          OBJECT IDENTIFIER ::= { lanSw 57 }      -- 2003/12/23, xiejianping added
        s3552F-SI       OBJECT IDENTIFIER ::= { lanSw 67 }      -- 2004-9-9,xiejianping added
        s3552F-EI       OBJECT IDENTIFIER ::= { lanSw 68 }      -- 2004-9-9,xiejianping added
        e026            OBJECT IDENTIFIER ::= { lanSw 69 }      -- 2004-9-9,xiejianping added
        e026-SI         OBJECT IDENTIFIER ::= { lanSw 70 }      -- 2004-9-9,xiejianping added
        e050            OBJECT IDENTIFIER ::= { lanSw 71 }      -- 2004-9-9,xiejianping added
END
