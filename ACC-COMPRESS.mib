ACC-COMPRESS DEFINITIONS ::= BEGIN

    IMPORTS
       OBJECT-TYPE, Counter, Gauge FROM RFC1155-SMI
		 accTrapLogSeqNum FROM ACC-SYSTEM
	accBRG, DisplayString, IfIndex, SmdsAddress
             FROM ACC-MIB
	RowStatus FROM SNMPv2-TC;

-- COMPRESSION Group
		accCompress OBJECT IDENTIFIER ::= { accBRG 6 }
		accCompressDialNeighborTable OBJECT-TYPE
			SYNTAX SEQUENCE OF AccCompressDialNeighborEntry
			ACCESS not-accessible
			STATUS mandatory
			DESCRIPTION
				"Data compression neighbor exception table
				for dial ports containing data compression
				parameters for selected neighbors."
			::= { accCompress 1 }
		accCompressDialNeighborEntry OBJECT-TYPE
			SYNTAX AccCompressDialNeighborEntry
			ACCESS not-accessible
			STATUS mandatory
			DESCRIPTION
				"Data compression neighbor exception table
				entry containing data compression parameters
				for a particular dial port neighbor."
			INDEX { accCompressDialNeighborIfIndex,
			accCompressDialNeighborCallAddress
			}
			::= { accCompressDialNeighborTable 1 }
		AccCompressDialNeighborEntry ::= SEQUENCE {
			accCompressDialNeighborIfIndex INTEGER,
			accCompressDialNeighborCallAddress DisplayString,
			accCompressDialNeighborStatus INTEGER
			}
		accCompressDialNeighborIfIndex OBJECT-TYPE
			SYNTAX INTEGER
			ACCESS read-only
			STATUS mandatory
			DESCRIPTION
				"The ifindex of the dial port via which the
				neighbor is accessed or connected."
			::= { accCompressDialNeighborEntry 1 }
		accCompressDialNeighborCallAddress OBJECT-TYPE
			SYNTAX DisplayString 
			ACCESS read-only
			STATUS mandatory
			DESCRIPTION
				"The call address of the neighbor to which
				the dial port is accessed or connected."
			::= { accCompressDialNeighborEntry 2 }
		accCompressDialNeighborStatus OBJECT-TYPE
			SYNTAX INTEGER {
				on(1),
				off(2),
				invalid(128)
			}
			ACCESS read-write
			STATUS mandatory
			DESCRIPTION
				"The administrative status of data
				compression for this dial neighbor.  ON
				enables data compression and OFF disables it.
				Setting the status to INVALID permanently
				removes the entry from the table."
			DEFVAL { off }
			::= { accCompressDialNeighborEntry 3 }
		accCompressFfrNeighborTable OBJECT-TYPE
			SYNTAX SEQUENCE OF AccCompressFfrNeighborEntry
			ACCESS not-accessible
			STATUS mandatory
			DESCRIPTION
				"Data compression neighbor exception table
				for frame relay circuits containing data
				compression parameters for selected
				neighbors."
			::= { accCompress 2 }
		accCompressFfrNeighborEntry OBJECT-TYPE
			SYNTAX AccCompressFfrNeighborEntry
			ACCESS not-accessible
			STATUS mandatory
			DESCRIPTION
				"Data compression neighbor exception table
				entry containing data compression parameters
				for a particular frame relay neighbor."
			INDEX { accCompressFfrNeighborIfIndex,
			accCompressFfrNeighborDlci }
			::= { accCompressFfrNeighborTable 1 }
		AccCompressFfrNeighborEntry ::= SEQUENCE {
			accCompressFfrNeighborIfIndex INTEGER,
			accCompressFfrNeighborDlci INTEGER,
			accCompressFfrNeighborStatus INTEGER }
		accCompressFfrNeighborIfIndex OBJECT-TYPE
			SYNTAX INTEGER
			ACCESS read-only
			STATUS mandatory
			DESCRIPTION
				"The physical port index via which the
				neighbor is accessed or connected."
			::= { accCompressFfrNeighborEntry 1 }
		accCompressFfrNeighborDlci OBJECT-TYPE
			SYNTAX INTEGER
			ACCESS read-only
			STATUS mandatory
			DESCRIPTION
				"A unique identifier for the neighbor.  In
				this case it is the local DLCI."
			::= { accCompressFfrNeighborEntry 2 }
		accCompressFfrNeighborStatus OBJECT-TYPE
			SYNTAX INTEGER {
				off(1),
				on(2),
				invalid(128)
			}
			ACCESS read-write
			STATUS mandatory
			DESCRIPTION
				"The administrative status of data
				compression for this neighbor.  ON enables
				data compression and OFF disables it.
				Setting the status to INVALID permanently
				removes the entry from the table."
			DEFVAL { off }
			::= { accCompressFfrNeighborEntry 3 }
		accCompressX25NeighborTable OBJECT-TYPE
			SYNTAX SEQUENCE OF AccCompressX25NeighborEntry
			ACCESS not-accessible
			STATUS mandatory
			DESCRIPTION
				"Data compression neighbor exception table
				for X25 circuits containing data compression
				parameters for selected neighbors."
			::= { accCompress 3 }
		accCompressX25NeighborEntry OBJECT-TYPE
			SYNTAX AccCompressX25NeighborEntry
			ACCESS not-accessible
			STATUS mandatory
			DESCRIPTION
				"Data compression neighbor exception table
				entry containing data compression parameters
				for a particular X.25 neighbor."
			INDEX { accCompressX25NeighborIfIndex,
			accCompressX25NeighborAddress }
			::= { accCompressX25NeighborTable 1 }
		AccCompressX25NeighborEntry ::= SEQUENCE {
			accCompressX25NeighborIfIndex INTEGER,
			accCompressX25NeighborAddress DisplayString,
			accCompressX25NeighborStatus INTEGER }
		accCompressX25NeighborIfIndex OBJECT-TYPE
			SYNTAX INTEGER
			ACCESS read-only
			STATUS mandatory
			DESCRIPTION
				"The physical port index via which the
				neighbor is accessed or connected."
			::= { accCompressX25NeighborEntry 1 }
		accCompressX25NeighborAddress OBJECT-TYPE
			SYNTAX  DisplayString 
			ACCESS read-only
			STATUS mandatory
			DESCRIPTION
				"A unique identifier for the neighbor.  This
				is the neighbor's DTE address"
			::= { accCompressX25NeighborEntry 2 }
		accCompressX25NeighborStatus OBJECT-TYPE
			SYNTAX INTEGER {
				off(1),
				on(2),
				invalid(128)
			}
			ACCESS read-write
			STATUS mandatory
			DESCRIPTION
				"The administrative status of data
				compression for this neighbor.  ON enables
				data compression and OFF disables it.
				Setting the status to INVALID permanently
				removes the entry from the table."
			DEFVAL { off }
			::= { accCompressX25NeighborEntry 3 }
--		Data Compression Statistics Table
		accCompressDialStatTable OBJECT-TYPE
			SYNTAX SEQUENCE OF AccCompressDialStatEntry
			ACCESS not-accessible
			STATUS mandatory
			DESCRIPTION
				"Data compression statistics table for dial
				ports containing data compression statistics
				for all active dial port neighbors."
			::= { accCompress 4 }
		accCompressDialStatEntry OBJECT-TYPE
			SYNTAX AccCompressDialStatEntry
			ACCESS not-accessible
			STATUS mandatory
			DESCRIPTION
				"Data compression dial port statistics table
				entry containing data compression statistics
				for a particular dial port neighbor."
			INDEX { accCompressDialStatIfIndex }
			::= { accCompressDialStatTable 1 }
		AccCompressDialStatEntry ::= SEQUENCE {
			accCompressDialStatIfIndex INTEGER,
			accCompressDialStatCallAddress OCTET STRING,
			accCompressDialStatStatus INTEGER,
			accCompressDialStatOctetsIns Counter,
			accCompressDialStatOctetsOuts Counter,
			accCompressDialStatPacketsIns Counter,
			accCompressDialStatPacketsOuts Counter,
			accCompressDialStatUnCompIns Counter,
			accCompressDialStatUnCompOuts Counter,
			accCompressDialStatAvgCompIn Gauge,
			accCompressDialStatAvgCompOut Gauge,
			accCompressDialStatHdrErrors Counter,
			accCompressDialStatResyncs Counter,
			accCompressDialStatNoEndMarks Counter,
			accCompressDialStatNoBufAvails Counter}
		accCompressDialStatIfIndex OBJECT-TYPE
			SYNTAX INTEGER
			ACCESS read-only
			STATUS mandatory
			DESCRIPTION
				"The interface index of the dial port via
				which the neighbor is accessed or connected."
			::= { accCompressDialStatEntry 1 }
		accCompressDialStatCallAddress OBJECT-TYPE
			SYNTAX OCTET STRING
			ACCESS read-only
			STATUS mandatory
			DESCRIPTION
				"The call address of the neighbor to which
				the dial port is currently connected."
			::= { accCompressDialStatEntry 2 }
		accCompressDialStatStatus OBJECT-TYPE
			SYNTAX INTEGER {
				disc(1),
				conn(2),
				sync(3),
				resync(4)
			}
			ACCESS read-only
			STATUS mandatory
			DESCRIPTION
				"The operational status of the neighbor."
			::= { accCompressDialStatEntry 3 }
		accCompressDialStatOctetsIns OBJECT-TYPE
			SYNTAX Counter
			ACCESS read-only
			STATUS mandatory
			DESCRIPTION
				"The total number of compressed octets
				presented for decompression."
			::= { accCompressDialStatEntry 4 }
		accCompressDialStatOctetsOuts OBJECT-TYPE
			SYNTAX Counter
			ACCESS read-only
			STATUS mandatory
			DESCRIPTION
				"The total number of compressed octets
				generated after compression."
			::= { accCompressDialStatEntry 5 }
		accCompressDialStatPacketsIns OBJECT-TYPE
			SYNTAX Counter
			ACCESS read-only
			STATUS mandatory
			DESCRIPTION
				"The total number of uncompressed packets
				generated by decompression."
			::= { accCompressDialStatEntry 6 }
		accCompressDialStatPacketsOuts OBJECT-TYPE
			SYNTAX Counter
			ACCESS read-only
			STATUS mandatory
			DESCRIPTION
				"The total number of uncompressed packets
				presented for compression."
			::= { accCompressDialStatEntry 7 }
		accCompressDialStatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressDialStatEntry 8 }
		accCompressDialStatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressDialStatEntry 9 }
		accCompressDialStatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressDialStatEntry 10 }
		accCompressDialStatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressDialStatEntry 11 }
		accCompressDialStatHdrErrors OBJECT-TYPE
			SYNTAX Counter
			ACCESS read-only
			STATUS mandatory
			DESCRIPTION
				"The number of packets received with invalid
				compression headers.  A header error requires
				a resynchronization of the history buffers at
				each end of the link."
			::= { accCompressDialStatEntry 12 }
		accCompressDialStatResyncs OBJECT-TYPE
			SYNTAX Counter
			ACCESS read-only
			STATUS mandatory
			DESCRIPTION
				"The number of resynchronizations."
			::= { accCompressDialStatEntry 13 }
		accCompressDialStatNoEndMarks OBJECT-TYPE
		SYNTAX Counter
			ACCESS read-only
			STATUS mandatory
			DESCRIPTION
				"The number of packets received with no end
				marker.  Missing end markers require a
				resynchronization of the history buffers at
				each end of the link."
			::= { accCompressDialStatEntry 14 }
		accCompressDialStatNoBufAvails OBJECT-TYPE
			SYNTAX Counter
			ACCESS read-only
			STATUS mandatory
			DESCRIPTION
				"The number of times the neighbor was
				connected and no history buffer could be
				allocated."
			::= { accCompressDialStatEntry 15 }
		accCompressFfrStatTable OBJECT-TYPE
			SYNTAX SEQUENCE OF AccCompressFfrStatEntry
			ACCESS not-accessible
			STATUS mandatory
			DESCRIPTION
				"Data compression statistics table containing
				data compression statistics for all active
				frame relay neighbors."
			::= { accCompress 5 }
		accCompressFfrStatEntry OBJECT-TYPE
			SYNTAX AccCompressFfrStatEntry
			ACCESS not-accessible
			STATUS mandatory
			DESCRIPTION
				"Data compression statistics table entry
				containing data compression statistics for a
				particular frame relay neighbor."
			INDEX { accCompressFfrStatIfIndex,
			accCompressFfrStatDlci }
			::= { accCompressFfrStatTable 1 }
		AccCompressFfrStatEntry ::= SEQUENCE {
			accCompressFfrStatIfIndex INTEGER,
			accCompressFfrStatDlci INTEGER,
			accCompressFfrStatStatus INTEGER,
			accCompressFfrStatOctetsIns Counter,
			accCompressFfrStatOctetsOuts Counter,
			accCompressFfrStatPacketsIns Counter,
			accCompressFfrStatPacketsOuts Counter,
			accCompressFfrStatUnCompIns Counter,
			accCompressFfrStatUnCompOuts Counter,
			accCompressFfrStatAvgCompIn Gauge,
			accCompressFfrStatAvgCompOut Gauge,
			accCompressFfrStatHdrErrors Counter,
			accCompressFfrStatResyncs Counter,
			accCompressFfrStatNoEndMarks Counter,
			accCompressFfrStatNoBufAvails Counter}
		accCompressFfrStatIfIndex OBJECT-TYPE
			SYNTAX INTEGER
			ACCESS read-only
			STATUS mandatory
			DESCRIPTION
				"The physical port index of the port via
				which the neighbor is accessed or connected."
			::= { accCompressFfrStatEntry 1 }
		accCompressFfrStatDlci OBJECT-TYPE
			SYNTAX INTEGER
			ACCESS read-only
			STATUS mandatory
			DESCRIPTION
				"This is the local DLCI for the frame relay
				neighbor."
			::= { accCompressFfrStatEntry 2 }
		accCompressFfrStatStatus OBJECT-TYPE
			SYNTAX INTEGER {
				disc(1),
				conn(2),
				sync(3),
				resync(4)
			}
			ACCESS read-only
			STATUS mandatory
			DESCRIPTION
				"The operational status of the neighbor."
			::= { accCompressFfrStatEntry 3 }
		accCompressFfrStatOctetsIns OBJECT-TYPE
			SYNTAX Counter
			ACCESS read-only
			STATUS mandatory
			DESCRIPTION
				"The total number of compressed octets
				presented for decompression."
			::= { accCompressFfrStatEntry 4 }
		accCompressFfrStatOctetsOuts OBJECT-TYPE
			SYNTAX Counter
			ACCESS read-only
			STATUS mandatory
			DESCRIPTION
				"The total number of compressed octets
				generated after compression."
			::= { accCompressFfrStatEntry 5 }
		accCompressFfrStatPacketsIns OBJECT-TYPE
			SYNTAX Counter
			ACCESS read-only
			STATUS mandatory
			DESCRIPTION
				"The total number of uncompressed packets
				generated by decompression."
			::= { accCompressFfrStatEntry 6 }
		accCompressFfrStatPacketsOuts OBJECT-TYPE
			SYNTAX Counter
			ACCESS read-only
			STATUS mandatory
			DESCRIPTION
				"The total number of uncompressed packets
				presented for compression."
			::= { accCompressFfrStatEntry 7 }
		accCompressFfrStatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressFfrStatEntry 8 }
		accCompressFfrStatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressFfrStatEntry 9 }
		accCompressFfrStatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressFfrStatEntry 10 }
		accCompressFfrStatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressFfrStatEntry 11 }
		accCompressFfrStatHdrErrors OBJECT-TYPE
			SYNTAX Counter
			ACCESS read-only
			STATUS mandatory
			DESCRIPTION
				"The number of packets received with invalid
				compression headers.  A header error requires
				a resynchronization of the history buffers at
				each end of the link."
			::= { accCompressFfrStatEntry 12 }
		accCompressFfrStatResyncs OBJECT-TYPE
			SYNTAX Counter
			ACCESS read-only
			STATUS mandatory
			DESCRIPTION
				"The number of resynchronizations."
			::= { accCompressFfrStatEntry 13 }
		accCompressFfrStatNoEndMarks OBJECT-TYPE
			SYNTAX Counter
			ACCESS read-only
			STATUS mandatory
			DESCRIPTION
				"The number of packets received with no end
				marker.  Missing end markers require a
				resynchronization of the history buffers at
				each end of the link."
			::= { accCompressFfrStatEntry 14 }
		accCompressFfrStatNoBufAvails OBJECT-TYPE
			SYNTAX Counter
			ACCESS read-only
			STATUS mandatory
			DESCRIPTION
				"The number of times the neighbor was
				connected and no history buffer could be
				allocated."
			::= { accCompressFfrStatEntry 15 }
		accCompressX25StatTable OBJECT-TYPE
		SYNTAX SEQUENCE OF AccCompressX25StatEntry
			ACCESS not-accessible
			STATUS mandatory
			DESCRIPTION
				"Data compression statistics table containing
				data compression statistics for all active
				X.25 neighbors."
			::= { accCompress 6 }
		accCompressX25StatEntry OBJECT-TYPE
			SYNTAX AccCompressX25StatEntry
			ACCESS not-accessible
			STATUS mandatory
			DESCRIPTION
				"Data compression statistics table entry
				containing data compression statistics for a
				particular X.25 neighbor."
			INDEX { accCompressX25StatIfIndex, 
				accCompressX25StatAddress }
			::= { accCompressX25StatTable 1 }
		AccCompressX25StatEntry ::= SEQUENCE {
			accCompressX25StatIfIndex INTEGER,
			accCompressX25StatAddress OCTET STRING,
			accCompressX25StatStatus INTEGER,
			accCompressX25StatOctetsIns Counter,
			accCompressX25StatOctetsOuts Counter,
			accCompressX25StatPacketsIns Counter,
			accCompressX25StatPacketsOuts Counter,
			accCompressX25StatUnCompIns Counter,
			accCompressX25StatUnCompOuts Counter,
			accCompressX25StatAvgCompIn Gauge,
			accCompressX25StatAvgCompOut Gauge,
			accCompressX25StatHdrErrors Counter,
			accCompressX25StatResyncs Counter,
			accCompressX25StatNoEndMarks Counter,
			accCompressX25StatNoBufAvails Counter}
		accCompressX25StatIfIndex OBJECT-TYPE
			SYNTAX INTEGER
			ACCESS read-only
			STATUS mandatory
			DESCRIPTION
				"The physical port index of the port via
				which the neighbor is accessed or connected."
			::= { accCompressX25StatEntry 1 }
		accCompressX25StatAddress OBJECT-TYPE
			SYNTAX OCTET STRING
			ACCESS read-only
			STATUS mandatory
			DESCRIPTION
				"DTE address for the X.25 neighbor."
			::= { accCompressX25StatEntry 2 }
		accCompressX25StatStatus OBJECT-TYPE
			SYNTAX INTEGER {
				disc(1),
				conn(2),
				sync(3),
				resync(4)
			}
			ACCESS read-only
			STATUS mandatory
			DESCRIPTION
				"The operational status of the neighbor."
			::= { accCompressX25StatEntry 3 }
		accCompressX25StatOctetsIns OBJECT-TYPE
			SYNTAX Counter
			ACCESS read-only
			STATUS mandatory
			DESCRIPTION
				"The total number of compressed octets
				presented for decompression."
			::= { accCompressX25StatEntry 4 }
		accCompressX25StatOctetsOuts OBJECT-TYPE
			SYNTAX Counter
			ACCESS read-only
			STATUS mandatory
			DESCRIPTION
				"The total number of compressed octets
				generated after compression."
			::= { accCompressX25StatEntry 5 }
		accCompressX25StatPacketsIns OBJECT-TYPE
			SYNTAX Counter
			ACCESS read-only
			STATUS mandatory
			DESCRIPTION
				"The total number of uncompressed packets
				generated by decompression."
			::= { accCompressX25StatEntry 6 }
		accCompressX25StatPacketsOuts OBJECT-TYPE
			SYNTAX Counter
			ACCESS read-only
			STATUS mandatory
			DESCRIPTION
				"The total number of uncompressed packets
				presented for compression."
			::= { accCompressX25StatEntry 7 }
		accCompressX25StatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressX25StatEntry 8 }
		accCompressX25StatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressX25StatEntry 9 }
		accCompressX25StatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressX25StatEntry 10 }
		accCompressX25StatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressX25StatEntry 11 }
		accCompressX25StatHdrErrors OBJECT-TYPE
			SYNTAX Counter
			ACCESS read-only
			STATUS mandatory
			DESCRIPTION
				"The number of packets received with invalid
				compression headers.  A header error requires
				a resynchronization of the history buffers at
				each end of the link."
			::= { accCompressX25StatEntry 12 }
		accCompressX25StatResyncs OBJECT-TYPE
			SYNTAX Counter
			ACCESS read-only
			STATUS mandatory
			DESCRIPTION
				"The number of resynchronizations."
			::= { accCompressX25StatEntry 13 }
		accCompressX25StatNoEndMarks OBJECT-TYPE
			SYNTAX Counter
			ACCESS read-only
			STATUS mandatory
			DESCRIPTION
				"The number of packets received with no end
				marker.  Missing end markers require a
				resynchronization of the history buffers at
				each end of the link."
			::= { accCompressX25StatEntry 14 }
		accCompressX25StatNoBufAvails OBJECT-TYPE
			SYNTAX Counter
			ACCESS read-only
			STATUS mandatory
			DESCRIPTION
				"The number of times the neighbor was
				connected and no history buffer could be
				allocated."
			::= { accCompressX25StatEntry 15 }
		accCompressPhysStatTable OBJECT-TYPE
			SYNTAX SEQUENCE OF AccCompressPhysStatEntry
			ACCESS not-accessible
			STATUS mandatory
			DESCRIPTION
				"Data compression statistics table for
				physical ports containing aggregate data
				compression statistics for all active and
				inactive neighbors."
			::= { accCompress 7 }
		accCompressPhysStatEntry OBJECT-TYPE
			SYNTAX AccCompressPhysStatEntry
			ACCESS not-accessible
			STATUS mandatory
			DESCRIPTION
				"Data compression statistics table entry
				containing aggregate data compression
				statistics for all neighbors through a
				particular physical port."
			INDEX { accCompressPhysStatIfIndex }
			::= { accCompressPhysStatTable 1 }
		AccCompressPhysStatEntry ::= SEQUENCE {
			accCompressPhysStatIfIndex 	INTEGER,
			accCompressPhysStatStatus 	INTEGER,
			accCompressPhysStatOctetsIns 	Counter,
			accCompressPhysStatOctetsOuts 	Counter,
			accCompressPhysStatPacketsIns 	Counter,
			accCompressPhysStatPacketsOuts 	Counter,
			accCompressPhysStatUnCompIns 	Counter,
			accCompressPhysStatUnCompOuts 	Counter,
			accCompressPhysStatAvgCompIn 	Gauge,
			accCompressPhysStatAvgCompOut 	Gauge,
			accCompressPhysStatHdrErrors 	Counter,
			accCompressPhysStatResyncs 	Counter,
			accCompressPhysStatNoEndMarks 	Counter,
			accCompressPhysStatNoBufAvails 	Counter,
			accCompressPhysStatusInStats	INTEGER,
			accCompressPhysStatusOutStats   INTEGER,
			accCompressPhysExpandInStats   	Counter,
			accCompressPhysExpandOutStats   Counter,
			accCompressPhysDiscardInStats   Counter,
			accCompressPhysDiscardOutStats  Counter}
		accCompressPhysStatIfIndex OBJECT-TYPE
			SYNTAX INTEGER
			ACCESS read-only
			STATUS mandatory
			DESCRIPTION
				"The index of the physical port via which the
				neighbor(s) is(are) accessed or connected."
			::= { accCompressPhysStatEntry 1 }
		accCompressPhysStatStatus OBJECT-TYPE
			SYNTAX INTEGER {
				disc(1),
				conn(2),
				sync(3),
				resync(4)
			}
			ACCESS read-only
			STATUS mandatory
			DESCRIPTION
				"The operational status of the neighbor. For
				X.25 and Frame Relay ports, as there can be
				more than one neighbor, this is the superior
				status."
			::= { accCompressPhysStatEntry 2 }
		accCompressPhysStatOctetsIns OBJECT-TYPE
			SYNTAX Counter
			ACCESS read-only
			STATUS mandatory
			DESCRIPTION
				"The total number of compressed octets
				presented for decompression."
			::= { accCompressPhysStatEntry 3 }
		accCompressPhysStatOctetsOuts OBJECT-TYPE
			SYNTAX Counter
			ACCESS read-only
			STATUS mandatory
			DESCRIPTION
				"The total number of compressed octets
				generated after compression."
			::= { accCompressPhysStatEntry 4 }
		accCompressPhysStatPacketsIns OBJECT-TYPE
			SYNTAX Counter
			ACCESS read-only
			STATUS mandatory
			DESCRIPTION
				"The total number of uncompressed packets
				generated by decompression."
			::= { accCompressPhysStatEntry 5 }
		accCompressPhysStatPacketsOuts OBJECT-TYPE
			SYNTAX Counter
			ACCESS read-only
			STATUS mandatory
			DESCRIPTION
				"The total number of uncompressed packets
				presented for compression."
			::= { accCompressPhysStatEntry 6 }
		accCompressPhysStatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressPhysStatEntry 7 }
		accCompressPhysStatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressPhysStatEntry 8 }
		accCompressPhysStatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressPhysStatEntry 9 }
		accCompressPhysStatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressPhysStatEntry 10 }
		accCompressPhysStatHdrErrors OBJECT-TYPE
			SYNTAX Counter
			ACCESS read-only
			STATUS mandatory
			DESCRIPTION
				"The number of packets received with invalid
				compression headers.  A header error requires
				a resynchronization of the history buffers at
				each end of the link."
			::= { accCompressPhysStatEntry 11 }
		accCompressPhysStatResyncs OBJECT-TYPE
			SYNTAX Counter
			ACCESS read-only
			STATUS mandatory
			DESCRIPTION
				"The number of resynchronizations."
			::= { accCompressPhysStatEntry 12 }
		accCompressPhysStatNoEndMarks OBJECT-TYPE
			SYNTAX Counter
			ACCESS read-only
			STATUS mandatory
			DESCRIPTION
				"The number of packets received with no end
				marker.  Missing end markers require a
				resynchronization of the history buffers at
				each end of the link."
			::= { accCompressPhysStatEntry 13 }
		accCompressPhysStatNoBufAvails OBJECT-TYPE
			SYNTAX Counter
			ACCESS read-only
			STATUS mandatory
			DESCRIPTION
				"The number of times the neighbor was
				connected and no history buffer could be
				allocated."
			::= { accCompressPhysStatEntry 14 }
                accCompressPhysStatusInStats OBJECT-TYPE
                        SYNTAX INTEGER {
					disc(1),
					conn(2),
					sync(3),
					resync(4)
			}
                        ACCESS read-only
                        STATUS mandatory
                        DESCRIPTION
                                 "The current status of the incoming packet 
			       	  port compression connection."
                        ::= { accCompressPhysStatEntry 15 }
                accCompressPhysStatusOutStats OBJECT-TYPE
                        SYNTAX INTEGER {
                                        disc(1),
                                        conn(2),
                                        sync(3),
                                        resync(4)
                        }
                        ACCESS read-only
                        STATUS mandatory
                        DESCRIPTION
                                 "The current status of the outgoing packet
                                  port compression connection."
                        ::= { accCompressPhysStatEntry 16 }
                accCompressPhysExpandInStats OBJECT-TYPE
                        SYNTAX Counter
                        ACCESS read-only
                        STATUS mandatory
                        DESCRIPTION
                                "The number of incoming packets that have 
				been uncompressed."
                        ::= { accCompressPhysStatEntry 17 }
                accCompressPhysExpandOutStats OBJECT-TYPE
                        SYNTAX Counter
                        ACCESS read-only
                        STATUS mandatory
                        DESCRIPTION
                                "The number of outgoing packets that have 
				been uncompressed."
                        ::= { accCompressPhysStatEntry 18 }
                accCompressPhysDiscardInStats OBJECT-TYPE
                        SYNTAX Counter
                        ACCESS read-only
                        STATUS mandatory
                        DESCRIPTION
                                "The number of incoming packets that have 
				been discarded."
                        ::= { accCompressPhysStatEntry 19 }
                accCompressPhysDiscardOutStats OBJECT-TYPE
                        SYNTAX Counter
                        ACCESS read-only
                        STATUS mandatory
                        DESCRIPTION
                                "The number outgoing packets that have 
				been discarded."
                        ::= { accCompressPhysStatEntry 20 }
-- SMDS Compression Table
		accCompressSmdsNeighborTable OBJECT-TYPE
			SYNTAX SEQUENCE OF AccCompressSmdsNeighborEntry
			ACCESS not-accessible
			STATUS mandatory
			DESCRIPTION
				"Data compression neighbor table
				for Smds connections containing data
				compression parameters for selected
				neighbors."
			::= { accCompress 8 }
		accCompressSmdsNeighborEntry OBJECT-TYPE
		    	SYNTAX AccCompressSmdsNeighborEntry
			ACCESS not-accessible
		    	STATUS mandatory
		    	DESCRIPTION
				"Data compression neighbor table
				entry containing data compression parameters
				for a particular Smds neighbor."
		    	INDEX 	{ accCompressSmdsNeighborIfIndex,
		    		  accCompressSmdsNeighborSNI }
		    	::= { accCompressSmdsNeighborTable 1 }
		AccCompressSmdsNeighborEntry ::= SEQUENCE {
			accCompressSmdsNeighborIfIndex	INTEGER,
			accCompressSmdsNeighborSNI	SmdsAddress,
			accCompressSmdsNeighborStatus	INTEGER,
			accCompressSmdsNeighborRowStatus	RowStatus
			}
		accCompressSmdsNeighborIfIndex OBJECT-TYPE
			SYNTAX INTEGER
			ACCESS read-only
			STATUS mandatory
			DESCRIPTION
			    "The physical port index via which the
			    neighbor is accessed or connected."
		::= { accCompressSmdsNeighborEntry 1 }
		accCompressSmdsNeighborSNI OBJECT-TYPE
			SYNTAX SmdsAddress
			ACCESS read-only
			STATUS mandatory
			DESCRIPTION
			    "A unique identifier for the neighbor.  In
			    this case it is the remote SNI address.
			    This is the unicast Subscriber Network Interface
			    address of the remote side in E.164 address
			    format (e.g., 0xC18005551212FFFF)"
			::= { accCompressSmdsNeighborEntry 2 }
		accCompressSmdsNeighborStatus OBJECT-TYPE
			SYNTAX INTEGER {
			off(1),
			on(2),
			invalid(128)
			}
			ACCESS read-write
			STATUS mandatory
			DESCRIPTION
			    "The administrative status of data
			    compression for this neighbor.  ON enables
			    data compression and OFF disables it.
			    Setting the status to INVALID permanently
			    removes the entry from the table."
			DEFVAL { off }
			::= { accCompressSmdsNeighborEntry 3 }
		accCompressSmdsNeighborRowStatus OBJECT-TYPE
			SYNTAX RowStatus
			ACCESS read-write
			STATUS mandatory
			DESCRIPTION
			"The current status of this neighbor entry."
			::= { accCompressSmdsNeighborEntry 4 }
-- SMDS Compression Statistics Table
		accCompressSmdsStatTable OBJECT-TYPE
			SYNTAX SEQUENCE OF AccCompressSmdsStatEntry
			ACCESS not-accessible
			STATUS mandatory
			DESCRIPTION
			    "Data compression statistics table containing
			    data compression statistics for all active
			    Smds neighbors."
			::= { accCompress 9 }
		accCompressSmdsStatEntry OBJECT-TYPE
			SYNTAX AccCompressSmdsStatEntry
			ACCESS not-accessible
			STATUS mandatory
			DESCRIPTION
			    "Data compression statistics table entry
			    containing data compression statistics for a
			    particular Smds neighbor."
			INDEX { accCompressSmdsStatIfIndex,
				accCompressSmdsStatSNI }
			::= { accCompressSmdsStatTable 1 }
		AccCompressSmdsStatEntry ::= SEQUENCE {
			accCompressSmdsStatIfIndex 	INTEGER,
			accCompressSmdsStatSNI 		SmdsAddress,
			accCompressSmdsStatStatus 	INTEGER,
			accCompressSmdsStatOctetsIns 	Counter,
			accCompressSmdsStatOctetsOuts	Counter,
			accCompressSmdsStatPacketsIns	Counter,
			accCompressSmdsStatPacketsOuts	Counter,
			accCompressSmdsStatUnCompIns	Counter,
			accCompressSmdsStatUnCompOuts	Counter,
			accCompressSmdsStatAvgCompIn	Gauge,
			accCompressSmdsStatAvgCompOut	Gauge,
			accCompressSmdsStatHdrErrors	Counter,
			accCompressSmdsStatResyncs	Counter,
			accCompressSmdsStatNoEndMarks	Counter,
			accCompressSmdsStatNoBufAvails	Counter
		}
		accCompressSmdsStatIfIndex OBJECT-TYPE
			SYNTAX INTEGER
			ACCESS read-only
			STATUS mandatory
			DESCRIPTION
			    "The physical port index of the port via
			    which the neighbor is accessed or connected."
			::= { accCompressSmdsStatEntry 1 }
		accCompressSmdsStatSNI OBJECT-TYPE
			SYNTAX SmdsAddress
			ACCESS read-write
			STATUS mandatory
			DESCRIPTION
			    "A unique identifier for the neighbor.  In
			    this case it is the remote SNI address.
			    This is the unicast Subscriber Network Interface
			    address of the remote side in E.164 address
			    format (e.g., 0xC18005551212FFFF)"
			::= { accCompressSmdsStatEntry 2 }
		accCompressSmdsStatStatus OBJECT-TYPE
			SYNTAX INTEGER {
			disc(1),
			conn(2),
			sync(3),
			resync(4)
			}
			ACCESS read-only
			STATUS mandatory
			DESCRIPTION
			    "The operational status of the neighbor."
			::= { accCompressSmdsStatEntry 3 }
		accCompressSmdsStatOctetsIns OBJECT-TYPE
			SYNTAX Counter
			ACCESS read-only
			STATUS mandatory
			DESCRIPTION
			    "The total number of compressed octets
			    presented for decompression."
			::= { accCompressSmdsStatEntry 4 }
		accCompressSmdsStatOctetsOuts OBJECT-TYPE
			SYNTAX Counter
			ACCESS read-only
			STATUS mandatory
			DESCRIPTION
			    "The total number of compressed octets
			    generated after compression."
			::= { accCompressSmdsStatEntry 5 }
		accCompressSmdsStatPacketsIns OBJECT-TYPE
			SYNTAX Counter
			ACCESS read-only
			STATUS mandatory
			DESCRIPTION
			    "The total number of uncompressed packets
			    generated by decompression."
			::= { accCompressSmdsStatEntry 6 }
		accCompressSmdsStatPacketsOuts OBJECT-TYPE
			SYNTAX Counter
			ACCESS read-only
			STATUS mandatory
			DESCRIPTION
			    "The total number of uncompressed packets
			    presented for compression."
			::= { accCompressSmdsStatEntry 7 }
		accCompressSmdsStatUnCompIns OBJECT-TYPE
			SYNTAX Counter
			ACCESS read-only
			STATUS mandatory
			DESCRIPTION
			    "The total number of uncompressed packets
			    presented for decompression (i.e., packets
			    which could not be compressed and were
			    therefore received in their uncompressed
			    form)."
			::= { accCompressSmdsStatEntry 8 }
		accCompressSmdsStatUnCompOuts OBJECT-TYPE
			SYNTAX Counter
			ACCESS read-only
			STATUS mandatory
			DESCRIPTION
			    "The total number of uncompressed packets
			    presented for compression which could not be
			    compressed (i.e., the packet expanded).
			    These packets are transmitted in their
			    uncompressed form."
			::= { accCompressSmdsStatEntry 9 }
		accCompressSmdsStatAvgCompIn OBJECT-TYPE
			SYNTAX Gauge
			ACCESS read-only
			STATUS mandatory
			DESCRIPTION
			    "The average compression rate of packets
			    presented for decompression expressed as a
			    percentage between 0 and 100.  100% is the
			    unattainable rate which could only be
			    achieved by compressing all packets to zero
			    bits."
			::= { accCompressSmdsStatEntry 10 }
		accCompressSmdsStatAvgCompOut OBJECT-TYPE
			SYNTAX Gauge
			ACCESS read-only
			STATUS mandatory
			DESCRIPTION
			    "The average compression rate of packets
			    presented for compression expressed as a
			    percentage between 0 and 100.  100% is the
			    unattainable rate which could only be
			    achieved by compressing all packets to zero
			    bits."
			::= { accCompressSmdsStatEntry 11 }
		accCompressSmdsStatHdrErrors OBJECT-TYPE
			SYNTAX Counter
			ACCESS read-only
			STATUS mandatory
			DESCRIPTION
			    "The number of packets received with invalid
			    compression headers.  A header error requires
			    a resynchronization of the history buffers at
			    each end of the link."
			::= { accCompressSmdsStatEntry 12 }
		accCompressSmdsStatResyncs OBJECT-TYPE
			SYNTAX Counter
			ACCESS read-only
			STATUS mandatory
			DESCRIPTION
			    "The number of resynchronizations."
			::= { accCompressSmdsStatEntry 13 }
		accCompressSmdsStatNoEndMarks OBJECT-TYPE
			SYNTAX Counter
			ACCESS read-only
			STATUS mandatory
			DESCRIPTION
			    "The number of packets received with no end
			    marker.  Missing end markers require a
			    resynchronization of the history buffers at
			    each end of the link."
			::= { accCompressSmdsStatEntry 14 }
		accCompressSmdsStatNoBufAvails OBJECT-TYPE
			SYNTAX Counter
			ACCESS read-only
			STATUS mandatory
			DESCRIPTION
			    "The number of times the neighbor was
			    connected and no history buffer could be
			    allocated."
			::= { accCompressSmdsStatEntry 15 }

END
