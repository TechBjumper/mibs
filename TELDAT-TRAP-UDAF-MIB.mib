-- file automatically created


TELDAT-TRAP-UDAF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


udafTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the UDAF event subsystem."
    REVISION "201401200930Z"
    DESCRIPTION "Initial implementation"
        ::= { telEventTraps 143 }


udafEventsGroup	OBJECT IDENTIFIER	::= { udafTrapsMIB 1 }

udafNotifications	OBJECT IDENTIFIER	::= { udafTrapsMIB 2 }
udafNotificationsPrefix	OBJECT IDENTIFIER	::= { udafNotifications 0 }

udafEventObjects1 OBJECT-IDENTITY
    STATUS current
    DESCRIPTION
        "Event UDAF.1
        Data has been received from POS."
    ::= { udafEventsGroup 1 }

udaf1-bytes-number OBJECT-TYPE
    SYNTAX Integer32
    MAX-ACCESS accessible-for-notify
    STATUS current
    DESCRIPTION
        "Parameter 'bytes-number' in event UDAF.1"
    ::= { udafEventObjects1 1 }

udaf1-interface OBJECT-TYPE
    SYNTAX DisplayString
    MAX-ACCESS accessible-for-notify
    STATUS current
    DESCRIPTION
        "Parameter 'interface' in event UDAF.1"
    ::= { udafEventObjects1 2 }

udafEventObjects2 OBJECT-IDENTITY
    STATUS current
    DESCRIPTION
        "Event UDAF.2
        An ACK control character has been received from POS."
    ::= { udafEventsGroup 2 }

udaf2-interface OBJECT-TYPE
    SYNTAX DisplayString
    MAX-ACCESS accessible-for-notify
    STATUS current
    DESCRIPTION
        "Parameter 'interface' in event UDAF.2"
    ::= { udafEventObjects2 1 }

udaf2-state OBJECT-TYPE
    SYNTAX Integer32
    MAX-ACCESS accessible-for-notify
    STATUS current
    DESCRIPTION
        "Parameter 'state' in event UDAF.2"
    ::= { udafEventObjects2 2 }

udafEventObjects3 OBJECT-IDENTITY
    STATUS current
    DESCRIPTION
        "Event UDAF.3
        An EOT control character has been received from POS."
    ::= { udafEventsGroup 3 }

udaf3-interface OBJECT-TYPE
    SYNTAX DisplayString
    MAX-ACCESS accessible-for-notify
    STATUS current
    DESCRIPTION
        "Parameter 'interface' in event UDAF.3"
    ::= { udafEventObjects3 1 }

udaf3-state OBJECT-TYPE
    SYNTAX Integer32
    MAX-ACCESS accessible-for-notify
    STATUS current
    DESCRIPTION
        "Parameter 'state' in event UDAF.3"
    ::= { udafEventObjects3 2 }

udafEventObjects4 OBJECT-IDENTITY
    STATUS current
    DESCRIPTION
        "Event UDAF.4
        A NAK control character has been received from POS."
    ::= { udafEventsGroup 4 }

udaf4-interface OBJECT-TYPE
    SYNTAX DisplayString
    MAX-ACCESS accessible-for-notify
    STATUS current
    DESCRIPTION
        "Parameter 'interface' in event UDAF.4"
    ::= { udafEventObjects4 1 }

udaf4-state OBJECT-TYPE
    SYNTAX Integer32
    MAX-ACCESS accessible-for-notify
    STATUS current
    DESCRIPTION
        "Parameter 'state' in event UDAF.4"
    ::= { udafEventObjects4 2 }

udafEventObjects5 OBJECT-IDENTITY
    STATUS current
    DESCRIPTION
        "Event UDAF.5
        A block with parity error has been received from POS."
    ::= { udafEventsGroup 5 }

udaf5-interface OBJECT-TYPE
    SYNTAX DisplayString
    MAX-ACCESS accessible-for-notify
    STATUS current
    DESCRIPTION
        "Parameter 'interface' in event UDAF.5"
    ::= { udafEventObjects5 1 }

udafEventObjects6 OBJECT-IDENTITY
    STATUS current
    DESCRIPTION
        "Event UDAF.6
        An ACK control character has been transmitted to POS."
    ::= { udafEventsGroup 6 }

udaf6-interface OBJECT-TYPE
    SYNTAX DisplayString
    MAX-ACCESS accessible-for-notify
    STATUS current
    DESCRIPTION
        "Parameter 'interface' in event UDAF.6"
    ::= { udafEventObjects6 1 }

udaf6-state OBJECT-TYPE
    SYNTAX Integer32
    MAX-ACCESS accessible-for-notify
    STATUS current
    DESCRIPTION
        "Parameter 'state' in event UDAF.6"
    ::= { udafEventObjects6 2 }

udafEventObjects7 OBJECT-IDENTITY
    STATUS current
    DESCRIPTION
        "Event UDAF.7
        An EOT control character has been transmitted to POS."
    ::= { udafEventsGroup 7 }

udaf7-interface OBJECT-TYPE
    SYNTAX DisplayString
    MAX-ACCESS accessible-for-notify
    STATUS current
    DESCRIPTION
        "Parameter 'interface' in event UDAF.7"
    ::= { udafEventObjects7 1 }

udaf7-state OBJECT-TYPE
    SYNTAX Integer32
    MAX-ACCESS accessible-for-notify
    STATUS current
    DESCRIPTION
        "Parameter 'state' in event UDAF.7"
    ::= { udafEventObjects7 2 }

udafEventObjects8 OBJECT-IDENTITY
    STATUS current
    DESCRIPTION
        "Event UDAF.8
        A NAK control character has been transmitted to POS."
    ::= { udafEventsGroup 8 }

udaf8-interface OBJECT-TYPE
    SYNTAX DisplayString
    MAX-ACCESS accessible-for-notify
    STATUS current
    DESCRIPTION
        "Parameter 'interface' in event UDAF.8"
    ::= { udafEventObjects8 1 }

udaf8-state OBJECT-TYPE
    SYNTAX Integer32
    MAX-ACCESS accessible-for-notify
    STATUS current
    DESCRIPTION
        "Parameter 'state' in event UDAF.8"
    ::= { udafEventObjects8 2 }

udafEventObjects9 OBJECT-IDENTITY
    STATUS current
    DESCRIPTION
        "Event UDAF.9
        An S message was expected and it has not been received properly."
    ::= { udafEventsGroup 9 }

udaf9-interface OBJECT-TYPE
    SYNTAX DisplayString
    MAX-ACCESS accessible-for-notify
    STATUS current
    DESCRIPTION
        "Parameter 'interface' in event UDAF.9"
    ::= { udafEventObjects9 1 }

udafEventObjects10 OBJECT-IDENTITY
    STATUS current
    DESCRIPTION
        "Event UDAF.10
        NA received from POS is not included in configuration profile list."
    ::= { udafEventsGroup 10 }

udaf10-na OBJECT-TYPE
    SYNTAX DisplayString
    MAX-ACCESS accessible-for-notify
    STATUS current
    DESCRIPTION
        "Parameter 'na' in event UDAF.10"
    ::= { udafEventObjects10 1 }

udaf10-interface OBJECT-TYPE
    SYNTAX DisplayString
    MAX-ACCESS accessible-for-notify
    STATUS current
    DESCRIPTION
        "Parameter 'interface' in event UDAF.10"
    ::= { udafEventObjects10 2 }

udafEventObjects11 OBJECT-IDENTITY
    STATUS current
    DESCRIPTION
        "Event UDAF.11
        The specified NA is trying the connection against IP Host and P port,
        using the specified transport protocol."
    ::= { udafEventsGroup 11 }

udaf11-na OBJECT-TYPE
    SYNTAX DisplayString
    MAX-ACCESS accessible-for-notify
    STATUS current
    DESCRIPTION
        "Parameter 'na' in event UDAF.11"
    ::= { udafEventObjects11 1 }

udaf11-transport OBJECT-TYPE
    SYNTAX DisplayString
    MAX-ACCESS accessible-for-notify
    STATUS current
    DESCRIPTION
        "Parameter 'transport' in event UDAF.11"
    ::= { udafEventObjects11 2 }

udaf11-ip-host-address OBJECT-TYPE
    SYNTAX IpAddress
    MAX-ACCESS accessible-for-notify
    STATUS current
    DESCRIPTION
        "Parameter 'ip-host-address' in event UDAF.11"
    ::= { udafEventObjects11 3 }

udaf11-port OBJECT-TYPE
    SYNTAX Integer32
    MAX-ACCESS accessible-for-notify
    STATUS current
    DESCRIPTION
        "Parameter 'port' in event UDAF.11"
    ::= { udafEventObjects11 4 }

udaf11-interface OBJECT-TYPE
    SYNTAX DisplayString
    MAX-ACCESS accessible-for-notify
    STATUS current
    DESCRIPTION
        "Parameter 'interface' in event UDAF.11"
    ::= { udafEventObjects11 5 }

udafEventObjects12 OBJECT-IDENTITY
    STATUS current
    DESCRIPTION
        "Event UDAF.12
        The connection against Host has failed."
    ::= { udafEventsGroup 12 }

udaf12-interface OBJECT-TYPE
    SYNTAX DisplayString
    MAX-ACCESS accessible-for-notify
    STATUS current
    DESCRIPTION
        "Parameter 'interface' in event UDAF.12"
    ::= { udafEventObjects12 1 }

udafEventObjects13 OBJECT-IDENTITY
    STATUS current
    DESCRIPTION
        "Event UDAF.13
        The transaction has been completed successfully."
    ::= { udafEventsGroup 13 }

udaf13-interface OBJECT-TYPE
    SYNTAX DisplayString
    MAX-ACCESS accessible-for-notify
    STATUS current
    DESCRIPTION
        "Parameter 'interface' in event UDAF.13"
    ::= { udafEventObjects13 1 }

udafEventObjects14 OBJECT-IDENTITY
    STATUS current
    DESCRIPTION
        "Event UDAF.14
        Trying to send message to Host."
    ::= { udafEventsGroup 14 }

udaf14-message-type OBJECT-TYPE
    SYNTAX DisplayString
    MAX-ACCESS accessible-for-notify
    STATUS current
    DESCRIPTION
        "Parameter 'message-type' in event UDAF.14"
    ::= { udafEventObjects14 1 }

udaf14-bytes-number OBJECT-TYPE
    SYNTAX Integer32
    MAX-ACCESS accessible-for-notify
    STATUS current
    DESCRIPTION
        "Parameter 'bytes-number' in event UDAF.14"
    ::= { udafEventObjects14 2 }

udaf14-interface OBJECT-TYPE
    SYNTAX DisplayString
    MAX-ACCESS accessible-for-notify
    STATUS current
    DESCRIPTION
        "Parameter 'interface' in event UDAF.14"
    ::= { udafEventObjects14 3 }

udafEventObjects15 OBJECT-IDENTITY
    STATUS current
    DESCRIPTION
        "Event UDAF.15
        A TRMTP message has been received."
    ::= { udafEventsGroup 15 }

udaf15-message-type OBJECT-TYPE
    SYNTAX DisplayString
    MAX-ACCESS accessible-for-notify
    STATUS current
    DESCRIPTION
        "Parameter 'message-type' in event UDAF.15"
    ::= { udafEventObjects15 1 }

udaf15-bytes-number OBJECT-TYPE
    SYNTAX Integer32
    MAX-ACCESS accessible-for-notify
    STATUS current
    DESCRIPTION
        "Parameter 'bytes-number' in event UDAF.15"
    ::= { udafEventObjects15 2 }

udaf15-interface OBJECT-TYPE
    SYNTAX DisplayString
    MAX-ACCESS accessible-for-notify
    STATUS current
    DESCRIPTION
        "Parameter 'interface' in event UDAF.15"
    ::= { udafEventObjects15 3 }

udaf15-state OBJECT-TYPE
    SYNTAX Integer32
    MAX-ACCESS accessible-for-notify
    STATUS current
    DESCRIPTION
        "Parameter 'state' in event UDAF.15"
    ::= { udafEventObjects15 4 }

udafEventObjects16 OBJECT-IDENTITY
    STATUS current
    DESCRIPTION
        "Event UDAF.16
        Trying TRMTP message retransmission."
    ::= { udafEventsGroup 16 }

udaf16-interface OBJECT-TYPE
    SYNTAX DisplayString
    MAX-ACCESS accessible-for-notify
    STATUS current
    DESCRIPTION
        "Parameter 'interface' in event UDAF.16"
    ::= { udafEventObjects16 1 }

udafEventObjects17 OBJECT-IDENTITY
    STATUS current
    DESCRIPTION
        "Event UDAF.17
        Trying retransmission to POS."
    ::= { udafEventsGroup 17 }

udaf17-interface OBJECT-TYPE
    SYNTAX DisplayString
    MAX-ACCESS accessible-for-notify
    STATUS current
    DESCRIPTION
        "Parameter 'interface' in event UDAF.17"
    ::= { udafEventObjects17 1 }

udafEventObjects18 OBJECT-IDENTITY
    STATUS current
    DESCRIPTION
        "Event UDAF.18
        A certain error was found."
    ::= { udafEventsGroup 18 }

udaf18-error-message OBJECT-TYPE
    SYNTAX DisplayString
    MAX-ACCESS accessible-for-notify
    STATUS current
    DESCRIPTION
        "Parameter 'error-message' in event UDAF.18"
    ::= { udafEventObjects18 1 }

udaf18-interface OBJECT-TYPE
    SYNTAX DisplayString
    MAX-ACCESS accessible-for-notify
    STATUS current
    DESCRIPTION
        "Parameter 'interface' in event UDAF.18"
    ::= { udafEventObjects18 2 }

udaf18-state OBJECT-TYPE
    SYNTAX Integer32
    MAX-ACCESS accessible-for-notify
    STATUS current
    DESCRIPTION
        "Parameter 'state' in event UDAF.18"
    ::= { udafEventObjects18 3 }

udafEventObjects19 OBJECT-IDENTITY
    STATUS current
    DESCRIPTION
        "Event UDAF.19
        A message from HOST has been received."
    ::= { udafEventsGroup 19 }

udaf19-message-type OBJECT-TYPE
    SYNTAX DisplayString
    MAX-ACCESS accessible-for-notify
    STATUS current
    DESCRIPTION
        "Parameter 'message-type' in event UDAF.19"
    ::= { udafEventObjects19 1 }

udaf19-bytes-number OBJECT-TYPE
    SYNTAX Integer32
    MAX-ACCESS accessible-for-notify
    STATUS current
    DESCRIPTION
        "Parameter 'bytes-number' in event UDAF.19"
    ::= { udafEventObjects19 2 }

udaf19-interface OBJECT-TYPE
    SYNTAX DisplayString
    MAX-ACCESS accessible-for-notify
    STATUS current
    DESCRIPTION
        "Parameter 'interface' in event UDAF.19"
    ::= { udafEventObjects19 3 }

udaf19-state OBJECT-TYPE
    SYNTAX Integer32
    MAX-ACCESS accessible-for-notify
    STATUS current
    DESCRIPTION
        "Parameter 'state' in event UDAF.19"
    ::= { udafEventObjects19 4 }

udafEventObjects20 OBJECT-IDENTITY
    STATUS current
    DESCRIPTION
        "Event UDAF.20
        A TCP packet has been received."
    ::= { udafEventsGroup 20 }

udaf20-message-type OBJECT-TYPE
    SYNTAX DisplayString
    MAX-ACCESS accessible-for-notify
    STATUS current
    DESCRIPTION
        "Parameter 'message-type' in event UDAF.20"
    ::= { udafEventObjects20 1 }

udaf20-bytes-number OBJECT-TYPE
    SYNTAX Integer32
    MAX-ACCESS accessible-for-notify
    STATUS current
    DESCRIPTION
        "Parameter 'bytes-number' in event UDAF.20"
    ::= { udafEventObjects20 2 }

udaf20-interface OBJECT-TYPE
    SYNTAX DisplayString
    MAX-ACCESS accessible-for-notify
    STATUS current
    DESCRIPTION
        "Parameter 'interface' in event UDAF.20"
    ::= { udafEventObjects20 3 }

udaf20-state OBJECT-TYPE
    SYNTAX Integer32
    MAX-ACCESS accessible-for-notify
    STATUS current
    DESCRIPTION
        "Parameter 'state' in event UDAF.20"
    ::= { udafEventObjects20 4 }

udafEventObjects21 OBJECT-IDENTITY
    STATUS current
    DESCRIPTION
        "Event UDAF.21
        The TCP session has been closed."
    ::= { udafEventsGroup 21 }

udaf21-interface OBJECT-TYPE
    SYNTAX DisplayString
    MAX-ACCESS accessible-for-notify
    STATUS current
    DESCRIPTION
        "Parameter 'interface' in event UDAF.21"
    ::= { udafEventObjects21 1 }

udaf21-state OBJECT-TYPE
    SYNTAX Integer32
    MAX-ACCESS accessible-for-notify
    STATUS current
    DESCRIPTION
        "Parameter 'state' in event UDAF.21"
    ::= { udafEventObjects21 2 }

udafEventObjects22 OBJECT-IDENTITY
    STATUS current
    DESCRIPTION
        "Event UDAF.22
        The TCP session has been closed by the remote HOST."
    ::= { udafEventsGroup 22 }

udaf22-interface OBJECT-TYPE
    SYNTAX DisplayString
    MAX-ACCESS accessible-for-notify
    STATUS current
    DESCRIPTION
        "Parameter 'interface' in event UDAF.22"
    ::= { udafEventObjects22 1 }

udaf22-state OBJECT-TYPE
    SYNTAX Integer32
    MAX-ACCESS accessible-for-notify
    STATUS current
    DESCRIPTION
        "Parameter 'state' in event UDAF.22"
    ::= { udafEventObjects22 2 }

udafEventObjects23 OBJECT-IDENTITY
    STATUS current
    DESCRIPTION
        "Event UDAF.23
        A TCP session has been opened by the remote HOST."
    ::= { udafEventsGroup 23 }

udaf23-interface OBJECT-TYPE
    SYNTAX DisplayString
    MAX-ACCESS accessible-for-notify
    STATUS current
    DESCRIPTION
        "Parameter 'interface' in event UDAF.23"
    ::= { udafEventObjects23 1 }

udaf23-state OBJECT-TYPE
    SYNTAX Integer32
    MAX-ACCESS accessible-for-notify
    STATUS current
    DESCRIPTION
        "Parameter 'state' in event UDAF.23"
    ::= { udafEventObjects23 2 }

udafEventObjects24 OBJECT-IDENTITY
    STATUS current
    DESCRIPTION
        "Event UDAF.24
        A message has been transmitted to POS."
    ::= { udafEventsGroup 24 }

udaf24-message-type OBJECT-TYPE
    SYNTAX DisplayString
    MAX-ACCESS accessible-for-notify
    STATUS current
    DESCRIPTION
        "Parameter 'message-type' in event UDAF.24"
    ::= { udafEventObjects24 1 }

udaf24-bytes-number OBJECT-TYPE
    SYNTAX Integer32
    MAX-ACCESS accessible-for-notify
    STATUS current
    DESCRIPTION
        "Parameter 'bytes-number' in event UDAF.24"
    ::= { udafEventObjects24 2 }

udaf24-interface OBJECT-TYPE
    SYNTAX DisplayString
    MAX-ACCESS accessible-for-notify
    STATUS current
    DESCRIPTION
        "Parameter 'interface' in event UDAF.24"
    ::= { udafEventObjects24 3 }

udaf24-state OBJECT-TYPE
    SYNTAX Integer32
    MAX-ACCESS accessible-for-notify
    STATUS current
    DESCRIPTION
        "Parameter 'state' in event UDAF.24"
    ::= { udafEventObjects24 4 }

udafEventObjects25 OBJECT-IDENTITY
    STATUS current
    DESCRIPTION
        "Event UDAF.25
        One OK message has been received from POS."
    ::= { udafEventsGroup 25 }

udaf25-message-type OBJECT-TYPE
    SYNTAX DisplayString
    MAX-ACCESS accessible-for-notify
    STATUS current
    DESCRIPTION
        "Parameter 'message-type' in event UDAF.25"
    ::= { udafEventObjects25 1 }

udaf25-bytes-number OBJECT-TYPE
    SYNTAX Integer32
    MAX-ACCESS accessible-for-notify
    STATUS current
    DESCRIPTION
        "Parameter 'bytes-number' in event UDAF.25"
    ::= { udafEventObjects25 2 }

udaf25-interface OBJECT-TYPE
    SYNTAX DisplayString
    MAX-ACCESS accessible-for-notify
    STATUS current
    DESCRIPTION
        "Parameter 'interface' in event UDAF.25"
    ::= { udafEventObjects25 3 }

udaf25-state OBJECT-TYPE
    SYNTAX Integer32
    MAX-ACCESS accessible-for-notify
    STATUS current
    DESCRIPTION
        "Parameter 'state' in event UDAF.25"
    ::= { udafEventObjects25 4 }

udafEventObjects26 OBJECT-IDENTITY
    STATUS current
    DESCRIPTION
        "Event UDAF.26
        One Bad message has been received from POS."
    ::= { udafEventsGroup 26 }

udaf26-interface OBJECT-TYPE
    SYNTAX DisplayString
    MAX-ACCESS accessible-for-notify
    STATUS current
    DESCRIPTION
        "Parameter 'interface' in event UDAF.26"
    ::= { udafEventObjects26 1 }

udaf26-state OBJECT-TYPE
    SYNTAX Integer32
    MAX-ACCESS accessible-for-notify
    STATUS current
    DESCRIPTION
        "Parameter 'state' in event UDAF.26"
    ::= { udafEventObjects26 2 }

udafEventObjects27 OBJECT-IDENTITY
    STATUS current
    DESCRIPTION
        "Event UDAF.27
        A change ON/OFF has been detected in Serial Control Signal Input."
    ::= { udafEventsGroup 27 }

udaf27-new-on-off-status OBJECT-TYPE
    SYNTAX DisplayString
    MAX-ACCESS accessible-for-notify
    STATUS current
    DESCRIPTION
        "Parameter 'new-on-off-status' in event UDAF.27"
    ::= { udafEventObjects27 1 }

udaf27-interface OBJECT-TYPE
    SYNTAX DisplayString
    MAX-ACCESS accessible-for-notify
    STATUS current
    DESCRIPTION
        "Parameter 'interface' in event UDAF.27"
    ::= { udafEventObjects27 2 }

udaf27-state OBJECT-TYPE
    SYNTAX Integer32
    MAX-ACCESS accessible-for-notify
    STATUS current
    DESCRIPTION
        "Parameter 'state' in event UDAF.27"
    ::= { udafEventObjects27 3 }

udafEventObjects28 OBJECT-IDENTITY
    STATUS current
    DESCRIPTION
        "Event UDAF.28
        An ENQ control character has been transmitted to POS."
    ::= { udafEventsGroup 28 }

udaf28-interface OBJECT-TYPE
    SYNTAX DisplayString
    MAX-ACCESS accessible-for-notify
    STATUS current
    DESCRIPTION
        "Parameter 'interface' in event UDAF.28"
    ::= { udafEventObjects28 1 }

udaf28-state OBJECT-TYPE
    SYNTAX Integer32
    MAX-ACCESS accessible-for-notify
    STATUS current
    DESCRIPTION
        "Parameter 'state' in event UDAF.28"
    ::= { udafEventObjects28 2 }

udafEventObjects29 OBJECT-IDENTITY
    STATUS current
    DESCRIPTION
        "Event UDAF.29
        Timeout has occur waiting data from POS."
    ::= { udafEventsGroup 29 }

udaf29-interface OBJECT-TYPE
    SYNTAX DisplayString
    MAX-ACCESS accessible-for-notify
    STATUS current
    DESCRIPTION
        "Parameter 'interface' in event UDAF.29"
    ::= { udafEventObjects29 1 }

udaf29-state OBJECT-TYPE
    SYNTAX Integer32
    MAX-ACCESS accessible-for-notify
    STATUS current
    DESCRIPTION
        "Parameter 'state' in event UDAF.29"
    ::= { udafEventObjects29 2 }

udafEventObjects30 OBJECT-IDENTITY
    STATUS current
    DESCRIPTION
        "Event UDAF.30
        Trying to send a Release message to X25 Gateway."
    ::= { udafEventsGroup 30 }

udaf30-interface OBJECT-TYPE
    SYNTAX DisplayString
    MAX-ACCESS accessible-for-notify
    STATUS current
    DESCRIPTION
        "Parameter 'interface' in event UDAF.30"
    ::= { udafEventObjects30 1 }

udaf30-state OBJECT-TYPE
    SYNTAX Integer32
    MAX-ACCESS accessible-for-notify
    STATUS current
    DESCRIPTION
        "Parameter 'state' in event UDAF.30"
    ::= { udafEventObjects30 2 }

udafEventObjects31 OBJECT-IDENTITY
    STATUS current
    DESCRIPTION
        "Event UDAF.31
        A message from POS has been received."
    ::= { udafEventsGroup 31 }

udaf31-message-type OBJECT-TYPE
    SYNTAX DisplayString
    MAX-ACCESS accessible-for-notify
    STATUS current
    DESCRIPTION
        "Parameter 'message-type' in event UDAF.31"
    ::= { udafEventObjects31 1 }

udaf31-interface OBJECT-TYPE
    SYNTAX DisplayString
    MAX-ACCESS accessible-for-notify
    STATUS current
    DESCRIPTION
        "Parameter 'interface' in event UDAF.31"
    ::= { udafEventObjects31 2 }

udaf31-state OBJECT-TYPE
    SYNTAX Integer32
    MAX-ACCESS accessible-for-notify
    STATUS current
    DESCRIPTION
        "Parameter 'state' in event UDAF.31"
    ::= { udafEventObjects31 3 }

udafEventObjects32 OBJECT-IDENTITY
    STATUS current
    DESCRIPTION
        "Event UDAF.32
        A packet was lost, due to TCP Tx overrun error."
    ::= { udafEventsGroup 32 }

udaf32-interface OBJECT-TYPE
    SYNTAX DisplayString
    MAX-ACCESS accessible-for-notify
    STATUS current
    DESCRIPTION
        "Parameter 'interface' in event UDAF.32"
    ::= { udafEventObjects32 1 }

udaf32-state OBJECT-TYPE
    SYNTAX Integer32
    MAX-ACCESS accessible-for-notify
    STATUS current
    DESCRIPTION
        "Parameter 'state' in event UDAF.32"
    ::= { udafEventObjects32 2 }

udafEventObjects33 OBJECT-IDENTITY
    STATUS current
    DESCRIPTION
        "Event UDAF.33
        Transaction against the destination whose NA and IP address are shown
        went wrong because of the indicated cause."
    ::= { udafEventsGroup 33 }

udaf33-na OBJECT-TYPE
    SYNTAX DisplayString
    MAX-ACCESS accessible-for-notify
    STATUS current
    DESCRIPTION
        "Parameter 'na' in event UDAF.33"
    ::= { udafEventObjects33 1 }

udaf33-ip-host-address OBJECT-TYPE
    SYNTAX IpAddress
    MAX-ACCESS accessible-for-notify
    STATUS current
    DESCRIPTION
        "Parameter 'ip-host-address' in event UDAF.33"
    ::= { udafEventObjects33 2 }

udaf33-cause OBJECT-TYPE
    SYNTAX Integer32
    MAX-ACCESS accessible-for-notify
    STATUS current
    DESCRIPTION
        "Parameter 'cause' in event UDAF.33"
    ::= { udafEventObjects33 3 }

udaf33-interface OBJECT-TYPE
    SYNTAX DisplayString
    MAX-ACCESS accessible-for-notify
    STATUS current
    DESCRIPTION
        "Parameter 'interface' in event UDAF.33"
    ::= { udafEventObjects33 4 }

udafEventObjects34 OBJECT-IDENTITY
    STATUS current
    DESCRIPTION
        "Event UDAF.34
        Transmission process is busy at new transaction start."
    ::= { udafEventsGroup 34 }

udaf34-interface OBJECT-TYPE
    SYNTAX DisplayString
    MAX-ACCESS accessible-for-notify
    STATUS current
    DESCRIPTION
        "Parameter 'interface' in event UDAF.34"
    ::= { udafEventObjects34 1 }

udaf34-state OBJECT-TYPE
    SYNTAX Integer32
    MAX-ACCESS accessible-for-notify
    STATUS current
    DESCRIPTION
        "Parameter 'state' in event UDAF.34"
    ::= { udafEventObjects34 2 }

udafEventObjects35 OBJECT-IDENTITY
    STATUS current
    DESCRIPTION
        "Event UDAF.35
        The TCP session has been closed due to inactivity timeout."
    ::= { udafEventsGroup 35 }

udaf35-interface OBJECT-TYPE
    SYNTAX DisplayString
    MAX-ACCESS accessible-for-notify
    STATUS current
    DESCRIPTION
        "Parameter 'interface' in event UDAF.35"
    ::= { udafEventObjects35 1 }

udaf35-state OBJECT-TYPE
    SYNTAX Integer32
    MAX-ACCESS accessible-for-notify
    STATUS current
    DESCRIPTION
        "Parameter 'state' in event UDAF.35"
    ::= { udafEventObjects35 2 }

udafEventObjects36 OBJECT-IDENTITY
    STATUS current
    DESCRIPTION
        "Event UDAF.36
        Data is received from POS, but the service is suspended by operator."
    ::= { udafEventsGroup 36 }

udaf36-bytes-number OBJECT-TYPE
    SYNTAX Integer32
    MAX-ACCESS accessible-for-notify
    STATUS current
    DESCRIPTION
        "Parameter 'bytes-number' in event UDAF.36"
    ::= { udafEventObjects36 1 }

udaf36-interface OBJECT-TYPE
    SYNTAX DisplayString
    MAX-ACCESS accessible-for-notify
    STATUS current
    DESCRIPTION
        "Parameter 'interface' in event UDAF.36"
    ::= { udafEventObjects36 2 }

udafEventObjects37 OBJECT-IDENTITY
    STATUS current
    DESCRIPTION
        "Event UDAF.37
        PAD has established X.25 connection with HOST."
    ::= { udafEventsGroup 37 }

udaf37-interface OBJECT-TYPE
    SYNTAX DisplayString
    MAX-ACCESS accessible-for-notify
    STATUS current
    DESCRIPTION
        "Parameter 'interface' in event UDAF.37"
    ::= { udafEventObjects37 1 }

udaf37-state OBJECT-TYPE
    SYNTAX Integer32
    MAX-ACCESS accessible-for-notify
    STATUS current
    DESCRIPTION
        "Parameter 'state' in event UDAF.37"
    ::= { udafEventObjects37 2 }

udafEventObjects38 OBJECT-IDENTITY
    STATUS current
    DESCRIPTION
        "Event UDAF.38
        Timeout has occur waiting data from HOST."
    ::= { udafEventsGroup 38 }

udaf38-interface OBJECT-TYPE
    SYNTAX DisplayString
    MAX-ACCESS accessible-for-notify
    STATUS current
    DESCRIPTION
        "Parameter 'interface' in event UDAF.38"
    ::= { udafEventObjects38 1 }

udaf38-state OBJECT-TYPE
    SYNTAX Integer32
    MAX-ACCESS accessible-for-notify
    STATUS current
    DESCRIPTION
        "Parameter 'state' in event UDAF.38"
    ::= { udafEventObjects38 2 }

udafEventObjects39 OBJECT-IDENTITY
    STATUS current
    DESCRIPTION
        "Event UDAF.39
        Release message was received from X25 Gateway."
    ::= { udafEventsGroup 39 }

udaf39-interface OBJECT-TYPE
    SYNTAX DisplayString
    MAX-ACCESS accessible-for-notify
    STATUS current
    DESCRIPTION
        "Parameter 'interface' in event UDAF.39"
    ::= { udafEventObjects39 1 }

udaf39-state OBJECT-TYPE
    SYNTAX Integer32
    MAX-ACCESS accessible-for-notify
    STATUS current
    DESCRIPTION
        "Parameter 'state' in event UDAF.39"
    ::= { udafEventObjects39 2 }

udafEventObjects40 OBJECT-IDENTITY
    STATUS current
    DESCRIPTION
        "Event UDAF.40
        A change ON/OFF has been made in Serial Control Signal Output."
    ::= { udafEventsGroup 40 }

udaf40-new-on-off-status OBJECT-TYPE
    SYNTAX DisplayString
    MAX-ACCESS accessible-for-notify
    STATUS current
    DESCRIPTION
        "Parameter 'new-on-off-status' in event UDAF.40"
    ::= { udafEventObjects40 1 }

udaf40-interface OBJECT-TYPE
    SYNTAX DisplayString
    MAX-ACCESS accessible-for-notify
    STATUS current
    DESCRIPTION
        "Parameter 'interface' in event UDAF.40"
    ::= { udafEventObjects40 2 }

udaf40-state OBJECT-TYPE
    SYNTAX Integer32
    MAX-ACCESS accessible-for-notify
    STATUS current
    DESCRIPTION
        "Parameter 'state' in event UDAF.40"
    ::= { udafEventObjects40 3 }

udafEventObjects41 OBJECT-IDENTITY
    STATUS current
    DESCRIPTION
        "Event UDAF.41
        A message (whose type is shown) has been transmitted to Host."
    ::= { udafEventsGroup 41 }

udaf41-message-type OBJECT-TYPE
    SYNTAX DisplayString
    MAX-ACCESS accessible-for-notify
    STATUS current
    DESCRIPTION
        "Parameter 'message-type' in event UDAF.41"
    ::= { udafEventObjects41 1 }

udaf41-bytes-number OBJECT-TYPE
    SYNTAX Integer32
    MAX-ACCESS accessible-for-notify
    STATUS current
    DESCRIPTION
        "Parameter 'bytes-number' in event UDAF.41"
    ::= { udafEventObjects41 2 }

udaf41-interface OBJECT-TYPE
    SYNTAX DisplayString
    MAX-ACCESS accessible-for-notify
    STATUS current
    DESCRIPTION
        "Parameter 'interface' in event UDAF.41"
    ::= { udafEventObjects41 3 }

udaf41-state OBJECT-TYPE
    SYNTAX Integer32
    MAX-ACCESS accessible-for-notify
    STATUS current
    DESCRIPTION
        "Parameter 'state' in event UDAF.41"
    ::= { udafEventObjects41 4 }


udafNotification1 NOTIFICATION-TYPE
    OBJECTS { 
              udaf1-bytes-number, 
              udaf1-interface 
            }
    STATUS current
    DESCRIPTION
        "Notification of Event UDAF.1

        Message: 'Rx Data from POS, $1 bytes, interface $2'

        Parameters list:
              $1: udaf1-bytes-number
              $2: udaf1-interface

        Data has been received from POS."
    ::= { udafNotificationsPrefix 1 }

udafNotification2 NOTIFICATION-TYPE
    OBJECTS { 
              udaf2-interface, 
              udaf2-state 
            }
    STATUS current
    DESCRIPTION
        "Notification of Event UDAF.2

        Message: 'Rx ACK control character from POS, interface $1, state $2'

        Parameters list:
              $1: udaf2-interface
              $2: udaf2-state

        An ACK control character has been received from POS."
    ::= { udafNotificationsPrefix 2 }

udafNotification3 NOTIFICATION-TYPE
    OBJECTS { 
              udaf3-interface, 
              udaf3-state 
            }
    STATUS current
    DESCRIPTION
        "Notification of Event UDAF.3

        Message: 'Rx EOT control character from POS, interface $1, state $2'

        Parameters list:
              $1: udaf3-interface
              $2: udaf3-state

        An EOT control character has been received from POS."
    ::= { udafNotificationsPrefix 3 }

udafNotification4 NOTIFICATION-TYPE
    OBJECTS { 
              udaf4-interface, 
              udaf4-state 
            }
    STATUS current
    DESCRIPTION
        "Notification of Event UDAF.4

        Message: 'Rx NAK control character from POS, interface $1, state $2'

        Parameters list:
              $1: udaf4-interface
              $2: udaf4-state

        A NAK control character has been received from POS."
    ::= { udafNotificationsPrefix 4 }

udafNotification5 NOTIFICATION-TYPE
    OBJECTS { 
              udaf5-interface 
            }
    STATUS current
    DESCRIPTION
        "Notification of Event UDAF.5

        Message: 'A block with LRC/CRC error has been received from POS, interface $1'

        Parameters list:
              $1: udaf5-interface

        A block with parity error has been received from POS."
    ::= { udafNotificationsPrefix 5 }

udafNotification6 NOTIFICATION-TYPE
    OBJECTS { 
              udaf6-interface, 
              udaf6-state 
            }
    STATUS current
    DESCRIPTION
        "Notification of Event UDAF.6

        Message: 'Tx ACK control character to POS, interface $1, state $2'

        Parameters list:
              $1: udaf6-interface
              $2: udaf6-state

        An ACK control character has been transmitted to POS."
    ::= { udafNotificationsPrefix 6 }

udafNotification7 NOTIFICATION-TYPE
    OBJECTS { 
              udaf7-interface, 
              udaf7-state 
            }
    STATUS current
    DESCRIPTION
        "Notification of Event UDAF.7

        Message: 'Tx EOT control character to POS, interface $1, state $2'

        Parameters list:
              $1: udaf7-interface
              $2: udaf7-state

        An EOT control character has been transmitted to POS."
    ::= { udafNotificationsPrefix 7 }

udafNotification8 NOTIFICATION-TYPE
    OBJECTS { 
              udaf8-interface, 
              udaf8-state 
            }
    STATUS current
    DESCRIPTION
        "Notification of Event UDAF.8

        Message: 'Tx NAK control character to POS, interface $1, state $2'

        Parameters list:
              $1: udaf8-interface
              $2: udaf8-state

        A NAK control character has been transmitted to POS."
    ::= { udafNotificationsPrefix 8 }

udafNotification9 NOTIFICATION-TYPE
    OBJECTS { 
              udaf9-interface 
            }
    STATUS current
    DESCRIPTION
        "Notification of Event UDAF.9

        Message: 'An S message was expected and it has not been received properly. Interface $1'

        Parameters list:
              $1: udaf9-interface

        An S message was expected and it has not been received properly."
    ::= { udafNotificationsPrefix 9 }

udafNotification10 NOTIFICATION-TYPE
    OBJECTS { 
              udaf10-na, 
              udaf10-interface 
            }
    STATUS current
    DESCRIPTION
        "Notification of Event UDAF.10

        Message: 'NA $1 received from POS is not included in configuration profile list. Interface $2'

        Parameters list:
              $1: udaf10-na
              $2: udaf10-interface

        NA received from POS is not included in configuration profile list."
    ::= { udafNotificationsPrefix 10 }

udafNotification11 NOTIFICATION-TYPE
    OBJECTS { 
              udaf11-na, 
              udaf11-transport,
              udaf11-ip-host-address,
              udaf11-port,
              udaf11-interface 
            }
    STATUS current
    DESCRIPTION
        "Notification of Event UDAF.11

        Message: 'NA $1 is trying the connection $2, against IP $3 Host, Port $4, Interface $5'

        Parameters list:
              $1: udaf11-na
              $2: udaf11-transport
              $3: udaf11-ip-host-address
              $4: udaf11-port
              $5: udaf11-interface

        The specified NA is trying the connection against IP Host and P port,
        using the specified transport protocol."
    ::= { udafNotificationsPrefix 11 }

udafNotification12 NOTIFICATION-TYPE
    OBJECTS { 
              udaf12-interface 
            }
    STATUS current
    DESCRIPTION
        "Notification of Event UDAF.12

        Message: 'The connection against Host has failed. Interface $1'

        Parameters list:
              $1: udaf12-interface

        The connection against Host has failed."
    ::= { udafNotificationsPrefix 12 }

udafNotification13 NOTIFICATION-TYPE
    OBJECTS { 
              udaf13-interface 
            }
    STATUS current
    DESCRIPTION
        "Notification of Event UDAF.13

        Message: 'The transaction has been completed successfully. Interface $1'

        Parameters list:
              $1: udaf13-interface

        The transaction has been completed successfully."
    ::= { udafNotificationsPrefix 13 }

udafNotification14 NOTIFICATION-TYPE
    OBJECTS { 
              udaf14-message-type, 
              udaf14-bytes-number,
              udaf14-interface 
            }
    STATUS current
    DESCRIPTION
        "Notification of Event UDAF.14

        Message: 'Trying to send $1 message to Host with $2 bytes. Interface $3'

        Parameters list:
              $1: udaf14-message-type
              $2: udaf14-bytes-number
              $3: udaf14-interface

        Trying to send message to Host."
    ::= { udafNotificationsPrefix 14 }

udafNotification15 NOTIFICATION-TYPE
    OBJECTS { 
              udaf15-message-type, 
              udaf15-bytes-number,
              udaf15-interface,
              udaf15-state 
            }
    STATUS current
    DESCRIPTION
        "Notification of Event UDAF.15

        Message: 'A TRMTP Message of $1 type has been received, $2 bytes. Interface $3, state $4'

        Parameters list:
              $1: udaf15-message-type
              $2: udaf15-bytes-number
              $3: udaf15-interface
              $4: udaf15-state

        A TRMTP message has been received."
    ::= { udafNotificationsPrefix 15 }

udafNotification16 NOTIFICATION-TYPE
    OBJECTS { 
              udaf16-interface 
            }
    STATUS current
    DESCRIPTION
        "Notification of Event UDAF.16

        Message: 'Trying TRMTP message Retransmission. Interface $1'

        Parameters list:
              $1: udaf16-interface

        Trying TRMTP message retransmission."
    ::= { udafNotificationsPrefix 16 }

udafNotification17 NOTIFICATION-TYPE
    OBJECTS { 
              udaf17-interface 
            }
    STATUS current
    DESCRIPTION
        "Notification of Event UDAF.17

        Message: 'Trying retransmission to POS. Interface $1'

        Parameters list:
              $1: udaf17-interface

        Trying retransmission to POS."
    ::= { udafNotificationsPrefix 17 }

udafNotification18 NOTIFICATION-TYPE
    OBJECTS { 
              udaf18-error-message, 
              udaf18-interface,
              udaf18-state 
            }
    STATUS current
    DESCRIPTION
        "Notification of Event UDAF.18

        Message: 'An Error $1 was found. Interface $2, state $3'

        Parameters list:
              $1: udaf18-error-message
              $2: udaf18-interface
              $3: udaf18-state

        A certain error was found."
    ::= { udafNotificationsPrefix 18 }

udafNotification19 NOTIFICATION-TYPE
    OBJECTS { 
              udaf19-message-type, 
              udaf19-bytes-number,
              udaf19-interface,
              udaf19-state 
            }
    STATUS current
    DESCRIPTION
        "Notification of Event UDAF.19

        Message: 'A message from HOST of $1 type has been received, $2 bytes. Interface $3, state $4'

        Parameters list:
              $1: udaf19-message-type
              $2: udaf19-bytes-number
              $3: udaf19-interface
              $4: udaf19-state

        A message from HOST has been received."
    ::= { udafNotificationsPrefix 19 }

udafNotification20 NOTIFICATION-TYPE
    OBJECTS { 
              udaf20-message-type, 
              udaf20-bytes-number,
              udaf20-interface,
              udaf20-state 
            }
    STATUS current
    DESCRIPTION
        "Notification of Event UDAF.20

        Message: 'A TCP Packet of $1 type has been received, $2 bytes. Interface $3, state $4'

        Parameters list:
              $1: udaf20-message-type
              $2: udaf20-bytes-number
              $3: udaf20-interface
              $4: udaf20-state

        A TCP packet has been received."
    ::= { udafNotificationsPrefix 20 }

udafNotification21 NOTIFICATION-TYPE
    OBJECTS { 
              udaf21-interface, 
              udaf21-state 
            }
    STATUS current
    DESCRIPTION
        "Notification of Event UDAF.21

        Message: 'The TCP session has been closed. Interface $1, state $2'

        Parameters list:
              $1: udaf21-interface
              $2: udaf21-state

        The TCP session has been closed."
    ::= { udafNotificationsPrefix 21 }

udafNotification22 NOTIFICATION-TYPE
    OBJECTS { 
              udaf22-interface, 
              udaf22-state 
            }
    STATUS current
    DESCRIPTION
        "Notification of Event UDAF.22

        Message: 'The TCP session has been closed by the remote HOST. Interface $1, state $2'

        Parameters list:
              $1: udaf22-interface
              $2: udaf22-state

        The TCP session has been closed by the remote HOST."
    ::= { udafNotificationsPrefix 22 }

udafNotification23 NOTIFICATION-TYPE
    OBJECTS { 
              udaf23-interface, 
              udaf23-state 
            }
    STATUS current
    DESCRIPTION
        "Notification of Event UDAF.23

        Message: 'The TCP session has been opened by the remote HOST. Interface $1, state $2'

        Parameters list:
              $1: udaf23-interface
              $2: udaf23-state

        A TCP session has been opened by the remote HOST."
    ::= { udafNotificationsPrefix 23 }

udafNotification24 NOTIFICATION-TYPE
    OBJECTS { 
              udaf24-message-type, 
              udaf24-bytes-number,
              udaf24-interface,
              udaf24-state 
            }
    STATUS current
    DESCRIPTION
        "Notification of Event UDAF.24

        Message: 'Tx $1 Message to POS, $2 bytes, interface $3 state $4'

        Parameters list:
              $1: udaf24-message-type
              $2: udaf24-bytes-number
              $3: udaf24-interface
              $4: udaf24-state

        A message has been transmitted to POS."
    ::= { udafNotificationsPrefix 24 }

udafNotification25 NOTIFICATION-TYPE
    OBJECTS { 
              udaf25-message-type, 
              udaf25-bytes-number,
              udaf25-interface,
              udaf25-state 
            }
    STATUS current
    DESCRIPTION
        "Notification of Event UDAF.25

        Message: 'Rx $1 Message from POS, $2 bytes, interface $3, state $4'

        Parameters list:
              $1: udaf25-message-type
              $2: udaf25-bytes-number
              $3: udaf25-interface
              $4: udaf25-state

        One OK message has been received from POS."
    ::= { udafNotificationsPrefix 25 }

udafNotification26 NOTIFICATION-TYPE
    OBJECTS { 
              udaf26-interface, 
              udaf26-state 
            }
    STATUS current
    DESCRIPTION
        "Notification of Event UDAF.26

        Message: 'Rx Bad Message from POS, interface $1, state $2'

        Parameters list:
              $1: udaf26-interface
              $2: udaf26-state

        One Bad message has been received from POS."
    ::= { udafNotificationsPrefix 26 }

udafNotification27 NOTIFICATION-TYPE
    OBJECTS { 
              udaf27-new-on-off-status, 
              udaf27-interface,
              udaf27-state 
            }
    STATUS current
    DESCRIPTION
        "Notification of Event UDAF.27

        Message: 'Serial Control Signal Input change to $1, interface $2, state $3'

        Parameters list:
              $1: udaf27-new-on-off-status
              $2: udaf27-interface
              $3: udaf27-state

        A change ON/OFF has been detected in Serial Control Signal Input."
    ::= { udafNotificationsPrefix 27 }

udafNotification28 NOTIFICATION-TYPE
    OBJECTS { 
              udaf28-interface, 
              udaf28-state 
            }
    STATUS current
    DESCRIPTION
        "Notification of Event UDAF.28

        Message: 'Tx ENQ control character to POS, interface $1, state $2'

        Parameters list:
              $1: udaf28-interface
              $2: udaf28-state

        An ENQ control character has been transmitted to POS."
    ::= { udafNotificationsPrefix 28 }

udafNotification29 NOTIFICATION-TYPE
    OBJECTS { 
              udaf29-interface, 
              udaf29-state 
            }
    STATUS current
    DESCRIPTION
        "Notification of Event UDAF.29

        Message: 'Timeout waiting data from POS, interface $1, state $2'

        Parameters list:
              $1: udaf29-interface
              $2: udaf29-state

        Timeout has occur waiting data from POS."
    ::= { udafNotificationsPrefix 29 }

udafNotification30 NOTIFICATION-TYPE
    OBJECTS { 
              udaf30-interface, 
              udaf30-state 
            }
    STATUS current
    DESCRIPTION
        "Notification of Event UDAF.30

        Message: 'Trying to send a Release message to X25 Gateway. Interface $1, state $2'

        Parameters list:
              $1: udaf30-interface
              $2: udaf30-state

        Trying to send a Release message to X25 Gateway."
    ::= { udafNotificationsPrefix 30 }

udafNotification31 NOTIFICATION-TYPE
    OBJECTS { 
              udaf31-message-type, 
              udaf31-interface,
              udaf31-state 
            }
    STATUS current
    DESCRIPTION
        "Notification of Event UDAF.31

        Message: 'A message from POS of $1 type has been received. Interface $2, state $3'

        Parameters list:
              $1: udaf31-message-type
              $2: udaf31-interface
              $3: udaf31-state

        A message from POS has been received."
    ::= { udafNotificationsPrefix 31 }

udafNotification32 NOTIFICATION-TYPE
    OBJECTS { 
              udaf32-interface, 
              udaf32-state 
            }
    STATUS current
    DESCRIPTION
        "Notification of Event UDAF.32

        Message: 'Packet lost due to TCP Tx overrun error. Interface $1, state $2'

        Parameters list:
              $1: udaf32-interface
              $2: udaf32-state

        A packet was lost, due to TCP Tx overrun error."
    ::= { udafNotificationsPrefix 32 }

udafNotification33 NOTIFICATION-TYPE
    OBJECTS { 
              udaf33-na, 
              udaf33-ip-host-address,
              udaf33-cause,
              udaf33-interface 
            }
    STATUS current
    DESCRIPTION
        "Notification of Event UDAF.33

        Message: 'The transaction has been wrong, against NA $1, IP $2, Cause $3, Interface $4'

        Parameters list:
              $1: udaf33-na
              $2: udaf33-ip-host-address
              $3: udaf33-cause
              $4: udaf33-interface

        Transaction against the destination whose NA and IP address are shown
        went wrong because of the indicated cause."
    ::= { udafNotificationsPrefix 33 }

udafNotification34 NOTIFICATION-TYPE
    OBJECTS { 
              udaf34-interface, 
              udaf34-state 
            }
    STATUS current
    DESCRIPTION
        "Notification of Event UDAF.34

        Message: 'Transmission process busy at transaction start. Interface $1, state $2'

        Parameters list:
              $1: udaf34-interface
              $2: udaf34-state

        Transmission process is busy at new transaction start."
    ::= { udafNotificationsPrefix 34 }

udafNotification35 NOTIFICATION-TYPE
    OBJECTS { 
              udaf35-interface, 
              udaf35-state 
            }
    STATUS current
    DESCRIPTION
        "Notification of Event UDAF.35

        Message: 'The TCP session has been closed due to inactivity timeout. Interface $1, state $2'

        Parameters list:
              $1: udaf35-interface
              $2: udaf35-state

        The TCP session has been closed due to inactivity timeout."
    ::= { udafNotificationsPrefix 35 }

udafNotification36 NOTIFICATION-TYPE
    OBJECTS { 
              udaf36-bytes-number, 
              udaf36-interface 
            }
    STATUS current
    DESCRIPTION
        "Notification of Event UDAF.36

        Message: 'Service is suspended when Rx Data from POS. $1 bytes, interface $2'

        Parameters list:
              $1: udaf36-bytes-number
              $2: udaf36-interface

        Data is received from POS, but the service is suspended by operator."
    ::= { udafNotificationsPrefix 36 }

udafNotification37 NOTIFICATION-TYPE
    OBJECTS { 
              udaf37-interface, 
              udaf37-state 
            }
    STATUS current
    DESCRIPTION
        "Notification of Event UDAF.37

        Message: 'Connection has been established with HOST. Interface $1, state $2'

        Parameters list:
              $1: udaf37-interface
              $2: udaf37-state

        PAD has established X.25 connection with HOST."
    ::= { udafNotificationsPrefix 37 }

udafNotification38 NOTIFICATION-TYPE
    OBJECTS { 
              udaf38-interface, 
              udaf38-state 
            }
    STATUS current
    DESCRIPTION
        "Notification of Event UDAF.38

        Message: 'Timeout waiting data from HOST, interface $1, state $2'

        Parameters list:
              $1: udaf38-interface
              $2: udaf38-state

        Timeout has occur waiting data from HOST."
    ::= { udafNotificationsPrefix 38 }

udafNotification39 NOTIFICATION-TYPE
    OBJECTS { 
              udaf39-interface, 
              udaf39-state 
            }
    STATUS current
    DESCRIPTION
        "Notification of Event UDAF.39

        Message: 'Release message was received from X25 Gateway. Interface $1, state $2'

        Parameters list:
              $1: udaf39-interface
              $2: udaf39-state

        Release message was received from X25 Gateway."
    ::= { udafNotificationsPrefix 39 }

udafNotification40 NOTIFICATION-TYPE
    OBJECTS { 
              udaf40-new-on-off-status, 
              udaf40-interface,
              udaf40-state 
            }
    STATUS current
    DESCRIPTION
        "Notification of Event UDAF.40

        Message: 'Serial Control Signal Output change to $1, interface $2, state $3'

        Parameters list:
              $1: udaf40-new-on-off-status
              $2: udaf40-interface
              $3: udaf40-state

        A change ON/OFF has been made in Serial Control Signal Output."
    ::= { udafNotificationsPrefix 40 }

udafNotification41 NOTIFICATION-TYPE
    OBJECTS { 
              udaf41-message-type, 
              udaf41-bytes-number,
              udaf41-interface,
              udaf41-state 
            }
    STATUS current
    DESCRIPTION
        "Notification of Event UDAF.41

        Message: 'Tx $1 Message to Host, $2 bytes, interface $3, state $4'

        Parameters list:
              $1: udaf41-message-type
              $2: udaf41-bytes-number
              $3: udaf41-interface
              $4: udaf41-state

        A message (whose type is shown) has been transmitted to Host."
    ::= { udafNotificationsPrefix 41 }


END
