-- ============================================================================
-- Copyright (C) 2012 by  HUAWEI TECHNOLOGIES. All rights reserved.
-- Description:  This mib is used for defining huawei's SIP MIB objects, which provides SIP management.
-- Reference:  
-- Version: V1.32
-- ============================================================================

 HUAWEI-VOIP-SIP-MIB DEFINITIONS ::= BEGIN
      IMPORTS
        	MODULE-IDENTITY, OBJECT-TYPE, NOTIFICATION-TYPE, private
        		FROM SNMPv2-SMI
        	MODULE-COMPLIANCE, OBJECT-GROUP, NOTIFICATION-GROUP
        		FROM SNMPv2-CONF
        	TEXTUAL-CONVENTION
        		FROM SNMPv2-TC
        	IpAddress,TimeTicks,Counter32,Integer32, Unsigned32
        		FROM SNMPv2-SMI
        	RowStatus,DisplayString
        		FROM SNMPv2-TC
        	huaweiUtility
        		FROM HUAWEI-MIB;
        
      hwVoip MODULE-IDENTITY
                LAST-UPDATED "201207040000Z"
                ORGANIZATION "Huawei Technologies Co., Ltd."
                CONTACT-INFO                                        
                             "Huawei Industrial Base                
                              Bantian, Longgang                     
                              Shenzhen 518129                       
                              People's Republic of China            
                              Website: http://www.huawei.com        
                              Email: support@huawei.com             
    	                     "                                      
                DESCRIPTION 
            	    "
            	    This mib is used for defining huawei's SIP MIB objects, which provides SIP management.
            	    "
		            
                --  Revision history
                REVISION     "201207040000Z"                                              
                DESCRIPTION  "V1.32, added hwSipMgSoftStringConfigParameter42, hwSipMgSoftStringRunningParameter42."
                
                REVISION     "201204120000Z"                                              
                DESCRIPTION  "V1.32, modify the Description of node hwSipVgwProxyRefreshMode of hwVGWConfigTable and hwSipVgwRunningProxyRefreshMode of hwVGWRunningTable ."
                
                REVISION     "201205260000Z"                                              
                DESCRIPTION  "V1.32, added hwVGWLoadsharingRunningTable"
                
                REVISION     "201205250000Z"                                              
                DESCRIPTION  "V1.32, added hwSipRingParallelGroupTable, hwSipRingParallelGroupMemberTable,
                              modified hwSipGroupNumberRightTable, hwSipGroupNumberConfigTable."
                
                REVISION     "201204120000Z"                                              
                DESCRIPTION  "V1.32, modify the value range of node hwSipVgwRunningProxyDualHome of hwVGWRunningTable and hwSipVgwProxyDualHome of hwVGWConfigTable."
                              
                REVISION     "201204120000Z"                                              
                DESCRIPTION  "V1.32, modify the description value of node MgSoftStringConfigParameter11, MgSoftStringConfigParameter13, MgSoftStringConfigParameter38              
                              MgSoftStringRunningParameter11, MgSoftStringRunningParameter13 and MgSoftStringRunningParameter38."
                
                REVISION     "201204120000Z"                                              
                DESCRIPTION  "V1.32, added hwSipMgSoftParameter29." 
                
                REVISION     "201204040000Z"                                              
                DESCRIPTION  "V1.31, modify the the value range of node hwSipGroupNumberGroupName"
                
                REVISION     "201112120000Z"                                              
                DESCRIPTION  "V1.31, modify the description of hwSipVgwConfigProxyAddressMode and hwSipVgwProxyRunningAddressMode, add the value of 5 -DNS-SRV-FIRST"
                                              
                REVISION     "201112120000Z"                                              
                DESCRIPTION  "V1.30, added hwSipVgwRegMode, hwSipVgwRunningRegMode, hwSipGroupNumberRightTable, hwSipGroupNumberOperTable,
                              hwSipGroupNumberConfigTable, hwSipHuntingGroupMemberTable, hwSipHuntingGroupTable."
 
                REVISION     "201109290000Z"                                              
                DESCRIPTION  "V1.29, modified the parameter value of node hwSipVgwRunningCurrentProxy,
                              modified the value range of node hwSipVgwProxyRunningState, Added hwSipMgSoftParameter28."   
                             
                REVISION     "201108310000Z"                                              
                DESCRIPTION  "V1.28, added hwSipVgwKeepActiveFlag, hwSipVgwKeepActivePeriod, hwSipVgwRunningKeepActiveFlag, hwSipVgwRunningKeepActivePeriod
                             hwSipstackParaToHeaderStrictCheckFlag."      

                REVISION     "201106020000Z"
                DESCRIPTION  "V1.27, added hwSipMgSoftParameter27, added hwSipMgSoftStringConfigParameter37, added hwSipMgSoftStringConfigParameter38,
                              added hwSipMgSoftStringRunningParameter37, added hwSipMgSoftStringRunningParameter38,
                              added hwSipstackParaToHeaderStrictCheckFlag."
                              
                REVISION     "201104210000Z"
                DESCRIPTION  "V1.26, added hwVGWDigitMapGroupRefTable."   
                
                REVISION     "201101200000Z"                                 
                DESCRIPTION  "V1.25, revised the error description"
                              
                REVISION     "201011090000Z"                                 
                DESCRIPTION  "V1.24, revised the error description"
                              
                REVISION     "201009190000Z"
                DESCRIPTION  "V1.23, modified the discription of hwSipVgwProxyRefreshMode; modify hwSipVgwRunningTransMode, hwSipMgSoftParameter2, hwSipMgSoftParameter3,
                							 hwSipMgSoftParameter4, hwSipMgSoftParameter5."
              

                REVISION     "201007190000Z"
                DESCRIPTION  "V1.22, revised the errors. Added hwSipVgwAuthMode, added hwSipVgwSubUAProfile,
                            added hwSipVgwSubRegState, added hwSipVgwSubMwi, added hwSipVgwSdpNegoMode,
                            added hwSipVgwProxyDualHome, added hwSipVgwProxyCheckMode, added hwSipVgwRunningAuthMode,
                            added hwSipVgwRunningSubUAProfile, added hwSipVgwRunningSubRegState, added hwSipVgwRunningSubMwi,
                            added hwSipVgwRunningSdpNegoMode, added hwSipVgwRunningProxyDualHome, and added hwSipVgwRunningProxyCheckMode
                            added hwSipVgwProxyRefreshMode, add hwSipVgwRunningProxyRefreshMode,add hwSipVgwRunningCurrentProxy"
              
                REVISION     "201005050000Z"
                DESCRIPTION  "V1.21, revised the errors"
                
                REVISION     "201004100000Z"
                DESCRIPTION  "V1.20, corrected the test errors"             
                
                REVISION     "201003250000Z"
                DESCRIPTION  "V1.19, modified the value type of node hwSipProxySign"
                
                REVISION     "201002250000Z"
                DESCRIPTION  "V1.18, modified the parameter value of node hwSipMgResetResult"
                
                REVISION     "201001250000Z"
                DESCRIPTION  "V1.17, added trap notification and corrected compile error"
                
                REVISION     "200912180000Z"        
                DESCRIPTION  "V1.16, added hwSipVgwMediaAddrName, hwSipVgwSignalAddrName, hwSipVgwRunningMediaAddrName, and hwSipVgwRunningSignalAddrName to support DHCP"
                
                REVISION     "200912010000Z"        
                DESCRIPTION  "V1.15, added hwSipDmmParaTable to support digitmap timer configuration"
            
               ::= { huaweiUtility 36 }
      
 hwIASVoipAlarmOids OBJECT IDENTIFIER ::= { hwIASVoipTraps 1 }
 
 hwIASVoipAlarmTraps OBJECT IDENTIFIER ::= { hwIASVoipTraps 0 }
-- cch for stand alone begin 
-- hwStandAloneParaTable OBJECT IDENTIFIER ::= { hwIASVoipObjects 24 } 
-- cch for standalone end
 
-- BEGIN: modified by wuguowang 20050722 FOR BT VAG 
 --hwDigitmapTable OBJECT IDENTIFIER ::= { hwIASVoipObjects 23 }
-- END: modified by wuguowang 20050722 FOR BT VAG 

 hwIASVoipObjects OBJECT IDENTIFIER ::= { hwVoip 1 }
  
 hwIASVoipTraps OBJECT IDENTIFIER ::= { hwVoip 2 }

 hwVoipSipObjects OBJECT IDENTIFIER ::= { hwIASVoipObjects 70 }

 hwIASSipTrapsVbOids OBJECT IDENTIFIER ::= { hwVoip 7 }

 hwIASSipTraps OBJECT IDENTIFIER ::= { hwVoip 8 }

 hwIASSipCommonTraps OBJECT IDENTIFIER ::= { hwIASSipTraps 1 }

 hwIASSipAlarmTraps OBJECT IDENTIFIER ::= { hwIASSipTraps 2 }

--

  hwVGWConfigTable OBJECT-TYPE
     SYNTAX      SEQUENCE OF HwVGWConfigEntry
     MAX-ACCESS  not-accessible
     STATUS      current
     DESCRIPTION
       "
       This table is used to config the parameters of SipVgw.
       The index of this table is hwSipVgwId.
       "
     ::= { hwVoipSipObjects 1 }

   hwVGWConfigEntry OBJECT-TYPE
     SYNTAX      HwVGWConfigEntry
     MAX-ACCESS  not-accessible
     STATUS      current
     DESCRIPTION
       "
       This table is used to config the parameters of SipVgw.
       The index of this entry is hwSipVgwId.
       "
     INDEX    {
                hwSipVgwId
              }
     ::= { hwVGWConfigTable 1 }

   HwVGWConfigEntry ::=
     SEQUENCE
     {
       hwSipVgwId       Integer32,
       hwSipVgwMediaIPAddress IpAddress,
       hwSipVgwSigIPAddress IpAddress,
       hwSipVgwSigPort Integer32,
       hwSipVgwProxyIPAddress IpAddress,
       hwSipVgwProxyPort  Integer32,
       hwSipVgwTransMode INTEGER,
       hwSipVgwDomainName OCTET STRING,
       hwSipVgwProxyDomainName OCTET STRING,
       hwSipVgwHomeDomainName OCTET STRING,
       hwSipVgwRegisterURI OCTET STRING,
       hwSipVgwConferenceFactoryURI OCTET STRING,
       hwSipVgwDesc OCTET STRING,
       hwSipVgwPhoneContext OCTET STRING,
       hwSipVgwAdminStatus INTEGER,
       hwSipVgwRowStatus RowStatus,
       hwSipVgwProfileIndex Integer32,
       hwSipVgwProfileName OCTET STRING,
       hwSipVgwProxyIPAddress2 IpAddress,
       hwSipVgwProxyPort2  Integer32,
       hwSipVgwAuthUserName OCTET STRING,
       hwSipVgwAuthPassword OCTET STRING,
       hwSipVgwMediaIPAddrDhcpClientIndex Integer32,
       hwSipVgwSigIPAddrDhcpClientIndex  Integer32,
       hwSipVgwSrvLogicName OCTET STRING,
       hwSipVgwServerDhcpOption INTEGER,
       hwSipVgwSwitchoverDestination INTEGER,
       hwSipVgwMediaAddrName OCTET STRING,
       hwSipVgwSignalAddrName OCTET STRING,
       hwSipVgwAuthPasswordMode INTEGER,
       hwSipVgwAuthHA1 OCTET STRING,
       hwSipVgwAuthMode INTEGER,
       hwSipVgwSubUAProfile INTEGER,
       hwSipVgwSubRegState INTEGER,
       hwSipVgwSubMwi INTEGER,
       hwSipVgwSdpNegoMode INTEGER,
       hwSipVgwProxyDualHome INTEGER,
       hwSipVgwProxyCheckMode INTEGER,
       hwSipVgwProxyRefreshMode INTEGER,
       hwSipVgwKeepActiveFlag INTEGER,
       hwSipVgwKeepActivePeriod Integer32,
       hwSipVgwRegMode INTEGER 
    }

    hwSipVgwId OBJECT-TYPE
     SYNTAX      Integer32(0..16777215)
     MAX-ACCESS  not-accessible
     STATUS      current
     DESCRIPTION
         "
         SIP GateWay ID.
         "
     ::= { hwVGWConfigEntry 1 }

    hwSipVgwMediaIPAddress OBJECT-TYPE
     SYNTAX      IpAddress
     MAX-ACCESS  read-write
     STATUS      current
     DESCRIPTION
         "
         Indicates the MediaIPAddress of SipVgw.
         "
     ::= { hwVGWConfigEntry 2 }

    hwSipVgwSigIPAddress OBJECT-TYPE
     SYNTAX      IpAddress
     MAX-ACCESS  read-write
     STATUS      current
     DESCRIPTION
         "
         Indicates the SigIPAddress of SipVgw.
         "
     ::= { hwVGWConfigEntry 3 }

    hwSipVgwSigPort OBJECT-TYPE
     SYNTAX      Integer32(5000..5999|65535)
     MAX-ACCESS  read-write
     STATUS      current
     DESCRIPTION
         "
         Indicates the SigPort of SipVgw.
         65535 means this parameter is not configurated.
         "
     ::= { hwVGWConfigEntry 4 }

    hwSipVgwProxyIPAddress OBJECT-TYPE
     SYNTAX      IpAddress
     MAX-ACCESS  read-write
     STATUS      current
     DESCRIPTION
         "
         Indicates the Master Proxy IP of SipVgw.
         "
     ::= { hwVGWConfigEntry 5 }

    hwSipVgwProxyPort OBJECT-TYPE
     SYNTAX      Integer32(1..65535)
     MAX-ACCESS  read-write
     STATUS      current
     DESCRIPTION
         "
         Indicates the Master ProxyPort of SipVgw.
         "
     ::= { hwVGWConfigEntry 6 }

    hwSipVgwTransMode OBJECT-TYPE
     SYNTAX      INTEGER{tcp(1),udp(2),sctp(3),tls(4)}
     MAX-ACCESS  read-write
     STATUS      current
     DESCRIPTION
         "
         Indicates the TransMode of SipVgw.
         Options:
         1. tcp(1) -TCP
         2. udp(2) -UDP
         3. sctp(3) -SCTP
         4. tls(4) -TLS
         "
     ::= { hwVGWConfigEntry 7 }

   hwSipVgwDomainName OBJECT-TYPE
     SYNTAX      OCTET STRING(SIZE (0..64))
     MAX-ACCESS  read-write
     STATUS      current
     DESCRIPTION
         "
         Indicates the DomainName of SipVgw.
         "
     ::= { hwVGWConfigEntry 8 }

    hwSipVgwProxyDomainName OBJECT-TYPE
     SYNTAX      OCTET STRING(SIZE (0..64))
     MAX-ACCESS  read-write
     STATUS      current
     DESCRIPTION
         "
         Indicates the ProxyDomainName of SipVgw.
         "
     ::= { hwVGWConfigEntry 9 }

   hwSipVgwHomeDomainName OBJECT-TYPE
     SYNTAX      OCTET STRING(SIZE (0..64))
     MAX-ACCESS  read-write
     STATUS      current
     DESCRIPTION
         "
         Indicates the HomeDomainName of SipVgw.
         "
     ::= { hwVGWConfigEntry 10 }

   hwSipVgwRegisterURI OBJECT-TYPE
     SYNTAX      OCTET STRING(SIZE (0..64))
     MAX-ACCESS  read-write
     STATUS      current
     DESCRIPTION
         "
         Indicates the Register-URI of SipVgw.
         "
     ::= { hwVGWConfigEntry 11 }

   hwSipVgwConferenceFactoryURI OBJECT-TYPE
     SYNTAX      OCTET STRING(SIZE (0..64))
     MAX-ACCESS  read-write
     STATUS      current
     DESCRIPTION
         "
         Indicates the ConferenceFactory-URI of SipVgw.
         "
     ::= { hwVGWConfigEntry 12 }

   hwSipVgwDesc OBJECT-TYPE
     SYNTAX      OCTET STRING(SIZE (0..32))
     MAX-ACCESS  read-write
     STATUS      current
     DESCRIPTION
         "
         Indicates the Description of SipVgw.
         "
     ::= { hwVGWConfigEntry 13 }

   hwSipVgwPhoneContext OBJECT-TYPE
     SYNTAX      OCTET STRING(SIZE (0..32))
     MAX-ACCESS  read-write
     STATUS      current
     DESCRIPTION
         "
         Indicates the PhoneContext of SipVgw.
         "
     ::= { hwVGWConfigEntry 14 }

  hwSipVgwAdminStatus OBJECT-TYPE
     SYNTAX      INTEGER{reset(1),switchover(2)}
     MAX-ACCESS  read-write
     STATUS      current
     DESCRIPTION
         "
         Indicates the AdminStatus of SipVgw.
         Options:
         1. reset(1) -reset
         2. switchover(2) -switchover
         "
     ::= { hwVGWConfigEntry 15 }

   hwSipVgwRowStatus OBJECT-TYPE
     SYNTAX      RowStatus
     MAX-ACCESS  read-write
     STATUS      current
     DESCRIPTION
         "
         This is used to create new rows in this table, modify existing rows, and delete existing rows.
         "
     ::= { hwVGWConfigEntry 16 }

   hwSipVgwProfileIndex OBJECT-TYPE
     SYNTAX      Integer32(0..254)
     MAX-ACCESS  read-write
     STATUS      current
     DESCRIPTION
         "
         Indicates the ProfileIndex of SipVgw.
         "
     ::= { hwVGWConfigEntry 17 }

   hwSipVgwProfileName OBJECT-TYPE
     SYNTAX      OCTET STRING(SIZE (1..67))
     MAX-ACCESS  read-only
     STATUS      current
     DESCRIPTION
         "
         Indicates the ProfileName of SipVgw.
         "
     ::= { hwVGWConfigEntry 18 }

    hwSipVgwProxyIPAddress2 OBJECT-TYPE
     SYNTAX      IpAddress
     MAX-ACCESS  read-write
     STATUS      current
     DESCRIPTION
         "
         Indicates the Slaver ProxyIPAddress of SipVgw.
         "
     ::= { hwVGWConfigEntry 19 }

    hwSipVgwProxyPort2 OBJECT-TYPE
     SYNTAX      Integer32(1..65535)
     MAX-ACCESS  read-write
     STATUS      current
     DESCRIPTION
         "
         Indicates the Slaver ProxyPort of SipVgw.
         "
     ::= { hwVGWConfigEntry 20 }

    hwSipVgwAuthUserName OBJECT-TYPE
     SYNTAX      OCTET STRING(SIZE (0..64))
     MAX-ACCESS  read-write
     STATUS      current
     DESCRIPTION
         "
         Indicates the Auth Username of SipVgw.
         "
     ::= { hwVGWConfigEntry 21 }

    hwSipVgwAuthPassword OBJECT-TYPE
     SYNTAX      OCTET STRING(SIZE (0..64))
     MAX-ACCESS  read-write
     STATUS      current
     DESCRIPTION
         "
         Indicates the Auth Password of SipVgw.
         "
     ::= { hwVGWConfigEntry 22 }

     hwSipVgwMediaIPAddrDhcpClientIndex OBJECT-TYPE
     SYNTAX      Integer32(1..4093|-1)
     MAX-ACCESS  read-write
     STATUS      current
     DESCRIPTION
         "
         Dhcp Media vlan id.
         The valid value is 1..4093, if the value is -1, the static media ip will be used.
         "
     ::= { hwVGWConfigEntry 23 }

     hwSipVgwSigIPAddrDhcpClientIndex OBJECT-TYPE
     SYNTAX      Integer32(1..4093|-1)
     MAX-ACCESS  read-write
     STATUS      current
     DESCRIPTION
         "
         Dhcp Signal vlan id.
         The valid value is 1..4093, if the value is -1, the static signal ip will be used.
         "
     ::= { hwVGWConfigEntry 24 }

   hwSipVgwSrvLogicName OBJECT-TYPE
     SYNTAX      OCTET STRING(SIZE (1..67))
     MAX-ACCESS  read-write
     STATUS      current
     DESCRIPTION
         "
         Indicates the ServeLogicName of SipVgw.
         "
     ::= { hwVGWConfigEntry 25 }

   hwSipVgwServerDhcpOption OBJECT-TYPE
     SYNTAX      INTEGER{none(1),option120(2),option21(3)}
     MAX-ACCESS  read-write
     STATUS      current
     DESCRIPTION
         "
         Indicates the DHCP option of SipVgw.
         Options:
         1. none(1) -none
         2. option120(2) -option120
         3. option21(3) -option21
         "
     DEFVAL      { {none(1)} }
     ::= { hwVGWConfigEntry 26 }

   hwSipVgwSwitchoverDestination OBJECT-TYPE
     SYNTAX      INTEGER{primary(1),secondary(2)}
     MAX-ACCESS  read-write
     STATUS      current
     DESCRIPTION
         "
         Indicates the target proxy of switchover.
         Options:
         1. primary(1) -primary proxy
         2. secondary(2) -secondary proxy
         "
     ::= { hwVGWConfigEntry 27 }


   hwSipVgwMediaAddrName OBJECT-TYPE
     SYNTAX      OCTET STRING(SIZE (0..64))
     MAX-ACCESS  read-write
     STATUS      current
     DESCRIPTION
         "
         Dynamic media IP name.
         "
     ::= { hwVGWConfigEntry 28 }

   hwSipVgwSignalAddrName OBJECT-TYPE
     SYNTAX      OCTET STRING(SIZE (0..64))
     MAX-ACCESS  read-write
     STATUS      current
     DESCRIPTION
         "
         Dynamic signal IP name.
         "
     ::= { hwVGWConfigEntry 29 }

     hwSipVgwAuthPasswordMode OBJECT-TYPE
     SYNTAX      INTEGER{password(1),ha1(2)}
     MAX-ACCESS  read-write
     STATUS      current
     DESCRIPTION
         "
         Auth Password mode. 
         Options:
         1. password(1) -auth by password
         2. ha1(2) -auth by ha1
         "
     DEFVAL      { {password(1)} }        
     ::= { hwVGWConfigEntry 30 }

   hwSipVgwAuthHA1 OBJECT-TYPE
     SYNTAX      OCTET STRING(SIZE (0..32))
     MAX-ACCESS  read-write
     STATUS      current
     DESCRIPTION
         "
         Indicates the Auth HA1 of SipVgw.
         "
     ::= { hwVGWConfigEntry 31 }

    hwSipVgwAuthMode OBJECT-TYPE
    SYNTAX      INTEGER{interface (1) ,singleuser (2)}
    MAX-ACCESS  read-write
    STATUS      current
    DESCRIPTION
     "
     Indicates the user authentication mode of SipVgw.
     Options:
     1. interface(1) -interface
     2. singleuser(2) -single user
     "
     DEFVAL      { {singleuser (2)} }   
    ::= { hwVGWConfigEntry 32 }

    hwSipVgwSubUAProfile OBJECT-TYPE
    SYNTAX      INTEGER{enable(1), disable(2)}
    MAX-ACCESS  read-write
    STATUS      current
    DESCRIPTION
     "
     Indicates subscribe to UA-Profile.
     Options:
     1. enable(1) -enable
     2. disable(2) -disable
     "
     DEFVAL      { {enable(1)} } 
    ::= { hwVGWConfigEntry 33 }

    hwSipVgwSubRegState OBJECT-TYPE
    SYNTAX      INTEGER{enable(1), disable(2)}
    MAX-ACCESS  read-write
    STATUS      current
    DESCRIPTION
     "
     Indicates subscribe to REG-STATE.
     Options:
     1. enable(1) -enable
     2. disable(2) -disable
     " 
      DEFVAL      { {disable(2)} } 
    ::= { hwVGWConfigEntry 34 }

    hwSipVgwSubMwi OBJECT-TYPE
    SYNTAX      INTEGER{enable(1), disable(2)}
    MAX-ACCESS  read-write
    STATUS      current
    DESCRIPTION
     "
     Indicates subscribe to MWI.
     Options:
     1. enable(1) -enable
     2. disable(2) -disable
     "
     DEFVAL      { {disable(2)} } 
    ::= { hwVGWConfigEntry 35 }

    hwSipVgwSdpNegoMode OBJECT-TYPE
    SYNTAX      INTEGER{local(1), remote(2)}
    MAX-ACCESS  read-write
    STATUS      current
    DESCRIPTION
     "
     Indicates SDP negotiation mode.
     Options:
     1. local(1) -Local end takes priority when codec negotiation
     2. remote(2) -Remote end takes priority when codec negotiation
     "     
     
     DEFVAL      { {remote (2)} }   
    ::= { hwVGWConfigEntry 36 }

    hwSipVgwProxyDualHome OBJECT-TYPE
    SYNTAX      INTEGER{ no(1), dualhome(2), autoswitchover(3), loadsharing(4)}
    MAX-ACCESS  read-write
    STATUS      current
    DESCRIPTION
     "
     Indicate mode of supporting proxy homing.
     Options:
     1. no(1) -not support proxy multi-homing
     2. dualhome(2) -support proxy dual-homing, but does not support auto-switchover
     3. autoswitchover(3) -support proxy dual-homing and auto-switchover
     4. loadsharing(4) -support proxy load sharing
     "
     DEFVAL      { {dualhome (2)} }
    ::= { hwVGWConfigEntry 37 }

    hwSipVgwProxyCheckMode OBJECT-TYPE
    SYNTAX      INTEGER{ option(1) , probe(2), register(3)}
    MAX-ACCESS  read-write
    STATUS      current
    DESCRIPTION
     "
     Indicate proxy detection mode.
     Options:
     1. option(1)   -detect proxy by option message
     2. probe(2)    -detect proxy by probe mode
     3. register(3) -detect proxy by register message
     "  
     DEFVAL      { {probe (2)} }       
    ::= { hwVGWConfigEntry 38 }
    
    hwSipVgwProxyRefreshMode OBJECT-TYPE
    SYNTAX      INTEGER{ immediate(1) , defer(2), no-switch(3), null(-1) }
    MAX-ACCESS  read-write
    STATUS      current
    DESCRIPTION
     "
     Indicate Proxy address refresh mode. 
     Options:
     1. immediate(1)     -immediate switch
     2. defer(2)         -switch in no calls cases
     3. no-switch(3)     -no switch
     4. null(-1)         -invalid value
     When the proxy homing mode is load sharing, parameters defer(2) and no-switch(3) do not take effect.
     "       
    ::= { hwVGWConfigEntry 39 }

    hwSipVgwKeepActiveFlag OBJECT-TYPE
    SYNTAX      INTEGER{enable(1), disable(2)}
    MAX-ACCESS  read-write
    STATUS      current
    DESCRIPTION
     "
     The switch for transfer connect regular renovate.
     Options:
     1. enable(1)        -enable
     2. disable(2)       -disable
     Default: disable(2)
     "
     DEFVAL     { {disable (2)} }       
    ::= { hwVGWConfigEntry 40 }
    
    hwSipVgwKeepActivePeriod OBJECT-TYPE
    SYNTAX      Integer32(1..3600)
    MAX-ACCESS  read-write
    STATUS      current
    DESCRIPTION
     "
     Indicates the configured period of transfer connect regular renovate.
     Unit: second
     Default:30
     "     
     DEFVAL     { 30 }      
    ::= { hwVGWConfigEntry 41 }
    
    hwSipVgwRegMode OBJECT-TYPE
    SYNTAX      INTEGER{single(1), wildcard(2)}
    MAX-ACCESS  read-write
    STATUS      current
    DESCRIPTION
     "
     The register mode of the sip user and account.
     Options:
     1. single(1)        -single
     2. wildcard(2)      -wildcard
     Default: single(1)
     "
     DEFVAL     { {single (1)} }       
    ::= { hwVGWConfigEntry 42 }
    
  hwVGWRunningTable OBJECT-TYPE
     SYNTAX      SEQUENCE OF HwVGWRunningEntry
     MAX-ACCESS  not-accessible
     STATUS      current
     DESCRIPTION
       "
       This table is used to query the running parameters of SipVgw.
       The index of this table is hwSipVgwRunningTblVgwId.
       "
     ::= { hwVoipSipObjects 2 }

   hwVGWRunningEntry OBJECT-TYPE
     SYNTAX      HwVGWRunningEntry
     MAX-ACCESS  not-accessible
     STATUS      current
     DESCRIPTION
       "
       This table is used to query the running parameters of SipVgw.
       The index of this entry is hwSipVgwRunningTblVgwId.
       "
     INDEX    {
                hwSipVgwRunningTblVgwId
              }
     ::= { hwVGWRunningTable 1 }

   HwVGWRunningEntry ::=
     SEQUENCE
     {
       hwSipVgwRunningTblVgwId       Integer32,
       hwSipVgwRunningMediaIPAddress IpAddress,
       hwSipVgwRunningSigIPAddress IpAddress,
       hwSipVgwRunningSigPort Integer32,
       hwSipVgwRunningProxyIPAddress IpAddress,
       hwSipVgwRunningProxyPort  Integer32,
       hwSipVgwRunningTransMode INTEGER,
       hwSipVgwRunningDomainName OCTET STRING,
       hwSipVgwRunningProxyDomainName OCTET STRING,
       hwSipVgwRunningHomeDomainName OCTET STRING,
       hwSipVgwRunningRegisterURI OCTET STRING,
       hwSipVgwRunningConferenceFactoryURI OCTET STRING,
       hwSipVgwRunningDesc OCTET STRING,
       hwSipVgwRunningPhoneContext OCTET STRING,
       hwSipVgwRunningProfileIndex Integer32,
       hwSipVgwRunningProfileName OCTET STRING,
       hwSipVgwRunningProxyIPAddress2 IpAddress,
       hwSipVgwRunningProxyPort2  Integer32,
       hwSipVgwProxy1OperStatus  INTEGER,
       hwSipVgwProxy2OperStatus  INTEGER,
       hwSipVgwRunningAuthUserName OCTET STRING,
       hwSipVgwRunningAuthPassword OCTET STRING,
       hwSipVgwRunningSrvLogicName OCTET STRING,
       hwSipVgwRunningServerDhcpOption INTEGER,
       hwSipVgwRunningMediaAddrName OCTET STRING,
       hwSipVgwRunningSignalAddrName OCTET STRING,
       hwSipVgwRunningAuthPasswordMode INTEGER,
       hwSipVgwRunningAuthHA1 OCTET STRING,
       hwSipVgwRunningAuthMode INTEGER,
       hwSipVgwRunningSubUAProfile INTEGER,
       hwSipVgwRunningSubRegState INTEGER,
       hwSipVgwRunningSubMwi INTEGER,
       hwSipVgwRunningSdpNegoMode INTEGER,
       hwSipVgwRunningProxyDualHome INTEGER,
       hwSipVgwRunningProxyCheckMode INTEGER,
       hwSipVgwRunningProxyRefreshMode INTEGER,
       hwSipVgwRunningCurrentProxy INTEGER,
       hwSipVgwRunningKeepActiveFlag INTEGER,
       hwSipVgwRunningKeepActivePeriod Integer32,
       hwSipVgwRunningRegMode INTEGER 
     }

    hwSipVgwRunningTblVgwId OBJECT-TYPE
     SYNTAX      Integer32(0..16777215)
     MAX-ACCESS  not-accessible
     STATUS      current
     DESCRIPTION
         "
         SIP GateWay ID.
         "
     ::= { hwVGWRunningEntry 1 }

    hwSipVgwRunningMediaIPAddress OBJECT-TYPE
     SYNTAX      IpAddress
     MAX-ACCESS  read-only
     STATUS      current
     DESCRIPTION
         "
         Indicates the MediaIPAddress of SipVgw.
         "
     ::= { hwVGWRunningEntry 2 }

    hwSipVgwRunningSigIPAddress OBJECT-TYPE
     SYNTAX      IpAddress
     MAX-ACCESS  read-only
     STATUS      current
     DESCRIPTION
         "
         Indicates the SigIPAddress of SipVgw.
         "
     ::= { hwVGWRunningEntry 3 }

    hwSipVgwRunningSigPort OBJECT-TYPE
     SYNTAX      Integer32(5000..5999|65535)
     MAX-ACCESS  read-only
     STATUS      current
     DESCRIPTION
         "
         Indicates the SigPort of SipVgw.
         65535 means the interface is not started.
         "
     ::= { hwVGWRunningEntry 4 }

    hwSipVgwRunningProxyIPAddress OBJECT-TYPE
     SYNTAX      IpAddress
     MAX-ACCESS  read-only
     STATUS      current
     DESCRIPTION
         "
         Indicates the Master Proxy IP of SipVgw.
         "
     ::= { hwVGWRunningEntry 5 }

    hwSipVgwRunningProxyPort OBJECT-TYPE
     SYNTAX      Integer32(1..65535)
     MAX-ACCESS  read-only
     STATUS      current
     DESCRIPTION
         "
         Indicates the Master ProxyPort of SipVgw.
         "
     ::= { hwVGWRunningEntry 6 }

    hwSipVgwRunningTransMode OBJECT-TYPE
     SYNTAX      INTEGER{tcp(1),udp(2),sctp(3),tls(4),null(255)}
     MAX-ACCESS  read-only
     STATUS      current
     DESCRIPTION
         "
         Indicates the TransMode of SipVgw. null(255) means the interface is not started.
         Options:
         1. tcp(1) -TCP
         2. udp(2) -UDP
         3. sctp(3) -SCTP
         4. tls(4) -TLS
         5. null(255) -interface is not started
         "
     ::= { hwVGWRunningEntry 7 }

   hwSipVgwRunningDomainName OBJECT-TYPE
     SYNTAX      OCTET STRING(SIZE (0..64))
     MAX-ACCESS  read-only
     STATUS      current
     DESCRIPTION
         "
         Indicates the DomainName of SipVgw.
         "
     ::= { hwVGWRunningEntry 8 }

    hwSipVgwRunningProxyDomainName OBJECT-TYPE
     SYNTAX      OCTET STRING(SIZE (0..64))
     MAX-ACCESS  read-only
     STATUS      current
     DESCRIPTION
         "
         Indicates the ProxyDomainName of SipVgw.
         "
     ::= { hwVGWRunningEntry 9 }

   hwSipVgwRunningHomeDomainName OBJECT-TYPE
     SYNTAX      OCTET STRING(SIZE (0..64))
     MAX-ACCESS  read-only
     STATUS      current
     DESCRIPTION
         "
         Indicates the HomeDomainName of SipVgw.
         "
     ::= { hwVGWRunningEntry 10 }

   hwSipVgwRunningRegisterURI OBJECT-TYPE
     SYNTAX      OCTET STRING(SIZE (0..64))
     MAX-ACCESS  read-only
     STATUS      current
     DESCRIPTION
         "
         Indicates the Register-URI of SipVgw.
         "
     ::= { hwVGWRunningEntry 11 }

   hwSipVgwRunningConferenceFactoryURI OBJECT-TYPE
     SYNTAX      OCTET STRING(SIZE (0..64))
     MAX-ACCESS  read-only
     STATUS      current
     DESCRIPTION
         "
         Indicates the ConferenceFactory-URI of SipVgw.
         "
     ::= { hwVGWRunningEntry 12 }

   hwSipVgwRunningDesc OBJECT-TYPE
     SYNTAX      OCTET STRING(SIZE (0..32))
     MAX-ACCESS  read-only
     STATUS      current
     DESCRIPTION
         "
         Indicates the Description of SipVgw.
         "
     ::= { hwVGWRunningEntry 13 }

   hwSipVgwRunningPhoneContext OBJECT-TYPE
     SYNTAX      OCTET STRING(SIZE (0..32))
     MAX-ACCESS  read-only
     STATUS      current
     DESCRIPTION
         "
         Indicates the PhoneContext of SipVgw.
         "
     ::= { hwVGWRunningEntry 14 }

   hwSipVgwRunningProfileIndex OBJECT-TYPE
     SYNTAX      Integer32(0..254)
     MAX-ACCESS  read-only
     STATUS      current
     DESCRIPTION
         "
         Indicates the ProfileIndex of SipVgw.
         "
     ::= { hwVGWRunningEntry 15 }

   hwSipVgwRunningProfileName OBJECT-TYPE
     SYNTAX      OCTET STRING(SIZE (1..67))
     MAX-ACCESS  read-only
     STATUS      current
     DESCRIPTION
         "
         Indicates the ProfileName of SipVgw.
         "
     ::= { hwVGWRunningEntry 16 }

   hwSipVgwRunningProxyIPAddress2 OBJECT-TYPE
     SYNTAX      IpAddress
     MAX-ACCESS  read-only
     STATUS      current
     DESCRIPTION
         "
         Indicates the Slaver ProxyIPAddress of SipVgw.
         "
     ::= { hwVGWRunningEntry 17 }

    hwSipVgwRunningProxyPort2 OBJECT-TYPE
     SYNTAX      Integer32(1..65535)
     MAX-ACCESS  read-only
     STATUS      current
     DESCRIPTION
         "
         Indicates the Slaver ProxyPort of SipVgw.
         "
     ::= { hwVGWRunningEntry 18 }

    hwSipVgwProxy1OperStatus OBJECT-TYPE
     SYNTAX      INTEGER{up(1),down(2),unknown(3)}
     MAX-ACCESS  read-only
     STATUS      current
     DESCRIPTION
         "
         Indicates the Master OperStatus of SipVgw.
         Options:
         1. up(1) -normal
         2. down(2) -fault
         3. unknown(3) -unknown
         "
     ::= { hwVGWRunningEntry 19 }

    hwSipVgwProxy2OperStatus OBJECT-TYPE
     SYNTAX      INTEGER{up(1),down(2),unknown(3)}
     MAX-ACCESS  read-only
     STATUS      current
     DESCRIPTION
         "
         Indicates the Slaver OperStatus of SipVgw.
         Options:
         1. up(1) -normal
         2. down(2) -fault
         3. unknown(3) -unknown
         "
     ::= { hwVGWRunningEntry 20 }

    hwSipVgwRunningAuthUserName OBJECT-TYPE
     SYNTAX      OCTET STRING(SIZE (0..64))
     MAX-ACCESS  read-only
     STATUS      current
     DESCRIPTION
         "
         Indicates the Auth Username of SipVgw.
         "
     ::= { hwVGWRunningEntry 21 }

    hwSipVgwRunningAuthPassword OBJECT-TYPE
     SYNTAX      OCTET STRING(SIZE (0..64))
     MAX-ACCESS  read-only
     STATUS      current
     DESCRIPTION
         "
         Indicates the Auth Password of SipVgw.
         "
     ::= { hwVGWRunningEntry 22 }

   hwSipVgwRunningSrvLogicName OBJECT-TYPE
     SYNTAX      OCTET STRING(SIZE (1..67))
     MAX-ACCESS  read-only
     STATUS      current
     DESCRIPTION
         "
         Indicates the ServeLogicName of SipVgw.
         "
     ::= { hwVGWRunningEntry 23 }

   hwSipVgwRunningServerDhcpOption OBJECT-TYPE
     SYNTAX      INTEGER{none(1),option120(2),option21(3)}
     MAX-ACCESS  read-only
     STATUS      current
     DESCRIPTION
         "
         Indicates the DHCP option of SipVgw.
         Options:
         1. none(1) -none
         2. option120(2) -option120
         3. option21(3) -option21
         Default: none(1)
         "

     ::= { hwVGWRunningEntry 24 }


  hwSipVgwRunningMediaAddrName OBJECT-TYPE
     SYNTAX      OCTET STRING(SIZE (0..64))
     MAX-ACCESS  read-only
     STATUS      current
     DESCRIPTION
         "
         Indicates the current dynamic media IP name of SipVgw.
         "
     ::= { hwVGWRunningEntry 25 }



   hwSipVgwRunningSignalAddrName OBJECT-TYPE
     SYNTAX      OCTET STRING(SIZE (0..64))
     MAX-ACCESS  read-only
     STATUS      current
     DESCRIPTION
         "
         Indicates the current dynamic signal IP name of SipVgw.
         "
     ::= { hwVGWRunningEntry 26 }

  hwSipVgwRunningAuthPasswordMode OBJECT-TYPE
     SYNTAX      INTEGER{password(1),ha1(2)}
     MAX-ACCESS  read-only
     STATUS      current
     DESCRIPTION
         "
         Auth Password mode.
         Options:
         1. password(1) -password
         2. ha1(2) -HA1 
         "
     ::= { hwVGWRunningEntry 27 }

  hwSipVgwRunningAuthHA1 OBJECT-TYPE
     SYNTAX      OCTET STRING(SIZE (0..32))
     MAX-ACCESS  read-only
     STATUS      current
     DESCRIPTION
         "
         Auth HA1.
         "
     ::= { hwVGWRunningEntry 28 }

  hwSipVgwRunningAuthMode OBJECT-TYPE
     SYNTAX      INTEGER{interface(1), singleuser(2)}
     MAX-ACCESS  read-only
     STATUS      current
     DESCRIPTION
         "
         Indicates user authentication mode of SipVgw.
         Options:
         1. interface(1) -interface
         2. singleuser(2) -single user
         "
     ::= { hwVGWRunningEntry 29 }

     hwSipVgwRunningSubUAProfile OBJECT-TYPE
     SYNTAX      INTEGER{enable(1), disable(2)}
     MAX-ACCESS  read-only
     STATUS      current
     DESCRIPTION
         "
         Indicates subscribe to UA-Profile.
         Options:
         1. enable(1) -enable
         2. disable(2) -disable
         "
     ::= { hwVGWRunningEntry 30 }

     hwSipVgwRunningSubRegState OBJECT-TYPE
     SYNTAX      INTEGER{enable(1), disable(2)}
     MAX-ACCESS  read-only
     STATUS      current
     DESCRIPTION
         "
         Indicates subscribe to REG-STATE.
         Options:
         1. enable(1) -enable
         2. disable(2) -disable
         "
     ::= { hwVGWRunningEntry 31 }

     hwSipVgwRunningSubMwi OBJECT-TYPE
     SYNTAX      INTEGER{enable(1), disable(2)}
     MAX-ACCESS  read-only
     STATUS      current
     DESCRIPTION
         "
         Indicates subscribe to MWI.
         Options:
         1. enable(1) -enable
         2. disable(2) -disable
         "
     ::= { hwVGWRunningEntry 32 }

    hwSipVgwRunningSdpNegoMode OBJECT-TYPE
    SYNTAX      INTEGER{local(1), remote (2)}
    MAX-ACCESS  read-only
    STATUS      current
    DESCRIPTION
        "
        Indicates SDP negotiation mode of SipVgw.
        Options:
        1. local(1) -local first
        2. remote(2) -remote first
        "
       ::= { hwVGWRunningEntry 33 }

    hwSipVgwRunningProxyDualHome OBJECT-TYPE
    SYNTAX      INTEGER{ no(1), dualhome(2), autoswitchover(3), loadsharing(4)}
    MAX-ACCESS  read-only
    STATUS      current
    DESCRIPTION
        "
        Indicate mode of supporting proxy homing of SipVgw.
        Options:
        1. no(1) -not support proxy multi-homing
        2. dualhome(2) -support proxy dual-homing, but does not support auto-switchover
        3. autoswitchover(3) -support proxy dual-homing and auto-switchover
        4. loadsharing(4) -support proxy load sharing
        "
       ::= { hwVGWRunningEntry 34 }

    hwSipVgwRunningProxyCheckMode OBJECT-TYPE
    SYNTAX      INTEGER{ option(1) , probe(2), register(3)}
    MAX-ACCESS  read-only
    STATUS      current
    DESCRIPTION
     "
     Indicate proxy detection mode.
     Options:
     1. option(1) -detection proxy by option message
     2. probe(2)  -detection proxy by probe mode
     3. register(3) -detection proxy by register message
     "     
    ::= { hwVGWRunningEntry 35 }

    hwSipVgwRunningProxyRefreshMode OBJECT-TYPE
    SYNTAX      INTEGER{ immediate(1), defer(2), no-switch(3)}
    MAX-ACCESS  read-only
    STATUS      current
    DESCRIPTION
     "
     Indicate Proxy address refresh mode. 
     Options:
     1. immediate(1) -immediate switch
     2. defer(2)     -switch in no calls cases
     3. no-switch(3) -no switch
     When the proxy homing mode is load sharing, parameters defer(2) and no-switch(3) do not take effect.
     "     
    ::= { hwVGWRunningEntry 36 }
    
    hwSipVgwRunningCurrentProxy OBJECT-TYPE
    SYNTAX      INTEGER{ primary-proxy(1), secondary-proxy(2), null(-1) }
    MAX-ACCESS  read-only
    STATUS      current
    DESCRIPTION
     "
     Indicate Current Proxy. 
     Options:
     1. primary-proxy(1)   -primary proxy
     2. secondary-proxy(2) -secondary proxy
     3. null(-1)           -invalid value
     "     
    ::= { hwVGWRunningEntry 37 }
    
    hwSipVgwRunningKeepActiveFlag OBJECT-TYPE
    SYNTAX      INTEGER{ enable(1), disable(2) }
    MAX-ACCESS  read-only
    STATUS      current               
    DESCRIPTION
     "
     Indicates the switch for transfer connect regular renovate.
     Options:
     1. enable(1)        -enable
     2. disable(2)       -disable
     "
    ::= { hwVGWRunningEntry 38 }
    
    hwSipVgwRunningKeepActivePeriod OBJECT-TYPE
    SYNTAX      Integer32(1..3600)
    MAX-ACCESS  read-only
    STATUS      current
    DESCRIPTION
     "
     Indicates the configured period of transfer connect regular renovate.
     Unit: second
     "         
    ::= { hwVGWRunningEntry 39 }
    
    hwSipVgwRunningRegMode OBJECT-TYPE
    SYNTAX      INTEGER{ single(1), wildcard(2) }
    MAX-ACCESS  read-only
    STATUS      current               
    DESCRIPTION
     "
     Indicates register mode of sip user and account.
     Options:
     1. single(1)        -single
     2. wildcard(2)      -wildcard
     "
    ::= { hwVGWRunningEntry 40 }
    
    hwSipstackParametersTable OBJECT IDENTIFIER ::= {  hwVoipSipObjects 3  }

    hwSipstackParaServer OBJECT-TYPE
    SYNTAX      OCTET STRING(SIZE (0..64))
    MAX-ACCESS  read-write
    STATUS      current
    DESCRIPTION
      "
      The head-field of Server.
      "
    ::= { hwSipstackParametersTable 1 }

    hwSipstackParaOrganization  OBJECT-TYPE
    SYNTAX      OCTET STRING(SIZE (0..64))
    MAX-ACCESS  read-write
    STATUS      current
    DESCRIPTION
      "
      The head-field of Organization.
      "
    ::= { hwSipstackParametersTable 2 }

    hwSipstackParaUserAgent  OBJECT-TYPE
    SYNTAX      OCTET STRING(SIZE (0..64))
    MAX-ACCESS  read-write
    STATUS      current
    DESCRIPTION
      "
      The head-field of UserAgent.
      "
    ::= { hwSipstackParametersTable 3 }

    hwSipstackParaMaxForwards   OBJECT-TYPE
    SYNTAX      Integer32(0..255)
    MAX-ACCESS  read-write
    STATUS      current
    DESCRIPTION
      "
      The MaxForwards parameter of SipStack.
      Default: 70
      "

    ::= { hwSipstackParametersTable 4 }

   hwSipstackParaT1   OBJECT-TYPE
    SYNTAX      Integer32(200..10000)
    MAX-ACCESS  read-write
    STATUS      current
    DESCRIPTION
      "
      The T1 timer(Round-Trip timer) of SipStack.
      Default: 500
      Unit: ms
      "

    ::= { hwSipstackParametersTable 5 }

    hwSipstackParaT2   OBJECT-TYPE
    SYNTAX      Integer32(200..10000)
    MAX-ACCESS  read-write
    STATUS      current
    DESCRIPTION
      "
      The T2 timer of SipStack(The maximum length of retransmission for non-invite request or invite response).
      Default: 4000
      Unit: millisecond
      "

    ::= { hwSipstackParametersTable 6 }

    hwSipstackParaT4   OBJECT-TYPE
    SYNTAX      Integer32(200..10000)
    MAX-ACCESS  read-write
    STATUS      current
    DESCRIPTION
      "
      The T4 timer of SipStack(The maximum length of message transmission in the network).
      Default: 5000
      Unit: millisecond
      "

    ::= { hwSipstackParametersTable 7 }

    hwSipstackParaTD   OBJECT-TYPE
    SYNTAX      Integer32(0..300000)
    MAX-ACCESS  read-write
    STATUS      current
    DESCRIPTION
      "
      The D timer of SipStack(The maximum length of message retransmission for getting a response).
      Default: 32000
      Unit: millisecond
      "

    ::= { hwSipstackParametersTable 8 }

    hwSipstackParaMinSE   OBJECT-TYPE
    SYNTAX      Integer32(90..65535)
    MAX-ACCESS  read-write
    STATUS      current
    DESCRIPTION
      "
      The timer for Minimum of Session-Expires.
      Default: 90
      Unit: second
      "

    ::= { hwSipstackParametersTable 9 }

    hwSipstackParaSessionProgress   OBJECT-TYPE
    SYNTAX      Integer32(0..65535)
    MAX-ACCESS  read-write
    STATUS      current
    DESCRIPTION
      "
      The length of retransmission for SessionProgress.
      Default: 180
      Unit: second
      "

    ::= { hwSipstackParametersTable 10 }

    hwSipstackParaSessionRelProgress   OBJECT-TYPE
    SYNTAX      Integer32(0..65535)
    MAX-ACCESS  read-write
    STATUS      current
    DESCRIPTION
      "
      The length of retransmission for SessionRelProgress.
      Default: 60
      Unit: second
      "

    ::= { hwSipstackParametersTable 11 }

    hwSipstackParaEntityBasedSessionsTimerFlag   OBJECT-TYPE
    SYNTAX      INTEGER{yes(1), no(2)}
    MAX-ACCESS  read-write
    STATUS      current
    DESCRIPTION
      "
      This flag indicates that whether the Sessions Timer based on UA-Entity.
      Options:
      1. yes(1) -Sessions Timer based on UA-Entity
      2. no(2)  -Sessions Timer not based on UA-Entity
      Default: no(2)
      "

    ::= { hwSipstackParametersTable 12 }

    hwSipstackParaHeaderFoldFlag   OBJECT-TYPE
    SYNTAX      INTEGER{disable(1),enable(2)}
    MAX-ACCESS  read-write
    STATUS      current
    DESCRIPTION
      "
      The flag indicates that whether the authentication header field is folded.
      Options:
      1. disable(1) -disable 
      2. enable(2)  -enable 
      Default: disable(1)
      "

    ::= { hwSipstackParametersTable 13 }
    
   hwSipstackParaToHeaderStrictCheckFlag   OBJECT-TYPE
    SYNTAX      INTEGER{disable(1),enable(2)}
    MAX-ACCESS  read-write
    STATUS      current
    DESCRIPTION
      "
      The flag indicates that whether the to header field is strictly checked.
      Options:
      1. disable(1) -disable 
      2. enable(2)  -enable 
      Default: disable(1)
      "

    ::= { hwSipstackParametersTable 14 }

   hwSipProfileSupportTable OBJECT-TYPE
     SYNTAX      SEQUENCE OF HwSipProfileSupportEntry
     MAX-ACCESS  not-accessible
     STATUS      current
     DESCRIPTION
       "
       This table is used to config the Sip Profile.
       The index of this table is hwSipProfileIndex.
       "
    ::= { hwVoipSipObjects 4 }

   hwSipProfileSupportEntry OBJECT-TYPE
     SYNTAX      HwSipProfileSupportEntry
     MAX-ACCESS  not-accessible
     STATUS      current
     DESCRIPTION
       "
       This table is used to config the Sip Profile.
       The index of this entry is hwSipProfileIndex.
       "
     INDEX    {
                hwSipProfileIndex
              }
    ::= { hwSipProfileSupportTable 1 }

   HwSipProfileSupportEntry ::=
     SEQUENCE
     {
       hwSipProfileIndex       Integer32,
       hwSipProfileName     OCTET STRING
     }

   hwSipProfileIndex OBJECT-TYPE
     SYNTAX      Integer32(0..254)
     MAX-ACCESS  not-accessible
     STATUS      current
     DESCRIPTION
         "
         Indicates the index of SipProfile.
         "
    ::= { hwSipProfileSupportEntry 1 }

   hwSipProfileName OBJECT-TYPE
     SYNTAX      OCTET STRING(SIZE (1..67))
     MAX-ACCESS  read-only
     STATUS      current
     DESCRIPTION
         "
         Indicates the Name of SipProfile.
         "
    ::= { hwSipProfileSupportEntry 2 }

--

  hwVGWProxyConfigTable OBJECT-TYPE
     SYNTAX      SEQUENCE OF HwVGWProxyConfigEntry
     MAX-ACCESS  not-accessible
     STATUS      current
     DESCRIPTION
       "
       This table is used to config the parameters of SipVgw.
       The indexes of this table are hwSipVgwConfigId, hwSipVgwConfigProxyIndex.
       "
     ::= { hwVoipSipObjects 5 }

   hwVGWProxyConfigEntry OBJECT-TYPE
     SYNTAX      HwVGWProxyConfigEntry
     MAX-ACCESS  not-accessible
     STATUS      current
     DESCRIPTION
       "
       This table is used to config the parameters of SipVgw.
       The indexes of this entry are hwSipVgwConfigId, hwSipVgwConfigProxyIndex.
       "
     INDEX    {
                hwSipVgwConfigId,
                hwSipVgwConfigProxyIndex
              }
     ::= { hwVGWProxyConfigTable 1 }

   HwVGWProxyConfigEntry ::=
     SEQUENCE
     {
       hwSipVgwConfigId          Integer32,
       hwSipVgwConfigProxyIndex       Integer32,
       hwSipVgwConfigProxyIPAddress1  IpAddress,
       hwSipVgwConfigProxyIPAddress2  IpAddress,
       hwSipVgwConfigProxyPort        Integer32,
       hwSipVgwConfigProxyDomainName  OCTET STRING,
       hwSipVgwConfigProxyAddressMode Integer32
    }

    hwSipVgwConfigId OBJECT-TYPE
     SYNTAX      Integer32(0..16777215)
     MAX-ACCESS  not-accessible
     STATUS      current
     DESCRIPTION
         "
         SIP GateWay ID.
         "
     ::= { hwVGWProxyConfigEntry 1 }

    hwSipVgwConfigProxyIndex OBJECT-TYPE
     SYNTAX      Integer32(0..1)
     MAX-ACCESS  not-accessible
     STATUS      current
     DESCRIPTION
         "
         proxy index. 
         0 -main 
         1 -standby
         "
     ::= { hwVGWProxyConfigEntry 2 }

    hwSipVgwConfigProxyIPAddress1 OBJECT-TYPE
     SYNTAX      IpAddress
     MAX-ACCESS  read-write
     STATUS      current
     DESCRIPTION
         "
         Indicates the first ProxyIPAddress of SipVgw.
         "
     ::= { hwVGWProxyConfigEntry 3 }

    hwSipVgwConfigProxyIPAddress2 OBJECT-TYPE
     SYNTAX      IpAddress
     MAX-ACCESS  read-write
     STATUS      current
     DESCRIPTION
         "
         Indicates the second ProxyIPAddress of SipVgw.
         "
     ::= { hwVGWProxyConfigEntry 4 }

    hwSipVgwConfigProxyPort OBJECT-TYPE
     SYNTAX      Integer32(1..65535)
     MAX-ACCESS  read-write
     STATUS      current
     DESCRIPTION
         "
         Indicates the ProxyPort of SipVgw.
         "
     ::= { hwVGWProxyConfigEntry 5 }

    hwSipVgwConfigProxyDomainName OBJECT-TYPE
     SYNTAX      OCTET STRING(SIZE (0..64))
     MAX-ACCESS  read-write
     STATUS      current
     DESCRIPTION
         "
         Indicates the ProxyDomainName of SipVgw.
         "
     ::= { hwVGWProxyConfigEntry 6 }

   hwSipVgwConfigProxyAddressMode OBJECT-TYPE
     SYNTAX      Integer32(1..5)
     MAX-ACCESS  read-write
     STATUS      current
     DESCRIPTION
         "
         The proxy address mode. 
         1 -IP
         2 -DNS-A
         3 -DNS-SRV
         4 -DNS-NAPTR
         5 -DNS-SRV-FIRST
         "
     ::= { hwVGWProxyConfigEntry 7 }

-------------------------------------------------------

  hwVGWProxyRunningTable OBJECT-TYPE
     SYNTAX      SEQUENCE OF HwVGWProxyRunningEntry
     MAX-ACCESS  not-accessible
     STATUS      current
     DESCRIPTION
       "
       This table is used to query the config parameters of SipVgw.
       The indexes of this table are hwSipVgwRunningId, hwSipVgwProxyRunningIndex.
       "
     ::= { hwVoipSipObjects 6 }

   hwVGWProxyRunningEntry OBJECT-TYPE
     SYNTAX      HwVGWProxyRunningEntry
     MAX-ACCESS  not-accessible
     STATUS      current
     DESCRIPTION
       "
       This table is used to query the config parameters of SipVgw.
       The indexes of this entry are hwSipVgwRunningId, hwSipVgwProxyRunningIndex.
       "
     INDEX    {
                hwSipVgwRunningId,
                hwSipVgwProxyRunningIndex
              }
     ::= { hwVGWProxyRunningTable 1 }

   HwVGWProxyRunningEntry ::=
     SEQUENCE
     {
       hwSipVgwRunningId                Integer32,
       hwSipVgwProxyRunningIndex        Integer32,
       hwSipVgwProxyRunningIPAddress1   IpAddress,
       hwSipVgwProxyRunningIPAddress2   IpAddress,
       hwSipVgwProxyRunningPort         Integer32,
       hwSipVgwProxyRunningDomainName   OCTET STRING,
       hwSipVgwProxyRunningAddressMode  Integer32,
       hwSipVgwProxyRunningState        Integer32
    }

    hwSipVgwRunningId OBJECT-TYPE
     SYNTAX      Integer32(0..16777215)
     MAX-ACCESS  not-accessible
     STATUS      current
     DESCRIPTION
         "
         SIP GateWay ID.
         "
     ::= { hwVGWProxyRunningEntry 1 }

    hwSipVgwProxyRunningIndex OBJECT-TYPE
     SYNTAX      Integer32(0..1)
     MAX-ACCESS  not-accessible
     STATUS      current
     DESCRIPTION
         "
         Proxy index. 
         0 -main
         1 -standby
         "
     ::= { hwVGWProxyRunningEntry 2 }

    hwSipVgwProxyRunningIPAddress1 OBJECT-TYPE
     SYNTAX      IpAddress
     MAX-ACCESS  read-only
     STATUS      current
     DESCRIPTION
         "
         Indicates the primary IP address of proxy.
         "
     ::= { hwVGWProxyRunningEntry 3 }

    hwSipVgwProxyRunningIPAddress2 OBJECT-TYPE
     SYNTAX      IpAddress
     MAX-ACCESS  read-only
     STATUS      current
     DESCRIPTION
         "
         Indicates the secondary IP address of proxy.
         "
     ::= { hwVGWProxyRunningEntry 4 }

    hwSipVgwProxyRunningPort OBJECT-TYPE
     SYNTAX      Integer32(1..65535)
     MAX-ACCESS  read-only
     STATUS      current
     DESCRIPTION
         "
         Indicates the ProxyPort of SipVgw.
         "
     ::= { hwVGWProxyRunningEntry 5 }

    hwSipVgwProxyRunningDomainName OBJECT-TYPE
     SYNTAX      OCTET STRING(SIZE (0..64))
     MAX-ACCESS  read-only
     STATUS      current
     DESCRIPTION
         "
         Indicates the ProxyDomainName of SipVgw.
         "
     ::= { hwVGWProxyRunningEntry 6 }

   hwSipVgwProxyRunningAddressMode OBJECT-TYPE
     SYNTAX      Integer32(1..5)
     MAX-ACCESS  read-only
     STATUS      current
     DESCRIPTION
         "
         The proxy address mode. 
         1 -IP
         2 -DNS-A
         3 -DNS-SRV
         4 -DNS-NAPTR 
         5 -DNS-SRV-FIRST
         "
     ::= { hwVGWProxyRunningEntry 7 }

   hwSipVgwProxyRunningState OBJECT-TYPE
     SYNTAX      Integer32(1..3|-1)
     MAX-ACCESS  read-only
     STATUS      current
     DESCRIPTION
         "
         The proxy state.
         1 -up(1) 
         2 -down(2)  
         3 -unknown(3)
         4 -the interface is not started(-1)
         "
     ::= { hwVGWProxyRunningEntry 8 }


----------------------------------------------------------
   hwSipSrvLogicSupportTable OBJECT-TYPE
     SYNTAX      SEQUENCE OF HwSipSrvLogicSupportEntry
     MAX-ACCESS  not-accessible
     STATUS      current
     DESCRIPTION
       "
       This table is used to config the Sip Serve-Logic list.
       The index of this table is hwSipSrvLogicIndex.
       "
    ::= { hwVoipSipObjects 7 }

   hwSipSrvLogicSupportEntry OBJECT-TYPE
     SYNTAX      HwSipSrvLogicSupportEntry
     MAX-ACCESS  not-accessible
     STATUS      current
     DESCRIPTION
       "
       This table is used to config the Sip Serve-Logic list.
       The index of this entry is hwSipSrvLogicIndex.
       "
     INDEX    {
                hwSipSrvLogicIndex
              }
    ::= { hwSipSrvLogicSupportTable 1 }

   HwSipSrvLogicSupportEntry ::=
     SEQUENCE
     {
       hwSipSrvLogicIndex       Integer32,
       hwSipSrvLogicName     OCTET STRING
     }

   hwSipSrvLogicIndex OBJECT-TYPE
     SYNTAX      Integer32(0..254)
     MAX-ACCESS  not-accessible
     STATUS      current
     DESCRIPTION
         "
         Indicates the index of SipServeLogic.
         "
    ::= { hwSipSrvLogicSupportEntry 1 }

   hwSipSrvLogicName OBJECT-TYPE
     SYNTAX      OCTET STRING(SIZE (1..67))
     MAX-ACCESS  read-only
     STATUS      current
     DESCRIPTION
         "
         Indicates the Name of SipServeLogic
         "
    ::= { hwSipSrvLogicSupportEntry 2 }

   hwSipMgSoftParameterTable OBJECT-TYPE
     SYNTAX      SEQUENCE OF HwSipMgSoftParameterEntry
     MAX-ACCESS  not-accessible
     STATUS      current
     DESCRIPTION
       "
       This table is used to config the soft Parameters of SIP interface.
       The index of this table is hwSipMgInterfaceIndex.
       "
    ::= { hwVoipSipObjects 8 }

   hwSipMgSoftParameterEntry OBJECT-TYPE
     SYNTAX      HwSipMgSoftParameterEntry
     MAX-ACCESS  not-accessible
     STATUS      current
     DESCRIPTION
       "
       This table is used to config the soft Parameters of SIP interface.
       The index of this entry is hwSipMgInterfaceIndex.
       "
     INDEX    {
                hwSipMgInterfaceIndex
              }
    ::= { hwSipMgSoftParameterTable 1 }

   HwSipMgSoftParameterEntry ::=
     SEQUENCE
     {
       hwSipMgInterfaceIndex     Integer32,
       hwSipMgSoftParameter0     INTEGER,
       hwSipMgSoftParameter1     INTEGER,
       hwSipMgSoftParameter2     INTEGER,
       hwSipMgSoftParameter3     INTEGER,
       hwSipMgSoftParameter4     INTEGER,
       hwSipMgSoftParameter5     INTEGER,
       hwSipMgSoftParameter6     INTEGER,
       hwSipMgSoftParameter7     INTEGER,
       hwSipMgSoftParameter8     INTEGER,
       hwSipMgSoftParameter9     INTEGER,
       hwSipMgSoftParameter10    INTEGER,
       hwSipMgSoftParameter11    INTEGER,
       hwSipMgSoftParameter12    INTEGER,
       hwSipMgSoftParameter13    INTEGER,
       hwSipMgSoftParameter14    INTEGER,
       hwSipMgSoftParameter15    INTEGER,
       hwSipMgSoftParameter16    INTEGER,
       hwSipMgSoftParameter17    INTEGER,
       hwSipMgSoftParameter18    INTEGER,
       hwSipMgSoftParameter19    INTEGER,
       hwSipMgSoftParameter20    INTEGER,
       hwSipMgSoftParameter21    INTEGER,
       hwSipMgSoftParameter22    INTEGER,
       hwSipMgSoftParameter23    Integer32,
       hwSipMgSoftParameter24    INTEGER,
       hwSipMgSoftParameter25    INTEGER,
       hwSipMgSoftParameter26    Integer32,
       hwSipMgSoftParameter27    Integer32,
       hwSipMgSoftParameter28    INTEGER,
       hwSipMgSoftParameter29    Integer32
     }

     hwSipMgInterfaceIndex OBJECT-TYPE
     SYNTAX      Integer32(0..16777215)
     MAX-ACCESS  not-accessible
     STATUS      current
     DESCRIPTION
         "
         SIP GateWay ID.
         "
     ::= { hwSipMgSoftParameterEntry 1 }

     hwSipMgSoftParameter0 OBJECT-TYPE
     SYNTAX      INTEGER{busy(1),        -- busy tone
                         congestion(2),  -- congestion tone
                         mute(3),        -- mute 
                         userdefine1(4), -- user define 1
                         userdefine2 (5) -- user define 2
                         }
     MAX-ACCESS  read-write
     STATUS      deprecated
     DESCRIPTION
         "
         The SIP MgSoftParameter0. Local Block Tone Type.
         Options:
         1. busy(1)         -busy tone
         2. congestion(2)   -congestion tone
         3. mute(3)         -mute 
         4. userdefine1(4)  -user define 1
         5. userdefine2 (5) -user define 2
         Default: busy(1)
         "
     ::= { hwSipMgSoftParameterEntry 2 }

  hwSipMgSoftParameter1 OBJECT-TYPE
     SYNTAX      INTEGER{busy(1),         -- busy tone
                         congestion(2),   -- congestion tone
                         mute(3),         -- mute 
                         userdefine1(4),  -- user define 1
                         userdefine2 (5)  -- user define 2
                         }
     MAX-ACCESS  read-write
     STATUS      deprecated
     DESCRIPTION
         "
         the SIP MgSoftParameter1. Remote Block Tone Type.
         Options:
         1. busy(1)         -busy tone
         2. congestion(2)   -congestion tone
         3. mute(3)         -mute 
         4. userdefine1(4)  -user define 1
         5. userdefine2 (5) -user define 2
         Default: busy(1)
         "
     ::= { hwSipMgSoftParameterEntry 3 }

  hwSipMgSoftParameter2 OBJECT-TYPE
     SYNTAX      INTEGER{enable(1),
                         disable(2)
                         }
     MAX-ACCESS  read-write
     STATUS      current
     DESCRIPTION
         "
         the SIP stand-alone flag
         Options:
         1. enable(1)        -support stand-alone
         2. disable(2)       -not support stand-alone
         Default: disable(2)
         "
     ::= { hwSipMgSoftParameterEntry 4 }

   hwSipMgSoftParameter3 OBJECT-TYPE
     SYNTAX      INTEGER{noControl(1),
                         callerControl(2),
                         calleeControl(3)
                         }
     MAX-ACCESS  read-write
     STATUS      current
     DESCRIPTION
         "
         the right of call control in normal call        
         Options:
         1. noControl(1)         -none control
         2. callerControl(2)     -caller control
         3. calleeControl(3)     -callee control
         Default: noControl(1)
         "
     ::= { hwSipMgSoftParameterEntry 5 }

   hwSipMgSoftParameter4 OBJECT-TYPE
     SYNTAX      INTEGER{noControl(1),
                         callerControl(2),
                         calleeControl(3),
                         emergencyCallCenterControl(4)
                         }
     MAX-ACCESS  read-write
     STATUS      current
     DESCRIPTION
         "
         the right of call control in emergency call
         Options:
         1. noControl(1)         -none control
         2. callerControl(2)     -caller control
         3. calleeControl(3)     -callee control
         4. emergencyCallCenterControl(4)     -Controlled by the emergency call control center
         Default: noControl(1)
         "
     ::= { hwSipMgSoftParameterEntry 6 }

   hwSipMgSoftParameter5 OBJECT-TYPE
     SYNTAX      INTEGER{close(1),
                         noControl(2)
                         }
     MAX-ACCESS  read-write
     STATUS      current
     DESCRIPTION
         "
         The flag of silence suppression in emergency call.
         Options:
         1. close(1)         -force close silence suppression when the call is emergency call
         2. noControl(2)     -the silence suppression is not controlled by the emergency call type
         Default: noControl(2)
         "
     ::= { hwSipMgSoftParameterEntry 7 }

   hwSipMgSoftParameter6 OBJECT-TYPE
     SYNTAX      INTEGER{enable(1),disable(2)}
     MAX-ACCESS  read-write
     STATUS      current
     DESCRIPTION
         "
         Whether to permit emergency calls when the port is remotely blocked.
         Options:
         1. enable(1)   -permit
         2. disable(2)  -not permit
         Default: disable(2)
         "
     ::= { hwSipMgSoftParameterEntry 8 }

   hwSipMgSoftParameter7 OBJECT-TYPE
     SYNTAX      INTEGER{yes(1),no(2)}
     MAX-ACCESS  read-write
     STATUS      current
     DESCRIPTION
         "
         The SIP MgSoftParameter7. Reserved.
         Options:
         1. yes(1) -yes
         2. no(2)  -no
         "
     ::= { hwSipMgSoftParameterEntry 9 }

   hwSipMgSoftParameter8 OBJECT-TYPE
     SYNTAX      INTEGER{disable(1),enable(2)}
     MAX-ACCESS  read-write
     STATUS      current
     DESCRIPTION
         "
         Enables the user options heartbeat message
         Options:
         1. disable(1) -disable
         2. enable(2)  -enable
         Default: disable(1)
         "
     ::= { hwSipMgSoftParameterEntry 10 }

   hwSipMgSoftParameter9 OBJECT-TYPE
     SYNTAX      INTEGER{yes(1),no(2)}
     MAX-ACCESS  read-write
     STATUS      current
     DESCRIPTION
         "
         The SIP MgSoftParameter9. Reserved.
         Options:
         1. yes(1) -yes
         2. no(2)  -no
         "
     ::= { hwSipMgSoftParameterEntry 11 }

   hwSipMgSoftParameter10 OBJECT-TYPE
     SYNTAX      INTEGER{yes(1),no(2)}
     MAX-ACCESS  read-write
     STATUS      current
     DESCRIPTION
         "
         The SIP MgSoftParameter10. Reserved.
         Options:
         1. yes(1) -yes
         2. no(2)  -no
         "
     ::= { hwSipMgSoftParameterEntry 12 }

   hwSipMgSoftParameter11 OBJECT-TYPE
     SYNTAX      INTEGER{yes(1),no(2)}
     MAX-ACCESS  read-write
     STATUS      current
     DESCRIPTION
         "
         The SIP MgSoftParameter11. Reserved.
         Options:
         1. yes(1) -yes
         2. no(2)  -no
         "
     ::= { hwSipMgSoftParameterEntry 13 }

   hwSipMgSoftParameter12 OBJECT-TYPE
     SYNTAX      INTEGER{yes(1),no(2)}
     MAX-ACCESS  read-write
     STATUS      current
     DESCRIPTION
         "
         The SIP MgSoftParameter12. Reserved.
         Options:
         1. yes(1) -yes
         2. no(2)  -no
         "
     ::= { hwSipMgSoftParameterEntry 14 }

  hwSipMgSoftParameter13 OBJECT-TYPE
     SYNTAX      INTEGER{min(1),max(2)}
     MAX-ACCESS  read-write
     STATUS      current
     DESCRIPTION
         "
         The SIP MgSoftParameter13. Digitmap matching mode. 
         Options:
         1. min(1) -shortest
         2. max(2) -longest
         Default: min(1)
         "
     ::= { hwSipMgSoftParameterEntry 15 }

  hwSipMgSoftParameter14 OBJECT-TYPE
     SYNTAX      INTEGER{yes(1),no(2)}
     MAX-ACCESS  read-write
     STATUS      current
     DESCRIPTION
         "
         The SIP MgSoftParameter14. Reserved.
         Options:
         1. yes(1) -yes
         2. no(2)  -no
         "
     ::= { hwSipMgSoftParameterEntry 16 }

  hwSipMgSoftParameter15 OBJECT-TYPE
     SYNTAX      INTEGER{nofilter(1),filter(2)}
     MAX-ACCESS  read-write
     STATUS      current
     DESCRIPTION
         "
         The SIP MgSoftParameter15, RTP filter switch. 
         Options:
         1. nofilter(1) -No Filter
         2. filter(2)   -Filter
         Default: nofilter(1)
         "
     ::= { hwSipMgSoftParameterEntry 17 }

  hwSipMgSoftParameter16 OBJECT-TYPE
     SYNTAX      INTEGER{yes(1),no(2)}
     MAX-ACCESS  read-write
     STATUS      current
     DESCRIPTION
         "
         The SIP MgSoftParameter16. Reserved.
         Options:
         1. yes(1) -yes
         2. no(2)  -no
         "
     ::= { hwSipMgSoftParameterEntry 18 }

  hwSipMgSoftParameter17 OBJECT-TYPE
     SYNTAX      INTEGER{yes(1),no(2)}
     MAX-ACCESS  read-write
     STATUS      current
     DESCRIPTION
         "
         The SIP MgSoftParameter17. Reserved.
         Options:
         1. yes(1) -yes
         2. no(2)  -no
         "
     ::= { hwSipMgSoftParameterEntry 19 }

  hwSipMgSoftParameter18 OBJECT-TYPE
     SYNTAX      INTEGER{yes(1),no(2)}
     MAX-ACCESS  read-write
     STATUS      current
     DESCRIPTION
         "
         The SIP MgSoftParameter18. Reserved.
         Options:
         1. yes(1) -yes
         2. no(2)  -no
         "
     ::= { hwSipMgSoftParameterEntry 20 }

  hwSipMgSoftParameter19 OBJECT-TYPE
     SYNTAX      INTEGER{yes(1),no(2)}
     MAX-ACCESS  read-write
     STATUS      current
     DESCRIPTION
         "
         The SIP MgSoftParameter19. Reserved.
         Options:
         1. yes(1) -yes
         2. no(2)  -no
         "
     ::= { hwSipMgSoftParameterEntry 21 }

  hwSipMgSoftParameter20 OBJECT-TYPE
     SYNTAX      INTEGER{yes(1),no(2)}
     MAX-ACCESS  read-write
     STATUS      current
     DESCRIPTION
         "
         The SIP MgSoftParameter20. Reserved.
         Options:
         1. yes(1) -yes
         2. no(2)  -no
         "
     ::= { hwSipMgSoftParameterEntry 22 }

  hwSipMgSoftParameter21 OBJECT-TYPE
     SYNTAX      INTEGER{yes(1),no(2)}
     MAX-ACCESS  read-write
     STATUS      current
     DESCRIPTION
         "
         The SIP MgSoftParameter21. Reserved.
         Options:
         1. yes(1) -yes
         2. no(2)  -no
         "
     ::= { hwSipMgSoftParameterEntry 23 }

  hwSipMgSoftParameter22 OBJECT-TYPE
     SYNTAX      INTEGER{yes(1),no(2)}
     MAX-ACCESS  read-write
     STATUS      current
     DESCRIPTION
         "
         The SIP MgSoftParameter22. Reserved.
         Options:
         1. yes(1) -yes
         2. no(2)  -no
         "
     ::= { hwSipMgSoftParameterEntry 24 }

  hwSipMgSoftParameter23 OBJECT-TYPE
     SYNTAX      Integer32(1..65534)
     MAX-ACCESS  read-write
     STATUS      current
     DESCRIPTION
         "
         The SIP MgSoftParameter23. Life time carried in the registration message. 
         Default: 600
         "

     ::= { hwSipMgSoftParameterEntry 25 }

  hwSipMgSoftParameter24 OBJECT-TYPE
     SYNTAX      INTEGER{timode(1),nonsupport(2)}
     MAX-ACCESS  read-write
     STATUS      current
     DESCRIPTION
         "
         The SIP MgSoftParameter24. QoS start rtcp static. 
         Options:
         1. timode(1) -TI mode
         2. nonsupport(2) -not support
         Default: nonsupport(2)
         "
     ::= { hwSipMgSoftParameterEntry 26 }
     
  hwSipMgSoftParameter25 OBJECT-TYPE
     SYNTAX      INTEGER{enable(1),disable(2)}
     MAX-ACCESS  read-write
     STATUS      current
     DESCRIPTION
         "
         The SIP MgSoftParameter25. Function of switching pulse signals and flash-hook events to DTMF signals. 
         Options:
         1. enable(1) -enable
         2. disable(2) -disable
         Default: disable(2)
         "
     ::= { hwSipMgSoftParameterEntry 27 }
     
  hwSipMgSoftParameter26 OBJECT-TYPE
     SYNTAX      Integer32(1..65535)
     MAX-ACCESS  read-write
     STATUS      current
     DESCRIPTION
         "
         The SIP MgSoftParameter26. Retry register interval. 
         Default: 30
         Unit: second
         "
     ::= { hwSipMgSoftParameterEntry 28 }     
 
  hwSipMgSoftParameter27 OBJECT-TYPE
     SYNTAX      Integer32(0..255)
     MAX-ACCESS  read-write
     STATUS      current
     DESCRIPTION
         "
         The SIP MgSoftParameter27. Length of defer hotline timer. 
         Default: 5
         Unit: second
         "
     ::= { hwSipMgSoftParameterEntry 29 } 

  hwSipMgSoftParameter28 OBJECT-TYPE
     SYNTAX      INTEGER{local(1),network(2)}
     MAX-ACCESS  read-write
     STATUS      current
     DESCRIPTION
         "
         The SIP MgSoftParameter28. Three-party audio mixing. 
         Options:
         1. local(1) -local audio mixing
         2. network(2) -network audio mixing
         Default: local(1)
         "
     ::= { hwSipMgSoftParameterEntry 30 }     
     
  hwSipMgSoftParameter29 OBJECT-TYPE
     SYNTAX      Integer32(0..65535)
     MAX-ACCESS  read-write
     STATUS      current
     DESCRIPTION
         "
         Service rights are set based on VAG interface. 
         Each service is represented with one bit(0: users have no service right; 1: users have a service right). 
         There are four bits in use, leaving other bits reserved, and the represented services are subAddress, UUS, CUG, and CDIV from low bits to high bits.
         Default: 65535
         "
     ::= { hwSipMgSoftParameterEntry 31 }  
     
  hwSipDmmParaTable OBJECT-TYPE
     SYNTAX      SEQUENCE OF HwSipDmmParaEntry
     MAX-ACCESS  not-accessible
     STATUS      current
     DESCRIPTION
       "
       This table is used to config the digitmap.
       The index of this table is hwSipDmmParaMgId.
       "
     ::= { hwVoipSipObjects 9 }

  hwSipDmmParaEntry OBJECT-TYPE
     SYNTAX      HwSipDmmParaEntry
     MAX-ACCESS  not-accessible
     STATUS      current
     DESCRIPTION
       "
       This table is used to config the digitmap.
       The index of this entry is hwSipDmmParaMgId.
       "
     INDEX    {
               hwSipDmmParaMgId
              }
     ::= { hwSipDmmParaTable 1 }

  HwSipDmmParaEntry ::=
     SEQUENCE
     {
       hwSipDmmParaMgId	   Unsigned32,
       hwSipDmmParaStartTimer Unsigned32,
       hwSipDmmParaShortTimer Unsigned32,
       hwSipDmmParaLongTimer  Unsigned32
     }

  hwSipDmmParaMgId OBJECT-TYPE
     SYNTAX      Unsigned32(0..16777215)
     MAX-ACCESS  not-accessible
     STATUS      current
     DESCRIPTION
         "
         Indicates the MG ID.
         "
     ::= { hwSipDmmParaEntry 1 }

  hwSipDmmParaStartTimer OBJECT-TYPE
     SYNTAX      Unsigned32(0..99)
     MAX-ACCESS  read-write
     STATUS      current
     DESCRIPTION
         "
         Indicates the length of the DMM start timer.
         Default: 20
         Unit: second
         "
     ::= { hwSipDmmParaEntry 2 }

  hwSipDmmParaShortTimer OBJECT-TYPE
     SYNTAX      Unsigned32(1..99)
     MAX-ACCESS  read-write
     STATUS      current
     DESCRIPTION
         "
         Indicates the length of the DMM short timer.
         Default: 4
         Unit: second
         "
     ::= { hwSipDmmParaEntry 3 }

  hwSipDmmParaLongTimer OBJECT-TYPE
     SYNTAX      Unsigned32(1..99)
     MAX-ACCESS  read-write
     STATUS      current
     DESCRIPTION
         "
         Indicates the length of the DMM long timer.
         Default: 20
         Unit: second
         "
     ::= { hwSipDmmParaEntry 4 }

------------------------------------------------------------------------


   ------  /* Start hwIASSipTrapsVbOids */

     hwSipTrapRequestID OBJECT-TYPE
     SYNTAX Unsigned32(0..4294967295)
     MAX-ACCESS accessible-for-notify
     STATUS current
     DESCRIPTION
         "
         The SIP trap request ID.
         "
     ::= { hwIASSipTrapsVbOids 1 }

     hwSipMgResetResult OBJECT-TYPE
         SYNTAX INTEGER
         {
             success(0),
             failed(1)
         }
         MAX-ACCESS accessible-for-notify
         STATUS current
         DESCRIPTION
             "
    	     The result of the SIP media gateway reset.
    	     Options:
    	     1. success(0) -reset succesful
    	     2. failed(1)  -reset failed
             "
         ::= { hwIASSipTrapsVbOids 2 }

     hwSipProxySign OBJECT-TYPE
     SYNTAX      Unsigned32(0..2)
     MAX-ACCESS accessible-for-notify
     STATUS current
     DESCRIPTION
         "
    	 The SIP proxy sign.
    	 0 -main
    	 1 -standby
         "
     ::= { hwIASSipTrapsVbOids 3 }

 ------  /*  End  hwIASSipTrapsVbOids */

 ------  /* Start hwIASSipCommonTraps */

     hwIASSipResetTrap NOTIFICATION-TYPE
     OBJECTS { hwSipTrapRequestID, hwSipVgwId, hwSipMgResetResult }
     STATUS current
     DESCRIPTION
         "
         This notification indicates that the result of SIP media gateway reset operation.
         "
     ::= { hwIASSipCommonTraps 0 1 }

 ------  /*  End  hwIASSipCommonTraps */

 ------  /* Start hwIASSipAlarmTraps */

    hwIASSipProxyFaultTrap NOTIFICATION-TYPE
    OBJECTS  { hwSipVgwId, hwSipProxySign }
    STATUS      current
    DESCRIPTION
        "
        This notification indicates that the SIP proxy server is abnormal.
        "
    ::= { hwIASSipAlarmTraps 0 1 }

    hwIASSipProxyRestoreTrap NOTIFICATION-TYPE
    OBJECTS  { hwSipVgwId, hwSipProxySign }
    STATUS      current
    DESCRIPTION
        "
        This notification indicates that the SIP proxy server restores from abnormal.
        "
    ::= { hwIASSipAlarmTraps 0 2 }

 ------  /*  End  hwIASSipAlarmTraps */

  hwVoiceUserGroupConfigTable OBJECT-TYPE
     SYNTAX      SEQUENCE OF HwVoiceUserGroupConfigEntry
     MAX-ACCESS  not-accessible
     STATUS      current
     DESCRIPTION
       "
       This table is used to config the parameters of sip user group.
       The indexes of this table are hwSipUserGroupVgwId, hwSipUserGroupid.
       "
     ::= { hwVoipSipObjects 10 }

   hwVoiceUserGroupConfigEntry OBJECT-TYPE
     SYNTAX      HwVoiceUserGroupConfigEntry
     MAX-ACCESS  not-accessible
     STATUS      current
     DESCRIPTION
       "
       This table is used to config the parameters of sip user group.
       The indexes of this entry are hwSipUserGroupVgwId, hwSipUserGroupid.
       "
     INDEX    {
                hwSipUserGroupVgwId,
                hwSipUserGroupid
              }
     ::= { hwVoiceUserGroupConfigTable 1 }

   HwVoiceUserGroupConfigEntry ::=
     SEQUENCE
     {
       hwSipUserGroupVgwId Integer32,
       hwSipUserGroupid Integer32,
       hwSipUserGroupRegisterUriMode INTEGER,
       hwSipUserGroupUri  OCTET STRING,
       hwSipUserGroupName  OCTET STRING,
       hwSipUserGroupAuthUserName  OCTET STRING,
       hwSipUserGroupAuthPassWordMode INTEGER,
       hwSipUserGroupAuthPassword  OCTET STRING,
       hwSipUserGroupAuthHA1  OCTET STRING,
       hwSipUserGroupPrecinctMode INTEGER,
       hwSipUserGroupSubscribeUaProfileFlag INTEGER,
       hwSipUserGroupRowStatus RowStatus,
       hwSipUserGroupAdminStatus INTEGER,
       hwSipUserGroupRunningState INTEGER
    }



    hwSipUserGroupVgwId OBJECT-TYPE
     SYNTAX      Integer32(0..16777215)
     MAX-ACCESS  not-accessible
     STATUS      current
     DESCRIPTION
         "
         SIP GateWay ID.
         "
     ::= { hwVoiceUserGroupConfigEntry 1 }

    hwSipUserGroupid OBJECT-TYPE
     SYNTAX      Integer32(0..65535)
     MAX-ACCESS  not-accessible
     STATUS      current
     DESCRIPTION
         "
         User Group ID.
         "
     ::= { hwVoiceUserGroupConfigEntry 2 }

   hwSipUserGroupRegisterUriMode OBJECT-TYPE
     SYNTAX      INTEGER{inneruser(1),alone(2)}
     MAX-ACCESS  read-write
     STATUS      current
     DESCRIPTION
         "
         Indicates the user group register URI mode.
         Options:
         1. inneruser(1) -inner user
         2. alone(2) -alone
         "
     ::= { hwVoiceUserGroupConfigEntry 3 }

    hwSipUserGroupUri OBJECT-TYPE
     SYNTAX      OCTET STRING(SIZE (0..64))
     MAX-ACCESS  read-write
     STATUS      current
     DESCRIPTION
         "
         Indicates the Register-URI of the sip user group.
         "
     ::= { hwVoiceUserGroupConfigEntry 4 }

    hwSipUserGroupName OBJECT-TYPE
     SYNTAX      OCTET STRING(SIZE (0..64))
     MAX-ACCESS  read-write
     STATUS      current
     DESCRIPTION
         "
         Indicates the sip user group Name.
         "
     ::= { hwVoiceUserGroupConfigEntry 5 }

    hwSipUserGroupAuthUserName OBJECT-TYPE
     SYNTAX      OCTET STRING(SIZE (0..64))
     MAX-ACCESS  read-write
     STATUS      current
     DESCRIPTION
         "
         Indicates the Auth Username of the sip user group.
         "
     ::= { hwVoiceUserGroupConfigEntry 6 }

   hwSipUserGroupAuthPassWordMode OBJECT-TYPE
     SYNTAX      INTEGER{password(1),ha1(2)}
     MAX-ACCESS  read-write
     STATUS      current
     DESCRIPTION
         "
         Indicates the Auth PasswordMode of the sip user group.
         Options:
         1. password(1) -auth by password
         2. ha1(2)      -auth by HA1
         "
     ::= { hwVoiceUserGroupConfigEntry 7 }

    hwSipUserGroupAuthPassword OBJECT-TYPE
     SYNTAX      OCTET STRING(SIZE (0..64))
     MAX-ACCESS  read-write
     STATUS      current
     DESCRIPTION
         "
         Indicates the Auth Password of the sip user group.
         "
     ::= { hwVoiceUserGroupConfigEntry 8 }

    hwSipUserGroupAuthHA1 OBJECT-TYPE
     SYNTAX      OCTET STRING(SIZE (0..32))
     MAX-ACCESS  read-write
     STATUS      current
     DESCRIPTION
         "
         Indicates the Auth HA1 value of the sip user group.
         "
     ::= { hwVoiceUserGroupConfigEntry 9 }

   hwSipUserGroupPrecinctMode OBJECT-TYPE
     SYNTAX      INTEGER{local(1), remote(2)}
     MAX-ACCESS  read-write
     STATUS      current
     DESCRIPTION
         "
         Indicates the user PrecinctMode in the sip user group.
         Options:
         1. local(1) -local
         2. remote(2) -remote
         "
     ::= { hwVoiceUserGroupConfigEntry 10 }

   hwSipUserGroupSubscribeUaProfileFlag OBJECT-TYPE
     SYNTAX      INTEGER{enable(1),disable(2)}
     MAX-ACCESS  read-write
     STATUS      current
     DESCRIPTION
         "
         Indicates the flag of the user group with the same UA Profile privilege.
         Options:
         1. enable(1) -enable
         2. disable(2) -disable
         "
     ::= { hwVoiceUserGroupConfigEntry 11 }

   hwSipUserGroupRowStatus OBJECT-TYPE
     SYNTAX      RowStatus
     MAX-ACCESS  read-write
     STATUS      current
     DESCRIPTION
         "
         This is used to create new rows in this table, modify existing rows, and to delete existing rows.
         "
     ::= { hwVoiceUserGroupConfigEntry 12 }

   hwSipUserGroupAdminStatus OBJECT-TYPE
     SYNTAX      INTEGER{endservice(1),startservice(2)}
     MAX-ACCESS  read-write
     STATUS      current
     DESCRIPTION
         "
         Indicates the admin operation of the sip user group.
         Options:
         1. endservice(1) -end service
         2. startservice(2) -start service
         "
     ::= { hwVoiceUserGroupConfigEntry 13 }

   hwSipUserGroupRunningState OBJECT-TYPE
     SYNTAX      INTEGER{null(1),startSvc(2),rBlock(3),lBlock(4)}
     MAX-ACCESS  read-only
     STATUS      current
     DESCRIPTION
         "
         Indicates the service state of user group.
         Options:
         1. null(1) -null
         2. startSvc(2) -start service
         3. rBlock(3) -remote block
         4. lBlock(4) -local block
         "
     ::= { hwVoiceUserGroupConfigEntry 14 }

------------------------------------------------------------------------

     hwSipMgSoftStringParameterConfigTable OBJECT-TYPE
     SYNTAX      SEQUENCE OF HwSipMgSoftStringParameterConfigEntry
     MAX-ACCESS  not-accessible
     STATUS      current
     DESCRIPTION
       "
       This table is used to config the soft string Parameters of SIP interface.
       The index of this table is hwSipMgSoftStringMgInterfaceIndexConfig.
       "
    ::= { hwVoipSipObjects 11 }

   hwSipMgSoftStringParameterConfigEntry OBJECT-TYPE
     SYNTAX      HwSipMgSoftStringParameterConfigEntry
     MAX-ACCESS  not-accessible
     STATUS      current
     DESCRIPTION
       "
       This table is used to config the soft string Parameters of SIP interface.
       The index of this entry is hwSipMgSoftStringMgInterfaceIndexConfig.
       "
     INDEX    {
                hwSipMgSoftStringMgInterfaceIndexConfig
              }
    ::= { hwSipMgSoftStringParameterConfigTable 1 }

   HwSipMgSoftStringParameterConfigEntry ::=
     SEQUENCE
     {
       hwSipMgSoftStringMgInterfaceIndexConfig     Integer32,
       hwSipMgSoftStringConfigParameter0     OCTET STRING,
       hwSipMgSoftStringConfigParameter1     OCTET STRING,
       hwSipMgSoftStringConfigParameter2     OCTET STRING,
       hwSipMgSoftStringConfigParameter3     OCTET STRING,
       hwSipMgSoftStringConfigParameter4     OCTET STRING,
       hwSipMgSoftStringConfigParameter5     OCTET STRING,
       hwSipMgSoftStringConfigParameter6     OCTET STRING,
       hwSipMgSoftStringConfigParameter7     OCTET STRING,
       hwSipMgSoftStringConfigParameter8     OCTET STRING,
       hwSipMgSoftStringConfigParameter9     OCTET STRING,
       hwSipMgSoftStringConfigParameter10    OCTET STRING,
       hwSipMgSoftStringConfigParameter11    OCTET STRING,
       hwSipMgSoftStringConfigParameter12    OCTET STRING,
       hwSipMgSoftStringConfigParameter13    OCTET STRING,
       hwSipMgSoftStringConfigParameter14    OCTET STRING,
       hwSipMgSoftStringConfigParameter15    OCTET STRING,
       hwSipMgSoftStringConfigParameter16    OCTET STRING,
       hwSipMgSoftStringConfigParameter17    OCTET STRING,
       hwSipMgSoftStringConfigParameter18    OCTET STRING,
       hwSipMgSoftStringConfigParameter19    OCTET STRING,
       hwSipMgSoftStringConfigParameter20    OCTET STRING,
       hwSipMgSoftStringConfigParameter21    OCTET STRING,
       hwSipMgSoftStringConfigParameter22    OCTET STRING,
       hwSipMgSoftStringConfigParameter23    OCTET STRING,
       hwSipMgSoftStringConfigParameter24    OCTET STRING,
       hwSipMgSoftStringConfigParameter25    OCTET STRING,
       hwSipMgSoftStringConfigParameter26    OCTET STRING,
       hwSipMgSoftStringConfigParameter27    OCTET STRING,
       hwSipMgSoftStringConfigParameter28    OCTET STRING,
       hwSipMgSoftStringConfigParameter29    OCTET STRING,
       hwSipMgSoftStringConfigParameter30    OCTET STRING,
       hwSipMgSoftStringConfigParameter31    OCTET STRING,
       hwSipMgSoftStringConfigParameter32    OCTET STRING,
       hwSipMgSoftStringConfigParameter33    OCTET STRING,
       hwSipMgSoftStringConfigParameter34    OCTET STRING,
       hwSipMgSoftStringConfigParameter35    OCTET STRING, 
       hwSipMgSoftStringConfigParameter36    OCTET STRING,
       hwSipMgSoftStringConfigParameter37    OCTET STRING,
       hwSipMgSoftStringConfigParameter38    OCTET STRING,
       hwSipMgSoftStringConfigParameter39    OCTET STRING,
       hwSipMgSoftStringConfigParameter40    OCTET STRING,
       hwSipMgSoftStringConfigParameter41    OCTET STRING,
       hwSipMgSoftStringConfigParameter42    OCTET STRING
     }

     hwSipMgSoftStringMgInterfaceIndexConfig OBJECT-TYPE
     SYNTAX      Integer32(0..16777215)
     MAX-ACCESS  not-accessible
     STATUS      current
     DESCRIPTION
         "
         SIP GateWay ID.
         "
     ::= { hwSipMgSoftStringParameterConfigEntry 1 }

     hwSipMgSoftStringConfigParameter0 OBJECT-TYPE
     SYNTAX      OCTET STRING(SIZE (0..64))
     MAX-ACCESS  read-write
     STATUS      current
     DESCRIPTION
         "
         The SIP MgSoftStringConfigParameter0, Reserved.
         "
     ::= { hwSipMgSoftStringParameterConfigEntry 2 }

  hwSipMgSoftStringConfigParameter1 OBJECT-TYPE
     SYNTAX      OCTET STRING(SIZE (0..64))
     MAX-ACCESS  read-write
     STATUS      current
     DESCRIPTION
         "
         The SIP MgSoftStringConfigParameter1, visited network.
         "
     ::= { hwSipMgSoftStringParameterConfigEntry 3 }

  hwSipMgSoftStringConfigParameter2 OBJECT-TYPE
     SYNTAX      OCTET STRING(SIZE (0..64))
     MAX-ACCESS  read-write
     STATUS      current
     DESCRIPTION
         "
         The SIP MgSoftStringConfigParameter2. Prefix of national long-distance call.
         "
     ::= { hwSipMgSoftStringParameterConfigEntry 4 }

   hwSipMgSoftStringConfigParameter3 OBJECT-TYPE
     SYNTAX      OCTET STRING(SIZE (0..64))
     MAX-ACCESS  read-write
     STATUS      current
     DESCRIPTION
         "
         The SIP MgSoftStringConfigParameter3. Prefix of international long-distance call.
         "
     ::= { hwSipMgSoftStringParameterConfigEntry 5 }

   hwSipMgSoftStringConfigParameter4 OBJECT-TYPE
     SYNTAX      OCTET STRING(SIZE (0..64))
     MAX-ACCESS  read-write
     STATUS      current
     DESCRIPTION
         "
         The SIP MgSoftStringConfigParameter4. CC number string.
         "
     ::= { hwSipMgSoftStringParameterConfigEntry 6 }

   hwSipMgSoftStringConfigParameter5 OBJECT-TYPE
     SYNTAX      OCTET STRING(SIZE (0..64))
     MAX-ACCESS  read-write
     STATUS      current
     DESCRIPTION
         "
         The SIP MgSoftStringConfigParameter5. NDC number string.
         "
     ::= { hwSipMgSoftStringParameterConfigEntry 7 }

   hwSipMgSoftStringConfigParameter6 OBJECT-TYPE
     SYNTAX      OCTET STRING(SIZE (0..64))
     MAX-ACCESS  read-write
     STATUS      current
     DESCRIPTION
         "
         The SIP MgSoftStringConfigParameter6. SCC domain name.
         "
     ::= { hwSipMgSoftStringParameterConfigEntry 8 }

   hwSipMgSoftStringConfigParameter7 OBJECT-TYPE
     SYNTAX      OCTET STRING(SIZE (0..64))
     MAX-ACCESS  read-write
     STATUS      current
     DESCRIPTION
         "
         The SIP MgSoftStringConfigParameter7. Reserved.
         "
     ::= { hwSipMgSoftStringParameterConfigEntry 9 }

   hwSipMgSoftStringConfigParameter8 OBJECT-TYPE
     SYNTAX      OCTET STRING(SIZE (0..64))
     MAX-ACCESS  read-write
     STATUS      current
     DESCRIPTION
         "
         The SIP MgSoftStringConfigParameter8. Reserved.
         "
     ::= { hwSipMgSoftStringParameterConfigEntry 10 }

   hwSipMgSoftStringConfigParameter9 OBJECT-TYPE
     SYNTAX      OCTET STRING(SIZE (0..64))
     MAX-ACCESS  read-write
     STATUS      current
     DESCRIPTION
         "
         The SIP MgSoftStringConfigParameter9. Reserved.
         "
     ::= { hwSipMgSoftStringParameterConfigEntry 11 }

   hwSipMgSoftStringConfigParameter10 OBJECT-TYPE
     SYNTAX      OCTET STRING(SIZE (0..64))
     MAX-ACCESS  read-write
     STATUS      current
     DESCRIPTION
         "
         The SIP MgSoftStringConfigParameter10. Reserved.
         "
     ::= { hwSipMgSoftStringParameterConfigEntry 12 }

   hwSipMgSoftStringConfigParameter11 OBJECT-TYPE
     SYNTAX      OCTET STRING(SIZE (0..64))
     MAX-ACCESS  read-write
     STATUS      current
     DESCRIPTION
         "
         The SIP MgSoftStringConfigParameter11. Character string indicating that CLID or COLP is unavailable.
         "
     ::= { hwSipMgSoftStringParameterConfigEntry 13 }

   hwSipMgSoftStringConfigParameter12 OBJECT-TYPE
     SYNTAX      OCTET STRING(SIZE (0..64))
     MAX-ACCESS  read-write
     STATUS      current
     DESCRIPTION
         "
         The SIP MgSoftStringConfigParameter12. Reserved.
         "
     ::= { hwSipMgSoftStringParameterConfigEntry 14 }

  hwSipMgSoftStringConfigParameter13 OBJECT-TYPE
     SYNTAX      OCTET STRING(SIZE (0..64))
     MAX-ACCESS  read-write
     STATUS      current
     DESCRIPTION
         "
         The SIP MgSoftStringConfigParameter13. Character string indicating that CLID or COLP is not subscribed.
         "
     ::= { hwSipMgSoftStringParameterConfigEntry 15 }

  hwSipMgSoftStringConfigParameter14 OBJECT-TYPE
     SYNTAX      OCTET STRING(SIZE (0..64))
     MAX-ACCESS  read-write
     STATUS      current
     DESCRIPTION
         "
         The SIP MgSoftStringConfigParameter14. SCC code of the MCID service.
         Pattern for similar regular expressions:
         1 Supported characters: *#xX[]().^|-0123456789'capital parentheses';
         2 x and X indicate a digit ranging from 0 to 9;
         3 [] indicates a matching range. For example, [0-37] indicates matching range 01237;
         4 'capital parentheses'indicates the maximum number that the preceding item can be mapped. The range is 0 to 64;
         5 () is used to extract characters in some scenarios;
         6 . indicates that the preceding item can be mapped to one to multiple times;
         7 ^ can only be the first symbol in [], indicating a supplementary set of a common mapping range. For example, [^0-7] indicates mapping range 89*#
         8 | is used to separate multiple sub-expressions and each sub-expression is mapped separately;
         9 - is used in [] or 'capital parentheses', indicating a range from the previous digit to the subsequent digit;
         "
     ::= { hwSipMgSoftStringParameterConfigEntry 16 }

  hwSipMgSoftStringConfigParameter15 OBJECT-TYPE
     SYNTAX      OCTET STRING(SIZE (0..64))
     MAX-ACCESS  read-write
     STATUS      current
     DESCRIPTION
         "
         The SIP MgSoftStringConfigParameter15. SCC code for activating the CFU service.
         "
     ::= { hwSipMgSoftStringParameterConfigEntry 17 }

  hwSipMgSoftStringConfigParameter16 OBJECT-TYPE
     SYNTAX      OCTET STRING(SIZE (0..64))
     MAX-ACCESS  read-write
     STATUS      current
     DESCRIPTION
         "
         The SIP MgSoftStringConfigParameter16. SCC code for deactivating the CFU service.
         "
     ::= { hwSipMgSoftStringParameterConfigEntry 18 }

  hwSipMgSoftStringConfigParameter17 OBJECT-TYPE
     SYNTAX      OCTET STRING(SIZE (0..64))
     MAX-ACCESS  read-write
     STATUS      current
     DESCRIPTION
         "
         The SIP MgSoftStringConfigParameter17. Owner name of o-row parameter of SDP. If is not configured, the default value is Huawei.
         "
     ::= { hwSipMgSoftStringParameterConfigEntry 19 }

  hwSipMgSoftStringConfigParameter18 OBJECT-TYPE
     SYNTAX      OCTET STRING(SIZE (0..64))
     MAX-ACCESS  read-write
     STATUS      current
     DESCRIPTION
         "
         The SIP MgSoftStringConfigParameter18. Session name of s-row parameter of SDP. If is not configured, the default value is -.
         "
     ::= { hwSipMgSoftStringParameterConfigEntry 20 }

  hwSipMgSoftStringConfigParameter19 OBJECT-TYPE
     SYNTAX      OCTET STRING(SIZE (0..64))
     MAX-ACCESS  read-only
     STATUS      current
     DESCRIPTION
         "
         The SIP MgSoftStringConfigParameter19. Ring mode name of back ring.
         "
     ::= { hwSipMgSoftStringParameterConfigEntry 21 }

  hwSipMgSoftStringConfigParameter20 OBJECT-TYPE
     SYNTAX      OCTET STRING(SIZE (0..64))
     MAX-ACCESS  read-write
     STATUS      current
     DESCRIPTION
         "
         The SIP MgSoftStringConfigParameter20. Hook flash event report content. If it is not configured, the default value is FLASH.
         "
     ::= { hwSipMgSoftStringParameterConfigEntry 22 }

  hwSipMgSoftStringConfigParameter21 OBJECT-TYPE
     SYNTAX      OCTET STRING(SIZE (0..64))
     MAX-ACCESS  read-write
     STATUS      current
     DESCRIPTION
         "
         The SIP MgSoftStringConfigParameter21. Resource priority header field parameter of CAT1 common call.
         "
     ::= { hwSipMgSoftStringParameterConfigEntry 23 }

  hwSipMgSoftStringConfigParameter22 OBJECT-TYPE
     SYNTAX      OCTET STRING(SIZE (0..64))
     MAX-ACCESS  read-write
     STATUS      current
     DESCRIPTION
         "
         The SIP MgSoftStringConfigParameter22. Resource priority header field parameter of CAT2 common call.
         "
     ::= { hwSipMgSoftStringParameterConfigEntry 24 }

   hwSipMgSoftStringConfigParameter23 OBJECT-TYPE
     SYNTAX      OCTET STRING(SIZE (0..64))
     MAX-ACCESS  read-write
     STATUS      current
     DESCRIPTION
         "
         The SIP MgSoftStringConfigParameter23. Resource priority header field parameter of CAT3 common call.
         "
     ::= { hwSipMgSoftStringParameterConfigEntry 25 }

    hwSipMgSoftStringConfigParameter24 OBJECT-TYPE
     SYNTAX      OCTET STRING(SIZE (0..64))
     MAX-ACCESS  read-write
     STATUS      current
     DESCRIPTION
         "
         The SIP MgSoftStringConfigParameter24. Resource priority header field parameter of CAT1 emergency call.
         "
     ::= { hwSipMgSoftStringParameterConfigEntry 26 }

    hwSipMgSoftStringConfigParameter25 OBJECT-TYPE
     SYNTAX      OCTET STRING(SIZE (0..64))
     MAX-ACCESS  read-write
     STATUS      current
     DESCRIPTION
         "
         The SIP MgSoftStringConfigParameter25. Resource priority header field parameter of CAT2 emergency call.
         "
     ::= { hwSipMgSoftStringParameterConfigEntry 27 }

    hwSipMgSoftStringConfigParameter26 OBJECT-TYPE
     SYNTAX      OCTET STRING(SIZE (0..64))
     MAX-ACCESS  read-write
     STATUS      current
     DESCRIPTION
         "
         The SIP MgSoftStringConfigParameter26. Resource priority header field parameter of CAT3 emergency call.
         "
     ::= { hwSipMgSoftStringParameterConfigEntry 28 }

    hwSipMgSoftStringConfigParameter27 OBJECT-TYPE
     SYNTAX      OCTET STRING(SIZE (0..64))
     MAX-ACCESS  read-write
     STATUS      current
     DESCRIPTION
         "
         The SIP MgSoftStringConfigParameter27. SERVICEDOMAIN in URI of ROUTE header field.
         "
     ::= { hwSipMgSoftStringParameterConfigEntry 29 }

    hwSipMgSoftStringConfigParameter28 OBJECT-TYPE
     SYNTAX      OCTET STRING(SIZE (0..64))
     MAX-ACCESS  read-write
     STATUS      current
     DESCRIPTION
         "
         The SIP MgSoftStringConfigParameter28. SCC code for activating a service. 
         To activate multiple services, the codes are separated by semicolon (;). 
         The first supported service is CW service.
         "
     ::= { hwSipMgSoftStringParameterConfigEntry 30 }

    hwSipMgSoftStringConfigParameter29 OBJECT-TYPE
     SYNTAX      OCTET STRING(SIZE (0..64))
     MAX-ACCESS  read-write
     STATUS      current
     DESCRIPTION
         "
         The SIP MgSoftStringConfigParameter29. SCC code for deactivating a service. 
         To deactivate multiple services, the codes are separated by semicolon (;). 
         The first supported service is CW service.
         "
     ::= { hwSipMgSoftStringParameterConfigEntry 31 }

    hwSipMgSoftStringConfigParameter30 OBJECT-TYPE
     SYNTAX      OCTET STRING(SIZE (0..64))
     MAX-ACCESS  read-only
     STATUS      current
     DESCRIPTION
         "
         The SIP MgSoftStringConfigParameter30. Ring mode name of default ring.
         "
     ::= { hwSipMgSoftStringParameterConfigEntry 32 }

    hwSipMgSoftStringConfigParameter31 OBJECT-TYPE
     SYNTAX      OCTET STRING(SIZE (0..64))
     MAX-ACCESS  read-write
     STATUS      current
     DESCRIPTION
         "
         The SIP MgSoftStringConfigParameter31. SCC1 code for activating the customized event.
         Pattern for similar regular expressions described in hwSipMgSoftStringConfigParameter14.
         "
     ::= { hwSipMgSoftStringParameterConfigEntry 33 }

     hwSipMgSoftStringConfigParameter32 OBJECT-TYPE
     SYNTAX      OCTET STRING(SIZE (0..64))
     MAX-ACCESS  read-write
     STATUS      current
     DESCRIPTION
         "
         The SIP MgSoftStringConfigParameter32. SCC2 code for activating the customized event.
         Pattern for similar regular expressions described in hwSipMgSoftStringConfigParameter14.
         "
     ::= { hwSipMgSoftStringParameterConfigEntry 34 }

     hwSipMgSoftStringConfigParameter33 OBJECT-TYPE
     SYNTAX      OCTET STRING(SIZE (0..64))
     MAX-ACCESS  read-write
     STATUS      current
     DESCRIPTION
         "
         The SIP MgSoftStringConfigParameter33. SCC3 code for activating the customized event.
         Pattern for similar regular expressions described in hwSipMgSoftStringConfigParameter14.
         "
     ::= { hwSipMgSoftStringParameterConfigEntry 35 }

     hwSipMgSoftStringConfigParameter34 OBJECT-TYPE
     SYNTAX      OCTET STRING(SIZE (0..64))
     MAX-ACCESS  read-write
     STATUS      current
     DESCRIPTION
         "
         The SIP MgSoftStringConfigParameter34. Indicate the p-Access-Network-Info head of POTS.
         "
     ::= { hwSipMgSoftStringParameterConfigEntry 36 }

     hwSipMgSoftStringConfigParameter35 OBJECT-TYPE
     SYNTAX      OCTET STRING(SIZE (0..64))
     MAX-ACCESS  read-write
     STATUS      current
     DESCRIPTION
         "
         The SIP MgSoftStringConfigParameter35. Indicate the p-Access-Network-Info head of BRI.
         "
     ::= { hwSipMgSoftStringParameterConfigEntry 37 }

     hwSipMgSoftStringConfigParameter36 OBJECT-TYPE
     SYNTAX      OCTET STRING(SIZE (0..64))
     MAX-ACCESS  read-write
     STATUS      current
     DESCRIPTION
         "
         The SIP MgSoftStringConfigParameter36. Indicate the p-Access-Network-Info head of PRI.
         "
     ::= { hwSipMgSoftStringParameterConfigEntry 38 }
     
     hwSipMgSoftStringConfigParameter37 OBJECT-TYPE
     SYNTAX      OCTET STRING(SIZE (0..64))
     MAX-ACCESS  read-write
     STATUS      current
     DESCRIPTION
         "
         The SIP MgSoftStringConfigParameter37. Default hotline number.
         "
     ::= { hwSipMgSoftStringParameterConfigEntry 39 }

     hwSipMgSoftStringConfigParameter38 OBJECT-TYPE
     SYNTAX      OCTET STRING(SIZE (0..64))
     MAX-ACCESS  read-write
     STATUS      current
     DESCRIPTION
         "
         The SIP MgSoftStringConfigParameter38. Character string indicating that CLID or COLP is restricted.
         "
     ::= { hwSipMgSoftStringParameterConfigEntry 40 }
     
     hwSipMgSoftStringConfigParameter39 OBJECT-TYPE
     SYNTAX      OCTET STRING(SIZE (0..64))
     MAX-ACCESS  read-write
     STATUS      current
     DESCRIPTION
         "
         The SIP MgSoftStringConfigParameter39. Indicate the p-Access-Network-Info head of R2.
         "
     ::= { hwSipMgSoftStringParameterConfigEntry 41 }   
     
     hwSipMgSoftStringConfigParameter40 OBJECT-TYPE
     SYNTAX      OCTET STRING(SIZE (0..64))
     MAX-ACCESS  read-write
     STATUS      current
     DESCRIPTION
         "
         The SIP MgSoftStringConfigParameter40. Indicate URI for emergency calls.
         "
     ::= { hwSipMgSoftStringParameterConfigEntry 42 }
     
     hwSipMgSoftStringConfigParameter41 OBJECT-TYPE
     SYNTAX      OCTET STRING(SIZE (0..64))
     MAX-ACCESS  read-write
     STATUS      current
     DESCRIPTION
         "
         The SIP MgSoftStringConfigParameter41. SCC5 code for activating the customized event.
         Pattern for similar regular expressions described in hwSipMgSoftStringConfigParameter14.
         "
     ::= { hwSipMgSoftStringParameterConfigEntry 43 }
     
     hwSipMgSoftStringConfigParameter42 OBJECT-TYPE
     SYNTAX      OCTET STRING(SIZE (0..64))
     MAX-ACCESS  read-write
     STATUS      current
     DESCRIPTION
         "
         The SIP MgSoftStringConfigParameter42. Indicate the pattern for fixed phone number.
         Pattern for similar regular expressions described in hwSipMgSoftStringConfigParameter14.
         "
     ::= { hwSipMgSoftStringParameterConfigEntry 44 }
 ------------------------------------------------------------------------

     hwSipMgSoftStringParameterRunningTable OBJECT-TYPE
     SYNTAX      SEQUENCE OF HwSipMgSoftStringParameterRunningEntry
     MAX-ACCESS  not-accessible
     STATUS      current
     DESCRIPTION
       "
       This table is used to config the soft string Parameters of SIP interface.
       The index of this table is hwSipMgSoftStringMgInterfaceIndexRunning.
       "
    ::= { hwVoipSipObjects 12 }

   hwSipMgSoftStringParameterRunningEntry OBJECT-TYPE
     SYNTAX      HwSipMgSoftStringParameterRunningEntry
     MAX-ACCESS  not-accessible
     STATUS      current
     DESCRIPTION
       "
       This table is used to config the soft string Parameters of SIP interface.
       The index of this entry is hwSipMgSoftStringMgInterfaceIndexRunning.
       "
     INDEX    {
                hwSipMgSoftStringMgInterfaceIndexRunning
              }
    ::= { hwSipMgSoftStringParameterRunningTable 1 }

   HwSipMgSoftStringParameterRunningEntry ::=
     SEQUENCE
     {
       hwSipMgSoftStringMgInterfaceIndexRunning     Integer32,
       hwSipMgSoftStringRunningParameter0     OCTET STRING,
       hwSipMgSoftStringRunningParameter1     OCTET STRING,
       hwSipMgSoftStringRunningParameter2     OCTET STRING,
       hwSipMgSoftStringRunningParameter3     OCTET STRING,
       hwSipMgSoftStringRunningParameter4     OCTET STRING,
       hwSipMgSoftStringRunningParameter5     OCTET STRING,
       hwSipMgSoftStringRunningParameter6     OCTET STRING,
       hwSipMgSoftStringRunningParameter7     OCTET STRING,
       hwSipMgSoftStringRunningParameter8     OCTET STRING,
       hwSipMgSoftStringRunningParameter9     OCTET STRING,
       hwSipMgSoftStringRunningParameter10    OCTET STRING,
       hwSipMgSoftStringRunningParameter11    OCTET STRING,
       hwSipMgSoftStringRunningParameter12    OCTET STRING,
       hwSipMgSoftStringRunningParameter13    OCTET STRING,
       hwSipMgSoftStringRunningParameter14    OCTET STRING,
       hwSipMgSoftStringRunningParameter15    OCTET STRING,
       hwSipMgSoftStringRunningParameter16    OCTET STRING,
       hwSipMgSoftStringRunningParameter17    OCTET STRING,
       hwSipMgSoftStringRunningParameter18    OCTET STRING,
       hwSipMgSoftStringRunningParameter19    OCTET STRING,
       hwSipMgSoftStringRunningParameter20    OCTET STRING,
       hwSipMgSoftStringRunningParameter21    OCTET STRING,
       hwSipMgSoftStringRunningParameter22    OCTET STRING,
       hwSipMgSoftStringRunningParameter23    OCTET STRING,
       hwSipMgSoftStringRunningParameter24    OCTET STRING,
       hwSipMgSoftStringRunningParameter25    OCTET STRING,
       hwSipMgSoftStringRunningParameter26    OCTET STRING,
       hwSipMgSoftStringRunningParameter27    OCTET STRING,
       hwSipMgSoftStringRunningParameter28    OCTET STRING,
       hwSipMgSoftStringRunningParameter29    OCTET STRING,
       hwSipMgSoftStringRunningParameter30    OCTET STRING,
       hwSipMgSoftStringRunningParameter31    OCTET STRING,
       hwSipMgSoftStringRunningParameter32    OCTET STRING,
       hwSipMgSoftStringRunningParameter33    OCTET STRING,
       hwSipMgSoftStringRunningParameter34    OCTET STRING,
       hwSipMgSoftStringRunningParameter35    OCTET STRING,
       hwSipMgSoftStringRunningParameter36    OCTET STRING,
       hwSipMgSoftStringRunningParameter37    OCTET STRING,
       hwSipMgSoftStringRunningParameter38    OCTET STRING,
       hwSipMgSoftStringRunningParameter39    OCTET STRING,
       hwSipMgSoftStringRunningParameter40    OCTET STRING,
       hwSipMgSoftStringRunningParameter41    OCTET STRING,
       hwSipMgSoftStringRunningParameter42    OCTET STRING
     }

     hwSipMgSoftStringMgInterfaceIndexRunning OBJECT-TYPE
     SYNTAX      Integer32(0..16777215)
     MAX-ACCESS  not-accessible
     STATUS      current
     DESCRIPTION
         "
         SIP GateWay ID.
         "
     ::= { hwSipMgSoftStringParameterRunningEntry 1 }

     hwSipMgSoftStringRunningParameter0 OBJECT-TYPE
     SYNTAX      OCTET STRING(SIZE (0..64))
     MAX-ACCESS  read-only
     STATUS      current
     DESCRIPTION
         "
         The SIP MgSoftStringRunningParameter0. Reserved.
         "
     ::= { hwSipMgSoftStringParameterRunningEntry 2 }

  hwSipMgSoftStringRunningParameter1 OBJECT-TYPE
     SYNTAX      OCTET STRING(SIZE (0..64))
     MAX-ACCESS  read-only
     STATUS      current
     DESCRIPTION
         "
         The SIP MgSoftStringRunningParameter1. Visited newwork ID.
         "
     ::= { hwSipMgSoftStringParameterRunningEntry 3 }

  hwSipMgSoftStringRunningParameter2 OBJECT-TYPE
     SYNTAX      OCTET STRING(SIZE (0..64))
     MAX-ACCESS  read-only
     STATUS      current
     DESCRIPTION
         "
         The SIP MgSoftStringRunningParameter2. Prefix of national long-distance call.
         "
     ::= { hwSipMgSoftStringParameterRunningEntry 4 }

   hwSipMgSoftStringRunningParameter3 OBJECT-TYPE
     SYNTAX      OCTET STRING(SIZE (0..64))
     MAX-ACCESS  read-only
     STATUS      current
     DESCRIPTION
         "
         The SIP MgSoftStringRunningParameter3. Prefix of international long-distance call.
         "
     ::= { hwSipMgSoftStringParameterRunningEntry 5 }

   hwSipMgSoftStringRunningParameter4 OBJECT-TYPE
     SYNTAX      OCTET STRING(SIZE (0..64))
     MAX-ACCESS  read-only
     STATUS      current
     DESCRIPTION
         "
         The SIP MgSoftStringRunningParameter4. CC number string.
         "
     ::= { hwSipMgSoftStringParameterRunningEntry 6 }

   hwSipMgSoftStringRunningParameter5 OBJECT-TYPE
     SYNTAX      OCTET STRING(SIZE (0..64))
     MAX-ACCESS  read-only
     STATUS      current
     DESCRIPTION
         "
         The SIP MgSoftStringRunningParameter5. NDC number string.
         "
     ::= { hwSipMgSoftStringParameterRunningEntry 7 }

   hwSipMgSoftStringRunningParameter6 OBJECT-TYPE
     SYNTAX      OCTET STRING(SIZE (0..64))
     MAX-ACCESS  read-only
     STATUS      current
     DESCRIPTION
         "
         The SIP MgSoftStringRunningParameter6. SCC domain name.
         "
     ::= { hwSipMgSoftStringParameterRunningEntry 8 }

   hwSipMgSoftStringRunningParameter7 OBJECT-TYPE
     SYNTAX      OCTET STRING(SIZE (0..64))
     MAX-ACCESS  read-only
     STATUS      current
     DESCRIPTION
         "
         The SIP MgSoftStringRunningParameter7. Reserved.
         "
     ::= { hwSipMgSoftStringParameterRunningEntry 9 }

   hwSipMgSoftStringRunningParameter8 OBJECT-TYPE
     SYNTAX      OCTET STRING(SIZE (0..64))
     MAX-ACCESS  read-only
     STATUS      current
     DESCRIPTION
         "
         The SIP MgSoftStringRunningParameter8. Reserved.
         "
     ::= { hwSipMgSoftStringParameterRunningEntry 10 }

   hwSipMgSoftStringRunningParameter9 OBJECT-TYPE
     SYNTAX      OCTET STRING(SIZE (0..64))
     MAX-ACCESS  read-only
     STATUS      current
     DESCRIPTION
         "
         The SIP MgSoftStringRunningParameter9. Reserved.
         "
     ::= { hwSipMgSoftStringParameterRunningEntry 11 }

   hwSipMgSoftStringRunningParameter10 OBJECT-TYPE
     SYNTAX      OCTET STRING(SIZE (0..64))
     MAX-ACCESS  read-only
     STATUS      current
     DESCRIPTION
         "
         The SIP MgSoftStringRunningParameter10. Reserved.
         "
     ::= { hwSipMgSoftStringParameterRunningEntry 12 }

   hwSipMgSoftStringRunningParameter11 OBJECT-TYPE
     SYNTAX      OCTET STRING(SIZE (0..64))
     MAX-ACCESS  read-only
     STATUS      current
     DESCRIPTION
         "
         The SIP MgSoftStringRunningParameter11. Character string indicating that CLID or COLP is unavailable.
         "
     ::= { hwSipMgSoftStringParameterRunningEntry 13 }

   hwSipMgSoftStringRunningParameter12 OBJECT-TYPE
     SYNTAX      OCTET STRING(SIZE (0..64))
     MAX-ACCESS  read-only
     STATUS      current
     DESCRIPTION
         "
         The SIP MgSoftStringRunningParameter12. Reserved.
         "
     ::= { hwSipMgSoftStringParameterRunningEntry 14 }

  hwSipMgSoftStringRunningParameter13 OBJECT-TYPE
     SYNTAX      OCTET STRING(SIZE (0..64))
     MAX-ACCESS  read-only
     STATUS      current
     DESCRIPTION
         "
         The SIP MgSoftStringRunningParameter13. Character string indicating that CLID or COLP is not subscribed.
         "
     ::= { hwSipMgSoftStringParameterRunningEntry 15 }

  hwSipMgSoftStringRunningParameter14 OBJECT-TYPE
     SYNTAX      OCTET STRING(SIZE (0..64))
     MAX-ACCESS  read-only
     STATUS      current
     DESCRIPTION
         "
         The SIP MgSoftStringRunningParameter14. SCC code of the MCID service.
         "
     ::= { hwSipMgSoftStringParameterRunningEntry 16 }

  hwSipMgSoftStringRunningParameter15 OBJECT-TYPE
     SYNTAX      OCTET STRING(SIZE (0..64))
     MAX-ACCESS  read-only
     STATUS      current
     DESCRIPTION
         "
         The SIP MgSoftStringRunningParameter15. SCC code for activating the CFU service.
         "
     ::= { hwSipMgSoftStringParameterRunningEntry 17 }

  hwSipMgSoftStringRunningParameter16 OBJECT-TYPE
     SYNTAX      OCTET STRING(SIZE (0..64))
     MAX-ACCESS  read-only
     STATUS      current
     DESCRIPTION
         "
         The SIP MgSoftStringRunningParameter16. SCC code for deactivating the CFU service.
         "
     ::= { hwSipMgSoftStringParameterRunningEntry 18 }

  hwSipMgSoftStringRunningParameter17 OBJECT-TYPE
     SYNTAX      OCTET STRING(SIZE (0..64))
     MAX-ACCESS  read-only
     STATUS      current
     DESCRIPTION
         "
         The SIP MgSoftStringRunningParameter17. Owner name of o-row parameter of SDP. If is not configured, the default value is Huawei.
         "
     ::= { hwSipMgSoftStringParameterRunningEntry 19 }

  hwSipMgSoftStringRunningParameter18 OBJECT-TYPE
     SYNTAX      OCTET STRING(SIZE (0..64))
     MAX-ACCESS  read-only
     STATUS      current
     DESCRIPTION
         "
         The SIP MgSoftStringRunningParameter18. Session name of s-row parameter of SDP. If is not configured, the default value is -.
         "
     ::= { hwSipMgSoftStringParameterRunningEntry 20 }

  hwSipMgSoftStringRunningParameter19 OBJECT-TYPE
     SYNTAX      OCTET STRING(SIZE (0..64))
     MAX-ACCESS  read-only
     STATUS      current
     DESCRIPTION
         "
         The SIP MgSoftStringRunningParameter19. Ring mode name of back ring.
         "
     ::= { hwSipMgSoftStringParameterRunningEntry 21 }

  hwSipMgSoftStringRunningParameter20 OBJECT-TYPE
     SYNTAX      OCTET STRING(SIZE (0..64))
     MAX-ACCESS  read-only
     STATUS      current
     DESCRIPTION
         "
         The SIP MgSoftStringRunningParameter20. Hook flash event report content. If it is not configured, the default value is FLASH.
         "
     ::= { hwSipMgSoftStringParameterRunningEntry 22 }

  hwSipMgSoftStringRunningParameter21 OBJECT-TYPE
     SYNTAX      OCTET STRING(SIZE (0..64))
     MAX-ACCESS  read-only
     STATUS      current
     DESCRIPTION
         "
         The SIP MgSoftStringRunningParameter21. Resource priority header field parameter of CAT1 common call.
         "
     ::= { hwSipMgSoftStringParameterRunningEntry 23 }

  hwSipMgSoftStringRunningParameter22 OBJECT-TYPE
     SYNTAX      OCTET STRING(SIZE (0..64))
     MAX-ACCESS  read-only
     STATUS      current
     DESCRIPTION
         "
         The SIP MgSoftStringRunningParameter22. Resource priority header field parameter of CAT2 common call.
         "
     ::= { hwSipMgSoftStringParameterRunningEntry 24 }

   hwSipMgSoftStringRunningParameter23 OBJECT-TYPE
     SYNTAX      OCTET STRING(SIZE (0..64))
     MAX-ACCESS  read-only
     STATUS      current
     DESCRIPTION
         "
         The SIP MgSoftStringRunningParameter23. Resource priority header field parameter of CAT3 common call.
         "
     ::= { hwSipMgSoftStringParameterRunningEntry 25 }

    hwSipMgSoftStringRunningParameter24 OBJECT-TYPE
     SYNTAX      OCTET STRING(SIZE (0..64))
     MAX-ACCESS  read-only
     STATUS      current
     DESCRIPTION
         "
         The SIP MgSoftStringRunningParameter24. Resource priority header field parameter of CAT1 emergency call.
         "
     ::= { hwSipMgSoftStringParameterRunningEntry 26 }

    hwSipMgSoftStringRunningParameter25 OBJECT-TYPE
     SYNTAX      OCTET STRING(SIZE (0..64))
     MAX-ACCESS  read-only
     STATUS      current
     DESCRIPTION
         "
         The SIP MgSoftStringRunningParameter25. Resource priority header field parameter of CAT2 emergency call.
         "
     ::= { hwSipMgSoftStringParameterRunningEntry 27 }

    hwSipMgSoftStringRunningParameter26 OBJECT-TYPE
     SYNTAX      OCTET STRING(SIZE (0..64))
     MAX-ACCESS  read-only
     STATUS      current
     DESCRIPTION
         "
         The SIP MgSoftStringRunningParameter26. Resource priority header field parameter of CAT3 emergency call.
         "
     ::= { hwSipMgSoftStringParameterRunningEntry 28 }

    hwSipMgSoftStringRunningParameter27 OBJECT-TYPE
     SYNTAX      OCTET STRING(SIZE (0..64))
     MAX-ACCESS  read-only
     STATUS      current
     DESCRIPTION
         "
         The SIP MgSoftStringRunningParameter27. SERVICEDOMAIN in URI of ROUTE header field.
         "
     ::= { hwSipMgSoftStringParameterRunningEntry 29 }

    hwSipMgSoftStringRunningParameter28 OBJECT-TYPE
     SYNTAX      OCTET STRING(SIZE (0..64))
     MAX-ACCESS  read-only
     STATUS      current
     DESCRIPTION
         "
         The SIP MgSoftStringConfigParameter28. SCC code for activating a service. 
         To activate multiple services, the codes are separated by semicolon (;). 
         The first supported service is CW service.
         "
     ::= { hwSipMgSoftStringParameterRunningEntry 30 }

    hwSipMgSoftStringRunningParameter29 OBJECT-TYPE
     SYNTAX      OCTET STRING(SIZE (0..64))
     MAX-ACCESS  read-only
     STATUS      current
     DESCRIPTION
         "
         The SIP MgSoftStringConfigParameter29. SCC code for deactivating a service. 
         To deactivate multiple services, the codes are separated by semicolon (;). 
         The first supported service is CW service.
         "
     ::= { hwSipMgSoftStringParameterRunningEntry 31 }

    hwSipMgSoftStringRunningParameter30 OBJECT-TYPE
     SYNTAX      OCTET STRING(SIZE (0..64))
     MAX-ACCESS  read-only
     STATUS      current
     DESCRIPTION
         "
         The SIP MgSoftStringRunningParameter30. Ring mode name of default ring.
         "
     ::= { hwSipMgSoftStringParameterRunningEntry 32 }

    hwSipMgSoftStringRunningParameter31 OBJECT-TYPE
     SYNTAX      OCTET STRING(SIZE (0..64))
     MAX-ACCESS  read-only
     STATUS      current
     DESCRIPTION
         "
         The SIP MgSoftStringRunningParameter31. SCC1 code for activating the customized event.
         "
     ::= { hwSipMgSoftStringParameterRunningEntry 33 }

     hwSipMgSoftStringRunningParameter32 OBJECT-TYPE
     SYNTAX      OCTET STRING(SIZE (0..64))
     MAX-ACCESS  read-only
     STATUS      current
     DESCRIPTION
         "
         The SIP MgSoftStringRunningParameter32. SCC2 code for activating the customized event.
         "
     ::= { hwSipMgSoftStringParameterRunningEntry 34 }

     hwSipMgSoftStringRunningParameter33 OBJECT-TYPE
     SYNTAX      OCTET STRING(SIZE (0..64))
     MAX-ACCESS  read-only
     STATUS      current
     DESCRIPTION
         "
         The SIP MgSoftStringRunningParameter33. SCC3 code for activating the customized event.
         "
     ::= { hwSipMgSoftStringParameterRunningEntry 35 }

     hwSipMgSoftStringRunningParameter34 OBJECT-TYPE
     SYNTAX      OCTET STRING(SIZE (0..64))
     MAX-ACCESS  read-only
     STATUS      current
     DESCRIPTION
         "
         The SIP MgSoftStringRunningParameter34. Indicates the p-Access-Network-Info header of POTS.
         "
     ::= { hwSipMgSoftStringParameterRunningEntry 36 }

     hwSipMgSoftStringRunningParameter35 OBJECT-TYPE
     SYNTAX      OCTET STRING(SIZE (0..64))
     MAX-ACCESS  read-only
     STATUS      current
     DESCRIPTION
         "
         The SIP MgSoftStringRunningParameter35. Indicates the p-Access-Network-Info header of BRI.
         "
     ::= { hwSipMgSoftStringParameterRunningEntry 37 }

     hwSipMgSoftStringRunningParameter36 OBJECT-TYPE
     SYNTAX      OCTET STRING(SIZE (0..64))
     MAX-ACCESS  read-only
     STATUS      current
     DESCRIPTION
         "
         The SIP MgSoftStringRunningParameter36. Indicates the p-Access-Network-Info header of PRI.
         "
     ::= { hwSipMgSoftStringParameterRunningEntry 38 }  
     
     hwSipMgSoftStringRunningParameter37 OBJECT-TYPE
     SYNTAX      OCTET STRING(SIZE (0..64))
     MAX-ACCESS  read-only
     STATUS      current
     DESCRIPTION
         "
         The SIP MgSoftStringRunningParameter37. Default hotline number.
         "
     ::= { hwSipMgSoftStringParameterRunningEntry 39 }
     
     hwSipMgSoftStringRunningParameter38 OBJECT-TYPE
     SYNTAX      OCTET STRING(SIZE (0..64))
     MAX-ACCESS  read-only
     STATUS      current
     DESCRIPTION
         "
         The SIP MgSoftStringRunningParameter38. Character string indicating that CLID or COLP is restricted.
         "
     ::= { hwSipMgSoftStringParameterRunningEntry 40 }
     
     hwSipMgSoftStringRunningParameter39 OBJECT-TYPE
     SYNTAX      OCTET STRING(SIZE (0..64))
     MAX-ACCESS  read-only
     STATUS      current
     DESCRIPTION
         "
         The SIP MgSoftStringRunningParameter39. Indicates the p-Access-Network-Info header of R2.
         "
     ::= { hwSipMgSoftStringParameterRunningEntry 41 }  
     
     hwSipMgSoftStringRunningParameter40 OBJECT-TYPE
     SYNTAX      OCTET STRING(SIZE (0..64))
     MAX-ACCESS  read-only
     STATUS      current
     DESCRIPTION
         "
         The SIP MgSoftStringRunningParameter40. Indicates URI for emergency calls.
         "
     ::= { hwSipMgSoftStringParameterRunningEntry 42 }    
     
     hwSipMgSoftStringRunningParameter41 OBJECT-TYPE
     SYNTAX      OCTET STRING(SIZE (0..64))
     MAX-ACCESS  read-only
     STATUS      current
     DESCRIPTION
         "
         The SIP MgSoftStringConfigParameter41. SCC5 code for activating the customized event.
         "
     ::= { hwSipMgSoftStringParameterRunningEntry 43 }  
     
     hwSipMgSoftStringRunningParameter42 OBJECT-TYPE
     SYNTAX      OCTET STRING(SIZE (0..64))
     MAX-ACCESS  read-only
     STATUS      current
     DESCRIPTION
         "
         The SIP MgSoftStringConfigParameter42. Indicates the pattern for fixed phone number.
         "
     ::= { hwSipMgSoftStringParameterRunningEntry 44 }
--     
   hwVGWDigitMapGroupRefTable OBJECT-TYPE
     SYNTAX      SEQUENCE OF HwVGWDigitMapGroupRefEntry
     MAX-ACCESS  not-accessible
     STATUS      current
     DESCRIPTION
       "
       This table is used to config the digitmap group refered to a gateway.
       The index of this table is hwVGWDigitMapGroupInterfaceID.
       "
     ::= { hwVoipSipObjects 13 }
   
   hwVGWDigitMapGroupRefEntry OBJECT-TYPE
     SYNTAX      HwVGWDigitMapGroupRefEntry
     MAX-ACCESS  not-accessible
     STATUS      current
     DESCRIPTION
       "
       This table is used to config the digitmap group refered to a gateway.
       The index of this entry is hwVGWDigitMapGroupInterfaceID.
       "
     INDEX    {  
                hwVGWDigitMapGroupInterfaceID
              }
     ::= { hwVGWDigitMapGroupRefTable 1 }
 
   HwVGWDigitMapGroupRefEntry ::=
     SEQUENCE
     {
       hwVGWDigitMapGroupInterfaceID   Integer32,
       hwVGWDigitMapGroupName   	OCTET STRING
     }
 
   hwVGWDigitMapGroupInterfaceID OBJECT-TYPE
     SYNTAX      Integer32(0..16777215)
     MAX-ACCESS  not-accessible
     STATUS      current
     DESCRIPTION
         "
         Indicates the ID of SIP gate way.
         "
     ::= { hwVGWDigitMapGroupRefEntry 1 }  
     
   hwVGWDigitMapGroupName OBJECT-TYPE
     SYNTAX      OCTET STRING(SIZE(0..32))
     MAX-ACCESS  read-write
     STATUS      current
     DESCRIPTION
         "
         Indicates the digitmap group refer to SIP gateway.
         "
     ::= { hwVGWDigitMapGroupRefEntry 2 }
     
--     
   hwVGWISDNCauseResponseMapTable  OBJECT-TYPE
     SYNTAX      SEQUENCE OF HwVGWISDNCauseResponseMapEntry
     MAX-ACCESS  not-accessible
     STATUS      current
     DESCRIPTION
       "
       This table is used to config the Q.850 Code to SIP Response code.
       The index of this table is hwIsdnCauseMapMgId and hwIsdnCauseMapCause.
       "
     ::= { hwVoipSipObjects 14 }
 
   hwVGWISDNCauseResponseMapEntry OBJECT-TYPE
     SYNTAX      HwVGWISDNCauseResponseMapEntry
     MAX-ACCESS  not-accessible
     STATUS      current
     DESCRIPTION
       "
       This table is used to config the Q.850 Code to SIP Response code.
       The index of this entry is hwIsdnCauseMapMgId and hwIsdnCauseMapCause.
       "
     INDEX    {  
                hwIsdnCauseMapMgId,
                hwIsdnCauseMapCause
              }
     ::= { hwVGWISDNCauseResponseMapTable 1 }
 
   HwVGWISDNCauseResponseMapEntry ::=
     SEQUENCE
     {
       hwIsdnCauseMapMgId          Integer32,
       hwIsdnCauseMapCause         Integer32,
       hwIsdnCauseMapSipResponse   Integer32,
       hwIsdnCauseMapRowStatus     RowStatus
     }
 
   hwIsdnCauseMapMgId OBJECT-TYPE
     SYNTAX      Integer32(0..16777215)
     MAX-ACCESS  not-accessible
     STATUS      current
     DESCRIPTION
         "
         Indicates the ID of SIP Interface.
         "
     ::= { hwVGWISDNCauseResponseMapEntry 1 }  
     
   hwIsdnCauseMapCause OBJECT-TYPE
     SYNTAX      Integer32(1..127)
     MAX-ACCESS  not-accessible
     STATUS      current
     DESCRIPTION
         "
         Indicates the Isdn Cause.
         "
     ::= { hwVGWISDNCauseResponseMapEntry 2 }
     
   hwIsdnCauseMapSipResponse OBJECT-TYPE
     SYNTAX      Integer32(300..699)
     MAX-ACCESS  read-write
     STATUS      current
     DESCRIPTION
         "
         Indicates the Sip Response Code.
         "
     ::= { hwVGWISDNCauseResponseMapEntry 3 }
     
   hwIsdnCauseMapRowStatus OBJECT-TYPE
     SYNTAX      RowStatus
     MAX-ACCESS  read-write
     STATUS      current
     DESCRIPTION
         "
         This is used to create new rows in this table, modify existing rows, and to delete existing rows.
         "
     ::= { hwVGWISDNCauseResponseMapEntry 4 }
   
--     
   hwVGWSIPResponseCauseMapTable  OBJECT-TYPE
     SYNTAX      SEQUENCE OF HwVGWSIPResponseCauseMapEntry
     MAX-ACCESS  not-accessible
     STATUS      current
     DESCRIPTION
       "
       This table is used to config the SIP Response code to Q.850 Code.
       The index of this table is hwIsdnCauseMapMgId and hwIsdnCauseMapCause.
       "
     ::= { hwVoipSipObjects 15 }
 
   hwVGWSIPResponseCauseMapEntry OBJECT-TYPE
     SYNTAX      HwVGWSIPResponseCauseMapEntry
     MAX-ACCESS  not-accessible
     STATUS      current
     DESCRIPTION
       "
       This table is used to config the SIP Response code to Q.850 Code.
       The index of this entry is hwIsdnCauseMapMgId and hwIsdnCauseMapCause.
       "
     INDEX    {  
                hwSipResponseMapMgId,
                hwSipResponseMapResponse
              }
     ::= { hwVGWSIPResponseCauseMapTable 1 }
 
   HwVGWSIPResponseCauseMapEntry ::=
     SEQUENCE
     {
       hwSipResponseMapMgId        Integer32,
       hwSipResponseMapResponse Integer32,
       hwSipResponseMapIsdnCause   Integer32,
       hwSipResponseMapRowStatus   RowStatus
     }
 
   hwSipResponseMapMgId OBJECT-TYPE
     SYNTAX      Integer32(0..16777215)
     MAX-ACCESS  not-accessible
     STATUS      current
     DESCRIPTION
         "
         Indicates the ID of SIP Interface.
         "
     ::= { hwVGWSIPResponseCauseMapEntry 1 }  
     
   hwSipResponseMapResponse OBJECT-TYPE
     SYNTAX      Integer32(300..699)
     MAX-ACCESS  not-accessible
     STATUS      current
     DESCRIPTION
         "
         Indicates the Sip Response Cause.
         "
     ::= { hwVGWSIPResponseCauseMapEntry 2 }
     
   hwSipResponseMapIsdnCause OBJECT-TYPE
     SYNTAX      Integer32(1..127)
     MAX-ACCESS  read-write
     STATUS      current
     DESCRIPTION
         "
         Indicates the Q.850 Cause Code.
         "
     ::= { hwVGWSIPResponseCauseMapEntry 3 }
     
   hwSipResponseMapRowStatus OBJECT-TYPE
     SYNTAX      RowStatus
     MAX-ACCESS  read-write
     STATUS      current
     DESCRIPTION
         "
         This is used to create new rows in this table, modify existing rows, and to delete existing rows.
         "
     ::= { hwVGWSIPResponseCauseMapEntry 4 }   
     
--     
   hwVGWSIPResponseCauseMapRunningTable  OBJECT-TYPE
     SYNTAX      SEQUENCE OF HwVGWSIPResponseCauseMapRunningEntry
     MAX-ACCESS  not-accessible
     STATUS      current
     DESCRIPTION
       "
       This table is used to config the SIP Response code to Q.850 Code.
       The index of this table is hwIsdnCauseMapMgId and hwIsdnCauseMapCause.
       "
     ::= { hwVoipSipObjects 16 }
 
   hwVGWSIPResponseCauseMapRunningEntry OBJECT-TYPE
     SYNTAX      HwVGWSIPResponseCauseMapRunningEntry
     MAX-ACCESS  not-accessible
     STATUS      current
     DESCRIPTION
       "
       This table is used to config the SIP Response code to Q.850 Code.
       The index of this entry is hwIsdnCauseMapMgId and hwIsdnCauseMapCause.
       "
     INDEX    {  
                hwSipResponseMaprunningMgId,
                hwSipResponseMaprunningResponse
              }
     ::= { hwVGWSIPResponseCauseMapRunningTable 1 }
 
   HwVGWSIPResponseCauseMapRunningEntry ::=
     SEQUENCE
     {
       hwSipResponseMaprunningMgId        Integer32,
       hwSipResponseMaprunningResponse Integer32,
       hwSipResponseMaprunningIsdnCause   Integer32
     }
 
   hwSipResponseMaprunningMgId OBJECT-TYPE
     SYNTAX      Integer32(0..16777215)
     MAX-ACCESS  not-accessible
     STATUS      current
     DESCRIPTION
         "
         Indicates the ID of SIP Interface.
         "
     ::= { hwVGWSIPResponseCauseMapRunningEntry 1 }  
     
   hwSipResponseMaprunningResponse OBJECT-TYPE
     SYNTAX      Integer32(300..699)
     MAX-ACCESS  not-accessible
     STATUS      current
     DESCRIPTION
         "
         Indicates the Sip Response Cause.
         "
     ::= { hwVGWSIPResponseCauseMapRunningEntry 2 }
     
   hwSipResponseMaprunningIsdnCause OBJECT-TYPE
     SYNTAX      Integer32(1..127)
     MAX-ACCESS  read-only
     STATUS      current
     DESCRIPTION
         "
         Indicates the Q.850 Cause Code.
         "
     ::= { hwVGWSIPResponseCauseMapRunningEntry 3 } 
     
 --     
   hwVGWISDNCauseResponseMapRunningTable  OBJECT-TYPE
     SYNTAX      SEQUENCE OF HwVGWISDNCauseResponseMapRunningEntry
     MAX-ACCESS  not-accessible
     STATUS      current
     DESCRIPTION
       "
       This table is used to config the Q.850 Code to SIP Response code.
       The index of this table is hwIsdnCauseMapMgId and hwIsdnCauseMapCause.
       "
     ::= { hwVoipSipObjects 17 }
 
   hwVGWISDNCauseResponseMapRunningEntry OBJECT-TYPE
     SYNTAX      HwVGWISDNCauseResponseMapRunningEntry
     MAX-ACCESS  not-accessible
     STATUS      current
     DESCRIPTION
       "
       This table is used to config the Q.850 Code to SIP Response code.
       The index of this entry is hwIsdnCauseMapMgId and hwIsdnCauseMapCause.
       "
     INDEX    {  
                hwIsdnCauseMaprunningMgId,
                hwIsdnCauseMaprunningCause
              }
     ::= { hwVGWISDNCauseResponseMapRunningTable 1 }
 
   HwVGWISDNCauseResponseMapRunningEntry ::=
     SEQUENCE
     {
       hwIsdnCauseMaprunningMgId          Integer32,
       hwIsdnCauseMaprunningCause         Integer32,
       hwIsdnCauseMaprunningSipResponse   Integer32
     }
 
   hwIsdnCauseMaprunningMgId OBJECT-TYPE
     SYNTAX      Integer32(0..16777215)
     MAX-ACCESS  not-accessible
     STATUS      current
     DESCRIPTION
         "
         Indicates the ID of SIP Interface.
         "
     ::= { hwVGWISDNCauseResponseMapRunningEntry 1 }  
     
   hwIsdnCauseMaprunningCause OBJECT-TYPE
     SYNTAX      Integer32(1..127)
     MAX-ACCESS  not-accessible
     STATUS      current
     DESCRIPTION
         "
         Indicates the Isdn Cause.
         "
     ::= { hwVGWISDNCauseResponseMapRunningEntry 2 }
     
   hwIsdnCauseMaprunningSipResponse OBJECT-TYPE
     SYNTAX      Integer32(300..699)
     MAX-ACCESS  read-only
     STATUS      current
     DESCRIPTION
         "
         Indicates the Sip Response Code.
         "
     ::= { hwVGWISDNCauseResponseMapRunningEntry 3 }
     
--    
   hwSipHuntingGroupTable OBJECT-TYPE
     SYNTAX      SEQUENCE OF HwSipHuntingGroupEntry
     MAX-ACCESS  not-accessible
     STATUS      current
     DESCRIPTION
       "
       This table is used to config the parameters of sip hunting group.
       The indexes of this table are hwSipHGVgwId, hwSipHGName.
       "
     ::= { hwVoipSipObjects 18 }

   hwSipHuntingGroupEntry OBJECT-TYPE
     SYNTAX      HwSipHuntingGroupEntry
     MAX-ACCESS  not-accessible
     STATUS      current
     DESCRIPTION
       "
       This table is used to config the parameters of sip hunting group.
       The indexes of this entry are hwSipHGVgwId, hwSipHGName.
       "
     INDEX    {
                hwSipHGVgwId,
                hwSipHGName
              }
     ::= { hwSipHuntingGroupTable 1 }

   HwSipHuntingGroupEntry ::=
     SEQUENCE
     {
       hwSipHGVgwId Integer32,
       hwSipHGName OCTET STRING,
       hwSipHGHuntingMode INTEGER,
       hwSipHGInheritFlag INTEGER,
       hwSipHGRowStatus RowStatus
     }

   hwSipHGVgwId OBJECT-TYPE
     SYNTAX      Integer32(0..16777215)
     MAX-ACCESS  not-accessible
     STATUS      current
     DESCRIPTION
         "
         SIP GateWay ID.
         "
     ::= { hwSipHuntingGroupEntry 1 }

   hwSipHGName OBJECT-TYPE
     SYNTAX      OCTET STRING(SIZE (1..32))
     MAX-ACCESS  not-accessible
     STATUS      current
     DESCRIPTION
         "
         Indicates the sip hunting group Name.
         "
     ::= { hwSipHuntingGroupEntry 2 }

   hwSipHGHuntingMode OBJECT-TYPE
     SYNTAX      INTEGER{order(1),round(2)}
     MAX-ACCESS  read-write
     STATUS      current
     DESCRIPTION
         "
         Indicates the Hunting Mode of the sip hunting group.
         Options:
         1. order(1) -hunt by order
         2. round(2) -hunt by round robin
         Default: round(2)
         "
     ::= { hwSipHuntingGroupEntry 3 }
     
   hwSipHGInheritFlag OBJECT-TYPE
     SYNTAX      INTEGER{enable(1),disable(2)}
     MAX-ACCESS  read-write
     STATUS      current
     DESCRIPTION
         "
         Indicates the inheritance flag of the hunting group.
         Options:
         1. enable(1) -enable
         2. disable(2) -disable
         Default: disable(2)
         "
     ::= { hwSipHuntingGroupEntry 4 }

   hwSipHGRowStatus OBJECT-TYPE
     SYNTAX      RowStatus
     MAX-ACCESS  read-write
     STATUS      current
     DESCRIPTION
         "
         This is used to create new rows in this table, modify existing rows, and to delete existing rows.
         "
     ::= { hwSipHuntingGroupEntry 5 }
     
--    
   hwSipHuntingGroupMemberTable OBJECT-TYPE
     SYNTAX      SEQUENCE OF HwSipHuntingGroupMemberEntry
     MAX-ACCESS  not-accessible
     STATUS      current
     DESCRIPTION
       "
       This table is used to config the parameters of sip hunting group member.
       The indexes of this table are hwSipHGMemberGroupName, hwSipHGMemberPortIndex, hwSipHGMemberSubGroupName.
       "
     ::= { hwVoipSipObjects 19 }

   hwSipHuntingGroupMemberEntry OBJECT-TYPE
     SYNTAX      HwSipHuntingGroupMemberEntry
     MAX-ACCESS  not-accessible
     STATUS      current
     DESCRIPTION
       "
       This table is used to config the parameters of sip hunting group member.
       The indexes of this entry are hwSipHGMemberGroupName, hwSipHGMemberPortIndex, hwSipHGMemberSubGroupName.
       "
     INDEX    {
                hwSipHGMemberGroupName,
                hwSipHGMemberPortIndex,
                hwSipHGMemberSubGroupName
              }
     ::= { hwSipHuntingGroupMemberTable 1 }

   HwSipHuntingGroupMemberEntry ::=
     SEQUENCE
     {
       hwSipHGMemberGroupName OCTET STRING,
       hwSipHGMemberPortIndex Unsigned32,
       hwSipHGMemberSubGroupName OCTET STRING,
       hwSipHGMemberOrder Integer32,
       hwSipHGMemberRowStatus RowStatus
     }

   hwSipHGMemberGroupName OBJECT-TYPE
     SYNTAX      OCTET STRING(SIZE (1..32))
     MAX-ACCESS  not-accessible
     STATUS      current
     DESCRIPTION
         "
         Indicates the sip hunting group member Name.
         "
     ::= { hwSipHuntingGroupMemberEntry 1 }
     
   hwSipHGMemberPortIndex OBJECT-TYPE
     SYNTAX      Unsigned32(0..4294967295)
     MAX-ACCESS  not-accessible
     STATUS      current
     DESCRIPTION
         "
         Indicates the index of the port member in sip hunting group.
         "
     ::= { hwSipHuntingGroupMemberEntry 2 }

   hwSipHGMemberSubGroupName OBJECT-TYPE
     SYNTAX      OCTET STRING(SIZE (0..32))
     MAX-ACCESS  not-accessible
     STATUS      current
     DESCRIPTION
         "
         Indicates the subgroup name in sip hunting group.
         "
     ::= { hwSipHuntingGroupMemberEntry 3 }
     
   hwSipHGMemberOrder OBJECT-TYPE
     SYNTAX      Integer32(1..65535)
     MAX-ACCESS  read-write
     STATUS      current
     DESCRIPTION
         "
         Indicates the priority of member in the sip hunting group.
         "
     ::= { hwSipHuntingGroupMemberEntry 4 }


   hwSipHGMemberRowStatus OBJECT-TYPE
     SYNTAX      RowStatus
     MAX-ACCESS  read-write
     STATUS      current
     DESCRIPTION
         "
         This is used to create new rows in this table, modify existing rows, and to delete existing rows.
         "
     ::= { hwSipHuntingGroupMemberEntry 5 }
     
--    
   hwSipGroupNumberConfigTable OBJECT-TYPE
     SYNTAX      SEQUENCE OF HwSipGroupNumberConfigEntry
     MAX-ACCESS  not-accessible
     STATUS      current
     DESCRIPTION
       "
       This table is used to config the parameters of sip group number.
       The indexes of this table are hwSipGroupNumberVgwId, hwSipGroupNumberUri.
       "
     ::= { hwVoipSipObjects 20 }

   hwSipGroupNumberConfigEntry OBJECT-TYPE
     SYNTAX      HwSipGroupNumberConfigEntry
     MAX-ACCESS  not-accessible
     STATUS      current
     DESCRIPTION
       "
       This table is used to config the parameters of sip group number.
       The indexes of this entry are hwSipGroupNumberVgwId, hwSipGroupNumberUri.
       "
     INDEX    {
                hwSipGroupNumberVgwId,
                hwSipGroupNumberUri
              }
     ::= { hwSipGroupNumberConfigTable 1 }

   HwSipGroupNumberConfigEntry ::=
     SEQUENCE
     {
       hwSipGroupNumberVgwId Integer32,
       hwSipGroupNumberUri OCTET STRING,
       hwSipGroupNumberGroupName OCTET STRING,
       hwSipGroupNumberRowStatus RowStatus
     }

   hwSipGroupNumberVgwId OBJECT-TYPE
     SYNTAX      Integer32(0..16777215)
     MAX-ACCESS  not-accessible
     STATUS      current
     DESCRIPTION
         "
         SIP GateWay ID.
         "
     ::= { hwSipGroupNumberConfigEntry 1 }

   hwSipGroupNumberUri OBJECT-TYPE
     SYNTAX      OCTET STRING(SIZE (1..64))
     MAX-ACCESS  not-accessible
     STATUS      current
     DESCRIPTION
         "
         Indicates the sip group number uri.
         "
     ::= { hwSipGroupNumberConfigEntry 2 }
     
   hwSipGroupNumberGroupName OBJECT-TYPE
     SYNTAX      OCTET STRING(SIZE (0..32))
     MAX-ACCESS  read-write
     STATUS      current
     DESCRIPTION
         "
         Indicates the name of the sip group which the sip group number assigned to.
         The name cannot contain a question mark or double quotation marks.
         "
     ::= { hwSipGroupNumberConfigEntry 3 }

   hwSipGroupNumberRowStatus OBJECT-TYPE
     SYNTAX      RowStatus
     MAX-ACCESS  read-write
     STATUS      current
     DESCRIPTION
         "
         This is used to create new rows in this table, modify existing rows, and to delete existing rows.
         "
     ::= { hwSipGroupNumberConfigEntry 4 }
     
--    
   hwSipGroupNumberOperTable OBJECT-TYPE
     SYNTAX      SEQUENCE OF HwSipGroupNumberOperEntry
     MAX-ACCESS  not-accessible
     STATUS      current
     DESCRIPTION
       "
       This table is used to operate the sip group number.
       The indexes of this table are hwSipGroupNumberOperVgwId, hwSipGroupNumberOperUri.
       "
     ::= { hwVoipSipObjects 21 }

   hwSipGroupNumberOperEntry OBJECT-TYPE
     SYNTAX      HwSipGroupNumberOperEntry
     MAX-ACCESS  not-accessible
     STATUS      current
     DESCRIPTION
       "
       This table is used to operate the sip group number.
       The indexes of this entry are hwSipGroupNumberOperVgwId, hwSipGroupNumberOperUri.
       "
     INDEX    {
                hwSipGroupNumberOperVgwId,
                hwSipGroupNumberOperUri
              }
     ::= { hwSipGroupNumberOperTable 1 }

   HwSipGroupNumberOperEntry ::=
     SEQUENCE
     {
       hwSipGroupNumberOperVgwId Integer32,
       hwSipGroupNumberOperUri OCTET STRING,
       hwSipGroupNumberAdminState INTEGER,
       hwSipGroupNumberOperType INTEGER
     }

   hwSipGroupNumberOperVgwId OBJECT-TYPE
     SYNTAX      Integer32(0..16777215)
     MAX-ACCESS  not-accessible
     STATUS      current
     DESCRIPTION
         "
         SIP GateWay ID.
         "
     ::= { hwSipGroupNumberOperEntry 1 }

   hwSipGroupNumberOperUri OBJECT-TYPE
     SYNTAX      OCTET STRING(SIZE (1..64))
     MAX-ACCESS  not-accessible
     STATUS      current
     DESCRIPTION
         "
         Indicates the sip group number uri.
         "
     ::= { hwSipGroupNumberOperEntry 2 }

   hwSipGroupNumberAdminState OBJECT-TYPE
     SYNTAX      INTEGER{blockedLocally(1),blockedRemotely(2),inService(3)}
     MAX-ACCESS  read-only
     STATUS      current
     DESCRIPTION
         "
         Indicates the Administration State of the sip group number.
         Options:
         1. blockedLocally(1) -the service is blocked cause of the local reason
         2. blockedRemotely(2) -the service is blocked cause of the remote reason
         3. inService(3) -the service is normal
         "
     ::= { hwSipGroupNumberOperEntry 3 }
     
   hwSipGroupNumberOperType OBJECT-TYPE
     SYNTAX      INTEGER{endService(1),startService(2)}
     MAX-ACCESS  read-write
     STATUS      current
     DESCRIPTION
         "
         Indicates the operation on the sip group number.
         Options:
         1. endService(1) -end service
         2. startService(2) -start service
         "
     ::= { hwSipGroupNumberOperEntry 4 }
     
--    
   hwSipGroupNumberRightTable OBJECT-TYPE
     SYNTAX      SEQUENCE OF HwSipGroupNumberRightEntry
     MAX-ACCESS  not-accessible
     STATUS      current
     DESCRIPTION
       "
       This table is used to config service rights or authentication informations of sip group number.
       The indexes of this table are hwSipGroupNumberRightVgwId, hwSipGroupNumberRightUri.
       "
     ::= { hwVoipSipObjects 22 }

   hwSipGroupNumberRightEntry OBJECT-TYPE
     SYNTAX      HwSipGroupNumberRightEntry
     MAX-ACCESS  not-accessible
     STATUS      current
     DESCRIPTION
       "
       This table is used to config service rights or authentication informations of sip group number.
       The indexes of this entry are hwSipGroupNumberRightVgwId, hwSipGroupNumberRightUri.
       "
     INDEX    {
                hwSipGroupNumberRightVgwId,
                hwSipGroupNumberRightUri
              }
     ::= { hwSipGroupNumberRightTable 1 }

   HwSipGroupNumberRightEntry ::=
     SEQUENCE
     {
       hwSipGroupNumberRightVgwId Integer32,
       hwSipGroupNumberRightUri OCTET STRING,
       hwSipGroupNumberRightCentrexNo Unsigned32,
       hwSipGroupNumberRightCentrexPrefix OCTET STRING,
       hwSipGroupNumberRightCentrexFlag INTEGER,
       hwSipGroupNumberRightCallHold INTEGER,
       hwSipGroupNumberRightThreeParty INTEGER,
       hwSipGroupNumberRightConf INTEGER,
       hwSipGroupNumberRightCt INTEGER,
       hwSipGroupNumberRightMcid INTEGER,
       hwSipGroupNumberRightAuthName OCTET STRING,
       hwSipGroupNumberRightAuthPasswordMode INTEGER,
       hwSipGroupNumberRightAuthPassword OCTET STRING,
       hwSipGroupNumberRightAuthHA1 OCTET STRING,
       hwSipGroupNumberRightCw INTEGER,
       hwSipGroupNumberRightDc INTEGER,
       hwSipGroupNumberRightMwi INTEGER,
       hwSipGroupNumberRightAnonymousCall INTEGER,
       hwSipGroupNumberRightAutoReversePolarity INTEGER,
       hwSipGroupNumberRightDisplayNameMode INTEGER,
       hwSipGroupNumberRightPermanentHold INTEGER,
       hwSipGroupNumberRightCutoffDisconnect INTEGER,
       hwSipGroupNumberRightSccClass INTEGER,
       hwSipGroupNumberRightFastDisconnect INTEGER,
       hwSipGroupNumberRightHotLine INTEGER,
       hwSipGroupNumberRightMwiMode INTEGER,
       hwSipGroupNumberRightHotTime Integer32,
       hwSipGroupNumberRightHotLineNum OCTET STRING,
       hwSipGroupNumberRightDialTone INTEGER,
       hwSipGroupNumberRightCfbNum OCTET STRING,
       hwSipGroupNumberRightCfnrNum OCTET STRING,
       hwSipGroupNumberRightCfuNum OCTET STRING,
       hwSipGroupNumberRightCfnrTime Integer32,
       hwSipGroupNumberRightDisplayName OCTET STRING,
       hwSipGroupNumberRightPermanentHoldMode INTEGER,
       hwSipGroupNumberRightPermanentHoldTime Integer32
     }

   hwSipGroupNumberRightVgwId OBJECT-TYPE
     SYNTAX      Integer32(0..16777215)
     MAX-ACCESS  not-accessible
     STATUS      current
     DESCRIPTION
         "
         SIP GateWay ID.
         "
     ::= { hwSipGroupNumberRightEntry 1 }

   hwSipGroupNumberRightUri OBJECT-TYPE
     SYNTAX      OCTET STRING(SIZE (1..64))
     MAX-ACCESS  not-accessible
     STATUS      current
     DESCRIPTION
         "
         Indicates the sip group number uri.
         "
     ::= { hwSipGroupNumberRightEntry 2 }
     
   hwSipGroupNumberRightCentrexNo OBJECT-TYPE
     SYNTAX      Unsigned32(0..4294967295)
     MAX-ACCESS  read-write
     STATUS      current
     DESCRIPTION
         "
         Indicates the centrexno of the sip group number.4294967295 means to clear the configuration.
         "
     ::= { hwSipGroupNumberRightEntry 3 }
     
   hwSipGroupNumberRightCentrexPrefix OBJECT-TYPE
     SYNTAX      OCTET STRING(SIZE (0..7))
     MAX-ACCESS  read-write
     STATUS      current
     DESCRIPTION
         "
         Indicates the centrexprefix of the sip group number.
         "
     ::= { hwSipGroupNumberRightEntry 4 }

   hwSipGroupNumberRightCentrexFlag OBJECT-TYPE
     SYNTAX      INTEGER{dialDirectly(1),dialSecondary(2)}
     MAX-ACCESS  read-write
     STATUS      current
     DESCRIPTION
         "
         Indicates the centrex flag of the sip group number.
         Options:
         1. dialDirectly(1) -dialDirectly
         2. dialSecondary(2) -dialSecondary
         Default: dialDirectly(1)
         "
     ::= { hwSipGroupNumberRightEntry 5 }
     
   hwSipGroupNumberRightCallHold OBJECT-TYPE
     SYNTAX      INTEGER{enable(1),disable(2)}
     MAX-ACCESS  read-write
     STATUS      current
     DESCRIPTION
         "
         Indicates the callhold right of the sip group number.
         Options:
         1. enable(1) -enable
         2. disable(2) -disable
         Default: enable(1)
         "
     ::= { hwSipGroupNumberRightEntry 6 }
     
   hwSipGroupNumberRightThreeParty OBJECT-TYPE
     SYNTAX      INTEGER{enable(1),disable(2)}
     MAX-ACCESS  read-write
     STATUS      current
     DESCRIPTION
         "
         Indicates the three-party right of the sip group number.
         Options:
         1. enable(1) -enable
         2. disable(2) -disable
         Default: enable(1)
         "
     ::= { hwSipGroupNumberRightEntry 7 }
     
   hwSipGroupNumberRightConf OBJECT-TYPE
     SYNTAX      INTEGER{enable(1),disable(2)}
     MAX-ACCESS  read-write
     STATUS      current
     DESCRIPTION
         "
         Indicates the conference right of the sip group number.
         Options:
         1. enable(1) -enable
         2. disable(2) -disable
         Default: enable(1)
         "
     ::= { hwSipGroupNumberRightEntry 8 }
     
   hwSipGroupNumberRightCt OBJECT-TYPE
     SYNTAX      INTEGER{enable(1),disable(2)}
     MAX-ACCESS  read-write
     STATUS      current
     DESCRIPTION
         "
         Indicates the calltransfer right of the sip group number.
         Options:
         1. enable(1) -enable
         2. disable(2) -disable
         Default: enable(1)
         "
     ::= { hwSipGroupNumberRightEntry 9 }
   
   hwSipGroupNumberRightMcid OBJECT-TYPE
     SYNTAX      INTEGER{enable(1),disable(2)}
     MAX-ACCESS  read-write
     STATUS      current
     DESCRIPTION
         "
         Indicates the mcid right of the sip group number.
         Options:
         1. enable(1) -enable
         2. disable(2) -disable
         Default: disable(2)
         "
     ::= { hwSipGroupNumberRightEntry 10 }  
   
   hwSipGroupNumberRightAuthName OBJECT-TYPE
     SYNTAX      OCTET STRING(SIZE (0..64))
     MAX-ACCESS  read-write
     STATUS      current
     DESCRIPTION
         "
         Indicates the Auth Name of the sip group number.
         "
     ::= { hwSipGroupNumberRightEntry 11 }
     
   hwSipGroupNumberRightAuthPasswordMode OBJECT-TYPE
     SYNTAX      INTEGER{password(1),ha1(2)}
     MAX-ACCESS  read-write
     STATUS      current
     DESCRIPTION
         "
         Indicates the Auth PasswordMode of the sip group number.
         Options:
         1. password(1) -auth by password
         2. ha1(2) -auth by HA1
         "
     ::= { hwSipGroupNumberRightEntry 12 }  
   
   hwSipGroupNumberRightAuthPassword OBJECT-TYPE
     SYNTAX      OCTET STRING(SIZE (0..64))
     MAX-ACCESS  read-write
     STATUS      current
     DESCRIPTION
         "
         Indicates the Auth Password of the sip group number.
         "
     ::= { hwSipGroupNumberRightEntry 13 }
     
   hwSipGroupNumberRightAuthHA1 OBJECT-TYPE
     SYNTAX      OCTET STRING(SIZE (0..32))
     MAX-ACCESS  read-write
     STATUS      current
     DESCRIPTION
         "
         Indicates the Auth HA1 value of the sip group number.
         "
     ::= { hwSipGroupNumberRightEntry 14 }
     
   hwSipGroupNumberRightCw OBJECT-TYPE
     SYNTAX      INTEGER{enable(1),disable(2)}
     MAX-ACCESS  read-write
     STATUS      current
     DESCRIPTION
         "
         Indicates the call-waiting right of the sip group number.It is valid to ring-parallel-group.
         Options:
         1. enable(1) -enable
         2. disable(2) -disable
         Default: disable(2)
         "
     ::= { hwSipGroupNumberRightEntry 15 }
     
   hwSipGroupNumberRightDc OBJECT-TYPE
     SYNTAX      INTEGER{enable(1),disable(2)}
     MAX-ACCESS  read-write
     STATUS      current
     DESCRIPTION
         "
         Indicates the dual communication right of the sip group number.
         Options:
         1. enable(1) -enable
         2. disable(2) -disable
         Default: enable(1)
         "
     ::= { hwSipGroupNumberRightEntry 16 }
   
   hwSipGroupNumberRightMwi OBJECT-TYPE
     SYNTAX      INTEGER{enable(1),disable(2)}
     MAX-ACCESS  read-write
     STATUS      current
     DESCRIPTION
         "
         Indicates the mwi right of the sip group number.It is valid to ring-parallel-group.
         Options:
         1. enable(1) -enable
         2. disable(2) -disable
         Default: disable(2)
         "
     ::= { hwSipGroupNumberRightEntry 17 }
     
   hwSipGroupNumberRightAnonymousCall OBJECT-TYPE
     SYNTAX      INTEGER{enable(1),disable(2)}
     MAX-ACCESS  read-write
     STATUS      current
     DESCRIPTION
         "
         Indicates the anonymous-call right of the sip group number.
         Options:
         1. enable(1) -enable
         2. disable(2) -disable
         Default: disable(2)
         "
     ::= { hwSipGroupNumberRightEntry 18 }
   
   hwSipGroupNumberRightAutoReversePolarity OBJECT-TYPE
     SYNTAX      INTEGER{enable(1),disable(2)}
     MAX-ACCESS  read-write
     STATUS      current
     DESCRIPTION
         "
         Indicates the auto reverse polarity right of the sip group number.It is valid to PSTN users.
         Options:
         1. enable(1) -enable
         2. disable(2) -disable
         Default: disable(2)
         "
     ::= { hwSipGroupNumberRightEntry 19 }
     
   hwSipGroupNumberRightDisplayNameMode OBJECT-TYPE
     SYNTAX      INTEGER{enable(1),disable(2)}
     MAX-ACCESS  read-write
     STATUS      current
     DESCRIPTION
         "
         Indicates the display name mode right of the sip group number.
         Options:
         1. enable(1) -enable
         2. disable(2) -disable
         Default: disable(2)
         "
     ::= { hwSipGroupNumberRightEntry 20 }
     
   hwSipGroupNumberRightPermanentHold OBJECT-TYPE
     SYNTAX      INTEGER{enable(1),disable(2)}
     MAX-ACCESS  read-write
     STATUS      current
     DESCRIPTION
         "
         Indicates the permanent-hold right of the sip group number.It is valid to PSTN users.
         Options:
         1. enable(1) -enable
         2. disable(2) -disable
         Default: disable(2)
         "
     ::= { hwSipGroupNumberRightEntry 21 }
     
   hwSipGroupNumberRightCutoffDisconnect OBJECT-TYPE
     SYNTAX      INTEGER{enable(1),disable(2)}
     MAX-ACCESS  read-write
     STATUS      current
     DESCRIPTION
         "
         Indicates the cutoff-disconnect right of the sip group number.It is valid to PSTN users.
         Options:
         1. enable(1) -enable
         2. disable(2) -disable
         Default: disable(2)
         "
     ::= { hwSipGroupNumberRightEntry 22 }
     
   hwSipGroupNumberRightSccClass OBJECT-TYPE
     SYNTAX      INTEGER{enable(1),disable(2)}
     MAX-ACCESS  read-write
     STATUS      current
     DESCRIPTION
         "
         Indicates the SCC class service( for example call-park, call-pickup, EBO.) right of the sip group number.It is valid to PSTN users.
         Options:
         1. enable(1) -enable
         2. disable(2) -disable
         Default: disable(2)
         "
     ::= { hwSipGroupNumberRightEntry 23 }
     
   hwSipGroupNumberRightFastDisconnect OBJECT-TYPE
     SYNTAX      INTEGER{enable(1),disable(2)}
     MAX-ACCESS  read-write
     STATUS      current
     DESCRIPTION
         "
         Indicates the fast-disconnect right of the sip group number.It is valid to PSTN users.
         Options:
         1. enable(1) -enable
         2. disable(2) -disable
         Default: disable(2)
         "
     ::= { hwSipGroupNumberRightEntry 24 }
   
   hwSipGroupNumberRightHotLine OBJECT-TYPE
     SYNTAX      INTEGER{enable(1),disable(2)}
     MAX-ACCESS  read-write
     STATUS      current
     DESCRIPTION
         "
         Indicates the hotline right of the sip group number.It is valid to PSTN users.
         Options:
         1. enable(1) -enable
         2. disable(2) -disable
         Default: disable(2)
         "
     ::= { hwSipGroupNumberRightEntry 25 }
     
   hwSipGroupNumberRightMwiMode OBJECT-TYPE
     SYNTAX      INTEGER{deferred(1),immediate(2),combine(3)}
     MAX-ACCESS  read-write
     STATUS      current
     DESCRIPTION
         "
         Indicates the MwiMode of the sip group number.It is valid to ring-parallel-group.
         Options:
         1. deferred(1) -deferred
         2. immediate(2) -immediate
         3. combine(3) -combine
         Default: deferred(1)
         "
     ::= { hwSipGroupNumberRightEntry 26 }
     
   hwSipGroupNumberRightHotTime OBJECT-TYPE
     SYNTAX      Integer32(0..255)
     MAX-ACCESS  read-write
     STATUS      current
     DESCRIPTION
         "
         Indicates the HotTime of the sip group number.It is valid to PSTN users.
         Unit: second
         Default: 5
         "
     ::= { hwSipGroupNumberRightEntry 27 }
        
   hwSipGroupNumberRightHotLineNum OBJECT-TYPE
     SYNTAX      OCTET STRING(SIZE(0..64))
     MAX-ACCESS  read-write
     STATUS      current
     DESCRIPTION
         "
         Indicates the HotLineNum of the sip group number, the length of hotlinenum mustn't exceed 64.It is valid to PSTN users.
         "
     ::= { hwSipGroupNumberRightEntry 28 }   
     
   hwSipGroupNumberRightDialTone OBJECT-TYPE
     SYNTAX      INTEGER{normal(1),special(2),mw(3),stutter(4)}
     MAX-ACCESS  read-write
     STATUS      current
     DESCRIPTION
         "
         Indicates the DialTone of the sip group number.
         Options:
         1. normal(1) -normal tone
         2. special(2) -special tone
         3. mw(3) -message waiting tone
         4. stutter(4) -stutter tone
         Default: normal(1)
         "
     ::= { hwSipGroupNumberRightEntry 29 }  
                             
   hwSipGroupNumberRightCfbNum OBJECT-TYPE
     SYNTAX      OCTET STRING(SIZE(0..64))
     MAX-ACCESS  read-write
     STATUS      current
     DESCRIPTION
         "
         Indicates the CfbNum of the sip group number.It is valid to ring-parallel-group.
         "
     ::= { hwSipGroupNumberRightEntry 30 }                          
                         
   hwSipGroupNumberRightCfnrNum OBJECT-TYPE
     SYNTAX      OCTET STRING(SIZE(0..64))
     MAX-ACCESS  read-write
     STATUS      current
     DESCRIPTION
         "
         Indicates the CfnrNum of the sip group number.It is valid to ring-parallel-group.
         "
     ::= { hwSipGroupNumberRightEntry 31 }  
     
   hwSipGroupNumberRightCfuNum OBJECT-TYPE
     SYNTAX      OCTET STRING(SIZE(0..64))
     MAX-ACCESS  read-write
     STATUS      current
     DESCRIPTION
         "
         Indicates the CfuNum of the sip group number.It is valid to ring-parallel-group.
         "
     ::= { hwSipGroupNumberRightEntry 32 }                      
   
   hwSipGroupNumberRightCfnrTime OBJECT-TYPE
     SYNTAX      Integer32(0..65535)
     MAX-ACCESS  read-write
     STATUS      current
     DESCRIPTION
         "
         Indicates the CfnrTime of the sip group number.It is valid to ring-parallel-group.
         Unit: second
         Default: 100
         "
     ::= { hwSipGroupNumberRightEntry 33 }
     
   hwSipGroupNumberRightDisplayName OBJECT-TYPE
     SYNTAX      OCTET STRING(SIZE(0..256))
     MAX-ACCESS  read-write
     STATUS      current
     DESCRIPTION
         "
         Indicates the display name string. The character set is unrestricted.
         "
     ::= { hwSipGroupNumberRightEntry 34 }
     
   hwSipGroupNumberRightPermanentHoldMode OBJECT-TYPE
     SYNTAX      INTEGER{norecall(1),reminder(2),recall(3)}
     MAX-ACCESS  read-write
     STATUS      current
     DESCRIPTION
         "
         Indicates the PermanentHoldMode of the sip group number.It is valid to PSTN users.
         Options:
         1. norecall(1) -no recall
         2. reminder(2) -reminder
         3. recall(3) -recall
         Default: norecall(1)
         "
     ::= { hwSipGroupNumberRightEntry 35 }
     
   hwSipGroupNumberRightPermanentHoldTime OBJECT-TYPE
     SYNTAX      Integer32(12..1023)
     MAX-ACCESS  read-write
     STATUS      current
     DESCRIPTION
         "
         Indicates the PermanentHoldTime of the sip group number.It is valid to PSTN users.
         Unit: second
         Default: 20
         " 
     ::= { hwSipGroupNumberRightEntry 36 }
     
--    
   hwSipRingParallelGroupTable OBJECT-TYPE
     SYNTAX      SEQUENCE OF HwSipRingParallelGroupEntry
     MAX-ACCESS  not-accessible
     STATUS      current
     DESCRIPTION
       "
       This table is used to config the parameters of sip ring-parallel-group.
       The indexes of this table are hwSipRPGVgwId, hwSipRPGName.
       "
     ::= { hwVoipSipObjects 23 }

   hwSipRingParallelGroupEntry OBJECT-TYPE
     SYNTAX      HwSipRingParallelGroupEntry
     MAX-ACCESS  not-accessible
     STATUS      current
     DESCRIPTION
       "
       This table is used to config the parameters of sip ring-parallel-group.
       The indexes of this entry are hwSipRPGVgwId, hwSipRPGName.
       "
     INDEX    {
                hwSipRPGVgwId,
                hwSipRPGName
              }
     ::= { hwSipRingParallelGroupTable 1 }

   HwSipRingParallelGroupEntry ::=
     SEQUENCE
     {
       hwSipRPGVgwId Integer32,
       hwSipRPGName OCTET STRING,
       hwSipRPGSelectMode INTEGER,
       hwSipRPGRowStatus RowStatus
     }

   hwSipRPGVgwId OBJECT-TYPE
     SYNTAX      Integer32(0..16777215)
     MAX-ACCESS  not-accessible
     STATUS      current
     DESCRIPTION
         "
         SIP GateWay ID.
         "
     ::= { hwSipRingParallelGroupEntry 1 }

   hwSipRPGName OBJECT-TYPE
     SYNTAX      OCTET STRING(SIZE (1..32))
     MAX-ACCESS  not-accessible
     STATUS      current
     DESCRIPTION
         "
         Indicates the sip ring-parallel-group Name.
         The name cannot contain a question mark or double quotation marks.
         "
     ::= { hwSipRingParallelGroupEntry 2 }

   hwSipRPGSelectMode OBJECT-TYPE
     SYNTAX      INTEGER{busyfirst(1),idlefirst(2)}
     MAX-ACCESS  read-write
     STATUS      current
     DESCRIPTION
         "
         Indicates the Select Mode of the sip ring-parallel-group.
         Options:
         1. busyfirst(1) -hunt all busy members first
         2. idlefirst(2) -hunt all idle members first
         Default: busyfirst(1)
         "
     ::= { hwSipRingParallelGroupEntry 3 }

   hwSipRPGRowStatus OBJECT-TYPE
     SYNTAX      RowStatus
     MAX-ACCESS  read-write
     STATUS      current
     DESCRIPTION
         "
         This is used to create new rows in this table, modify existing rows, and to delete existing rows.
         "
     ::= { hwSipRingParallelGroupEntry 4 }
     
--    
   hwSipRingParallelGroupMemberTable OBJECT-TYPE
     SYNTAX      SEQUENCE OF HwSipRingParallelGroupMemberEntry
     MAX-ACCESS  not-accessible
     STATUS      current
     DESCRIPTION
       "
       This table is used to config the parameters of sip ring-parallel-group member.
       The indexes of this table are hwSipRPGMemberGroupName, hwSipRPGMemberPortIndex.
       "
     ::= { hwVoipSipObjects 24 }

   hwSipRingParallelGroupMemberEntry OBJECT-TYPE
     SYNTAX      HwSipRingParallelGroupMemberEntry
     MAX-ACCESS  not-accessible
     STATUS      current
     DESCRIPTION
       "
       This table is used to config the parameters of sip ring-parallel-group member.
       The indexes of this entry are hwSipRPGMemberGroupName, hwSipRPGMemberPortIndex.
       "
     INDEX    {
                hwSipRPGMemberGroupName,
                hwSipRPGMemberPortIndex
              }
     ::= { hwSipRingParallelGroupMemberTable 1 }

   HwSipRingParallelGroupMemberEntry ::=
     SEQUENCE
     {
       hwSipRPGMemberGroupName OCTET STRING,
       hwSipRPGMemberPortIndex Unsigned32,
       hwSipRPGMemberRowStatus RowStatus
     }

   hwSipRPGMemberGroupName OBJECT-TYPE
     SYNTAX      OCTET STRING(SIZE (1..32))
     MAX-ACCESS  not-accessible
     STATUS      current
     DESCRIPTION
         "
         Indicates the sip ring-parallel-group member Name.
         The name cannot contain a question mark or double quotation marks.
         "
     ::= { hwSipRingParallelGroupMemberEntry 1 }
     
   hwSipRPGMemberPortIndex OBJECT-TYPE
     SYNTAX      Unsigned32(0..4294967295)
     MAX-ACCESS  not-accessible
     STATUS      current
     DESCRIPTION
         "
         Indicates the index of the port member in sip ring-parallel-group.
         "
     ::= { hwSipRingParallelGroupMemberEntry 2 }

   hwSipRPGMemberRowStatus OBJECT-TYPE
     SYNTAX      RowStatus
     MAX-ACCESS  read-write
     STATUS      current
     DESCRIPTION
         "
         This is used to create new rows in this table, modify existing rows, and to delete existing rows.
         "
     ::= { hwSipRingParallelGroupMemberEntry 3 }
   
--    
   hwVGWLoadsharingRunningTable OBJECT-TYPE
     SYNTAX      SEQUENCE OF HwVGWLoadsharingRunningEntry
     MAX-ACCESS  not-accessible
     STATUS      current
     DESCRIPTION
       "
       This table is used to query load sharing addresses of proxy.
       The indexes of this table are hwVGWLoadsharingRunningVgwId, hwVGWLoadsharingRunningAddressIndex.
       "
     ::= { hwVoipSipObjects 25 }

   hwVGWLoadsharingRunningEntry OBJECT-TYPE
     SYNTAX      HwVGWLoadsharingRunningEntry
     MAX-ACCESS  not-accessible
     STATUS      current
     DESCRIPTION
       "
       This table is used to query load sharing addresses of proxy.
       The indexes of this entry are hwVGWLoadsharingRunningVgwId, hwVGWLoadsharingRunningAddressIndex.
       "
     INDEX    {
                hwVGWLoadsharingRunningVgwId,
                hwVGWLoadsharingRunningAddressIndex
              }
     ::= { hwVGWLoadsharingRunningTable 1 }

   HwVGWLoadsharingRunningEntry ::=
     SEQUENCE
     {
       hwVGWLoadsharingRunningVgwId Integer32,
       hwVGWLoadsharingRunningAddressIndex Integer32,
       hwVGWLoadsharingRunningIpAddress IpAddress,
       hwVGWLoadsharingRunningPort Integer32
     }

   hwVGWLoadsharingRunningVgwId OBJECT-TYPE
     SYNTAX      Integer32(-1..16777215)
     MAX-ACCESS  not-accessible
     STATUS      current
     DESCRIPTION
         "
         SIP GateWay ID.
         "
     ::= { hwVGWLoadsharingRunningEntry 1 }

   hwVGWLoadsharingRunningAddressIndex OBJECT-TYPE
     SYNTAX      Integer32(-1..7)
     MAX-ACCESS  not-accessible
     STATUS      current
     DESCRIPTION
         "
         Indicates address index.
         "
     ::= { hwVGWLoadsharingRunningEntry 2 }
     
   hwVGWLoadsharingRunningIpAddress OBJECT-TYPE
     SYNTAX      IpAddress
     MAX-ACCESS  read-only
     STATUS      current
     DESCRIPTION
         "
         Indicates the load sharing IP of SipVgw.
         "
     ::= { hwVGWLoadsharingRunningEntry 3 }
     
   hwVGWLoadsharingRunningPort OBJECT-TYPE
     SYNTAX      Integer32(1..65535)
     MAX-ACCESS  read-only
     STATUS      current
     DESCRIPTION
         "
         Indicates the load sharing port of SipVgw.
         "
     ::= { hwVGWLoadsharingRunningEntry 4 }      
 END
