-- file automatically created


TELDAT-TRAP-PGMO-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


pgmoTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the PGMO event subsystem."
    REVISION "201401200930Z"
    DESCRIPTION "Initial implementation"
        ::= { telEventTraps 158 }


pgmoEventsGroup	OBJECT IDENTIFIER	::= { pgmoTrapsMIB 1 }

pgmoNotifications	OBJECT IDENTIFIER	::= { pgmoTrapsMIB 2 }
pgmoNotificationsPrefix	OBJECT IDENTIFIER	::= { pgmoNotifications 0 }

pgmoEventObjects1 OBJECT-IDENTITY
    STATUS current
    DESCRIPTION
        "Event PGMO.1
        POS Gateway don't answer to monitoring ping."
    ::= { pgmoEventsGroup 1 }

pgmo1-virtual-ip OBJECT-TYPE
    SYNTAX IpAddress
    MAX-ACCESS accessible-for-notify
    STATUS current
    DESCRIPTION
        "Parameter 'virtual-ip' in event PGMO.1"
    ::= { pgmoEventObjects1 1 }

pgmo1-destination-ip OBJECT-TYPE
    SYNTAX IpAddress
    MAX-ACCESS accessible-for-notify
    STATUS current
    DESCRIPTION
        "Parameter 'destination-ip' in event PGMO.1"
    ::= { pgmoEventObjects1 2 }

pgmoEventObjects2 OBJECT-IDENTITY
    STATUS current
    DESCRIPTION
        "Event PGMO.2
        POS Gateway are accessible, leve inaccessible state."
    ::= { pgmoEventsGroup 2 }

pgmo2-virtual-ip OBJECT-TYPE
    SYNTAX IpAddress
    MAX-ACCESS accessible-for-notify
    STATUS current
    DESCRIPTION
        "Parameter 'virtual-ip' in event PGMO.2"
    ::= { pgmoEventObjects2 1 }

pgmo2-destination-ip OBJECT-TYPE
    SYNTAX IpAddress
    MAX-ACCESS accessible-for-notify
    STATUS current
    DESCRIPTION
        "Parameter 'destination-ip' in event PGMO.2"
    ::= { pgmoEventObjects2 2 }

pgmoEventObjects3 OBJECT-IDENTITY
    STATUS current
    DESCRIPTION
        "Event PGMO.3
        POS Gateway IP address are freeze due changes in destination port."
    ::= { pgmoEventsGroup 3 }

pgmo3-virtual-ip OBJECT-TYPE
    SYNTAX IpAddress
    MAX-ACCESS accessible-for-notify
    STATUS current
    DESCRIPTION
        "Parameter 'virtual-ip' in event PGMO.3"
    ::= { pgmoEventObjects3 1 }

pgmo3-destination-ip OBJECT-TYPE
    SYNTAX IpAddress
    MAX-ACCESS accessible-for-notify
    STATUS current
    DESCRIPTION
        "Parameter 'destination-ip' in event PGMO.3"
    ::= { pgmoEventObjects3 2 }

pgmoEventObjects4 OBJECT-IDENTITY
    STATUS current
    DESCRIPTION
        "Event PGMO.4
        POS Gateway IP address are unfreeze."
    ::= { pgmoEventsGroup 4 }

pgmo4-virtual-ip OBJECT-TYPE
    SYNTAX IpAddress
    MAX-ACCESS accessible-for-notify
    STATUS current
    DESCRIPTION
        "Parameter 'virtual-ip' in event PGMO.4"
    ::= { pgmoEventObjects4 1 }

pgmo4-destination-ip OBJECT-TYPE
    SYNTAX IpAddress
    MAX-ACCESS accessible-for-notify
    STATUS current
    DESCRIPTION
        "Parameter 'destination-ip' in event PGMO.4"
    ::= { pgmoEventObjects4 2 }

pgmoEventObjects5 OBJECT-IDENTITY
    STATUS current
    DESCRIPTION
        "Event PGMO.5
        A change in destination port was detected."
    ::= { pgmoEventsGroup 5 }

pgmo5-virtual-ip OBJECT-TYPE
    SYNTAX IpAddress
    MAX-ACCESS accessible-for-notify
    STATUS current
    DESCRIPTION
        "Parameter 'virtual-ip' in event PGMO.5"
    ::= { pgmoEventObjects5 1 }

pgmo5-destination-ip OBJECT-TYPE
    SYNTAX IpAddress
    MAX-ACCESS accessible-for-notify
    STATUS current
    DESCRIPTION
        "Parameter 'destination-ip' in event PGMO.5"
    ::= { pgmoEventObjects5 2 }


pgmoNotification1 NOTIFICATION-TYPE
    OBJECTS { 
              pgmo1-virtual-ip, 
              pgmo1-destination-ip 
            }
    STATUS current
    DESCRIPTION
        "Notification of Event PGMO.1

        Message: 'POS Gateway not accessible (Virt:$1 Dest:$2)'

        Parameters list:
              $1: pgmo1-virtual-ip
              $2: pgmo1-destination-ip

        POS Gateway don't answer to monitoring ping."
    ::= { pgmoNotificationsPrefix 1 }

pgmoNotification2 NOTIFICATION-TYPE
    OBJECTS { 
              pgmo2-virtual-ip, 
              pgmo2-destination-ip 
            }
    STATUS current
    DESCRIPTION
        "Notification of Event PGMO.2

        Message: 'POS Gateway accessible (Virt:$1 Dest:$2)'

        Parameters list:
              $1: pgmo2-virtual-ip
              $2: pgmo2-destination-ip

        POS Gateway are accessible, leve inaccessible state."
    ::= { pgmoNotificationsPrefix 2 }

pgmoNotification3 NOTIFICATION-TYPE
    OBJECTS { 
              pgmo3-virtual-ip, 
              pgmo3-destination-ip 
            }
    STATUS current
    DESCRIPTION
        "Notification of Event PGMO.3

        Message: 'POS Gateway freeze (Virt:$1 Dest:$2)'

        Parameters list:
              $1: pgmo3-virtual-ip
              $2: pgmo3-destination-ip

        POS Gateway IP address are freeze due changes in destination port."
    ::= { pgmoNotificationsPrefix 3 }

pgmoNotification4 NOTIFICATION-TYPE
    OBJECTS { 
              pgmo4-virtual-ip, 
              pgmo4-destination-ip 
            }
    STATUS current
    DESCRIPTION
        "Notification of Event PGMO.4

        Message: 'POS Gateway unfreeze (Virt:$1 Dest:$2)'

        Parameters list:
              $1: pgmo4-virtual-ip
              $2: pgmo4-destination-ip

        POS Gateway IP address are unfreeze."
    ::= { pgmoNotificationsPrefix 4 }

pgmoNotification5 NOTIFICATION-TYPE
    OBJECTS { 
              pgmo5-virtual-ip, 
              pgmo5-destination-ip 
            }
    STATUS current
    DESCRIPTION
        "Notification of Event PGMO.5

        Message: 'Destination Port change detected (Virt:$1 Dest:$2)'

        Parameters list:
              $1: pgmo5-virtual-ip
              $2: pgmo5-destination-ip

        A change in destination port was detected."
    ::= { pgmoNotificationsPrefix 5 }


END
