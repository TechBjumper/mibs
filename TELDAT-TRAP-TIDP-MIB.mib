-- file automatically created


TELDAT-TRAP-TIDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tidpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TIDP event subsystem."
    REVISION "201401200930Z"
    DESCRIPTION "Initial implementation"
        ::= { telEventTraps 197 }


tidpEventsGroup	OBJECT IDENTIFIER	::= { tidpTrapsMIB 1 }

tidpNotifications	OBJECT IDENTIFIER	::= { tidpTrapsMIB 2 }
tidpNotificationsPrefix	OBJECT IDENTIFIER	::= { tidpNotifications 0 }

tidpEventObjects1 OBJECT-IDENTITY
    STATUS current
    DESCRIPTION
        "Event TIDP.1
        Sending Notification Message"
    ::= { tidpEventsGroup 1 }

tidp1-ipdestination OBJECT-TYPE
    SYNTAX IpAddress
    MAX-ACCESS accessible-for-notify
    STATUS current
    DESCRIPTION
        "Parameter 'ipdestination' in event TIDP.1"
    ::= { tidpEventObjects1 1 }

tidp1-hostname OBJECT-TYPE
    SYNTAX DisplayString
    MAX-ACCESS accessible-for-notify
    STATUS current
    DESCRIPTION
        "Parameter 'hostname' in event TIDP.1"
    ::= { tidpEventObjects1 2 }

tidp1-serialnumber OBJECT-TYPE
    SYNTAX DisplayString
    MAX-ACCESS accessible-for-notify
    STATUS current
    DESCRIPTION
        "Parameter 'serialnumber' in event TIDP.1"
    ::= { tidpEventObjects1 3 }

tidp1-code OBJECT-TYPE
    SYNTAX Integer32
    MAX-ACCESS accessible-for-notify
    STATUS current
    DESCRIPTION
        "Parameter 'code' in event TIDP.1"
    ::= { tidpEventObjects1 4 }

tidp1-sequencenumber OBJECT-TYPE
    SYNTAX Integer32
    MAX-ACCESS accessible-for-notify
    STATUS current
    DESCRIPTION
        "Parameter 'sequencenumber' in event TIDP.1"
    ::= { tidpEventObjects1 5 }

tidp1-ack-rvd OBJECT-TYPE
    SYNTAX DisplayString
    MAX-ACCESS accessible-for-notify
    STATUS current
    DESCRIPTION
        "Parameter 'ack-rvd' in event TIDP.1"
    ::= { tidpEventObjects1 6 }

tidpEventObjects2 OBJECT-IDENTITY
    STATUS current
    DESCRIPTION
        "Event TIDP.2
        Sending Management Message"
    ::= { tidpEventsGroup 2 }

tidp2-ipdestination OBJECT-TYPE
    SYNTAX IpAddress
    MAX-ACCESS accessible-for-notify
    STATUS current
    DESCRIPTION
        "Parameter 'ipdestination' in event TIDP.2"
    ::= { tidpEventObjects2 1 }

tidp2-hostname OBJECT-TYPE
    SYNTAX DisplayString
    MAX-ACCESS accessible-for-notify
    STATUS current
    DESCRIPTION
        "Parameter 'hostname' in event TIDP.2"
    ::= { tidpEventObjects2 2 }

tidp2-serialnumber OBJECT-TYPE
    SYNTAX DisplayString
    MAX-ACCESS accessible-for-notify
    STATUS current
    DESCRIPTION
        "Parameter 'serialnumber' in event TIDP.2"
    ::= { tidpEventObjects2 3 }

tidp2-code OBJECT-TYPE
    SYNTAX Integer32
    MAX-ACCESS accessible-for-notify
    STATUS current
    DESCRIPTION
        "Parameter 'code' in event TIDP.2"
    ::= { tidpEventObjects2 4 }

tidp2-sequencenumber OBJECT-TYPE
    SYNTAX Integer32
    MAX-ACCESS accessible-for-notify
    STATUS current
    DESCRIPTION
        "Parameter 'sequencenumber' in event TIDP.2"
    ::= { tidpEventObjects2 5 }

tidpEventObjects3 OBJECT-IDENTITY
    STATUS current
    DESCRIPTION
        "Event TIDP.3
        Sending Management Request Message"
    ::= { tidpEventsGroup 3 }

tidp3-hostname OBJECT-TYPE
    SYNTAX DisplayString
    MAX-ACCESS accessible-for-notify
    STATUS current
    DESCRIPTION
        "Parameter 'hostname' in event TIDP.3"
    ::= { tidpEventObjects3 1 }

tidp3-ipdestination OBJECT-TYPE
    SYNTAX IpAddress
    MAX-ACCESS accessible-for-notify
    STATUS current
    DESCRIPTION
        "Parameter 'ipdestination' in event TIDP.3"
    ::= { tidpEventObjects3 2 }

tidp3-port OBJECT-TYPE
    SYNTAX Integer32
    MAX-ACCESS accessible-for-notify
    STATUS current
    DESCRIPTION
        "Parameter 'port' in event TIDP.3"
    ::= { tidpEventObjects3 3 }

tidpEventObjects4 OBJECT-IDENTITY
    STATUS current
    DESCRIPTION
        "Event TIDP.4
        A packet has been received with wrong HMAC checksum"
    ::= { tidpEventsGroup 4 }

tidp4-ipdestination OBJECT-TYPE
    SYNTAX IpAddress
    MAX-ACCESS accessible-for-notify
    STATUS current
    DESCRIPTION
        "Parameter 'ipdestination' in event TIDP.4"
    ::= { tidpEventObjects4 1 }

tidpEventObjects5 OBJECT-IDENTITY
    STATUS current
    DESCRIPTION
        "Event TIDP.5
        A packet has been received with wrong protocol version"
    ::= { tidpEventsGroup 5 }

tidp5-ipdestination OBJECT-TYPE
    SYNTAX IpAddress
    MAX-ACCESS accessible-for-notify
    STATUS current
    DESCRIPTION
        "Parameter 'ipdestination' in event TIDP.5"
    ::= { tidpEventObjects5 1 }

tidpEventObjects6 OBJECT-IDENTITY
    STATUS current
    DESCRIPTION
        "Event TIDP.6
        A packet has been received with wrong packet type"
    ::= { tidpEventsGroup 6 }

tidp6-ipdestination OBJECT-TYPE
    SYNTAX IpAddress
    MAX-ACCESS accessible-for-notify
    STATUS current
    DESCRIPTION
        "Parameter 'ipdestination' in event TIDP.6"
    ::= { tidpEventObjects6 1 }

tidpEventObjects7 OBJECT-IDENTITY
    STATUS current
    DESCRIPTION
        "Event TIDP.7
        Notify Request Received"
    ::= { tidpEventsGroup 7 }

tidp7-ipdestination OBJECT-TYPE
    SYNTAX IpAddress
    MAX-ACCESS accessible-for-notify
    STATUS current
    DESCRIPTION
        "Parameter 'ipdestination' in event TIDP.7"
    ::= { tidpEventObjects7 1 }

tidpEventObjects8 OBJECT-IDENTITY
    STATUS current
    DESCRIPTION
        "Event TIDP.8
        Management Request Received"
    ::= { tidpEventsGroup 8 }

tidp8-ipdestination OBJECT-TYPE
    SYNTAX IpAddress
    MAX-ACCESS accessible-for-notify
    STATUS current
    DESCRIPTION
        "Parameter 'ipdestination' in event TIDP.8"
    ::= { tidpEventObjects8 1 }

tidpEventObjects9 OBJECT-IDENTITY
    STATUS current
    DESCRIPTION
        "Event TIDP.9
        Unknown Type Message Received"
    ::= { tidpEventsGroup 9 }

tidp9-ipdestination OBJECT-TYPE
    SYNTAX IpAddress
    MAX-ACCESS accessible-for-notify
    STATUS current
    DESCRIPTION
        "Parameter 'ipdestination' in event TIDP.9"
    ::= { tidpEventObjects9 1 }

tidpEventObjects10 OBJECT-IDENTITY
    STATUS current
    DESCRIPTION
        "Event TIDP.10
        Notification Messege Received, might be Filtered by in Management"
    ::= { tidpEventsGroup 10 }

tidp10-ipsource OBJECT-TYPE
    SYNTAX IpAddress
    MAX-ACCESS accessible-for-notify
    STATUS current
    DESCRIPTION
        "Parameter 'ipsource' in event TIDP.10"
    ::= { tidpEventObjects10 1 }

tidp10-hostname OBJECT-TYPE
    SYNTAX DisplayString
    MAX-ACCESS accessible-for-notify
    STATUS current
    DESCRIPTION
        "Parameter 'hostname' in event TIDP.10"
    ::= { tidpEventObjects10 2 }

tidp10-serialnumber OBJECT-TYPE
    SYNTAX DisplayString
    MAX-ACCESS accessible-for-notify
    STATUS current
    DESCRIPTION
        "Parameter 'serialnumber' in event TIDP.10"
    ::= { tidpEventObjects10 3 }

tidp10-code OBJECT-TYPE
    SYNTAX Integer32
    MAX-ACCESS accessible-for-notify
    STATUS current
    DESCRIPTION
        "Parameter 'code' in event TIDP.10"
    ::= { tidpEventObjects10 4 }

tidp10-sequencenumber OBJECT-TYPE
    SYNTAX Integer32
    MAX-ACCESS accessible-for-notify
    STATUS current
    DESCRIPTION
        "Parameter 'sequencenumber' in event TIDP.10"
    ::= { tidpEventObjects10 5 }

tidp10-ack-rvd OBJECT-TYPE
    SYNTAX DisplayString
    MAX-ACCESS accessible-for-notify
    STATUS current
    DESCRIPTION
        "Parameter 'ack-rvd' in event TIDP.10"
    ::= { tidpEventObjects10 6 }

tidp10-payloadip OBJECT-TYPE
    SYNTAX IpAddress
    MAX-ACCESS accessible-for-notify
    STATUS current
    DESCRIPTION
        "Parameter 'payloadip' in event TIDP.10"
    ::= { tidpEventObjects10 7 }

tidp10-status OBJECT-TYPE
    SYNTAX DisplayString
    MAX-ACCESS accessible-for-notify
    STATUS current
    DESCRIPTION
        "Parameter 'status' in event TIDP.10"
    ::= { tidpEventObjects10 8 }

tidpEventObjects11 OBJECT-IDENTITY
    STATUS current
    DESCRIPTION
        "Event TIDP.11
        Management Messege Received might be Filtered by in Management"
    ::= { tidpEventsGroup 11 }

tidp11-ipsource OBJECT-TYPE
    SYNTAX IpAddress
    MAX-ACCESS accessible-for-notify
    STATUS current
    DESCRIPTION
        "Parameter 'ipsource' in event TIDP.11"
    ::= { tidpEventObjects11 1 }

tidp11-hostname OBJECT-TYPE
    SYNTAX DisplayString
    MAX-ACCESS accessible-for-notify
    STATUS current
    DESCRIPTION
        "Parameter 'hostname' in event TIDP.11"
    ::= { tidpEventObjects11 2 }

tidp11-serialnumber OBJECT-TYPE
    SYNTAX DisplayString
    MAX-ACCESS accessible-for-notify
    STATUS current
    DESCRIPTION
        "Parameter 'serialnumber' in event TIDP.11"
    ::= { tidpEventObjects11 3 }

tidp11-code OBJECT-TYPE
    SYNTAX Integer32
    MAX-ACCESS accessible-for-notify
    STATUS current
    DESCRIPTION
        "Parameter 'code' in event TIDP.11"
    ::= { tidpEventObjects11 4 }

tidp11-sequencenumber OBJECT-TYPE
    SYNTAX Integer32
    MAX-ACCESS accessible-for-notify
    STATUS current
    DESCRIPTION
        "Parameter 'sequencenumber' in event TIDP.11"
    ::= { tidpEventObjects11 5 }

tidp11-payloadip OBJECT-TYPE
    SYNTAX IpAddress
    MAX-ACCESS accessible-for-notify
    STATUS current
    DESCRIPTION
        "Parameter 'payloadip' in event TIDP.11"
    ::= { tidpEventObjects11 6 }

tidp11-status OBJECT-TYPE
    SYNTAX DisplayString
    MAX-ACCESS accessible-for-notify
    STATUS current
    DESCRIPTION
        "Parameter 'status' in event TIDP.11"
    ::= { tidpEventObjects11 7 }

tidpEventObjects14 OBJECT-IDENTITY
    STATUS current
    DESCRIPTION
        "Event TIDP.14
        Management lost from remote client. No management received in the expected time
        but client can hear master"
    ::= { tidpEventsGroup 14 }

tidp14-hostname OBJECT-TYPE
    SYNTAX DisplayString
    MAX-ACCESS accessible-for-notify
    STATUS current
    DESCRIPTION
        "Parameter 'hostname' in event TIDP.14"
    ::= { tidpEventObjects14 1 }

tidp14-serialnumber OBJECT-TYPE
    SYNTAX DisplayString
    MAX-ACCESS accessible-for-notify
    STATUS current
    DESCRIPTION
        "Parameter 'serialnumber' in event TIDP.14"
    ::= { tidpEventObjects14 2 }

tidpEventObjects15 OBJECT-IDENTITY
    STATUS current
    DESCRIPTION
        "Event TIDP.15
        Management lost from remote client. No management received in the expected time
        and client can not hear master"
    ::= { tidpEventsGroup 15 }

tidp15-hostname OBJECT-TYPE
    SYNTAX DisplayString
    MAX-ACCESS accessible-for-notify
    STATUS current
    DESCRIPTION
        "Parameter 'hostname' in event TIDP.15"
    ::= { tidpEventObjects15 1 }

tidp15-serialnumber OBJECT-TYPE
    SYNTAX DisplayString
    MAX-ACCESS accessible-for-notify
    STATUS current
    DESCRIPTION
        "Parameter 'serialnumber' in event TIDP.15"
    ::= { tidpEventObjects15 2 }

tidpEventObjects16 OBJECT-IDENTITY
    STATUS current
    DESCRIPTION
        "Event TIDP.16
        Notification lost from remote client. No notification received in the expected time."
    ::= { tidpEventsGroup 16 }

tidp16-hostname OBJECT-TYPE
    SYNTAX DisplayString
    MAX-ACCESS accessible-for-notify
    STATUS current
    DESCRIPTION
        "Parameter 'hostname' in event TIDP.16"
    ::= { tidpEventObjects16 1 }

tidp16-serialnumber OBJECT-TYPE
    SYNTAX DisplayString
    MAX-ACCESS accessible-for-notify
    STATUS current
    DESCRIPTION
        "Parameter 'serialnumber' in event TIDP.16"
    ::= { tidpEventObjects16 2 }

tidpEventObjects17 OBJECT-IDENTITY
    STATUS current
    DESCRIPTION
        "Event TIDP.17
        Sending Reset Request Message"
    ::= { tidpEventsGroup 17 }

tidp17-hostname OBJECT-TYPE
    SYNTAX DisplayString
    MAX-ACCESS accessible-for-notify
    STATUS current
    DESCRIPTION
        "Parameter 'hostname' in event TIDP.17"
    ::= { tidpEventObjects17 1 }

tidp17-ipdestination OBJECT-TYPE
    SYNTAX IpAddress
    MAX-ACCESS accessible-for-notify
    STATUS current
    DESCRIPTION
        "Parameter 'ipdestination' in event TIDP.17"
    ::= { tidpEventObjects17 2 }

tidp17-port OBJECT-TYPE
    SYNTAX Integer32
    MAX-ACCESS accessible-for-notify
    STATUS current
    DESCRIPTION
        "Parameter 'port' in event TIDP.17"
    ::= { tidpEventObjects17 3 }

tidpEventObjects18 OBJECT-IDENTITY
    STATUS current
    DESCRIPTION
        "Event TIDP.18
        Management Reset Received"
    ::= { tidpEventsGroup 18 }

tidp18-ipdestination OBJECT-TYPE
    SYNTAX IpAddress
    MAX-ACCESS accessible-for-notify
    STATUS current
    DESCRIPTION
        "Parameter 'ipdestination' in event TIDP.18"
    ::= { tidpEventObjects18 1 }


tidpNotification1 NOTIFICATION-TYPE
    OBJECTS { 
              tidp1-ipdestination, 
              tidp1-hostname,
              tidp1-serialnumber,
              tidp1-code,
              tidp1-sequencenumber,
              tidp1-ack-rvd 
            }
    STATUS current
    DESCRIPTION
        "Notification of Event TIDP.1

        Message: 'Sending Notify to $1->host $2, serial $3, code $4, seq $5, mng-rcv-ack $6'

        Parameters list:
              $1: tidp1-ipdestination
              $2: tidp1-hostname
              $3: tidp1-serialnumber
              $4: tidp1-code
              $5: tidp1-sequencenumber
              $6: tidp1-ack-rvd

        Sending Notification Message"
    ::= { tidpNotificationsPrefix 1 }

tidpNotification2 NOTIFICATION-TYPE
    OBJECTS { 
              tidp2-ipdestination, 
              tidp2-hostname,
              tidp2-serialnumber,
              tidp2-code,
              tidp2-sequencenumber 
            }
    STATUS current
    DESCRIPTION
        "Notification of Event TIDP.2

        Message: 'Sending Management to $1->host $2, serial $3, code $4, seq $5'

        Parameters list:
              $1: tidp2-ipdestination
              $2: tidp2-hostname
              $3: tidp2-serialnumber
              $4: tidp2-code
              $5: tidp2-sequencenumber

        Sending Management Message"
    ::= { tidpNotificationsPrefix 2 }

tidpNotification3 NOTIFICATION-TYPE
    OBJECTS { 
              tidp3-hostname, 
              tidp3-ipdestination,
              tidp3-port 
            }
    STATUS current
    DESCRIPTION
        "Notification of Event TIDP.3

        Message: 'Sending Management Request to hostname $1, $2, port $3'

        Parameters list:
              $1: tidp3-hostname
              $2: tidp3-ipdestination
              $3: tidp3-port

        Sending Management Request Message"
    ::= { tidpNotificationsPrefix 3 }

tidpNotification4 NOTIFICATION-TYPE
    OBJECTS { 
              tidp4-ipdestination 
            }
    STATUS current
    DESCRIPTION
        "Notification of Event TIDP.4

        Message: 'Bad HMAC from $1'

        Parameters list:
              $1: tidp4-ipdestination

        A packet has been received with wrong HMAC checksum"
    ::= { tidpNotificationsPrefix 4 }

tidpNotification5 NOTIFICATION-TYPE
    OBJECTS { 
              tidp5-ipdestination 
            }
    STATUS current
    DESCRIPTION
        "Notification of Event TIDP.5

        Message: 'Bad protocol version from $1'

        Parameters list:
              $1: tidp5-ipdestination

        A packet has been received with wrong protocol version"
    ::= { tidpNotificationsPrefix 5 }

tidpNotification6 NOTIFICATION-TYPE
    OBJECTS { 
              tidp6-ipdestination 
            }
    STATUS current
    DESCRIPTION
        "Notification of Event TIDP.6

        Message: 'Bad packet type from $1'

        Parameters list:
              $1: tidp6-ipdestination

        A packet has been received with wrong packet type"
    ::= { tidpNotificationsPrefix 6 }

tidpNotification7 NOTIFICATION-TYPE
    OBJECTS { 
              tidp7-ipdestination 
            }
    STATUS current
    DESCRIPTION
        "Notification of Event TIDP.7

        Message: 'Notify Request Received from $1'

        Parameters list:
              $1: tidp7-ipdestination

        Notify Request Received"
    ::= { tidpNotificationsPrefix 7 }

tidpNotification8 NOTIFICATION-TYPE
    OBJECTS { 
              tidp8-ipdestination 
            }
    STATUS current
    DESCRIPTION
        "Notification of Event TIDP.8

        Message: 'Management Request Received from $1'

        Parameters list:
              $1: tidp8-ipdestination

        Management Request Received"
    ::= { tidpNotificationsPrefix 8 }

tidpNotification9 NOTIFICATION-TYPE
    OBJECTS { 
              tidp9-ipdestination 
            }
    STATUS current
    DESCRIPTION
        "Notification of Event TIDP.9

        Message: 'Unknown Type Message Received from $1'

        Parameters list:
              $1: tidp9-ipdestination

        Unknown Type Message Received"
    ::= { tidpNotificationsPrefix 9 }

tidpNotification10 NOTIFICATION-TYPE
    OBJECTS { 
              tidp10-ipsource, 
              tidp10-hostname,
              tidp10-serialnumber,
              tidp10-code,
              tidp10-sequencenumber,
              tidp10-ack-rvd,
              tidp10-payloadip,
              tidp10-status 
            }
    STATUS current
    DESCRIPTION
        "Notification of Event TIDP.10

        Message: 'Notify Received from $1, hostname $2, serial $3, code $4, seq $5, mng-rcv-ack $6, payload IP $7, status $8'

        Parameters list:
              $1: tidp10-ipsource
              $2: tidp10-hostname
              $3: tidp10-serialnumber
              $4: tidp10-code
              $5: tidp10-sequencenumber
              $6: tidp10-ack-rvd
              $7: tidp10-payloadip
              $8: tidp10-status

        Notification Messege Received, might be Filtered by in Management"
    ::= { tidpNotificationsPrefix 10 }

tidpNotification11 NOTIFICATION-TYPE
    OBJECTS { 
              tidp11-ipsource, 
              tidp11-hostname,
              tidp11-serialnumber,
              tidp11-code,
              tidp11-sequencenumber,
              tidp11-payloadip,
              tidp11-status 
            }
    STATUS current
    DESCRIPTION
        "Notification of Event TIDP.11

        Message: 'Management Received from $1, hostname $2, serial $3, code $4, seq $5, payload IP $6, status $7'

        Parameters list:
              $1: tidp11-ipsource
              $2: tidp11-hostname
              $3: tidp11-serialnumber
              $4: tidp11-code
              $5: tidp11-sequencenumber
              $6: tidp11-payloadip
              $7: tidp11-status

        Management Messege Received might be Filtered by in Management"
    ::= { tidpNotificationsPrefix 11 }

tidpNotification12 NOTIFICATION-TYPE
    STATUS current
    DESCRIPTION
        "Notification of Event TIDP.12

        Message: 'Disable Filter of Notify Received Messages'

        Disables Filter of Notify Received Messages"
    ::= { tidpNotificationsPrefix 12 }

tidpNotification13 NOTIFICATION-TYPE
    STATUS current
    DESCRIPTION
        "Notification of Event TIDP.13

        Message: 'Disable Filter of Management Received Messages'

        Disables Filter of Management Received Messages"
    ::= { tidpNotificationsPrefix 13 }

tidpNotification14 NOTIFICATION-TYPE
    OBJECTS { 
              tidp14-hostname, 
              tidp14-serialnumber 
            }
    STATUS current
    DESCRIPTION
        "Notification of Event TIDP.14

        Message: 'Management lost from hostname $1, serial $2, though client can hear master'

        Parameters list:
              $1: tidp14-hostname
              $2: tidp14-serialnumber

        Management lost from remote client. No management received in the expected time
        but client can hear master"
    ::= { tidpNotificationsPrefix 14 }

tidpNotification15 NOTIFICATION-TYPE
    OBJECTS { 
              tidp15-hostname, 
              tidp15-serialnumber 
            }
    STATUS current
    DESCRIPTION
        "Notification of Event TIDP.15

        Message: 'Management lost from hostname $1, serial $2, and client can not hear master'

        Parameters list:
              $1: tidp15-hostname
              $2: tidp15-serialnumber

        Management lost from remote client. No management received in the expected time
        and client can not hear master"
    ::= { tidpNotificationsPrefix 15 }

tidpNotification16 NOTIFICATION-TYPE
    OBJECTS { 
              tidp16-hostname, 
              tidp16-serialnumber 
            }
    STATUS current
    DESCRIPTION
        "Notification of Event TIDP.16

        Message: 'Notify lost from hostname $1, serial $2'

        Parameters list:
              $1: tidp16-hostname
              $2: tidp16-serialnumber

        Notification lost from remote client. No notification received in the expected time."
    ::= { tidpNotificationsPrefix 16 }

tidpNotification17 NOTIFICATION-TYPE
    OBJECTS { 
              tidp17-hostname, 
              tidp17-ipdestination,
              tidp17-port 
            }
    STATUS current
    DESCRIPTION
        "Notification of Event TIDP.17

        Message: 'Sending Reset Request to hostname $1, $2, port $3'

        Parameters list:
              $1: tidp17-hostname
              $2: tidp17-ipdestination
              $3: tidp17-port

        Sending Reset Request Message"
    ::= { tidpNotificationsPrefix 17 }

tidpNotification18 NOTIFICATION-TYPE
    OBJECTS { 
              tidp18-ipdestination 
            }
    STATUS current
    DESCRIPTION
        "Notification of Event TIDP.18

        Message: 'Management Reset Received from $1'

        Parameters list:
              $1: tidp18-ipdestination

        Management Reset Received"
    ::= { tidpNotificationsPrefix 18 }


END
