NWA1100-NI DEFINITIONS ::= BEGIN

IMPORTS
    ifIndex         
        FROM RFC1213-MIB            
    enterprises, IpAddress, Integer32, Counter32, Counter64, OBJECT-TYPE, 
    MODULE-IDENTITY         
        FROM SNMPv2-SMI         
    DisplayString, MacAddress           
        FROM SNMPv2-TC
    
    
	esMgmt			        FROM ZYXEL-ES-SMI
	esConformance			FROM ZYXEL-ES-SMI;

--supported groups by esMgmt
esSysInfo           OBJECT IDENTIFIER ::= { esMgmt 1 }
esSysMgmt           OBJECT IDENTIFIER ::= { esMgmt 2 }
esWireless          OBJECT IDENTIFIER ::= { esMgmt 5 }

--
-- esSysInfo
--

--
-- The sub tree for system information.
--

sysSwPlatform OBJECT-TYPE
    SYNTAX DisplayString
    MAX-ACCESS read-only
    STATUS current
    DESCRIPTION
        "ZyXEL S/W platform information"
    ::= { esSysInfo 1 }
        
sysSwMajorVersion OBJECT-TYPE
    SYNTAX DisplayString
    MAX-ACCESS read-only
    STATUS current
    DESCRIPTION
        "The major version for ZyXEL S/W platform"
    ::= { esSysInfo 2 }
        
sysSwMinorVersion OBJECT-TYPE
    SYNTAX DisplayString
    MAX-ACCESS read-only
    STATUS current
    DESCRIPTION
        "The minor version for ZyXEL S/W platform"
    ::= { esSysInfo 3 }
        
sysSwModel OBJECT-TYPE
    SYNTAX DisplayString
    MAX-ACCESS read-only
    STATUS current
    DESCRIPTION
        "The F/W ID for each device model"
    ::= { esSysInfo 4 }

sysSwPatchNumber OBJECT-TYPE
    SYNTAX DisplayString
    MAX-ACCESS read-only
    STATUS current
    DESCRIPTION
        "The F/W patch number for each device model"
    ::= { esSysInfo 5 }

sysSwVersionString OBJECT-TYPE
    SYNTAX DisplayString
    MAX-ACCESS read-only
    STATUS current
    DESCRIPTION
        "Device firmware version"
    ::= { esSysInfo 6 }

sysSwDay OBJECT-TYPE
    SYNTAX DisplayString
    MAX-ACCESS read-only
    STATUS current
    DESCRIPTION
        "The F/W release date(Day)"
    ::= { esSysInfo 7 }

sysSwMonth OBJECT-TYPE
    SYNTAX DisplayString
    MAX-ACCESS read-only
    STATUS current
    DESCRIPTION
        "The F/W release date(Month)"
    ::= { esSysInfo 8 }

sysSwYear OBJECT-TYPE
    SYNTAX DisplayString
    MAX-ACCESS read-only
    STATUS current
    DESCRIPTION
        "The F/W release date(Year)"
    ::= { esSysInfo 9 }

sysProductFamily OBJECT-TYPE
    SYNTAX DisplayString
    MAX-ACCESS read-only
    STATUS current
    DESCRIPTION
        "The product line information"
    ::= { esSysInfo 10 }

sysProductModel OBJECT-TYPE
    SYNTAX DisplayString
    MAX-ACCESS read-only
    STATUS current
    DESCRIPTION
        "Device model name"
    ::= { esSysInfo 11 }

sysProductSerialNumber OBJECT-TYPE
    SYNTAX DisplayString
    MAX-ACCESS read-only
    STATUS current
    DESCRIPTION
        "The serial number for each product"
    ::= { esSysInfo 12 }

sysHwMajorVersion OBJECT-TYPE
    SYNTAX DisplayString
    MAX-ACCESS read-only
    STATUS current
    DESCRIPTION
        "Hardware major version"
    ::= { esSysInfo 13 }

sysHwMinorVersion OBJECT-TYPE
    SYNTAX DisplayString
    MAX-ACCESS read-only
    STATUS current
    DESCRIPTION
        "Hardware minor version"
    ::= { esSysInfo 14 }

sysHwVersionString OBJECT-TYPE
    SYNTAX DisplayString
    MAX-ACCESS read-only
    STATUS current
    DESCRIPTION
        "Hardware version string"
    ::= { esSysInfo 15 }

sysCountryCode OBJECT-TYPE
    SYNTAX INTEGER
        {
        au(36),
        ai(40),
        ca(124),
        cn(156),
        tw(158),
        dk(208),
        fi(246),
        fr(250),
        de(276),
        hk(344),
        is(352),
        id(356),
        ie(372),
        it(380),
        jp(392),
        li(438),
        lu(442),
        nl(528),
        nz(554),
        no(578),
        pt(620),
        sg(702),
        es(724),
        se(752),
        ch(756),
        uk(826),
        us(840)
        }
    MAX-ACCESS read-only
    STATUS current
    DESCRIPTION
        "System country code."
    ::= { esSysInfo 16 }

sysCurrentDateTime OBJECT-TYPE
    SYNTAX DisplayString
    MAX-ACCESS read-only
    STATUS current
    DESCRIPTION
        "System current date."
    ::= { esSysInfo 17 }

sysCurrentTime OBJECT-TYPE
    SYNTAX DisplayString
    MAX-ACCESS read-only
    STATUS current
    DESCRIPTION
        "System current time."
    ::= { esSysInfo 18 }

--
-- esSysMgmt
--

--
-- The sub tree for basic system management.
--

sysMgmtReboot OBJECT-TYPE
    SYNTAX INTEGER
        {
        no(0),
        yes(1)
        }
    MAX-ACCESS read-write
    STATUS current
    DESCRIPTION
        "Reboot the device."
    ::= { esSysMgmt 1 }

sysMgmtConfigSave OBJECT-TYPE
    SYNTAX OCTET STRING
    MAX-ACCESS read-write
    STATUS current
    DESCRIPTION
        "Enter any string to save all configuration into flash memory"
    ::= { esSysMgmt 2 }

sysMgmtRestoreDefaultConfig OBJECT-TYPE
    SYNTAX INTEGER
        {
        running(0),
        restore(1)
        }
    MAX-ACCESS read-write
    STATUS current
    DESCRIPTION
        "Reset device to system default configuration"
    ::= { esSysMgmt 3 }

sysMgmtCPUUsage OBJECT-TYPE
    SYNTAX DisplayString (SIZE (0..100))
    MAX-ACCESS read-only
    STATUS current
    DESCRIPTION
        "Device CPU load."
    ::= { esSysMgmt 4 }

sysMgmtMemUsage OBJECT-TYPE
    SYNTAX DisplayString (SIZE (0..100))
    MAX-ACCESS read-only
    STATUS current
    DESCRIPTION
        "Device RAM usage."
    ::= { esSysMgmt 5 }

sysMgmtFlashUsage OBJECT-TYPE
    SYNTAX DisplayString (SIZE (0..100))
    MAX-ACCESS read-only
    STATUS current
    DESCRIPTION
        "Device FLASH usage."
    ::= { esSysMgmt 6 }

sysMgmtVLANControl OBJECT-TYPE
    SYNTAX INTEGER
        {
        enable(1),
        disable(2)
        }
    MAX-ACCESS read-write
    STATUS current
    DESCRIPTION
        "Management vlan tag."
    ::= { esSysMgmt 13 }

sysMgmtVLANID OBJECT-TYPE
    SYNTAX INTEGER (1..4094)
    MAX-ACCESS read-write
    STATUS current
    DESCRIPTION
        "Management vlan id."
    ::= { esSysMgmt 14 }

sys8021QControl OBJECT-TYPE
    SYNTAX INTEGER
        {
        enable(1),
        disable(2)
        }
    MAX-ACCESS read-write
    STATUS current
    DESCRIPTION
        "System vlan status."
    ::= { esSysMgmt 15 }

devGatewayIPAddr OBJECT-TYPE
    SYNTAX IpAddress
    MAX-ACCESS read-write
    STATUS current
    DESCRIPTION
        "Gateway of device."
    ::= { esSysMgmt 17 }

adminPassword OBJECT-TYPE
    SYNTAX DisplayString
    MAX-ACCESS read-write
    STATUS current
    DESCRIPTION
        "Password of admin."
    ::= { esSysMgmt 18 }

--
-- esWireless
--

--
-- The sub tree for wlanRadioTable.
--

wlanRadioTable OBJECT-TYPE
    SYNTAX SEQUENCE OF WlanRadioEntry
    MAX-ACCESS not-accessible
    STATUS current
    DESCRIPTION
        "Description."
    ::= { esWireless 1 }

wlanRadioEntry OBJECT-TYPE
    SYNTAX WlanRadioEntry
    MAX-ACCESS not-accessible
    STATUS current
    DESCRIPTION
        "Description."
    INDEX { ifIndex }
    ::= { wlanRadioTable 1 }

WlanRadioEntry ::=
    SEQUENCE { 
        wlanCurrentChannel
            INTEGER,
        wlanStationCount
            INTEGER,
        wlanSupportedChannel
            DisplayString,
        wlanSupportedRate
            DisplayString,
        wlanMode
            INTEGER,
        wlanChannel
            INTEGER,
        wlanTxPower
            INTEGER,
        wlanRadioActivate
            INTEGER,
        wlanOperationMode
            INTEGER,
        wlanChannelWidth
            INTEGER,
        wlanAPSSIDProfileIndex
            INTEGER,
        wlanSTAAssocMCSThreshold
            INTEGER,
        wlanSTAAgingTime
            INTEGER
    }

wlanCurrentChannel OBJECT-TYPE
    SYNTAX INTEGER
    {
    auto(0),
    channel1(1),
    channel2(2),
    channel3(3),
    channel4(4),
    channel5(5),
    channel6(6),
    channel7(7),
    channel8(8),
    channel9(9),
    channel10(10),
    channel11(11),
    channel12(12),
    channel13(13)
    }
    MAX-ACCESS read-only
    STATUS current
    DESCRIPTION
        "Indicate current channel in use."
    ::= { wlanRadioEntry 1 }

wlanStationCount OBJECT-TYPE
    SYNTAX INTEGER (0..256)
    MAX-ACCESS read-only
    STATUS current
    DESCRIPTION
        "Indicate associated station numbers."
    ::= { wlanRadioEntry 2 }

wlanSupportedChannel OBJECT-TYPE
    SYNTAX DisplayString (SIZE (0..64))
    MAX-ACCESS read-only
    STATUS current
    DESCRIPTION
        "Indicate supported channel."
    ::= { wlanRadioEntry 3 }

wlanSupportedRate OBJECT-TYPE
    SYNTAX DisplayString
    MAX-ACCESS read-only
    STATUS current
    DESCRIPTION
        "Indicate supported rate."
    ::= { wlanRadioEntry 4 }

wlanMode OBJECT-TYPE
    SYNTAX INTEGER
        {
        dot11bg(0),
        dot11a(1),
        dot11bgn(8),
        dot11n(9),
        dot11an(10)
        }
    MAX-ACCESS read-write
    STATUS current
    DESCRIPTION
        "Indicate wireless mode."
    ::= { wlanRadioEntry 5 }

wlanChannel OBJECT-TYPE
    SYNTAX INTEGER (0..14)
    MAX-ACCESS read-write
    STATUS current
    DESCRIPTION
        "Indicate channel for wlan."
    ::= { wlanRadioEntry 6 }

wlanTxPower OBJECT-TYPE
    SYNTAX INTEGER
        {
        full(0),
        half(1),
        quarter(2),
        eighth(3),
        min(4)
        }
    MAX-ACCESS read-write
    STATUS current
    DESCRIPTION
        "Indicate transmit power for wlan."
    ::= { wlanRadioEntry 7 }

wlanRadioActivate OBJECT-TYPE
    SYNTAX INTEGER
        {
        disable(2),
        enable(1)
        }
    MAX-ACCESS read-write
    STATUS current
    DESCRIPTION
        "Indicate the wireless status."
    ::= { wlanRadioEntry 8 }

wlanOperationMode OBJECT-TYPE
    SYNTAX INTEGER
        {
        modeMultiSSID(0),
        modeWirelessClient(1),
        modeBridge(4),
        modeApRepeater(5),
        modeAccessPoint(8),
        modeRootAccessPoint(9)
        }
    MAX-ACCESS read-write
    STATUS current
    DESCRIPTION
        "Indicate operation mode for wlan."
    ::= { wlanRadioEntry 9 }

wlanChannelWidth OBJECT-TYPE
    SYNTAX INTEGER
        {
        mode20MHz(0),
        mode20or40MHz(1)
        }
    MAX-ACCESS read-write
    STATUS current
    DESCRIPTION
        "Indicate channel width for wlan."
    ::= { wlanRadioEntry 11 }

wlanAPSSIDProfileIndex OBJECT-TYPE
    SYNTAX INTEGER (1..8)
    MAX-ACCESS read-write
    STATUS current
    DESCRIPTION
        "Indicate ap ssid profile index."
    ::= { wlanRadioEntry 19 }

wlanSTAAssocMCSThreshold OBJECT-TYPE
    SYNTAX INTEGER (1..8)
    MAX-ACCESS read-write
    STATUS current
    DESCRIPTION
        "STA assocate MCS threshold."
    ::= { wlanRadioEntry 23 }

wlanSTAAgingTime OBJECT-TYPE
    SYNTAX INTEGER (1..8)
    MAX-ACCESS read-write
    STATUS current
    DESCRIPTION
        "STA aging time."
    ::= { wlanRadioEntry 24 }

--
-- The sub tree for wlanStationTable.
--

wlanStationTable OBJECT-TYPE
    SYNTAX SEQUENCE OF WlanStationEntry
    MAX-ACCESS not-accessible
    STATUS current
    DESCRIPTION
        "Description."
    ::= { esWireless 2 }
        
wlanStationEntry OBJECT-TYPE
    SYNTAX WlanStationEntry
    MAX-ACCESS not-accessible
    STATUS current
    DESCRIPTION
        "Description."
    INDEX { ifIndex }
    ::= { wlanStationTable 1 }

WlanStationEntry ::=
    SEQUENCE { 
        stationIndex
            INTEGER,
        stationMacAddress
            MacAddress,
        stationAssociatedTime
            DisplayString,
        stationSSID
            DisplayString,
        stationSignalRSSI
            INTEGER,
        stationIPAddr
            IpAddress,
        stationCurrentDataRate
            DisplayString,
        stationInOctet
            INTEGER,
        stationOutOctet
            INTEGER,
        stationTxPkt
            INTEGER,
        stationRxPkt
            INTEGER,
        stationSignalSNR
            INTEGER,
        stationAssociatedVAPMac
            MacAddress,
        stationDeviceInformation
            DisplayString,
        stationBand
            INTEGER,
        stationTransmitRate
            INTEGER,
        stationPacketErrorRatio
            INTEGER
    }

stationIndex OBJECT-TYPE
    SYNTAX INTEGER (0..256)
    MAX-ACCESS read-only
    STATUS current
    DESCRIPTION
        "Index of station table."
    ::= { wlanStationEntry 1 }

stationMacAddress OBJECT-TYPE
    SYNTAX MacAddress
    MAX-ACCESS read-only
    STATUS current
    DESCRIPTION
        "Associated MAC Address."
    ::= { wlanStationEntry 2 }

stationAssociatedTime OBJECT-TYPE
    SYNTAX DisplayString
    MAX-ACCESS read-only
    STATUS current
    DESCRIPTION
        "Associated time."
    ::= { wlanStationEntry 3 }

stationSSID OBJECT-TYPE
    SYNTAX DisplayString
    MAX-ACCESS read-only
    STATUS current
    DESCRIPTION
        "Associated ssid."
    ::= { wlanStationEntry 4 }

stationSignalRSSI OBJECT-TYPE
    SYNTAX INTEGER
    MAX-ACCESS read-only
    STATUS current
    DESCRIPTION
        "station signal RSSI"
    ::= { wlanStationEntry 5 }

stationIPAddr OBJECT-TYPE
    SYNTAX IpAddress
    MAX-ACCESS read-only
    STATUS current
    DESCRIPTION
        "IP address of the station."
    ::= { wlanStationEntry 6 }

stationCurrentDataRate OBJECT-TYPE
    SYNTAX DisplayString
    MAX-ACCESS read-only
    STATUS current
    DESCRIPTION
        "Current data rate of the station."
    ::= { wlanStationEntry 7 }

stationInOctet OBJECT-TYPE
    SYNTAX INTEGER
    MAX-ACCESS read-only
    STATUS current
    DESCRIPTION
        "Received bytes of the station."
    ::= { wlanStationEntry 8 }

stationOutOctet OBJECT-TYPE
    SYNTAX INTEGER
    MAX-ACCESS read-only
    STATUS current
    DESCRIPTION
        "Transmit bytes of the station."
    ::= { wlanStationEntry 9 }

stationTxPkt OBJECT-TYPE
    SYNTAX INTEGER
    MAX-ACCESS read-only
    STATUS current
    DESCRIPTION
        "Transmit packets number of the station."
    ::= { wlanStationEntry 10 }

stationRxPkt OBJECT-TYPE
    SYNTAX INTEGER
    MAX-ACCESS read-only
    STATUS current
    DESCRIPTION
        "Received packet number of the station."
    ::= { wlanStationEntry 11 }

stationSignalSNR OBJECT-TYPE
    SYNTAX INTEGER
    MAX-ACCESS read-only
    STATUS current
    DESCRIPTION
        "Station  signal SNR strength."
    ::= { wlanStationEntry 12 }

--
-- The sub tree for wlanStatisticTable.
--

wlanStatisticTable OBJECT-TYPE
    SYNTAX SEQUENCE OF WlanStatisticEntry
    MAX-ACCESS not-accessible
    STATUS current
    DESCRIPTION
        "Description."
    ::= { esWireless 3 }

wlanStatisticEntry OBJECT-TYPE
    SYNTAX WlanStatisticEntry
    MAX-ACCESS not-accessible
    STATUS current
    DESCRIPTION
        "Description."
    INDEX { ifIndex }
    ::= { wlanStatisticTable 1 }

WlanStatisticEntry ::=
    SEQUENCE { 
        dot11FailedCount
            Counter64,
        dot11RetryCount
            Counter64,
        dot11ACKFailureCount
            Counter64,
        dot11ReceivedFragmentCount
            Counter64,
        dot11TransmittedFrameCount
            Counter64,
        dot11ReceivedPktCount
            Counter64,
        dot11TransmittedPktCount
            Counter64
    }

dot11FailedCount OBJECT-TYPE
    SYNTAX Counter64
    MAX-ACCESS read-only
    STATUS current
    DESCRIPTION
        "This counter shall increment when an MSDU is not transmitted successfully due to the number of transmit attempts exceeding either the dot11ShortRetryLimit or dot11LongRetryLimit."
    ::= { wlanStatisticEntry 1 }

dot11RetryCount OBJECT-TYPE
    SYNTAX Counter64
    MAX-ACCESS read-only
    STATUS current
    DESCRIPTION
        "This counter shall increment when an MSDU is successfully transmitted after one or more retransmissions."
    ::= { wlanStatisticEntry 2 }

dot11ACKFailureCount OBJECT-TYPE
    SYNTAX Counter64
    MAX-ACCESS read-only
    STATUS current
    DESCRIPTION
        "This counter shall increment when an ACK is not received when expected."
    ::= { wlanStatisticEntry 3 }

dot11ReceivedFragmentCount OBJECT-TYPE
    SYNTAX Counter64
    MAX-ACCESS read-only
    STATUS current
    DESCRIPTION
        "This counter shall be incremented for each successfully received MPDU of type Data or Management."
    ::= { wlanStatisticEntry 4 }

dot11TransmittedFrameCount OBJECT-TYPE
    SYNTAX Counter64
    MAX-ACCESS read-only
    STATUS current
    DESCRIPTION
        "This counter shall increment for each successfully transmitted MSDU."
    ::= { wlanStatisticEntry 5 }

dot11ReceivedPktCount OBJECT-TYPE
    SYNTAX Counter64
    MAX-ACCESS read-only
    STATUS current
    DESCRIPTION
        "This counter shall increment for each successfully received packet."
    ::= { wlanStatisticEntry 6 }

dot11TransmittedPktCount OBJECT-TYPE
    SYNTAX Counter64
    MAX-ACCESS read-only
    STATUS current
    DESCRIPTION
        "This counter shall increment for each successfully transmitted packet."
    ::= { wlanStatisticEntry 7 }

--
-- The sub tree for wlanTraps.
--

wlanTraps OBJECT IDENTIFIER ::= { esWireless 4 }

wlanTrapsControl OBJECT IDENTIFIER ::= { wlanTraps 1 }

trapWirelessControl OBJECT-TYPE
    SYNTAX INTEGER
        {
        disabled(0),
        enabled(1)
        }
    MAX-ACCESS read-write
    STATUS current
    DESCRIPTION
        "Controls wireless group traps enable(1) or disable(0)."
    ::= { wlanTrapsControl 1 }

--
-- The sub tree for wlanChannelUsageTable.
--

wlanChannelUsageTable OBJECT-TYPE
    SYNTAX SEQUENCE OF WlanChannelUsageEntry
    MAX-ACCESS not-accessible
    STATUS current
    DESCRIPTION
        "Description."
    ::= { esWireless 5 }

wlanChannelUsageEntry OBJECT-TYPE
    SYNTAX WlanChannelUsageEntry
    MAX-ACCESS not-accessible
    STATUS current
    DESCRIPTION
        "Description."
    INDEX { ifIndex }
    ::= { wlanChannelUsageTable 1 }

WlanChannelUsageEntry ::=
    SEQUENCE { 
        wlanAPIndex
            INTEGER,
        wlanAPSSID
            DisplayString,
        wlanAPChannel
            INTEGER,
        wlanAPMacAddress
            MacAddress,
        wlanAPRadioMode
            INTEGER,
        wlanAPSignal
            INTEGER,
        wlanAPSecurity
            DisplayString
    }

wlanAPIndex OBJECT-TYPE
    SYNTAX INTEGER
    MAX-ACCESS read-only
    STATUS current
    DESCRIPTION
        "Index of row."
    ::= { wlanChannelUsageEntry 1 }

wlanAPSSID OBJECT-TYPE
    SYNTAX DisplayString
    MAX-ACCESS read-only
    STATUS current
    DESCRIPTION
        "SSID of AP."
    ::= { wlanChannelUsageEntry 2 }

wlanAPChannel OBJECT-TYPE
    SYNTAX INTEGER
    MAX-ACCESS read-only
    STATUS current
    DESCRIPTION
        "Channel of AP."
    ::= { wlanChannelUsageEntry 3 }

wlanAPMacAddress OBJECT-TYPE
    SYNTAX MacAddress
    MAX-ACCESS read-only
    STATUS current
    DESCRIPTION
        "MAC address of AP."
    ::= { wlanChannelUsageEntry 4 }

wlanAPRadioMode OBJECT-TYPE
    SYNTAX INTEGER
        {
        dot11bg(0),
        dot11a(1),
        dot11bgn(8),
        dot11n(9),
        dot11an(10)
        }
    MAX-ACCESS read-only
    STATUS current
    DESCRIPTION
        "Wireless mode of AP."
    ::= { wlanChannelUsageEntry 5 }

wlanAPSignal OBJECT-TYPE
    SYNTAX INTEGER
    MAX-ACCESS read-only
    STATUS current
    DESCRIPTION
        "Signal of AP."
    ::= { wlanChannelUsageEntry 6 }

wlanAPSecurity OBJECT-TYPE
    SYNTAX DisplayString
    MAX-ACCESS read-only
    STATUS current
    DESCRIPTION
        "Security of AP."
    ::= { wlanChannelUsageEntry 7 }

--
-- The sub tree for wlanMultiVAPTable.
--

wlanMultiVAPTable OBJECT-TYPE
    SYNTAX SEQUENCE OF WlanVAPEntry
    MAX-ACCESS not-accessible
    STATUS current
    DESCRIPTION
        "Description."
    ::= { esWireless 6 }

wlanVAPEntry OBJECT-TYPE
    SYNTAX WlanVAPEntry
    MAX-ACCESS not-accessible
    STATUS current
    DESCRIPTION
        "Description."
    INDEX { ifIndex }
    ::= { wlanMultiVAPTable 1 }

WlanVAPEntry ::=
    SEQUENCE { 
        wlanVAPActivate
            INTEGER,
        wlanVAPSSIDProfileIndex
            INTEGER,
        wlanVAPVLANTag
            INTEGER,
        wlanVAPVLANID
            INTEGER,
        wlanVAPVLANQoS
            INTEGER
    }

wlanVAPActivate OBJECT-TYPE
    SYNTAX INTEGER
        {
        disable(2),
        enable(1)
        }
    MAX-ACCESS read-write
    STATUS current
    DESCRIPTION
        "Indicate vap status."
    ::= { wlanVAPEntry 1 }

wlanVAPSSIDProfileIndex OBJECT-TYPE
    SYNTAX INTEGER (1..8)
    MAX-ACCESS read-write
    STATUS current
    DESCRIPTION
        "Indicate vap ssid profile index."
    ::= { wlanVAPEntry 2 }

wlanVAPVLANTag OBJECT-TYPE
    SYNTAX INTEGER
        {
        disable(2),
        enable(1)
        }
    MAX-ACCESS read-write
    STATUS current
    DESCRIPTION
        "Indicate vap vlan status."
    ::= { wlanVAPEntry 3 }

wlanVAPVLANID OBJECT-TYPE
    SYNTAX INTEGER (1..4094)
    MAX-ACCESS read-write
    STATUS current
    DESCRIPTION
        "Indicate vap vlan id."
    ::= { wlanVAPEntry 4 }

wlanVAPVLANQoS OBJECT-TYPE
    SYNTAX INTEGER (1..8)
    MAX-ACCESS read-write
    STATUS current
    DESCRIPTION
        "Indicate vap vlan qos."
    ::= { wlanVAPEntry 5 }

--
-- The sub tree for wlanMSSIDProfileControlTable.
--

wlanMSSIDProfileControlTable OBJECT-TYPE
    SYNTAX SEQUENCE OF WlanMSSIDProfileControlEntry
    MAX-ACCESS not-accessible
    STATUS current
    DESCRIPTION
        "Description."
    ::= { esWireless 7 }

wlanMSSIDProfileControlEntry OBJECT-TYPE
    SYNTAX WlanMSSIDProfileControlEntry
    MAX-ACCESS not-accessible
    STATUS current
    DESCRIPTION
        "Description."
    INDEX { ifIndex }
    ::= { wlanMSSIDProfileControlTable 1 }

WlanMSSIDProfileControlEntry ::=
    SEQUENCE { 
        wlanSSIDProfileName
            DisplayString,
        wlanSSID
            DisplayString,
        wlanSSIDProfileSecIndex
            INTEGER,
        wlanSSIDProfileRadiusIndex
            INTEGER,
        wlanSSIDProfileMACFilterIndex
            INTEGER,
        wlanSSIDProfileQoSIndex
            INTEGER,
        wlanSSIDProfileAllowSTACount
            INTEGER,
        wlanSSIDProfileHiddenSSID
            INTEGER,
        wlanSSIDProfileIntraBSSBlock
            INTEGER
    }

wlanSSIDProfileName OBJECT-TYPE
    SYNTAX DisplayString
    MAX-ACCESS read-write
    STATUS current
    DESCRIPTION
        "Indicate ssid profile name in ssid profile."
    ::= { wlanMSSIDProfileControlEntry 1 }

wlanSSID OBJECT-TYPE
    SYNTAX DisplayString
    MAX-ACCESS read-write
    STATUS current
    DESCRIPTION
        "Indicate wlan ssid in ssid profile."
    ::= { wlanMSSIDProfileControlEntry 2 }

wlanSSIDProfileSecIndex OBJECT-TYPE
    SYNTAX INTEGER (1..8)
    MAX-ACCESS read-write
    STATUS current
    DESCRIPTION
        "Indicate security profile index in ssid profile."
    ::= { wlanMSSIDProfileControlEntry 3 }

wlanSSIDProfileRadiusIndex OBJECT-TYPE
    SYNTAX INTEGER (1..4)
    MAX-ACCESS read-write
    STATUS current
    DESCRIPTION
        "Indicate radius profile index in ssid profile."
    ::= { wlanMSSIDProfileControlEntry 4 }

wlanSSIDProfileMACFilterIndex OBJECT-TYPE
    SYNTAX INTEGER (1..8)
    MAX-ACCESS read-write
    STATUS current
    DESCRIPTION
        "Indicate mac filter profile index in ssid profile."
    ::= { wlanMSSIDProfileControlEntry 5 }

wlanSSIDProfileQoSIndex OBJECT-TYPE
    SYNTAX INTEGER
        {
        bestEffort(0),
        backGround(1),
        video(2),
        voice(3),
        wmm(4),
        none(255)
        }
    MAX-ACCESS read-write
    STATUS current
    DESCRIPTION
        "Indicate qos mode in ssid profile."
    ::= { wlanMSSIDProfileControlEntry 6 }

wlanSSIDProfileAllowSTACount OBJECT-TYPE
    SYNTAX INTEGER (0..64)
    MAX-ACCESS read-write
    STATUS current
    DESCRIPTION
        "Indicate allow station numbers in ssid profile."
    ::= { wlanMSSIDProfileControlEntry 7 }

wlanSSIDProfileHiddenSSID OBJECT-TYPE
    SYNTAX INTEGER
        {
        hidden(1), 
        broadcast(0)
        }
    MAX-ACCESS read-write
    STATUS current
    DESCRIPTION
        "Indicate ssid broadcast status in ssid profile."
    ::= { wlanMSSIDProfileControlEntry 8 }

wlanSSIDProfileIntraBSSBlock OBJECT-TYPE
    SYNTAX INTEGER
        {
        disable(2),
        enable(1)
        }
    MAX-ACCESS read-write
    STATUS current
    DESCRIPTION
        "Indicate Intra-BSS traffic blocking status in ssid profile."
    ::= { wlanMSSIDProfileControlEntry 9 }

--
-- The sub tree for wlanRadiusProfileControlTable.
--

wlanSecurityProfileControlTable OBJECT-TYPE
    SYNTAX SEQUENCE OF WlanSecurityProfileControlEntry
    MAX-ACCESS not-accessible
    STATUS current
    DESCRIPTION
        "Description."
    ::= { esWireless 8 }

wlanSecurityProfileControlEntry OBJECT-TYPE
    SYNTAX WlanSecurityProfileControlEntry
    MAX-ACCESS not-accessible
    STATUS current
    DESCRIPTION
        "Description."
    INDEX { ifIndex }
    ::= { wlanSecurityProfileControlTable 1 }

WlanSecurityProfileControlEntry ::=
    SEQUENCE { 
        wlanSecMode
            INTEGER,
        wlanWPAGroupKeyRekey
            INTEGER,
        wlanWPAPreSharedKey
            DisplayString,
        wlanWEPEncryption
            INTEGER,
        wlanWEPKeyIndex
            INTEGER,
        wlanWEPKey1
            DisplayString,
        wlanWEPKey2
            DisplayString,
        wlanWEPKey3
            DisplayString,
        wlanWEPKey4
            DisplayString,
        wlanWEPAuthMethod
            INTEGER,
        wlanSecProfileName
            DisplayString,
        wlan8021xReauthTime
            INTEGER,
        wlan8021xGroupKeyRekeyControl
            INTEGER
    }

wlanSecMode OBJECT-TYPE
    SYNTAX INTEGER
        {
        modeOpenSystem(0),
        modeSharedKey(1),
        mode8021x(2),
        modeWpaWith8021x(4),
        modeWpa2With8021x(8),
        modeWpaWpa2With8021x(12),
        modeWpaPsk(16),
        modeWpa2Psk(32),
        modeWpaWpa2Psk(48)
        }
    MAX-ACCESS read-write
    STATUS current
    DESCRIPTION
        "Indicate wireless security mode."
    ::= { wlanSecurityProfileControlEntry 1 }

wlanWPAGroupKeyRekey OBJECT-TYPE
    SYNTAX INTEGER (100..3600)
    MAX-ACCESS read-write
    STATUS current
    DESCRIPTION
        "Indicate wlan wpa group rekey time."
    ::= { wlanSecurityProfileControlEntry 2 }

wlanWPAPreSharedKey OBJECT-TYPE
    SYNTAX DisplayString
    MAX-ACCESS read-write
    STATUS current
    DESCRIPTION
        "Indicate wpa pre shared key."
    ::= { wlanSecurityProfileControlEntry 3 }

wlanWEPEncryption OBJECT-TYPE
    SYNTAX INTEGER
        {
        disable(0),
        mode64hex(40),
        mode128hex(104),
        mode152hex(128),
        dynamic(250)
        }
    MAX-ACCESS read-write
    STATUS current
    DESCRIPTION
        "Indicate wep key type."
    ::= { wlanSecurityProfileControlEntry 4 }

wlanWEPKeyIndex OBJECT-TYPE
    SYNTAX INTEGER
        {
        key1(1),
        key2(2),
        key3(3),
        key4(4)
        }
    MAX-ACCESS read-write
    STATUS current
    DESCRIPTION
        "Indicate wep key default index."
    ::= { wlanSecurityProfileControlEntry 6 }

wlanWEPKey1 OBJECT-TYPE
    SYNTAX DisplayString
    MAX-ACCESS read-write
    STATUS current
    DESCRIPTION
        "Indicate wep key1."
    ::= { wlanSecurityProfileControlEntry 7 }

wlanWEPKey2 OBJECT-TYPE
    SYNTAX DisplayString
    MAX-ACCESS read-write
    STATUS current
    DESCRIPTION
        "Indicate wep key2."
    ::= { wlanSecurityProfileControlEntry 8 }

wlanWEPKey3 OBJECT-TYPE
    SYNTAX DisplayString
    MAX-ACCESS read-write
    STATUS current
    DESCRIPTION
        "Indicate wep key3."
    ::= { wlanSecurityProfileControlEntry 9 }

wlanWEPKey4 OBJECT-TYPE
    SYNTAX DisplayString
    MAX-ACCESS read-write
    STATUS current
    DESCRIPTION
        "Indicate wep key4."
    ::= { wlanSecurityProfileControlEntry 10 }

wlanWEPAuthMethod OBJECT-TYPE
    SYNTAX INTEGER
        {
        tls(13),
        leap(17),
        ttls(21),
        peap(25)
        }
    MAX-ACCESS read-write
    STATUS current
    DESCRIPTION
        "Auth method of device."
    ::= { wlanSecurityProfileControlEntry 11 }

wlanSecProfileName OBJECT-TYPE
    SYNTAX DisplayString
    MAX-ACCESS read-write
    STATUS current
    DESCRIPTION
        "Indicate security profile name."
    ::= { wlanSecurityProfileControlEntry 12 }

wlan8021xReauthTime OBJECT-TYPE
    SYNTAX INTEGER (100..3600)
    MAX-ACCESS read-write
    STATUS current
    DESCRIPTION
        "Indicate 802.1x reauthen time."
    ::= { wlanSecurityProfileControlEntry 13 }

wlan8021xGroupKeyRekeyControl OBJECT-TYPE
    SYNTAX INTEGER
        {
        disable(2),
        enable(1)
        }
    MAX-ACCESS read-write
    STATUS current
    DESCRIPTION
        "Indicate 802.1x group key rekey status."
    ::= { wlanSecurityProfileControlEntry 14 }

--
-- The sub tree for wlanRadiusProfileControlTable.
--

wlanRadiusProfileControlTable OBJECT-TYPE
    SYNTAX SEQUENCE OF WlanRadiusProfileControlEntry
    MAX-ACCESS not-accessible
    STATUS current
    DESCRIPTION
        "Description."
    ::= { esWireless 9 }

wlanRadiusProfileControlEntry OBJECT-TYPE
    SYNTAX WlanRadiusProfileControlEntry
    MAX-ACCESS not-accessible
    STATUS current
    DESCRIPTION
        "Description."
    INDEX { ifIndex }
    ::= { wlanRadiusProfileControlTable 1 }

WlanRadiusProfileControlEntry ::=
    SEQUENCE { 
        wlanRadiusProfileName
            DisplayString,
        wlanRadiusNASIdentifier
            DisplayString,
        wlanRadiusPrimaryAcitvate
            INTEGER,
        wlanRadiusPriSrvIPAddr
            IpAddress,
        wlanRadiusPriSrvPort
            Integer32,
        wlanRadiusPriShareSecret
            DisplayString,
        wlanRadiusPriACCAcitvate
            INTEGER,
        wlanRadiusPriACCSrvIPAddr
            IpAddress,
        wlanRadiusPriACCSrvPort
            Integer32,
        wlanRadiusPriACCShareSecret
            DisplayString,
        wlanRadiusBUAcitvate
            INTEGER,
        wlanRadiusBUSrvIPAddr
            IpAddress,
        wlanRadiusBUSrvPort
            Integer32,
        wlanRadiusBUShareSecret
            DisplayString,
        wlanRadiusBUACCAcitvate
            INTEGER,
        wlanRadiusBUACCSrvIPAddr
            IpAddress,
        wlanRadiusBUACCSrvPort
            Integer32,
        wlanRadiusBUACCShareSecret
            DisplayString
    }

wlanRadiusProfileName OBJECT-TYPE
    SYNTAX DisplayString
    MAX-ACCESS read-write
    STATUS current
    DESCRIPTION
        "Indicate radius profile name."
    ::= { wlanRadiusProfileControlEntry 1 }

wlanRadiusNASIdentifier OBJECT-TYPE
    SYNTAX DisplayString
    MAX-ACCESS read-write
    STATUS current
    DESCRIPTION
        "Indicate NAS identifier."
    ::= { wlanRadiusProfileControlEntry 2 }

wlanRadiusPrimaryAcitvate OBJECT-TYPE
    SYNTAX INTEGER
        {
        disable(2),
        enable(1)
        }
    MAX-ACCESS read-write
    STATUS current
    DESCRIPTION
        "Indicate primary radius authentication server status."
    ::= { wlanRadiusProfileControlEntry 3 }

wlanRadiusPriSrvIPAddr OBJECT-TYPE
    SYNTAX IpAddress
    MAX-ACCESS read-write
    STATUS current
    DESCRIPTION
        "Indicate primary radius authentication server ip address."
    ::= { wlanRadiusProfileControlEntry 4 }

wlanRadiusPriSrvPort OBJECT-TYPE
    SYNTAX Integer32
    MAX-ACCESS read-write
    STATUS current
    DESCRIPTION
        "Indicate primary radius authentication server port."
    ::= { wlanRadiusProfileControlEntry 5 }

wlanRadiusPriShareSecret OBJECT-TYPE
    SYNTAX DisplayString
    MAX-ACCESS read-write
    STATUS current
    DESCRIPTION
        "Indicate primary radius authentication server shared secret."
    ::= { wlanRadiusProfileControlEntry 6 }

wlanRadiusPriACCAcitvate OBJECT-TYPE
    SYNTAX INTEGER
        {
        disable(2),
        enable(1)
        }
    MAX-ACCESS read-write
    STATUS current
    DESCRIPTION
        "Indicate primary radius accounting server status."
    ::= { wlanRadiusProfileControlEntry 7 }

wlanRadiusPriACCSrvIPAddr OBJECT-TYPE
    SYNTAX IpAddress
    MAX-ACCESS read-write
    STATUS current
    DESCRIPTION
        "Indicate primary radius accounting server ip address."
    ::= { wlanRadiusProfileControlEntry 8 }

wlanRadiusPriACCSrvPort OBJECT-TYPE
    SYNTAX Integer32
    MAX-ACCESS read-write
    STATUS current
    DESCRIPTION
        "Indicate primary radius accounting server port."
    ::= { wlanRadiusProfileControlEntry 9 }

wlanRadiusPriACCShareSecret OBJECT-TYPE
    SYNTAX DisplayString
    MAX-ACCESS read-write
    STATUS current
    DESCRIPTION
        "Indicate primary radius accounting server shared secret."
    ::= { wlanRadiusProfileControlEntry 10 }

wlanRadiusBUAcitvate OBJECT-TYPE
    SYNTAX INTEGER
        {
        disable(2),
        enable(1)
        }
    MAX-ACCESS read-write
    STATUS current
    DESCRIPTION
        "Indicate backup radius authentication server status."
    ::= { wlanRadiusProfileControlEntry 11 }

wlanRadiusBUSrvIPAddr OBJECT-TYPE
    SYNTAX IpAddress
    MAX-ACCESS read-write
    STATUS current
    DESCRIPTION
        "Indicate backup radius authentication server ip address."
    ::= { wlanRadiusProfileControlEntry 12 }

wlanRadiusBUSrvPort OBJECT-TYPE
    SYNTAX Integer32
    MAX-ACCESS read-write
    STATUS current
    DESCRIPTION
        "Indicate backup radius authentication server port."
    ::= { wlanRadiusProfileControlEntry 13 }

wlanRadiusBUShareSecret OBJECT-TYPE
    SYNTAX DisplayString
    MAX-ACCESS read-write
    STATUS current
    DESCRIPTION
        "Indicate backup radius authentication server shared secret."
    ::= { wlanRadiusProfileControlEntry 14 }

wlanRadiusBUACCAcitvate OBJECT-TYPE
    SYNTAX INTEGER
        {
        disable(2),
        enable(1)
        }
    MAX-ACCESS read-write
    STATUS current
    DESCRIPTION
        "Indicate backup radius accounting server status."
    ::= { wlanRadiusProfileControlEntry 15 }

wlanRadiusBUACCSrvIPAddr OBJECT-TYPE
    SYNTAX IpAddress
    MAX-ACCESS read-write
    STATUS current
    DESCRIPTION
        "Indicate backup radius accounting server ip address."
    ::= { wlanRadiusProfileControlEntry 16 }

wlanRadiusBUACCSrvPort OBJECT-TYPE
    SYNTAX Integer32
    MAX-ACCESS read-write
    STATUS current
    DESCRIPTION
        "Indicate backup radius accounting server port."
    ::= { wlanRadiusProfileControlEntry 17 }

wlanRadiusBUACCShareSecret OBJECT-TYPE
    SYNTAX DisplayString
    MAX-ACCESS read-write
    STATUS current
    DESCRIPTION
        "Indicate backup radius accounting server shared secret."
    ::= { wlanRadiusProfileControlEntry 18 }

--
-- The sub tree for wlanMACFilterProfileControlTable.
--

wlanMACFilterProfileControlTable OBJECT-TYPE
    SYNTAX SEQUENCE OF WlanMACFilterProfileControlEntry
    MAX-ACCESS not-accessible
    STATUS current
    DESCRIPTION
        "Table of MAC filter profile."
    ::= { esWireless 10 }

wlanMACFilterProfileControlEntry OBJECT-TYPE
    SYNTAX WlanMACFilterProfileControlEntry
    MAX-ACCESS not-accessible
    STATUS current
    DESCRIPTION
        "Entry of MAC filter profile."
    INDEX { ifIndex }
    ::= { wlanMACFilterProfileControlTable 1 }

WlanMACFilterProfileControlEntry ::=
    SEQUENCE { 
        wlanMACFilterProfileName
            DisplayString,
        wlanMACFilterACLMode
            INTEGER
    }

wlanMACFilterProfileName OBJECT-TYPE
    SYNTAX DisplayString
    MAX-ACCESS read-write
    STATUS current
    DESCRIPTION
        "Indicate mac filter profile name."
    ::= { wlanMACFilterProfileControlEntry 1 }

wlanMACFilterACLMode OBJECT-TYPE
    SYNTAX INTEGER
        {
        disable(0),
        allow(1),
        deny(2)
        }
    MAX-ACCESS read-write
    STATUS current
    DESCRIPTION
        "Indicate acl mode in mac filter profile."
    ::= { wlanMACFilterProfileControlEntry 2 }


END
