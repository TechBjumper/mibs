VERILINK-ENTERPRISE-NCMIDCSU-MIB

        -- set up MIB-wide defaults
        -- all functions can use %n for object name and
        -- %t for object type, %p for parent name,
        -- %d for name of default-bearing node and %% for %
        --DEFAULT test-function    it-exists
        --DEFAULT    set-function    set-%n
        --DEFAULT    get-function    get-%n
        --DEFAULT    next-function    std-next
        --DEFAULT cookie        (char *)NULL

          DEFINITIONS ::= BEGIN

     IMPORTS
              DisplayString
                     FROM RFC1213-MIB
		Gauge
                     FROM RFC1155-SMI

             OBJECT-TYPE
                     FROM RFC-1212
	     ncm-idcsu
		     FROM 
             VERILINK-ENTERPRISE-NCMALARM-MIB;

             
 
     --  This MIB module uses the extended OBJECT-TYPE macro as
     --  defined in RFC 1212.
     --  This MIB module uses the TRAP-TYPE macro as
     --  defined in RFC 1215.
















	 -- The ncmidcsu configuration table
     
        ncmidcsuConfigTable OBJECT-TYPE
        SYNTAX SEQUENCE OF  NcmidcsuConfigEntry
        ACCESS not-accessible
        STATUS mandatory
	DESCRIPTION
               "The ncm idcsu configuration table."

	--DEFAULT test-function idcsu-test
	--DEFAULT next-function idcsu-next
	

                  ::= { ncm-idcsu 10000 }


        ncmidcsuConfigEntry OBJECT-TYPE
        SYNTAX NcmidcsuConfigEntry
        ACCESS not-accessible
        STATUS mandatory
        DESCRIPTION
               "An entry in the ncmidcsu configuration table."
        INDEX   { ncmidcsucfgNIDIndex, ncmidcsuLineIndex }
        ::= { ncmidcsuConfigTable 1 }


	 NcmidcsuConfigEntry ::= 
        SEQUENCE {
             ncmidcsucfgNIDIndex
		INTEGER,
             ncmidcsuLineIndex
                 INTEGER,       
             ncmidcsuNetLineBuildOut 
                 INTEGER,
             ncmidcsuNetworkKeepAlive
                 INTEGER,
             ncmidcsuExcessiveError
                 INTEGER,
             ncmidcsuOutOfFrame
                 INTEGER,       
             ncmidcsuFormat
                 INTEGER,
             ncmidcsuNetDensityEnforcement
                 INTEGER,
	     ncmidcsuNetLossOfSignal
                 INTEGER,
	     ncmidcsuJitterBuf
                INTEGER,
             ncmidcsuTestSigCfgEnable
                INTEGER,
             ncmidcsuTestSigCfgFrameSignal
                INTEGER,
             ncmidcsuCfgRptSendPRM
                INTEGER,
             ncmidcsuCfgRptPollFarEnd
                INTEGER,
             ncmidcsuCfgRptDataLinkUnsolicit
                INTEGER,
             ncmidcsuCfgRptAlmReporting
                INTEGER,
             ncmidcsuCfgRptPRMType
                INTEGER,
             ncmidcsuCfgCodeRegenCRC
                INTEGER,
             ncmidcsuCfgCodeXYellowAlarm
                INTEGER,
             ncmidcsuCfgCodeEQFIFO
                INTEGER,
             ncmidcsuCfgCodeNETFIFO
                INTEGER,
             ncmidcsuCfgCodeTranMode
                INTEGER,
             ncmidcsuCfgCodeSend1sLnkIdle
                INTEGER,
             ncmidcsuCfgAlmSelfTest
                INTEGER,
             ncmidcsuCfgAlmEnableTestState
                INTEGER,
             ncmidcsuCfgAlmUnframedMode
                INTEGER,
             ncmidcsuCfgAlmOnEqLoop
                INTEGER,
             ncmidcsuCfgAlmOnNetLoop
                INTEGER,
             ncmidcsuCfgAlmOnPowerUpLoop
		INTEGER,
	     ncmidcsuCfgLoopRespLLB
                INTEGER,
             ncmidcsuCfgLoopRespPLB
                INTEGER,
             ncmidcsuCfgLoopRespELB
                INTEGER,
             ncmidcsuCfgLoopRespRLB
                INTEGER,
             ncmidcsuCfgLoopRespLLBTONE
                INTEGER,
             ncmidcsuCfgLoopRespPLBTONE
                INTEGER,
             ncmidcsuCfgSendReceiveInBandCode
                INTEGER

	     }

        ncmidcsucfgNIDIndex OBJECT-TYPE
          SYNTAX  INTEGER (1..'7fffffff'h)
          ACCESS  read-only
          STATUS  mandatory
          DESCRIPTION
		"This variable indicates the node id value of the node."
        ::= { ncmidcsuConfigEntry 1 }

	ncmidcsuLineIndex OBJECT-TYPE
        SYNTAX  INTEGER 
        ACCESS  read-only
        STATUS  mandatory
DESCRIPTION ""
        --DEFAULT get-function get-ncmcsuMainLineIndex

        ::= { ncmidcsuConfigEntry 2 }

	ncmidcsuNetLineBuildOut OBJECT-TYPE
	SYNTAX INTEGER
			{
			db-Zero(1),
			db-Seven-point-five(2),
			db-Fifteen(3)
			}
        ACCESS read-write
        STATUS mandatory
        DESCRIPTION
               "The ncmidcsu net line build out."  
        ::= { ncmidcsuConfigEntry 3 }


	ncmidcsuNetworkKeepAlive OBJECT-TYPE
        SYNTAX INTEGER {

                       none(1),
                       loop(2),
                       ais(3),
                       framed-all-ones(4) 

               }
        ACCESS read-write
        STATUS mandatory
        DESCRIPTION
               "The ncmidcsu  network keep alive varaible ."
               
        ::= { ncmidcsuConfigEntry 4 }

	ncmidcsuExcessiveError OBJECT-TYPE
        SYNTAX INTEGER {

                        signal(1),
                        ais(2)

                          }
        ACCESS read-write
        STATUS mandatory
        DESCRIPTION
               "The Net/Eq has excessive errors."

        ::= { ncmidcsuConfigEntry 5 }

	ncmidcsuOutOfFrame   OBJECT-TYPE
        SYNTAX INTEGER {

                       signal(1),
                       ais(2) 

               }
        ACCESS read-write
        STATUS mandatory
        DESCRIPTION
               "The ncmidcsu Eq is out of frame (OOF)."

        ::= { ncmidcsuConfigEntry 6 }

	ncmidcsuFormat OBJECT-TYPE
        SYNTAX INTEGER {

                       unframed(1),         
                       sf(2),
                       esf(3),
                       zbtsi(4)         

               }
        ACCESS read-write
        STATUS mandatory
        DESCRIPTION
               "The ncmidcsu Net/Eq format."

        ::= { ncmidcsuConfigEntry 7 }


	ncmidcsuNetDensityEnforcement OBJECT-TYPE
        SYNTAX INTEGER {
                        none(1),
                        fcc-part-68(2),
                        pub-62411(3),
                        eighty-zeroes(4),
                        fifteen-zeroes(5)

                        }
         ACCESS read-write
         STATUS mandatory
         DESCRIPTION
               "The ncmidcsu net density enforcement."
         ::= { ncmidcsuConfigEntry 8 }


       
	 	
	ncmidcsuNetLossOfSignal OBJECT-TYPE
        SYNTAX INTEGER 
        ACCESS read-only
        STATUS mandatory
        DESCRIPTION
               "The ncmidcsu Net/Eq uas interval."
        ::= { ncmidcsuConfigEntry 9 }


	
	 ncmidcsuJitterBuf OBJECT-TYPE
         SYNTAX INTEGER {
                        eq-Net-16-16(1),
                        eq-Net-40-16(2),
                        eq-Net-16-40(3),
                        eq-Net-40-40(4)

               } 
        ACCESS read-write
        STATUS mandatory
        DESCRIPTION
               "The ncmidcsu Net/Eq Jitter buffer in bits."
        ::= { ncmidcsuConfigEntry 10 }


        ncmidcsuTestSigCfgEnable    OBJECT-TYPE
        SYNTAX INTEGER  {
                        no(1),
                        yes(2)
        }
        ACCESS read-write
        STATUS mandatory
        DESCRIPTION
               "bit 1 of MSGOUT+47 for read or of MSGIN+47 for write is test signal enable
                in this test signal configuration message."
        ::= { ncmidcsuConfigEntry 11 }


        ncmidcsuTestSigCfgFrameSignal  OBJECT-TYPE
        SYNTAX INTEGER  {
                        no(1),
                        yes(2)
        }
        ACCESS read-write
        STATUS mandatory
        DESCRIPTION
               "bit 7 of MSGOUT+47 for read or of MSGIN+47 for write is frame test signal
                in this test signal configuration message."
        ::= { ncmidcsuConfigEntry 12 }


         
 
        ncmidcsuCfgRptSendPRM        OBJECT-TYPE
        SYNTAX INTEGER  {
                        no(1),
                        yes(2)
        }
        ACCESS read-write
        STATUS mandatory
        DESCRIPTION
               "bit 0 of MSGOUT+52 for read or MSGIN+52 for write is send prm
                in this configure report message."
        ::= { ncmidcsuConfigEntry 13 }

	 ncmidcsuCfgRptPollFarEnd     OBJECT-TYPE
        SYNTAX INTEGER  {
                        no(1),
                        yes(2)
        }
        ACCESS read-write
        STATUS mandatory
        DESCRIPTION
               "bit 1 of MSGOUT+52 for read or MSGIN+52 for write is poll far end
                in this configure report message."
        ::= { ncmidcsuConfigEntry 14 }
 
 
        ncmidcsuCfgRptDataLinkUnsolicit   OBJECT-TYPE
        SYNTAX INTEGER  {
                        no(1),
                        yes(2)
        }
        ACCESS read-write
        STATUS mandatory
        DESCRIPTION
               "bit 2 of MSGOUT+52 for read or MSGIN+52 for write is data link unsolicited
report
                in this configure report message."
        ::= { ncmidcsuConfigEntry 15 }
 
 
        ncmidcsuCfgRptAlmReporting    OBJECT-TYPE
        SYNTAX INTEGER  {
                        no(1),
                        yes(2)
        }
        ACCESS read-write
        STATUS mandatory
        DESCRIPTION
               "bit 3 of MSGOUT+52 for read or MSGIN+52 for write is alarm reporting
                in this configure report message."
        ::= { ncmidcsuConfigEntry 16 }
 
 
        ncmidcsuCfgRptPRMType        OBJECT-TYPE
        SYNTAX INTEGER  {
                        tELCO(1),
                        uSER(2)
        }
        ACCESS read-write
        STATUS mandatory
        DESCRIPTION
               "bit 4,5 of MSGOUT+52 for read or of MSGIN+52 for write is PRM type
                in this configure report message."
        ::= { ncmidcsuConfigEntry 17 }


	 ncmidcsuCfgCodeRegenCRC      OBJECT-TYPE
        SYNTAX INTEGER  {
                        pass(1),
                        net-to-Eq(2),
                        eq-to-Net(3),
                        both(4)
        }
        ACCESS read-write
        STATUS mandatory
        DESCRIPTION
               "bit 0,1 of MSGOUT+53 for read or MSGIN+53 for write is regenerate
                crc from net to dte or eq to net in this configure coding message. "
        ::= { ncmidcsuConfigEntry 18 }
 
 
        ncmidcsuCfgCodeXYellowAlarm  OBJECT-TYPE
        SYNTAX INTEGER  {
                        off(1),
                        net-to-Eq(2),
                        eq-to-Net(3),
                        both(4)
        }
        ACCESS read-write
        STATUS mandatory
        DESCRIPTION
               "bit 2,3 of MSGOUT+53 for read or MSGIN+53 for write is transcode yellow
                alarm from net to dte or eq to net in this configure coding message. "
        ::= { ncmidcsuConfigEntry 19 }
         
 
        ncmidcsuCfgCodeEQFIFO        OBJECT-TYPE
        SYNTAX INTEGER  {
                        fifteen-bits(1),
                        forty-bits(2)
        }
        ACCESS read-write
        STATUS mandatory
        DESCRIPTION
               "bit 4 of MSGOUT+53 for read or MSGIN+53 for write is eq fifo
                in this configure coding message. "
        ::= { ncmidcsuConfigEntry 20 }
         
 
        ncmidcsuCfgCodeNETFIFO        OBJECT-TYPE
        SYNTAX INTEGER  {
                        fifteen-bits(1),
                        forty-bits(2)
        }
        ACCESS read-write
        STATUS mandatory
        DESCRIPTION
               "bit 5 of MSGOUT+53 for read or MSGIN+53 for write is net fifo
                in this configure coding message. "
        ::= { ncmidcsuConfigEntry 21 }


	ncmidcsuCfgCodeTranMode      OBJECT-TYPE
        SYNTAX INTEGER  {
                        no(1),
                        yes(2)
        }
        ACCESS read-write
        STATUS mandatory
        DESCRIPTION
               "bit 6 of MSGOUT+53 for read or MSGIN+53 for write is transparent
                mode in this configure report message."
        ::= { ncmidcsuConfigEntry 22 }
 
 
        ncmidcsuCfgCodeSend1sLnkIdle   OBJECT-TYPE
        SYNTAX INTEGER  {
                        no(1),
                        yes(2)
        }
        ACCESS read-write
        STATUS mandatory
        DESCRIPTION
               "bit 7 of MSGOUT+53 for read or MSGIN+53 for write is send ones
                data link idle code in this configure report message."
        ::= { ncmidcsuConfigEntry 23 }
         
 
        ncmidcsuCfgAlmSelfTest       OBJECT-TYPE
        SYNTAX INTEGER  {
                        no(1),
                        yes(2)
        }
        ACCESS read-write
        STATUS mandatory
        DESCRIPTION
               "bit 0 of MSGOUT+54 for read or MSGIN+54 for write is enable
                power up self test in this configure alarm message."
        ::= { ncmidcsuConfigEntry 24 }
         
 
        ncmidcsuCfgAlmEnableTestState   OBJECT-TYPE
        SYNTAX INTEGER  {
                        no(1),
                        yes(2)
        }
        ACCESS read-write
        STATUS mandatory
        DESCRIPTION
               "bit 1 of MSGOUT+54 for read or MSGIN+54 for write is enable
                alarms in test state in this configure alarm message."
        ::= { ncmidcsuConfigEntry 25 }
         
 
        ncmidcsuCfgAlmUnframedMode   OBJECT-TYPE
        SYNTAX INTEGER  {
                        no(1),
                        yes(2)
        }
        ACCESS read-write
        STATUS mandatory
        DESCRIPTION
               "bit 2 of MSGOUT+54 for read or MSGIN+54 for write is
                alarms in unframe mode in this configure alarm message."
        ::= { ncmidcsuConfigEntry 26 }


	ncmidcsuCfgAlmOnEqLoop       OBJECT-TYPE
        SYNTAX INTEGER  {
                        no(1),
                        yes(2)
        }
        ACCESS read-write
        STATUS mandatory
        DESCRIPTION
               "bit 3 of MSGOUT+54 for read or MSGIN+54 for write is alarm
                on eq loop loop in this configure alarm message."
        ::= { ncmidcsuConfigEntry 27 }
         
 
        ncmidcsuCfgAlmOnNetLoop       OBJECT-TYPE
        SYNTAX INTEGER  {
                        no(1),
                        yes(2)
        }
        ACCESS read-write
        STATUS mandatory
        DESCRIPTION
               "bit 4 of MSGOUT+54 for read or MSGIN+54 for write is alarm
                on net loop in this configure alarm message."
        ::= { ncmidcsuConfigEntry 28 }
         
 
        ncmidcsuCfgAlmOnPowerUpLoop       OBJECT-TYPE
        SYNTAX INTEGER  {
                        no(1),
                        yes(2)
        }
        ACCESS read-write
        STATUS mandatory
        DESCRIPTION
               "bit 5 of MSGOUT+54 for read or MSGIN+54 for write is alarm
                power up loop in this configure alarm message."
        ::= { ncmidcsuConfigEntry 29 }



	ncmidcsuCfgLoopRespLLB      OBJECT-TYPE
        SYNTAX INTEGER  {
                        no(1),
                        yes(2)
        }
        ACCESS read-write
        STATUS mandatory
        DESCRIPTION
               "bit 0 of MSGOUT+55 for read or MSGIN+55 for respond to LLB
                in this configure Loop Response Message."
        ::= { ncmidcsuConfigEntry 30 }
 
 
        ncmidcsuCfgLoopRespPLB      OBJECT-TYPE
        SYNTAX INTEGER  {
                        no(1),
                        yes(2)
        }
        ACCESS read-write
        STATUS mandatory
        DESCRIPTION
               "bit 1 of MSGOUT+55 for read or MSGIN+55 for respond to PLB
                in this configure Loop Response Message."
        ::= { ncmidcsuConfigEntry 31 }
 
 
        ncmidcsuCfgLoopRespELB     OBJECT-TYPE
        SYNTAX INTEGER  {
                        no(1),
                        yes(2)
        }
        ACCESS read-write
        STATUS mandatory
        DESCRIPTION
               "bit 2 of MSGOUT+55 for read or MSGIN+55 for respond to ELB
                in this configure Loop Response Message."
        ::= { ncmidcsuConfigEntry 32 }
 
 
        ncmidcsuCfgLoopRespRLB     OBJECT-TYPE
        SYNTAX INTEGER  {
                        no(1),
                        yes(2)
        }
        ACCESS read-write
        STATUS mandatory
        DESCRIPTION
               "bit 3 of MSGOUT+55 for read or MSGIN+55 for respond to RLB
                in this configure Loop Response Message."
        ::= { ncmidcsuConfigEntry 33 }
 
 
        ncmidcsuCfgLoopRespLLBTONE     OBJECT-TYPE
        SYNTAX INTEGER  {
                        no(1),
                        yes(2)
        }
        ACCESS read-write
        STATUS mandatory
        DESCRIPTION
               "bit 4 of MSGOUT+55 for read or MSGIN+55 for respond to LLB (T1.403)
                in this configure Loop Response Message."
        ::= { ncmidcsuConfigEntry 34 }


	ncmidcsuCfgLoopRespPLBTONE     OBJECT-TYPE
        SYNTAX INTEGER  {
                        no(1),
                        yes(2)
        }
        ACCESS read-write
        STATUS mandatory
        DESCRIPTION
               "bit 5 of MSGOUT+55 for read or MSGIN+55 for respond to PLB (T1.403)
                in this configure Loop Response Message."
        ::= { ncmidcsuConfigEntry 35 }
 
 
        ncmidcsuCfgSendReceiveInBandCode     OBJECT-TYPE
        SYNTAX INTEGER  {
                        disable(1),
                        enable(2)
        }
        ACCESS read-write
        STATUS mandatory
        DESCRIPTION
               "bit 6 of MSGOUT+55 for read or MSGIN+55 for enable to Send/Receive
                of in-band code."
        ::= { ncmidcsuConfigEntry 36 }
 
 

 





	 -- The ncmidcsu Threshold Interval Table
     
        ncmidcsuThresholdIntervalTable OBJECT-TYPE
        SYNTAX SEQUENCE OF  NcmidcsuThresholdIntervalEntry
        ACCESS not-accessible
        STATUS mandatory
	 DESCRIPTION
               "The ncm idcsu threshold interval table."


	--DEFAULT test-function idcsu-test
	--DEFAULT next-function idcsu-next
	
                  ::= { ncm-idcsu 10001 }


        ncmidcsuThresholdIntervalEntry  OBJECT-TYPE
        SYNTAX NcmidcsuThresholdIntervalEntry 
        ACCESS not-accessible
        STATUS mandatory
        DESCRIPTION
               "An entry in the ncmidcsu threshold interval table."
        INDEX   { ncmidcsuThresholdNIDIndex, ncmidcsuThresholdIntervalIndex }
        ::= { ncmidcsuThresholdIntervalTable 1 }

	 NcmidcsuThresholdIntervalEntry  ::= 
        SEQUENCE {
             ncmidcsuThresholdNIDIndex
		INTEGER,
             ncmidcsuThresholdIntervalIndex
                 INTEGER, 
	     ncmidcsuBERThreshold
                 INTEGER,
	     ncmidcsubpvSecThreshold
                 INTEGER,
             ncmidcsubpvSecInterval
	 	INTEGER,    
             ncmidcsuESThreshold
                 INTEGER,
             ncmidcsuESInterval
                 INTEGER,
             ncmidcsuUASThreshold
                 INTEGER,
             ncmidcsuUASInterval
                 INTEGER


		}

        ncmidcsuThresholdNIDIndex OBJECT-TYPE
          SYNTAX  INTEGER (1..'7fffffff'h)
          ACCESS  read-only
          STATUS  mandatory
          DESCRIPTION
		"This variable indicates the node id value of the node."
        ::= { ncmidcsuThresholdIntervalEntry 1 }

	ncmidcsuThresholdIntervalIndex OBJECT-TYPE
        SYNTAX  INTEGER 
        ACCESS  read-only
        STATUS  mandatory
DESCRIPTION ""
        --DEFAULT get-function get-ncmcsuMainLineIndex

        ::= { ncmidcsuThresholdIntervalEntry 2 }


	ncmidcsuBERThreshold OBJECT-TYPE
        SYNTAX INTEGER {

                       disable(1),
                       ten-to-Four(2),
                       ten-to-Five(3),
                       ten-to-Six(4),
                       ten-to-Seven(5),
                       ten-to-Eight(6),
                       ten-to-Nine(7)

               }
        ACCESS read-write
        STATUS mandatory
        DESCRIPTION
               "The ncmidcsu Net/Eq ber threshold."
        ::= { ncmidcsuThresholdIntervalEntry 3 }


	ncmidcsubpvSecThreshold OBJECT-TYPE
        SYNTAX INTEGER
        ACCESS read-write
        STATUS mandatory
        DESCRIPTION
               "The ncmidcsu Net/Eq bpv sec threshold."
        ::= { ncmidcsuThresholdIntervalEntry 4 }



	ncmidcsubpvSecInterval OBJECT-TYPE
        SYNTAX INTEGER 
        ACCESS read-write
        STATUS mandatory
        DESCRIPTION
               "The ncmidcsu Net/Eq bpv sec interval."
        ::= { ncmidcsuThresholdIntervalEntry 5 }


	ncmidcsuESThreshold OBJECT-TYPE
        SYNTAX INTEGER
        ACCESS read-write
        STATUS mandatory
        DESCRIPTION
               "The ncmidcsu Net/Eq es threshold."
        ::= { ncmidcsuThresholdIntervalEntry 6 }


        ncmidcsuESInterval OBJECT-TYPE
        SYNTAX INTEGER 
        ACCESS read-write
        STATUS mandatory
        DESCRIPTION
               "The ncmidcsu Net/Eq es interval."
        ::= { ncmidcsuThresholdIntervalEntry 7 }


	ncmidcsuUASThreshold OBJECT-TYPE
        SYNTAX INTEGER
        ACCESS read-write
        STATUS mandatory
        DESCRIPTION
               "The ncmidcsu Net/Eq uas threshold."
          ::= { ncmidcsuThresholdIntervalEntry 8 }

	ncmidcsuUASInterval OBJECT-TYPE
        SYNTAX INTEGER 
        ACCESS read-write
        STATUS mandatory
        DESCRIPTION
               "The ncmidcsu Net/Eq uas interval."
        ::= { ncmidcsuThresholdIntervalEntry 9 }


	



	 -- The ncmidcsu configuration table1
     
        ncmidcsuConfigOneTable OBJECT-TYPE
        SYNTAX SEQUENCE OF  NcmidcsuConfigOneEntry
        ACCESS not-accessible
        STATUS mandatory
	DESCRIPTION
        "The ncm idcsu configuration table1."


	--DEFAULT test-function idcsu-test
	--DEFAULT next-function idcsu-next
	
                  ::= { ncm-idcsu 10002 }


        ncmidcsuConfigOneEntry OBJECT-TYPE
        SYNTAX NcmidcsuConfigOneEntry
        ACCESS not-accessible
        STATUS mandatory
        DESCRIPTION
               "An entry in the ncmidcsu configuration table1."
        INDEX   { ncmidcsucfg1NIDIndex, ncmidcsuLineIndex1 }
        ::= { ncmidcsuConfigOneTable 1 }

	NcmidcsuConfigOneEntry ::= 
        SEQUENCE {
             ncmidcsucfg1NIDIndex
		INTEGER,
             ncmidcsuLineIndex1
                 INTEGER, 
	     ncmidcsuDS0Channel
		 DisplayString,
	     ncmidcsuRLBTimeoutIndex
                 INTEGER,
	     ncmidcsuNetLofcIndexTime
                 INTEGER,
	     ncmidcsuTiming
                 INTEGER,
	     ncmidcsuLineCode
		INTEGER,
	     ncmidcsuMode
		INTEGER,
	     ncmidcsuClock
		INTEGER,
	     ncmidcsuScramble
		INTEGER,
	     ncmidcsuLosLead
		INTEGER,
	     ncmidcsuPortLoopEnable
		INTEGER,
	     ncmidcsuDataInvert
		INTEGER,
	     ncmidcsuTimingUnit
		INTEGER,
	     ncmidcsuAlarmReporting
		INTEGER
             
			}

        ncmidcsucfg1NIDIndex OBJECT-TYPE
          SYNTAX  INTEGER (1..'7fffffff'h)
          ACCESS  read-only
          STATUS  mandatory
          DESCRIPTION
		"This variable indicates the node id value of the node."
        ::= { ncmidcsuConfigOneEntry 1 }
 
      	ncmidcsuLineIndex1 OBJECT-TYPE
        SYNTAX  INTEGER 
        ACCESS  read-only
        STATUS  mandatory
DESCRIPTION ""
	--DEFAULT  get-function get-ncmcsuMainLineIndex
        
        ::= { ncmidcsuConfigOneEntry 2 }

	
	ncmidcsuDS0Channel OBJECT-TYPE
        SYNTAX DisplayString (SIZE (0..255))
        ACCESS read-write
        STATUS mandatory
        DESCRIPTION

	"This variable indicates the channel assignment for the
        dsu for the port."        
        ::= { ncmidcsuConfigOneEntry 3 }



	ncmidcsuRLBTimeoutIndex OBJECT-TYPE
        SYNTAX INTEGER 
        ACCESS read-write
        STATUS mandatory
        DESCRIPTION
               "The ncmidcsu rlb timeout index."
        ::= { ncmidcsuConfigOneEntry 4 }
	

	ncmidcsuNetLofcIndexTime OBJECT-TYPE
        SYNTAX INTEGER 
        ACCESS read-write
        STATUS mandatory
        DESCRIPTION
               "The net lofc index time ."
        ::= { ncmidcsuConfigOneEntry 5 }


	ncmidcsuTiming OBJECT-TYPE
        SYNTAX INTEGER  {
                timing (1),
                internal (2),
                external-422 (3),
                reserved (4),
                net(5),
                eq(6),
                reserved-two(7),
                dsu(8)
                                }
        ACCESS read-write
        STATUS mandatory
        DESCRIPTION
               "The ncmidcsu timing."
        ::= { ncmidcsuConfigOneEntry 6 }


	ncmidcsuLineCode   OBJECT-TYPE
        SYNTAX INTEGER {

                       ami(1),
                       b8zs(2) 

               }
        ACCESS read-write
        STATUS mandatory
        DESCRIPTION
               "The ncmidcsu net/eq Line Code."

        ::= { ncmidcsuConfigOneEntry 7}


	ncmidcsuMode   OBJECT-TYPE
        SYNTAX INTEGER {

                       mode-56k(1),
                       mode-64k(2) 

               }
        ACCESS read-write
        STATUS mandatory
        DESCRIPTION
               "The ncmidcsu data transmission mode for the DS-0s channel."

        ::= { ncmidcsuConfigOneEntry 8 }


	ncmidcsuClock   OBJECT-TYPE
        SYNTAX INTEGER {

                       sT(1),
                       iNVST(2),
		       tT(3)	 

               }
        ACCESS read-write
        STATUS mandatory
        DESCRIPTION
               "The ncmidcsu clock for the data port."

        ::= { ncmidcsuConfigOneEntry 9 }


	ncmidcsuScramble  OBJECT-TYPE
        SYNTAX INTEGER {

                       off(1),
                       on(2)
		       	 

               }
        ACCESS read-write
        STATUS mandatory
        DESCRIPTION
               "The ncmidcsu data scrambling option ."

        ::= { ncmidcsuConfigOneEntry 10 }


	ncmidcsuLosLead OBJECT-TYPE
        SYNTAX INTEGER 
        ACCESS read-write
        STATUS mandatory
        DESCRIPTION
	"This variable indicates the DTE lead bits
        for port. The DTE leads can be set by setting the relevant
        bit to 1 and reset by setting the relevant bit to zero.

        Bit     Value   Name    Description
                0               set the dsu port configuration to zero
        0       1       DTR     set uses DTR
        1       2       RTS     set uses RTS
        2       4       DSR     set uses DSR
        3       8       CTS     set uses CTS
        4       16      DCD     set uses DCD
        5       32      LOS     use both bits: bits set to use for alarm
        6       64      LOS     0 = Disable LOS detect, 1=use RTS , 2 = DTR
        7       128     DDSMode set for 56k DDS ."

        ::= { ncmidcsuConfigOneEntry 11 }


	ncmidcsuPortLoopEnable OBJECT-TYPE
        SYNTAX INTEGER {

                       no(1),
                       yes(2)
		       
		       	 

               }
        ACCESS read-write
        STATUS mandatory
        DESCRIPTION
               "The Port Loop Enable of the dsu of idscsu ."

        ::= { ncmidcsuConfigOneEntry 12 }



	ncmidcsuDataInvert OBJECT-TYPE
        SYNTAX INTEGER {
 
                      disable(1),
                      enable(2)
                       
                       
 
               } 
        ACCESS read-write
        STATUS mandatory
        DESCRIPTION
               "This variable specifies the  data invert for idscsu ."
                  
        ::= { ncmidcsuConfigOneEntry 13 }


	ncmidcsuTimingUnit OBJECT-TYPE 
        SYNTAX INTEGER { 
  
                      disable(1),
                      enable(2) 
                           
                       
 
               } 
        ACCESS read-write
        STATUS mandatory
        DESCRIPTION    
               "This variable specifies if the DSU port is configured as timing unit for idscsu ." 
                   
        ::= { ncmidcsuConfigOneEntry 14 } 


	ncmidcsuAlarmReporting OBJECT-TYPE 
        SYNTAX INTEGER { 
  
                      no(1),
                      yes(2) 
                           
                       
 
               } 
        ACCESS read-write
        STATUS mandatory
        DESCRIPTION    
               "This variable specifies if the DSU port has to report Alarm to the SAM for ncmidcsu." 
                   
        ::= { ncmidcsuConfigOneEntry 15 } 

  

 




 	
        

	 -- The ncmidcsu diagnostic table
     
        ncmidcsuDiagnosticTable OBJECT-TYPE
        SYNTAX SEQUENCE OF NcmidcsuDiagnosticEntry
        ACCESS not-accessible
        STATUS mandatory
	DESCRIPTION
        "The ncm idcsu diagnostic table."


	--DEFAULT test-function idcsu-test
	--DEFAULT next-function idcsu-next

                  ::= { ncm-idcsu 10003 }


        ncmidcsuDiagnosticEntry OBJECT-TYPE
        SYNTAX NcmidcsuDiagnosticEntry
        ACCESS not-accessible
        STATUS mandatory
        DESCRIPTION
               "An entry in the ncmidcsu diagnostic table."
        INDEX   { ncmidcsuDiagNIDIndex, ncmidcsuDiagnosticIndex }
        ::= { ncmidcsuDiagnosticTable 1 }

	NcmidcsuDiagnosticEntry ::= 
        SEQUENCE {

             	ncmidcsuDiagNIDIndex
		 INTEGER,
		 ncmidcsuDiagnosticIndex
                 INTEGER, 
		 ncmidcsuAlarmSetDelay
                 INTEGER,
	     	 ncmidcsuAlarmClearDelay
		 INTEGER,
		 ncmidcsuAlarmEnable
		 INTEGER,
		 ncmidcsuLoopback
		 INTEGER,
		 ncmdteloops
		 INTEGER,
		 ncmidcsuTestPattern
		 INTEGER,
		 ncmidcsuResetPerfReg
                 INTEGER,
                 ncmidcsuTestErrorCounter
                 Gauge,
                 ncmidcsuTestSecondsRemain
                 Gauge,
                 ncmidcsuTestTimeSeconds
                 INTEGER,
                 ncmidcsuNetLOFCIndexTime
                 INTEGER,
                 ncmidcsuChannelMask
                 DisplayString,
                 ncmidcsuApplication
                 INTEGER,
                 ncmidcsuTestIntervalIndex
                 INTEGER

	


		}


        ncmidcsuDiagNIDIndex OBJECT-TYPE
          SYNTAX  INTEGER (1..'7fffffff'h)
          ACCESS  read-only
          STATUS  mandatory
          DESCRIPTION
		"This variable indicates the node id value of the node."
        ::= { ncmidcsuDiagnosticEntry 1 }
	
	ncmidcsuDiagnosticIndex OBJECT-TYPE
        SYNTAX  INTEGER 
        ACCESS  read-only
        STATUS  mandatory
DESCRIPTION ""
	--DEFAULT  get-function get-ncmcsuMainLineIndex
        
        ::= { ncmidcsuDiagnosticEntry 2 }


	ncmidcsuAlarmSetDelay OBJECT-TYPE
        SYNTAX INTEGER 
        ACCESS read-write
        STATUS mandatory
        DESCRIPTION
               "The ncmidcsu alarm set delay."
        ::= { ncmidcsuDiagnosticEntry 3 }


        ncmidcsuAlarmClearDelay OBJECT-TYPE
        SYNTAX INTEGER 
        ACCESS read-write
        STATUS mandatory
        DESCRIPTION
               "The ncmidcsu alarm clear delay."
        ::= { ncmidcsuDiagnosticEntry 4 }


	ncmidcsuAlarmEnable   OBJECT-TYPE
        SYNTAX INTEGER {

                       disable(1),
                       enable(2) 

               }
        ACCESS read-write
        STATUS mandatory
        DESCRIPTION
               "The ncmidcsu alarm reporting."

        ::= { ncmidcsuDiagnosticEntry 5 }



	ncmidcsuLoopback OBJECT-TYPE
        SYNTAX INTEGER {
		csu-Payload-Loop-Back(1),
		line-Loop-Back(2),
		repeater-Loop-Back(3),
		csu-Equip-Loop-Back(4),
		csu-No-Loop-Back(5),
                deactivate-LLB-and-PLB(6),
                deactivate-ELB-and-RLB(7),
                deactivate-Payload-Loop-Back(8),
                send-Inband-Loop-Up(9),
                send-Inband-Loop-Down(10)
                
                        }
                
        ACCESS read-write
        STATUS mandatory
        DESCRIPTION
            " The ncmidcsu loop back config. "

        ::= { ncmidcsuDiagnosticEntry 6 }


	ncmdteloops OBJECT-TYPE
        SYNTAX INTEGER {

		       no-loop(1), 
                       near-on(2),
                       near-off(3),
	               far-on(4),
	               far-off(5),
                       repeater-loopback(6)


               }
        ACCESS read-write
        STATUS mandatory
        DESCRIPTION
               "The dte loops of the ncmidcsu  ."

        ::= { ncmidcsuDiagnosticEntry 7 }



	
        ncmidcsuTestPattern OBJECT-TYPE
        SYNTAX INTEGER {

                no-test(1),
                qrss(2),
                one-in-eight(3),
                three-in-twenty-four(4),
                all-ones(5)


                        }  

        ACCESS read-write
        STATUS mandatory
        DESCRIPTION
            " The ncmidcsu test pattern config. "

        ::= { ncmidcsuDiagnosticEntry 8  }


	ncmidcsuResetPerfReg OBJECT-TYPE
        SYNTAX INTEGER {

                no(1),
                yes(2)
                        }

        ACCESS read-write
        STATUS mandatory
        DESCRIPTION
            " The ncmcsu  reset performance monitoring register "
 
        ::= { ncmidcsuDiagnosticEntry 9 }


        ncmidcsuTestErrorCounter OBJECT-TYPE
        SYNTAX Gauge
        ACCESS read-only
        STATUS mandatory
        DESCRIPTION
            " The ncm idcsu test error counter in the test status  "
 
        ::= { ncmidcsuDiagnosticEntry 10 }




        ncmidcsuTestSecondsRemain OBJECT-TYPE
        SYNTAX Gauge
        ACCESS read-only
        STATUS mandatory
        DESCRIPTION
            " The ncm idcsu test seconds remaining in the test status  "
 
        ::= { ncmidcsuDiagnosticEntry 11 }
 
 
 
        ncmidcsuTestTimeSeconds OBJECT-TYPE
        SYNTAX INTEGER
        ACCESS read-write
        STATUS mandatory
        DESCRIPTION
            " The idcsu test time duration. Enter Value (0-142, 255)
              0         corresponds to 0 Sec (Default)
              1 - 59    corresponds to 1-59 Seconds
              60 - 118  corresponds to 1-59 Min
              119 - 142 corresponds to 1-24 HR
              255       corresponds to (Forever) option "
 
        ::= { ncmidcsuDiagnosticEntry 12 }
 
 
        ncmidcsuNetLOFCIndexTime OBJECT-TYPE
        SYNTAX INTEGER
        ACCESS read-write
        STATUS mandatory
        DESCRIPTION
            " The idcsu net lofc index time  "
 
        ::= { ncmidcsuDiagnosticEntry 13  }



	ncmidcsuChannelMask OBJECT-TYPE
        SYNTAX DisplayString (SIZE (0..255))
        ACCESS read-write
        STATUS mandatory
        DESCRIPTION
            " The idcsu channel mask for the 24 channels  "
 
        ::= {ncmidcsuDiagnosticEntry 14  }
 
 
        ncmidcsuApplication OBJECT-TYPE
        SYNTAX INTEGER  {
                         none(1),
                         csu(2),
                         smds(3)
                        }
        ACCESS read-write
        STATUS mandatory
        DESCRIPTION
            " The idcsu application mode  "
 
        ::= { ncmidcsuDiagnosticEntry 15 }
 
 
 
        ncmidcsuTestIntervalIndex OBJECT-TYPE
        SYNTAX INTEGER
        ACCESS read-write
        STATUS mandatory
        DESCRIPTION
        "The idcsu Test Inteval Index value used for test pattern (0 - config default)."
        ::= { ncmidcsuDiagnosticEntry 16 }









END
