MR-MIB DEFINITIONS ::= BEGIN

IMPORTS
        MODULE-IDENTITY, OBJECT-TYPE,
        enterprises, Unsigned32, Counter64, IpAddress
                FROM SNMPv2-SMI
        DisplayString
                FROM SNMPv2-TC;

zxr10mrInstance MODULE-IDENTITY
        LAST-UPDATED "201706051500Z"
        ORGANIZATION "ZTE Corporation."
        CONTACT-INFO
               "Xu benchong
               Tel: 025-698109
               E-Mail:xu.benchong@zte.com.cn"
        DESCRIPTION
                "The MIB module to describe the MR protocol."
        REVISION "201706051500Z" 
        DESCRIPTION
                "add: zxr10mrInstanceNeverSwitchAcl"
        REVISION "201702281500Z" 
        DESCRIPTION
                "add: zxr10mrInstanceSwitchThreshold
                      zxr10mrInstanceSwitchThresholdAcl"
        REVISION "201701181000Z"
        DESCRIPTION
                "add: zxr10nexthopTrackName"
        REVISION "201701061000Z"
        DESCRIPTION
                "add: zxr10pimsmIntfHelloTrackSupport"
        REVISION "201612021000Z"
        DESCRIPTION
                "add: zxr10mrInstanceBgpInterAs,
                      zxr10mrInstanceBgpSegmented,
                      zxr10mrInstanceSwitchInterval,
                      zxr10mrSegBorderTable"
        REVISION "201603181500Z"
        DESCRIPTION
                "add: zxr10pimsmInstStatisticsAclName"
        REVISION "201601081100Z" 
        DESCRIPTION
                "add: zxr10peerKeychain"
        REVISION "201512181500Z" 
        DESCRIPTION
                "add: zxr10mstaticRouteIncMask
                      zxr10mstaticRouteCount"
        REVISION "201512111500Z" 
        DESCRIPTION
                "add: zxr10nexthopFallbackGlobal
                      zxr10nexthopFallbackVrfName"
        REVISION "201511201400Z" 
        DESCRIPTION
                "modify:the description of zxr10mrInstanceRpfProxyVector
                 add: zxr10mrInstanceRpfProxyMbgpAcl
                      zxr10mrInstanceMrouteLimitInst"
        REVISION "201509231000Z" 
        DESCRIPTION
                "add: zxr10pimsmInstPimdmReg"
        REVISION "201508281100Z"
        DESCRIPTION
                "add: zxr10mstaticRoutePermanent,
                      zxr10mstaticRouteSlaveIifName,
                      zxr10mstaticRouteTrackName,
                      zxr10mstaticRouteSlaveTrackName,
                      zxr10mstaticFrrTable"
        REVISION "201507071100Z"
        DESCRIPTION
                "modify: the ranges of zxr10mstaticLimitXgLimit 
                 and zxr10mstaticLimitSgLimit are both 0-2048,
                 the max values get from performance parameter."
        REVISION "201506241000Z"
        DESCRIPTION
                "modify:zxr10igmpGroupTable is obsolete
                 add:zxr10igmpStaticGroupTable "
        REVISION "201506201400Z" 
        DESCRIPTION
                "add: zxr10pimsmIntfHelloDrAddr"
        REVISION "201506011000Z" 
        DESCRIPTION
                "add: zxr10pimsmInstCbsrHoldtime,
                      zxr10pimsmInstCbsrInterval,
                      zxr10pimsmCrpHoldtime"
        REVISION "201503201000Z"
        DESCRIPTION
                "add: zxr10pimsmInstJpSpeed
                      zxr10pimsmInstKeepAlivePeriod
                      zxr10pimsmInstAssertHoldTime
                      zxr10pimsmInstGraftTime
                      zxr10pimsmIntfPropagationDelay
                      zxr10pimsmIntfOverrideInterval
                      zxr10pimsmIntfJpMaxpktLen" 
        REVISION "201503091400Z" 
        DESCRIPTION
                "add: zxr10msdpInstanceSaAdvTime,
                      zxr10msdpInstanceSaCacheTimeout,
                      zxr10peerHoldtime,
                      zxr10peerKeepaliveTime,
                      zxr10peerReconnectTime,
                      zxr10peerInactiveTime"
        REVISION "201503021500Z"
        DESCRIPTION
                "modify: the status of zxr10mstaticOifIndexVlanMin and zxr10mstaticOifIndexVlanMax is obsolete"
        REVISION "201502281000Z"
        DESCRIPTION
                "add: zxr10nexthopNextHopSlave"
        REVISION "201410101000Z"
        DESCRIPTION
                "add: zxr10pimsmInterfaceFrrEn
                      zxr10pimsmInstMldpSignalEn
                      zxr10pimsmInstMldpSignalAclName"        
        REVISION "201409011400Z"
        DESCRIPTION
                "modify:range of zxr10mrInstanceMultipathSghash is 
                {none(0),sbased(1),sgbasic(2),sgnexthopbased(3),sgbalance(4)}"
        REVISION "201408261100Z"
        DESCRIPTION
                "modify: the range of zxr10mrInstanceDownstreamLimit is 0-1024, the max value gets from performance parameter"
        REVISION "201407221100Z"
        DESCRIPTION
                "modify: the status of zxr10mdtDataMdtDataThreshold is obsolete"
        REVISION "201406181600Z" 
        DESCRIPTION
            "modify: range of zxr10mrInstanceTosValue is (0..63|255),
                     DESCRIPTION of zxr10mrMonitorRouteMrMoniterSource,
                     range of zxr10pimsmInstDrSwitchDelayValue is (0..300)"
        REVISION "201403131000Z" 
        DESCRIPTION
                "add: zxr10mrInstanceMdtAutoDiscovery,
                      zxr10mdtDefaultMdtRootAddr,
                      zxr10mdtDataMdtDataNumTree"
        REVISION "201402211400Z" 
        DESCRIPTION
            "modify: DESCRIPTION of some nodes,
                     range of zxr10mrInstanceSearchMode is (0..1),
                     range of zxr10pimsmInstDrSwitchDelayValue is (1..300),
                     range of zxr10pimsmInstMofrrAclName is (0..30),
                     range of zxr10mrTtlNum is (1..255),
                     leaf node order of zxr10pimBindTable, 
                     zxr10pimBindGroupName and zxr10pimBindIntfName"
        REVISION "201401211400Z" 
        DESCRIPTION
            "add: zxr10pimsmInstMofrrAclName"
        REVISION "201401081700Z"
        DESCRIPTION
                "modify: range of zxr10pimsmInstJpInterval is (10..6000),
                         DESCRIPTION of zxr10igmpIntfImmediateAll"
        REVISION "201312031700Z"
        DESCRIPTION
                "add: zxr10mrInstanceRpfProxyVector"
        REVISION "201310121400Z"
        DESCRIPTION
                "add: zxr10pimsmInstJpInterval 
                      zxr10pimsmInstRegHoldtime"
        REVISION "201308011530Z"
        DESCRIPTION
                "add: zxr10igmpIntfIpSourceCheck
                      zxr10igmpGroupLimitTable"
        REVISION "201307181530Z"
        DESCRIPTION
                "add: zxr10pimsmInstBidirPim
                      zxr10pimsmCrpBidirPim
                      zxr10pimsmSrpBidirPim"
        REVISION "201307161400Z"
        DESCRIPTION
                "modify:range of zxr10mrInstanceMrouteLimit is (0..131070),
                        range of zxr10mrInstanceDownstreamLimit is (0..64)
                        range of zxr10mrInstanceMultipathSghash is {none(0),sbased(1),sgbasic(2),sgnexthopbased(3)}
                        range of zxr10mstaticInstMstaticFlag is (0..1)                
                "   
        REVISION "201306081400Z"
        DESCRIPTION
                "modify:the size from SIZE (0..32) to SIZE (0..31),
                        including of zxr10pimGroupName
                        zxr10pimBindGroupName                
                "        
        REVISION "201305211400Z"
        DESCRIPTION
                "modify:the data type of enumeration is converted from Unsigned32 to INTEGER, 
                        including of zxr10mrInstanceMultipathSghash
                        zxr10pimBindIntfActive
                        zxr10pimBindIntfPassive
                        zxr10igmpIntfVersion
                        zxr10igmpGroupStaticFlag
                        zxr10igmpGroupFilterMode
                        zxr10mvpnInstProviderTunnel
                        zxr10mrFilterInterfaceMode
                        zxr10mrFilterInterfaceType
                        zxr10mrFilterMrouteInterfaceType
                        zxr10mrFilterMrouteModeType
                        zxr10mrForwordingPolicyType ,and hyphen of node is deleted,
                        including of zxr10mrInstanceMultipathSghash
                        zxr10safilterinTable
                        zxr10safilteroutTable
                        zxr10mvpnInstProviderTunnel          
                        "
        REVISION "201305131400Z"
        DESCRIPTION
                "modify:zxr10pimBindIntfActive
                        zxr10pimBindIntfPassive"
        REVISION "201304031400Z"
        DESCRIPTION
                "add: zxr10pimBindTable
                      zxr10pimBindTable
                 modify:zxr10mrFilterInterfaceIntfname
                        zxr10mrFilterMrouteInterfaceIntfname"
        REVISION "201102090000Z"
        DESCRIPTION
                "Initial version of this MIB module."
        ::= { zxr10mrInstanceMIBs 1 }

    zte OBJECT IDENTIFIER ::= { enterprises 3902 }

    zxr10 OBJECT IDENTIFIER ::= { zte 3}

    zxr10RosngMIB OBJECT IDENTIFIER ::= { zxr10 6000}

    zxr10mrInstanceMIBs OBJECT IDENTIFIER ::= { zxr10RosngMIB 165}

        
zxr10mrInstanceMIB OBJECT IDENTIFIER ::= { zxr10mrInstance 1 }

zxr10mrInstanceTable OBJECT-TYPE
        SYNTAX  SEQUENCE OF Zxr10mrInstanceEntry
        MAX-ACCESS  not-accessible
        STATUS  current
        DESCRIPTION
            "A table to MR instance"
        ::= { zxr10mrInstanceMIB 1 }

zxr10mrInstanceEntry OBJECT-TYPE
        SYNTAX Zxr10mrInstanceEntry
        MAX-ACCESS  not-accessible
        STATUS  current
        DESCRIPTION
            "An entry to MR instance"
        INDEX  { zxr10mrInstanceVrfName }
        ::= { zxr10mrInstanceTable 1 }

Zxr10mrInstanceEntry ::=
        SEQUENCE {
            zxr10mrInstanceVrfName
                DisplayString,
            zxr10mrInstanceMrouteLimit
                Unsigned32,
            zxr10mrInstanceNsfTime
                INTEGER,
            zxr10mrInstanceDownstreamLimit
                INTEGER,
            zxr10mrInstanceMultipathSghash
                INTEGER,
            zxr10mrInstanceSearchMode
                Unsigned32,            
            zxr10mrInstanceLongestMatch
                Unsigned32,
            zxr10mrInstanceStaticFirst
                Unsigned32,
            zxr10mrInstanceTosValue
                Unsigned32,
            zxr10mrInstanceDampingEnable
                Unsigned32,
            zxr10mrInstanceDampingThreshold
                Unsigned32,
            zxr10mrInstanceRpfProxyVector
                INTEGER,
            zxr10mrInstanceMdtAutoDiscovery
                INTEGER,
            zxr10mrInstanceRpfProxyMbgpAcl
                DisplayString,
            zxr10mrInstanceMrouteLimitInst
                Unsigned32,
            zxr10mrInstanceBgpInterAs
                INTEGER,
            zxr10mrInstanceBgpSegmented
                INTEGER,
            zxr10mrInstanceSwitchInterval
                Unsigned32,
            zxr10mrInstanceSwitchThreshold
                Unsigned32,
            zxr10mrInstanceSwitchThresholdAcl
                DisplayString,
            zxr10mrInstanceNeverSwitchAcl
                DisplayString
        }

zxr10mrInstanceVrfName OBJECT-TYPE
        SYNTAX DisplayString (SIZE (0..32))
        MAX-ACCESS  read-only
        STATUS  current
        DESCRIPTION
            "vrf name"
        ::= { zxr10mrInstanceEntry 1 }

zxr10mrInstanceMrouteLimit OBJECT-TYPE
        SYNTAX Unsigned32 (0..131070)
        MAX-ACCESS  read-only
        STATUS  current
        DESCRIPTION
            "mroute limit"
        ::= { zxr10mrInstanceEntry 3 }

zxr10mrInstanceNsfTime OBJECT-TYPE
        SYNTAX INTEGER (30..1800)
        MAX-ACCESS  read-only
        STATUS  current
        DESCRIPTION
            "nsf time"
        ::= { zxr10mrInstanceEntry 4 }

zxr10mrInstanceDownstreamLimit OBJECT-TYPE
        SYNTAX INTEGER (0..1024)
        MAX-ACCESS  read-only
        STATUS  current
        DESCRIPTION
            "downstream limit, the max value gets from performance parameter"
        ::= { zxr10mrInstanceEntry 5 }

zxr10mrInstanceMultipathSghash OBJECT-TYPE
        SYNTAX INTEGER {none(0),sbased(1),sgbasic(2),sgnexthopbased(3),sgbalance(4)}     
        MAX-ACCESS  read-only
        STATUS  current
        DESCRIPTION
            "multipath based sg-hash"
        ::= { zxr10mrInstanceEntry 7 }

zxr10mrInstanceSearchMode OBJECT-TYPE  
        SYNTAX Unsigned32 (0..1)
        MAX-ACCESS  read-only
        STATUS  current
        DESCRIPTION
            "multicast search mode"
        ::= { zxr10mrInstanceEntry 8 }

zxr10mrInstanceLongestMatch OBJECT-TYPE
        SYNTAX Unsigned32 (0..1)
        MAX-ACCESS  read-only
        STATUS  current
        DESCRIPTION
            "longest match of lookup unicast"
        ::= { zxr10mrInstanceEntry 10 }

zxr10mrInstanceStaticFirst OBJECT-TYPE   
        SYNTAX Unsigned32 (0..1)
        MAX-ACCESS  read-only
        STATUS  current
        DESCRIPTION
            "static first of lookup unicast"
        ::= { zxr10mrInstanceEntry 11 }

zxr10mrInstanceTosValue OBJECT-TYPE
        SYNTAX Unsigned32 (0..63|255)
        MAX-ACCESS  read-only
        STATUS  current
        DESCRIPTION
            "tos value of multicast protocol packet"
        ::= { zxr10mrInstanceEntry 12 }

zxr10mrInstanceDampingEnable OBJECT-TYPE
        SYNTAX Unsigned32 (0..1) 
        MAX-ACCESS  read-only
        STATUS  current
        DESCRIPTION
            "damping enable"
        ::= { zxr10mrInstanceEntry 13 }

zxr10mrInstanceDampingThreshold OBJECT-TYPE
        SYNTAX Unsigned32 (2..100)
        MAX-ACCESS  read-only
        STATUS  current
        DESCRIPTION
            "damping threshold"
        ::= { zxr10mrInstanceEntry 14 }

zxr10mrInstanceRpfProxyVector OBJECT-TYPE
        SYNTAX INTEGER {false(255),true(1)}
        MAX-ACCESS  read-only
        STATUS  current
        DESCRIPTION
            "RPF proxy vector for MDT"
        ::= { zxr10mrInstanceEntry 15 }

zxr10mrInstanceMdtAutoDiscovery OBJECT-TYPE
        SYNTAX INTEGER {false(255),true(1)}
        MAX-ACCESS  read-only
        STATUS  current
        DESCRIPTION
            "mdt auto discovery"
        ::= { zxr10mrInstanceEntry 16 }

zxr10mrInstanceRpfProxyMbgpAcl OBJECT-TYPE
        SYNTAX DisplayString (SIZE (0..31))
        MAX-ACCESS  read-only
        STATUS  current
        DESCRIPTION
            "RPF proxy vector ACL name for MBGP"
        ::= { zxr10mrInstanceEntry 17 }

zxr10mrInstanceMrouteLimitInst OBJECT-TYPE
        SYNTAX Unsigned32 (0..131072)
        MAX-ACCESS  read-only
        STATUS  current
        DESCRIPTION
            "mroute limit for instance, the max value gets
            from performance parameter"
        ::= { zxr10mrInstanceEntry 18 }

zxr10mrInstanceBgpInterAs OBJECT-TYPE
        SYNTAX INTEGER {false(255),true(1)}
        MAX-ACCESS  read-only
        STATUS  current
        DESCRIPTION
            "BGP auto-discovery of inter-AS MVPN."
        ::= { zxr10mrInstanceEntry 19 }

zxr10mrInstanceBgpSegmented OBJECT-TYPE
        SYNTAX INTEGER {false(255),true(1)}
        MAX-ACCESS  read-only
        STATUS  current
        DESCRIPTION
            "BGP auto-discovery of segmented multicast."
        ::= { zxr10mrInstanceEntry 20 }  

zxr10mrInstanceSwitchInterval OBJECT-TYPE
        SYNTAX Unsigned32 (3..65535)
        UNITS   "seconds"
        MAX-ACCESS  read-only
        STATUS  current
        DESCRIPTION
            "MVPN tunnel switchover interval."
        ::= { zxr10mrInstanceEntry 21 }

zxr10mrInstanceSwitchThreshold OBJECT-TYPE
        SYNTAX Unsigned32 (1..4294967295)
        UNITS   "Kbps"
        MAX-ACCESS  read-only
        STATUS  current
        DESCRIPTION
            "MVPN tunnel switchover threshold."
        ::= { zxr10mrInstanceEntry 22 }

zxr10mrInstanceSwitchThresholdAcl OBJECT-TYPE
        SYNTAX DisplayString (SIZE (0..31))
        MAX-ACCESS  read-only
        STATUS  current
        DESCRIPTION
            "ACL for MVPN tunnel switchover"
        ::= { zxr10mrInstanceEntry 23 }

zxr10mrInstanceNeverSwitchAcl OBJECT-TYPE
        SYNTAX DisplayString (SIZE (0..31))
        MAX-ACCESS  read-only
        STATUS  current
        DESCRIPTION
            "ACL for MVPN tunnel never switch to data tree"
        ::= { zxr10mrInstanceEntry 24 }

zxr10mstaticInstMIB OBJECT IDENTIFIER ::= { zxr10mrInstanceMIB 2 }

zxr10mstaticInstTable OBJECT-TYPE
        SYNTAX  SEQUENCE OF Zxr10mstaticInstEntry
        MAX-ACCESS  not-accessible
        STATUS  current
        DESCRIPTION
            "A table to mstatic instance"
        ::= { zxr10mstaticInstMIB 1 }

zxr10mstaticInstEntry OBJECT-TYPE
        SYNTAX Zxr10mstaticInstEntry
        MAX-ACCESS  not-accessible
        STATUS  current
        DESCRIPTION
            "An entry to mstatic instance"
        INDEX  { zxr10mstaticInstVrfName }
        ::= { zxr10mstaticInstTable 1 }

Zxr10mstaticInstEntry ::=
        SEQUENCE {
            zxr10mstaticInstVrfName
                DisplayString,
            zxr10mstaticInstMstaticFlag
                Unsigned32
        }

zxr10mstaticInstVrfName OBJECT-TYPE
        SYNTAX DisplayString (SIZE (0..32))       
        MAX-ACCESS  read-only
        STATUS  current
        DESCRIPTION
            "vrf name"
        ::= { zxr10mstaticInstEntry 1 }

zxr10mstaticInstMstaticFlag OBJECT-TYPE
        SYNTAX Unsigned32 (0..1)
        MAX-ACCESS  read-only
        STATUS  current
        DESCRIPTION
            "enable mstatic flag"
        ::= { zxr10mstaticInstEntry 2 }



zxr10mstaticOifIndexTable OBJECT-TYPE
        SYNTAX  SEQUENCE OF Zxr10mstaticOifIndexEntry
        MAX-ACCESS  not-accessible
        STATUS  current
        DESCRIPTION
            "A table to mstatic oif"
        ::= { zxr10mstaticInstMIB 2 }

zxr10mstaticOifIndexEntry OBJECT-TYPE
        SYNTAX Zxr10mstaticOifIndexEntry
        MAX-ACCESS  not-accessible
        STATUS  current
        DESCRIPTION
            "An entry to mstatic oif"
        INDEX  { zxr10mstaticOifIndexVrfName,
        zxr10mstaticOifIndexIntfName,
        zxr10mstaticOifIndexOifIndex }
        ::= { zxr10mstaticOifIndexTable 1 }

Zxr10mstaticOifIndexEntry ::=
        SEQUENCE {
            zxr10mstaticOifIndexVrfName
                DisplayString,
            zxr10mstaticOifIndexIntfName
                DisplayString,
            zxr10mstaticOifIndexOifIndex
                Unsigned32,
            zxr10mstaticOifIndexVlanMin
                Unsigned32,
            zxr10mstaticOifIndexVlanMax
                Unsigned32
        }

zxr10mstaticOifIndexVrfName OBJECT-TYPE
        SYNTAX DisplayString (SIZE (0..32))
        MAX-ACCESS  read-only
        STATUS  current
        DESCRIPTION
            "vrf name"
        ::= { zxr10mstaticOifIndexEntry 1 }

zxr10mstaticOifIndexIntfName OBJECT-TYPE
        SYNTAX DisplayString (SIZE (0..32))
        MAX-ACCESS  read-only
        STATUS  current
        DESCRIPTION
            "interface name"
        ::= { zxr10mstaticOifIndexEntry 2 }

zxr10mstaticOifIndexOifIndex OBJECT-TYPE
        SYNTAX Unsigned32 (0..100)
        MAX-ACCESS  read-only
        STATUS  current
        DESCRIPTION
            "oif index"
        ::= { zxr10mstaticOifIndexEntry 3 }

zxr10mstaticOifIndexVlanMin OBJECT-TYPE
        SYNTAX Unsigned32 (0..65536)
        MAX-ACCESS  read-only
        STATUS  obsolete
        DESCRIPTION
            "vlan min"
        ::= { zxr10mstaticOifIndexEntry 4 }

zxr10mstaticOifIndexVlanMax OBJECT-TYPE
        SYNTAX Unsigned32 (0..65536)
        MAX-ACCESS  read-only
        STATUS  obsolete
        DESCRIPTION
            "vlan max"
        ::= { zxr10mstaticOifIndexEntry 5 }


zxr10mstaticLimitMIB OBJECT IDENTIFIER ::= { zxr10mstaticInstMIB 3 }

zxr10mstaticLimitTable OBJECT-TYPE
        SYNTAX  SEQUENCE OF Zxr10mstaticLimitEntry
        MAX-ACCESS  not-accessible
        STATUS  current
        DESCRIPTION
            "A table to mstatic route limit"
        ::= { zxr10mstaticLimitMIB 1 }

zxr10mstaticLimitEntry OBJECT-TYPE
        SYNTAX Zxr10mstaticLimitEntry
        MAX-ACCESS  not-accessible
        STATUS  current
        DESCRIPTION
            "An entry to mstatic route limit"
        INDEX  { zxr10mstaticLimitVrfname }
        ::= { zxr10mstaticLimitTable 1 }
     
Zxr10mstaticLimitEntry ::=
        SEQUENCE {
            zxr10mstaticLimitVrfname
                DisplayString,
            zxr10mstaticLimitXgLimit
                INTEGER,
            zxr10mstaticLimitSgLimit
                INTEGER
        }

zxr10mstaticLimitVrfname OBJECT-TYPE  
        SYNTAX DisplayString (SIZE (0..32))
        MAX-ACCESS  read-only
        STATUS  current
        DESCRIPTION
            "vrf name"
        ::= { zxr10mstaticLimitEntry 1 }

zxr10mstaticLimitXgLimit OBJECT-TYPE
        SYNTAX INTEGER (0..2048)
        MAX-ACCESS  read-only
        STATUS  current
        DESCRIPTION
            "xg limit, the max value gets from performance parameter."
        ::= { zxr10mstaticLimitEntry 2 }

zxr10mstaticLimitSgLimit OBJECT-TYPE
        SYNTAX INTEGER (0..2048)
        MAX-ACCESS  read-only
        STATUS  current
        DESCRIPTION
            "sg limit, the max value gets from performance parameter."
        ::= { zxr10mstaticLimitEntry 3 }

zxr10mstaticRouteTable OBJECT-TYPE
        SYNTAX  SEQUENCE OF Zxr10mstaticRouteEntry
        MAX-ACCESS  not-accessible
        STATUS  current
        DESCRIPTION
            "A table to mstatic route"
        ::= { zxr10mstaticLimitMIB 2 }

zxr10mstaticRouteEntry OBJECT-TYPE
        SYNTAX Zxr10mstaticRouteEntry
        MAX-ACCESS  not-accessible
        STATUS  current
        DESCRIPTION
            "An entry to mstatic route"
        INDEX  { zxr10mstaticRouteVrfName,
        zxr10mstaticRouteMstaticGroupAddr,
        zxr10mstaticRouteMstaticSourceAddr }
        ::= { zxr10mstaticRouteTable 1 }

Zxr10mstaticRouteEntry ::=
        SEQUENCE {
            zxr10mstaticRouteVrfName
                DisplayString,
            zxr10mstaticRouteMstaticGroupAddr
                IpAddress,
            zxr10mstaticRouteMstaticSourceAddr
                IpAddress,
            zxr10mstaticRouteIifIntfname
                DisplayString,
            zxr10mstaticRouteOifIndex
                Unsigned32,
            zxr10mstaticRoutePermanent
                INTEGER,
            zxr10mstaticRouteSlaveIifName
                DisplayString,
            zxr10mstaticRouteTrackName
                DisplayString,
            zxr10mstaticRouteSlaveTrackName
                DisplayString,
            zxr10mstaticRouteIncMask
                IpAddress,
            zxr10mstaticRouteCount
                Unsigned32
        }

zxr10mstaticRouteVrfName OBJECT-TYPE       
        SYNTAX DisplayString (SIZE (0..32))
        MAX-ACCESS  read-only                             
        STATUS  current
        DESCRIPTION
            "vrf name"
        ::= { zxr10mstaticRouteEntry 1 }

zxr10mstaticRouteMstaticGroupAddr OBJECT-TYPE
        SYNTAX IpAddress
        MAX-ACCESS  read-only
        STATUS  current
        DESCRIPTION
            "group address"
        ::= { zxr10mstaticRouteEntry 2 }

zxr10mstaticRouteMstaticSourceAddr OBJECT-TYPE
        SYNTAX IpAddress
        MAX-ACCESS  read-only
        STATUS  current
        DESCRIPTION
            "source address"
        ::= { zxr10mstaticRouteEntry 3 }

zxr10mstaticRouteIifIntfname OBJECT-TYPE
        SYNTAX DisplayString (SIZE (0..32))
        MAX-ACCESS  read-only
        STATUS  current
        DESCRIPTION
            "iif interface name"
        ::= { zxr10mstaticRouteEntry 4 }

zxr10mstaticRouteOifIndex OBJECT-TYPE
        SYNTAX Unsigned32 (0..100)
        MAX-ACCESS  read-only
        STATUS  current
        DESCRIPTION
            "oif interface name"
        ::= { zxr10mstaticRouteEntry 5 }

zxr10mstaticRoutePermanent OBJECT-TYPE
        SYNTAX INTEGER {false(255),true(1)}
        MAX-ACCESS  read-only
        STATUS  current
        DESCRIPTION
            "permanent"
        ::= { zxr10mstaticRouteEntry 6 }

zxr10mstaticRouteSlaveIifName OBJECT-TYPE
        SYNTAX DisplayString (SIZE (0..32))
        MAX-ACCESS  read-only
        STATUS  current
        DESCRIPTION
            "slave iif interface name"
        ::= { zxr10mstaticRouteEntry 7 }

zxr10mstaticRouteTrackName OBJECT-TYPE
        SYNTAX DisplayString (SIZE (0..31))
        MAX-ACCESS  read-only
        STATUS  current
        DESCRIPTION
            "track name"
        ::= { zxr10mstaticRouteEntry 8 }

zxr10mstaticRouteSlaveTrackName OBJECT-TYPE
        SYNTAX DisplayString (SIZE (0..31))
        MAX-ACCESS  read-only
        STATUS  current
        DESCRIPTION
            "slave track name"
        ::= { zxr10mstaticRouteEntry 9 }

zxr10mstaticRouteIncMask OBJECT-TYPE
        SYNTAX IpAddress
        MAX-ACCESS  read-only
        STATUS  current
        DESCRIPTION
            "Increment mask of MSTATIC group address"
        ::= { zxr10mstaticRouteEntry 10 }
        
zxr10mstaticRouteCount OBJECT-TYPE
        SYNTAX Unsigned32 (0..512)
        MAX-ACCESS  read-only
        STATUS  current
        DESCRIPTION
            "The number of MSTATIC group addresses"
        ::= { zxr10mstaticRouteEntry 11 }
        
zxr10mstaticFrrTable OBJECT-TYPE
        SYNTAX  SEQUENCE OF Zxr10mstaticFrrEntry
        MAX-ACCESS  not-accessible
        STATUS  current
        DESCRIPTION
            "A table to mstatic fast reroute"
        ::= { zxr10mstaticInstMIB 4 }

zxr10mstaticFrrEntry OBJECT-TYPE
        SYNTAX Zxr10mstaticFrrEntry
        MAX-ACCESS  not-accessible
        STATUS  current
        DESCRIPTION
            "An entry to mstatic fast reroute"
        INDEX  { zxr10mstaticFrrVrfName }
        ::= { zxr10mstaticFrrTable 1 }
            
Zxr10mstaticFrrEntry ::=
        SEQUENCE {
            zxr10mstaticFrrVrfName
                DisplayString,
            zxr10mstaticFrrWtr
                Unsigned32
        }

zxr10mstaticFrrVrfName OBJECT-TYPE
        SYNTAX DisplayString (SIZE (0..32))
        MAX-ACCESS  not-accessible
        STATUS  current
        DESCRIPTION
            "vrf name"
        ::= { zxr10mstaticFrrEntry 1 }

zxr10mstaticFrrWtr OBJECT-TYPE
        SYNTAX Unsigned32 (0..12)
        MAX-ACCESS  read-only
        STATUS  current
        DESCRIPTION
            "wait to restore"
        ::= { zxr10mstaticFrrEntry 2 }

zxr10nexthopTable OBJECT-TYPE
        SYNTAX  SEQUENCE OF Zxr10nexthopEntry
        MAX-ACCESS  not-accessible
        STATUS  current
        DESCRIPTION
            "A table to multicast nexthop"
        ::= { zxr10mrInstanceMIB 3 }

zxr10nexthopEntry OBJECT-TYPE
        SYNTAX Zxr10nexthopEntry
        MAX-ACCESS  not-accessible
        STATUS  current
        DESCRIPTION
            "An entry to multicast nexthop"
        INDEX  { zxr10nexthopVrfName,
        zxr10nexthopIntfName,
        zxr10nexthopIpAddr,
        zxr10nexthopIpMask,
        zxr10nexthopNextHopAddr }
        ::= { zxr10nexthopTable 1 }

Zxr10nexthopEntry ::=
        SEQUENCE {
            zxr10nexthopVrfName
                DisplayString,
            zxr10nexthopIntfName
                DisplayString,
            zxr10nexthopIpAddr
                IpAddress,
            zxr10nexthopIpMask
                IpAddress,
            zxr10nexthopNextHopAddr
                IpAddress,
            zxr10nexthopNextHopSlave
                INTEGER,
            zxr10nexthopFallbackGlobal
                INTEGER,
            zxr10nexthopFallbackVrfName
                DisplayString,
            zxr10nexthopTrackName
                DisplayString
        }

zxr10nexthopVrfName OBJECT-TYPE
        SYNTAX DisplayString (SIZE (0..32))
        MAX-ACCESS  read-only
        STATUS  current
        DESCRIPTION
            "vrf name"
        ::= { zxr10nexthopEntry 1 }

zxr10nexthopIntfName OBJECT-TYPE
        SYNTAX DisplayString (SIZE (0..32))
        MAX-ACCESS  read-only
        STATUS  current
        DESCRIPTION
            "interface name"
        ::= { zxr10nexthopEntry 2 }

zxr10nexthopIpAddr OBJECT-TYPE
        SYNTAX IpAddress
        MAX-ACCESS  read-only
        STATUS  current
        DESCRIPTION
            "ip address"
        ::= { zxr10nexthopEntry 3 }

zxr10nexthopIpMask OBJECT-TYPE
        SYNTAX IpAddress
        MAX-ACCESS  read-only
        STATUS  current
        DESCRIPTION
            "ip address mask"
        ::= { zxr10nexthopEntry 4 }

zxr10nexthopNextHopAddr OBJECT-TYPE
        SYNTAX IpAddress
        MAX-ACCESS  read-only
        STATUS  current
        DESCRIPTION
            "nexthop address"
        ::= { zxr10nexthopEntry 5 }

zxr10nexthopNextHopSlave OBJECT-TYPE
        SYNTAX  INTEGER {false(255),true(1)}
        MAX-ACCESS  read-only
        STATUS  current
        DESCRIPTION
            "nexthop slave"
        ::= { zxr10nexthopEntry 6 }

zxr10nexthopFallbackGlobal OBJECT-TYPE
        SYNTAX  INTEGER {false(255),true(1)}
        MAX-ACCESS  read-only
        STATUS  current
        DESCRIPTION
            "the global instance of nexthop fallback"
        ::= { zxr10nexthopEntry 7 }

zxr10nexthopFallbackVrfName OBJECT-TYPE
        SYNTAX DisplayString (SIZE (0..32))
        MAX-ACCESS  read-only
        STATUS  current
        DESCRIPTION
            "the VRF name of nexthop fallback"
        ::= { zxr10nexthopEntry 8 }

zxr10nexthopTrackName OBJECT-TYPE
        SYNTAX DisplayString (SIZE (0..31))
        MAX-ACCESS  read-only
        STATUS  current
        DESCRIPTION
            "nexthop track name"
        ::= { zxr10nexthopEntry 9 }

zxr10mrMonitorRouteTable OBJECT-TYPE
        SYNTAX  SEQUENCE OF Zxr10mrMonitorRouteEntry
        MAX-ACCESS  not-accessible
        STATUS  current
        DESCRIPTION
            "A table to monitor route"
        ::= { zxr10mrInstanceMIB 4 }

zxr10mrMonitorRouteEntry OBJECT-TYPE
        SYNTAX Zxr10mrMonitorRouteEntry
        MAX-ACCESS  not-accessible
        STATUS  current
        DESCRIPTION
            "An entry to monitor route"
        INDEX  { zxr10mrMonitorRouteVrfName,
        zxr10mrMonitorRouteMrMonitorIntf,
        zxr10mrMonitorRouteMrMoniterSource,
        zxr10mrMonitorRouteMrMonitorGroup }
        ::= { zxr10mrMonitorRouteTable 1 }

Zxr10mrMonitorRouteEntry ::=
        SEQUENCE {
            zxr10mrMonitorRouteVrfName
                DisplayString,
            zxr10mrMonitorRouteMrMonitorIntf
                DisplayString,
            zxr10mrMonitorRouteMrMoniterSource
                IpAddress,
            zxr10mrMonitorRouteMrMonitorGroup
                IpAddress
        }

zxr10mrMonitorRouteVrfName OBJECT-TYPE      
        SYNTAX DisplayString (SIZE (0..32))
        MAX-ACCESS  read-only
        STATUS  current
        DESCRIPTION
            "vrf name"
        ::= { zxr10mrMonitorRouteEntry 1 }

zxr10mrMonitorRouteMrMonitorIntf OBJECT-TYPE
        SYNTAX DisplayString (SIZE (0..32))
        MAX-ACCESS  read-only
        STATUS  current
        DESCRIPTION
            "monitor interface"
        ::= { zxr10mrMonitorRouteEntry 2 }

zxr10mrMonitorRouteMrMoniterSource OBJECT-TYPE
        SYNTAX IpAddress
        MAX-ACCESS  read-only
        STATUS  current
        DESCRIPTION
            "monitor source"
        ::= { zxr10mrMonitorRouteEntry 3 }

zxr10mrMonitorRouteMrMonitorGroup OBJECT-TYPE
        SYNTAX IpAddress
        MAX-ACCESS  read-only
        STATUS  current
        DESCRIPTION
            "group address"
        ::= { zxr10mrMonitorRouteEntry 4 }

zxr10mdtDataTable OBJECT-TYPE
        SYNTAX  SEQUENCE OF Zxr10mdtDataEntry
        MAX-ACCESS  not-accessible
        STATUS  current
        DESCRIPTION
            "A table to data mdt"
        ::= { zxr10mrInstanceMIB 5 }

zxr10mdtDataEntry OBJECT-TYPE
        SYNTAX Zxr10mdtDataEntry
        MAX-ACCESS  not-accessible
        STATUS  current
        DESCRIPTION
            "An entry to data mdt"
        INDEX  { zxr10mdtDataVrfName }
        ::= { zxr10mdtDataTable 1 }

Zxr10mdtDataEntry ::=
        SEQUENCE {
            zxr10mdtDataVrfName
                DisplayString,
            zxr10mdtDataMdtDataAclname
                DisplayString,
            zxr10mdtDataMdtDataGroupAddr
                IpAddress,
            zxr10mdtDataMdtDataGroupMask
                IpAddress,
            zxr10mdtDataMdtDataThreshold
                Unsigned32,
            zxr10mdtDataMdtDataNumTree
                Unsigned32
        }

zxr10mdtDataVrfName OBJECT-TYPE
        SYNTAX DisplayString (SIZE (0..32))
        MAX-ACCESS  read-only
        STATUS  current
        DESCRIPTION
            "vrf name"
        ::= { zxr10mdtDataEntry 1 }

zxr10mdtDataMdtDataAclname OBJECT-TYPE
        SYNTAX DisplayString (SIZE (0..31))
        MAX-ACCESS  read-only
        STATUS  current
        DESCRIPTION
            "mdt ACL name"
        ::= { zxr10mdtDataEntry 2 }

zxr10mdtDataMdtDataGroupAddr OBJECT-TYPE
        SYNTAX IpAddress
        MAX-ACCESS  read-only
        STATUS  current
        DESCRIPTION
            "mdt group"
        ::= { zxr10mdtDataEntry 3 }

zxr10mdtDataMdtDataGroupMask OBJECT-TYPE
        SYNTAX IpAddress
        MAX-ACCESS  read-only
        STATUS  current
        DESCRIPTION
            "mdt group mask"
        ::= { zxr10mdtDataEntry 4 }

zxr10mdtDataMdtDataThreshold OBJECT-TYPE
        SYNTAX Unsigned32 (0..1)
        MAX-ACCESS  read-only
        STATUS  obsolete
        DESCRIPTION
            "mdt switch threshold"
        ::= { zxr10mdtDataEntry 5 }

zxr10mdtDataMdtDataNumTree OBJECT-TYPE
        SYNTAX Unsigned32 (1..5000)
        MAX-ACCESS  read-only
        STATUS  current
        DESCRIPTION
            "mdt number tree"
        ::= { zxr10mdtDataEntry 6 }

zxr10mdtDefaultTable OBJECT-TYPE
        SYNTAX  SEQUENCE OF Zxr10mdtDefaultEntry
        MAX-ACCESS  not-accessible
        STATUS  current
        DESCRIPTION
            "A table to default mdt"
        ::= { zxr10mrInstanceMIB 6 }

zxr10mdtDefaultEntry OBJECT-TYPE
        SYNTAX Zxr10mdtDefaultEntry
        MAX-ACCESS  not-accessible
        STATUS  current
        DESCRIPTION
            "An entry to default mdt"
        INDEX  { zxr10mdtDefaultVrfName }
        ::= { zxr10mdtDefaultTable 1 }

Zxr10mdtDefaultEntry ::=
        SEQUENCE {
            zxr10mdtDefaultVrfName
                DisplayString,
            zxr10mdtDefaultMdtDefaultGroupAddr
                IpAddress,
            zxr10mdtDefaultMdtRootAddr
                IpAddress
        }

zxr10mdtDefaultVrfName OBJECT-TYPE
        SYNTAX DisplayString (SIZE (0..32))
        MAX-ACCESS  read-only
        STATUS  current
        DESCRIPTION
            "vrf name"
        ::= { zxr10mdtDefaultEntry 1 }

zxr10mdtDefaultMdtDefaultGroupAddr OBJECT-TYPE
        SYNTAX IpAddress
        MAX-ACCESS  read-only
        STATUS  current
        DESCRIPTION
            "default mdt group"
        ::= { zxr10mdtDefaultEntry 2 }

zxr10mdtDefaultMdtRootAddr OBJECT-TYPE
        SYNTAX IpAddress
        MAX-ACCESS  read-only
        STATUS  current
        DESCRIPTION
            "root addr"
        ::= { zxr10mdtDefaultEntry 3 }

zxr10mrMonitorIntfTable OBJECT-TYPE
        SYNTAX  SEQUENCE OF Zxr10mrMonitorIntfEntry
        MAX-ACCESS  not-accessible
        STATUS  current
        DESCRIPTION
            "A table to monitor interface"
        ::= { zxr10mrInstanceMIB 7 }

zxr10mrMonitorIntfEntry OBJECT-TYPE
        SYNTAX Zxr10mrMonitorIntfEntry
        MAX-ACCESS  not-accessible
        STATUS  current
        DESCRIPTION
            "An entry to monitor interface"
        INDEX  { zxr10mrMonitorIntfVrfName,zxr10mrMonitorIntfIntfname }
        ::= { zxr10mrMonitorIntfTable 1 }

Zxr10mrMonitorIntfEntry ::=
        SEQUENCE {
            zxr10mrMonitorIntfVrfName
                DisplayString,
            zxr10mrMonitorIntfIntfname
                DisplayString
        }

zxr10mrMonitorIntfVrfName OBJECT-TYPE
        SYNTAX DisplayString (SIZE (0..32))
        MAX-ACCESS  read-only
        STATUS  current
        DESCRIPTION
            "vrf name"
        ::= { zxr10mrMonitorIntfEntry 1 }

zxr10mrMonitorIntfIntfname OBJECT-TYPE
        SYNTAX DisplayString (SIZE (0..32))
        MAX-ACCESS  read-only
        STATUS  current
        DESCRIPTION
            "interface name"
        ::= { zxr10mrMonitorIntfEntry 2 }

zxr10pimsmInstMIB OBJECT IDENTIFIER ::= { zxr10mrInstanceMIB 8 }

zxr10pimsmInstTable OBJECT-TYPE
        SYNTAX  SEQUENCE OF Zxr10pimsmInstEntry
        MAX-ACCESS  not-accessible
        STATUS  current
        DESCRIPTION
            "A table to PIMSM instance"
        ::= { zxr10pimsmInstMIB 1 }

zxr10pimsmInstEntry OBJECT-TYPE
        SYNTAX Zxr10pimsmInstEntry
        MAX-ACCESS  not-accessible
        STATUS  current
        DESCRIPTION
            "An entry to PIMSM instance"
        INDEX  { zxr10pimsmInstVrfName }
        ::= { zxr10pimsmInstTable 1 }
  
Zxr10pimsmInstEntry ::=
        SEQUENCE {
            zxr10pimsmInstVrfName
                DisplayString,
            zxr10pimsmInstRouterPimsm
                Unsigned32,
            zxr10pimsmInstSrpOverride
                Unsigned32,
            zxr10pimsmInstSrpSmartswitch
                Unsigned32,
            zxr10pimsmInstBsmUnicast
                Unsigned32,
            zxr10pimsmInstSsmEnable
                Unsigned32,
            zxr10pimsmInstSsmDefault
                Unsigned32,
            zxr10pimsmInstDrSwitchDelayValue
                Unsigned32,
            zxr10pimsmInstSsmDataAclName
                DisplayString,
            zxr10pimsmInstAcceptRpAclName
                DisplayString,
            zxr10pimsmInstRegFilterAclName
                DisplayString,
            zxr10pimsmInstDataFilterAclName
                DisplayString,
            zxr10pimsmInstJpHoldtime
                Unsigned32,
            zxr10pimsmInstRpProxy
                Unsigned32,
            zxr10pimsmInstRegProbeInterval
                Unsigned32,
            zxr10pimsmInstRegSuppressionInterval
                Unsigned32,
            zxr10pimsmInstBidirPim
                INTEGER,
            zxr10pimsmInstJpInterval
                Unsigned32,
            zxr10pimsmInstRegHoldtime
                Unsigned32,
            zxr10pimsmInstMofrrAclName
                DisplayString,
            zxr10pimsmInstMldpSignalEn
                INTEGER,
            zxr10pimsmInstMldpSignalAclName
                DisplayString,
            zxr10pimsmInstJpSpeed
                Unsigned32,
            zxr10pimsmInstKeepAlivePeriod
                Unsigned32,
            zxr10pimsmInstAssertHoldTime
                Unsigned32,
            zxr10pimsmInstGraftTime
                Unsigned32,
            zxr10pimsmInstCbsrHoldtime
                Unsigned32,
            zxr10pimsmInstCbsrInterval
                Unsigned32,
            zxr10pimsmInstPimdmReg
                INTEGER,
            zxr10pimsmInstStatisticsAclName
                DisplayString
        }

zxr10pimsmInstVrfName OBJECT-TYPE              
        SYNTAX DisplayString (SIZE (0..32))
        MAX-ACCESS  read-only
        STATUS  current
        DESCRIPTION
            "vrf name"
        ::= { zxr10pimsmInstEntry 1 }

zxr10pimsmInstRouterPimsm OBJECT-TYPE
        SYNTAX Unsigned32 (0..1)
        MAX-ACCESS  read-only
        STATUS  current
        DESCRIPTION
            "enable PIMSM"
        ::= { zxr10pimsmInstEntry 2 }

zxr10pimsmInstSrpOverride OBJECT-TYPE
        SYNTAX Unsigned32 (0..1)
        MAX-ACCESS  read-only
        STATUS  current
        DESCRIPTION
            "enable static RP override"
        ::= { zxr10pimsmInstEntry 3 }

zxr10pimsmInstSrpSmartswitch OBJECT-TYPE
        SYNTAX Unsigned32 (0..1)
        MAX-ACCESS  read-only
        STATUS  current
        DESCRIPTION
            "enable static RP smart switch"
        ::= { zxr10pimsmInstEntry 4 }

zxr10pimsmInstBsmUnicast OBJECT-TYPE
        SYNTAX Unsigned32 (0..1)
        MAX-ACCESS  read-only
        STATUS  current
        DESCRIPTION
            "unicast bsm"
        ::= { zxr10pimsmInstEntry 5 }

zxr10pimsmInstSsmEnable OBJECT-TYPE
        SYNTAX Unsigned32 (0..1)
        MAX-ACCESS  read-only
        STATUS  current
        DESCRIPTION
            "enable SSM"
        ::= { zxr10pimsmInstEntry 6 }

zxr10pimsmInstSsmDefault OBJECT-TYPE
        SYNTAX Unsigned32 (0..1)
        MAX-ACCESS  read-only
        STATUS  current
        DESCRIPTION
            "ssm default group"
        ::= { zxr10pimsmInstEntry 7 }

zxr10pimsmInstDrSwitchDelayValue OBJECT-TYPE
        SYNTAX Unsigned32 (0..300)
        MAX-ACCESS  read-only
        STATUS  current
        DESCRIPTION
            "dr switch delay value in case of bfd enable"
        ::= { zxr10pimsmInstEntry 8 }

zxr10pimsmInstSsmDataAclName OBJECT-TYPE
        SYNTAX DisplayString (SIZE (0..31))
        MAX-ACCESS  read-only
        STATUS  current
        DESCRIPTION
            "ssm data ACL name"
        ::= { zxr10pimsmInstEntry 9 }

zxr10pimsmInstAcceptRpAclName OBJECT-TYPE
        SYNTAX DisplayString (SIZE (0..31))
        MAX-ACCESS  read-only
        STATUS  current
        DESCRIPTION
            "accept RP ACL name"
        ::= { zxr10pimsmInstEntry 10 }

zxr10pimsmInstRegFilterAclName OBJECT-TYPE
        SYNTAX DisplayString (SIZE (0..31))
        MAX-ACCESS  read-only
        STATUS  current
        DESCRIPTION
            "register packet filter ACL name"
        ::= { zxr10pimsmInstEntry 11 }

zxr10pimsmInstDataFilterAclName OBJECT-TYPE
        SYNTAX DisplayString (SIZE (0..31))
        MAX-ACCESS  read-only
        STATUS  current
        DESCRIPTION
            "PIM source filter ACL name"
        ::= { zxr10pimsmInstEntry 12 }

zxr10pimsmInstJpHoldtime OBJECT-TYPE
        SYNTAX Unsigned32 (210..65535)
        MAX-ACCESS  read-only
        STATUS  current
        DESCRIPTION
            "J/P packet hold time"
        ::= { zxr10pimsmInstEntry 13 }

zxr10pimsmInstRpProxy OBJECT-TYPE
        SYNTAX Unsigned32 (0..1)
        MAX-ACCESS  read-only
        STATUS  current
        DESCRIPTION
            "RP proxy"
        ::= { zxr10pimsmInstEntry 14 }

zxr10pimsmInstRegProbeInterval OBJECT-TYPE
        SYNTAX Unsigned32 (1..210)
        MAX-ACCESS  read-only
        STATUS  current
        DESCRIPTION
            "register probe interval"
        ::= { zxr10pimsmInstEntry 15 }

zxr10pimsmInstRegSuppressionInterval OBJECT-TYPE
        SYNTAX Unsigned32 (60..3600)
        MAX-ACCESS  read-only
        STATUS  current
        DESCRIPTION
            "register suppression interval"
        ::= { zxr10pimsmInstEntry 16 }

zxr10pimsmInstBidirPim OBJECT-TYPE
        SYNTAX INTEGER {false(255),true(1)}
        MAX-ACCESS  read-only
        STATUS  current
        DESCRIPTION
            "bidir PIM"
        ::= { zxr10pimsmInstEntry 17 }

zxr10pimsmInstJpInterval OBJECT-TYPE
        SYNTAX Unsigned32 (10..6000)
        MAX-ACCESS  read-only
        STATUS  current
        DESCRIPTION
            "J/P packet interval"
        ::= { zxr10pimsmInstEntry 18 }

zxr10pimsmInstRegHoldtime OBJECT-TYPE
        SYNTAX Unsigned32 (1..600)
        MAX-ACCESS  read-only
        STATUS  current
        DESCRIPTION
            "Register hold time without receiving register stop packet"
        ::= { zxr10pimsmInstEntry 19 }

zxr10pimsmInstMofrrAclName OBJECT-TYPE
        SYNTAX DisplayString (SIZE (0..31))
        MAX-ACCESS  read-only
        STATUS  current
        DESCRIPTION
            "mofrr ACL name"
        ::= { zxr10pimsmInstEntry 20 }

zxr10pimsmInstMldpSignalEn OBJECT-TYPE
        SYNTAX INTEGER {false(255),true(1)}
        MAX-ACCESS  read-only
        STATUS  current
        DESCRIPTION
            "PIM mldp signal enable"
        ::= { zxr10pimsmInstEntry 21 }
        
 zxr10pimsmInstMldpSignalAclName OBJECT-TYPE
        SYNTAX DisplayString (SIZE (0..31))
        MAX-ACCESS  read-only
        STATUS  current
        DESCRIPTION
            "PIM mldp signal ACL name"
        ::= { zxr10pimsmInstEntry 22 }    

zxr10pimsmInstJpSpeed OBJECT-TYPE
        SYNTAX Unsigned32 (1000..50000)
        MAX-ACCESS  read-only
        STATUS  current
        DESCRIPTION
            "PIM Join/Prune speed"
        ::= { zxr10pimsmInstEntry 23 }
            
zxr10pimsmInstKeepAlivePeriod OBJECT-TYPE
        SYNTAX Unsigned32 (60..65535)
        MAX-ACCESS  read-only
        STATUS  current
        DESCRIPTION
            "PIM keepalive period"
        ::= { zxr10pimsmInstEntry 24 }
            
zxr10pimsmInstAssertHoldTime OBJECT-TYPE
        SYNTAX Unsigned32 (60..65535)
        MAX-ACCESS  read-only
        STATUS  current
        DESCRIPTION
            "PIM assert holdtime"
        ::= { zxr10pimsmInstEntry 25 }
            
zxr10pimsmInstGraftTime OBJECT-TYPE
        SYNTAX Unsigned32 (1..65535)
        MAX-ACCESS  read-only
        STATUS  current
        DESCRIPTION
            "PIM graft retry time"
        ::= { zxr10pimsmInstEntry 26 }

zxr10pimsmInstCbsrHoldtime OBJECT-TYPE
        SYNTAX Unsigned32 (130..65535)
        MAX-ACCESS  read-only
        STATUS  current
        DESCRIPTION
            "C-BSR holdtime"
        ::= { zxr10pimsmInstEntry 27 }

zxr10pimsmInstCbsrInterval OBJECT-TYPE
        SYNTAX Unsigned32 (10..65535)
        MAX-ACCESS  read-only
        STATUS  current
        DESCRIPTION
            "C-BSR interval"
        ::= { zxr10pimsmInstEntry 28 }

zxr10pimsmInstPimdmReg OBJECT-TYPE
        SYNTAX INTEGER {false(255),true(1)}
        MAX-ACCESS  read-only
        STATUS  current
        DESCRIPTION
            "Send register packets when the PIM-DM interface receives 
             indirectly connected stream"
        ::= { zxr10pimsmInstEntry 29 }

zxr10pimsmInstStatisticsAclName OBJECT-TYPE
        SYNTAX DisplayString (SIZE (0..31))
        MAX-ACCESS  read-only
        STATUS  current
        DESCRIPTION
            "PIM packet statistics ACL name"
        ::= { zxr10pimsmInstEntry 30 }

zxr10pimsmIntfTable OBJECT-TYPE
        SYNTAX  SEQUENCE OF Zxr10pimsmIntfEntry
        MAX-ACCESS  not-accessible
        STATUS  current
        DESCRIPTION
            "A table to PIMSM interface"
        ::= { zxr10pimsmInstMIB 2 }

zxr10pimsmIntfEntry OBJECT-TYPE
        SYNTAX Zxr10pimsmIntfEntry
        MAX-ACCESS  not-accessible
        STATUS  current
        DESCRIPTION
            "An entry to PIMSM interface"
        INDEX  { zxr10pimsmIntfVrfName,zxr10pimsmIntfName }
        ::= { zxr10pimsmIntfTable 1 }

Zxr10pimsmIntfEntry ::=
        SEQUENCE {
            zxr10pimsmIntfVrfName
                DisplayString,
            zxr10pimsmIntfName
                DisplayString,
            zxr10pimsmIntfPimsm
                Unsigned32,
            zxr10pimsmIntfAssertDisable
                Unsigned32,
            zxr10pimsmIntfBfdEnable
                Unsigned32,
            zxr10pimsmIntfBsrBorder
                Unsigned32,
            zxr10pimsmIntfDrPriority
                Unsigned32,
            zxr10pimsmIntfNbrFilterAclName
                DisplayString,
            zxr10pimsmIntfHelloInterval
                Unsigned32,
            zxr10pimsmIntfPimDm
                Unsigned32,
            zxr10pimsmIntfSilent
                Unsigned32,
            zxr10pimsmIntfDrIgnore
                Unsigned32,
            zxr10pimsmInterfaceVrfName
                DisplayString,
            zxr10pimsmInterfaceFrrEn
                INTEGER,
            zxr10pimsmIntfPropagationDelay
                Unsigned32,
            zxr10pimsmIntfOverrideInterval
                Unsigned32,
            zxr10pimsmIntfJpMaxpktLen
                Unsigned32,
            zxr10pimsmIntfHelloDrAddr
                INTEGER,
            zxr10pimsmIntfHelloTrackSupport
                INTEGER
        }

zxr10pimsmIntfVrfName OBJECT-TYPE
        SYNTAX DisplayString (SIZE (0..32))
        MAX-ACCESS  read-only
        STATUS  current
        DESCRIPTION
            "vrf name"
        ::= { zxr10pimsmIntfEntry 1 }

zxr10pimsmIntfName OBJECT-TYPE
        SYNTAX DisplayString (SIZE (0..32))
        MAX-ACCESS  read-only
        STATUS  current
        DESCRIPTION
            "interface name"
        ::= { zxr10pimsmIntfEntry 2 }

zxr10pimsmIntfPimsm OBJECT-TYPE
        SYNTAX Unsigned32 (0..1)
        MAX-ACCESS  read-only
        STATUS  current
        DESCRIPTION
            "enable PIMSM"
        ::= { zxr10pimsmIntfEntry 3 }

zxr10pimsmIntfAssertDisable OBJECT-TYPE
        SYNTAX Unsigned32 (0..1)
        MAX-ACCESS  read-only
        STATUS  current
        DESCRIPTION
            "assert disable"
        ::= { zxr10pimsmIntfEntry 4 }

zxr10pimsmIntfBfdEnable OBJECT-TYPE
        SYNTAX Unsigned32 (0..1)
        MAX-ACCESS  read-only
        STATUS  current
        DESCRIPTION
            "enable BFD"
        ::= { zxr10pimsmIntfEntry 5 }

zxr10pimsmIntfBsrBorder OBJECT-TYPE
        SYNTAX Unsigned32 (0..1)
        MAX-ACCESS  read-only
        STATUS  current
        DESCRIPTION
            "BSR border"
        ::= { zxr10pimsmIntfEntry 6 }

zxr10pimsmIntfDrPriority OBJECT-TYPE
        SYNTAX Unsigned32  (0..4294967295)
        MAX-ACCESS  read-only
        STATUS  current
        DESCRIPTION
            "dr priority"
        ::= { zxr10pimsmIntfEntry 7 }

zxr10pimsmIntfNbrFilterAclName OBJECT-TYPE
        SYNTAX DisplayString (SIZE (0..31))
        MAX-ACCESS  read-only
        STATUS  current
        DESCRIPTION
            "pimsm neighbour filter"
        ::= { zxr10pimsmIntfEntry 8 }

zxr10pimsmIntfHelloInterval OBJECT-TYPE
        SYNTAX Unsigned32 (1..65535)
        MAX-ACCESS  read-only
        STATUS  current
        DESCRIPTION
            "hello packet interval"
        ::= { zxr10pimsmIntfEntry 9 }

zxr10pimsmIntfPimDm OBJECT-TYPE
        SYNTAX Unsigned32 (0..1)
        MAX-ACCESS  read-only
        STATUS  current
        DESCRIPTION
            "dense mode"
        ::= { zxr10pimsmIntfEntry 10 }

zxr10pimsmIntfSilent OBJECT-TYPE
        SYNTAX Unsigned32 (0..1)
        MAX-ACCESS  read-only
        STATUS  current
        DESCRIPTION
            "PIM silent"
        ::= { zxr10pimsmIntfEntry 11 }

zxr10pimsmIntfDrIgnore OBJECT-TYPE   
        SYNTAX Unsigned32 (0..1)
        MAX-ACCESS  read-only
        STATUS  current
        DESCRIPTION
            "dr ignore"
        ::= { zxr10pimsmIntfEntry 12 }

zxr10pimsmInterfaceVrfName OBJECT-TYPE
        SYNTAX DisplayString (SIZE (0..32))
        MAX-ACCESS  read-only
        STATUS  current
        DESCRIPTION
            "interface vrf name"
        ::= { zxr10pimsmIntfEntry 13 }

zxr10pimsmInterfaceFrrEn OBJECT-TYPE
        SYNTAX INTEGER {false(255),true(1)}
        MAX-ACCESS  read-only
        STATUS  current
        DESCRIPTION
            "PIM frr enable"
        ::= { zxr10pimsmIntfEntry 14 }

zxr10pimsmIntfPropagationDelay OBJECT-TYPE
        SYNTAX Unsigned32 (1..100)
        MAX-ACCESS  read-only
        STATUS  current
        DESCRIPTION
            "propagation delay"
        ::= { zxr10pimsmIntfEntry 15 }

zxr10pimsmIntfOverrideInterval OBJECT-TYPE
        SYNTAX Unsigned32 (1..600)
        MAX-ACCESS  read-only
        STATUS  current
        DESCRIPTION
            "override interval"
        ::= { zxr10pimsmIntfEntry 16 }

zxr10pimsmIntfJpMaxpktLen OBJECT-TYPE
        SYNTAX Unsigned32 (100..8100)
        MAX-ACCESS  read-only
        STATUS  current
        DESCRIPTION
            "max length of PIM Join/Prune packet"
        ::= { zxr10pimsmIntfEntry 17 }

zxr10pimsmIntfHelloDrAddr OBJECT-TYPE
        SYNTAX INTEGER {false(255),true(1)}
        MAX-ACCESS  read-only
        STATUS  current
        DESCRIPTION
            "PIM hello packet sent with hello DR address"
        ::= { zxr10pimsmIntfEntry 18 }

zxr10pimsmIntfHelloTrackSupport OBJECT-TYPE
        SYNTAX INTEGER {false(255),true(1)}
        MAX-ACCESS  read-only
        STATUS  current
        DESCRIPTION
            "PIM hello tracking support enable"
        ::= { zxr10pimsmIntfEntry 19 }

zxr10pimsmBsrTable OBJECT-TYPE
        SYNTAX  SEQUENCE OF Zxr10pimsmBsrEntry
        MAX-ACCESS  not-accessible
        STATUS  current
        DESCRIPTION
            "A table to BSR"
        ::= { zxr10pimsmInstMIB 3 }

zxr10pimsmBsrEntry OBJECT-TYPE
        SYNTAX Zxr10pimsmBsrEntry
        MAX-ACCESS  not-accessible
        STATUS  current
        DESCRIPTION
            "An entry to BSR"
        INDEX  { zxr10pimsmBsrVrfName }
        ::= { zxr10pimsmBsrTable 1 }
            
Zxr10pimsmBsrEntry ::=
        SEQUENCE {
            zxr10pimsmBsrVrfName
                DisplayString,
            zxr10pimsmBsrIfName
                DisplayString,
            zxr10pimsmBsrPriority
                Unsigned32,
            zxr10pimsmBsrHashLen
                Unsigned32,
            zxr10pimsmBsrIntfVrfName
                DisplayString
        }

zxr10pimsmBsrVrfName OBJECT-TYPE
        SYNTAX DisplayString (SIZE (0..32))
        MAX-ACCESS  read-only
        STATUS  current
        DESCRIPTION
            "vrf name"
        ::= { zxr10pimsmBsrEntry 1 }

zxr10pimsmBsrIfName OBJECT-TYPE
        SYNTAX DisplayString (SIZE (0..32))
        MAX-ACCESS  read-only
        STATUS  current
        DESCRIPTION
            "interface name"
        ::= { zxr10pimsmBsrEntry 2 }

zxr10pimsmBsrPriority OBJECT-TYPE
        SYNTAX Unsigned32 (0..255)
        MAX-ACCESS  read-only
        STATUS  current
        DESCRIPTION
            "BSR priority"
        ::= { zxr10pimsmBsrEntry 3 }

zxr10pimsmBsrHashLen OBJECT-TYPE
        SYNTAX Unsigned32 (0..32)
        MAX-ACCESS  read-only
        STATUS  current
        DESCRIPTION
            "BSR hash mask length"
        ::= { zxr10pimsmBsrEntry 4 }

zxr10pimsmBsrIntfVrfName OBJECT-TYPE
        SYNTAX DisplayString (SIZE (0..32))
        MAX-ACCESS  read-only
        STATUS  current
        DESCRIPTION
            "interface vrf name"
        ::= { zxr10pimsmBsrEntry 5 }

zxr10pimsmCrpTable OBJECT-TYPE
        SYNTAX  SEQUENCE OF Zxr10pimsmCrpEntry
        MAX-ACCESS  not-accessible
        STATUS  current
        DESCRIPTION
            "A table to candidate RP"
        ::= { zxr10pimsmInstMIB 4 }

zxr10pimsmCrpEntry OBJECT-TYPE
        SYNTAX Zxr10pimsmCrpEntry
        MAX-ACCESS  not-accessible
        STATUS  current
        DESCRIPTION
            "An entry to candidate RP"
        INDEX  { zxr10pimsmCrpVrfName,zxr10pimsmCrpIntfName }
        ::= { zxr10pimsmCrpTable 1 }
            
Zxr10pimsmCrpEntry ::=
        SEQUENCE {
            zxr10pimsmCrpVrfName
                DisplayString,
            zxr10pimsmCrpIntfName
                DisplayString,
            zxr10pimsmCrpPrefixList
                DisplayString,
            zxr10pimsmCrpPriority
                Unsigned32,
            zxr10pimsmCrpIntfVrfName
                DisplayString,
            zxr10pimsmCrpBidirPim
                INTEGER,
            zxr10pimsmCrpHoldtime
                Unsigned32
        }

zxr10pimsmCrpVrfName OBJECT-TYPE
        SYNTAX DisplayString (SIZE (0..32))
        MAX-ACCESS  read-only
        STATUS  current
        DESCRIPTION
            "vrf name"
        ::= { zxr10pimsmCrpEntry 1 }

zxr10pimsmCrpIntfName OBJECT-TYPE
        SYNTAX DisplayString (SIZE (0..32))
        MAX-ACCESS  read-only
        STATUS  current
        DESCRIPTION
            "interface name"
        ::= { zxr10pimsmCrpEntry 2 }

zxr10pimsmCrpPrefixList OBJECT-TYPE
        SYNTAX DisplayString (SIZE (0..31))
        MAX-ACCESS  read-only
        STATUS  current
        DESCRIPTION
            "candidate RP prefix list"
        ::= { zxr10pimsmCrpEntry 3 }

zxr10pimsmCrpPriority OBJECT-TYPE
        SYNTAX Unsigned32 (0..255)
        MAX-ACCESS  read-only
        STATUS  current
        DESCRIPTION
            "candidate RP priority"
        ::= { zxr10pimsmCrpEntry 4 }

zxr10pimsmCrpIntfVrfName OBJECT-TYPE
        SYNTAX DisplayString (SIZE (0..32))
        MAX-ACCESS  read-only
        STATUS  current
        DESCRIPTION
            "interface vrf name"
        ::= { zxr10pimsmCrpEntry 5 }

zxr10pimsmCrpBidirPim OBJECT-TYPE
        SYNTAX INTEGER {false(255),true(1)}
        MAX-ACCESS  read-only
        STATUS  current
        DESCRIPTION
            "candidate RP bidir"
        ::= { zxr10pimsmCrpEntry 6 }

zxr10pimsmCrpHoldtime OBJECT-TYPE
        SYNTAX Unsigned32 (150..65535)
        MAX-ACCESS  read-only
        STATUS  current
        DESCRIPTION
            "candidate RP holdtime"
        ::= { zxr10pimsmCrpEntry 7 }

zxr10pimsmSrpTable OBJECT-TYPE
        SYNTAX  SEQUENCE OF Zxr10pimsmSrpEntry
        MAX-ACCESS  not-accessible
        STATUS  current
        DESCRIPTION
            "A table to static RP"
        ::= { zxr10pimsmInstMIB 5 }

zxr10pimsmSrpEntry OBJECT-TYPE
        SYNTAX Zxr10pimsmSrpEntry
        MAX-ACCESS  not-accessible
        STATUS  current
        DESCRIPTION
            "An entry to static RP"
        INDEX  { zxr10pimsmSrpVrfName,zxr10pimsmSrpIpAddr }
        ::= { zxr10pimsmSrpTable 1 }
            
Zxr10pimsmSrpEntry ::=
        SEQUENCE {
            zxr10pimsmSrpVrfName
                DisplayString,
            zxr10pimsmSrpIpAddr
                IpAddress,
            zxr10pimsmSrpPrefixList
                DisplayString,
            zxr10pimsmSrpPriority
                Unsigned32,
            zxr10pimsmSrpBidirPim
                INTEGER
        }

zxr10pimsmSrpVrfName OBJECT-TYPE
        SYNTAX DisplayString (SIZE (0..32))
        MAX-ACCESS  read-only
        STATUS  current
        DESCRIPTION
            "vrf name"
        ::= { zxr10pimsmSrpEntry 1 }

zxr10pimsmSrpIpAddr OBJECT-TYPE
        SYNTAX IpAddress
        MAX-ACCESS  read-only
        STATUS  current
        DESCRIPTION
            "static RP ip address"
        ::= { zxr10pimsmSrpEntry 2 }

zxr10pimsmSrpPrefixList OBJECT-TYPE
        SYNTAX DisplayString (SIZE (0..31))
        MAX-ACCESS  read-only
        STATUS  current
        DESCRIPTION
            "static RP prefix list"
        ::= { zxr10pimsmSrpEntry 3 }

zxr10pimsmSrpPriority OBJECT-TYPE
        SYNTAX Unsigned32 (0..255)
        MAX-ACCESS  read-only
        STATUS  current
        DESCRIPTION
            "static RP priority"
        ::= { zxr10pimsmSrpEntry 4 }

zxr10pimsmSrpBidirPim OBJECT-TYPE
        SYNTAX INTEGER {false(255),true(1)}
        MAX-ACCESS  read-only
        STATUS  current
        DESCRIPTION
            "static RP bidir"
        ::= { zxr10pimsmSrpEntry 5 }

zxr10pimsmArpPeerTable OBJECT-TYPE
        SYNTAX  SEQUENCE OF Zxr10pimsmArpPeerEntry
        MAX-ACCESS  not-accessible
        STATUS  current
        DESCRIPTION
            "A table to pimsm anycast-RP peer"
        ::= { zxr10pimsmInstMIB 6 }

zxr10pimsmArpPeerEntry OBJECT-TYPE
        SYNTAX Zxr10pimsmArpPeerEntry
        MAX-ACCESS  not-accessible
        STATUS  current
        DESCRIPTION
            "An entry to pimsm anycast-RP peer"
        INDEX  { zxr10pimsmArpPeerVrfName,zxr10pimsmArpPeerIpAddr }
        ::= { zxr10pimsmArpPeerTable 1 }

Zxr10pimsmArpPeerEntry ::=
        SEQUENCE {
            zxr10pimsmArpPeerVrfName
                DisplayString,
            zxr10pimsmArpPeerIpAddr
                IpAddress
        }

zxr10pimsmArpPeerVrfName OBJECT-TYPE
        SYNTAX DisplayString (SIZE (0..32))
        MAX-ACCESS  read-only
        STATUS  current
        DESCRIPTION
            "vrf name"
        ::= { zxr10pimsmArpPeerEntry 1 }

zxr10pimsmArpPeerIpAddr OBJECT-TYPE
        SYNTAX IpAddress
        MAX-ACCESS  read-only
        STATUS  current
        DESCRIPTION
            "anycast-RP peer address"
        ::= { zxr10pimsmArpPeerEntry 2 }

zxr10pimsmSptTable OBJECT-TYPE
        SYNTAX  SEQUENCE OF Zxr10pimsmSptEntry
        MAX-ACCESS  not-accessible
        STATUS  current
        DESCRIPTION
            "A table to SPT switch"
        ::= { zxr10pimsmInstMIB 7 }

zxr10pimsmSptEntry OBJECT-TYPE
        SYNTAX Zxr10pimsmSptEntry
        MAX-ACCESS  not-accessible
        STATUS  current
        DESCRIPTION
            "An entry to SPT switch"
        INDEX  { zxr10pimsmSptVrfName }
        ::= { zxr10pimsmSptTable 1 }
            
Zxr10pimsmSptEntry ::=
        SEQUENCE {
            zxr10pimsmSptVrfName
                DisplayString,
            zxr10pimsmSptAcl
                DisplayString,
            zxr10pimsmSptThreshold
                Unsigned32,
            zxr10pimsmSptInfinity
                Unsigned32
        }

zxr10pimsmSptVrfName OBJECT-TYPE
        SYNTAX DisplayString (SIZE (0..32))
        MAX-ACCESS  read-only
        STATUS  current
        DESCRIPTION
            "vrf name"
        ::= { zxr10pimsmSptEntry 1 }

zxr10pimsmSptAcl OBJECT-TYPE
        SYNTAX DisplayString (SIZE (0..31))
        MAX-ACCESS  read-only
        STATUS  current
        DESCRIPTION
            "SPT infinity ACL name"
        ::= { zxr10pimsmSptEntry 2 }

zxr10pimsmSptThreshold OBJECT-TYPE
        SYNTAX Unsigned32
        MAX-ACCESS  read-only
        STATUS  current
        DESCRIPTION
            "SPT threshold"
        ::= { zxr10pimsmSptEntry 3 }

zxr10pimsmSptInfinity OBJECT-TYPE
        SYNTAX Unsigned32 (0..1)
        MAX-ACCESS  read-only
        STATUS  current
        DESCRIPTION
            "SPT infinity"
        ::= { zxr10pimsmSptEntry 4 }

zxr10pimsmArpLocalTable OBJECT-TYPE
        SYNTAX  SEQUENCE OF Zxr10pimsmArpLocalEntry
        MAX-ACCESS  not-accessible
        STATUS  current
        DESCRIPTION
            "A table to ARP_LOCAL"
        ::= { zxr10pimsmInstMIB 8 }

zxr10pimsmArpLocalEntry OBJECT-TYPE
        SYNTAX Zxr10pimsmArpLocalEntry
        MAX-ACCESS  not-accessible
        STATUS  current
        DESCRIPTION
            "An entry to ARP_LOCAL"
        INDEX  { zxr10pimsmArpLocalVrfName }
        ::= { zxr10pimsmArpLocalTable 1 }
            
Zxr10pimsmArpLocalEntry ::=
        SEQUENCE {
            zxr10pimsmArpLocalVrfName
                DisplayString,
            zxr10pimsmArpLocalIntfName
                DisplayString,
            zxr10pimsmArpLocalIntfVrfName
                DisplayString
        }

zxr10pimsmArpLocalVrfName OBJECT-TYPE
        SYNTAX DisplayString (SIZE (0..32))
        MAX-ACCESS  read-only
        STATUS  current
        DESCRIPTION
            "vrf name"
        ::= { zxr10pimsmArpLocalEntry 1 }

zxr10pimsmArpLocalIntfName OBJECT-TYPE
        SYNTAX DisplayString (SIZE (0..32))
        MAX-ACCESS  read-only
        STATUS  current
        DESCRIPTION
            "anycast-RP local interface name"
        ::= { zxr10pimsmArpLocalEntry 2 }

zxr10pimsmArpLocalIntfVrfName OBJECT-TYPE
        SYNTAX DisplayString (SIZE (0..32))
        MAX-ACCESS  read-only
        STATUS  current
        DESCRIPTION
            "interface vrf name"
        ::= { zxr10pimsmArpLocalEntry 3 }
        
        
zxr10pimsmRegSourceTable OBJECT-TYPE
        SYNTAX  SEQUENCE OF Zxr10pimsmRegSourceEntry
        MAX-ACCESS  not-accessible
        STATUS  current
        DESCRIPTION
            "A table to register source"
        ::= { zxr10pimsmInstMIB 9 }

zxr10pimsmRegSourceEntry OBJECT-TYPE
        SYNTAX Zxr10pimsmRegSourceEntry
        MAX-ACCESS  not-accessible
        STATUS  current
        DESCRIPTION
            "An entry to register source"
        INDEX  { zxr10pimsmRegSourceVrfName }
        ::= { zxr10pimsmRegSourceTable 1 }
            
Zxr10pimsmRegSourceEntry ::=
        SEQUENCE {
            zxr10pimsmRegSourceVrfName
                DisplayString,
            zxr10pimsmRegSourceIntfName
                DisplayString            
        }

zxr10pimsmRegSourceVrfName OBJECT-TYPE
        SYNTAX DisplayString (SIZE (0..32))
        MAX-ACCESS  read-only
        STATUS  current
        DESCRIPTION
            "vrf name"
        ::= { zxr10pimsmRegSourceEntry 1 }

zxr10pimsmRegSourceIntfName OBJECT-TYPE
        SYNTAX DisplayString (SIZE (0..32))
        MAX-ACCESS  read-only
        STATUS  current
        DESCRIPTION
            "register source interface name"
        ::= { zxr10pimsmRegSourceEntry 2 }

zxr10pimGroupTable OBJECT-TYPE
        SYNTAX  SEQUENCE OF Zxr10pimGroupEntry
        MAX-ACCESS  not-accessible
        STATUS  current
        DESCRIPTION
            "A table to PIM group"
        ::= { zxr10pimsmInstMIB 10 }

zxr10pimGroupEntry OBJECT-TYPE
        SYNTAX Zxr10pimGroupEntry
        MAX-ACCESS  not-accessible
        STATUS  current
        DESCRIPTION
            "An entry to PIM group"
        INDEX  { zxr10pimGroupVrfName, zxr10pimGroupName }
        ::= { zxr10pimGroupTable 1 }

Zxr10pimGroupEntry ::=
        SEQUENCE {
            zxr10pimGroupVrfName
                DisplayString,
            zxr10pimGroupName
                DisplayString
        }

zxr10pimGroupVrfName OBJECT-TYPE
        SYNTAX DisplayString (SIZE (0..32))
        MAX-ACCESS  not-accessible
        STATUS  current
        DESCRIPTION
            "vrf name"
        ::= { zxr10pimGroupEntry 1 }

zxr10pimGroupName OBJECT-TYPE
        SYNTAX DisplayString (SIZE (0..31))
        MAX-ACCESS  read-only
        STATUS  current
        DESCRIPTION
            "PIM group name"
        ::= { zxr10pimGroupEntry 2 }


zxr10pimBindTable OBJECT-TYPE
        SYNTAX  SEQUENCE OF Zxr10pimBindEntry
        MAX-ACCESS  not-accessible
        STATUS  current
        DESCRIPTION
            "A table to PIM bind"
        ::= { zxr10pimsmInstMIB 11 }

zxr10pimBindEntry OBJECT-TYPE
        SYNTAX Zxr10pimBindEntry
        MAX-ACCESS  not-accessible
        STATUS  current
        DESCRIPTION
            "An entry to PIM bind"
        INDEX  { zxr10pimBindVrfName,
        zxr10pimBindGroupName,
        zxr10pimBindIntfName}
        ::= { zxr10pimBindTable 1 }
            
Zxr10pimBindEntry ::=
        SEQUENCE {
            zxr10pimBindVrfName
                DisplayString,
            zxr10pimBindGroupName
                DisplayString,
            zxr10pimBindIntfName
                DisplayString,
            zxr10pimBindIntfActive
                INTEGER,
            zxr10pimBindIntfPassive
                INTEGER
        }

zxr10pimBindVrfName OBJECT-TYPE
        SYNTAX DisplayString (SIZE (0..32))
        MAX-ACCESS  not-accessible
        STATUS  current
        DESCRIPTION
            "vrf name"
        ::= { zxr10pimBindEntry 1 }

zxr10pimBindGroupName OBJECT-TYPE
        SYNTAX DisplayString (SIZE (0..31))
        MAX-ACCESS  not-accessible
        STATUS  current
        DESCRIPTION
            "PIM group name"
        ::= { zxr10pimBindEntry 2 }

zxr10pimBindIntfName OBJECT-TYPE
        SYNTAX DisplayString (SIZE (0..32))
        MAX-ACCESS  not-accessible
        STATUS  current
        DESCRIPTION
            "PIM bind interface name"
        ::= { zxr10pimBindEntry 3 }

zxr10pimBindIntfActive OBJECT-TYPE
        SYNTAX INTEGER {false(255),true(1)} 
        MAX-ACCESS  read-only
        STATUS  current
        DESCRIPTION
            "If PIM group binds active interface,
             zxr10pimBindIntfActive is true,
             zxr10pimBindIntfPassive is false"
        ::= { zxr10pimBindEntry 4 }

zxr10pimBindIntfPassive OBJECT-TYPE
        SYNTAX INTEGER {false(255),true(2)} 
        MAX-ACCESS  read-only
        STATUS  current
        DESCRIPTION
            "If PIM group binds passive interface,
             zxr10pimBindIntfActive is false,
             zxr10pimBindIntfPassive is true"
        ::= { zxr10pimBindEntry 5 }


zxr10igmpInstMIB OBJECT IDENTIFIER ::= { zxr10mrInstanceMIB 10 }

zxr10igmpInstTable OBJECT-TYPE
        SYNTAX  SEQUENCE OF Zxr10igmpInstEntry
        MAX-ACCESS  not-accessible
        STATUS  current
        DESCRIPTION
            "A table to IGMP instance"
        ::= { zxr10igmpInstMIB 1 }

zxr10igmpInstEntry OBJECT-TYPE
        SYNTAX Zxr10igmpInstEntry
        MAX-ACCESS  not-accessible
        STATUS  current
        DESCRIPTION
            "An entry to IGMP instance"
        INDEX  { zxr10igmpInstVrfName }
        ::= { zxr10igmpInstTable 1 }
            
Zxr10igmpInstEntry ::=
        SEQUENCE {
            zxr10igmpInstVrfName
                DisplayString,
            zxr10igmpInstShapingNum
                Unsigned32,
            zxr10igmpInstProxyEnable
                Unsigned32,
            zxr10igmpInstRequireAlertOptions
                Unsigned32
        }

zxr10igmpInstVrfName OBJECT-TYPE                         
        SYNTAX DisplayString (SIZE (0..32))
        MAX-ACCESS  read-only
        STATUS  current
        DESCRIPTION
            "vrf name"
        ::= { zxr10igmpInstEntry 1 }

zxr10igmpInstShapingNum OBJECT-TYPE
        SYNTAX Unsigned32 (0..4294967295)
        MAX-ACCESS  read-only
        STATUS  current
        DESCRIPTION
            "shaping number"
        ::= { zxr10igmpInstEntry 2 }

zxr10igmpInstProxyEnable OBJECT-TYPE
        SYNTAX Unsigned32 (0..1)
        MAX-ACCESS  read-only
        STATUS  current
        DESCRIPTION
            "enable IGMP Proxy"
        ::= { zxr10igmpInstEntry 3 }

zxr10igmpInstRequireAlertOptions OBJECT-TYPE
        SYNTAX Unsigned32 (0..1)
        MAX-ACCESS  read-only
        STATUS  current
        DESCRIPTION
            "require IGMP router alert options"
        ::= { zxr10igmpInstEntry 4 }

zxr10igmpSsmmapTable OBJECT-TYPE
        SYNTAX  SEQUENCE OF Zxr10igmpSsmmapEntry
        MAX-ACCESS  not-accessible
        STATUS  current
        DESCRIPTION
            "A table to IGMP SSMMAP"
        ::= { zxr10igmpInstMIB 2 }

zxr10igmpSsmmapEntry OBJECT-TYPE
        SYNTAX Zxr10igmpSsmmapEntry
        MAX-ACCESS  not-accessible
        STATUS  current
        DESCRIPTION
            "An entry to IGMP SSMMAP"
        INDEX  { zxr10igmpSsmmapVrfName,
        zxr10igmpSsmmapAclName,
        zxr10igmpSsmmapSrcAddr,
        zxr10igmpSsmmapDefault }
        ::= { zxr10igmpSsmmapTable 1 }

Zxr10igmpSsmmapEntry ::=
        SEQUENCE {
            zxr10igmpSsmmapVrfName
                DisplayString,
            zxr10igmpSsmmapAclName
                DisplayString,
            zxr10igmpSsmmapSrcAddr
                IpAddress,
            zxr10igmpSsmmapDefault
                Unsigned32
        }

zxr10igmpSsmmapVrfName OBJECT-TYPE               
        SYNTAX DisplayString (SIZE (0..32))
        MAX-ACCESS  read-only
        STATUS  current
        DESCRIPTION
            "vrf name"
        ::= { zxr10igmpSsmmapEntry 1 }

zxr10igmpSsmmapAclName OBJECT-TYPE
        SYNTAX DisplayString (SIZE (0..31))
        MAX-ACCESS  read-only
        STATUS  current
        DESCRIPTION
            "SSM map ACL name"
        ::= { zxr10igmpSsmmapEntry 2 }

zxr10igmpSsmmapSrcAddr OBJECT-TYPE
        SYNTAX IpAddress
        MAX-ACCESS  read-only
        STATUS  current
        DESCRIPTION
            "source address"
        ::= { zxr10igmpSsmmapEntry 3 }

zxr10igmpSsmmapDefault OBJECT-TYPE
        SYNTAX Unsigned32 (0..1)
        MAX-ACCESS  read-only
        STATUS  current
        DESCRIPTION
            "SSM default"
        ::= { zxr10igmpSsmmapEntry 4 }


zxr10igmpIntfMIB OBJECT IDENTIFIER ::= { zxr10igmpInstMIB 3 }

zxr10igmpIntfTable OBJECT-TYPE
        SYNTAX  SEQUENCE OF Zxr10igmpIntfEntry
        MAX-ACCESS  not-accessible
        STATUS  current
        DESCRIPTION
            "A table to IGMP interface"
        ::= { zxr10igmpIntfMIB 1 }

zxr10igmpIntfEntry OBJECT-TYPE
        SYNTAX Zxr10igmpIntfEntry
        MAX-ACCESS  not-accessible
        STATUS  current
        DESCRIPTION
            "An entry to IGMP interface"
        INDEX  { zxr10igmpIntfVrfName,zxr10igmpIntfIfName }
        ::= { zxr10igmpIntfTable 1 }
            
Zxr10igmpIntfEntry ::=
        SEQUENCE {
            zxr10igmpIntfVrfName
                DisplayString,
            zxr10igmpIntfIfName
                DisplayString,            
            zxr10igmpIntfAccessGroup
                DisplayString,
            zxr10igmpIntfImmediateAcl
                DisplayString,
            zxr10igmpIntfLastMemberQueryInterval
                Unsigned32,
            zxr10igmpIntfMaximumJoins
                Unsigned32,
            zxr10igmpIntfQuerierTimeout
                Unsigned32,
            zxr10igmpIntfQueryInterval
                Unsigned32,
            zxr10igmpIntfQueryMaxResponseTime
                Unsigned32,
            zxr10igmpIntfRobustnessCount
                Unsigned32,
            zxr10igmpIntfShapingPacketsNumber
                Unsigned32,
            zxr10igmpIntfVersion
                INTEGER,
            zxr10igmpIntfImmediateAll
                Unsigned32,
            zxr10igmpIntfQuerierElectionDisable
                Unsigned32,
            zxr10igmpIntfQuerierElectionConnect
                Unsigned32,
            zxr10igmpIntfProxyService
                Unsigned32,
            zxr10igmpIntfOldQuerierPresent
                Unsigned32,
            zxr10igmpIntfReportInterval
                Unsigned32,            
            zxr10igmpIntfIfVrfName
                DisplayString,
            zxr10igmpIntfIpSourceCheck
                INTEGER
        }

zxr10igmpIntfVrfName OBJECT-TYPE                  
        SYNTAX DisplayString (SIZE (0..32))
        MAX-ACCESS  read-only
        STATUS  current
        DESCRIPTION
            "vrf name"
        ::= { zxr10igmpIntfEntry 1 }

zxr10igmpIntfIfName OBJECT-TYPE
        SYNTAX DisplayString (SIZE (0..32))
        MAX-ACCESS  read-only
        STATUS  current
        DESCRIPTION
            "interface name"
        ::= { zxr10igmpIntfEntry 2 }

zxr10igmpIntfAccessGroup OBJECT-TYPE
        SYNTAX DisplayString (SIZE (0..31))
        MAX-ACCESS  read-only
        STATUS  current
        DESCRIPTION
            "access group"
        ::= { zxr10igmpIntfEntry 5 }

zxr10igmpIntfImmediateAcl OBJECT-TYPE
        SYNTAX DisplayString (SIZE (0..31))
        MAX-ACCESS  read-only
        STATUS  current
        DESCRIPTION
            "immediate leave ACL name"
        ::= { zxr10igmpIntfEntry 6 }

zxr10igmpIntfLastMemberQueryInterval OBJECT-TYPE
        SYNTAX Unsigned32 (1..25)
        MAX-ACCESS  read-only
        STATUS  current
        DESCRIPTION
            "last member query interval"
        ::= { zxr10igmpIntfEntry 7 }

zxr10igmpIntfMaximumJoins OBJECT-TYPE
        SYNTAX Unsigned32 (0..40000)
        MAX-ACCESS  read-only
        STATUS  current
        DESCRIPTION
            "maximum joins number"
        ::= { zxr10igmpIntfEntry 8 }

zxr10igmpIntfQuerierTimeout OBJECT-TYPE
        SYNTAX Unsigned32 (60..300)
        MAX-ACCESS  read-only
        STATUS  current
        DESCRIPTION
            "querier timeout"
        ::= { zxr10igmpIntfEntry 9 }

zxr10igmpIntfQueryInterval OBJECT-TYPE
        SYNTAX Unsigned32 (1..65535)
        MAX-ACCESS  read-only
        STATUS  current
        DESCRIPTION
            "query interval"
        ::= { zxr10igmpIntfEntry 10 }

zxr10igmpIntfQueryMaxResponseTime OBJECT-TYPE
        SYNTAX Unsigned32 (1..25)
        MAX-ACCESS  read-only
        STATUS  current
        DESCRIPTION
            "query max response time"
        ::= { zxr10igmpIntfEntry 11 }

zxr10igmpIntfRobustnessCount OBJECT-TYPE
        SYNTAX Unsigned32 (2..7)
        MAX-ACCESS  read-only
        STATUS  current
        DESCRIPTION
            "robustness count"
        ::= { zxr10igmpIntfEntry 12 }

zxr10igmpIntfShapingPacketsNumber OBJECT-TYPE
        SYNTAX Unsigned32 (0..4294967295)
        MAX-ACCESS  read-only
        STATUS  current
        DESCRIPTION
            "shaping packet number"
        ::= { zxr10igmpIntfEntry 13 }

zxr10igmpIntfVersion OBJECT-TYPE
        SYNTAX INTEGER{version1(1),version2(2),version3(3)}
        MAX-ACCESS  read-only
        STATUS  current
        DESCRIPTION
            "IGMP version"
        ::= { zxr10igmpIntfEntry 14 }

zxr10igmpIntfImmediateAll OBJECT-TYPE
        SYNTAX Unsigned32 (0..1)       
        MAX-ACCESS  read-only
        STATUS  current
        DESCRIPTION
            "immediate leave all"
        ::= { zxr10igmpIntfEntry 15 }

zxr10igmpIntfQuerierElectionDisable OBJECT-TYPE
        SYNTAX Unsigned32 (0..2)
        MAX-ACCESS  read-only
        STATUS  current
        DESCRIPTION
            "querier election disable"
        ::= { zxr10igmpIntfEntry 16 }

zxr10igmpIntfQuerierElectionConnect OBJECT-TYPE
        SYNTAX Unsigned32 (0..2)
        MAX-ACCESS  read-only
        STATUS  current
        DESCRIPTION
            "querier election connect"
        ::= { zxr10igmpIntfEntry 17 }

zxr10igmpIntfProxyService OBJECT-TYPE
        SYNTAX Unsigned32 (0..1)
        MAX-ACCESS  read-only
        STATUS  current
        DESCRIPTION
            "enable proxy service"
        ::= { zxr10igmpIntfEntry 18 }

zxr10igmpIntfOldQuerierPresent OBJECT-TYPE
        SYNTAX Unsigned32 (60..32000)
        MAX-ACCESS  read-only
        STATUS  current
        DESCRIPTION
            "old querier present"
        ::= { zxr10igmpIntfEntry 19 }

zxr10igmpIntfReportInterval OBJECT-TYPE
        SYNTAX Unsigned32 (1..25)
        MAX-ACCESS  read-only
        STATUS  current
        DESCRIPTION
            "report interval"
        ::= { zxr10igmpIntfEntry 20 }

zxr10igmpIntfIfVrfName OBJECT-TYPE
        SYNTAX DisplayString (SIZE (0..32))
        MAX-ACCESS  read-only
        STATUS  current
        DESCRIPTION
            "interface vrf name"
        ::= { zxr10igmpIntfEntry 22 }

zxr10igmpIntfIpSourceCheck OBJECT-TYPE
        SYNTAX INTEGER{false(255),true(1)}
        MAX-ACCESS  read-only
        STATUS  current
        DESCRIPTION
            "IGMP ip source check"
        ::= { zxr10igmpIntfEntry 23 }

zxr10igmpGroupTable OBJECT-TYPE
        SYNTAX  SEQUENCE OF Zxr10igmpGroupEntry
        MAX-ACCESS  not-accessible
        STATUS  obsolete
        DESCRIPTION
            "A table to static group"
        ::= { zxr10igmpIntfMIB 2 }

zxr10igmpGroupEntry OBJECT-TYPE
        SYNTAX Zxr10igmpGroupEntry
        MAX-ACCESS  not-accessible
        STATUS  obsolete
        DESCRIPTION
            "An entry to static group"
        INDEX  { zxr10igmpGroupVrfName,
        zxr10igmpGroupIfName,
        zxr10igmpGroupGroup,
        zxr10igmpGroupSource,
        zxr10igmpGroupSsmMap,
        zxr10igmpGroupStaticFlag }
        ::= { zxr10igmpGroupTable 1 }
            
Zxr10igmpGroupEntry ::=
        SEQUENCE {
            zxr10igmpGroupVrfName
                DisplayString,
            zxr10igmpGroupIfName
                DisplayString,
            zxr10igmpGroupGroup
                IpAddress,
            zxr10igmpGroupSource
                IpAddress,
            zxr10igmpGroupSsmMap
                Unsigned32,
            zxr10igmpGroupStaticFlag
                INTEGER,
            zxr10igmpGroupFilterMode
                INTEGER
                
        }

zxr10igmpGroupVrfName OBJECT-TYPE
        SYNTAX DisplayString (SIZE (0..32))
        MAX-ACCESS  read-only
        STATUS  obsolete
        DESCRIPTION
            "vrf name"
        ::= { zxr10igmpGroupEntry 1 }

zxr10igmpGroupIfName OBJECT-TYPE
        SYNTAX DisplayString (SIZE (0..32))
        MAX-ACCESS  read-only
        STATUS  obsolete
        DESCRIPTION
            "interface name"
        ::= { zxr10igmpGroupEntry 2 }

zxr10igmpGroupGroup OBJECT-TYPE
        SYNTAX IpAddress
        MAX-ACCESS  read-only
        STATUS  obsolete
        DESCRIPTION
            "group address"
        ::= { zxr10igmpGroupEntry 3 }

zxr10igmpGroupSource OBJECT-TYPE
        SYNTAX IpAddress
        MAX-ACCESS  read-only
        STATUS  obsolete
        DESCRIPTION
            "source address"
        ::= { zxr10igmpGroupEntry 4 }

zxr10igmpGroupSsmMap OBJECT-TYPE
        SYNTAX Unsigned32 (0..1)
        MAX-ACCESS  read-only
        STATUS  obsolete
        DESCRIPTION
            "SSM map"
        ::= { zxr10igmpGroupEntry 5 }

zxr10igmpGroupStaticFlag OBJECT-TYPE
        SYNTAX INTEGER {staticGroup(1),joinGroup(2)}
        MAX-ACCESS  read-only
        STATUS  obsolete
        DESCRIPTION
            "static group flag"
        ::= { zxr10igmpGroupEntry 6 }
        
zxr10igmpGroupFilterMode OBJECT-TYPE
        SYNTAX INTEGER {none(0),include(3),exclude(4)}
        MAX-ACCESS  read-only
        STATUS  obsolete
        DESCRIPTION
            "source filter mode"
        ::= { zxr10igmpGroupEntry 7 }



zxr10igmpProxyTable OBJECT-TYPE
        SYNTAX  SEQUENCE OF Zxr10igmpProxyEntry
        MAX-ACCESS  not-accessible
        STATUS  current
        DESCRIPTION
            "A table to IGMP proxy"
        ::= { zxr10igmpIntfMIB 4 }

zxr10igmpProxyEntry OBJECT-TYPE
        SYNTAX Zxr10igmpProxyEntry
        MAX-ACCESS  not-accessible
        STATUS  current
        DESCRIPTION
            "An entry to IGMP proxy"
        INDEX  { zxr10igmpProxyVrfName,zxr10igmpProxyIfName }
        ::= { zxr10igmpProxyTable 1 }
            
Zxr10igmpProxyEntry ::=
        SEQUENCE {
            zxr10igmpProxyVrfName
                DisplayString,
            zxr10igmpProxyIfName
                DisplayString,
            zxr10igmpProxyUpIfName
                DisplayString,
            zxr10igmpProxyIntfVrfName
                DisplayString
        }

zxr10igmpProxyVrfName OBJECT-TYPE
        SYNTAX DisplayString (SIZE (0..32))
        MAX-ACCESS  read-only
        STATUS  current
        DESCRIPTION
            "vrf name"
        ::= { zxr10igmpProxyEntry 1 }

zxr10igmpProxyIfName OBJECT-TYPE
        SYNTAX DisplayString (SIZE (0..32))
        MAX-ACCESS  read-only
        STATUS  current
        DESCRIPTION
            "interface name"
        ::= { zxr10igmpProxyEntry 2 }

zxr10igmpProxyUpIfName OBJECT-TYPE
        SYNTAX DisplayString (SIZE (0..32))
        MAX-ACCESS  read-only
        STATUS  current
        DESCRIPTION
            "proxy upstream interface name"
        ::= { zxr10igmpProxyEntry 3 }

zxr10igmpProxyIntfVrfName OBJECT-TYPE
        SYNTAX DisplayString (SIZE (0..32))
        MAX-ACCESS  read-only
        STATUS  current
        DESCRIPTION
            "interface vrf name"
        ::= { zxr10igmpProxyEntry 4 }



zxr10mrouteProxyTable OBJECT-TYPE
        SYNTAX  SEQUENCE OF Zxr10mrouteProxyEntry
        MAX-ACCESS  not-accessible
        STATUS  current
        DESCRIPTION
            "A table to MROUTE proxy"
        ::= { zxr10igmpIntfMIB 5 }

zxr10mrouteProxyEntry OBJECT-TYPE
        SYNTAX Zxr10mrouteProxyEntry
        MAX-ACCESS  not-accessible
        STATUS  current
        DESCRIPTION
            "An entry to MROUTE proxy"
        INDEX  { zxr10mrouteProxyVrfName,zxr10mrouteProxyIfName }
        ::= { zxr10mrouteProxyTable 1 }
            
Zxr10mrouteProxyEntry ::=
        SEQUENCE {
            zxr10mrouteProxyVrfName
                DisplayString,
            zxr10mrouteProxyIfName
                DisplayString,
            zxr10mrouteProxyUpIfName
                DisplayString,
            zxr10mrouteProxyIntfVrfName
                DisplayString
        }

zxr10mrouteProxyVrfName OBJECT-TYPE  
        SYNTAX DisplayString (SIZE (0..32))
        MAX-ACCESS  read-only
        STATUS  current
        DESCRIPTION
            "vrf name"
        ::= { zxr10mrouteProxyEntry 1 }

zxr10mrouteProxyIfName OBJECT-TYPE
        SYNTAX DisplayString (SIZE (0..32))
        MAX-ACCESS  read-only
        STATUS  current
        DESCRIPTION
            "interface name"
        ::= { zxr10mrouteProxyEntry 2 }

zxr10mrouteProxyUpIfName OBJECT-TYPE
        SYNTAX DisplayString (SIZE (0..32))
        MAX-ACCESS  read-only
        STATUS  current
        DESCRIPTION
            "proxy upstream interface name"
        ::= { zxr10mrouteProxyEntry 3 }

zxr10mrouteProxyIntfVrfName OBJECT-TYPE
        SYNTAX DisplayString (SIZE (0..32))
        MAX-ACCESS  read-only
        STATUS  current
        DESCRIPTION
            "interface vrf name"
        ::= { zxr10mrouteProxyEntry 4 }

zxr10igmpStaticGroupTable OBJECT-TYPE
        SYNTAX  SEQUENCE OF Zxr10igmpStaticGroupEntry
        MAX-ACCESS  not-accessible
        STATUS  current
        DESCRIPTION
            "A table to static group"
        ::= { zxr10igmpIntfMIB 6 }

zxr10igmpStaticGroupEntry OBJECT-TYPE
        SYNTAX Zxr10igmpStaticGroupEntry
        MAX-ACCESS  not-accessible
        STATUS  current
        DESCRIPTION
            "An entry to static group"
        INDEX  { zxr10igmpStaticGroupVrfName,
        zxr10igmpStaticGroupIfName,
        zxr10igmpStaticGroupGroup,
        zxr10igmpStaticGroupSource,
        zxr10igmpStaticGroupSsmMap,
        zxr10igmpStaticGroupStaticFlag,
        zxr10igmpStaticGroupIncMask}
        ::= { zxr10igmpStaticGroupTable 1 }
            
Zxr10igmpStaticGroupEntry ::=
        SEQUENCE {
            zxr10igmpStaticGroupVrfName
                DisplayString,
            zxr10igmpStaticGroupIfName
                DisplayString,
            zxr10igmpStaticGroupGroup
                IpAddress,
            zxr10igmpStaticGroupSource
                IpAddress,
            zxr10igmpStaticGroupSsmMap
                Unsigned32,
            zxr10igmpStaticGroupStaticFlag
                INTEGER,
            zxr10igmpStaticGroupIncMask
                IpAddress,
            zxr10igmpStaticGroupFilterMode
                INTEGER,
            zxr10igmpStaticGroupCount
                Unsigned32
                
        }

zxr10igmpStaticGroupVrfName OBJECT-TYPE
        SYNTAX DisplayString (SIZE (0..32))
        MAX-ACCESS  not-accessible
        STATUS  current
        DESCRIPTION
            "vrf name"
        ::= { zxr10igmpStaticGroupEntry 1 }

zxr10igmpStaticGroupIfName OBJECT-TYPE
        SYNTAX DisplayString (SIZE (0..32))
        MAX-ACCESS  not-accessible
        STATUS  current
        DESCRIPTION
            "interface name"
        ::= { zxr10igmpStaticGroupEntry 2 }

zxr10igmpStaticGroupGroup OBJECT-TYPE
        SYNTAX IpAddress
        MAX-ACCESS  not-accessible
        STATUS  current
        DESCRIPTION
            "group address"
        ::= { zxr10igmpStaticGroupEntry 3 }

zxr10igmpStaticGroupSource OBJECT-TYPE
        SYNTAX IpAddress
        MAX-ACCESS  not-accessible
        STATUS  current
        DESCRIPTION
            "source address"
        ::= { zxr10igmpStaticGroupEntry 4 }

zxr10igmpStaticGroupSsmMap OBJECT-TYPE
        SYNTAX Unsigned32 (0..1)
        MAX-ACCESS  not-accessible
        STATUS  current
        DESCRIPTION
            "SSM map"
        ::= { zxr10igmpStaticGroupEntry 5 }

zxr10igmpStaticGroupStaticFlag OBJECT-TYPE
        SYNTAX INTEGER {staticGroup(1),joinGroup(2)}
        MAX-ACCESS  not-accessible
        STATUS  current
        DESCRIPTION
            "static group flag"
        ::= { zxr10igmpStaticGroupEntry 6 }
 zxr10igmpStaticGroupIncMask OBJECT-TYPE
        SYNTAX IpAddress
        MAX-ACCESS  not-accessible
        STATUS  current
        DESCRIPTION
            "increment mask for group address"
        ::= { zxr10igmpStaticGroupEntry 7 }

zxr10igmpStaticGroupFilterMode OBJECT-TYPE
        SYNTAX INTEGER {none(255),include(3),exclude(4)}
        MAX-ACCESS  read-only
        STATUS  current
        DESCRIPTION
            "source filter mode"
        ::= { zxr10igmpStaticGroupEntry 8 }

zxr10igmpStaticGroupCount OBJECT-TYPE
        SYNTAX Unsigned32 (0..512)
        MAX-ACCESS  read-only
        STATUS  current
        DESCRIPTION
            "number of group addresses to join"
        ::= { zxr10igmpStaticGroupEntry 9 }

zxr10igmpGroupLimitTable OBJECT-TYPE
        SYNTAX  SEQUENCE OF Zxr10igmpGroupLimitEntry
        MAX-ACCESS  not-accessible
        STATUS  current
        DESCRIPTION
            "A table to IGMP group limit"
        ::= { zxr10igmpInstMIB 4 }

zxr10igmpGroupLimitEntry OBJECT-TYPE
        SYNTAX Zxr10igmpGroupLimitEntry
        MAX-ACCESS  not-accessible
        STATUS  current
        DESCRIPTION
            "An entry to IGMP group limit"
        INDEX  { zxr10igmpGroupLimitVrfName,zxr10igmpGroupLimitGroupAddr}
        ::= { zxr10igmpGroupLimitTable 1 }
            
Zxr10igmpGroupLimitEntry ::=
        SEQUENCE {
            zxr10igmpGroupLimitVrfName
                DisplayString,
            zxr10igmpGroupLimitGroupAddr
                IpAddress,
            zxr10igmpGroupLimitNum
                Unsigned32
        }

zxr10igmpGroupLimitVrfName OBJECT-TYPE
        SYNTAX DisplayString (SIZE (0..32))
        MAX-ACCESS  not-accessible
        STATUS  current
        DESCRIPTION
            "vrf name"
        ::= { zxr10igmpGroupLimitEntry 1 }

zxr10igmpGroupLimitGroupAddr OBJECT-TYPE
        SYNTAX IpAddress
        MAX-ACCESS  not-accessible
        STATUS  current
        DESCRIPTION
            "group address"
        ::= { zxr10igmpGroupLimitEntry 2 }

zxr10igmpGroupLimitNum OBJECT-TYPE
        SYNTAX Unsigned32 (1..64)
        MAX-ACCESS  read-only
        STATUS  current
        DESCRIPTION
            "limit number"
        ::= { zxr10igmpGroupLimitEntry 3 }

zxr10msdpInstanceMIB OBJECT IDENTIFIER ::= { zxr10mrInstanceMIB 11 }

zxr10msdpInstanceTable OBJECT-TYPE
        SYNTAX  SEQUENCE OF Zxr10msdpInstanceEntry
        MAX-ACCESS  not-accessible
        STATUS  current
        DESCRIPTION
            "A table to MSDP instance"
        ::= { zxr10msdpInstanceMIB 1 }

zxr10msdpInstanceEntry OBJECT-TYPE
        SYNTAX Zxr10msdpInstanceEntry
        MAX-ACCESS  not-accessible
        STATUS  current
        DESCRIPTION
            "An entry to MSDP instance"
        INDEX  { zxr10msdpInstanceVrfName }
        ::= { zxr10msdpInstanceTable 1 }
            
Zxr10msdpInstanceEntry ::=
        SEQUENCE {
            zxr10msdpInstanceVrfName
                DisplayString,            
            zxr10msdpInstanceRouterMsdp
                Unsigned32,
            zxr10msdpInstanceSaAdvTime
                Unsigned32,
            zxr10msdpInstanceSaCacheTimeout
                Unsigned32
        }

zxr10msdpInstanceVrfName OBJECT-TYPE     
        SYNTAX DisplayString (SIZE (0..32))
        MAX-ACCESS  read-only
        STATUS  current
        DESCRIPTION
            "vrf name"
        ::= { zxr10msdpInstanceEntry 1 }

zxr10msdpInstanceRouterMsdp OBJECT-TYPE
        SYNTAX Unsigned32 (0..1)
        MAX-ACCESS  read-only
        STATUS  current
        DESCRIPTION
            "enable MSDP"
        ::= { zxr10msdpInstanceEntry 6 }
        
zxr10msdpInstanceSaAdvTime OBJECT-TYPE
        SYNTAX Unsigned32 (1..60)
        MAX-ACCESS  read-only
        STATUS  current
        DESCRIPTION
            "Sa advertisement message interval"
        ::= { zxr10msdpInstanceEntry 7 }

zxr10msdpInstanceSaCacheTimeout OBJECT-TYPE
        SYNTAX Unsigned32 (150..3600)
        MAX-ACCESS  read-only
        STATUS  current
        DESCRIPTION
            "Sa cache item timeout"
        ::= { zxr10msdpInstanceEntry 8 }

zxr10peerMIB OBJECT IDENTIFIER ::= { zxr10msdpInstanceMIB 2 }

zxr10peerTable OBJECT-TYPE
        SYNTAX  SEQUENCE OF Zxr10peerEntry
        MAX-ACCESS  not-accessible
        STATUS  current
        DESCRIPTION
            "A table to MSDP peer"
        ::= { zxr10peerMIB 1 }

zxr10peerEntry OBJECT-TYPE
        SYNTAX Zxr10peerEntry
        MAX-ACCESS  not-accessible
        STATUS  current
        DESCRIPTION
            "An entry to MSDP PEER."
        INDEX  { zxr10peerVrfName,zxr10peerPeerAddr }
        ::= { zxr10peerTable 1 }
            
Zxr10peerEntry ::=
        SEQUENCE {
            zxr10peerVrfName
                DisplayString,
            zxr10peerPeerAddr
                IpAddress,
            zxr10peerMeshGroupName
                DisplayString,            
            zxr10peerSaLimit
                Unsigned32,
            zxr10peerDescriptionText
                DisplayString,
            zxr10peerPassword
                DisplayString,
            zxr10peerPeerTtl
                Unsigned32,
            zxr10peerTtlSecurityHops
                INTEGER,            
            zxr10peerShutdown
                Unsigned32,
            zxr10peerBfdEnable
                Unsigned32,
            zxr10peerHoldtime
                Unsigned32,
            zxr10peerKeepaliveTime
                Unsigned32,
            zxr10peerReconnectTime
                Unsigned32,
            zxr10peerInactiveTime
                Unsigned32,
            zxr10peerKeychain
                DisplayString
        }

zxr10peerVrfName OBJECT-TYPE              
        SYNTAX DisplayString (SIZE (0..32))
        MAX-ACCESS  read-only
        STATUS  current
        DESCRIPTION
            "vrf name"
        ::= { zxr10peerEntry 1 }

zxr10peerPeerAddr OBJECT-TYPE
        SYNTAX IpAddress
        MAX-ACCESS  read-only
        STATUS  current
        DESCRIPTION
            "peer address"
        ::= { zxr10peerEntry 2 }

zxr10peerMeshGroupName OBJECT-TYPE      
        SYNTAX DisplayString (SIZE (0..32))
        MAX-ACCESS  read-only
        STATUS  current
        DESCRIPTION
            "mesh group"
        ::= { zxr10peerEntry 3 }

zxr10peerSaLimit OBJECT-TYPE
        SYNTAX Unsigned32 (0..2147483646)
        MAX-ACCESS  read-only
        STATUS  current
        DESCRIPTION
            "SA limit value"
        ::= { zxr10peerEntry 7 }

zxr10peerDescriptionText OBJECT-TYPE
        SYNTAX DisplayString (SIZE (0..80))
        MAX-ACCESS  read-only
        STATUS  current
        DESCRIPTION
            "peer description"
        ::= { zxr10peerEntry 8 }

zxr10peerPassword OBJECT-TYPE
        SYNTAX DisplayString (SIZE (0..120))
        MAX-ACCESS  read-only
        STATUS  current
        DESCRIPTION
            "MD5 password"
        ::= { zxr10peerEntry 9 }

zxr10peerPeerTtl OBJECT-TYPE
        SYNTAX Unsigned32 (0..255)
        MAX-ACCESS  read-only
        STATUS  current
        DESCRIPTION
            "ttl threshold"
        ::= { zxr10peerEntry 10 }

zxr10peerTtlSecurityHops OBJECT-TYPE
        SYNTAX INTEGER (0..255)
        MAX-ACCESS  read-only
        STATUS  current
        DESCRIPTION
            "ttl security hops"
        ::= { zxr10peerEntry 11 }

zxr10peerShutdown OBJECT-TYPE
        SYNTAX Unsigned32 (0..1)
        MAX-ACCESS  read-only
        STATUS  current
        DESCRIPTION
            "shutdown peer"
        ::= { zxr10peerEntry 14 }

zxr10peerBfdEnable OBJECT-TYPE
        SYNTAX Unsigned32 (0..1)
        MAX-ACCESS  read-only
        STATUS  current
        DESCRIPTION
            "enable BFD"
        ::= { zxr10peerEntry 15 }
        
zxr10peerHoldtime OBJECT-TYPE
        SYNTAX Unsigned32 (1..75)
        MAX-ACCESS  read-only
        STATUS  current
        DESCRIPTION
            "peer holdtime"
        ::= { zxr10peerEntry 16 }
        
zxr10peerKeepaliveTime OBJECT-TYPE
        SYNTAX Unsigned32 (1..60)
        MAX-ACCESS  read-only
        STATUS  current
        DESCRIPTION
            "peer keepalive message interval"
        ::= { zxr10peerEntry 17 }

zxr10peerReconnectTime OBJECT-TYPE
        SYNTAX Unsigned32 (1..60)
        MAX-ACCESS  read-only
        STATUS  current
        DESCRIPTION
            "peer connect retry time"
        ::= { zxr10peerEntry 18 }
        
zxr10peerInactiveTime OBJECT-TYPE
        SYNTAX Unsigned32 (1..60)
        MAX-ACCESS  read-only
        STATUS  current
        DESCRIPTION
            "peer inactive time"
        ::= { zxr10peerEntry 19 }

zxr10peerKeychain OBJECT-TYPE
        SYNTAX DisplayString (SIZE (0..31))
        MAX-ACCESS  read-only
        STATUS  current
        DESCRIPTION
            "Keychain name"
        ::= { zxr10peerEntry 20 }

zxr10defaultPeerTable OBJECT-TYPE
        SYNTAX  SEQUENCE OF Zxr10defaultPeerEntry
        MAX-ACCESS  not-accessible
        STATUS  current
        DESCRIPTION
            "A table to default peer"
        ::= { zxr10peerMIB 2 }

zxr10defaultPeerEntry OBJECT-TYPE
        SYNTAX Zxr10defaultPeerEntry
        MAX-ACCESS  not-accessible
        STATUS  current
        DESCRIPTION
            "An entry to default peer"
        INDEX  { zxr10defaultPeerVrfName,zxr10defaultPeerAddr }
        ::= { zxr10defaultPeerTable 1 }
            
Zxr10defaultPeerEntry ::=
        SEQUENCE {
            zxr10defaultPeerVrfName
                DisplayString,
            zxr10defaultPeerAddr
                IpAddress,
            zxr10defaultPeerAclName
                DisplayString
        }

zxr10defaultPeerVrfName OBJECT-TYPE      
        SYNTAX DisplayString (SIZE (0..32))
        MAX-ACCESS  read-only
        STATUS  current
        DESCRIPTION
            "vrf name"
        ::= { zxr10defaultPeerEntry 1 }

zxr10defaultPeerAddr OBJECT-TYPE
        SYNTAX IpAddress
        MAX-ACCESS  read-only
        STATUS  current
        DESCRIPTION
            "peer address"
        ::= { zxr10defaultPeerEntry 2 }

zxr10defaultPeerAclName OBJECT-TYPE
        SYNTAX DisplayString (SIZE (0..31))
        MAX-ACCESS  read-only
        STATUS  current
        DESCRIPTION
            "default peer ACL name"
        ::= { zxr10defaultPeerEntry 3 }



zxr10safilterinTable OBJECT-TYPE
        SYNTAX  SEQUENCE OF Zxr10safilterinEntry
        MAX-ACCESS  not-accessible
        STATUS  current
        DESCRIPTION
            "A table to SA-FILTER-IN"
        ::= { zxr10peerMIB 3 }

zxr10safilterinEntry OBJECT-TYPE
        SYNTAX Zxr10safilterinEntry
        MAX-ACCESS  not-accessible
        STATUS  current
        DESCRIPTION
            "An entry to SA-FILTER-IN."
        INDEX  { zxr10safilterinVrf,zxr10safilterinPeerAddr }
        ::= { zxr10safilterinTable 1 }
            
Zxr10safilterinEntry ::=
        SEQUENCE {
            zxr10safilterinVrf
                DisplayString,
            zxr10safilterinPeerAddr
                IpAddress,
            zxr10safilterinAcl
                DisplayString
        }

zxr10safilterinVrf OBJECT-TYPE
        SYNTAX DisplayString (SIZE (0..32))
        MAX-ACCESS  read-only
        STATUS  current
        DESCRIPTION
            "vrf name"
        ::= { zxr10safilterinEntry 1 }

zxr10safilterinPeerAddr OBJECT-TYPE
        SYNTAX IpAddress
        MAX-ACCESS  read-only
        STATUS  current
        DESCRIPTION
            "peer address"
        ::= { zxr10safilterinEntry 2 }

zxr10safilterinAcl OBJECT-TYPE
        SYNTAX DisplayString (SIZE (0..31))
        MAX-ACCESS  read-only
        STATUS  current
        DESCRIPTION
            "SA filter in ACL name"
        ::= { zxr10safilterinEntry 3 }

zxr10safilteroutTable OBJECT-TYPE
        SYNTAX  SEQUENCE OF Zxr10safilteroutEntry
        MAX-ACCESS  not-accessible
        STATUS  current
        DESCRIPTION
            "A table to SA-FILTER-OUT"
        ::= { zxr10peerMIB 4 }

zxr10safilteroutEntry OBJECT-TYPE
        SYNTAX Zxr10safilteroutEntry
        MAX-ACCESS  not-accessible
        STATUS  current
        DESCRIPTION
            "An entry to SA-FILTER-OUT."
        INDEX  { zxr10safilteroutVrf,zxr10safilteroutPeerAddr }
        ::= { zxr10safilteroutTable 1 }
            
Zxr10safilteroutEntry ::=
        SEQUENCE {
            zxr10safilteroutVrf
                DisplayString,
            zxr10safilteroutPeerAddr
                IpAddress,
            zxr10safilteroutAcl
                DisplayString
        }

zxr10safilteroutVrf OBJECT-TYPE
        SYNTAX DisplayString (SIZE (0..32))
        MAX-ACCESS  read-only
        STATUS  current
        DESCRIPTION
            "vrf name"
        ::= { zxr10safilteroutEntry 1 }

zxr10safilteroutPeerAddr OBJECT-TYPE
        SYNTAX IpAddress
        MAX-ACCESS  read-only
        STATUS  current
        DESCRIPTION
            "peer address"
        ::= { zxr10safilteroutEntry 2 }

zxr10safilteroutAcl OBJECT-TYPE
        SYNTAX DisplayString (SIZE (0..31))
        MAX-ACCESS  read-only
        STATUS  current
        DESCRIPTION
            "ACL name"
        ::= { zxr10safilteroutEntry 3 }



zxr10peerConnectSourceTable OBJECT-TYPE
        SYNTAX  SEQUENCE OF Zxr10peerConnectSourceEntry
        MAX-ACCESS  not-accessible
        STATUS  current
        DESCRIPTION
            "A table to peer connect source"
        ::= { zxr10peerMIB 5 }

zxr10peerConnectSourceEntry OBJECT-TYPE
        SYNTAX Zxr10peerConnectSourceEntry
        MAX-ACCESS  not-accessible
        STATUS  current
        DESCRIPTION
            "An entry to peer connect source"
        INDEX  { zxr10peerConnectSourceVrf,zxr10peerConnectSourcePeerAddr }
        ::= { zxr10peerConnectSourceTable 1 }
            
Zxr10peerConnectSourceEntry ::=
        SEQUENCE {
            zxr10peerConnectSourceVrf
                DisplayString,
            zxr10peerConnectSourcePeerAddr
                IpAddress,
            zxr10peerConnectSourceIntfName
                DisplayString
        }

zxr10peerConnectSourceVrf OBJECT-TYPE
        SYNTAX DisplayString (SIZE (0..32))
        MAX-ACCESS  read-only
        STATUS  current
        DESCRIPTION
            "vrf name"
        ::= { zxr10peerConnectSourceEntry 1 }

zxr10peerConnectSourcePeerAddr OBJECT-TYPE
        SYNTAX IpAddress
        MAX-ACCESS  read-only
        STATUS  current
        DESCRIPTION
            "peer address"
        ::= { zxr10peerConnectSourceEntry 2 }

zxr10peerConnectSourceIntfName OBJECT-TYPE
        SYNTAX DisplayString (SIZE (0..32))
        MAX-ACCESS  read-only
        STATUS  current
        DESCRIPTION
            "connect source interface name"
        ::= { zxr10peerConnectSourceEntry 3 }


zxr10msdpRedistributeTable OBJECT-TYPE
        SYNTAX  SEQUENCE OF Zxr10msdpRedistributeEntry
        MAX-ACCESS  not-accessible
        STATUS  current
        DESCRIPTION
            "A table to SA redistribute"
        ::= { zxr10msdpInstanceMIB 3 }

zxr10msdpRedistributeEntry OBJECT-TYPE
        SYNTAX Zxr10msdpRedistributeEntry
        MAX-ACCESS  not-accessible
        STATUS  current
        DESCRIPTION
            "An entry to SA redistribute"
        INDEX  { zxr10msdpRedistributeVrf }
        ::= { zxr10msdpRedistributeTable 1 }
            
Zxr10msdpRedistributeEntry ::=
        SEQUENCE {
            zxr10msdpRedistributeVrf
                DisplayString,
            zxr10msdpRedistributeAcl
                DisplayString
        }

zxr10msdpRedistributeVrf OBJECT-TYPE
        SYNTAX DisplayString (SIZE (0..32))
        MAX-ACCESS  read-only
        STATUS  current
        DESCRIPTION
            "vrf name"
        ::= { zxr10msdpRedistributeEntry 1 }

zxr10msdpRedistributeAcl OBJECT-TYPE
        SYNTAX DisplayString (SIZE (0..31))
        MAX-ACCESS  read-only
        STATUS  current
        DESCRIPTION
            "SA redistribute ACL name"
        ::= { zxr10msdpRedistributeEntry 2 }

zxr10msdpOriginatorTable OBJECT-TYPE
        SYNTAX  SEQUENCE OF Zxr10msdpOriginatorEntry
        MAX-ACCESS  not-accessible
        STATUS  current
        DESCRIPTION
            "A table to originator ID"
        ::= { zxr10msdpInstanceMIB 4 }

zxr10msdpOriginatorEntry OBJECT-TYPE
        SYNTAX Zxr10msdpOriginatorEntry
        MAX-ACCESS  not-accessible
        STATUS  current
        DESCRIPTION
            "An entry to originator ID"
        INDEX  { zxr10msdpOriginatorVrf }
        ::= { zxr10msdpOriginatorTable 1 }
            
Zxr10msdpOriginatorEntry ::=
        SEQUENCE {
            zxr10msdpOriginatorVrf
                DisplayString,
            zxr10msdpOriginatorIntfName
                DisplayString
        }

zxr10msdpOriginatorVrf OBJECT-TYPE
        SYNTAX DisplayString (SIZE (0..32))
        MAX-ACCESS  read-only
        STATUS  current
        DESCRIPTION
            "vrf name"
        ::= { zxr10msdpOriginatorEntry 1 }

zxr10msdpOriginatorIntfName OBJECT-TYPE
        SYNTAX DisplayString (SIZE (0..32))
        MAX-ACCESS  read-only
        STATUS  current
        DESCRIPTION
            "interface name"
        ::= { zxr10msdpOriginatorEntry 2 }

zxr10msdpConnectSourceTable OBJECT-TYPE
        SYNTAX  SEQUENCE OF Zxr10msdpConnectSourceEntry
        MAX-ACCESS  not-accessible
        STATUS  current
        DESCRIPTION
            "A table to connect source"
        ::= { zxr10msdpInstanceMIB 5 }

zxr10msdpConnectSourceEntry OBJECT-TYPE
        SYNTAX Zxr10msdpConnectSourceEntry
        MAX-ACCESS  not-accessible
        STATUS  current
        DESCRIPTION
            "An entry to connect source"
        INDEX  { zxr10msdpConnectSourceVrf }
        ::= { zxr10msdpConnectSourceTable 1 }
            
Zxr10msdpConnectSourceEntry ::=
        SEQUENCE {
            zxr10msdpConnectSourceVrf
                DisplayString,
            zxr10msdpConnectSourceIntfName
                DisplayString
        }

zxr10msdpConnectSourceVrf OBJECT-TYPE
        SYNTAX DisplayString (SIZE (0..32))
        MAX-ACCESS  read-only
        STATUS  current
        DESCRIPTION
            "vrf name"
        ::= { zxr10msdpConnectSourceEntry 1 }

zxr10msdpConnectSourceIntfName OBJECT-TYPE
        SYNTAX DisplayString (SIZE (0..32))
        MAX-ACCESS  read-only
        STATUS  current
        DESCRIPTION
            "connect source interface name"
        ::= { zxr10msdpConnectSourceEntry 2 }

zxr10mvpnInstTable OBJECT-TYPE
        SYNTAX  SEQUENCE OF Zxr10mvpnInstEntry
        MAX-ACCESS  not-accessible
        STATUS  current
        DESCRIPTION
            "A table to MVPN instance"
        ::= { zxr10mrInstanceMIB 12 }

zxr10mvpnInstEntry OBJECT-TYPE
        SYNTAX Zxr10mvpnInstEntry
        MAX-ACCESS  not-accessible
        STATUS  current
        DESCRIPTION
            "An entry to MVPN instance"
        INDEX  { zxr10mvpnInstVrfName }
        ::= { zxr10mvpnInstTable 1 }
            
Zxr10mvpnInstEntry ::=
        SEQUENCE {
            zxr10mvpnInstVrfName
                DisplayString,
            zxr10mvpnInstProviderTunnel
                INTEGER            
        }

zxr10mvpnInstVrfName OBJECT-TYPE
        SYNTAX DisplayString (SIZE (0..32))
        MAX-ACCESS  read-only
        STATUS  current
        DESCRIPTION
            "vrf name"
        ::= { zxr10mvpnInstEntry 1 }

zxr10mvpnInstProviderTunnel OBJECT-TYPE
        SYNTAX INTEGER {rsvpte(1),mldpp2mp(2),pimssm(3),pimsm(4),
             pimbidir(5),ingressrpl(6),mldpmp2mp(7),pimmdt(8)}
        MAX-ACCESS  read-only
        STATUS  current
        DESCRIPTION
            "provider tunnel"
        ::= { zxr10mvpnInstEntry 2 }

zxr10mrMtunnelTable OBJECT-TYPE
        SYNTAX  SEQUENCE OF Zxr10mrMtunnelEntry
        MAX-ACCESS  not-accessible
        STATUS  current
        DESCRIPTION
            "A table to mtunnel"
        ::= { zxr10mrInstanceMIB 13 }

zxr10mrMtunnelEntry OBJECT-TYPE
        SYNTAX Zxr10mrMtunnelEntry
        MAX-ACCESS  not-accessible
        STATUS  current
        DESCRIPTION
            "An entry to mtunnel"
        INDEX  { zxr10mrMtunnelVrfname }
        ::= { zxr10mrMtunnelTable 1 }
            
Zxr10mrMtunnelEntry ::=
        SEQUENCE {
            zxr10mrMtunnelVrfname
                DisplayString,
            zxr10mrMtunnelIntfname
                DisplayString
        }

zxr10mrMtunnelVrfname OBJECT-TYPE
        SYNTAX DisplayString (SIZE (0..32))
        MAX-ACCESS  read-only
        STATUS  current
        DESCRIPTION
            "vrf name"
        ::= { zxr10mrMtunnelEntry 1 }

zxr10mrMtunnelIntfname OBJECT-TYPE
        SYNTAX DisplayString (SIZE (0..32))
        MAX-ACCESS  read-only
        STATUS  current
        DESCRIPTION
            "mtunnel interface"
        ::= { zxr10mrMtunnelEntry 2 }



zxr10mrTtlTable OBJECT-TYPE
        SYNTAX  SEQUENCE OF Zxr10mrTtlEntry
        MAX-ACCESS  not-accessible
        STATUS  current
        DESCRIPTION
            "A table to ttl"
        ::= { zxr10mrInstanceMIB 15 }

zxr10mrTtlEntry OBJECT-TYPE
        SYNTAX Zxr10mrTtlEntry
        MAX-ACCESS  not-accessible
        STATUS  current
        DESCRIPTION
            "An entry to ttl"
        INDEX  { zxr10mrTtlVrfname,zxr10mrTtlIntfName }
        ::= { zxr10mrTtlTable 1 }
            
Zxr10mrTtlEntry ::=
        SEQUENCE {
            zxr10mrTtlVrfname
                DisplayString,
            zxr10mrTtlIntfName
                DisplayString,
            zxr10mrTtlNum
                INTEGER
        }

zxr10mrTtlVrfname OBJECT-TYPE
        SYNTAX DisplayString (SIZE (0..32))
        MAX-ACCESS  read-only
        STATUS  current
        DESCRIPTION
            "vrf name"
        ::= { zxr10mrTtlEntry 1 }

zxr10mrTtlIntfName OBJECT-TYPE
        SYNTAX DisplayString (SIZE (0..32))
        MAX-ACCESS  read-only
        STATUS  current
        DESCRIPTION
            "interface name"
        ::= { zxr10mrTtlEntry 2 }

zxr10mrTtlNum OBJECT-TYPE
        SYNTAX INTEGER (1..255)
        MAX-ACCESS  read-only
        STATUS  current
        DESCRIPTION
            "ttl number"
        ::= { zxr10mrTtlEntry 3 }

zxr10mrBoundaryTable OBJECT-TYPE
        SYNTAX  SEQUENCE OF Zxr10mrBoundaryEntry
        MAX-ACCESS  not-accessible
        STATUS  current
        DESCRIPTION
            "A table to mroute boundary"
        ::= { zxr10mrInstanceMIB 16 }

zxr10mrBoundaryEntry OBJECT-TYPE
        SYNTAX Zxr10mrBoundaryEntry
        MAX-ACCESS  not-accessible
        STATUS  current
        DESCRIPTION
            "An entry to mroute boundary"
        INDEX  { zxr10mrBoundaryVrfname,zxr10mrBoundaryIntfName }
        ::= { zxr10mrBoundaryTable 1 }
            
Zxr10mrBoundaryEntry ::=
        SEQUENCE {
            zxr10mrBoundaryVrfname
                DisplayString,
            zxr10mrBoundaryIntfName
                DisplayString,
            zxr10mrBoundaryAclname
                DisplayString
        }

zxr10mrBoundaryVrfname OBJECT-TYPE
        SYNTAX DisplayString (SIZE (0..32))
        MAX-ACCESS  read-only
        STATUS  current
        DESCRIPTION
            "vrf name"
        ::= { zxr10mrBoundaryEntry 1 }

zxr10mrBoundaryIntfName OBJECT-TYPE
        SYNTAX DisplayString (SIZE (0..32))
        MAX-ACCESS  read-only
        STATUS  current
        DESCRIPTION
            "interface name"
        ::= { zxr10mrBoundaryEntry 2 }

zxr10mrBoundaryAclname OBJECT-TYPE
        SYNTAX DisplayString (SIZE (0..31))
        MAX-ACCESS  read-only
        STATUS  current
        DESCRIPTION
            "mroute boundary ACL name"
        ::= { zxr10mrBoundaryEntry 3 }



zxr10mrRejectinboundTable OBJECT-TYPE
        SYNTAX  SEQUENCE OF Zxr10mrRejectinboundEntry
        MAX-ACCESS  not-accessible
        STATUS  current
        DESCRIPTION
            "A table to reject inbound data"
        ::= { zxr10mrInstanceMIB 17 }

zxr10mrRejectinboundEntry OBJECT-TYPE
        SYNTAX Zxr10mrRejectinboundEntry
        MAX-ACCESS  not-accessible
        STATUS  current
        DESCRIPTION
            "An entry to reject inbound data"
        INDEX  { zxr10mrRejectinboundVrfName,zxr10mrRejectinboundIntfname }
        ::= { zxr10mrRejectinboundTable 1 }

Zxr10mrRejectinboundEntry ::=
        SEQUENCE {
            zxr10mrRejectinboundVrfName
                DisplayString,
            zxr10mrRejectinboundIntfname
                DisplayString
        }

zxr10mrRejectinboundVrfName OBJECT-TYPE
        SYNTAX DisplayString (SIZE (0..32))
        MAX-ACCESS  read-only
        STATUS  current
        DESCRIPTION
            "vrf name"
        ::= { zxr10mrRejectinboundEntry 1 }

zxr10mrRejectinboundIntfname OBJECT-TYPE
        SYNTAX DisplayString (SIZE (0..32))
        MAX-ACCESS  read-only
        STATUS  current
        DESCRIPTION
            "interface name"
        ::= { zxr10mrRejectinboundEntry 2 }
        
        
zxr10mrFilterInterfaceTable OBJECT-TYPE
        SYNTAX  SEQUENCE OF Zxr10mrFilterInterfaceEntry
        MAX-ACCESS  not-accessible
        STATUS  current
        DESCRIPTION
            "A table to filter policy monitor interface"
        ::= { zxr10mrInstanceMIB 18 }

zxr10mrFilterInterfaceEntry OBJECT-TYPE
        SYNTAX Zxr10mrFilterInterfaceEntry
        MAX-ACCESS  not-accessible
        STATUS  current
        DESCRIPTION
            "An entry to filter policy monitor interface"
        INDEX  { zxr10mrFilterInterfaceVrfName,zxr10mrFilterInterfaceIntfName }
        ::= { zxr10mrFilterInterfaceTable 1 }
            
Zxr10mrFilterInterfaceEntry ::=
        SEQUENCE {
            zxr10mrFilterInterfaceVrfName
                DisplayString,
            zxr10mrFilterInterfaceIntfName
                DisplayString,
            zxr10mrFilterInterfaceMode
                INTEGER,
            zxr10mrFilterInterfaceType
                INTEGER
        }

zxr10mrFilterInterfaceVrfName OBJECT-TYPE
        SYNTAX DisplayString (SIZE (0..32))
        MAX-ACCESS  read-only
        STATUS  current
        DESCRIPTION
            "vrf name"
        ::= { zxr10mrFilterInterfaceEntry 1 }

zxr10mrFilterInterfaceIntfName OBJECT-TYPE
        SYNTAX DisplayString (SIZE (0..32))
        MAX-ACCESS  read-only
        STATUS  current
        DESCRIPTION
            "interface name"
        ::= { zxr10mrFilterInterfaceEntry 2 }
        
zxr10mrFilterInterfaceMode OBJECT-TYPE
        SYNTAX INTEGER {include(0),exclude(1)}
        MAX-ACCESS  read-only
        STATUS  current
        DESCRIPTION
            "filter interface mode"
        ::= { zxr10mrFilterInterfaceEntry 3 }
        
zxr10mrFilterInterfaceType OBJECT-TYPE
        SYNTAX INTEGER {add(0),delete(1)}
        MAX-ACCESS  read-only
        STATUS  current
        DESCRIPTION
            "filter interface type"
        ::= { zxr10mrFilterInterfaceEntry 4 }
        
        
zxr10mrFilterMrouteInterfaceTable OBJECT-TYPE
        SYNTAX  SEQUENCE OF Zxr10mrFilterMrouteInterfaceEntry
        MAX-ACCESS  not-accessible
        STATUS  current
        DESCRIPTION
            "A table to filter policy monitor mroute interface"
        ::= { zxr10mrInstanceMIB 19 }

zxr10mrFilterMrouteInterfaceEntry OBJECT-TYPE
        SYNTAX Zxr10mrFilterMrouteInterfaceEntry
        MAX-ACCESS  not-accessible
        STATUS  current
        DESCRIPTION
            "An entry to filter policy monitor mroute interface"
        INDEX  { zxr10mrFilterMrouteInterfaceVrfName,
        zxr10mrFilterMrouteInterfaceIntfName,
        zxr10mrFilterMrouteInterfaceSourceAddr,
        zxr10mrFilterMrouteInterfaceGroupAddr }
        ::= { zxr10mrFilterMrouteInterfaceTable 1 }
            
Zxr10mrFilterMrouteInterfaceEntry ::=
        SEQUENCE {
            zxr10mrFilterMrouteInterfaceVrfName
                DisplayString,
            zxr10mrFilterMrouteInterfaceIntfName
                DisplayString,
            zxr10mrFilterMrouteInterfaceSourceAddr
                IpAddress,    
            zxr10mrFilterMrouteInterfaceGroupAddr
                IpAddress,
            zxr10mrFilterMrouteInterfaceType
                INTEGER
        }

zxr10mrFilterMrouteInterfaceVrfName OBJECT-TYPE
        SYNTAX DisplayString (SIZE (0..32))
        MAX-ACCESS  read-only
        STATUS  current
        DESCRIPTION
            "vrf name"
        ::= { zxr10mrFilterMrouteInterfaceEntry 1 }

zxr10mrFilterMrouteInterfaceIntfName OBJECT-TYPE
        SYNTAX DisplayString (SIZE (0..32))
        MAX-ACCESS  read-only
        STATUS  current
        DESCRIPTION
            "interface name"
        ::= { zxr10mrFilterMrouteInterfaceEntry 2 }
        
zxr10mrFilterMrouteInterfaceSourceAddr OBJECT-TYPE
        SYNTAX IpAddress
        MAX-ACCESS  read-only
        STATUS  current
        DESCRIPTION
            "source address"
        ::= { zxr10mrFilterMrouteInterfaceEntry 3 }
        
zxr10mrFilterMrouteInterfaceGroupAddr OBJECT-TYPE
        SYNTAX IpAddress
        MAX-ACCESS  read-only
        STATUS  current
        DESCRIPTION
            "group address"
        ::= { zxr10mrFilterMrouteInterfaceEntry 4 }
        
zxr10mrFilterMrouteInterfaceType OBJECT-TYPE
        SYNTAX INTEGER {add(0),delete(1)}
        MAX-ACCESS  read-only
        STATUS  current
        DESCRIPTION
            "filter interface type"
        ::= { zxr10mrFilterMrouteInterfaceEntry 5 }
        
        
        
zxr10mrFilterMrouteModeTable OBJECT-TYPE
        SYNTAX  SEQUENCE OF Zxr10mrFilterMrouteModeEntry
        MAX-ACCESS  not-accessible
        STATUS  current
        DESCRIPTION
            "A table to filter policy monitor mroute mode"
        ::= { zxr10mrInstanceMIB 20 }

zxr10mrFilterMrouteModeEntry OBJECT-TYPE
        SYNTAX Zxr10mrFilterMrouteModeEntry
        MAX-ACCESS  not-accessible
        STATUS  current
        DESCRIPTION
            "An entry to filter policy monitor mroute mode"
        INDEX  { zxr10mrFilterMrouteModeVrfName,
        zxr10mrFilterMrouteModeSourceAddr,
        zxr10mrFilterMrouteModeGroupAddr }
        ::= { zxr10mrFilterMrouteModeTable 1 }
            
Zxr10mrFilterMrouteModeEntry ::=
        SEQUENCE {
            zxr10mrFilterMrouteModeVrfName
                DisplayString,            
            zxr10mrFilterMrouteModeSourceAddr
                IpAddress,    
            zxr10mrFilterMrouteModeGroupAddr
                IpAddress,
            zxr10mrFilterMrouteModeType
                INTEGER
        }

zxr10mrFilterMrouteModeVrfName OBJECT-TYPE
        SYNTAX DisplayString (SIZE (0..32))
        MAX-ACCESS  read-only
        STATUS  current
        DESCRIPTION
            "vrf name"
        ::= { zxr10mrFilterMrouteModeEntry 1 }
        
zxr10mrFilterMrouteModeSourceAddr OBJECT-TYPE
        SYNTAX IpAddress
        MAX-ACCESS  read-only
        STATUS  current
        DESCRIPTION
            "source address"
        ::= { zxr10mrFilterMrouteModeEntry 2 }
        
zxr10mrFilterMrouteModeGroupAddr OBJECT-TYPE
        SYNTAX IpAddress
        MAX-ACCESS  read-only
        STATUS  current
        DESCRIPTION
            "group address"
        ::= { zxr10mrFilterMrouteModeEntry 3 }
        
zxr10mrFilterMrouteModeType OBJECT-TYPE
        SYNTAX INTEGER {include(0),exclude(1)}
        MAX-ACCESS  read-only
        STATUS  current
        DESCRIPTION
            "filter mode type"
        ::= { zxr10mrFilterMrouteModeEntry 4 }
        
        
zxr10mrForwordingPolicyTable OBJECT-TYPE
        SYNTAX  SEQUENCE OF Zxr10mrForwordingPolicyEntry
        MAX-ACCESS  not-accessible
        STATUS  current
        DESCRIPTION
            "A table to forwording policy"
        ::= { zxr10mrInstanceMIB 21 }

zxr10mrForwordingPolicyEntry OBJECT-TYPE
        SYNTAX Zxr10mrForwordingPolicyEntry
        MAX-ACCESS  not-accessible
        STATUS  current
        DESCRIPTION
            "An entry to forwarding policy"
        INDEX  { zxr10mrForwordingPolicyVrfName,zxr10mrForwordingPolicyAcl,
          zxr10mrForwordingPolicyType }
        ::= { zxr10mrForwordingPolicyTable 1 }

Zxr10mrForwordingPolicyEntry ::=
        SEQUENCE {
            zxr10mrForwordingPolicyVrfName
                DisplayString,            
            zxr10mrForwordingPolicyAcl
                DisplayString,            
            zxr10mrForwordingPolicyType
                INTEGER
        }

zxr10mrForwordingPolicyVrfName OBJECT-TYPE
        SYNTAX DisplayString (SIZE (0..32))
        MAX-ACCESS  read-only
        STATUS  current
        DESCRIPTION
            "vrf name"
        ::= { zxr10mrForwordingPolicyEntry 1 }
        
zxr10mrForwordingPolicyAcl OBJECT-TYPE
        SYNTAX DisplayString (SIZE (0..31))
        MAX-ACCESS  read-only
        STATUS  current
        DESCRIPTION
            "ACL name"
        ::= { zxr10mrForwordingPolicyEntry 2 }
        
zxr10mrForwordingPolicyType OBJECT-TYPE
        SYNTAX INTEGER {perpacket(1),peruser(2),perstream(3)}
        MAX-ACCESS  read-only
        STATUS  current
        DESCRIPTION
            "forwording policy type"
        ::= { zxr10mrForwordingPolicyEntry 3 }


zxr10nexthopRouteTable OBJECT-TYPE
        SYNTAX  SEQUENCE OF Zxr10nexthopRouteEntry
        MAX-ACCESS  not-accessible
        STATUS  current
        DESCRIPTION
            "A table to multicast nexthop route"
        ::= { zxr10mrInstanceMIB 22 }

zxr10nexthopRouteEntry OBJECT-TYPE
        SYNTAX Zxr10nexthopRouteEntry
        MAX-ACCESS  not-accessible
        STATUS  current
        DESCRIPTION
            "An entry to multicast nexthop route"
        INDEX  { zxr10nexthopRouteVrfName,
        zxr10nexthopRouteIntfName,
        zxr10nexthopRouteIpAddr,
        zxr10nexthopRouteIpMask,
        zxr10nexthopRouteNextHopAddr,
        zxr10nexthopRouteSourceAddr,
        zxr10nexthopRouteGroupAddr}
        ::= { zxr10nexthopRouteTable 1 }

Zxr10nexthopRouteEntry ::=
        SEQUENCE {
            zxr10nexthopRouteVrfName
                DisplayString,
            zxr10nexthopRouteIntfName
                DisplayString,
            zxr10nexthopRouteIpAddr
                IpAddress,
            zxr10nexthopRouteIpMask
                IpAddress,
            zxr10nexthopRouteNextHopAddr
                IpAddress,
            zxr10nexthopRouteSourceAddr
                IpAddress,
            zxr10nexthopRouteGroupAddr
                IpAddress
        }

zxr10nexthopRouteVrfName OBJECT-TYPE
        SYNTAX DisplayString (SIZE (0..32))
        MAX-ACCESS  read-only
        STATUS  current
        DESCRIPTION
            "vrf name"
        ::= { zxr10nexthopRouteEntry 1 }

zxr10nexthopRouteIntfName OBJECT-TYPE
        SYNTAX DisplayString (SIZE (0..32))
        MAX-ACCESS  read-only
        STATUS  current
        DESCRIPTION
            "interface name"
        ::= { zxr10nexthopRouteEntry 2 }

zxr10nexthopRouteIpAddr OBJECT-TYPE
        SYNTAX IpAddress
        MAX-ACCESS  read-only
        STATUS  current
        DESCRIPTION
            "ip address"
        ::= { zxr10nexthopRouteEntry 3 }

zxr10nexthopRouteIpMask OBJECT-TYPE
        SYNTAX IpAddress
        MAX-ACCESS  read-only
        STATUS  current
        DESCRIPTION
            "ip address mask"
        ::= { zxr10nexthopRouteEntry 4 }

zxr10nexthopRouteNextHopAddr OBJECT-TYPE
        SYNTAX IpAddress
        MAX-ACCESS  read-only
        STATUS  current
        DESCRIPTION
            "nexthop address"
        ::= { zxr10nexthopRouteEntry 5 }
        
zxr10nexthopRouteSourceAddr OBJECT-TYPE
        SYNTAX IpAddress
        MAX-ACCESS  read-only
        STATUS  current
        DESCRIPTION
            "source address"
        ::= { zxr10nexthopRouteEntry 6 }
        
zxr10nexthopRouteGroupAddr OBJECT-TYPE
        SYNTAX IpAddress
        MAX-ACCESS  read-only
        STATUS  current
        DESCRIPTION
            "group address"
        ::= { zxr10nexthopRouteEntry 7 }
        
zxr10mrSegBorderTable OBJECT-TYPE
        SYNTAX  SEQUENCE OF Zxr10mrSegBorderEntry
        MAX-ACCESS  not-accessible
        STATUS  current
        DESCRIPTION
            "A table to segment border."
        ::= { zxr10mrInstanceMIB 23 }

zxr10mrSegBorderEntry OBJECT-TYPE
        SYNTAX Zxr10mrSegBorderEntry
        MAX-ACCESS  not-accessible
        STATUS  current
        DESCRIPTION
            "An entry to segment border."
        INDEX  { zxr10mrSegBorderVrfName }
        ::= { zxr10mrSegBorderTable 1 }

Zxr10mrSegBorderEntry ::=
        SEQUENCE {
            zxr10mrSegBorderVrfName
                DisplayString,            
            zxr10mrSegBorderIntraAs
                INTEGER,            
            zxr10mrSegBorderIntraAsNhp
                INTEGER,
            zxr10mrSegBorderInterAs
                INTEGER,            
            zxr10mrSegBorderInterAsNhp
                INTEGER
        }

zxr10mrSegBorderVrfName OBJECT-TYPE
        SYNTAX DisplayString (SIZE (0..32))
        MAX-ACCESS  not-accessible
        STATUS  current
        DESCRIPTION
            "VRF name"
        ::= { zxr10mrSegBorderEntry 1 }
        
zxr10mrSegBorderIntraAs OBJECT-TYPE
        SYNTAX INTEGER {false(255),true(1)}
        MAX-ACCESS  read-only
        STATUS  current
        DESCRIPTION
            "Intra-AS segment border router"
        ::= { zxr10mrSegBorderEntry 2 }
        
zxr10mrSegBorderIntraAsNhp OBJECT-TYPE
        SYNTAX INTEGER {false(255),true(1)}
        MAX-ACCESS  read-only
        STATUS  current
        DESCRIPTION
            "Segmented nexthop of extended community"
        ::= { zxr10mrSegBorderEntry 3 }

zxr10mrSegBorderInterAs OBJECT-TYPE
        SYNTAX INTEGER {false(255),true(1)}
        MAX-ACCESS  read-only
        STATUS  current
        DESCRIPTION
            "Inter-AS segment border router"
        ::= { zxr10mrSegBorderEntry 4 }
        
zxr10mrSegBorderInterAsNhp OBJECT-TYPE
        SYNTAX INTEGER {false(255),true(1)}
        MAX-ACCESS  read-only
        STATUS  current
        DESCRIPTION
            "Segmented nexthop of Inter-AS"
        ::= { zxr10mrSegBorderEntry 5 } 
        
END
