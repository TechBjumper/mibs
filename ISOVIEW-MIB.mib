ISOVIEW-MIB DEFINITIONS ::=
BEGIN

        IMPORTS
        OBJECT-TYPE FROM RFC-1212
		  NetworkAddress, IpAddress, enterprises,
        Counter, Gauge, TimeTicks
        FROM RFC1065-SMI;
 
        bitec           OBJECT IDENTIFIER ::= { enterprises 170 }
        bdn              OBJECT IDENTIFIER ::= { bitec 1}
        third-party    OBJECT IDENTIFIER ::= { bdn 1}
        retix            OBJECT IDENTIFIER ::= { third-party 1 } 
 
        station    OBJECT IDENTIFIER ::= { retix 1 } -- Station Group
        lapb       OBJECT IDENTIFIER ::= { retix 2 } -- LAPB Group
        ieee8023   OBJECT IDENTIFIER ::= { retix 3 } -- IEEE 802.3 Group
        phySerIf   OBJECT IDENTIFIER ::= { retix 4 } -- Physical Serial Group
        mlink      OBJECT IDENTIFIER ::= { retix 5 } -- Multilink Group
        lan        OBJECT IDENTIFIER ::= { retix 6 } -- LAN Group
        bridge     OBJECT IDENTIFIER ::= { retix 7 } -- Bridge Group
        product    OBJECT IDENTIFIER ::= { retix 8 } -- Product Group
        br12       OBJECT IDENTIFIER ::= { retix 9 } -- Br12 Bridge Group
        router     OBJECT IDENTIFIER ::= { retix 10 } -- Router Group
        boot       OBJECT IDENTIFIER ::= { retix 11 } -- Bootp Group
        boothelper OBJECT IDENTIFIER ::= { retix 12 } -- Boothelper Group
 
-- object types
 
        -- the Product group
        
        p4942      OBJECT IDENTIFIER ::= { product 1 } 
        p2244m2    OBJECT IDENTIFIER ::= { product 2 } 
        p2265      OBJECT IDENTIFIER ::= { product 3 } 
        p4660      OBJECT IDENTIFIER ::= { product 4 } 
        p4820      OBJECT IDENTIFIER ::= { product 5 } 
        p4880      OBJECT IDENTIFIER ::= { product 6 } 
        p4850      OBJECT IDENTIFIER ::= { product 7 } 
        p4760      OBJECT IDENTIFIER ::= { product 8 } 
        p4941      OBJECT IDENTIFIER ::= { product 9 } 
 
        -- Station Group
 
        stationTime OBJECT-TYPE
                SYNTAX  OCTET STRING (SIZE(13))
                ACCESS  read-write
                STATUS  mandatory
DESCRIPTION ""
                ::=  { station 1 }
 
        stationResetCounter OBJECT-TYPE
                SYNTAX  Counter
                ACCESS  read-only
                STATUS  mandatory
DESCRIPTION ""
                ::=  { station 2 }
 
        freeBufferCount OBJECT-TYPE
                SYNTAX  INTEGER
                ACCESS  read-only
                STATUS  optional
DESCRIPTION ""
                ::=  { station 3 }
 
        freeHeaderCount OBJECT-TYPE
                SYNTAX  INTEGER
                ACCESS  read-only
                STATUS  optional
DESCRIPTION ""
                ::=  { station 4 }
 
        physBlkSize OBJECT-TYPE
                SYNTAX  INTEGER (300..1600)
                ACCESS  read-only
                STATUS  optional
DESCRIPTION ""
                ::=  { station 5 }
 
        newPhysBlkSize OBJECT-TYPE
                SYNTAX  INTEGER (300..1600)
                ACCESS  read-write
                STATUS  optional
DESCRIPTION ""
                ::=  { station 6 }
 
        resetStation OBJECT-TYPE
                SYNTAX  INTEGER
                ACCESS  read-write
                STATUS  mandatory
DESCRIPTION ""
                ::=  { station 7 }
 
        initStation OBJECT-TYPE
                SYNTAX  INTEGER
                ACCESS  read-write
                STATUS  mandatory
DESCRIPTION ""
                ::=  { station 8 }
 
        resetStats OBJECT-TYPE
                SYNTAX  INTEGER
                ACCESS  read-write
                STATUS  mandatory
DESCRIPTION ""
                ::=  { station 9 }
 
        processorLoading OBJECT-TYPE
                SYNTAX  INTEGER
                ACCESS  read-only
                STATUS  optional
DESCRIPTION ""
                ::=  { station 10 }
 
        trapDestinationTable OBJECT IDENTIFIER ::= { station 11 }
 
        trapDestTable OBJECT-TYPE
                SYNTAX  SEQUENCE OF TrapDestEntry
                ACCESS  read-write
                STATUS  mandatory
DESCRIPTION ""
                ::=  { trapDestinationTable 1 }
 
        trapDestEntry OBJECT-TYPE
                SYNTAX  TrapDestEntry
                ACCESS  read-write
                STATUS  mandatory
DESCRIPTION ""
                INDEX   {trapDestEntryIpAddr}
                ::=  { trapDestTable 1 }
 
        TrapDestEntry ::= SEQUENCE {
                                trapDestEntryIpAddr
                                        IpAddress,
                                trapDestEntryCommunityName
                                        OCTET STRING,
                                trapDestEntryType
                                        INTEGER
                                }
 
        trapDestEntryIpAddr OBJECT-TYPE
                SYNTAX  IpAddress
                ACCESS  read-write
                STATUS  mandatory
DESCRIPTION ""
                ::=  { trapDestEntry 1 }
 
        trapDestEntryCommunityName OBJECT-TYPE
                SYNTAX  OCTET STRING (SIZE(0..10))
                ACCESS  read-write
                STATUS  mandatory
DESCRIPTION ""
                ::=  { trapDestEntry 2 }
 
        trapDestEntryType OBJECT-TYPE
                SYNTAX  INTEGER
                ACCESS  read-write
                STATUS  mandatory
DESCRIPTION ""
                ::=  { trapDestEntry 3 }
 
        trapDestAction OBJECT-TYPE
                SYNTAX  INTEGER
                ACCESS  read-write
                STATUS  mandatory
DESCRIPTION ""
                ::=  { trapDestinationTable 2 }
 
        trapDestPage OBJECT-TYPE
                SYNTAX  OCTET STRING (SIZE(240))
                ACCESS  read-only
                STATUS  mandatory
DESCRIPTION ""
                ::=  { trapDestinationTable 3 }
 
        passWord OBJECT-TYPE
                SYNTAX  OCTET STRING (SIZE(0..10))
                ACCESS  read-write
                STATUS  optional
DESCRIPTION ""
                ::=  { station 12 }
 
        snmpAccessPolicyObject OBJECT IDENTIFIER ::= { station 13 }
 
        snmpAccessPolicyTable OBJECT-TYPE
                SYNTAX  SEQUENCE OF SnmpAccessPolicyEntry
                ACCESS  read-write
                STATUS  mandatory
DESCRIPTION ""
                ::=  { snmpAccessPolicyObject 1 }
 
        snmpAccessPolicyEntry OBJECT-TYPE
                SYNTAX  SnmpAccessPolicyEntry
                ACCESS  read-write
                STATUS  mandatory
DESCRIPTION ""
                INDEX   {accessPolicyIndex}
                ::=  { snmpAccessPolicyTable 1 }
 
         SnmpAccessPolicyEntry ::= SEQUENCE {
                accessPolicyIndex
                        INTEGER,
                communityName
                        OCTET STRING (SIZE(0..10)),
                accessMode
                        INTEGER,
                snmpAccessPolicyType
                        INTEGER
                }
 
        accessPolicyIndex OBJECT-TYPE
                SYNTAX  INTEGER
                ACCESS  read-write
                STATUS  mandatory
DESCRIPTION ""
                ::=  { snmpAccessPolicyEntry 1 }
 
        communityName OBJECT-TYPE
                SYNTAX  OCTET STRING ( SIZE (0..10))
                ACCESS  read-write
                STATUS  mandatory
DESCRIPTION ""
                ::=  { snmpAccessPolicyEntry 2 }
 
        accessMode OBJECT-TYPE
                SYNTAX  INTEGER
                ACCESS  read-write
                STATUS  mandatory
DESCRIPTION ""
                ::=  { snmpAccessPolicyEntry 3 }
 
        snmpAccessPolicyType OBJECT-TYPE
                SYNTAX  INTEGER
                ACCESS  read-write
                STATUS  mandatory
DESCRIPTION ""
                ::=  { snmpAccessPolicyEntry 4 }
 
        snmpAccessPolicyAction OBJECT-TYPE
                SYNTAX  INTEGER
                ACCESS  read-write
                STATUS  mandatory
DESCRIPTION ""
                ::=  { snmpAccessPolicyObject 2 }
 
        snmpAccessPolicyPage OBJECT-TYPE
                SYNTAX  OCTET STRING (SIZE(256))
                ACCESS  read-only
                STATUS  mandatory
DESCRIPTION ""
                ::=  { snmpAccessPolicyObject 3 }
 
        authenticationTrapStatus OBJECT-TYPE
                SYNTAX  INTEGER (0..1)
                ACCESS  read-write
                STATUS  mandatory
DESCRIPTION ""
                ::=  { station 14 }
 
        serialTxQueueSize OBJECT-TYPE
                SYNTAX  INTEGER (1..127)
                ACCESS  read-write
                STATUS  optional
DESCRIPTION ""
                ::=  { station 15 }
 
        internalQueueCurrentLength OBJECT-TYPE
                SYNTAX  INTEGER
                ACCESS  read-only
                STATUS  optional
DESCRIPTION ""
                ::=  { station 16 }
 
        queueUpperLimit OBJECT-TYPE
                SYNTAX  INTEGER
                ACCESS  read-write
                STATUS  optional
DESCRIPTION ""
                ::=  { station 17 }
 
        lanQueueSize OBJECT-TYPE
                SYNTAX  INTEGER
                ACCESS  read-only
                STATUS  optional
DESCRIPTION ""
                ::=  { station 18 }
 
        --  LAPB Group
 
        lapbNumber OBJECT-TYPE
                SYNTAX  INTEGER
                ACCESS  read-only
                STATUS  mandatory
DESCRIPTION ""
                ::=  { lapb 1 }
 
        lapbTable OBJECT-TYPE
                SYNTAX  SEQUENCE OF LapbEntry
                ACCESS  read-write
                STATUS  mandatory
DESCRIPTION ""
                ::=  { lapb 2 }
 
        lapbEntry OBJECT-TYPE
                SYNTAX  LapbEntry
                ACCESS  read-write
                STATUS  mandatory
DESCRIPTION ""
                INDEX   {lapbIndex}
                ::=  { lapbTable 1 }
 
        LapbEntry ::= SEQUENCE {
                lapbIndex
                        INTEGER,
                lapbModeT1
                        INTEGER (0..1),
                lapbAutoT1value
                        INTEGER,
                lapbManualT1value
                        INTEGER (10..5000),
                lapbWindow
                        INTEGER (7..127),
                lapbPolarity
                        INTEGER (0..1),
                lapbResetCount
                        Counter,
                lapbSendFrameCount
                        Counter,
                lapbRcvFrameCount
                        Counter,
                lapbSendOctetCount
                        Counter,
                lapbRcvOctetCount
                        Counter,
                lapbAbortCount
                        Counter,
                lapbCrcErrorCount
                        Counter,
                lapbState
                        INTEGER (0..3),
                lapbLastResetTime
                        OCTET STRING (SIZE (13)),
                lapbLastResetReason
                        INTEGER (0..8),
                lapbLinkReset
                        INTEGER
                }
 
        lapbIndex OBJECT-TYPE
                SYNTAX  INTEGER
                ACCESS  read-only
                STATUS  mandatory
DESCRIPTION ""
                ::=  { lapbEntry 1 }
 
        lapbModeT1 OBJECT-TYPE
                SYNTAX  INTEGER (0..1)
                ACCESS  read-write
                STATUS  mandatory
DESCRIPTION ""
                ::=  { lapbEntry 2 }
 
        lapbAutoT1value OBJECT-TYPE
                SYNTAX  INTEGER
                ACCESS  read-only
                STATUS  mandatory
DESCRIPTION ""
                ::=  { lapbEntry 3 }
 
        lapbManualT1value OBJECT-TYPE
                SYNTAX  INTEGER (10..5000)
                ACCESS  read-write
                STATUS  mandatory
DESCRIPTION ""
                ::=  { lapbEntry 4 }
 
        lapbWindow OBJECT-TYPE
                SYNTAX  INTEGER (7..127)
                ACCESS  read-only
                STATUS  mandatory
DESCRIPTION ""
                ::=  { lapbEntry 5 }
 
        lapbPolarity OBJECT-TYPE
                SYNTAX  INTEGER (0..1)
                ACCESS  read-only
                STATUS  mandatory
DESCRIPTION ""
                ::=  { lapbEntry 6 }
 
        lapbResetCount OBJECT-TYPE
                SYNTAX  Counter
                ACCESS  read-only
                STATUS  mandatory
DESCRIPTION ""
                ::=  { lapbEntry 7 }
 
        lapbSendFrameCount OBJECT-TYPE
                SYNTAX  Counter
                ACCESS  read-only
                STATUS  mandatory
DESCRIPTION ""
                ::=  { lapbEntry 8 }
 
        lapbRcvFrameCount OBJECT-TYPE
                SYNTAX  Counter
                ACCESS  read-only
                STATUS  mandatory
DESCRIPTION ""
                ::=  { lapbEntry 9 }
 
        lapbSendOctetCount OBJECT-TYPE
                SYNTAX  Counter
                ACCESS  read-only
                STATUS  mandatory
DESCRIPTION ""
                ::=  { lapbEntry 10 }
 
        lapbRcvOctetCount OBJECT-TYPE
                SYNTAX  Counter
                ACCESS  read-only
                STATUS  mandatory
DESCRIPTION ""
                ::=  { lapbEntry 11 }
 
        lapbAbortCount OBJECT-TYPE
                SYNTAX  Counter
                ACCESS  read-only
                STATUS  mandatory
DESCRIPTION ""
                ::=  { lapbEntry 12 }
 
        lapbCrcErrorCount OBJECT-TYPE
                SYNTAX  Counter
                ACCESS  read-only
                STATUS  mandatory
DESCRIPTION ""
                ::=  { lapbEntry 13 }
 
        lapbState OBJECT-TYPE
                SYNTAX  INTEGER (0..3)
                ACCESS  read-only
                STATUS  mandatory
DESCRIPTION ""
                ::=  { lapbEntry 14 }
 
        lapbLastResetTime OBJECT-TYPE
                SYNTAX  OCTET STRING (SIZE (13))
                ACCESS  read-only
                STATUS  mandatory
DESCRIPTION ""
                ::=  { lapbEntry 15 }
 
        lapbLastResetReason OBJECT-TYPE
                SYNTAX  INTEGER (0..8)
                ACCESS  read-only
                STATUS  mandatory
DESCRIPTION ""
                ::=  { lapbEntry 16 }
 
        lapbLinkReset OBJECT-TYPE
                SYNTAX  INTEGER 
                ACCESS  read-write
                STATUS  mandatory
DESCRIPTION ""
                ::=  { lapbEntry 17 }
 
        lapbRetryCount OBJECT-TYPE
                SYNTAX  INTEGER
                ACCESS  read-write
                STATUS  mandatory
DESCRIPTION ""
                ::=  { lapb 3 }
 
        --  IEEE8023 Group
 
        ieee8023Number   OBJECT-TYPE
                SYNTAX  INTEGER
                ACCESS  read-only
                STATUS  mandatory
DESCRIPTION ""
                ::= { ieee8023 1 }
 
        ieee8023Table OBJECT-TYPE
                SYNTAX  SEQUENCE OF Ieee8023Entry
                ACCESS  read-write
                STATUS  mandatory
DESCRIPTION ""
                ::= { ieee8023 2 }
 
        ieee8023Entry OBJECT-TYPE
                SYNTAX  Ieee8023Entry
                ACCESS  read-write
                STATUS  mandatory
DESCRIPTION ""
                INDEX   {ieee8023Index}
                ::= { ieee8023Table 1 }
 
        Ieee8023Entry ::= SEQUENCE {
                ieee8023Index
                        INTEGER,
                ieee8023FramesTransmittedOks
                        Counter,
                ieee8023SingleCollisionFrames
                        Counter,
                ieee8023MultipleCollisionFrames
                        Counter,
                ieee8023OctetsTransmittedOks
                        Counter,
                ieee8023DeferredTransmissions
                        Counter,
                ieee8023MulticastFramesTransmittedOks
                        Counter,
                ieee8023BroadcastFramesTransmittedOks
                        Counter,
                ieee8023Latecollisions
                        Counter,
                ieee8023ExcessiveCollisionsColls
                        Counter,
                ieee8023InternalMacTransmitErrors
                        Counter,
                ieee8023CarrierSenseErrors
                        Counter,
                ieee8023ExcessiveDeferals
                        Counter,
                ieee8023FramesReceivedOks
                        Counter,
                ieee8023OctetsReceivedOks
                        Counter,
                ieee8023MulticastFramesReceivedOks
                        Counter,
                ieee8023BroadcastFramesReceivedOks
                        Counter,
                ieee8023FrameTooLongs
                        Counter,
                ieee8023AlignmentErrors
                        Counter,
                ieee8023FCSErrors
                        Counter,
                ieee8023inRangeLengthErrors
                        Counter,
                ieee8023outOfRangeLengthFields
                        Counter,
                ieee8023InternalMACReceiveErrors
                        Counter,
                ieee8023InitializeMAC
                        INTEGER,
                ieee8023PromiscuousReceiveStatus
                        INTEGER,
                ieee8023MACSubLayerStatus
                        INTEGER,
                ieee8023TransmitStatus
                        INTEGER,
                ieee8023MulticastReceiveStatus
                        INTEGER,
                ieee8023MACAddress
                        OCTET STRING (SIZE(6)),
                ieee8023SQETestErrors
                        Counter
                }
 
        ieee8023Index   OBJECT-TYPE
                SYNTAX  INTEGER
                ACCESS  read-only
                STATUS  mandatory
DESCRIPTION ""
                ::= { ieee8023Entry 1 }
        
        ieee8023FramesTransmittedOks OBJECT-TYPE
                SYNTAX  Counter
                ACCESS  read-only
                STATUS  mandatory
DESCRIPTION ""
                ::= { ieee8023Entry 2 }
        
        ieee8023SingleCollisionFrames OBJECT-TYPE
                SYNTAX  Counter
                ACCESS  read-only
                STATUS  mandatory
DESCRIPTION ""
                ::= { ieee8023Entry 3 }
        
        ieee8023MultipleCollisionFrames OBJECT-TYPE
                SYNTAX  Counter
                ACCESS  read-only
                STATUS  mandatory
DESCRIPTION ""
                ::= { ieee8023Entry 4 }
        
        ieee8023OctetsTransmittedOks OBJECT-TYPE
                SYNTAX  Counter
                ACCESS  read-only
                STATUS  mandatory
DESCRIPTION ""
                ::= { ieee8023Entry 5 }
        
        ieee8023DeferredTransmissions OBJECT-TYPE
                SYNTAX  Counter
                ACCESS  read-only
                STATUS  mandatory
DESCRIPTION ""
                ::= { ieee8023Entry 6 }
        
        ieee8023MulticastFramesTransmittedOks OBJECT-TYPE
                SYNTAX  Counter
                ACCESS  read-only
                STATUS  optional
DESCRIPTION ""
                ::= { ieee8023Entry 7 }
        
        ieee8023BroadcastFramesTransmittedOks OBJECT-TYPE
                SYNTAX  Counter
                ACCESS  read-only
                STATUS  optional
DESCRIPTION ""
                ::= { ieee8023Entry 8 }
        
        ieee8023LateCollisions OBJECT-TYPE
                SYNTAX  Counter
                ACCESS  read-only
                STATUS  mandatory
DESCRIPTION ""
                ::= { ieee8023Entry 9 }
        
        ieee8023ExcessiveCollisions OBJECT-TYPE
                SYNTAX  Counter
                ACCESS  read-only
                STATUS  mandatory
DESCRIPTION ""
                ::= { ieee8023Entry 10 }
        
        ieee8023InternalMACTransmitErrors OBJECT-TYPE
                SYNTAX  Counter
                ACCESS  read-only
                STATUS  mandatory
DESCRIPTION ""
                ::= { ieee8023Entry 11 }
        
        ieee8023CarrierSenseErrors OBJECT-TYPE
                SYNTAX  Counter
                ACCESS  read-only
                STATUS  mandatory
DESCRIPTION ""
                ::= { ieee8023Entry 12 }
        
        ieee8023ExcessiveDeferrals OBJECT-TYPE
                SYNTAX  Counter
                ACCESS  read-only
                STATUS  optional
DESCRIPTION ""
                ::= { ieee8023Entry 13 }
        
        ieee8023FramesReceivedOks OBJECT-TYPE
                SYNTAX  Counter
                ACCESS  read-only
                STATUS  mandatory
DESCRIPTION ""
                ::= { ieee8023Entry 14 }
        
        ieee8023OctetsReceivedOks OBJECT-TYPE
                SYNTAX  Counter
                ACCESS  read-only
                STATUS  mandatory
DESCRIPTION ""
                ::= { ieee8023Entry 15 }
        
        ieee8023MulticastFramesReceivedOks OBJECT-TYPE
                SYNTAX  Counter
                ACCESS  read-only
                STATUS  optional
DESCRIPTION ""
                ::= { ieee8023Entry 16 }
        
        ieee8023BroadcastFramesReceivedOks OBJECT-TYPE
                SYNTAX  Counter
                ACCESS  read-only
                STATUS  optional
DESCRIPTION ""
                ::= { ieee8023Entry 17 }
        
        ieee8023FrameTooLongs OBJECT-TYPE
                SYNTAX  Counter
                ACCESS  read-only
                STATUS  optional
DESCRIPTION ""
                ::= { ieee8023Entry 18 }
        
        ieee8023AlignmentErrors OBJECT-TYPE
                SYNTAX  Counter
                ACCESS  read-only
                STATUS  mandatory
DESCRIPTION ""
                ::= { ieee8023Entry 19 }
        
        ieee8023FCSErrors OBJECT-TYPE
                SYNTAX  Counter
                ACCESS  read-only
                STATUS  mandatory
DESCRIPTION ""
                ::= { ieee8023Entry 20 }
        
        ieee8023inRangeLengthErrors OBJECT-TYPE
                SYNTAX  Counter
                ACCESS  read-only
                STATUS  optional
DESCRIPTION ""
                ::= { ieee8023Entry 21 }
        
        ieee8023outOfRangeLengthFields OBJECT-TYPE
                SYNTAX  Counter
                ACCESS  read-only
                STATUS  optional
DESCRIPTION ""
                ::= { ieee8023Entry 22 }
        
        ieee8023InternalMACReceiveErrors OBJECT-TYPE
                SYNTAX  Counter
                ACCESS  read-only
                STATUS  mandatory
DESCRIPTION ""
                ::= { ieee8023Entry 23 }
        
        ieee8023InitializeMAC OBJECT-TYPE
                SYNTAX  INTEGER {
                        initialize (1)
                        }
                ACCESS  read-write
                STATUS  mandatory
DESCRIPTION ""
                ::= { ieee8023Entry 24 }
        
        ieee8023PromiscuousReceiveStatus OBJECT-TYPE
                SYNTAX  INTEGER {
                        enabled (1)
                        }
                ACCESS  read-write
                STATUS  mandatory
DESCRIPTION ""
                ::= { ieee8023Entry 25 }
        
        ieee8023MACSubLayerStatus OBJECT-TYPE
                SYNTAX  INTEGER {
                        enabled (1)
                        }
                ACCESS  read-write
                STATUS  optional
DESCRIPTION ""
                ::= { ieee8023Entry 26 }
        
        ieee8023TransmitStatus OBJECT-TYPE
                SYNTAX  INTEGER {
                        enabled (1),
                        disabled (2)
                        }
                ACCESS  read-write
                STATUS  optional
DESCRIPTION ""
                ::= { ieee8023Entry 27 }
        
        ieee8023MulticastReceiveStatus OBJECT-TYPE
                SYNTAX  INTEGER {
                        enabled (1)
                        }
                ACCESS  read-write
                STATUS  optional
DESCRIPTION ""
                ::= { ieee8023Entry 28 }
        
        ieee8023MACAddress OBJECT-TYPE
                SYNTAX  OCTET STRING (SIZE (6))
                ACCESS  read-only
                STATUS  optional
DESCRIPTION ""
                ::= { ieee8023Entry 29 }
        
        ieee8023SQETestErrors OBJECT-TYPE
                SYNTAX  Counter
                ACCESS  read-only
                STATUS  mandatory
DESCRIPTION ""
                ::= { ieee8023Entry 30 }
        
        ieee8023NewMACAddress OBJECT-TYPE
                SYNTAX  SEQUENCE OF Ieee8023newMACAddressEntry
                ACCESS  read-write
                STATUS  mandatory
DESCRIPTION ""
                ::= { ieee8023 3 }
        
        ieee8023NewMACAddressEntry OBJECT-TYPE
                SYNTAX  Ieee8023newMACAddressEntry
                ACCESS  read-write
                STATUS  mandatory
DESCRIPTION ""
                INDEX   {ieee8023NewMACAddressIndex}
                ::= { ieee8023NewMACAddress 1 }
 
        Ieee8023newMACAddressEntry ::= SEQUENCE {
                ieee8023NewMACAddressIndex
                        INTEGER,
                ieee8023NewMACAddressValue
                        OCTET STRING (SIZE (6))
                }
 
        ieee8023NewMACAddressIndex OBJECT-TYPE
                SYNTAX  INTEGER
                ACCESS  read-only
                STATUS  mandatory
DESCRIPTION ""
                ::= { ieee8023NewMACAddressEntry 1 }
 
        ieee8023NewMACAddressValue OBJECT-TYPE
                SYNTAX  OCTET STRING (SIZE (6))
                ACCESS  read-write
                STATUS  mandatory
DESCRIPTION ""
                ::= { ieee8023NewMACAddressEntry 2 }
 
 
        --  Physical Serial Group
 
        phySerIfNumber OBJECT-TYPE
                SYNTAX  INTEGER
                ACCESS  read-only
                STATUS  mandatory
DESCRIPTION ""
                ::=  { phySerIf 1 }
 
        phySerIfTable OBJECT-TYPE
                SYNTAX  SEQUENCE OF PhySerIfEntry
                ACCESS  read-write
                STATUS  mandatory
DESCRIPTION ""
                ::=  { phySerIf 2 }
 
        phySerIfEntry OBJECT-TYPE
                SYNTAX  PhySerIfEntry
                ACCESS  read-write
                STATUS  mandatory
DESCRIPTION ""
                INDEX   {phySerIfIndex}
                ::=  { phySerIfTable 1 }
 
        PhySerIfEntry ::= SEQUENCE {
                phySerIfIndex
                        INTEGER,
                phySerIfInterfaceType
                        INTEGER,
                phySerIfMeasuredSpeed
                        INTEGER,
                phySerIfIsSpeedsettable
                        INTEGER,
                phySerIfPortSpeed
                        INTEGER,
                phySerIfTransitDelay
                        INTEGER,
                phySerIfT1clockSource
                        INTEGER,
                phySerIfT1SlotLvalue
                         INTEGER,
                phySerIfT1SlotHvalue
                         INTEGER,
                phySerIfT1dRatePerChan
                         INTEGER,
                phySerIfT1frameAndCode
                         INTEGER,
                phySerIfMeasuredSpeed
                        INTEGER,
                phySerIfPartnerAddress
                        OCTET STRING (SIZE (6))
                }
 
 
        phySerIfIndex OBJECT-TYPE
                SYNTAX  INTEGER
                ACCESS  read-only
                STATUS  mandatory
DESCRIPTION ""
                ::=  { phySerIfEntry 1 }
 
        phySerIfInterfaceType OBJECT-TYPE
                SYNTAX  INTEGER {
                        x21dte(1),
                        x21dce(2),
                        rs449(3),
                        g703(4),
                        v35(5),
                        v35btb(6),
                        rs232(7),
                        t1(8)
                        }
                ACCESS  read-write
                STATUS  mandatory
DESCRIPTION ""
                ::=  { phySerIfEntry 2 }
 
        phySerIfMeasuredSpeed OBJECT-TYPE
                SYNTAX  INTEGER
                ACCESS  read-only
                STATUS  mandatory
DESCRIPTION ""
                ::=  { phySerIfEntry 3 }
 
        phySerIfIsSpeedsettable OBJECT-TYPE
                SYNTAX  INTEGER (0..1)
                ACCESS  read-only
                STATUS  mandatory
DESCRIPTION ""
                ::=  { phySerIfEntry 4 }
 
        phySerIfPortSpeed OBJECT-TYPE
                SYNTAX  INTEGER {
                        b1200(1200),
                        b2400(2400),
                        b4800(4800),
                        b9600(9600),
                        b19200(19200),
                        b24000(24000),
                        b32000(32000),
                        b48000(48000),
                        b64000(64000),
                        b256000(256000),
                        b512000(512000),
                        b1024000(1024000),
                        b2048000(2048000)
                        }
                ACCESS  read-write
                STATUS  mandatory
DESCRIPTION ""
                ::=  { phySerIfEntry 5 }
 
        phySerIfTransitDelay OBJECT-TYPE
                SYNTAX  INTEGER
                ACCESS  read-only
                STATUS  mandatory
DESCRIPTION ""
                ::=  { phySerIfEntry 6 }
 
        phySerIfT1clockSource OBJECT-TYPE
                SYNTAX  INTEGER(0..2)
                ACCESS  read-write
                STATUS  mandatory
DESCRIPTION ""
                ::=  { phySerIfEntry 7 }
 
        phySerIfT1SlotLvalue OBJECT-TYPE
                SYNTAX  INTEGER (1..24)
                ACCESS  read-write
                STATUS  mandatory
DESCRIPTION ""
                ::=  { phySerIfEntry 8 }
 
        phySerIfT1SlotHvalue OBJECT-TYPE
                SYNTAX  INTEGER (1..24)
                ACCESS  read-write
                STATUS  mandatory
DESCRIPTION ""
                ::=  { phySerIfEntry 9 }
 
        phySerIfT1dRatePerChan OBJECT-TYPE
                SYNTAX  INTEGER (0..1)
                ACCESS  read-write
                STATUS  mandatory
DESCRIPTION ""
                ::=  { phySerIfEntry 10 }
 
        phySerIfT1frameAndCode OBJECT-TYPE
                SYNTAX  INTEGER (0..3) 
                ACCESS  read-write
                STATUS  mandatory
DESCRIPTION ""
                ::=  { phySerIfEntry 11 }
 
        phySerIfpartnerAddress OBJECT-TYPE
                SYNTAX  OCTET STRING (SIZE (0..6))
                ACCESS  read-only
                STATUS  mandatory
DESCRIPTION ""
                ::=  { phySerIfEntry 12 }
 
 
        --  Multilink Group
 
        mlinkNumber OBJECT-TYPE
                SYNTAX  INTEGER
                ACCESS  read-only
                STATUS  mandatory
DESCRIPTION ""
                ::=  { mlink 1 }
 
        mlinkTable OBJECT-TYPE
                SYNTAX  SEQUENCE OF MlinkEntry
                ACCESS  read-only
                STATUS  mandatory
DESCRIPTION ""
                ::=  { mlink 2 }
 
        mlinkEntry OBJECT-TYPE
                SYNTAX  MlinkEntry
                ACCESS  read-only
                STATUS  mandatory
DESCRIPTION ""
                INDEX   {mlinkIndex}
                ::=  { mlinkTable 1 }
 
        MlinkEntry ::= SEQUENCE {
                mlinkIndex
                        INTEGER,
                mlinkState
                        INTEGER,
                mlinkSendSeq
                         INTEGER,
                mlinkRcvSeq
                        INTEGER,
                mlinkSendUpperEdge
                        INTEGER,
                mlinkRcvUpperEdge
                        INTEGER,
                mlinkFramesLost
                        Counter,
                deletedMlinkFrames
                        Counter,
                expressQueueCurrentLength
                        INTEGER,
                expressQueueUpperLimit
                        INTEGER,
                hiPriQueueCurrentLength
                        INTEGER,
                hiPriQueueUpperLimit
                        INTEGER,
                loPriQueueCurrentLength
                        INTEGER,
                loPriQueueUpperLimit
                        INTEGER
                }
 
        mlinkIndex OBJECT-TYPE
                SYNTAX  INTEGER
                ACCESS  read-only
                STATUS  mandatory
DESCRIPTION ""
                ::=  { mlinkEntry 1 }
 
        mlinkState OBJECT-TYPE
                SYNTAX  INTEGER (0..3)
                ACCESS  read-only
                STATUS  mandatory
DESCRIPTION ""
                ::=  { mlinkEntry 2 }
 
        mlinkSendSeq OBJECT-TYPE
                SYNTAX  INTEGER
                ACCESS  read-only
                STATUS  mandatory
DESCRIPTION ""
                ::=  { mlinkEntry 3 }
 
        mlinkRcvSeq OBJECT-TYPE
                SYNTAX  INTEGER
                ACCESS  read-only
                STATUS  mandatory
DESCRIPTION ""
                ::=  { mlinkEntry 4 }
 
        mlinkSendUpperEdge OBJECT-TYPE
                SYNTAX  INTEGER
                ACCESS  read-only
                STATUS  mandatory
DESCRIPTION ""
                ::=  { mlinkEntry 5 }
 
        mlinkRcvUpperEdge OBJECT-TYPE
                SYNTAX  INTEGER
                ACCESS  read-only
                STATUS  mandatory
DESCRIPTION ""
                ::=  { mlinkEntry 6 }
 
        mlinkFramesLost OBJECT-TYPE
                SYNTAX  Counter
                ACCESS  read-only
                STATUS  mandatory
DESCRIPTION ""
                ::=  { mlinkEntry 7 }
 
        deletedMlinkFrames OBJECT-TYPE
                SYNTAX  Counter
                ACCESS  read-only
                STATUS  mandatory
DESCRIPTION ""
                ::=  { mlinkEntry 8 }
 
        expressQueueCurrentLength OBJECT-TYPE
                SYNTAX  INTEGER
                ACCESS  read-only
                STATUS  mandatory
DESCRIPTION ""
                ::=  { mlinkEntry 9 }
 
        expressQueueUpperLimit OBJECT-TYPE
                SYNTAX  INTEGER
                ACCESS  read-only
                STATUS  mandatory
DESCRIPTION ""
                ::=  { mlinkEntry 10 }
 
        hiPriQueueCurrentLength OBJECT-TYPE
                SYNTAX  INTEGER
                ACCESS  read-only
                STATUS  mandatory
DESCRIPTION ""
                ::=  { mlinkEntry 11 }
 
        hiPriQueueUpperLimit OBJECT-TYPE
                SYNTAX  INTEGER
                ACCESS  read-only
                STATUS  mandatory
DESCRIPTION ""
                ::=  { mlinkEntry 12 }
 
        loPriQueueCurrentLength OBJECT-TYPE
                SYNTAX  INTEGER
                ACCESS  read-only
                STATUS  mandatory
DESCRIPTION ""
                ::=  { mlinkEntry 13 }
 
        loPriQueueUpperLimit OBJECT-TYPE
                SYNTAX  INTEGER
                ACCESS  read-only
                STATUS  mandatory
DESCRIPTION ""
                ::=  { mlinkEntry 14 }
 
        mlinkWindow OBJECT-TYPE
                SYNTAX  INTEGER
                ACCESS  read-write
                STATUS  mandatory
DESCRIPTION ""
                ::=  { mlink 3 }
 
        mlinkRxTimeout OBJECT-TYPE
                SYNTAX  INTEGER
                ACCESS  read-write
                STATUS  mandatory
DESCRIPTION ""
                ::=  { mlink 4 }
 
 
        --  LAN Group
 
        lanInterfaceType OBJECT-TYPE
                SYNTAX  INTEGER (1..3)
                ACCESS  read-only
                STATUS  mandatory
DESCRIPTION ""
                ::=  { lan 1 }
 
        --  Bridge Group
 
        portNumber OBJECT-TYPE
                SYNTAX  INTEGER
                ACCESS  read-only
                STATUS  mandatory
DESCRIPTION ""
                ::=  { bridge 1 }
 
        bridgeStatsTable OBJECT-TYPE
                SYNTAX  SEQUENCE OF BridgeStatsEntry
                ACCESS  read-only
                STATUS  mandatory
DESCRIPTION ""
                ::=  { bridge 2 }
 
        bridgeStatsEntry OBJECT-TYPE
                SYNTAX  BridgeStatsEntry
                ACCESS  read-write
                STATUS  mandatory
DESCRIPTION ""
                INDEX   {bridgeStatsIndex}
                ::=  { bridgeStatsTable 1 }
 
        BridgeStatsEntry ::= SEQUENCE {
                bridgeStatsIndex
                        INTEGER,
                averageForwarded
                        Counter,
                maxForwarded
                        Counter,
                averageRejected
                        Counter,
                maxRejected
                        Counter,
                lanAccepts
                        Counter,
                lanRejects
                        Counter,
                deletedFrames
                        Counter
                }
 
        bridgeStatsIndex OBJECT-TYPE
                SYNTAX  INTEGER
                ACCESS  read-only
                STATUS  mandatory
DESCRIPTION ""
                ::=  { bridgeStatsEntry 1 }
 
        averageForwarded OBJECT-TYPE
                SYNTAX  Counter
                ACCESS  read-only
                STATUS  mandatory
DESCRIPTION ""
                ::=  { bridgeStatsEntry 2 }
 
        maxForwarded OBJECT-TYPE
                SYNTAX Counter
                ACCESS  read-only
                STATUS  mandatory
DESCRIPTION ""
                ::=  { bridgeStatsEntry 3 }
 
        averageRejected OBJECT-TYPE
                SYNTAX  Counter
                ACCESS  read-only
                STATUS  mandatory
DESCRIPTION ""
                ::=  { bridgeStatsEntry 4 }
 
        maxRejected OBJECT-TYPE
                SYNTAX Counter
                ACCESS  read-only
                STATUS  mandatory
DESCRIPTION ""
                ::=  { bridgeStatsEntry 5 }
 
        lanAccepts OBJECT-TYPE
                SYNTAX Counter
                ACCESS  read-only
                STATUS  mandatory
DESCRIPTION ""
                ::=  { bridgeStatsEntry 6 }
 
        lanRejects OBJECT-TYPE
                SYNTAX Counter
                ACCESS  read-only
                STATUS  mandatory
DESCRIPTION ""
                ::=  { bridgeStatsEntry 7 }
 
        deletedLanFrames OBJECT-TYPE
                SYNTAX Counter
                ACCESS  read-only
                STATUS  mandatory
DESCRIPTION ""
                ::=  { bridgeStatsEntry 8 }
 
        stpTable OBJECT-TYPE
                SYNTAX  SEQUENCE OF StpEntry
                ACCESS  read-write
                STATUS  mandatory
DESCRIPTION ""
                ::=  { bridge 3 }
 
        stpEntry OBJECT-TYPE
                SYNTAX  StpEntry
                ACCESS  read-write
                STATUS  mandatory
DESCRIPTION ""
                INDEX   {stpIndex}
                ::=  { stpTable 1 }
 
        StpEntry ::= SEQUENCE {
                stpIndex
                        INTEGER,
                portSpatState
                        INTEGER,
                pathCostMode
                        INTEGER,
                pathCostAutoValue
                        INTEGER,
                pathCostManValue
                        INTEGER,
                portPriorityMode
                        INTEGER,
                portPriorityAutoValue
                        INTEGER,
                portPriorityManualValue
                        INTEGER
                }
 
 
        stpIndex OBJECT-TYPE
                SYNTAX  INTEGER
                ACCESS  read-only
                STATUS  mandatory
DESCRIPTION ""
                ::=  { stpEntry 1 }
 
        pathCostMode OBJECT-TYPE
                SYNTAX INTEGER(0..1)
                ACCESS  read-write
                STATUS  mandatory
DESCRIPTION ""
                ::=  { stpEntry 2 }
 
        pathCostAutoValue OBJECT-TYPE
                SYNTAX INTEGER
                ACCESS  read-only
                STATUS  mandatory
DESCRIPTION ""
                ::=  { stpEntry 3 }
 
        pathCostManualValue OBJECT-TYPE
                SYNTAX INTEGER(0..65535)
                ACCESS  read-write
                STATUS  mandatory
DESCRIPTION ""
                ::=  { stpEntry 4 }
 
        portSpatState OBJECT-TYPE
                SYNTAX INTEGER
                ACCESS  read-only
                STATUS  mandatory
DESCRIPTION ""
                ::=  { stpEntry 5 }
 
        portPriorityMode OBJECT-TYPE
                SYNTAX INTEGER(0..1)
                ACCESS  read-write
                STATUS  mandatory
DESCRIPTION ""
                ::=  { stpEntry 6 }
 
        portPriorityAutoValue OBJECT-TYPE
                SYNTAX INTEGER
                ACCESS  read-only
                STATUS  mandatory
DESCRIPTION ""
                ::=  { stpEntry 7 }
 
        portPriorityManualValue OBJECT-TYPE
                SYNTAX INTEGER(0..255)
                ACCESS  read-write
                STATUS  mandatory
DESCRIPTION ""
                ::=  { stpEntry 8 }
 
        spanningTree OBJECT-TYPE
                SYNTAX INTEGER (0..1)
                ACCESS read-write
                STATUS mandatory
DESCRIPTION ""
                ::=  { bridge 4 }
 
        spatPriority OBJECT-TYPE
                SYNTAX INTEGER (1..65535)
                ACCESS read-write
                STATUS mandatory
DESCRIPTION ""
                ::=  { bridge 5 }
 
        spatHelloTimer OBJECT-TYPE
                SYNTAX INTEGER (1..10)
                ACCESS read-write
                STATUS mandatory
DESCRIPTION ""
                ::=  { bridge 6 }
 
        spatResetTimer OBJECT-TYPE
                SYNTAX INTEGER (1..1800)
                ACCESS read-write
                STATUS mandatory
DESCRIPTION ""
                ::=  { bridge 7 }
 
        spatVersion OBJECT-TYPE
                SYNTAX INTEGER {
                          revisionC(3),
                          revision8(8)
                          }
                ACCESS read-write
                STATUS mandatory
DESCRIPTION ""
                ::=  { bridge 8 }
 
        spanningMcastAddr OBJECT-TYPE
                SYNTAX OCTET STRING ( SIZE (6))
                ACCESS read-write
                STATUS mandatory
DESCRIPTION ""
                ::=  { bridge 9 }
 
        operatingMode OBJECT-TYPE
                SYNTAX  INTEGER (0..1)
                ACCESS  read-write
                STATUS  mandatory
DESCRIPTION ""
                ::=  { bridge 10 }
 
        preconfSourceFilter OBJECT-TYPE
                SYNTAX  INTEGER (0..1)
                ACCESS  read-write
                STATUS  mandatory
DESCRIPTION ""
                ::=  { bridge 11 }
 
        typeFilter OBJECT-TYPE
                SYNTAX  INTEGER (0..1)
                ACCESS  read-write
                STATUS  mandatory
DESCRIPTION ""
                ::=  { bridge 12 }
 
        typePrioritisation OBJECT-TYPE
                SYNTAX  INTEGER (0..1)
                ACCESS  read-write
                STATUS  mandatory
DESCRIPTION ""
                ::=  { bridge 13 }
 
        dynamicLearningInLM OBJECT-TYPE
                SYNTAX  INTEGER (0..1)
                ACCESS  read-write
                STATUS  mandatory
DESCRIPTION ""
                ::=  { bridge 14 }
 
        forgetAddressTimer OBJECT-TYPE
                SYNTAX  INTEGER (24..1000)
                ACCESS  read-write
                STATUS  mandatory
DESCRIPTION ""
                ::=  { bridge 15 }
 
        deleteAddressTimer OBJECT-TYPE
                SYNTAX  INTEGER (1..20000)
                ACCESS  read-write
                STATUS  mandatory
DESCRIPTION ""
                ::=  { bridge 16 }
 
        multicastDisposition OBJECT-TYPE
                SYNTAX  INTEGER (0..1)
                ACCESS  read-write
                STATUS  mandatory
DESCRIPTION ""
                ::=  { bridge 17 }
 
        filterMatches OBJECT-TYPE
                SYNTAX  INTEGER (0..1)
                ACCESS  read-write
                STATUS  mandatory
DESCRIPTION ""
                ::=  { bridge 18 }
 
        ieeeFormatFilter OBJECT-TYPE
                SYNTAX  INTEGER (0..1)
                ACCESS  read-write
                STATUS  mandatory
DESCRIPTION ""
                ::=  { bridge 19 }
 
        priorityMatches OBJECT-TYPE
                SYNTAX  INTEGER (0..1)
                ACCESS  read-write
                STATUS  mandatory
DESCRIPTION ""
                ::=  { bridge 20 }
 
        ieeeFormatPriority OBJECT-TYPE
                SYNTAX  INTEGER (0..1)
                ACCESS  read-write
                STATUS  mandatory
DESCRIPTION ""
                ::=  { bridge 21 }
 
        averagePeriod OBJECT-TYPE
                SYNTAX  INTEGER
                ACCESS  read-only
                STATUS  mandatory
DESCRIPTION ""
                ::=  { bridge 22 }
 
        triangulation OBJECT-TYPE
                SYNTAX  INTEGER(0..1)
                ACCESS  read-write
                STATUS  mandatory
DESCRIPTION ""
                ::=  { bridge 23 }
 
        adaptiveRouting OBJECT-TYPE
                SYNTAX  INTEGER (0..1)
                ACCESS  read-write
                STATUS  mandatory
DESCRIPTION ""
                ::=  { bridge 24 }
 
        adaptiveMcastAddr OBJECT-TYPE
                SYNTAX  OCTET STRING ( SIZE (6))
                ACCESS  read-write
                STATUS  mandatory
DESCRIPTION ""
                ::=  { bridge 25 }
 
arAddressInfo OBJECT IDENTIFIER ::= { bridge 26 }
 
        standbyRemote OBJECT-TYPE
                SYNTAX INTEGER
                ACCESS read-only
                STATUS mandatory
DESCRIPTION ""
                ::=  { arAddressInfo 1 }
 
        standbyLocal OBJECT-TYPE
                SYNTAX INTEGER
                ACCESS read-only
                STATUS mandatory
DESCRIPTION ""
                ::=  { arAddressInfo 2 }
 
        activeRemote OBJECT-TYPE
                SYNTAX INTEGER
                ACCESS read-only
                STATUS mandatory
DESCRIPTION ""
                ::=  { arAddressInfo 3 }
 
        activeLocal OBJECT-TYPE
                SYNTAX INTEGER
                ACCESS read-only
                STATUS mandatory
DESCRIPTION ""
                ::=  { arAddressInfo 4 }
 
        maxSerialLoading OBJECT-TYPE
                SYNTAX INTEGER
                ACCESS read-write
                STATUS mandatory
DESCRIPTION ""
                ::=     { bridge 27 }
                        
        serialLoadPeriod OBJECT-TYPE
                SYNTAX INTEGER
                ACCESS read-write
                STATUS mandatory
DESCRIPTION ""
                ::=     { bridge 28 }
 
        serialLoading OBJECT-TYPE
                SYNTAX  INTEGER
                ACCESS  read-only
                STATUS  mandatory
DESCRIPTION ""
                ::=  { bridge 29 }
 
        filteringDataBaseTable OBJECT IDENTIFIER ::= { bridge 30 }
 
        filteringDbTable OBJECT-TYPE
                SYNTAX SEQUENCE OF FilteringDbEntry
                ACCESS read-write
                STATUS mandatory
DESCRIPTION ""
                ::=  { filteringDataBaseTable 1 }
 
        filteringDbEntry OBJECT-TYPE
                SYNTAX SEQUENCE OF FilteringDbEntry
                ACCESS read-write
                STATUS mandatory
DESCRIPTION ""
                INDEX  {filteringDbMacAddress}
                ::=  { filteringDbTable 1 }
 
        FilteringDbEntry ::= SEQUENCE {
                filteringDbMacAddress
                        OCTET STRING,
                filteringDbDisposition
                        INTEGER,
                filteringDbStatus
                        INTEGER,
                filteringDbType
                        INTEGER
                }
 
        filteringDbMacAddress OBJECT-TYPE
                SYNTAX OCTET STRING
                ACCESS read-write
                STATUS mandatory
DESCRIPTION ""
                ::=  { filteringDbEntry 1 }
 
        filteringDbDisposition OBJECT-TYPE
                SYNTAX INTEGER
                ACCESS read-write
                STATUS mandatory
DESCRIPTION ""
                ::=  { filteringDbEntry 2 }
 
        filteringDbStatus OBJECT-TYPE
                SYNTAX INTEGER
                ACCESS read-write
                STATUS mandatory
DESCRIPTION ""
                ::=  { filteringDbEntry 3 }
 
        filteringDbType OBJECT-TYPE
                SYNTAX INTEGER
                ACCESS read-write
                STATUS mandatory
DESCRIPTION ""
                ::=  { filteringDbEntry 4 }
 
        filteringDbAction OBJECT-TYPE
                SYNTAX INTEGER
                ACCESS read-write
                STATUS mandatory
DESCRIPTION ""
                ::=  {filteringDataBaseTable 2 }
 
        filteringDbPage OBJECT IDENTIFIER ::= { filteringDataBaseTable 3 }
        -- filteringDbPage OBJECT-TYPE
                -- SYNTAX SEQUENCE OF FilteringDbPageValue
                -- ACCESS read-write
                -- STATUS mandatory
				-- DESCRIPTION ""
                -- ::=  { filteringDataBaseTable 3 }
 
        filteringDbPageValue OBJECT-TYPE
                SYNTAX OCTET STRING (SIZE(0..640))
                ACCESS read-write
                STATUS mandatory
DESCRIPTION ""
                ::=  { filteringDbPage 1 }
 
        priorityTable    OBJECT IDENTIFIER ::= { bridge 31 }
 
        prioritySubTable OBJECT-TYPE
                SYNTAX SEQUENCE OF PriorityTableEntry
                ACCESS read-write
                STATUS mandatory
DESCRIPTION ""
                ::=  { priorityTable 1 }
 
        priorityTableEntry OBJECT-TYPE
                SYNTAX PriorityTableEntry
                ACCESS read-write
                STATUS mandatory
DESCRIPTION ""
                INDEX  {priorityTableEntryType}
                ::=  { prioritySubTable 1 }
 
        PriorityTableEntry ::= SEQUENCE {
                priorityTableEntryValue
                        INTEGER,
                priorityTableEntryType
                        INTEGER
                }
 
        priorityTableEntryValue OBJECT-TYPE
                SYNTAX INTEGER
                ACCESS read-write
                STATUS mandatory
DESCRIPTION ""
                ::=  { priorityTableEntry 1 }
 
        priorityTableEntryType OBJECT-TYPE
                SYNTAX INTEGER
                ACCESS read-write
                STATUS mandatory
DESCRIPTION ""
                ::=  { priorityTableEntry 2 }
 
        priorityTableAction OBJECT-TYPE
                SYNTAX INTEGER
                ACCESS read-write
                STATUS mandatory
DESCRIPTION ""
                ::=  { priorityTable 2 }
 
        priorityPage OBJECT-TYPE
                SYNTAX OCTET STRING (SIZE(8))
                ACCESS read-write
                STATUS mandatory
DESCRIPTION ""
                ::=  { priorityTable 3 }
 
        filterTable      OBJECT IDENTIFIER ::= { bridge 32 }
 
        filterSubTable OBJECT-TYPE
                SYNTAX SEQUENCE OF FilterTableEntry
                ACCESS read-write
                STATUS mandatory
DESCRIPTION ""
                ::=  { filterTable 1 }
 
        filterTableEntry OBJECT-TYPE
                SYNTAX SEQUENCE OF FilterTableEntry
                ACCESS read-write
                STATUS mandatory
DESCRIPTION ""
                INDEX  {filterTableEntryType}
                ::=  { filterSubTable 1 }
 
        FilterTableEntry ::= SEQUENCE {
                filterTableEntryValue
                        INTEGER,
                filterTableEntryType
                        INTEGER
                }
 
        filterTableEntryValue OBJECT-TYPE
                SYNTAX INTEGER
                ACCESS read-write
                STATUS mandatory
DESCRIPTION ""
                ::=  { filterTableEntry 1 }
 
        filterTableEntryType OBJECT-TYPE
                SYNTAX INTEGER
                ACCESS read-write
                STATUS mandatory
DESCRIPTION ""
                ::=  { filterTableEntry 2 }
 
        filterTableAction OBJECT-TYPE
                SYNTAX INTEGER
                ACCESS read-write
                STATUS mandatory
DESCRIPTION ""
                ::=  { filterTable 2 }
 
        filterPage OBJECT-TYPE
                SYNTAX OCTET STRING (SIZE(8))
                ACCESS read-write
                STATUS mandatory
DESCRIPTION ""
                ::=  { filterTable 3 }
 
 
-- the router group
 
-- The next sequence contains entries from the
-- Router Status and IP Data screens
 
        ipRSTable OBJECT-TYPE
                SYNTAX  SEQUENCE OF IpRSEntry
                ACCESS  read-write
                STATUS  mandatory
DESCRIPTION ""
                ::=  { router 1 }
 
        ipRSEntry OBJECT-TYPE
                SYNTAX  IpRSEntry
                ACCESS  read-write
                STATUS  mandatory
DESCRIPTION ""
                INDEX   {ipRSIndex}
                ::=  { ipRSTable 1 }
 
 
        IpRSEntry ::= SEQUENCE {
                ipRSIndex
                        INTEGER,
                gwProtocol
                        INTEGER,
                ifStatus
                        INTEGER,
                receivedTotal
                        Counter,
                transmittedTotal
                        Counter,
                outDiscardsTotal
                        Counter,
                noRouteTotal
                        Counter
                }
 
-- Router Status Screen
 
        ipRSIndex OBJECT-TYPE
                SYNTAX  INTEGER
                ACCESS  read-only
                STATUS  mandatory
DESCRIPTION ""
                ::=  { ipRSEntry 1 }
 
        gwProtocol OBJECT-TYPE
                SYNTAX  INTEGER
                ACCESS  read-write
                STATUS  mandatory
DESCRIPTION ""
                ::=  { ipRSEntry 2 }
 
        ifStatus OBJECT-TYPE
                SYNTAX  INTEGER
                ACCESS  read-only
                STATUS  mandatory
DESCRIPTION ""
                ::=  { ipRSEntry 3 }
 
-- IP Data Screen
 
        receivedTotal OBJECT-TYPE
                SYNTAX  Counter
                ACCESS  read-only
                STATUS  mandatory
DESCRIPTION ""
                ::=  { ipRSEntry 4 }
 
        transmittedTotal OBJECT-TYPE
                SYNTAX  Counter
                ACCESS  read-only
                STATUS  mandatory
DESCRIPTION ""
                ::=  { ipRSEntry 5 }
 
        outDiscardsTotal OBJECT-TYPE
                SYNTAX  Counter
                ACCESS  read-only
                STATUS  mandatory
DESCRIPTION ""
                ::=  { ipRSEntry 6 }
 
        noRouteTotal OBJECT-TYPE
                SYNTAX  Counter
                ACCESS  read-only
                STATUS  mandatory
DESCRIPTION ""
                ::=  { ipRSEntry 7 }
 
 
-- The next sequence contains entries from the
-- ICMP Data screen
 
        icmpRSTable OBJECT IDENTIFIER ::= { router 2 }
 
-- ICMP Data screen
 
        destUnreachLastRx OBJECT-TYPE
                SYNTAX  OCTET STRING (SIZE(13))
                ACCESS  read-only
                STATUS  mandatory
DESCRIPTION ""
                ::=  { icmpRSTable 1 }
 
        destUnreachLastTx OBJECT-TYPE
                SYNTAX  OCTET STRING (SIZE(13))
                ACCESS  read-only
                STATUS  mandatory
DESCRIPTION ""
                ::=  { icmpRSTable 2 }
 
        sourceQuenchLastRx OBJECT-TYPE
                SYNTAX  OCTET STRING (SIZE(13))
                ACCESS  read-only
                STATUS  mandatory
DESCRIPTION ""
                ::=  { icmpRSTable 3 }
 
        sourceQuenchLastTx OBJECT-TYPE
                SYNTAX  OCTET STRING (SIZE(13))
                ACCESS  read-only
                STATUS  mandatory
DESCRIPTION ""
                ::=  { icmpRSTable 4 }
 
        redirectsLastRx OBJECT-TYPE
                SYNTAX  OCTET STRING (SIZE(13))
                ACCESS  read-only
                STATUS  mandatory
DESCRIPTION ""
                ::=  { icmpRSTable 5 }
 
        redirectsLastTx OBJECT-TYPE
                SYNTAX  OCTET STRING (SIZE(13))
                ACCESS  read-only
                STATUS  mandatory
DESCRIPTION ""
                ::=  { icmpRSTable 6 }
 
        echoRequestsLastRx OBJECT-TYPE
                SYNTAX  OCTET STRING (SIZE(13))
                ACCESS  read-only
                STATUS  mandatory
DESCRIPTION ""
                ::=  { icmpRSTable 7 }
 
        echoRequestsLastTx OBJECT-TYPE
                SYNTAX  OCTET STRING (SIZE(13))
                ACCESS  read-only
                STATUS  mandatory
DESCRIPTION ""
                ::=  { icmpRSTable 8 }
 
        timeExceededLastRx OBJECT-TYPE
                SYNTAX  OCTET STRING (SIZE(13))
                ACCESS  read-only
                STATUS  mandatory
DESCRIPTION ""
                ::=  { icmpRSTable 9 }
 
        timeExceededLastTx OBJECT-TYPE
                SYNTAX  OCTET STRING (SIZE(13))
                ACCESS  read-only
                STATUS  mandatory
DESCRIPTION ""
                ::=  { icmpRSTable 10 }
 
        paramProbLastRx OBJECT-TYPE
                SYNTAX  OCTET STRING (SIZE(13))
                ACCESS  read-only
                STATUS  mandatory
DESCRIPTION ""
                ::=  { icmpRSTable 11 }
 
        paramProbLastTx OBJECT-TYPE
                SYNTAX  OCTET STRING (SIZE(13))
                ACCESS  read-only
                STATUS  mandatory
DESCRIPTION ""
                ::=  { icmpRSTable 12 }
 
-- Router Status Screen
 
        ipRouting OBJECT-TYPE
                SYNTAX  INTEGER
                ACCESS  read-write
                STATUS  mandatory
DESCRIPTION ""
                ::=  { router 3 }
 
 
--      boot group
 
        bootpRetryCount  OBJECT-TYPE
                SYNTAX  INTEGER ( 0..65535 )
                ACCESS  read-write
                STATUS  optional
DESCRIPTION ""
                ::= { boot 1 }
 
        downloadRetryCount  OBJECT-TYPE
                SYNTAX  INTEGER ( 0..65535 )
                ACCESS  read-write
                STATUS  optional
DESCRIPTION ""
                ::= { boot 2 }
 
        downloadFilename  OBJECT-TYPE
                SYNTAX  OCTET STRING (SIZE( 0..128))
                ACCESS  read-write
                STATUS  optional
DESCRIPTION ""
                ::= { boot 3 }
 
        bootserverIpAddress  OBJECT-TYPE
                SYNTAX  IpAddress
                ACCESS  read-write
                STATUS  optional
DESCRIPTION ""
                ::= { boot 4 }
 
        loadserverIpAddress  OBJECT-TYPE
                SYNTAX  IpAddress
                ACCESS  read-write
                STATUS  optional
DESCRIPTION ""
                ::= { boot 5 }
 
        uniqueBroadcastAddress  OBJECT-TYPE
                SYNTAX  IpAddress
                ACCESS  read-write
                STATUS  optional
DESCRIPTION ""
                ::= { boot 6 }
 
        tftpRetryCount  OBJECT-TYPE
                SYNTAX  INTEGER ( 0..65535)
                ACCESS  read-write
                STATUS  optional
DESCRIPTION ""
                ::= { boot 7 }
 
        tftpRetryPeriod  OBJECT-TYPE
                SYNTAX  INTEGER (0..65535)
                ACCESS  read-write
                STATUS  optional
DESCRIPTION ""
                ::= { boot 8 }
 
        initiateBootpDll  OBJECT-TYPE
                SYNTAX  INTEGER
                ACCESS  read-write
                STATUS  optional
DESCRIPTION ""
                ::= { boot 9 }
 
 
--      Boothelper group
 
        boothelperEnabled  OBJECT-TYPE
                SYNTAX  INTEGER
                ACCESS  read-write
                STATUS  optional
DESCRIPTION ""
                ::= { boothelper 1 }
 
        boothelperHopsLimit  OBJECT-TYPE
                SYNTAX  INTEGER (0..255)
                ACCESS  read-write
                STATUS  optional
DESCRIPTION ""
                ::= { boothelper 2 }
 
        boothelperForwardingAddress  OBJECT-TYPE
                SYNTAX  IpAddress
                ACCESS  read-write
                STATUS  optional
DESCRIPTION ""
                ::= { boothelper 3 }
 
 
                END
