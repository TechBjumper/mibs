-- =================================================================
-- Copyright (C) 2003 by  HUAWEI TECHNOLOGIES. All rights reserved.
--
-- Description: Demonstrates how to maintain VFB ports
-- Reference:   None
-- Version:     V1.0    
-- History:
-- liguanrong, 2003-03-23, VFB MIB first define
-- liguanrong, 2003-05-24, VFB mib modify transmit gain
-- =================================================================

HUAWEI-VFB-MIB DEFINITIONS ::= BEGIN
IMPORTS
    MODULE-IDENTITY, OBJECT-TYPE
        FROM SNMPv2-SMI

    Integer32
        FROM SNMPv2-SMI

        ifIndex
                FROM IF-MIB
    huaweiUtility 
                FROM HUAWEI-MIB;

hwVFB MODULE-IDENTITY
            LAST-UPDATED "0302280900Z"
            ORGANIZATION
                "Huawei Technologies co.,Ltd."
            CONTACT-INFO
                "Kefa Road,
                 Fx-Net Dep, Huawei Technologies Co.,Ltd.
			     Science-Based Industrial Park, 
			     Nanshan District,Shenzhen  P.R. China
			     http://www.huawei.com
			     Zip:518057"
    DESCRIPTION "The HUAWEI-VFB-MIB demonstrates how to maintain VFB ports"
    ::= { huaweiUtility 23 }

        hwVFBMibObjects       OBJECT IDENTIFIER  ::= { hwVFB   1 }

  vfbTable OBJECT-TYPE
    SYNTAX      SEQUENCE OF VfbEntry
    MAX-ACCESS  not-accessible
    STATUS      current
    DESCRIPTION
      "VFB maintain table"
    ::= { hwVFBMibObjects 1 }

  vfbEntry OBJECT-TYPE
    SYNTAX      VfbEntry
    MAX-ACCESS  not-accessible
    STATUS      current
    DESCRIPTION
      "VFB maintain table index"
    INDEX    {  
              ifIndex
             }
    ::= { vfbTable 1 }

  VfbEntry ::=
    SEQUENCE
    {
     hwVfbWorkMode       INTEGER,
     hwVfbReceiveGain    INTEGER,
     hwVfbTransmitGain   INTEGER,
     hwVfbUserName       OCTET STRING,
     hwVfbResistance     Integer32,
     hwVfbUsable         INTEGER,
     hwVfbPortState      INTEGER,
     hwVfbOprType        INTEGER
    }

  hwVfbWorkMode OBJECT-TYPE
    SYNTAX      INTEGER
         {
          twoline(1),
          fourline(2)
         }
    MAX-ACCESS  read-write
    STATUS      current
    DESCRIPTION
        " 
          1.two userline mode
          2.four userline mode
          Only even port can work in four userline mode, and the port after will of can not use.
          

        "
    DEFVAL {1}
    ::= { vfbEntry 1 }

  hwVfbReceiveGain OBJECT-TYPE
    SYNTAX      INTEGER(1..16)
    MAX-ACCESS  read-write
    STATUS      current
    DESCRIPTION
        " 
         port receive gain select, two userline mode range(5-10), four userline mode range(1-16)
         1:-11dB,
         2:-10dB,
         3:-9dB,
         4:-8dB,
         5:-7dB, 
         6:-6dB, 
         7:-5dB, 
         8:-4dB, 
         9:-3dB, 
         10:-2dB, 
         11:-1dB, 
         12:0dB, 
         13:+1dB, 
         14:+2dB, 
         15:+3dB, 
         16:+4dB
         
     
        "
    DEFVAL {5}
    ::= { vfbEntry 2 }

  hwVfbTransmitGain OBJECT-TYPE
    SYNTAX      INTEGER(1..16)
    MAX-ACCESS  read-write
    STATUS      current
    DESCRIPTION
        " 
         port transmit gain select, two userline mode range(10-15), four userline mode range(1-16)
         1:+14dB,
         2:+13dB,
         3:+12dB,
         4:+11dB,
         5:+10dB,
         6:+9dB,
         7:+8dB,
         8:+7dB,
         9:+6dB,
         10:+5dB,
         11:+4dB,
         12:+3dB,
         13:+2dB,
         14:+1dB,
         15:0dB,
         16:-1dB         
          
          
        "
    DEFVAL {10}
    ::= { vfbEntry 3 }

  hwVfbUserName OBJECT-TYPE
    SYNTAX      OCTET STRING (SIZE (0..20))
    MAX-ACCESS  read-write
    STATUS      current
    DESCRIPTION
        " 
          port user name
          
        "
    ::= { vfbEntry 4 }

  hwVfbResistance OBJECT-TYPE
    SYNTAX      Integer32(600)
    MAX-ACCESS  read-only
    STATUS      current
    DESCRIPTION
        " 
          port resistance

        "
    ::= { vfbEntry 5 }

  hwVfbUsable OBJECT-TYPE
    SYNTAX      INTEGER
          {
           usable(1),
           unusable(2)
          }
    MAX-ACCESS  read-only
    STATUS      current
    DESCRIPTION
        " 
          Is port can be used.
           1:usable,
           2:unusable
          
 
        "
    ::= { vfbEntry 6 }

  hwVfbPortState OBJECT-TYPE
    SYNTAX      INTEGER
         {
          fault(1),
          normal(2),
          busy(3),
          local-loopback(4)
         }
    MAX-ACCESS  read-only
    STATUS      current
    DESCRIPTION
        " 
          Port state,
           1:fault,
           2:normal,
           3:busy,
           4:local loopback
          

        "
    ::= { vfbEntry 7 }

  hwVfbOprType OBJECT-TYPE
    SYNTAX      INTEGER
         {
          local-Loopback(1),
          cancelLoop(2),
          reset(3)
         }
    MAX-ACCESS  read-write
    STATUS      current
    DESCRIPTION
        " 
          Port operation type,
           1:local loopback,
           2:cancel loopback,
           3:reset.
          When read, return -1.

        "
    ::= { vfbEntry 8 }

END
