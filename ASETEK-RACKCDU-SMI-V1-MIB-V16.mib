--
-- ASETEK-RACKCDU-SMI-V1-MIB-V16.mib
-- MIB generated by MG-SOFT Visual MIB Builder 2013 (64-bit) Version 9.0  Build 740
-- Wednesday, June 24, 2015 at 14:57:05
--
-- *************************************************************************
-- ASETEK A/S SNMP RackCDU MIB
-- *************************************************************************
-- Copyright (c) 2015 Asetek A/S
-- RackCDU is a Trademark of Asetek A/S.
-- 
-- Title: Asetek RackCDU MIB
-- 
-- *************************************************************************
--
-- 
--            LAST-UPDATED "201506241451Z"		 June 24, 2015 at 14:51 GMT
--            ORGANIZATION 
--                "Asetek A/S"
--            CONTACT-INFO 
--                "Asetek A/S
--                Assensvej 2
--                DK-9220 Aalborg East
--                Denmark
--                
--                Internet: http://asetek.com/
--                Email: kfj@asetek.com
--                
--                Phone: +45 9645 0047
--                Fax: +45 9645 0048
--                
--
--            DESCRIPTION 
--                "Asetek SMIv2 MIB definition file containing Data Objects used in 
--                conjunction with the Rack Cooling Distribution Unit (RackCDU)."
--            REVISION "201506241450Z"		 June 24, 2015 at 14:50 GMT
--            DESCRIPTION 
--                "Removed sysUpTime and snmpTrapOID bindings from traps. Removed 
--                snmpTrapOID and snmpTrapEnterprise from imports. Corrected misplaced 
--                value ranges on warningMaxPressureServer, alarmMaxPressureServer,
--                warningMaxPressureFacility and alarmMaxPressureFacility objects. Corrected
--                description for all pressure values under notifications group."
--            REVISION "201503241008Z"		 March 24, 2015 at 10:08 GMT
--            DESCRIPTION 
--                "Added traps: facilitySupplyWarning, facilityReturnWarning, 
--                serverSupplyWarning, serverReturnWarning, facilityPressureWarning, 
--                serverPressureWarning, facilityFlowWarning, facilitySupplyAlarm, 
--                facilityReturnAlarm, serverSupplyAlarm, serverReturnAlarm, 
--                facilityPressureAlarm, serverPressureAlarm, leakDetectionAlarm, 
--                liquidLevelAlarm & facilityFlowAlarm.
--                Made alarmNotify & warningNotify obsolete.
--                Added event descriptors: eventDescription & evetnValue.
--                Added cduEventGroup.
--                Replaced cduTrapGroup with cduTrapGroupRev2.
--                Replaced cduCompliances with cduCompliancesRev2."
--            REVISION "201503040846Z"		 March 04, 2015 at 08:46 GMT
--            DESCRIPTION 
--                "Optimized MIB for both SMIv1 and SMIv2 compliancy.
--                Added status object type."
--            REVISION "201411270929Z"		 November 27, 2014 at 09:29 GMT
--            DESCRIPTION 
--                "Added object groups, notification groups,
--                compliance module and corrected Interger32
--                to INTERGER base type for enumerated 
--                integers to comply with SMIv2."
--            REVISION "201405150953Z"		 May 15, 2014 at 09:53 GMT
--            DESCRIPTION 
--                "Made MIB syntax compatible with NET-SNMP."
--            REVISION "201311281413Z"		 November 28, 2013 at 14:13 GMT
--            DESCRIPTION 
--                "Updated MIB module to SMIv2."
--            REVISION "201306180841Z"		 June 18, 2013 at 08:41 GMT
--            DESCRIPTION 
--                "Removed unknown module objects."
--
    ASETEK-RACKCDU-SMI-V1-MIB-V16 DEFINITIONS ::= BEGIN
 
        IMPORTS
            OBJECT-TYPE            
                FROM RFC-1212            
            TRAP-TYPE            
                FROM RFC-1215            
            enterprises, IpAddress, Gauge            
                FROM RFC1155-SMI            
            sysDescr, sysObjectID, sysUpTime, sysContact, sysName, 
            sysLocation, sysServices, DisplayString            
                FROM RFC1213-MIB;
    
    
    
--
-- Node definitions
--
    
        -- 1.3.6.1.4.1.39829
        asetek OBJECT IDENTIFIER ::= { enterprises 39829 }

        
        -- 1.3.6.1.4.1.39829.1
        rackCDU OBJECT IDENTIFIER ::= { asetek 1 }

        
-- Notifications
        -- 1.3.6.1.4.1.39829.1.0
        traps OBJECT IDENTIFIER ::= { rackCDU 0 }

        
-- Product Information
        -- 1.3.6.1.4.1.39829.1.1
        product OBJECT IDENTIFIER ::= { rackCDU 1 }

        
        -- 1.3.6.1.4.1.39829.1.1.1
        name OBJECT-TYPE
            SYNTAX DisplayString
            ACCESS read-write
            STATUS mandatory
            DESCRIPTION
                "Product name."
            ::= { product 1 }

        
        -- 1.3.6.1.4.1.39829.1.1.2
        version OBJECT-TYPE
            SYNTAX DisplayString
            ACCESS read-only
            STATUS mandatory
            DESCRIPTION
                "Software version."
            ::= { product 2 }

        
        -- 1.3.6.1.4.1.39829.1.1.3
        date OBJECT-TYPE
            SYNTAX DisplayString
            ACCESS read-only
            STATUS mandatory
            DESCRIPTION
                "Software revision date."
            ::= { product 3 }

        
        -- 1.3.6.1.4.1.39829.1.1.4
        rackNumber OBJECT-TYPE
            SYNTAX DisplayString
            ACCESS read-write
            STATUS mandatory
            DESCRIPTION
                "RackCDU number."
            ::= { product 4 }

        
        -- 1.3.6.1.4.1.39829.1.1.5
        description OBJECT-TYPE
            SYNTAX DisplayString
            ACCESS read-write
            STATUS mandatory
            DESCRIPTION
                "RackCDU description."
            ::= { product 5 }

        
        -- 1.3.6.1.4.1.39829.1.1.6
        status OBJECT-TYPE
            SYNTAX INTEGER
                {
                ok(1),
                warning(2),
                error(3),
                unknown(5)
                }
            ACCESS read-only
            STATUS mandatory
            DESCRIPTION
                "The overall status of the RackCDU. Status is evaluated based on the
                notification settings. If a noticiation has been disabled it will not
                be included in the overall status either."
            ::= { product 6 }

        
-- Notification Table
        -- 1.3.6.1.4.1.39829.1.2
        setup OBJECT IDENTIFIER ::= { rackCDU 2 }

        
        -- 1.3.6.1.4.1.39829.1.2.1
        notifyTable OBJECT-TYPE
            SYNTAX SEQUENCE OF NotifyEntry
            ACCESS not-accessible
            STATUS mandatory
            DESCRIPTION
                "Table of settings used to setup notifications."
            ::= { setup 1 }

        
        -- 1.3.6.1.4.1.39829.1.2.1.1
        notifyEntry OBJECT-TYPE
            SYNTAX NotifyEntry
            ACCESS not-accessible
            STATUS mandatory
            DESCRIPTION
                "Single notify entry containing notification receiver info."
            INDEX { notifyReceiverNumber }
            ::= { notifyTable 1 }

        
        NotifyEntry ::=
            SEQUENCE { 
                notifyReceiverNumber
                    INTEGER,
                notifyEnabled
                    INTEGER,
                notifyReceiverIPAddress
                    IpAddress,
                notifyCommunity
                    DisplayString
             }

        -- 1.3.6.1.4.1.39829.1.2.1.1.1
        notifyReceiverNumber OBJECT-TYPE
            SYNTAX INTEGER (0..4)
            ACCESS read-only
            STATUS mandatory
            DESCRIPTION
                "Index of notification receiver."
            ::= { notifyEntry 1 }

        
        -- 1.3.6.1.4.1.39829.1.2.1.1.2
        notifyEnabled OBJECT-TYPE
            SYNTAX INTEGER
                {
                no(1),
                yes(2)
                }
            ACCESS read-write
            STATUS mandatory
            DESCRIPTION
                "Indicates if this notify entry is enabled or not."
            ::= { notifyEntry 2 }

        
        -- 1.3.6.1.4.1.39829.1.2.1.1.3
        notifyReceiverIPAddress OBJECT-TYPE
            SYNTAX IpAddress
            ACCESS read-write
            STATUS mandatory
            DESCRIPTION
                "Notification receiver IP address."
            ::= { notifyEntry 3 }

        
        -- 1.3.6.1.4.1.39829.1.2.1.1.4
        notifyCommunity OBJECT-TYPE
            SYNTAX DisplayString (SIZE (0..7))
            ACCESS read-write
            STATUS mandatory
            DESCRIPTION
                "Notification community to be used by agent to send trap."
            ::= { notifyEntry 4 }

        
-- Sensor Values
        -- 1.3.6.1.4.1.39829.1.3
        measurements OBJECT IDENTIFIER ::= { rackCDU 3 }

        
        -- 1.3.6.1.4.1.39829.1.3.100
        temperatureFacilityIn OBJECT-TYPE
            SYNTAX INTEGER (-870..999)
            ACCESS read-only
            STATUS mandatory
            DESCRIPTION
                "The temperature of the water going into the RackCDU on the Facility side
                (cold)."
            ::= { measurements 100 }

        
        -- 1.3.6.1.4.1.39829.1.3.101
        temperatureFacilityOut OBJECT-TYPE
            SYNTAX INTEGER (-870..999)
            ACCESS read-only
            STATUS mandatory
            DESCRIPTION
                "The temperature of the water going out of the RackCDU on the Facility
                side (hot)."
            ::= { measurements 101 }

        
        -- 1.3.6.1.4.1.39829.1.3.102
        temperatureServerIn OBJECT-TYPE
            SYNTAX INTEGER (-870..999)
            ACCESS read-only
            STATUS mandatory
            DESCRIPTION
                "The temperature of the water going into the servers node (cold)."
            ::= { measurements 102 }

        
        -- 1.3.6.1.4.1.39829.1.3.103
        temperatureServerOut OBJECT-TYPE
            SYNTAX INTEGER (-870..999)
            ACCESS read-only
            STATUS mandatory
            DESCRIPTION
                "The temperature of the water going out of the servers node (hot)."
            ::= { measurements 103 }

        
        -- 1.3.6.1.4.1.39829.1.3.104
        temperatureAmbient OBJECT-TYPE
            SYNTAX INTEGER (-870..999)
            ACCESS read-only
            STATUS obsolete
            DESCRIPTION
                "The temperature of the ambient air close to the RackCDU."
            ::= { measurements 104 }

        
        -- 1.3.6.1.4.1.39829.1.3.105
        pressureServer OBJECT-TYPE
            SYNTAX Gauge
            ACCESS read-only
            STATUS mandatory
            DESCRIPTION
                "The pressure inside the RackCDU on the server side."
            ::= { measurements 105 }

        
        -- 1.3.6.1.4.1.39829.1.3.106
        pressureFacility OBJECT-TYPE
            SYNTAX Gauge
            ACCESS read-only
            STATUS mandatory
            DESCRIPTION
                "The pressure inside the RackCDU on the facility side."
            ::= { measurements 106 }

        
        -- 1.3.6.1.4.1.39829.1.3.107
        serverLeak OBJECT-TYPE
            SYNTAX INTEGER
                {
                ok(1),
                leak(2)
                }
            ACCESS read-only
            STATUS mandatory
            DESCRIPTION
                "Boolean indication of whether the RackCDU has detected a leak in the
                system."
            ::= { measurements 107 }

        
        -- 1.3.6.1.4.1.39829.1.3.108
        serverLevel OBJECT-TYPE
            SYNTAX INTEGER
                {
                ok(1),
                low(2)
                }
            ACCESS read-only
            STATUS mandatory
            DESCRIPTION
                "Boolean indication of whether the RackCDU has detected a low level of
                cooleant."
            ::= { measurements 108 }

        
        -- 1.3.6.1.4.1.39829.1.3.109
        flowFacility OBJECT-TYPE
            SYNTAX Gauge
            ACCESS read-only
            STATUS mandatory
            DESCRIPTION
                "The flow of the cooleant on the facility side."
            ::= { measurements 109 }

        
        -- 1.3.6.1.4.1.39829.1.3.110
        heatload OBJECT-TYPE
            SYNTAX Gauge
            ACCESS read-only
            STATUS mandatory
            DESCRIPTION
                "The heatload of the cooleant on the facility side. Can be averaged from
                e.g. 1 to 28800 (24 hours) sec."
            ::= { measurements 110 }

        
        -- 1.3.6.1.4.1.39829.1.3.111
        controllerOut OBJECT-TYPE
            SYNTAX Gauge
            ACCESS read-only
            STATUS mandatory
            DESCRIPTION
                "The controller output."
            ::= { measurements 111 }

        
-- Network Settings
        -- 1.3.6.1.4.1.39829.1.4
        network OBJECT IDENTIFIER ::= { rackCDU 4 }

        
        -- 1.3.6.1.4.1.39829.1.4.91
        ipStoreFlash OBJECT-TYPE
            SYNTAX INTEGER
                {
                normal(1),
                store(2)
                }
            ACCESS read-write
            STATUS mandatory
            DESCRIPTION
                "store settings to Flash."
            ::= { network 91 }

        
        -- 1.3.6.1.4.1.39829.1.4.92
        modeOfOperation OBJECT-TYPE
            SYNTAX INTEGER
                {
                agent(1),
                master(2)
                }
            ACCESS read-write
            STATUS mandatory
            DESCRIPTION
                "Mode of operation of ControlBox, can be agent or master."
            ::= { network 92 }

        
        -- 1.3.6.1.4.1.39829.1.4.93
        ipAddr OBJECT-TYPE
            SYNTAX IpAddress
            ACCESS read-write
            STATUS mandatory
            DESCRIPTION
                "IP address of ControlBox."
            ::= { network 93 }

        
        -- 1.3.6.1.4.1.39829.1.4.94
        priDNS OBJECT-TYPE
            SYNTAX IpAddress
            ACCESS read-write
            STATUS mandatory
            DESCRIPTION
                "Primary DNS address of ControlBox."
            ::= { network 94 }

        
        -- 1.3.6.1.4.1.39829.1.4.95
        secDNS OBJECT-TYPE
            SYNTAX IpAddress
            ACCESS read-write
            STATUS mandatory
            DESCRIPTION
                "Secondary DNS address of ControlBox."
            ::= { network 95 }

        
        -- 1.3.6.1.4.1.39829.1.4.96
        netMask OBJECT-TYPE
            SYNTAX IpAddress
            ACCESS read-write
            STATUS mandatory
            DESCRIPTION
                "Netmask of ControlBox."
            ::= { network 96 }

        
        -- 1.3.6.1.4.1.39829.1.4.97
        gateway OBJECT-TYPE
            SYNTAX IpAddress
            ACCESS read-write
            STATUS mandatory
            DESCRIPTION
                "Gateway of ControlBox."
            ::= { network 97 }

        
        -- 1.3.6.1.4.1.39829.1.4.98
        ipSrc OBJECT-TYPE
            SYNTAX INTEGER
                {
                static(1),
                dhcp(2)
                }
            ACCESS read-write
            STATUS mandatory
            DESCRIPTION
                "IP address source of ControlBox, eg. static or dhcp."
            ::= { network 98 }

        
        -- 1.3.6.1.4.1.39829.1.4.99
        ipReboot OBJECT-TYPE
            SYNTAX INTEGER
                {
                normal(1),
                reboot(2)
                }
            ACCESS read-write
            STATUS mandatory
            DESCRIPTION
                "IP address reboot."
            ::= { network 99 }

        
-- Heat Control Settings
        -- 1.3.6.1.4.1.39829.1.5
        controller OBJECT IDENTIFIER ::= { rackCDU 5 }

        
        -- 1.3.6.1.4.1.39829.1.5.80
        gainProportional OBJECT-TYPE
            SYNTAX DisplayString
            ACCESS read-write
            STATUS mandatory
            DESCRIPTION
                "Proportional gain in PID controller."
            ::= { controller 80 }

        
        -- 1.3.6.1.4.1.39829.1.5.81
        gainIntegral OBJECT-TYPE
            SYNTAX DisplayString
            ACCESS read-write
            STATUS mandatory
            DESCRIPTION
                "Integral gain in PID controller."
            ::= { controller 81 }

        
        -- 1.3.6.1.4.1.39829.1.5.82
        gainDifferential OBJECT-TYPE
            SYNTAX DisplayString
            ACCESS read-write
            STATUS mandatory
            DESCRIPTION
                "Differential gain in PID controller."
            ::= { controller 82 }

        
        -- 1.3.6.1.4.1.39829.1.5.83
        deltaOutMax OBJECT-TYPE
            SYNTAX Gauge
            ACCESS read-write
            STATUS mandatory
            DESCRIPTION
                "Maximum delta output from controller."
            ::= { controller 83 }

        
        -- 1.3.6.1.4.1.39829.1.5.84
        limitPwmMax OBJECT-TYPE
            SYNTAX Gauge
            ACCESS read-write
            STATUS mandatory
            DESCRIPTION
                "Maximum PWM output."
            ::= { controller 84 }

        
        -- 1.3.6.1.4.1.39829.1.5.85
        limitPwmMin OBJECT-TYPE
            SYNTAX Gauge
            ACCESS read-write
            STATUS mandatory
            DESCRIPTION
                "Minimum PWM output."
            ::= { controller 85 }

        
        -- 1.3.6.1.4.1.39829.1.5.86
        setpointFacilityOut OBJECT-TYPE
            SYNTAX INTEGER (0..100)
            ACCESS read-write
            STATUS mandatory
            DESCRIPTION
                "Setpoint for Facility Out Temperature."
            ::= { controller 86 }

        
        -- 1.3.6.1.4.1.39829.1.5.87
        controllerOutAlpha OBJECT-TYPE
            SYNTAX DisplayString
            ACCESS read-write
            STATUS mandatory
            DESCRIPTION
                "Controller Out Alpha - damping factor of output."
            ::= { controller 87 }

        
-- Factors and Defines
        -- 1.3.6.1.4.1.39829.1.6
        units OBJECT IDENTIFIER ::= { rackCDU 6 }

        
        -- 1.3.6.1.4.1.39829.1.6.70
        fluidHeatCapacity OBJECT-TYPE
            SYNTAX INTEGER (0..65000)
            ACCESS read-write
            STATUS mandatory
            DESCRIPTION
                "Heat Capacity of the liquid coolant utilized in the facility loop."
            ::= { units 70 }

        
        -- 1.3.6.1.4.1.39829.1.6.71
        heatAverageFactor OBJECT-TYPE
            SYNTAX Gauge
            ACCESS read-write
            STATUS mandatory
            DESCRIPTION
                "The time frame of which the heat load is averaged. A short time frame
                make the heat load sensative to small changes is temperature and flow
                which results in a highly fluctuating value. A long time frame
                stabilizes the value, but also results in a long response time."
            ::= { units 71 }

        
        -- 1.3.6.1.4.1.39829.1.6.72
        harnessVersion OBJECT-TYPE
            SYNTAX Gauge
            ACCESS read-write
            STATUS mandatory
            DESCRIPTION
                "Must be set to the harness version utilized by the RackCDU. The harness
                version may affect the functionality of the RackCDU and it it therefor
                important that the versions is matched."
            ::= { units 72 }

        
-- Notification Settings
        -- 1.3.6.1.4.1.39829.1.7
        notifications OBJECT IDENTIFIER ::= { rackCDU 7 }

        
-- SNMP notification
        -- 1.3.6.1.4.1.39829.1.7.150
        snmpTrapsAlarmEnable OBJECT-TYPE
            SYNTAX INTEGER
                {
                disabled(1),
                enabled(2)
                }
            ACCESS read-write
            STATUS mandatory
            DESCRIPTION
                "Enable SNMP Alarm traps."
            ::= { notifications 150 }

        
        -- 1.3.6.1.4.1.39829.1.7.151
        snmpTrapsWarningEnable OBJECT-TYPE
            SYNTAX INTEGER
                {
                disabled(1),
                enabled(2)
                }
            ACCESS read-write
            STATUS mandatory
            DESCRIPTION
                "Enable SNMP Warning traps."
            ::= { notifications 151 }

        
-- SMTP notification
        -- 1.3.6.1.4.1.39829.1.7.152
        smtpTrapsAlarmEnable OBJECT-TYPE
            SYNTAX INTEGER
                {
                disabled(1),
                enabled(2)
                }
            ACCESS read-write
            STATUS mandatory
            DESCRIPTION
                "Enable SMTP Alarm traps."
            ::= { notifications 152 }

        
        -- 1.3.6.1.4.1.39829.1.7.153
        smtpTrapsWarningEnable OBJECT-TYPE
            SYNTAX INTEGER
                {
                disabled(1),
                enabled(2)
                }
            ACCESS read-write
            STATUS mandatory
            DESCRIPTION
                "Enable SMTP Warning traps."
            ::= { notifications 153 }

        
-- Facility inlet temperature warning notitication
        -- 1.3.6.1.4.1.39829.1.7.154
        warningMinFi OBJECT-TYPE
            SYNTAX INTEGER (-75..75)
            ACCESS read-write
            STATUS mandatory
            DESCRIPTION
                "Set Facility In Min Warning level."
            ::= { notifications 154 }

        
        -- 1.3.6.1.4.1.39829.1.7.155
        warningMinEnableFi OBJECT-TYPE
            SYNTAX INTEGER
                {
                disabled(1),
                enabled(2)
                }
            ACCESS read-write
            STATUS mandatory
            DESCRIPTION
                "Enable Facility In Min Warning level."
            ::= { notifications 155 }

        
        -- 1.3.6.1.4.1.39829.1.7.156
        warningMaxFi OBJECT-TYPE
            SYNTAX INTEGER (-75..75)
            ACCESS read-write
            STATUS mandatory
            DESCRIPTION
                "Set Facility In Max Warning level."
            ::= { notifications 156 }

        
        -- 1.3.6.1.4.1.39829.1.7.157
        warningMaxEnableFi OBJECT-TYPE
            SYNTAX INTEGER
                {
                disabled(1),
                enabled(2)
                }
            ACCESS read-write
            STATUS mandatory
            DESCRIPTION
                "Enable Facility In Max Warning level."
            ::= { notifications 157 }

        
-- Facility inlet temperature alarm notitication
        -- 1.3.6.1.4.1.39829.1.7.158
        alarmMinFi OBJECT-TYPE
            SYNTAX INTEGER (-75..75)
            ACCESS read-write
            STATUS mandatory
            DESCRIPTION
                "Set Facility In Min Alarm level."
            ::= { notifications 158 }

        
        -- 1.3.6.1.4.1.39829.1.7.159
        alarmMinEnableFi OBJECT-TYPE
            SYNTAX INTEGER
                {
                disabled(1),
                enabled(2)
                }
            ACCESS read-write
            STATUS mandatory
            DESCRIPTION
                "Enable Facility In Min Alarm level."
            ::= { notifications 159 }

        
        -- 1.3.6.1.4.1.39829.1.7.160
        alarmMaxFi OBJECT-TYPE
            SYNTAX INTEGER (-75..75)
            ACCESS read-write
            STATUS mandatory
            DESCRIPTION
                "Set Facility In Max Alarm level."
            ::= { notifications 160 }

        
        -- 1.3.6.1.4.1.39829.1.7.161
        alarmMaxEnableFi OBJECT-TYPE
            SYNTAX INTEGER
                {
                disabled(1),
                enabled(2)
                }
            ACCESS read-write
            STATUS mandatory
            DESCRIPTION
                "Enable Facility In Max Alarm level."
            ::= { notifications 161 }

        
-- Facility outlet temperature warning notitication
        -- 1.3.6.1.4.1.39829.1.7.162
        warningMinFo OBJECT-TYPE
            SYNTAX INTEGER (-75..75)
            ACCESS read-write
            STATUS mandatory
            DESCRIPTION
                "Set Facility Out Min Warning level."
            ::= { notifications 162 }

        
        -- 1.3.6.1.4.1.39829.1.7.163
        warningMinEnableFo OBJECT-TYPE
            SYNTAX INTEGER
                {
                disabled(1),
                enabled(2)
                }
            ACCESS read-write
            STATUS mandatory
            DESCRIPTION
                "Enable Facility Out Min Warning level."
            ::= { notifications 163 }

        
        -- 1.3.6.1.4.1.39829.1.7.164
        warningMaxFo OBJECT-TYPE
            SYNTAX INTEGER (-75..75)
            ACCESS read-write
            STATUS mandatory
            DESCRIPTION
                "Set Facility Out Max Warning level."
            ::= { notifications 164 }

        
        -- 1.3.6.1.4.1.39829.1.7.165
        warningMaxEnableFo OBJECT-TYPE
            SYNTAX INTEGER
                {
                disabled(1),
                enabled(2)
                }
            ACCESS read-write
            STATUS mandatory
            DESCRIPTION
                "Enable Facility Out Max Warning level."
            ::= { notifications 165 }

        
-- Facility outlet temperature alarm notitication
        -- 1.3.6.1.4.1.39829.1.7.166
        alarmMinFo OBJECT-TYPE
            SYNTAX INTEGER (-75..75)
            ACCESS read-write
            STATUS mandatory
            DESCRIPTION
                "Set Facility Out Min alarm level."
            ::= { notifications 166 }

        
        -- 1.3.6.1.4.1.39829.1.7.167
        alarmMinEnableFo OBJECT-TYPE
            SYNTAX INTEGER
                {
                disabled(1),
                enabled(2)
                }
            ACCESS read-write
            STATUS mandatory
            DESCRIPTION
                "Enable Facility Out Min alarm level."
            ::= { notifications 167 }

        
        -- 1.3.6.1.4.1.39829.1.7.168
        alarmMaxFo OBJECT-TYPE
            SYNTAX INTEGER (-75..75)
            ACCESS read-write
            STATUS mandatory
            DESCRIPTION
                "Set Facility Out Max Alarm level."
            ::= { notifications 168 }

        
        -- 1.3.6.1.4.1.39829.1.7.169
        alarmMaxEnableFo OBJECT-TYPE
            SYNTAX INTEGER
                {
                disabled(1),
                enabled(2)
                }
            ACCESS read-write
            STATUS mandatory
            DESCRIPTION
                "Enable Facility Out Max Alarm level."
            ::= { notifications 169 }

        
-- Server inlet temperature warning notitication
        -- 1.3.6.1.4.1.39829.1.7.170
        warningMinSi OBJECT-TYPE
            SYNTAX INTEGER (-75..75)
            ACCESS read-write
            STATUS mandatory
            DESCRIPTION
                "Set Server In Min Warning level."
            ::= { notifications 170 }

        
        -- 1.3.6.1.4.1.39829.1.7.171
        warningMinEnableSi OBJECT-TYPE
            SYNTAX INTEGER
                {
                disabled(1),
                enabled(2)
                }
            ACCESS read-write
            STATUS mandatory
            DESCRIPTION
                "Enable Server In Min Warning level."
            ::= { notifications 171 }

        
        -- 1.3.6.1.4.1.39829.1.7.172
        warningMaxSi OBJECT-TYPE
            SYNTAX INTEGER (-75..75)
            ACCESS read-write
            STATUS mandatory
            DESCRIPTION
                "Set Server In Max Warning level."
            ::= { notifications 172 }

        
        -- 1.3.6.1.4.1.39829.1.7.173
        warningMaxEnableSi OBJECT-TYPE
            SYNTAX INTEGER
                {
                disabled(1),
                enabled(2)
                }
            ACCESS read-write
            STATUS mandatory
            DESCRIPTION
                "Enable Server In Max Warning level."
            ::= { notifications 173 }

        
-- Server inlet temperature alarm notitication
        -- 1.3.6.1.4.1.39829.1.7.174
        alarmMinSi OBJECT-TYPE
            SYNTAX INTEGER (-75..75)
            ACCESS read-write
            STATUS mandatory
            DESCRIPTION
                "Set Server In Min Alarm level."
            ::= { notifications 174 }

        
        -- 1.3.6.1.4.1.39829.1.7.175
        alarmMinEnableSi OBJECT-TYPE
            SYNTAX INTEGER
                {
                disabled(1),
                enabled(2)
                }
            ACCESS read-write
            STATUS mandatory
            DESCRIPTION
                "Enable Server In Min Alarm level."
            ::= { notifications 175 }

        
        -- 1.3.6.1.4.1.39829.1.7.176
        alarmMaxSi OBJECT-TYPE
            SYNTAX INTEGER (-75..75)
            ACCESS read-write
            STATUS mandatory
            DESCRIPTION
                "Set Server In Max Alarm level."
            ::= { notifications 176 }

        
        -- 1.3.6.1.4.1.39829.1.7.177
        alarmMaxEnableSi OBJECT-TYPE
            SYNTAX INTEGER
                {
                disabled(1),
                enabled(2)
                }
            ACCESS read-write
            STATUS mandatory
            DESCRIPTION
                "Enable Server In Max Alarm level."
            ::= { notifications 177 }

        
-- Server outlet temperature warning notitication
        -- 1.3.6.1.4.1.39829.1.7.178
        warningMinSo OBJECT-TYPE
            SYNTAX INTEGER (-75..75)
            ACCESS read-write
            STATUS mandatory
            DESCRIPTION
                "Set Server Out Min Warning level."
            ::= { notifications 178 }

        
        -- 1.3.6.1.4.1.39829.1.7.179
        warningMinEnableSo OBJECT-TYPE
            SYNTAX INTEGER
                {
                disabled(1),
                enabled(2)
                }
            ACCESS read-write
            STATUS mandatory
            DESCRIPTION
                "Enable Server Out Min Warning level."
            ::= { notifications 179 }

        
        -- 1.3.6.1.4.1.39829.1.7.180
        warningMaxSo OBJECT-TYPE
            SYNTAX INTEGER (-75..75)
            ACCESS read-write
            STATUS mandatory
            DESCRIPTION
                "Set Server Out Max Warning level."
            ::= { notifications 180 }

        
        -- 1.3.6.1.4.1.39829.1.7.181
        warningMaxEnableSo OBJECT-TYPE
            SYNTAX INTEGER
                {
                disabled(1),
                enabled(2)
                }
            ACCESS read-write
            STATUS mandatory
            DESCRIPTION
                "Enable Server Out Max Warning level."
            ::= { notifications 181 }

        
--  Server outlet temperature alarm notitication
        -- 1.3.6.1.4.1.39829.1.7.182
        alarmMinSo OBJECT-TYPE
            SYNTAX INTEGER (-75..75)
            ACCESS read-write
            STATUS mandatory
            DESCRIPTION
                "Set Server Out Min Alarm level."
            ::= { notifications 182 }

        
        -- 1.3.6.1.4.1.39829.1.7.183
        alarmMinEnableSo OBJECT-TYPE
            SYNTAX INTEGER
                {
                disabled(1),
                enabled(2)
                }
            ACCESS read-write
            STATUS mandatory
            DESCRIPTION
                "Enable Server Out Min Alarm level."
            ::= { notifications 183 }

        
        -- 1.3.6.1.4.1.39829.1.7.184
        alarmMaxSo OBJECT-TYPE
            SYNTAX INTEGER (-75..75)
            ACCESS read-write
            STATUS mandatory
            DESCRIPTION
                "Set Server Out Max Alarm level."
            ::= { notifications 184 }

        
        -- 1.3.6.1.4.1.39829.1.7.185
        alarmMaxEnableSo OBJECT-TYPE
            SYNTAX INTEGER
                {
                disabled(1),
                enabled(2)
                }
            ACCESS read-write
            STATUS mandatory
            DESCRIPTION
                "Enable Server Out Max Alarm level."
            ::= { notifications 185 }

        
-- Flow warning notitication
        -- 1.3.6.1.4.1.39829.1.7.186
        warningMinFlow OBJECT-TYPE
            SYNTAX INTEGER (0..3500000)
            ACCESS read-write
            STATUS mandatory
            DESCRIPTION
                "Set Flow Min Warning level."
            ::= { notifications 186 }

        
        -- 1.3.6.1.4.1.39829.1.7.187
        warningMinEnableFlow OBJECT-TYPE
            SYNTAX INTEGER
                {
                disabled(1),
                enabled(2)
                }
            ACCESS read-write
            STATUS mandatory
            DESCRIPTION
                "Enable Flow Min Warning level."
            ::= { notifications 187 }

        
        -- 1.3.6.1.4.1.39829.1.7.188
        warningMaxFlow OBJECT-TYPE
            SYNTAX INTEGER (0..3500000)
            ACCESS read-write
            STATUS mandatory
            DESCRIPTION
                "Set Flow Max Warning level."
            ::= { notifications 188 }

        
        -- 1.3.6.1.4.1.39829.1.7.189
        warningMaxEnableFlow OBJECT-TYPE
            SYNTAX INTEGER
                {
                disabled(1),
                enabled(2)
                }
            ACCESS read-write
            STATUS mandatory
            DESCRIPTION
                "Enable Flow Max Warning level."
            ::= { notifications 189 }

        
-- Flow alarm notitication
        -- 1.3.6.1.4.1.39829.1.7.190
        alarmMinFlow OBJECT-TYPE
            SYNTAX INTEGER (0..3500000)
            ACCESS read-write
            STATUS mandatory
            DESCRIPTION
                "Set Flow Min Alarm level."
            ::= { notifications 190 }

        
        -- 1.3.6.1.4.1.39829.1.7.191
        alarmMinEnableFlow OBJECT-TYPE
            SYNTAX INTEGER
                {
                disabled(1),
                enabled(2)
                }
            ACCESS read-write
            STATUS mandatory
            DESCRIPTION
                "Enable Flow Min Alarm level."
            ::= { notifications 191 }

        
        -- 1.3.6.1.4.1.39829.1.7.192
        alarmMaxFlow OBJECT-TYPE
            SYNTAX INTEGER (0..3500000)
            ACCESS read-write
            STATUS mandatory
            DESCRIPTION
                "Set Flow Max Alarm level."
            ::= { notifications 192 }

        
        -- 1.3.6.1.4.1.39829.1.7.193
        alarmMaxEnableFlow OBJECT-TYPE
            SYNTAX INTEGER
                {
                disabled(1),
                enabled(2)
                }
            ACCESS read-write
            STATUS mandatory
            DESCRIPTION
                "Enable Flow Max Alarm level."
            ::= { notifications 193 }

        
-- Server pressure warning notitication
        -- 1.3.6.1.4.1.39829.1.7.194
        warningMinPressureServer OBJECT-TYPE
            SYNTAX INTEGER (0..3500)
            ACCESS read-write
            STATUS mandatory
            DESCRIPTION
                "Set Server Pressure Min Warning level."
            ::= { notifications 194 }

        
        -- 1.3.6.1.4.1.39829.1.7.195
        warningMinEnablePressureServer OBJECT-TYPE
            SYNTAX INTEGER
                {
                disabled(1),
                enabled(2)
                }
            ACCESS read-write
            STATUS mandatory
            DESCRIPTION
                "Enable Server Pressure Min Warning level."
            ::= { notifications 195 }

        
        -- 1.3.6.1.4.1.39829.1.7.196
        warningMaxPressureServer OBJECT-TYPE
            SYNTAX INTEGER (0..3500)
            ACCESS read-write
            STATUS mandatory
            DESCRIPTION
                "Set Server Pressure Max Warning level."
            ::= { notifications 196 }

        
        -- 1.3.6.1.4.1.39829.1.7.197
        warningMaxEnablePressureServer OBJECT-TYPE
            SYNTAX INTEGER
                {
                disabled(1),
                enabled(2)
                }
            ACCESS read-write
            STATUS mandatory
            DESCRIPTION
                "Enable Server Pressure Max Warning level."
            ::= { notifications 197 }

        
--  Server pressure alarm notitication
        -- 1.3.6.1.4.1.39829.1.7.198
        alarmMinPressureServer OBJECT-TYPE
            SYNTAX INTEGER (0..3500)
            ACCESS read-write
            STATUS mandatory
            DESCRIPTION
                "Set Server Pressure Min Alarm level."
            ::= { notifications 198 }

        
        -- 1.3.6.1.4.1.39829.1.7.199
        alarmMinEnablePressureServer OBJECT-TYPE
            SYNTAX INTEGER
                {
                disabled(1),
                enabled(2)
                }
            ACCESS read-write
            STATUS mandatory
            DESCRIPTION
                "Enable Server Pressure Min Alarm level."
            ::= { notifications 199 }

        
        -- 1.3.6.1.4.1.39829.1.7.200
        alarmMaxPressureServer OBJECT-TYPE
            SYNTAX INTEGER (0..3500)
            ACCESS read-write
            STATUS mandatory
            DESCRIPTION
                "Set Server Pressure Max Alarm level."
            ::= { notifications 200 }

        
        -- 1.3.6.1.4.1.39829.1.7.201
        alarmMaxEnablePressureServer OBJECT-TYPE
            SYNTAX INTEGER
                {
                disabled(1),
                enabled(2)
                }
            ACCESS read-write
            STATUS mandatory
            DESCRIPTION
                "Enable Server Pressure Max Alarm level."
            ::= { notifications 201 }

        
-- Facility pressure Warning notification
        -- 1.3.6.1.4.1.39829.1.7.202
        warningMinPressureFacility OBJECT-TYPE
            SYNTAX INTEGER (0..3500)
            ACCESS read-write
            STATUS mandatory
            DESCRIPTION
                "Set Facility Pressure Min Warning level."
            ::= { notifications 202 }

        
        -- 1.3.6.1.4.1.39829.1.7.203
        warningMinEnablePressureFacility OBJECT-TYPE
            SYNTAX INTEGER
                {
                disabled(1),
                enabled(2)
                }
            ACCESS read-write
            STATUS mandatory
            DESCRIPTION
                "Enable Facility Pressure Min Warning level."
            ::= { notifications 203 }

        
        -- 1.3.6.1.4.1.39829.1.7.204
        warningMaxPressureFacility OBJECT-TYPE
            SYNTAX INTEGER (0..3500)
            ACCESS read-write
            STATUS mandatory
            DESCRIPTION
                "Set Facility Pressure Max Warning level."
            ::= { notifications 204 }

        
        -- 1.3.6.1.4.1.39829.1.7.205
        warningMaxEnablePressureFacility OBJECT-TYPE
            SYNTAX INTEGER
                {
                disabled(1),
                enabled(2)
                }
            ACCESS read-write
            STATUS mandatory
            DESCRIPTION
                "Enable Facility Pressure Max Warning level."
            ::= { notifications 205 }

        
--  Facility pressure alarm notification
        -- 1.3.6.1.4.1.39829.1.7.206
        alarmMinPressureFacility OBJECT-TYPE
            SYNTAX INTEGER (0..3500)
            ACCESS read-write
            STATUS mandatory
            DESCRIPTION
                "Set Facility Pressure Min Alarm level."
            ::= { notifications 206 }

        
        -- 1.3.6.1.4.1.39829.1.7.207
        alarmMinEnablePressureFacility OBJECT-TYPE
            SYNTAX INTEGER
                {
                disabled(1),
                enabled(2)
                }
            ACCESS read-write
            STATUS mandatory
            DESCRIPTION
                "Enable Facility Pressure Min Alarm level."
            ::= { notifications 207 }

        
        -- 1.3.6.1.4.1.39829.1.7.208
        alarmMaxPressureFacility OBJECT-TYPE
            SYNTAX INTEGER (0..3500)
            ACCESS read-write
            STATUS mandatory
            DESCRIPTION
                "Set Facility Pressure Max Alarm level."
            ::= { notifications 208 }

        
        -- 1.3.6.1.4.1.39829.1.7.209
        alarmMaxEnablePressureFacility OBJECT-TYPE
            SYNTAX INTEGER
                {
                disabled(1),
                enabled(2)
                }
            ACCESS read-write
            STATUS mandatory
            DESCRIPTION
                "Enable Facility Pressure Max Alarm level."
            ::= { notifications 209 }

        
-- Leak detection notification
        -- 1.3.6.1.4.1.39829.1.7.210
        alarmEnableLeak OBJECT-TYPE
            SYNTAX INTEGER
                {
                disabled(1),
                enabled(2)
                }
            ACCESS read-write
            STATUS mandatory
            DESCRIPTION
                "Enable leak detection."
            ::= { notifications 210 }

        
-- Low liquid level notification
        -- 1.3.6.1.4.1.39829.1.7.211
        alarmEnableLevel OBJECT-TYPE
            SYNTAX INTEGER
                {
                disabled(1),
                enabled(2)
                }
            ACCESS read-write
            STATUS mandatory
            DESCRIPTION
                "Enable low liquid level."
            ::= { notifications 211 }

        
-- Conformance
        -- 1.3.6.1.4.1.39829.1.8
        conformance OBJECT IDENTIFIER ::= { rackCDU 8 }

        
        -- 1.3.6.1.4.1.39829.1.8.1
        cduProdGroup OBJECT IDENTIFIER ::= { conformance 1 }

        
        -- 1.3.6.1.4.1.39829.1.8.2
        cduSetupGroup OBJECT IDENTIFIER ::= { conformance 2 }

        
        -- 1.3.6.1.4.1.39829.1.8.3
        cduMeasGroup OBJECT IDENTIFIER ::= { conformance 3 }

        
        -- 1.3.6.1.4.1.39829.1.8.4
        cduMeasGroupRev2 OBJECT IDENTIFIER ::= { conformance 4 }

        
        -- 1.3.6.1.4.1.39829.1.8.5
        cduNetGroup OBJECT IDENTIFIER ::= { conformance 5 }

        
        -- 1.3.6.1.4.1.39829.1.8.6
        cduCntlGroup OBJECT IDENTIFIER ::= { conformance 6 }

        
        -- 1.3.6.1.4.1.39829.1.8.7
        cduUnitGroup OBJECT IDENTIFIER ::= { conformance 7 }

        
        -- 1.3.6.1.4.1.39829.1.8.8
        cduNotifyGroup OBJECT IDENTIFIER ::= { conformance 8 }

        
        -- 1.3.6.1.4.1.39829.1.8.9
        cduTrapGroup OBJECT IDENTIFIER ::= { conformance 9 }

        
        -- 1.3.6.1.4.1.39829.1.8.10
        cduCompliances OBJECT IDENTIFIER ::= { conformance 10 }

        
        -- 1.3.6.1.4.1.39829.1.8.11
        cduEventGroup OBJECT IDENTIFIER ::= { conformance 11 }

        
        -- 1.3.6.1.4.1.39829.1.8.12
        cduTrapGroupRev2 OBJECT IDENTIFIER ::= { conformance 12 }

        
        -- 1.3.6.1.4.1.39829.1.8.13
        cduCompliancesRev2 OBJECT IDENTIFIER ::= { conformance 13 }

        
-- Event Descriptors
        -- 1.3.6.1.4.1.39829.1.9
        eventDescriptors OBJECT IDENTIFIER ::= { rackCDU 9 }

        
        -- 1.3.6.1.4.1.39829.1.9.1
        eventDescription OBJECT-TYPE
            SYNTAX DisplayString
            ACCESS read-only
            STATUS mandatory
            DESCRIPTION
                "Text which provide the user with a corrective action in case of a 
                warning or alarm trap.
                
                IMPORTANT: Must only be used in traps! Any other use of this object is
                invalid.
                "
            ::= { eventDescriptors 1 }

        
        -- 1.3.6.1.4.1.39829.1.9.2
        eventValue OBJECT-TYPE
            SYNTAX INTEGER
            ACCESS read-only
            STATUS mandatory
            DESCRIPTION
                "Event value placeholder sent with generic traps where the unit of the 
                value can be different.
                
                IMPORTANT: Must only be used in traps! Any other use of this object is
                invalid"
            ::= { eventDescriptors 2 }

        
    
--
-- Trap definitions
--
    
-- Traps/Notifications
        alarmNotify TRAP-TYPE 
            ENTERPRISE rackCDU
            VARIABLES { eventValue, eventDescription }
            DESCRIPTION 
                "Trap alarm notification information for the SNMP Manager (obsolete)."
                --#TYPE      "Alarm notification"
                --#SUMMARY   "An alarm were triggered. Sensor value is: %d"
                --#ARGUMENTS {0}
                --#SEVERITY  CRITICAL
                --#TIMEINDEX 5
                --#HELP      "This notification is obsolete. Please update the RackCDU control box firmware."
                --#HELPTAG   0
                --#STATE     NONOPERATIONAL
            ::=  500

        warningNotify TRAP-TYPE 
            ENTERPRISE rackCDU
            VARIABLES { eventValue, eventDescription }
            DESCRIPTION 
                "Trap warning notification information for the SNMP Manager (obsolete)."
                --#TYPE      "Warning notification"
                --#SUMMARY   "An warning were triggered. Sensor value is: %d"
                --#ARGUMENTS {0}
                --#SEVERITY  MAJOR
                --#TIMEINDEX 5
                --#HELP      "This notification is obsolete. Please update the RackCDU control box firmware."
                --#HELPTAG   0
                --#STATE     DEGRADED
            ::=  501

        facilitySupplyWarning TRAP-TYPE 
            ENTERPRISE rackCDU
            VARIABLES { temperatureFacilityIn, eventDescription, rackNumber }
            DESCRIPTION 
                "Facility supply temperature warning."
                --#TYPE      "Facility supply temperature warning"
                --#SUMMARY   "Warning: Facility supply temperature in rack %s has exceeded its limits: Temperature is %d oC."
                --#ARGUMENTS {2, 0}
                --#SEVERITY  MAJOR
                --#TIMEINDEX 5
                --#HELP      "Action (high temperature): Apply auxiliary cooling to RackCDU or reduce server workloads. Action (low temperature): Raise facility liquid supply temperature."
                --#HELPTAG   0
                --#STATE     DEGRADED
            ::=  504

        facilityReturnWarning TRAP-TYPE 
            ENTERPRISE rackCDU
            VARIABLES { temperatureFacilityOut, eventDescription, rackNumber }
            DESCRIPTION 
                "Facility return temperature warning."
                --#TYPE      "Facility return temperature warning"
                --#SUMMARY   "Warning: Facility return temperature in rack %s has exceeded its limits: Temperature is %d oC."
                --#ARGUMENTS {2, 0}
                --#SEVERITY  MAJOR
                --#TIMEINDEX 5
                --#HELP      "Action (high temperature): Increase facility flow. Action (low temperature): Decrease facility flow."
                --#HELPTAG   0
                --#STATE     DEGRADED
            ::=  505

        serverSupplyWarning TRAP-TYPE 
            ENTERPRISE rackCDU
            VARIABLES { temperatureServerIn, eventDescription, rackNumber }
            DESCRIPTION 
                "Server supply temperature warning."
                --#TYPE      "Server supply temperature warning"
                --#SUMMARY   "Warning: Server supply temperature in rack %s has exceeded its limits: Temperature is %d oC."
                --#ARGUMENTS {2, 0}
                --#SEVERITY  MAJOR
                --#TIMEINDEX 5
                --#HELP      "Action (high temperature): Increase facility flow. Action (low temperature): Decrease facility flow."
                --#HELPTAG   0
                --#STATE     DEGRADED
            ::=  506

        serverReturnWarning TRAP-TYPE 
            ENTERPRISE rackCDU
            VARIABLES { temperatureServerOut, eventDescription, rackNumber }
            DESCRIPTION 
                "Server return temperature warning."
                --#TYPE      "Server return temperature warning"
                --#SUMMARY   "Warning: Server return temperature in rack %s has exceeded its limits: Temperature is %d oC."
                --#ARGUMENTS {2, 0}
                --#SEVERITY  MAJOR
                --#TIMEINDEX 5
                --#HELP      "Action (high temperature): Throttle down server workloads. Action (low temperature): Throttle up server workloads."
                --#HELPTAG   0
                --#STATE     DEGRADED
            ::=  507

        facilityPressureWarning TRAP-TYPE 
            ENTERPRISE rackCDU
            VARIABLES { pressureFacility, eventDescription, rackNumber }
            DESCRIPTION 
                "Facility pressure warning."
                --#TYPE      "Facility pressure warning"
                --#SUMMARY   "Warning: Facility pressure in rack %s has exceeded its limits: Pressure is %d mBar."
                --#ARGUMENTS {2, 0}
                --#SEVERITY  MAJOR
                --#TIMEINDEX 5
                --#HELP      "Action (high pressure): Throttle down facility pumps and check for blockage at other locations. Action (low pressure): Check facility pump health."
                --#HELPTAG   0
                --#STATE     DEGRADED
            ::=  508

        serverPressureWarning TRAP-TYPE 
            ENTERPRISE rackCDU
            VARIABLES { pressureServer, eventDescription, rackNumber }
            DESCRIPTION 
                "Server pressure warning."
                --#TYPE      "Server pressure warning"
                --#SUMMARY   "Warning: Server pressure in rack %s has exceeded its limits: Pressure is %d mBar."
                --#ARGUMENTS {2, 0}
                --#SEVERITY  MAJOR
                --#TIMEINDEX 5
                --#HELP      "Action (high pressure): Open reservoir seal to allow venting. Action (low pressure): No action needed."
                --#HELPTAG   0
                --#STATE     DEGRADED
            ::=  509

        facilityFlowWarning TRAP-TYPE 
            ENTERPRISE rackCDU
            VARIABLES { flowFacility, eventDescription, rackNumber }
            DESCRIPTION 
                "Facility flow warning."
                --#TYPE      "Facility flow warning"
                --#SUMMARY   "Warning: Facility flow in rack %s has exceeded its limits: Flow is %d ml/s."
                --#ARGUMENTS {2, 0}
                --#SEVERITY  MAJOR
                --#TIMEINDEX 5
                --#HELP      "Action (high flow): Throttle down facility pumps. Action (low flow): Check manual valves to RackCDU and check facility pump health."
                --#HELPTAG   0
                --#STATE     DEGRADED
            ::=  512

        facilitySupplyAlarm TRAP-TYPE 
            ENTERPRISE rackCDU
            VARIABLES { temperatureFacilityIn, eventDescription, rackNumber }
            DESCRIPTION 
                "Facility supply temperature alarm."
                --#TYPE      "Facility supply temperature alarm"
                --#SUMMARY   "Alarm: Facility supply temperature in rack %s has exceeded its limits: Temperature is %d oC."
                --#ARGUMENTS {2, 0}
                --#SEVERITY  CRITICAL
                --#TIMEINDEX 5
                --#HELP      "Action (high temperature): Apply auxiliary cooling to RackCDU or reduce server workloads. Action (low temperature): Raise facility liquid supply temperature."
                --#HELPTAG   0
                --#STATE     NONOPERATIONAL
            ::=  517

        facilityReturnAlarm TRAP-TYPE 
            ENTERPRISE rackCDU
            VARIABLES { temperatureFacilityOut, eventDescription, rackNumber }
            DESCRIPTION 
                "Facility return temperature alarm."
                --#TYPE      "Facility return temperature alarm"
                --#SUMMARY   "Alarm: Facility return temperature in rack %s has exceeded its limits: Temperature is %d oC."
                --#ARGUMENTS {2, 0}
                --#SEVERITY  CRITICAL
                --#TIMEINDEX 5
                --#HELP      "Action (high temperature): Increase facility flow. Action (low temperature): Decrease facility flow."
                --#HELPTAG   0
                --#STATE     NONOPERATIONAL
            ::=  518

        serverSupplyAlarm TRAP-TYPE 
            ENTERPRISE rackCDU
            VARIABLES { temperatureServerIn, eventDescription, rackNumber }
            DESCRIPTION 
                "Server supply temperature alarm."
                --#TYPE      "Server supply temperature alarm"
                --#SUMMARY   "Alarm: Server supply temperature in rack %s has exceeded its limits: Temperature is %d oC."
                --#ARGUMENTS {2, 0}
                --#SEVERITY  CRITICAL
                --#TIMEINDEX 5
                --#HELP      "Action (high temperature): Increase facility flow. Action (low temperature): Decrease facility flow."
                --#HELPTAG   0
                --#STATE     NONOPERATIONAL
            ::=  519

        serverReturnAlarm TRAP-TYPE 
            ENTERPRISE rackCDU
            VARIABLES { temperatureServerOut, eventDescription, rackNumber }
            DESCRIPTION 
                "Server return temperature alarm."
                --#TYPE      "Server return temperature alarm"
                --#SUMMARY   "Alarm: Server return temperature in rack %s has exceeded its limits: Temperature is %d oC."
                --#ARGUMENTS {2, 0}
                --#SEVERITY  CRITICAL
                --#TIMEINDEX 5
                --#HELP      "Action (high temperature): Throttle down server workloads. Action (low temperature): Throttle up server workloads."
                --#HELPTAG   0
                --#STATE     NONOPERATIONAL
            ::=  520

        facilityPressureAlarm TRAP-TYPE 
            ENTERPRISE rackCDU
            VARIABLES { pressureFacility, eventDescription, rackNumber }
            DESCRIPTION 
                "Facility pressure alarm."
                --#TYPE      "Facility pressure alarm"
                --#SUMMARY   "Alarm: Facility pressure in rack %s has exceeded its limits: Pressure is %d mBar."
                --#ARGUMENTS {2, 0}
                --#SEVERITY  CRITICAL
                --#TIMEINDEX 5
                --#HELP      "Action (high pressure): Throttle down facility pumps and check for blockage at other locations. Action (low pressure): Check facility pump health."
                --#HELPTAG   0
                --#STATE     NONOPERATIONAL
            ::=  521

        serverPressureAlarm TRAP-TYPE 
            ENTERPRISE rackCDU
            VARIABLES { pressureServer, eventDescription, rackNumber }
            DESCRIPTION 
                "Server pressure alarm."
                --#TYPE      "Server pressure alarm"
                --#SUMMARY   "Alarm: Server pressure in rack %s has exceeded its limits: Pressure is %d mBar."
                --#ARGUMENTS {2, 0}
                --#SEVERITY  CRITICAL
                --#TIMEINDEX 5
                --#HELP      "Action (high pressure): Open reservoir seal to allow venting. Action (low pressure): No action needed."
                --#HELPTAG   0
                --#STATE     NONOPERATIONAL
            ::=  522

        leakDetectionAlarm TRAP-TYPE 
            ENTERPRISE rackCDU
            VARIABLES { serverLeak, eventDescription, rackNumber }
            DESCRIPTION 
                "Leak detection alarm."
                --#TYPE      "Leak detection alarm"
                --#SUMMARY   "Alarm: A leak were detected in rack %s."
                --#ARGUMENTS {2}
                --#SEVERITY  CRITICAL
                --#TIMEINDEX 5
                --#HELP      "Action: Shut down servers and power of PDUs."
                --#HELPTAG   0
                --#STATE     NONOPERATIONAL
            ::=  523

        liquidLevelAlarm TRAP-TYPE 
            ENTERPRISE rackCDU
            VARIABLES { serverLevel, eventDescription, rackNumber }
            DESCRIPTION 
                "Low liquid level alarm."
                --#TYPE      "Low liquid level alarm"
                --#SUMMARY   "Alarm: The liquid level in rack %s. is low."
                --#ARGUMENTS {2}
                --#SEVERITY  CRITICAL
                --#TIMEINDEX 5
                --#HELP      "Action: Refill RackCDU reservoir."
                --#HELPTAG   0
                --#STATE     NONOPERATIONAL
            ::=  524

        facilityFlowAlarm TRAP-TYPE 
            ENTERPRISE rackCDU
            VARIABLES { flowFacility, eventDescription, rackNumber }
            DESCRIPTION 
                "Facility flow alarm."
                --#TYPE      "Facility flow alarm"
                --#SUMMARY   "Alarm: Facility flow in rack %s has exceeded its limits: Flow is %d ml/s."
                --#ARGUMENTS {2, 0}
                --#SEVERITY  CRITICAL
                --#TIMEINDEX 5
                --#HELP      "Action (high flow): Throttle down facility pumps. Action (low flow): Check manual valves to RackCDU and check facility pump health."
                --#HELPTAG   0
                --#STATE     NONOPERATIONAL
            ::=  525

    
    END

--
-- ASETEK-RACKCDU-SMI-V1-MIB-V16.mib
--
