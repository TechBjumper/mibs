-- Teldat, S.A.

    -- Parque Tecnolgico de Madrid

    -- 28760, Tres Cantos (Madrid)

    -- Tlf: +34-918076565

    -- Fax: +34-918076521

    -- e-mail: id@teldat.com


    -- MIB privada de Teldat


    -- MIB de monitorizacin de LLC


    -- Historial:
    --      07/02/14    M.A. Pastor     XH 3523. Errors with HP Openview 9.20
    -- 1.1  08/07/09    I. Muoz        Revisin de todas las MIB para evitar
    --                  M.A. Pastor     warnings y errores de compilacin
    -- 1.0  01/07/04    J. Molina       Archivo procedente de LLC.mib


    -- Historial de LLC.mib:
    -- 01-10-01  N.Villaseor       Traduccin al ingles
    -- 01-12-00  M.A. Pastor        Modificaciones para que pueda ser
    --                              compilada utilizando compiladores
    --                              distintos del de Teldat
        -- 14-09-00  J. Alvarez         Implementacion inicial

TELDAT-MON-INTERF-LLC-MIB DEFINITIONS ::= BEGIN

    IMPORTS
        Counter
            FROM RFC1155-SMI
        OBJECT-TYPE
            FROM RFC-1212
        DisplayString
            FROM RFC1213-MIB
        telProdNpMonInterfRouter
            FROM TELDAT-SW-STRUCTURE-MIB;


    -- Grupo telProdNpMonInterfLLC

    telProdNpMonInterfLLC   OBJECT IDENTIFIER ::= { telProdNpMonInterfRouter 8 }

    -- Tabla de borrado de contadores

    telProdNpMonInterfLLCClearCountersTable OBJECT-TYPE
        SYNTAX  SEQUENCE OF TelProdNpMonInterfLLCClearCountersEntry
        ACCESS  not-accessible
        STATUS  mandatory
        DESCRIPTION
        "This table allows to delete statistics of a LLC interfaz."
        ::={ telProdNpMonInterfLLC 1 }

    telProdNpMonInterfLLCClearCountersEntry OBJECT-TYPE
        SYNTAX  TelProdNpMonInterfLLCClearCountersEntry
        ACCESS  not-accessible
        STATUS  mandatory
        DESCRIPTION
        ""
        INDEX { telProdNpMonInterfLLCClearCountersIfc }
        ::={ telProdNpMonInterfLLCClearCountersTable 1 }

    TelProdNpMonInterfLLCClearCountersEntry ::=
        SEQUENCE {
            telProdNpMonInterfLLCClearCountersIfc
                INTEGER,
            telProdNpMonInterfLLCClearCountersCmd
                INTEGER
            }

    telProdNpMonInterfLLCClearCountersIfc OBJECT-TYPE
        SYNTAX  INTEGER
        ACCESS  read-only
        STATUS  mandatory
        DESCRIPTION
        "Interface number. Table index"
        ::={ telProdNpMonInterfLLCClearCountersEntry 1 }

    telProdNpMonInterfLLCClearCountersCmd OBJECT-TYPE
        SYNTAX  INTEGER{
            delete(1),
            ok(2),
            error(3),
            undefined(4)
            }
        ACCESS  read-write
        STATUS  mandatory
        DESCRIPTION
        "Deletes the counters containing LLC statistics. In case the delete
        operation were correct, the variable will be ok(2). Otherwise,
        the variable will be error(3)."
        ::={ telProdNpMonInterfLLCClearCountersEntry 2 }

    -- Tabla de informacin de SAPs y sesiones abiertas por interfaz

    telProdNpMonInterfLLCListInterfTable OBJECT-TYPE
        SYNTAX  SEQUENCE OF TelProdNpMonInterfLLCListInterfEntry
        ACCESS  not-accessible
        STATUS  mandatory
        DESCRIPTION
        "Displays all SAPs opened on this interface, providing also the
        number of open sessions on each interface."
        ::={ telProdNpMonInterfLLC 2 }

    telProdNpMonInterfLLCListInterfEntry OBJECT-TYPE
        SYNTAX  TelProdNpMonInterfLLCListInterfEntry
        ACCESS  not-accessible
        STATUS  mandatory
        DESCRIPTION
        "The table index are: Interface and SAP number."
        INDEX { telProdNpMonInterfLLCListInterfNumIfc,telProdNpMonInterfLLCListInterfNumSAP }
        ::={ telProdNpMonInterfLLCListInterfTable 1 }

    TelProdNpMonInterfLLCListInterfEntry ::=
        SEQUENCE {
            telProdNpMonInterfLLCListInterfNumIfc
                INTEGER,
            telProdNpMonInterfLLCListInterfNumSAP
                INTEGER,
            telProdNpMonInterfLLCListInterfNumSess
                INTEGER
            }

    telProdNpMonInterfLLCListInterfNumIfc OBJECT-TYPE
        SYNTAX  INTEGER
        ACCESS  read-only
        STATUS  mandatory
        DESCRIPTION
        "Interface number. First table index."
        ::={ telProdNpMonInterfLLCListInterfEntry 1 }

    telProdNpMonInterfLLCListInterfNumSAP OBJECT-TYPE
        SYNTAX  INTEGER
        ACCESS  read-only
        STATUS  mandatory
        DESCRIPTION
        "SAP Number. Second table index."
        ::={ telProdNpMonInterfLLCListInterfEntry 2 }

    telProdNpMonInterfLLCListInterfNumSess OBJECT-TYPE
        SYNTAX  INTEGER
        ACCESS  read-only
        STATUS  mandatory
        DESCRIPTION
        "Number of active sessions."
        ::={ telProdNpMonInterfLLCListInterfEntry 3 }

    -- Tabla de informacin por SAP

    telProdNpMonInterfLLCListSAPTable OBJECT-TYPE
        SYNTAX  SEQUENCE OF TelProdNpMonInterfLLCListSAPEntry
        ACCESS  not-accessible
        STATUS  mandatory
        DESCRIPTION
        "Display information for the specified SAP on the interface."
        ::={ telProdNpMonInterfLLC 3 }

    telProdNpMonInterfLLCListSAPEntry OBJECT-TYPE
        SYNTAX  TelProdNpMonInterfLLCListSAPEntry
        ACCESS  not-accessible
        STATUS  mandatory
        DESCRIPTION
        "Table index: interface and SAP number."
        INDEX { telProdNpMonInterfLLCListSAPNumIfc,telProdNpMonInterfLLCListSAPNumSAP }
        ::={ telProdNpMonInterfLLCListSAPTable 1 }

    TelProdNpMonInterfLLCListSAPEntry ::=
        SEQUENCE {
            telProdNpMonInterfLLCListSAPNumIfc
                INTEGER,
            telProdNpMonInterfLLCListSAPNumSAP
                INTEGER,
            telProdNpMonInterfLLCListSAPTypeIfc
                INTEGER,
            telProdNpMonInterfLLCListSAPT1
                INTEGER,
            telProdNpMonInterfLLCListSAPT2
                INTEGER,
            telProdNpMonInterfLLCListSAPTi
                INTEGER,
            telProdNpMonInterfLLCListSAPN2
                INTEGER,
            telProdNpMonInterfLLCListSAPN1
                INTEGER,
            telProdNpMonInterfLLCListSAPN3
                INTEGER,
            telProdNpMonInterfLLCListSAPTw
                INTEGER,
            telProdNpMonInterfLLCListSAPNw
                INTEGER,
            telProdNpMonInterfLLCListSAPXmtUI
                Counter,
            telProdNpMonInterfLLCListSAPRcvdUI
                Counter,
            telProdNpMonInterfLLCListSAPXmtTEST
                Counter,
            telProdNpMonInterfLLCListSAPRcvdTEST
                Counter,
            telProdNpMonInterfLLCListSAPXmtXID
                Counter,
            telProdNpMonInterfLLCListSAPRcvdXID
                Counter,
            telProdNpMonInterfLLCListSAPXmtI
                Counter,
            telProdNpMonInterfLLCListSAPRcvdI
                Counter,
            telProdNpMonInterfLLCListSAPXmtRR
                Counter,
            telProdNpMonInterfLLCListSAPRcvdRR
                Counter,
            telProdNpMonInterfLLCListSAPXmtRNR
                Counter,
            telProdNpMonInterfLLCListSAPRcvdRNR
                Counter,
            telProdNpMonInterfLLCListSAPXmtREJ
                Counter,
            telProdNpMonInterfLLCListSAPRcvdREJ
                Counter,
            telProdNpMonInterfLLCListSAPXmtSABME
                Counter,
            telProdNpMonInterfLLCListSAPRcvdSABME
                Counter,
            telProdNpMonInterfLLCListSAPXmtUA
                Counter,
            telProdNpMonInterfLLCListSAPRcvdUA
                Counter,
            telProdNpMonInterfLLCListSAPXmtDISC
                Counter,
            telProdNpMonInterfLLCListSAPRcvdDISC
                Counter,
            telProdNpMonInterfLLCListSAPXmtDM
                Counter,
            telProdNpMonInterfLLCListSAPRcvdDM
                Counter,
            telProdNpMonInterfLLCListSAPXmtFRMR
                Counter,
            telProdNpMonInterfLLCListSAPRcvdFRMR
                Counter,
            telProdNpMonInterfLLCListSAPDiscarded
                Counter,
            telProdNpMonInterfLLCListSAPRefused
                Counter,
            telProdNpMonInterfLLCListSAPNumOpenSess
                INTEGER,
            telProdNpMonInterfLLCListSAPNumActivSess
                INTEGER,
            telProdNpMonInterfLLCListSAPIdSess
                DisplayString
            }

    telProdNpMonInterfLLCListSAPNumIfc OBJECT-TYPE
        SYNTAX  INTEGER
        ACCESS  read-only
        STATUS  mandatory
        DESCRIPTION
        "Interface number. First table index."
        ::={ telProdNpMonInterfLLCListSAPEntry 1 }

    telProdNpMonInterfLLCListSAPNumSAP OBJECT-TYPE
        SYNTAX  INTEGER
        ACCESS  read-only
        STATUS  mandatory
        DESCRIPTION
        "SAP number. Second table index."
        ::={ telProdNpMonInterfLLCListSAPEntry 2 }

    telProdNpMonInterfLLCListSAPTypeIfc OBJECT-TYPE
        SYNTAX  INTEGER{
            vi(0),
            pn(1),
            pri(2),
            xeth(3),
            arpa(4),
            chp(5),
            astm(6),
            eth(7),
            sl(8),
            x28(9),
            dmr(10),
            tkr(11),
            snk(12),
            x25(13),
            man(14),
            atr(15),
            fddi(16),
            srly(17),
            ippn(18),
            fr(19),
            ppp(20),
            bdg(21),
            null(22),
            gwt-ntype-b-isdn(23),
            sdlc(24),
            v25b(25),
            r-n(26),
            n-r(27),
            rdsid(28),
            xot(29),
            a270(30),
            tnip(31),
            mppp(32),
            atm(33),
            subatm(34)
            }
        ACCESS  read-only
        STATUS  mandatory
        DESCRIPTION
        "Interface type.
        VI (0)                  VI LNI
        PN (1)                  ProNET
        PRI (2)                 PRI IFC
        XETH (3)                Experimental EtherNet (3 MBit)
        ARPA (4)                ARPANet
        CHP (5)                 CHAOS protocol net
        ASTM (6)                ASTM line interface
        Eth (7)                 EtherNet (10 MBit)
        SL (8)                  New serial line link
        X28 (9)                 X.28
        DMR (10)                DEC DMR interface
        TKR (11)                802.5 token ring
        SNK (12)                Sink network (not a real network)
        X25 (13)                X25 network
        MAN (14)                802.6 metro area network
        ATR (15)                Apollo Token Ring
        FDDI (16)               FDDI
        SRLY (17)               SDLC relay int
        IPPN (18)               IP Protocol Net
        FR (19)                 Frame Relay network
        PPP (20)                PPP network
        BDG (21)                Bridging pseudo-handler
        NULL (22)               Null device
        GWT-NTYPE-B-ISDN (23)   ISDN network channel B
        SDLC (24)               TRUE SDLC int
        V25B (25)               V.25bis base network
        R->N (26)               Teldat Micro-node
        N->R (27)               Teldat Router
        RDSID (28)              ISDN D Channel
        XOT (29)
        270 (30)
        TNIP (31)               Interface real IP tunnel
        MPPP (32)               Interface Multilink PPP
        ATM (33)                Interface ATM
        SUBATM (34)             Subinterface ATM."
        ::={ telProdNpMonInterfLLCListSAPEntry 3 }

    telProdNpMonInterfLLCListSAPT1 OBJECT-TYPE
        SYNTAX  INTEGER
        ACCESS  read-only
        STATUS  mandatory
        DESCRIPTION
        "Time it takes for this timer to expire when the LLC fails to
        receive an acknowledgment or response from the other LLC
        station. In case it were 0, it woeld not be active."
        ::={ telProdNpMonInterfLLCListSAPEntry 4 }

    telProdNpMonInterfLLCListSAPT2 OBJECT-TYPE
        SYNTAX  INTEGER
        ACCESS  read-only
        STATUS  mandatory
        DESCRIPTION
        "Time delay the LLC uses before sending an ACK for a received
        I-frame. In case it were 0, it would not be active."
        ::={ telProdNpMonInterfLLCListSAPEntry 5 }

    telProdNpMonInterfLLCListSAPTi OBJECT-TYPE
        SYNTAX  INTEGER
        ACCESS  read-only
        STATUS  mandatory
        DESCRIPTION
        "Time the LLC waits during inactivity before issuing an RR.
        In case it were 0, it would not be active."
        ::={ telProdNpMonInterfLLCListSAPEntry 6 }

    telProdNpMonInterfLLCListSAPN2 OBJECT-TYPE
        SYNTAX  INTEGER
        ACCESS  read-only
        STATUS  mandatory
        DESCRIPTION
        "Maximum number of retries by the LLC protocol."
        ::={ telProdNpMonInterfLLCListSAPEntry 7 }

    telProdNpMonInterfLLCListSAPN1 OBJECT-TYPE
        SYNTAX  INTEGER
        ACCESS  read-only
        STATUS  mandatory
        DESCRIPTION
        "Data (in bytes) allowed in the I-field of an LLC2 frame."
        ::={ telProdNpMonInterfLLCListSAPEntry 8 }

    telProdNpMonInterfLLCListSAPN3 OBJECT-TYPE
        SYNTAX  INTEGER
        ACCESS  read-only
        STATUS  mandatory
        DESCRIPTION
        "Value that is used with T2 timer to reduce acknowledgment traffic
        for received I-frames."
        ::={ telProdNpMonInterfLLCListSAPEntry 9 }

    telProdNpMonInterfLLCListSAPTw OBJECT-TYPE
        SYNTAX  INTEGER
        ACCESS  read-only
        STATUS  mandatory
        DESCRIPTION
        "I-frames that can be sent before receiving an RR."
        ::={ telProdNpMonInterfLLCListSAPEntry 10 }

    telProdNpMonInterfLLCListSAPNw OBJECT-TYPE
        SYNTAX  INTEGER
        ACCESS  read-only
        STATUS  mandatory
        DESCRIPTION
        "I-frames that the LLC must receive before incrementing Ww by 1."
        ::={ telProdNpMonInterfLLCListSAPEntry 11 }

    telProdNpMonInterfLLCListSAPXmtUI OBJECT-TYPE
        SYNTAX  Counter
        ACCESS  read-only
        STATUS  mandatory
        DESCRIPTION
        "Frames type UI transmitted (Xmt)."
        ::={ telProdNpMonInterfLLCListSAPEntry 12 }

    telProdNpMonInterfLLCListSAPRcvdUI OBJECT-TYPE
        SYNTAX  Counter
        ACCESS  read-only
        STATUS  mandatory
        DESCRIPTION
        "Frames type UI received (Rcvd)."
        ::={ telProdNpMonInterfLLCListSAPEntry 13 }

    telProdNpMonInterfLLCListSAPXmtTEST OBJECT-TYPE
        SYNTAX  Counter
        ACCESS  read-only
        STATUS  mandatory
        DESCRIPTION
        "Frames type TEST transmitted (Xmt)."
        ::={ telProdNpMonInterfLLCListSAPEntry 14 }

    telProdNpMonInterfLLCListSAPRcvdTEST OBJECT-TYPE
        SYNTAX  Counter
        ACCESS  read-only
        STATUS  mandatory
        DESCRIPTION
        "Frames type TEST received (Rcvd)."
        ::={ telProdNpMonInterfLLCListSAPEntry 15 }

    telProdNpMonInterfLLCListSAPXmtXID OBJECT-TYPE
        SYNTAX  Counter
        ACCESS  read-only
        STATUS  mandatory
        DESCRIPTION
        "Frames type XID transmitted (Xmt)."
        ::={ telProdNpMonInterfLLCListSAPEntry 16 }

    telProdNpMonInterfLLCListSAPRcvdXID OBJECT-TYPE
        SYNTAX  Counter
        ACCESS  read-only
        STATUS  mandatory
        DESCRIPTION
        "Frames type XID received (Rcvd)."
        ::={ telProdNpMonInterfLLCListSAPEntry 17 }

    telProdNpMonInterfLLCListSAPXmtI OBJECT-TYPE
        SYNTAX  Counter
        ACCESS  read-only
        STATUS  mandatory
        DESCRIPTION
        "Frames type I transmitted (Xmt)."
        ::={ telProdNpMonInterfLLCListSAPEntry 18 }

    telProdNpMonInterfLLCListSAPRcvdI OBJECT-TYPE
        SYNTAX  Counter
        ACCESS  read-only
        STATUS  mandatory
        DESCRIPTION
        "Frames type I received (Rcvd)."
        ::={ telProdNpMonInterfLLCListSAPEntry 19 }

    telProdNpMonInterfLLCListSAPXmtRR OBJECT-TYPE
        SYNTAX  Counter
        ACCESS  read-only
        STATUS  mandatory
        DESCRIPTION
        "Frames type RR transmitted (Xmt)."
        ::={ telProdNpMonInterfLLCListSAPEntry 20 }

    telProdNpMonInterfLLCListSAPRcvdRR OBJECT-TYPE
        SYNTAX  Counter
        ACCESS  read-only
        STATUS  mandatory
        DESCRIPTION
        "Frames type RR received (Rcvd)."
        ::={ telProdNpMonInterfLLCListSAPEntry 21 }

    telProdNpMonInterfLLCListSAPXmtRNR OBJECT-TYPE
        SYNTAX  Counter
        ACCESS  read-only
        STATUS  mandatory
        DESCRIPTION
        "Frames type RNR transmitted (Xmt)."
        ::={ telProdNpMonInterfLLCListSAPEntry 22 }

    telProdNpMonInterfLLCListSAPRcvdRNR OBJECT-TYPE
        SYNTAX  Counter
        ACCESS  read-only
        STATUS  mandatory
        DESCRIPTION
        "Frames type RNR received (Rcvd)."
        ::={ telProdNpMonInterfLLCListSAPEntry 23 }

    telProdNpMonInterfLLCListSAPXmtREJ OBJECT-TYPE
        SYNTAX  Counter
        ACCESS  read-only
        STATUS  mandatory
        DESCRIPTION
        "Frames type REJ transmitted (Xmt)."
        ::={ telProdNpMonInterfLLCListSAPEntry 24 }

    telProdNpMonInterfLLCListSAPRcvdREJ OBJECT-TYPE
        SYNTAX  Counter
        ACCESS  read-only
        STATUS  mandatory
        DESCRIPTION
        "Frames type REJ received (Rcvd)."
        ::={ telProdNpMonInterfLLCListSAPEntry 25 }

    telProdNpMonInterfLLCListSAPXmtSABME OBJECT-TYPE
        SYNTAX  Counter
        ACCESS  read-only
        STATUS  mandatory
        DESCRIPTION
        "Frames type SABME transmitted (Xmt)."
        ::={ telProdNpMonInterfLLCListSAPEntry 26 }

    telProdNpMonInterfLLCListSAPRcvdSABME OBJECT-TYPE
        SYNTAX  Counter
        ACCESS  read-only
        STATUS  mandatory
        DESCRIPTION
        "Frames type SABME received (Rcvd)."
        ::={ telProdNpMonInterfLLCListSAPEntry 27 }

    telProdNpMonInterfLLCListSAPXmtUA OBJECT-TYPE
        SYNTAX  Counter
        ACCESS  read-only
        STATUS  mandatory
        DESCRIPTION
        "Frames type UA transmitted (Xmt)."
        ::={ telProdNpMonInterfLLCListSAPEntry 28 }

    telProdNpMonInterfLLCListSAPRcvdUA OBJECT-TYPE
        SYNTAX  Counter
        ACCESS  read-only
        STATUS  mandatory
        DESCRIPTION
        "Frames type UA received (Rcvd)."
        ::={ telProdNpMonInterfLLCListSAPEntry 29 }

    telProdNpMonInterfLLCListSAPXmtDISC OBJECT-TYPE
        SYNTAX  Counter
        ACCESS  read-only
        STATUS  mandatory
        DESCRIPTION
        "Frames type DISC transmitted (Xmt)."
        ::={ telProdNpMonInterfLLCListSAPEntry 30 }

    telProdNpMonInterfLLCListSAPRcvdDISC OBJECT-TYPE
        SYNTAX  Counter
        ACCESS  read-only
        STATUS  mandatory
        DESCRIPTION
        "Frames type DISC received (Rcvd)."
        ::={ telProdNpMonInterfLLCListSAPEntry 31 }

    telProdNpMonInterfLLCListSAPXmtDM OBJECT-TYPE
        SYNTAX  Counter
        ACCESS  read-only
        STATUS  mandatory
        DESCRIPTION
        "Frames type DM transmitted (Xmt)."
        ::={ telProdNpMonInterfLLCListSAPEntry 32 }

    telProdNpMonInterfLLCListSAPRcvdDM OBJECT-TYPE
        SYNTAX  Counter
        ACCESS  read-only
        STATUS  mandatory
        DESCRIPTION
        "Frames type DM received (Rcvd)."
        ::={ telProdNpMonInterfLLCListSAPEntry 33 }

    telProdNpMonInterfLLCListSAPXmtFRMR OBJECT-TYPE
        SYNTAX  Counter
        ACCESS  read-only
        STATUS  mandatory
        DESCRIPTION
        "Frames type FRMR transmitted (Xmt)."
        ::={ telProdNpMonInterfLLCListSAPEntry 34 }

    telProdNpMonInterfLLCListSAPRcvdFRMR OBJECT-TYPE
        SYNTAX  Counter
        ACCESS  read-only
        STATUS  mandatory
        DESCRIPTION
        "Frames type FRMR received (Rcvd)."
        ::={ telProdNpMonInterfLLCListSAPEntry 35 }

    telProdNpMonInterfLLCListSAPDiscarded OBJECT-TYPE
        SYNTAX  Counter
        ACCESS  read-only
        STATUS  mandatory
        DESCRIPTION
        "I-frames discarded by LLC, normally because the sequence number
        is out of sequence."
        ::={ telProdNpMonInterfLLCListSAPEntry 36 }

    telProdNpMonInterfLLCListSAPRefused OBJECT-TYPE
        SYNTAX  Counter
        ACCESS  read-only
        STATUS  mandatory
        DESCRIPTION
        "I-frames discarded by the software above the LLC. For example:
        LNM (LAN Network Manager) and DLSw (Data Link Switching)."
        ::={ telProdNpMonInterfLLCListSAPEntry 37 }

    telProdNpMonInterfLLCListSAPNumOpenSess OBJECT-TYPE
        SYNTAX  INTEGER
        ACCESS  read-only
        STATUS  mandatory
        DESCRIPTION
        "Sessions that were opened over this SAP."
        ::={ telProdNpMonInterfLLCListSAPEntry 38 }

    telProdNpMonInterfLLCListSAPNumActivSess OBJECT-TYPE
        SYNTAX  INTEGER
        ACCESS  read-only
        STATUS  mandatory
        DESCRIPTION
        "Currently active sessions running over the interface."
        ::={ telProdNpMonInterfLLCListSAPEntry 39 }

    telProdNpMonInterfLLCListSAPIdSess OBJECT-TYPE
        SYNTAX  DisplayString(SIZE(0..30))
        ACCESS  read-only
        STATUS  mandatory
        DESCRIPTION
        "Session ID for the interface."
        ::={ telProdNpMonInterfLLCListSAPEntry 40 }

    -- Tabla de informacin por sesiones

    telProdNpMonInterfLLCListSessTable OBJECT-TYPE
        SYNTAX  SEQUENCE OF TelProdNpMonInterfLLCListSessEntry
        ACCESS  not-accessible
        STATUS  mandatory
        DESCRIPTION
        "Displays information for the specific LLC session opened on the
        interface."
        ::={ telProdNpMonInterfLLC 4 }

     telProdNpMonInterfLLCListSessEntry OBJECT-TYPE
        SYNTAX  TelProdNpMonInterfLLCListSessEntry
        ACCESS  not-accessible
        STATUS  mandatory
        DESCRIPTION
        "The table index is by order of session appearance."
        INDEX { telProdNpMonInterfLLCListSessInd }
        ::={ telProdNpMonInterfLLCListSessTable 1 }

     TelProdNpMonInterfLLCListSessEntry ::=
        SEQUENCE {
            telProdNpMonInterfLLCListSessInd
                INTEGER,
            telProdNpMonInterfLLCListSessIdSess
                DisplayString,
            telProdNpMonInterfLLCListSessRemoteMAC
                DisplayString,
            telProdNpMonInterfLLCListSessSourceMAC
                DisplayString,
            telProdNpMonInterfLLCListSessRemoteSAP
                INTEGER,
            telProdNpMonInterfLLCListSessLocalSAP
                INTEGER,
            telProdNpMonInterfLLCListSessRIF
                DisplayString,
            telProdNpMonInterfLLCListSessPriority
                INTEGER,
            telProdNpMonInterfLLCListSessState
                INTEGER,
            telProdNpMonInterfLLCListSessT1
                INTEGER,
            telProdNpMonInterfLLCListSessT2
                INTEGER,
            telProdNpMonInterfLLCListSessTi
                INTEGER,
            telProdNpMonInterfLLCListSessN1
                INTEGER,
            telProdNpMonInterfLLCListSessN2
                INTEGER,
            telProdNpMonInterfLLCListSessN3
                INTEGER,
            telProdNpMonInterfLLCListSessTw
                INTEGER,
            telProdNpMonInterfLLCListSessWw
                INTEGER,
            telProdNpMonInterfLLCListSessNw
                INTEGER,
            telProdNpMonInterfLLCListSessVs
                INTEGER,
            telProdNpMonInterfLLCListSessVr
                INTEGER,
            telProdNpMonInterfLLCListSessVa
                INTEGER,
            telProdNpMonInterfLLCListSessACKpend
                INTEGER,
            telProdNpMonInterfLLCListSessTXpend
                INTEGER,
            telProdNpMonInterfLLCListSessLocalBusy
                INTEGER,
            telProdNpMonInterfLLCListSessRemoteBusy
                INTEGER,
            telProdNpMonInterfLLCListSessRetryCount
                INTEGER,
            telProdNpMonInterfLLCListSessApOuFlStop
                INTEGER,
            telProdNpMonInterfLLCListSessSeProRunning
                INTEGER,
            telProdNpMonInterfLLCListSessXmtI
                Counter,
            telProdNpMonInterfLLCListSessRcvdI
                Counter,
            telProdNpMonInterfLLCListSessXmtRR
                Counter,
            telProdNpMonInterfLLCListSessRcvdRR
                Counter,
            telProdNpMonInterfLLCListSessXmtRNR
                Counter,
            telProdNpMonInterfLLCListSessRcvdRNR
                Counter,
            telProdNpMonInterfLLCListSessXmtREJ
                Counter,
            telProdNpMonInterfLLCListSessRcvdREJ
                Counter,
            telProdNpMonInterfLLCListSessDiscarded
                Counter,
            telProdNpMonInterfLLCListSessRefused
                Counter
            }

    telProdNpMonInterfLLCListSessInd OBJECT-TYPE
        SYNTAX  INTEGER
        ACCESS  read-only
        STATUS  mandatory
        DESCRIPTION
        "Entry number. Table index."
        ::={ telProdNpMonInterfLLCListSessEntry 1 }

    telProdNpMonInterfLLCListSessIdSess OBJECT-TYPE
        SYNTAX  DisplayString(SIZE(0..10))
        ACCESS  read-only
        STATUS  mandatory
        DESCRIPTION
        "Session ID for the interface. Written with format XX-XX-XXXX in
        hexadecimal, the two first digits indicate the interface, the two next
        the SAP number, and the last four the session number."
        ::={ telProdNpMonInterfLLCListSessEntry 2 }

    telProdNpMonInterfLLCListSessRemoteMAC OBJECT-TYPE
        SYNTAX  DisplayString(SIZE(0..17))
        ACCESS  read-only
        STATUS  mandatory
        DESCRIPTION
        "Router remote LLC MAC addresss."
        ::={ telProdNpMonInterfLLCListSessEntry 3 }

    telProdNpMonInterfLLCListSessSourceMAC OBJECT-TYPE
        SYNTAX  DisplayString(SIZE(0..17))
        ACCESS  read-only
        STATUS  mandatory
        DESCRIPTION
        "Router local LLC MAC address."
        ::={ telProdNpMonInterfLLCListSessEntry 4 }

    telProdNpMonInterfLLCListSessRemoteSAP OBJECT-TYPE
        SYNTAX  INTEGER
        ACCESS  read-only
        STATUS  mandatory
        DESCRIPTION
        "Router remote SAP address for the LLC connection."
        ::={ telProdNpMonInterfLLCListSessEntry 5 }

    telProdNpMonInterfLLCListSessLocalSAP OBJECT-TYPE
        SYNTAX  INTEGER
        ACCESS  read-only
        STATUS  mandatory
        DESCRIPTION
        "Router local SAP address for the LLC connection."
        ::={ telProdNpMonInterfLLCListSessEntry 6 }

    telProdNpMonInterfLLCListSessRIF OBJECT-TYPE
        SYNTAX  DisplayString(SIZE(0..29))
        ACCESS  read-only
        STATUS  mandatory
        DESCRIPTION
        "RIF of the frame."
        ::={  telProdNpMonInterfLLCListSessEntry 7 }

    telProdNpMonInterfLLCListSessPriority OBJECT-TYPE
        SYNTAX  INTEGER
        ACCESS  read-only
        STATUS  mandatory
        DESCRIPTION
        "Priority of the packet. 0-7 for upper layer control."
        ::={  telProdNpMonInterfLLCListSessEntry 8 }

    telProdNpMonInterfLLCListSessState OBJECT-TYPE
        SYNTAX  INTEGER{
            link-closed(1),
            disconnected(2),
            link-opening(3),
            disconnecting(4),
            frmr-sent(5),
            link-opened(6),
            local-busy(7),
            rejection(8),
            checkpointing(9),
            ckpt-lb(10),
            ckpt-rej(11),
            resetting(12),
            remote-busy(13),
            lb-rb(14),
            rej-lb(15),
            rej-rb(16),
            ckpt-rej-lb(17),
            ckpt-clr(18),
            ckpt-rej-clr(19),
            rej-lb-rb(20),
            frmr-received(21)
            }
        ACCESS  read-only
        STATUS  mandatory
        DESCRIPTION
        "The finite state(s) that results from interaction between
        the LLC peers:
        LINK-CLOSED (1):    The remote LLC peer is not known to the local LLC
                            peer and is considered as not existing.
        DISCONNECTED (2):   The local LLC peer is known to the other peer.This
                            LLC peer can send and receive XID, TEST, SABME,
                            and DISC commands; and XID TEST, UA, and DM
                            responses.
        LINK-OPENING (3):   The state of the local LLC peer after sending
                            a SABME or UA in response to a received SABME.
        DISCONNECTING (4):  The state of the local LLC after sending a DISC
                            command to the remote LLC peer.
        FRMR-SENT (5):      The local LLC peer has entered the frame reject
                            exception state and has sent a FRMR response
                            across the link.
        LINK-OPENED (6):    The local LLC peer is in the data transfer phase.
        LOCAL-BUSY (7):     The local LLC peer is unable to receive additional
                            I-frames.
        REJECTION (8):      A local LLC peer that has received one or more
                            out-of-sequence I-frames.
        CHECKPOINTING (9):  The local LLC peer has sent a poll to the remote LLC
                            peer and is waiting for an appropiate response.
        CKPT-LB (10):       Combination of checkpointing and local busy states.
        CKPT-REJ (11):      Combination of checkpointing and rejection states.
        RESETTING (12):     The local LLC peer has received a SABME and is
                            reestablishing the link.
        REMOTE-BUSY (13):   The state that occurs when an RNR is received from the
                            remote LLC peer.
        LB-RB (14):         Combination of Local-Busy and Remote-Busy states.
        REJ-LB (15):        Combination of rejection and Local-Busy states.
        REJ-RB (16):        Combination of rejection and Remote-Busy states.
        CKPT-REJ-LB (17):   Combination of checkpointing, rejection, and
                            Local-Busy states.
        CKPT-CLR (18):      Combination state resulting from the termination of
                            a Local-Busy condition while the LLC peer is
                            CKPT-LB.
        CKPT-REJ-CLR (19):  Combination state resulting from the transfer of
                            an unconfirmed Local-Busy clear while the link
                            station  is in the CKPT-REJ-LB state.
        REJ-LB-RB (20):     Combination of the rejection, Local-Busy, and
                            Remote-Busy states.
        FRMR-RECEIVED (21): The local LLC peer has received an FRMR response
                            from the remote LLC peer."
        ::={ telProdNpMonInterfLLCListSessEntry 9 }

    telProdNpMonInterfLLCListSessT1 OBJECT-TYPE
        SYNTAX  INTEGER
        ACCESS  read-only
        STATUS  mandatory
        DESCRIPTION
        "Time it takes for this timer to expire when the LLC fails to
        receive an acknowledgment or response from the other LLC
        station."
        ::={ telProdNpMonInterfLLCListSessEntry 10 }

    telProdNpMonInterfLLCListSessT2 OBJECT-TYPE
        SYNTAX  INTEGER
        ACCESS  read-only
        STATUS  mandatory
        DESCRIPTION
        "Time delay the LLC uses before sending an ACK for a received I-frame."
        ::={ telProdNpMonInterfLLCListSessEntry 11 }

    telProdNpMonInterfLLCListSessTi OBJECT-TYPE
        SYNTAX  INTEGER
        ACCESS  read-only
        STATUS  mandatory
        DESCRIPTION
        "Time the LLC waits during inactivity before issuing an RR."
        ::={ telProdNpMonInterfLLCListSessEntry 12 }

    telProdNpMonInterfLLCListSessN1 OBJECT-TYPE
        SYNTAX  INTEGER
        ACCESS  read-only
        STATUS  mandatory
        DESCRIPTION
        "Maximum size of the data field (in bytes) of a frame. Default is
        the size of the interface."
        ::={ telProdNpMonInterfLLCListSessEntry 13 }

    telProdNpMonInterfLLCListSessN2 OBJECT-TYPE
        SYNTAX  INTEGER
        ACCESS  read-only
        STATUS  mandatory
        DESCRIPTION
        "Number of times the LLC transmits an RR without receiving an
        acknowledgment."
        ::={ telProdNpMonInterfLLCListSessEntry 14 }

    telProdNpMonInterfLLCListSessN3 OBJECT-TYPE
        SYNTAX  INTEGER
        ACCESS  read-only
        STATUS  mandatory
        DESCRIPTION
        "Value that is used with T2 timer to reduce acknowledgement
        traffic for received I-frames."
        ::={ telProdNpMonInterfLLCListSessEntry 15 }

    telProdNpMonInterfLLCListSessTw OBJECT-TYPE
        SYNTAX  INTEGER
        ACCESS  read-only
        STATUS  mandatory
        DESCRIPTION
        "Number of I-frames that can be sent before receiving an RR."
        ::={ telProdNpMonInterfLLCListSessEntry 16 }

    telProdNpMonInterfLLCListSessWw OBJECT-TYPE
        SYNTAX  INTEGER
        ACCESS  read-only
        STATUS  mandatory
        DESCRIPTION
        "Number of I-frames that are sent before receiving an RR. This can be
        less than Tw during the dynamic window algorithm."
        ::={ telProdNpMonInterfLLCListSessEntry 17 }

    telProdNpMonInterfLLCListSessNw OBJECT-TYPE
        SYNTAX  INTEGER
        ACCESS  read-only
        STATUS  mandatory
        DESCRIPTION
        "Number of acknowledgements to initialize Ww."
        ::={ telProdNpMonInterfLLCListSessEntry 18 }

    telProdNpMonInterfLLCListSessVs OBJECT-TYPE
        SYNTAX  INTEGER
        ACCESS  read-only
        STATUS  mandatory
        DESCRIPTION
        "Send state variable (Ns value for the next I-frame to be transferred)."
        ::={ telProdNpMonInterfLLCListSessEntry 19 }

    telProdNpMonInterfLLCListSessVr OBJECT-TYPE
        SYNTAX  INTEGER
        ACCESS  read-only
        STATUS  mandatory
        DESCRIPTION
        "Receive state variable (next in-sequence Ns to be accepted)."
        ::={ telProdNpMonInterfLLCListSessEntry 20 }

    telProdNpMonInterfLLCListSessVa OBJECT-TYPE
        SYNTAX  INTEGER
        ACCESS  read-only
        STATUS  mandatory
        DESCRIPTION
        "Acknowledged state variable (last valid Nr received)."
        ::={ telProdNpMonInterfLLCListSessEntry 21 }

    telProdNpMonInterfLLCListSessACKpend OBJECT-TYPE
        SYNTAX  INTEGER
        ACCESS  read-only
        STATUS  mandatory
        DESCRIPTION
        "Transmited I-frames waiting for acknowledgment."
        ::={ telProdNpMonInterfLLCListSessEntry 22 }

    telProdNpMonInterfLLCListSessTXpend OBJECT-TYPE
        SYNTAX  INTEGER
        ACCESS  read-only
        STATUS  mandatory
        DESCRIPTION
        "Number of frames waiting to be transmited."
        ::={ telProdNpMonInterfLLCListSessEntry 23 }

    telProdNpMonInterfLLCListSessLocalBusy OBJECT-TYPE
        SYNTAX  INTEGER{
            no(0),
            yes(1)
            }
        ACCESS  read-only
        STATUS  mandatory
        DESCRIPTION
        "The router local LLC connection is sending RNRs. YES(1), NO(0)."
        ::={ telProdNpMonInterfLLCListSessEntry 24 }

    telProdNpMonInterfLLCListSessRemoteBusy OBJECT-TYPE
        SYNTAX  INTEGER{
            no(0),
            yes(1)
            }
        ACCESS  read-only
        STATUS  mandatory
        DESCRIPTION
        "The router remote LLC is receiving RNRs. YES(1), NO(0)."
        ::={ telProdNpMonInterfLLCListSessEntry 25 }

    telProdNpMonInterfLLCListSessRetryCount OBJECT-TYPE
        SYNTAX  INTEGER
        ACCESS  read-only
        STATUS  mandatory
        DESCRIPTION
        "Current value of the retry of the counter in the LLC protocol."
        ::={ telProdNpMonInterfLLCListSessEntry 26 }

    telProdNpMonInterfLLCListSessApOuFlStop OBJECT-TYPE
        SYNTAX  INTEGER{
            no(0),
            yes(1)
            }
        ACCESS  read-only
        STATUS  mandatory
        DESCRIPTION
        "LLC has told the application to stop giving it outgoing data frames.
        YES(1), NO(0)."
        ::={  telProdNpMonInterfLLCListSessEntry 27 }

    telProdNpMonInterfLLCListSessSeProRunning OBJECT-TYPE
        SYNTAX  INTEGER{
            no(0),
            yes(1)
            }
        ACCESS  read-only
        STATUS  mandatory
        DESCRIPTION
        "This process runs concurrently with all other frame actions and takes
        I-frames in the transmit queue and sends them. YES(1), NO(0)."
        ::={ telProdNpMonInterfLLCListSessEntry 28 }

    telProdNpMonInterfLLCListSessXmtI OBJECT-TYPE
        SYNTAX  Counter
        ACCESS  read-only
        STATUS  mandatory
        DESCRIPTION
        "Frames type I transmitted."
        ::={ telProdNpMonInterfLLCListSessEntry 29 }

    telProdNpMonInterfLLCListSessRcvdI OBJECT-TYPE
        SYNTAX  Counter
        ACCESS  read-only
        STATUS  mandatory
        DESCRIPTION
        "Frames type I received."
        ::={  telProdNpMonInterfLLCListSessEntry 30 }

    telProdNpMonInterfLLCListSessXmtRR OBJECT-TYPE
        SYNTAX  Counter
        ACCESS  read-only
        STATUS  mandatory
        DESCRIPTION
        "Frames type RR transmitted."
        ::={ telProdNpMonInterfLLCListSessEntry 31 }

    telProdNpMonInterfLLCListSessRcvdRR OBJECT-TYPE
        SYNTAX  Counter
        ACCESS  read-only
        STATUS  mandatory
        DESCRIPTION
        "Frames type RR received."
        ::={ telProdNpMonInterfLLCListSessEntry 32 }

    telProdNpMonInterfLLCListSessXmtRNR OBJECT-TYPE
        SYNTAX  Counter
        ACCESS  read-only
        STATUS  mandatory
        DESCRIPTION
        "Frames type RNR transmitted."
        ::={ telProdNpMonInterfLLCListSessEntry 33 }

    telProdNpMonInterfLLCListSessRcvdRNR OBJECT-TYPE
        SYNTAX  Counter
        ACCESS  read-only
        STATUS  mandatory
        DESCRIPTION
        "Frames type RNR received."
        ::={ telProdNpMonInterfLLCListSessEntry 34 }

    telProdNpMonInterfLLCListSessXmtREJ OBJECT-TYPE
        SYNTAX  Counter
        ACCESS  read-only
        STATUS  mandatory
        DESCRIPTION
        "Frames type REJ transmitted."
        ::={ telProdNpMonInterfLLCListSessEntry 35 }

    telProdNpMonInterfLLCListSessRcvdREJ OBJECT-TYPE
        SYNTAX  Counter
        ACCESS  read-only
        STATUS  mandatory
        DESCRIPTION
        "Frames type REJ received."
        ::={ telProdNpMonInterfLLCListSessEntry 36 }

    telProdNpMonInterfLLCListSessDiscarded OBJECT-TYPE
        SYNTAX  Counter
        ACCESS  read-only
        STATUS  mandatory
        DESCRIPTION
        "I-frames discarded by the LLC, usually because the sequence number is
        wrong."
        ::={ telProdNpMonInterfLLCListSessEntry 37 }

    telProdNpMonInterfLLCListSessRefused OBJECT-TYPE
        SYNTAX  Counter
        ACCESS  read-only
        STATUS  mandatory
        DESCRIPTION
        "I-frames discarded by the software above the LLC.For example, LNM
        (LAN Network Manager) and DLSw (Data Link Switching)."
        ::={ telProdNpMonInterfLLCListSessEntry 38 }

    -- Tabla de set de parametros para protocolo LLC

    telProdNpMonInterfLLCSetTable OBJECT-TYPE
        SYNTAX  SEQUENCE OF TelProdNpMonInterfLLCSetEntry
        ACCESS  not-accessible
        STATUS  mandatory
        DESCRIPTION
        "Dynamically configures the LLC parameters on a current LLC session.
        Changes that you make to the parameters are effective for the life
        of session."
        ::={ telProdNpMonInterfLLC 5 }

    telProdNpMonInterfLLCSetEntry OBJECT-TYPE
        SYNTAX  TelProdNpMonInterfLLCSetEntry
        ACCESS  not-accessible
        STATUS  mandatory
        DESCRIPTION
        ""
        INDEX { telProdNpMonInterfLLCSetInd}
        ::={ telProdNpMonInterfLLCSetTable 1 }

    TelProdNpMonInterfLLCSetEntry ::=
        SEQUENCE {
            telProdNpMonInterfLLCSetInd
                INTEGER,
            telProdNpMonInterfLLCSetIdSess
                DisplayString,
            telProdNpMonInterfLLCSetN2
                INTEGER,
            telProdNpMonInterfLLCSetN3
                INTEGER,
            telProdNpMonInterfLLCSetNw
                INTEGER,
            telProdNpMonInterfLLCSetT1
                INTEGER,
            telProdNpMonInterfLLCSetT2
                INTEGER,
            telProdNpMonInterfLLCSetTi
                INTEGER,
            telProdNpMonInterfLLCSetTw
                INTEGER
            }

    telProdNpMonInterfLLCSetInd OBJECT-TYPE
        SYNTAX  INTEGER
        ACCESS  read-only
        STATUS  mandatory
        DESCRIPTION
        "Entry number. It is the index."
        ::={ telProdNpMonInterfLLCSetEntry 1 }

    telProdNpMonInterfLLCSetIdSess OBJECT-TYPE
        SYNTAX  DisplayString(SIZE(0..10))
        ACCESS  read-only
        STATUS  mandatory
        DESCRIPTION
        "Session identifier."
        ::={ telProdNpMonInterfLLCSetEntry 2 }

    telProdNpMonInterfLLCSetN2 OBJECT-TYPE
        SYNTAX  INTEGER(1..127)
        ACCESS  read-write
        STATUS  mandatory
        DESCRIPTION
        "The maximum number of times the LLC protocol transmits an RR without
        receiving an acknowledgment when the inactivity timer expires. The range
        is 1 to 127. Default is 8."
        DEFVAL { 8 }
        ::={ telProdNpMonInterfLLCSetEntry 3 }

    telProdNpMonInterfLLCSetN3 OBJECT-TYPE
        SYNTAX  INTEGER(1..255)
        ACCESS  read-write
        STATUS  mandatory
        DESCRIPTION
        "This value is used with the T2 timer to reduce acknowledgment traffic
        for received I-frames. Set this counter to a specified value. Each time
        an I-frame is received, this value is decremented. When this counter
        reaches 0, or the T2 timer expires, an acknowledgment is sent. The
        range is 1 to 255. Default is 1."
        DEFVAL { 1 }
        ::={ telProdNpMonInterfLLCSetEntry 4 }

    telProdNpMonInterfLLCSetNw OBJECT-TYPE
        SYNTAX  INTEGER(1..127)
        ACCESS  read-write
        STATUS  mandatory
        DESCRIPTION
        "When the ability to send I-frames is not working, the LLC protocol goes
        into a mode where the working window (Ww) is set back to 1, and is
        then slowly increased back to its normal size (Tw). This is known as the
        dynamic window algorithm. This value is the number of I-frames that the
        LLC must receive before incrementing Ww by 1. The  range is 1 to 127.
        Default is 1."
        DEFVAL { 1 }
        ::={ telProdNpMonInterfLLCSetEntry 5 }

    telProdNpMonInterfLLCSetT1 OBJECT-TYPE
        SYNTAX  INTEGER(1..256)
        ACCESS  read-write
        STATUS  mandatory
        DESCRIPTION
        "This timer expires when the LLC fails to receive a required
        acknowledgment or response from the other LLC station. When this timer
        expires, an RR is sent with the poll bit set and T1 is started again.
        If the LLC receives no response after the configured maximum number
        of retries (N2), the link underneath is declared inoperative. The range
        is 1 to 256.  Default is 1."
        DEFVAL { 1 }
        ::={ telProdNpMonInterfLLCSetEntry 6 }

    telProdNpMonInterfLLCSetT2 OBJECT-TYPE
        SYNTAX  INTEGER(1..2560)
        ACCESS  read-write
        STATUS  mandatory
        DESCRIPTION
        "This timer is used to delay sending of an acknowledgment for a
        received I-format frame. This timer is started when an I-frame is
        received and reset when an acknowledgment is sent. If this timer
        expires, LLC2 sends an acknowledgment as soon as possible. Set
        this value so that it is less than that of T1.  This insures that the
        remote LLC2 peer receives the delayed acknowledgment before the
        T1 timer expires. The range is 1 to 2,560. Default is 1 (100 ms)."
        DEFVAL { 1 }
        ::={ telProdNpMonInterfLLCSetEntry 7 }

    telProdNpMonInterfLLCSetTi OBJECT-TYPE
        SYNTAX  INTEGER(1..256)
        ACCESS  read-write
        STATUS  mandatory
        DESCRIPTION
        "This timer expires when the LLC does not receive a frame for a
        specified time period.  When this timer expires the LLC transmits
        an RR until the other LLC responds or the N2 timer expires. The
        range is 1 to 256. Default is 30 seconds."
        DEFVAL { 30 }
        ::={ telProdNpMonInterfLLCSetEntry 8 }

    telProdNpMonInterfLLCSetTw OBJECT-TYPE
        SYNTAX  INTEGER(1..127)
        ACCESS  read-write
        STATUS  mandatory
        DESCRIPTION
        "Sets the maximum number of I-frames that can be sent before
        receiving an RR. Assuming that the other end of the LLC session
        can actually receive this many consecutive I-frames, and the router
        has enough heap memory to keep copies of these frames until an
        acknowledgment is received, increasing this value may increase the
        throughput. The range is 1 to 127. Default is 2."
        DEFVAL { 2 }
        ::={ telProdNpMonInterfLLCSetEntry 9 }

END
