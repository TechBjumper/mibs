-- file automatically created


TELDAT-TRAP-SCAD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


scadTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SCAD event subsystem."
    REVISION "201401200930Z"
    DESCRIPTION "Initial implementation"
        ::= { telEventTraps 178 }


scadEventsGroup	OBJECT IDENTIFIER	::= { scadTrapsMIB 1 }

scadNotifications	OBJECT IDENTIFIER	::= { scadTrapsMIB 2 }
scadNotificationsPrefix	OBJECT IDENTIFIER	::= { scadNotifications 0 }

scadEventObjects1 OBJECT-IDENTITY
    STATUS current
    DESCRIPTION
        "Event SCAD.1
        Data has been received from Serial Terminal."
    ::= { scadEventsGroup 1 }

scad1-bytes-number OBJECT-TYPE
    SYNTAX Integer32
    MAX-ACCESS accessible-for-notify
    STATUS current
    DESCRIPTION
        "Parameter 'bytes-number' in event SCAD.1"
    ::= { scadEventObjects1 1 }

scad1-interface OBJECT-TYPE
    SYNTAX DisplayString
    MAX-ACCESS accessible-for-notify
    STATUS current
    DESCRIPTION
        "Parameter 'interface' in event SCAD.1"
    ::= { scadEventObjects1 2 }

scadEventObjects2 OBJECT-IDENTITY
    STATUS current
    DESCRIPTION
        "Event SCAD.2
        One OK Message has been received from Serial Terminal."
    ::= { scadEventsGroup 2 }

scad2-coment OBJECT-TYPE
    SYNTAX DisplayString
    MAX-ACCESS accessible-for-notify
    STATUS current
    DESCRIPTION
        "Parameter 'coment' in event SCAD.2"
    ::= { scadEventObjects2 1 }

scad2-serrial-address OBJECT-TYPE
    SYNTAX Integer32
    MAX-ACCESS accessible-for-notify
    STATUS current
    DESCRIPTION
        "Parameter 'serrial-address' in event SCAD.2"
    ::= { scadEventObjects2 2 }

scad2-bytes-number OBJECT-TYPE
    SYNTAX Integer32
    MAX-ACCESS accessible-for-notify
    STATUS current
    DESCRIPTION
        "Parameter 'bytes-number' in event SCAD.2"
    ::= { scadEventObjects2 3 }

scad2-interface OBJECT-TYPE
    SYNTAX DisplayString
    MAX-ACCESS accessible-for-notify
    STATUS current
    DESCRIPTION
        "Parameter 'interface' in event SCAD.2"
    ::= { scadEventObjects2 4 }

scad2-state OBJECT-TYPE
    SYNTAX Integer32
    MAX-ACCESS accessible-for-notify
    STATUS current
    DESCRIPTION
        "Parameter 'state' in event SCAD.2"
    ::= { scadEventObjects2 5 }

scadEventObjects3 OBJECT-IDENTITY
    STATUS current
    DESCRIPTION
        "Event SCAD.3
        A Message with bad address has been received from Serial Terminal."
    ::= { scadEventsGroup 3 }

scad3-bad-addr OBJECT-TYPE
    SYNTAX Integer32
    MAX-ACCESS accessible-for-notify
    STATUS current
    DESCRIPTION
        "Parameter 'bad-addr' in event SCAD.3"
    ::= { scadEventObjects3 1 }

scad3-interface OBJECT-TYPE
    SYNTAX DisplayString
    MAX-ACCESS accessible-for-notify
    STATUS current
    DESCRIPTION
        "Parameter 'interface' in event SCAD.3"
    ::= { scadEventObjects3 2 }

scadEventObjects4 OBJECT-IDENTITY
    STATUS current
    DESCRIPTION
        "Event SCAD.4
        One Bad Message has been received from Serial Terminal."
    ::= { scadEventsGroup 4 }

scad4-cause OBJECT-TYPE
    SYNTAX DisplayString
    MAX-ACCESS accessible-for-notify
    STATUS current
    DESCRIPTION
        "Parameter 'cause' in event SCAD.4"
    ::= { scadEventObjects4 1 }

scad4-interface OBJECT-TYPE
    SYNTAX DisplayString
    MAX-ACCESS accessible-for-notify
    STATUS current
    DESCRIPTION
        "Parameter 'interface' in event SCAD.4"
    ::= { scadEventObjects4 2 }

scad4-state OBJECT-TYPE
    SYNTAX Integer32
    MAX-ACCESS accessible-for-notify
    STATUS current
    DESCRIPTION
        "Parameter 'state' in event SCAD.4"
    ::= { scadEventObjects4 3 }

scadEventObjects5 OBJECT-IDENTITY
    STATUS current
    DESCRIPTION
        "Event SCAD.5
        A message with LRC/CRC error has been received from Serial Terminal."
    ::= { scadEventsGroup 5 }

scad5-interface OBJECT-TYPE
    SYNTAX DisplayString
    MAX-ACCESS accessible-for-notify
    STATUS current
    DESCRIPTION
        "Parameter 'interface' in event SCAD.5"
    ::= { scadEventObjects5 1 }

scad5-state OBJECT-TYPE
    SYNTAX Integer32
    MAX-ACCESS accessible-for-notify
    STATUS current
    DESCRIPTION
        "Parameter 'state' in event SCAD.5"
    ::= { scadEventObjects5 2 }

scadEventObjects6 OBJECT-IDENTITY
    STATUS current
    DESCRIPTION
        "Event SCAD.6
        A message with error has been received from Remote."
    ::= { scadEventsGroup 6 }

scad6-error-type OBJECT-TYPE
    SYNTAX DisplayString
    MAX-ACCESS accessible-for-notify
    STATUS current
    DESCRIPTION
        "Parameter 'error-type' in event SCAD.6"
    ::= { scadEventObjects6 1 }

scad6-interface OBJECT-TYPE
    SYNTAX DisplayString
    MAX-ACCESS accessible-for-notify
    STATUS current
    DESCRIPTION
        "Parameter 'interface' in event SCAD.6"
    ::= { scadEventObjects6 2 }

scad6-state OBJECT-TYPE
    SYNTAX Integer32
    MAX-ACCESS accessible-for-notify
    STATUS current
    DESCRIPTION
        "Parameter 'state' in event SCAD.6"
    ::= { scadEventObjects6 3 }

scadEventObjects7 OBJECT-IDENTITY
    STATUS current
    DESCRIPTION
        "Event SCAD.7
        Addres received from Serial Terminal is not included in configuration
        registers list."
    ::= { scadEventsGroup 7 }

scad7-serial-address OBJECT-TYPE
    SYNTAX Integer32
    MAX-ACCESS accessible-for-notify
    STATUS current
    DESCRIPTION
        "Parameter 'serial-address' in event SCAD.7"
    ::= { scadEventObjects7 1 }

scad7-interface OBJECT-TYPE
    SYNTAX DisplayString
    MAX-ACCESS accessible-for-notify
    STATUS current
    DESCRIPTION
        "Parameter 'interface' in event SCAD.7"
    ::= { scadEventObjects7 2 }

scadEventObjects8 OBJECT-IDENTITY
    STATUS current
    DESCRIPTION
        "Event SCAD.8
        It's trying the connection against remote IP and P port."
    ::= { scadEventsGroup 8 }

scad8-serial-address OBJECT-TYPE
    SYNTAX Integer32
    MAX-ACCESS accessible-for-notify
    STATUS current
    DESCRIPTION
        "Parameter 'serial-address' in event SCAD.8"
    ::= { scadEventObjects8 1 }

scad8-rtu-ip-address OBJECT-TYPE
    SYNTAX IpAddress
    MAX-ACCESS accessible-for-notify
    STATUS current
    DESCRIPTION
        "Parameter 'rtu-ip-address' in event SCAD.8"
    ::= { scadEventObjects8 2 }

scad8-port OBJECT-TYPE
    SYNTAX Integer32
    MAX-ACCESS accessible-for-notify
    STATUS current
    DESCRIPTION
        "Parameter 'port' in event SCAD.8"
    ::= { scadEventObjects8 3 }

scad8-interface OBJECT-TYPE
    SYNTAX DisplayString
    MAX-ACCESS accessible-for-notify
    STATUS current
    DESCRIPTION
        "Parameter 'interface' in event SCAD.8"
    ::= { scadEventObjects8 4 }

scadEventObjects9 OBJECT-IDENTITY
    STATUS current
    DESCRIPTION
        "Event SCAD.9
        The Transfer has been completed successfully."
    ::= { scadEventsGroup 9 }

scad9-interface OBJECT-TYPE
    SYNTAX DisplayString
    MAX-ACCESS accessible-for-notify
    STATUS current
    DESCRIPTION
        "Parameter 'interface' in event SCAD.9"
    ::= { scadEventObjects9 1 }

scadEventObjects10 OBJECT-IDENTITY
    STATUS current
    DESCRIPTION
        "Event SCAD.10
        Trying to send message to Remote end."
    ::= { scadEventsGroup 10 }

scad10-bytes OBJECT-TYPE
    SYNTAX Integer32
    MAX-ACCESS accessible-for-notify
    STATUS current
    DESCRIPTION
        "Parameter 'bytes' in event SCAD.10"
    ::= { scadEventObjects10 1 }

scad10-interface OBJECT-TYPE
    SYNTAX DisplayString
    MAX-ACCESS accessible-for-notify
    STATUS current
    DESCRIPTION
        "Parameter 'interface' in event SCAD.10"
    ::= { scadEventObjects10 2 }

scadEventObjects11 OBJECT-IDENTITY
    STATUS current
    DESCRIPTION
        "Event SCAD.11
        A message from Remote end has been received."
    ::= { scadEventsGroup 11 }

scad11-message-type OBJECT-TYPE
    SYNTAX Integer32
    MAX-ACCESS accessible-for-notify
    STATUS current
    DESCRIPTION
        "Parameter 'message-type' in event SCAD.11"
    ::= { scadEventObjects11 1 }

scad11-bytes OBJECT-TYPE
    SYNTAX Integer32
    MAX-ACCESS accessible-for-notify
    STATUS current
    DESCRIPTION
        "Parameter 'bytes' in event SCAD.11"
    ::= { scadEventObjects11 2 }

scad11-interface OBJECT-TYPE
    SYNTAX DisplayString
    MAX-ACCESS accessible-for-notify
    STATUS current
    DESCRIPTION
        "Parameter 'interface' in event SCAD.11"
    ::= { scadEventObjects11 3 }

scad11-state OBJECT-TYPE
    SYNTAX Integer32
    MAX-ACCESS accessible-for-notify
    STATUS current
    DESCRIPTION
        "Parameter 'state' in event SCAD.11"
    ::= { scadEventObjects11 4 }

scadEventObjects12 OBJECT-IDENTITY
    STATUS current
    DESCRIPTION
        "Event SCAD.12
        A TCP Packet has been received."
    ::= { scadEventsGroup 12 }

scad12-message-type OBJECT-TYPE
    SYNTAX DisplayString
    MAX-ACCESS accessible-for-notify
    STATUS current
    DESCRIPTION
        "Parameter 'message-type' in event SCAD.12"
    ::= { scadEventObjects12 1 }

scad12-bytes OBJECT-TYPE
    SYNTAX Integer32
    MAX-ACCESS accessible-for-notify
    STATUS current
    DESCRIPTION
        "Parameter 'bytes' in event SCAD.12"
    ::= { scadEventObjects12 2 }

scad12-foreign-host OBJECT-TYPE
    SYNTAX IpAddress
    MAX-ACCESS accessible-for-notify
    STATUS current
    DESCRIPTION
        "Parameter 'foreign-host' in event SCAD.12"
    ::= { scadEventObjects12 3 }

scad12-remote-port OBJECT-TYPE
    SYNTAX Integer32
    MAX-ACCESS accessible-for-notify
    STATUS current
    DESCRIPTION
        "Parameter 'remote-port' in event SCAD.12"
    ::= { scadEventObjects12 4 }

scadEventObjects13 OBJECT-IDENTITY
    STATUS current
    DESCRIPTION
        "Event SCAD.13
        The TCP session has been closed."
    ::= { scadEventsGroup 13 }

scad13-foreign-host OBJECT-TYPE
    SYNTAX IpAddress
    MAX-ACCESS accessible-for-notify
    STATUS current
    DESCRIPTION
        "Parameter 'foreign-host' in event SCAD.13"
    ::= { scadEventObjects13 1 }

scad13-remote-port OBJECT-TYPE
    SYNTAX Integer32
    MAX-ACCESS accessible-for-notify
    STATUS current
    DESCRIPTION
        "Parameter 'remote-port' in event SCAD.13"
    ::= { scadEventObjects13 2 }

scadEventObjects14 OBJECT-IDENTITY
    STATUS current
    DESCRIPTION
        "Event SCAD.14
        The TCP session has been closed by the Remote end."
    ::= { scadEventsGroup 14 }

scad14-foreign-host OBJECT-TYPE
    SYNTAX IpAddress
    MAX-ACCESS accessible-for-notify
    STATUS current
    DESCRIPTION
        "Parameter 'foreign-host' in event SCAD.14"
    ::= { scadEventObjects14 1 }

scad14-remote-port OBJECT-TYPE
    SYNTAX Integer32
    MAX-ACCESS accessible-for-notify
    STATUS current
    DESCRIPTION
        "Parameter 'remote-port' in event SCAD.14"
    ::= { scadEventObjects14 2 }

scadEventObjects15 OBJECT-IDENTITY
    STATUS current
    DESCRIPTION
        "Event SCAD.15
        The TCP session has been opened by the Remote end."
    ::= { scadEventsGroup 15 }

scad15-remote-ip OBJECT-TYPE
    SYNTAX IpAddress
    MAX-ACCESS accessible-for-notify
    STATUS current
    DESCRIPTION
        "Parameter 'remote-ip' in event SCAD.15"
    ::= { scadEventObjects15 1 }

scad15-remote-port OBJECT-TYPE
    SYNTAX Integer32
    MAX-ACCESS accessible-for-notify
    STATUS current
    DESCRIPTION
        "Parameter 'remote-port' in event SCAD.15"
    ::= { scadEventObjects15 2 }

scadEventObjects16 OBJECT-IDENTITY
    STATUS current
    DESCRIPTION
        "Event SCAD.16
        A Message has been transmitted to Serial Terminal."
    ::= { scadEventsGroup 16 }

scad16-address OBJECT-TYPE
    SYNTAX Integer32
    MAX-ACCESS accessible-for-notify
    STATUS current
    DESCRIPTION
        "Parameter 'address' in event SCAD.16"
    ::= { scadEventObjects16 1 }

scad16-bytes OBJECT-TYPE
    SYNTAX Integer32
    MAX-ACCESS accessible-for-notify
    STATUS current
    DESCRIPTION
        "Parameter 'bytes' in event SCAD.16"
    ::= { scadEventObjects16 2 }

scad16-interface OBJECT-TYPE
    SYNTAX DisplayString
    MAX-ACCESS accessible-for-notify
    STATUS current
    DESCRIPTION
        "Parameter 'interface' in event SCAD.16"
    ::= { scadEventObjects16 3 }

scad16-state OBJECT-TYPE
    SYNTAX Integer32
    MAX-ACCESS accessible-for-notify
    STATUS current
    DESCRIPTION
        "Parameter 'state' in event SCAD.16"
    ::= { scadEventObjects16 4 }

scadEventObjects17 OBJECT-IDENTITY
    STATUS current
    DESCRIPTION
        "Event SCAD.17
        A change ON/OFF has been detected in Serial Control Signal Input."
    ::= { scadEventsGroup 17 }

scad17-message-type OBJECT-TYPE
    SYNTAX DisplayString
    MAX-ACCESS accessible-for-notify
    STATUS current
    DESCRIPTION
        "Parameter 'message-type' in event SCAD.17"
    ::= { scadEventObjects17 1 }

scad17-interface OBJECT-TYPE
    SYNTAX DisplayString
    MAX-ACCESS accessible-for-notify
    STATUS current
    DESCRIPTION
        "Parameter 'interface' in event SCAD.17"
    ::= { scadEventObjects17 2 }

scad17-state OBJECT-TYPE
    SYNTAX Integer32
    MAX-ACCESS accessible-for-notify
    STATUS current
    DESCRIPTION
        "Parameter 'state' in event SCAD.17"
    ::= { scadEventObjects17 3 }

scadEventObjects18 OBJECT-IDENTITY
    STATUS current
    DESCRIPTION
        "Event SCAD.18
        Timeout has occur waiting data."
    ::= { scadEventsGroup 18 }

scad18-site OBJECT-TYPE
    SYNTAX DisplayString
    MAX-ACCESS accessible-for-notify
    STATUS current
    DESCRIPTION
        "Parameter 'site' in event SCAD.18"
    ::= { scadEventObjects18 1 }

scad18-interface OBJECT-TYPE
    SYNTAX DisplayString
    MAX-ACCESS accessible-for-notify
    STATUS current
    DESCRIPTION
        "Parameter 'interface' in event SCAD.18"
    ::= { scadEventObjects18 2 }

scad18-state OBJECT-TYPE
    SYNTAX Integer32
    MAX-ACCESS accessible-for-notify
    STATUS current
    DESCRIPTION
        "Parameter 'state' in event SCAD.18"
    ::= { scadEventObjects18 3 }

scadEventObjects19 OBJECT-IDENTITY
    STATUS current
    DESCRIPTION
        "Event SCAD.19
        A packet was lost, due TCP Tx overrun error."
    ::= { scadEventsGroup 19 }

scad19-interface OBJECT-TYPE
    SYNTAX DisplayString
    MAX-ACCESS accessible-for-notify
    STATUS current
    DESCRIPTION
        "Parameter 'interface' in event SCAD.19"
    ::= { scadEventObjects19 1 }

scad19-state OBJECT-TYPE
    SYNTAX Integer32
    MAX-ACCESS accessible-for-notify
    STATUS current
    DESCRIPTION
        "Parameter 'state' in event SCAD.19"
    ::= { scadEventObjects19 2 }

scadEventObjects20 OBJECT-IDENTITY
    STATUS current
    DESCRIPTION
        "Event SCAD.20
        A packet was lost, due TCP is closed."
    ::= { scadEventsGroup 20 }

scad20-interface OBJECT-TYPE
    SYNTAX DisplayString
    MAX-ACCESS accessible-for-notify
    STATUS current
    DESCRIPTION
        "Parameter 'interface' in event SCAD.20"
    ::= { scadEventObjects20 1 }

scad20-state OBJECT-TYPE
    SYNTAX Integer32
    MAX-ACCESS accessible-for-notify
    STATUS current
    DESCRIPTION
        "Parameter 'state' in event SCAD.20"
    ::= { scadEventObjects20 2 }

scadEventObjects21 OBJECT-IDENTITY
    STATUS current
    DESCRIPTION
        "Event SCAD.21
        The transfer has been wrong against specified NA and IP addr."
    ::= { scadEventsGroup 21 }

scad21-na OBJECT-TYPE
    SYNTAX Integer32
    MAX-ACCESS accessible-for-notify
    STATUS current
    DESCRIPTION
        "Parameter 'na' in event SCAD.21"
    ::= { scadEventObjects21 1 }

scad21-ip-host-address OBJECT-TYPE
    SYNTAX IpAddress
    MAX-ACCESS accessible-for-notify
    STATUS current
    DESCRIPTION
        "Parameter 'ip-host-address' in event SCAD.21"
    ::= { scadEventObjects21 2 }

scad21-cause OBJECT-TYPE
    SYNTAX Integer32
    MAX-ACCESS accessible-for-notify
    STATUS current
    DESCRIPTION
        "Parameter 'cause' in event SCAD.21"
    ::= { scadEventObjects21 3 }

scad21-interface OBJECT-TYPE
    SYNTAX DisplayString
    MAX-ACCESS accessible-for-notify
    STATUS current
    DESCRIPTION
        "Parameter 'interface' in event SCAD.21"
    ::= { scadEventObjects21 4 }

scadEventObjects22 OBJECT-IDENTITY
    STATUS current
    DESCRIPTION
        "Event SCAD.22
        TCP generic event was occurred."
    ::= { scadEventsGroup 22 }

scad22-event OBJECT-TYPE
    SYNTAX DisplayString
    MAX-ACCESS accessible-for-notify
    STATUS current
    DESCRIPTION
        "Parameter 'event' in event SCAD.22"
    ::= { scadEventObjects22 1 }

scad22-ip OBJECT-TYPE
    SYNTAX IpAddress
    MAX-ACCESS accessible-for-notify
    STATUS current
    DESCRIPTION
        "Parameter 'ip' in event SCAD.22"
    ::= { scadEventObjects22 2 }

scad22-port OBJECT-TYPE
    SYNTAX Integer32
    MAX-ACCESS accessible-for-notify
    STATUS current
    DESCRIPTION
        "Parameter 'port' in event SCAD.22"
    ::= { scadEventObjects22 3 }

scadEventObjects23 OBJECT-IDENTITY
    STATUS current
    DESCRIPTION
        "Event SCAD.23
        A change ON/OFF has been make in Serial Control Signal Output."
    ::= { scadEventsGroup 23 }

scad23-message-type OBJECT-TYPE
    SYNTAX DisplayString
    MAX-ACCESS accessible-for-notify
    STATUS current
    DESCRIPTION
        "Parameter 'message-type' in event SCAD.23"
    ::= { scadEventObjects23 1 }

scad23-interface OBJECT-TYPE
    SYNTAX DisplayString
    MAX-ACCESS accessible-for-notify
    STATUS current
    DESCRIPTION
        "Parameter 'interface' in event SCAD.23"
    ::= { scadEventObjects23 2 }

scad23-state OBJECT-TYPE
    SYNTAX Integer32
    MAX-ACCESS accessible-for-notify
    STATUS current
    DESCRIPTION
        "Parameter 'state' in event SCAD.23"
    ::= { scadEventObjects23 3 }

scadEventObjects24 OBJECT-IDENTITY
    STATUS current
    DESCRIPTION
        "Event SCAD.24
        Data error from Serial Terminal has been received."
    ::= { scadEventsGroup 24 }

scad24-message-type OBJECT-TYPE
    SYNTAX DisplayString
    MAX-ACCESS accessible-for-notify
    STATUS current
    DESCRIPTION
        "Parameter 'message-type' in event SCAD.24"
    ::= { scadEventObjects24 1 }

scad24-interface OBJECT-TYPE
    SYNTAX DisplayString
    MAX-ACCESS accessible-for-notify
    STATUS current
    DESCRIPTION
        "Parameter 'interface' in event SCAD.24"
    ::= { scadEventObjects24 2 }

scad24-state OBJECT-TYPE
    SYNTAX Integer32
    MAX-ACCESS accessible-for-notify
    STATUS current
    DESCRIPTION
        "Parameter 'state' in event SCAD.24"
    ::= { scadEventObjects24 3 }

scadEventObjects25 OBJECT-IDENTITY
    STATUS current
    DESCRIPTION
        "Event SCAD.25
        TCP Listen has been closed, due max session number has been reached."
    ::= { scadEventsGroup 25 }

scad25-port OBJECT-TYPE
    SYNTAX Integer32
    MAX-ACCESS accessible-for-notify
    STATUS current
    DESCRIPTION
        "Parameter 'port' in event SCAD.25"
    ::= { scadEventObjects25 1 }

scadEventObjects26 OBJECT-IDENTITY
    STATUS current
    DESCRIPTION
        "Event SCAD.26
        An input TCP session has been rejet."
    ::= { scadEventsGroup 26 }

scad26-event OBJECT-TYPE
    SYNTAX DisplayString
    MAX-ACCESS accessible-for-notify
    STATUS current
    DESCRIPTION
        "Parameter 'event' in event SCAD.26"
    ::= { scadEventObjects26 1 }

scad26-ip OBJECT-TYPE
    SYNTAX IpAddress
    MAX-ACCESS accessible-for-notify
    STATUS current
    DESCRIPTION
        "Parameter 'ip' in event SCAD.26"
    ::= { scadEventObjects26 2 }

scad26-port OBJECT-TYPE
    SYNTAX Integer32
    MAX-ACCESS accessible-for-notify
    STATUS current
    DESCRIPTION
        "Parameter 'port' in event SCAD.26"
    ::= { scadEventObjects26 3 }

scadEventObjects27 OBJECT-IDENTITY
    STATUS current
    DESCRIPTION
        "Event SCAD.27
        Detailed Data send to serial interface."
    ::= { scadEventsGroup 27 }

scad27-interface OBJECT-TYPE
    SYNTAX DisplayString
    MAX-ACCESS accessible-for-notify
    STATUS current
    DESCRIPTION
        "Parameter 'interface' in event SCAD.27"
    ::= { scadEventObjects27 1 }

scad27-serial-address OBJECT-TYPE
    SYNTAX Integer32
    MAX-ACCESS accessible-for-notify
    STATUS current
    DESCRIPTION
        "Parameter 'serial-address' in event SCAD.27"
    ::= { scadEventObjects27 2 }

scad27-lenght OBJECT-TYPE
    SYNTAX Integer32
    MAX-ACCESS accessible-for-notify
    STATUS current
    DESCRIPTION
        "Parameter 'lenght' in event SCAD.27"
    ::= { scadEventObjects27 3 }

scad27-hex-data OBJECT-TYPE
    SYNTAX DisplayString
    MAX-ACCESS accessible-for-notify
    STATUS current
    DESCRIPTION
        "Parameter 'hex-data' in event SCAD.27"
    ::= { scadEventObjects27 4 }

scadEventObjects28 OBJECT-IDENTITY
    STATUS current
    DESCRIPTION
        "Event SCAD.28
        Detailed Data received from serial interface."
    ::= { scadEventsGroup 28 }

scad28-interface OBJECT-TYPE
    SYNTAX DisplayString
    MAX-ACCESS accessible-for-notify
    STATUS current
    DESCRIPTION
        "Parameter 'interface' in event SCAD.28"
    ::= { scadEventObjects28 1 }

scad28-serial-address OBJECT-TYPE
    SYNTAX Integer32
    MAX-ACCESS accessible-for-notify
    STATUS current
    DESCRIPTION
        "Parameter 'serial-address' in event SCAD.28"
    ::= { scadEventObjects28 2 }

scad28-lenght OBJECT-TYPE
    SYNTAX Integer32
    MAX-ACCESS accessible-for-notify
    STATUS current
    DESCRIPTION
        "Parameter 'lenght' in event SCAD.28"
    ::= { scadEventObjects28 3 }

scad28-hex-data OBJECT-TYPE
    SYNTAX DisplayString
    MAX-ACCESS accessible-for-notify
    STATUS current
    DESCRIPTION
        "Parameter 'hex-data' in event SCAD.28"
    ::= { scadEventObjects28 4 }

scadEventObjects29 OBJECT-IDENTITY
    STATUS current
    DESCRIPTION
        "Event SCAD.29
        Configured NSLA track has triggered."
    ::= { scadEventsGroup 29 }

scad29-state OBJECT-TYPE
    SYNTAX DisplayString
    MAX-ACCESS accessible-for-notify
    STATUS current
    DESCRIPTION
        "Parameter 'state' in event SCAD.29"
    ::= { scadEventObjects29 1 }

scad29-interface OBJECT-TYPE
    SYNTAX DisplayString
    MAX-ACCESS accessible-for-notify
    STATUS current
    DESCRIPTION
        "Parameter 'interface' in event SCAD.29"
    ::= { scadEventObjects29 2 }


scadNotification1 NOTIFICATION-TYPE
    OBJECTS { 
              scad1-bytes-number, 
              scad1-interface 
            }
    STATUS current
    DESCRIPTION
        "Notification of Event SCAD.1

        Message: 'Rx Data from Serial Terminal $1 bytes, interface $2'

        Parameters list:
              $1: scad1-bytes-number
              $2: scad1-interface

        Data has been received from Serial Terminal."
    ::= { scadNotificationsPrefix 1 }

scadNotification2 NOTIFICATION-TYPE
    OBJECTS { 
              scad2-coment, 
              scad2-serrial-address,
              scad2-bytes-number,
              scad2-interface,
              scad2-state 
            }
    STATUS current
    DESCRIPTION
        "Notification of Event SCAD.2

        Message: 'Rx Message$1 from Serial Terminal address $2, $3 bytes, interface $4 state $5'

        Parameters list:
              $1: scad2-coment
              $2: scad2-serrial-address
              $3: scad2-bytes-number
              $4: scad2-interface
              $5: scad2-state

        One OK Message has been received from Serial Terminal."
    ::= { scadNotificationsPrefix 2 }

scadNotification3 NOTIFICATION-TYPE
    OBJECTS { 
              scad3-bad-addr, 
              scad3-interface 
            }
    STATUS current
    DESCRIPTION
        "Notification of Event SCAD.3

        Message: 'Rx Address error from Serial Terminal $1 bytes, interface $2'

        Parameters list:
              $1: scad3-bad-addr
              $2: scad3-interface

        A Message with bad address has been received from Serial Terminal."
    ::= { scadNotificationsPrefix 3 }

scadNotification4 NOTIFICATION-TYPE
    OBJECTS { 
              scad4-cause, 
              scad4-interface,
              scad4-state 
            }
    STATUS current
    DESCRIPTION
        "Notification of Event SCAD.4

        Message: 'Rx Bad Message from Serial Terminal ($1), interface $2 state $3'

        Parameters list:
              $1: scad4-cause
              $2: scad4-interface
              $3: scad4-state

        One Bad Message has been received from Serial Terminal."
    ::= { scadNotificationsPrefix 4 }

scadNotification5 NOTIFICATION-TYPE
    OBJECTS { 
              scad5-interface, 
              scad5-state 
            }
    STATUS current
    DESCRIPTION
        "Notification of Event SCAD.5

        Message: 'A block with LRC/CRC error has been received from Serial Terminal, interface $1 state $2'

        Parameters list:
              $1: scad5-interface
              $2: scad5-state

        A message with LRC/CRC error has been received from Serial Terminal."
    ::= { scadNotificationsPrefix 5 }

scadNotification6 NOTIFICATION-TYPE
    OBJECTS { 
              scad6-error-type, 
              scad6-interface,
              scad6-state 
            }
    STATUS current
    DESCRIPTION
        "Notification of Event SCAD.6

        Message: 'A block with $1 error has been received from Serial Terminal, interface $2 state $3'

        Parameters list:
              $1: scad6-error-type
              $2: scad6-interface
              $3: scad6-state

        A message with error has been received from Remote."
    ::= { scadNotificationsPrefix 6 }

scadNotification7 NOTIFICATION-TYPE
    OBJECTS { 
              scad7-serial-address, 
              scad7-interface 
            }
    STATUS current
    DESCRIPTION
        "Notification of Event SCAD.7

        Message: 'Address $1 received from Serial Terminal is not included in configuration regiters. Interface $2'

        Parameters list:
              $1: scad7-serial-address
              $2: scad7-interface

        Addres received from Serial Terminal is not included in configuration
        registers list."
    ::= { scadNotificationsPrefix 7 }

scadNotification8 NOTIFICATION-TYPE
    OBJECTS { 
              scad8-serial-address, 
              scad8-rtu-ip-address,
              scad8-port,
              scad8-interface 
            }
    STATUS current
    DESCRIPTION
        "Notification of Event SCAD.8

        Message: 'Address $1 is trying the connection against IP $2 Host, Port $3, Interface $4'

        Parameters list:
              $1: scad8-serial-address
              $2: scad8-rtu-ip-address
              $3: scad8-port
              $4: scad8-interface

        It's trying the connection against remote IP and P port."
    ::= { scadNotificationsPrefix 8 }

scadNotification9 NOTIFICATION-TYPE
    OBJECTS { 
              scad9-interface 
            }
    STATUS current
    DESCRIPTION
        "Notification of Event SCAD.9

        Message: 'The Transfer has been completed successfully. Interface $1'

        Parameters list:
              $1: scad9-interface

        The Transfer has been completed successfully."
    ::= { scadNotificationsPrefix 9 }

scadNotification10 NOTIFICATION-TYPE
    OBJECTS { 
              scad10-bytes, 
              scad10-interface 
            }
    STATUS current
    DESCRIPTION
        "Notification of Event SCAD.10

        Message: 'Trying to send a message to Remote with $1 bytes. Interface $2'

        Parameters list:
              $1: scad10-bytes
              $2: scad10-interface

        Trying to send message to Remote end."
    ::= { scadNotificationsPrefix 10 }

scadNotification11 NOTIFICATION-TYPE
    OBJECTS { 
              scad11-message-type, 
              scad11-bytes,
              scad11-interface,
              scad11-state 
            }
    STATUS current
    DESCRIPTION
        "Notification of Event SCAD.11

        Message: 'A message from Remote of $1 type has been received, $2 bytes. Interface $3 state $4'

        Parameters list:
              $1: scad11-message-type
              $2: scad11-bytes
              $3: scad11-interface
              $4: scad11-state

        A message from Remote end has been received."
    ::= { scadNotificationsPrefix 11 }

scadNotification12 NOTIFICATION-TYPE
    OBJECTS { 
              scad12-message-type, 
              scad12-bytes,
              scad12-foreign-host,
              scad12-remote-port 
            }
    STATUS current
    DESCRIPTION
        "Notification of Event SCAD.12

        Message: 'A TCP packet $1 has been received, $2 bytes. rem. IP: $3, Port: $4'

        Parameters list:
              $1: scad12-message-type
              $2: scad12-bytes
              $3: scad12-foreign-host
              $4: scad12-remote-port

        A TCP Packet has been received."
    ::= { scadNotificationsPrefix 12 }

scadNotification13 NOTIFICATION-TYPE
    OBJECTS { 
              scad13-foreign-host, 
              scad13-remote-port 
            }
    STATUS current
    DESCRIPTION
        "Notification of Event SCAD.13

        Message: 'The TCP session has been closed. rem. IP: $1, Port: $2'

        Parameters list:
              $1: scad13-foreign-host
              $2: scad13-remote-port

        The TCP session has been closed."
    ::= { scadNotificationsPrefix 13 }

scadNotification14 NOTIFICATION-TYPE
    OBJECTS { 
              scad14-foreign-host, 
              scad14-remote-port 
            }
    STATUS current
    DESCRIPTION
        "Notification of Event SCAD.14

        Message: 'The TCP session has been closed by the Remote end. rem. IP: $1, Port: $2'

        Parameters list:
              $1: scad14-foreign-host
              $2: scad14-remote-port

        The TCP session has been closed by the Remote end."
    ::= { scadNotificationsPrefix 14 }

scadNotification15 NOTIFICATION-TYPE
    OBJECTS { 
              scad15-remote-ip, 
              scad15-remote-port 
            }
    STATUS current
    DESCRIPTION
        "Notification of Event SCAD.15

        Message: 'The TCP session has been opened by the Remote end. Remote IP:$1 , Port: $2'

        Parameters list:
              $1: scad15-remote-ip
              $2: scad15-remote-port

        The TCP session has been opened by the Remote end."
    ::= { scadNotificationsPrefix 15 }

scadNotification16 NOTIFICATION-TYPE
    OBJECTS { 
              scad16-address, 
              scad16-bytes,
              scad16-interface,
              scad16-state 
            }
    STATUS current
    DESCRIPTION
        "Notification of Event SCAD.16

        Message: 'Tx Message to Serial Terminal,address: $1, $2 bytes interface $3 state $4'

        Parameters list:
              $1: scad16-address
              $2: scad16-bytes
              $3: scad16-interface
              $4: scad16-state

        A Message has been transmitted to Serial Terminal."
    ::= { scadNotificationsPrefix 16 }

scadNotification17 NOTIFICATION-TYPE
    OBJECTS { 
              scad17-message-type, 
              scad17-interface,
              scad17-state 
            }
    STATUS current
    DESCRIPTION
        "Notification of Event SCAD.17

        Message: 'Serial Control Signal Imput change to $1, interface $2 state $3'

        Parameters list:
              $1: scad17-message-type
              $2: scad17-interface
              $3: scad17-state

        A change ON/OFF has been detected in Serial Control Signal Input."
    ::= { scadNotificationsPrefix 17 }

scadNotification18 NOTIFICATION-TYPE
    OBJECTS { 
              scad18-site, 
              scad18-interface,
              scad18-state 
            }
    STATUS current
    DESCRIPTION
        "Notification of Event SCAD.18

        Message: 'Timeout waiting data from $1, interface $2 state $3'

        Parameters list:
              $1: scad18-site
              $2: scad18-interface
              $3: scad18-state

        Timeout has occur waiting data."
    ::= { scadNotificationsPrefix 18 }

scadNotification19 NOTIFICATION-TYPE
    OBJECTS { 
              scad19-interface, 
              scad19-state 
            }
    STATUS current
    DESCRIPTION
        "Notification of Event SCAD.19

        Message: 'Packet lost due TCP Tx overrun error. Interface $1 state $2'

        Parameters list:
              $1: scad19-interface
              $2: scad19-state

        A packet was lost, due TCP Tx overrun error."
    ::= { scadNotificationsPrefix 19 }

scadNotification20 NOTIFICATION-TYPE
    OBJECTS { 
              scad20-interface, 
              scad20-state 
            }
    STATUS current
    DESCRIPTION
        "Notification of Event SCAD.20

        Message: 'Packet lost due TCP session is closes. Interface $1 state $2'

        Parameters list:
              $1: scad20-interface
              $2: scad20-state

        A packet was lost, due TCP is closed."
    ::= { scadNotificationsPrefix 20 }

scadNotification21 NOTIFICATION-TYPE
    OBJECTS { 
              scad21-na, 
              scad21-ip-host-address,
              scad21-cause,
              scad21-interface 
            }
    STATUS current
    DESCRIPTION
        "Notification of Event SCAD.21

        Message: 'The transfer has been wrong, against address $1, IP $2, Cause $3, interface $4'

        Parameters list:
              $1: scad21-na
              $2: scad21-ip-host-address
              $3: scad21-cause
              $4: scad21-interface

        The transfer has been wrong against specified NA and IP addr."
    ::= { scadNotificationsPrefix 21 }

scadNotification22 NOTIFICATION-TYPE
    OBJECTS { 
              scad22-event, 
              scad22-ip,
              scad22-port 
            }
    STATUS current
    DESCRIPTION
        "Notification of Event SCAD.22

        Message: 'The TCP event: $1 . Rem. IP: $2, rem. Port: $3'

        Parameters list:
              $1: scad22-event
              $2: scad22-ip
              $3: scad22-port

        TCP generic event was occurred."
    ::= { scadNotificationsPrefix 22 }

scadNotification23 NOTIFICATION-TYPE
    OBJECTS { 
              scad23-message-type, 
              scad23-interface,
              scad23-state 
            }
    STATUS current
    DESCRIPTION
        "Notification of Event SCAD.23

        Message: 'Serial Control Output change to $1, interface $2 state $3'

        Parameters list:
              $1: scad23-message-type
              $2: scad23-interface
              $3: scad23-state

        A change ON/OFF has been make in Serial Control Signal Output."
    ::= { scadNotificationsPrefix 23 }

scadNotification24 NOTIFICATION-TYPE
    OBJECTS { 
              scad24-message-type, 
              scad24-interface,
              scad24-state 
            }
    STATUS current
    DESCRIPTION
        "Notification of Event SCAD.24

        Message: 'Data ERROR from Serial Terminal has been received type: $1. Interface $2 state $3'

        Parameters list:
              $1: scad24-message-type
              $2: scad24-interface
              $3: scad24-state

        Data error from Serial Terminal has been received."
    ::= { scadNotificationsPrefix 24 }

scadNotification25 NOTIFICATION-TYPE
    OBJECTS { 
              scad25-port 
            }
    STATUS current
    DESCRIPTION
        "Notification of Event SCAD.25

        Message: 'Max sessions number has been reached, port $1'

        Parameters list:
              $1: scad25-port

        TCP Listen has been closed, due max session number has been reached."
    ::= { scadNotificationsPrefix 25 }

scadNotification26 NOTIFICATION-TYPE
    OBJECTS { 
              scad26-event, 
              scad26-ip,
              scad26-port 
            }
    STATUS current
    DESCRIPTION
        "Notification of Event SCAD.26

        Message: 'TCP inout session rejet: $1 . Rem. IP: $2, rem. Port: $3'

        Parameters list:
              $1: scad26-event
              $2: scad26-ip
              $3: scad26-port

        An input TCP session has been rejet."
    ::= { scadNotificationsPrefix 26 }

scadNotification27 NOTIFICATION-TYPE
    OBJECTS { 
              scad27-interface, 
              scad27-serial-address,
              scad27-lenght,
              scad27-hex-data 
            }
    STATUS current
    DESCRIPTION
        "Notification of Event SCAD.27

        Message: 'Data transmitted to serial interface $1 (addr:$2,$3 bytes):$4'

        Parameters list:
              $1: scad27-interface
              $2: scad27-serial-address
              $3: scad27-lenght
              $4: scad27-hex-data

        Detailed Data send to serial interface."
    ::= { scadNotificationsPrefix 27 }

scadNotification28 NOTIFICATION-TYPE
    OBJECTS { 
              scad28-interface, 
              scad28-serial-address,
              scad28-lenght,
              scad28-hex-data 
            }
    STATUS current
    DESCRIPTION
        "Notification of Event SCAD.28

        Message: 'Data received from serial interface $1 (addr:$2,$3 bytes):$4'

        Parameters list:
              $1: scad28-interface
              $2: scad28-serial-address
              $3: scad28-lenght
              $4: scad28-hex-data

        Detailed Data received from serial interface."
    ::= { scadNotificationsPrefix 28 }

scadNotification29 NOTIFICATION-TYPE
    OBJECTS { 
              scad29-state, 
              scad29-interface 
            }
    STATUS current
    DESCRIPTION
        "Notification of Event SCAD.29

        Message: 'Track nsla triggered(state:$1) ifc $2'

        Parameters list:
              $1: scad29-state
              $2: scad29-interface

        Configured NSLA track has triggered."
    ::= { scadNotificationsPrefix 29 }


END
