-- file automatically created


TELDAT-TRAP-LDAP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ldapTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LDAP event subsystem."
    REVISION "201401200930Z"
    DESCRIPTION "Initial implementation"
        ::= { telEventTraps 146 }


ldapEventsGroup	OBJECT IDENTIFIER	::= { ldapTrapsMIB 1 }

ldapNotifications	OBJECT IDENTIFIER	::= { ldapTrapsMIB 2 }
ldapNotificationsPrefix	OBJECT IDENTIFIER	::= { ldapNotifications 0 }

ldapEventObjects1 OBJECT-IDENTITY
    STATUS current
    DESCRIPTION
        "Event LDAP.1
        Succesfull Bind Operation. A requested bind operation finished
        with a correct connection establishment."
    ::= { ldapEventsGroup 1 }

ldap1-ldap-sequence OBJECT-TYPE
    SYNTAX Integer32
    MAX-ACCESS accessible-for-notify
    STATUS current
    DESCRIPTION
        "Parameter 'ldap-sequence' in event LDAP.1"
    ::= { ldapEventObjects1 1 }

ldap1-ip-source OBJECT-TYPE
    SYNTAX DisplayString
    MAX-ACCESS accessible-for-notify
    STATUS current
    DESCRIPTION
        "Parameter 'ip-source' in event LDAP.1"
    ::= { ldapEventObjects1 2 }

ldap1-ip-destination OBJECT-TYPE
    SYNTAX DisplayString
    MAX-ACCESS accessible-for-notify
    STATUS current
    DESCRIPTION
        "Parameter 'ip-destination' in event LDAP.1"
    ::= { ldapEventObjects1 3 }

ldapEventObjects2 OBJECT-IDENTITY
    STATUS current
    DESCRIPTION
        "Event LDAP.2
        Unsuccesfull bind operation between a source an a destination returned
        no room available. Bind was right but when trying to send connection
        information the router tell us there is no space left to send it."
    ::= { ldapEventsGroup 2 }

ldap2-ldap-sequence OBJECT-TYPE
    SYNTAX Integer32
    MAX-ACCESS accessible-for-notify
    STATUS current
    DESCRIPTION
        "Parameter 'ldap-sequence' in event LDAP.2"
    ::= { ldapEventObjects2 1 }

ldap2-ip-source OBJECT-TYPE
    SYNTAX DisplayString
    MAX-ACCESS accessible-for-notify
    STATUS current
    DESCRIPTION
        "Parameter 'ip-source' in event LDAP.2"
    ::= { ldapEventObjects2 2 }

ldap2-ip-destination OBJECT-TYPE
    SYNTAX DisplayString
    MAX-ACCESS accessible-for-notify
    STATUS current
    DESCRIPTION
        "Parameter 'ip-destination' in event LDAP.2"
    ::= { ldapEventObjects2 3 }

ldapEventObjects3 OBJECT-IDENTITY
    STATUS current
    DESCRIPTION
        "Event LDAP.3
        Unsuccesfull bind operation between a source an a destination returned
        timeout."
    ::= { ldapEventsGroup 3 }

ldap3-ldap-sequence OBJECT-TYPE
    SYNTAX Integer32
    MAX-ACCESS accessible-for-notify
    STATUS current
    DESCRIPTION
        "Parameter 'ldap-sequence' in event LDAP.3"
    ::= { ldapEventObjects3 1 }

ldap3-ip-source OBJECT-TYPE
    SYNTAX DisplayString
    MAX-ACCESS accessible-for-notify
    STATUS current
    DESCRIPTION
        "Parameter 'ip-source' in event LDAP.3"
    ::= { ldapEventObjects3 2 }

ldap3-ip-destination OBJECT-TYPE
    SYNTAX DisplayString
    MAX-ACCESS accessible-for-notify
    STATUS current
    DESCRIPTION
        "Parameter 'ip-destination' in event LDAP.3"
    ::= { ldapEventObjects3 3 }

ldapEventObjects4 OBJECT-IDENTITY
    STATUS current
    DESCRIPTION
        "Event LDAP.4
        An operation was requested by an LDAP client and LDAP Server
        returned OK."
    ::= { ldapEventsGroup 4 }

ldap4-ldap-sequence OBJECT-TYPE
    SYNTAX Integer32
    MAX-ACCESS accessible-for-notify
    STATUS current
    DESCRIPTION
        "Parameter 'ldap-sequence' in event LDAP.4"
    ::= { ldapEventObjects4 1 }

ldap4-operation OBJECT-TYPE
    SYNTAX DisplayString
    MAX-ACCESS accessible-for-notify
    STATUS current
    DESCRIPTION
        "Parameter 'operation' in event LDAP.4"
    ::= { ldapEventObjects4 2 }

ldap4-ip-source OBJECT-TYPE
    SYNTAX DisplayString
    MAX-ACCESS accessible-for-notify
    STATUS current
    DESCRIPTION
        "Parameter 'ip-source' in event LDAP.4"
    ::= { ldapEventObjects4 3 }

ldap4-ip-destination OBJECT-TYPE
    SYNTAX DisplayString
    MAX-ACCESS accessible-for-notify
    STATUS current
    DESCRIPTION
        "Parameter 'ip-destination' in event LDAP.4"
    ::= { ldapEventObjects4 4 }

ldapEventObjects5 OBJECT-IDENTITY
    STATUS current
    DESCRIPTION
        "Event LDAP.5
        An operation was requested by an LDAP client and LDAP Server returned
        any value meaning error."
    ::= { ldapEventsGroup 5 }

ldap5-ldap-sequence OBJECT-TYPE
    SYNTAX Integer32
    MAX-ACCESS accessible-for-notify
    STATUS current
    DESCRIPTION
        "Parameter 'ldap-sequence' in event LDAP.5"
    ::= { ldapEventObjects5 1 }

ldap5-operation OBJECT-TYPE
    SYNTAX DisplayString
    MAX-ACCESS accessible-for-notify
    STATUS current
    DESCRIPTION
        "Parameter 'operation' in event LDAP.5"
    ::= { ldapEventObjects5 2 }

ldap5-ip-source OBJECT-TYPE
    SYNTAX DisplayString
    MAX-ACCESS accessible-for-notify
    STATUS current
    DESCRIPTION
        "Parameter 'ip-source' in event LDAP.5"
    ::= { ldapEventObjects5 3 }

ldap5-ip-destination OBJECT-TYPE
    SYNTAX DisplayString
    MAX-ACCESS accessible-for-notify
    STATUS current
    DESCRIPTION
        "Parameter 'ip-destination' in event LDAP.5"
    ::= { ldapEventObjects5 4 }

ldap5-result-desc OBJECT-TYPE
    SYNTAX DisplayString
    MAX-ACCESS accessible-for-notify
    STATUS current
    DESCRIPTION
        "Parameter 'result-desc' in event LDAP.5"
    ::= { ldapEventObjects5 5 }

ldap5-result-code OBJECT-TYPE
    SYNTAX Integer32
    MAX-ACCESS accessible-for-notify
    STATUS current
    DESCRIPTION
        "Parameter 'result-code' in event LDAP.5"
    ::= { ldapEventObjects5 6 }

ldap5-dn-affected OBJECT-TYPE
    SYNTAX DisplayString
    MAX-ACCESS accessible-for-notify
    STATUS current
    DESCRIPTION
        "Parameter 'dn-affected' in event LDAP.5"
    ::= { ldapEventObjects5 7 }

ldap5-error-message OBJECT-TYPE
    SYNTAX DisplayString
    MAX-ACCESS accessible-for-notify
    STATUS current
    DESCRIPTION
        "Parameter 'error-message' in event LDAP.5"
    ::= { ldapEventObjects5 8 }

ldapEventObjects6 OBJECT-IDENTITY
    STATUS current
    DESCRIPTION
        "Event LDAP.6
        All operations are composed by a set of sub-operations. The flow of
        this sub-operations is followed through a state machine. In this case
        a sub-operation appears when other was expected."
    ::= { ldapEventsGroup 6 }

ldap6-ldap-sequence OBJECT-TYPE
    SYNTAX Integer32
    MAX-ACCESS accessible-for-notify
    STATUS current
    DESCRIPTION
        "Parameter 'ldap-sequence' in event LDAP.6"
    ::= { ldapEventObjects6 1 }

ldap6-actual-state OBJECT-TYPE
    SYNTAX DisplayString
    MAX-ACCESS accessible-for-notify
    STATUS current
    DESCRIPTION
        "Parameter 'actual-state' in event LDAP.6"
    ::= { ldapEventObjects6 2 }

ldap6-expected-state OBJECT-TYPE
    SYNTAX DisplayString
    MAX-ACCESS accessible-for-notify
    STATUS current
    DESCRIPTION
        "Parameter 'expected-state' in event LDAP.6"
    ::= { ldapEventObjects6 3 }

ldapEventObjects7 OBJECT-IDENTITY
    STATUS current
    DESCRIPTION
        "Event LDAP.7
        Unsuccesfull unbind operation between a source an a destination
        returned timeout."
    ::= { ldapEventsGroup 7 }

ldap7-ldap-sequence OBJECT-TYPE
    SYNTAX Integer32
    MAX-ACCESS accessible-for-notify
    STATUS current
    DESCRIPTION
        "Parameter 'ldap-sequence' in event LDAP.7"
    ::= { ldapEventObjects7 1 }

ldap7-ip-source OBJECT-TYPE
    SYNTAX DisplayString
    MAX-ACCESS accessible-for-notify
    STATUS current
    DESCRIPTION
        "Parameter 'ip-source' in event LDAP.7"
    ::= { ldapEventObjects7 2 }

ldap7-ip-destination OBJECT-TYPE
    SYNTAX DisplayString
    MAX-ACCESS accessible-for-notify
    STATUS current
    DESCRIPTION
        "Parameter 'ip-destination' in event LDAP.7"
    ::= { ldapEventObjects7 3 }

ldapEventObjects8 OBJECT-IDENTITY
    STATUS current
    DESCRIPTION
        "Event LDAP.8
        An error occurred when allocating memory for a command buffer."
    ::= { ldapEventsGroup 8 }

ldap8-ldap-sequence OBJECT-TYPE
    SYNTAX Integer32
    MAX-ACCESS accessible-for-notify
    STATUS current
    DESCRIPTION
        "Parameter 'ldap-sequence' in event LDAP.8"
    ::= { ldapEventObjects8 1 }

ldap8-command OBJECT-TYPE
    SYNTAX DisplayString
    MAX-ACCESS accessible-for-notify
    STATUS current
    DESCRIPTION
        "Parameter 'command' in event LDAP.8"
    ::= { ldapEventObjects8 2 }

ldapEventObjects9 OBJECT-IDENTITY
    STATUS current
    DESCRIPTION
        "Event LDAP.9
        An LDAP Timeout occurred while performing request operation between
        client and server."
    ::= { ldapEventsGroup 9 }

ldap9-ldap-sequence OBJECT-TYPE
    SYNTAX Integer32
    MAX-ACCESS accessible-for-notify
    STATUS current
    DESCRIPTION
        "Parameter 'ldap-sequence' in event LDAP.9"
    ::= { ldapEventObjects9 1 }

ldap9-ip-source OBJECT-TYPE
    SYNTAX DisplayString
    MAX-ACCESS accessible-for-notify
    STATUS current
    DESCRIPTION
        "Parameter 'ip-source' in event LDAP.9"
    ::= { ldapEventObjects9 2 }

ldap9-ip-destination OBJECT-TYPE
    SYNTAX DisplayString
    MAX-ACCESS accessible-for-notify
    STATUS current
    DESCRIPTION
        "Parameter 'ip-destination' in event LDAP.9"
    ::= { ldapEventObjects9 3 }

ldapEventObjects10 OBJECT-IDENTITY
    STATUS current
    DESCRIPTION
        "Event LDAP.10
        After a request operation an unexpected frame is received."
    ::= { ldapEventsGroup 10 }

ldap10-ldap-sequence OBJECT-TYPE
    SYNTAX Integer32
    MAX-ACCESS accessible-for-notify
    STATUS current
    DESCRIPTION
        "Parameter 'ldap-sequence' in event LDAP.10"
    ::= { ldapEventObjects10 1 }

ldap10-operation OBJECT-TYPE
    SYNTAX DisplayString
    MAX-ACCESS accessible-for-notify
    STATUS current
    DESCRIPTION
        "Parameter 'operation' in event LDAP.10"
    ::= { ldapEventObjects10 2 }

ldap10-ip-source OBJECT-TYPE
    SYNTAX DisplayString
    MAX-ACCESS accessible-for-notify
    STATUS current
    DESCRIPTION
        "Parameter 'ip-source' in event LDAP.10"
    ::= { ldapEventObjects10 3 }

ldap10-ip-destination OBJECT-TYPE
    SYNTAX DisplayString
    MAX-ACCESS accessible-for-notify
    STATUS current
    DESCRIPTION
        "Parameter 'ip-destination' in event LDAP.10"
    ::= { ldapEventObjects10 4 }

ldap10-frame-data OBJECT-TYPE
    SYNTAX DisplayString
    MAX-ACCESS accessible-for-notify
    STATUS current
    DESCRIPTION
        "Parameter 'frame-data' in event LDAP.10"
    ::= { ldapEventObjects10 5 }

ldapEventObjects11 OBJECT-IDENTITY
    STATUS current
    DESCRIPTION
        "Event LDAP.11
        Shows the evolution on the LDAP TCP STATE MACHINE."
    ::= { ldapEventsGroup 11 }

ldap11-origin OBJECT-TYPE
    SYNTAX Integer32
    MAX-ACCESS accessible-for-notify
    STATUS current
    DESCRIPTION
        "Parameter 'origin' in event LDAP.11"
    ::= { ldapEventObjects11 1 }

ldap11-destination OBJECT-TYPE
    SYNTAX Integer32
    MAX-ACCESS accessible-for-notify
    STATUS current
    DESCRIPTION
        "Parameter 'destination' in event LDAP.11"
    ::= { ldapEventObjects11 2 }

ldapEventObjects12 OBJECT-IDENTITY
    STATUS current
    DESCRIPTION
        "Event LDAP.12
        Shows the bytes sent to LDAP Server."
    ::= { ldapEventsGroup 12 }

ldap12-bytes OBJECT-TYPE
    SYNTAX DisplayString
    MAX-ACCESS accessible-for-notify
    STATUS current
    DESCRIPTION
        "Parameter 'bytes' in event LDAP.12"
    ::= { ldapEventObjects12 1 }

ldapEventObjects13 OBJECT-IDENTITY
    STATUS current
    DESCRIPTION
        "Event LDAP.13
        Shows the bytes received from LDAP Server."
    ::= { ldapEventsGroup 13 }

ldap13-bytes OBJECT-TYPE
    SYNTAX DisplayString
    MAX-ACCESS accessible-for-notify
    STATUS current
    DESCRIPTION
        "Parameter 'bytes' in event LDAP.13"
    ::= { ldapEventObjects13 1 }

ldapEventObjects14 OBJECT-IDENTITY
    STATUS current
    DESCRIPTION
        "Event LDAP.14
        When a search operation is requested, LDAP Server sends results to
        the client. This results are stored into buffers. Users can establish
        how many buffers are to be filled. When they are reached
        operation is finished OK."
    ::= { ldapEventsGroup 14 }

ldap14-ldap-sequence OBJECT-TYPE
    SYNTAX Integer32
    MAX-ACCESS accessible-for-notify
    STATUS current
    DESCRIPTION
        "Parameter 'ldap-sequence' in event LDAP.14"
    ::= { ldapEventObjects14 1 }

ldap14-ip-source OBJECT-TYPE
    SYNTAX DisplayString
    MAX-ACCESS accessible-for-notify
    STATUS current
    DESCRIPTION
        "Parameter 'ip-source' in event LDAP.14"
    ::= { ldapEventObjects14 2 }

ldap14-ip-destination OBJECT-TYPE
    SYNTAX DisplayString
    MAX-ACCESS accessible-for-notify
    STATUS current
    DESCRIPTION
        "Parameter 'ip-destination' in event LDAP.14"
    ::= { ldapEventObjects14 3 }

ldapEventObjects15 OBJECT-IDENTITY
    STATUS current
    DESCRIPTION
        "Event LDAP.15
        When a search operation is requested, LDAP Server sends results to
        the client. This results are stored into buffers. The size of
        the reception buffer is determined by the window size. If Server sends
        data and client is no able to store it then this error occurs."
    ::= { ldapEventsGroup 15 }

ldap15-ldap-sequence OBJECT-TYPE
    SYNTAX Integer32
    MAX-ACCESS accessible-for-notify
    STATUS current
    DESCRIPTION
        "Parameter 'ldap-sequence' in event LDAP.15"
    ::= { ldapEventObjects15 1 }

ldap15-ip-source OBJECT-TYPE
    SYNTAX DisplayString
    MAX-ACCESS accessible-for-notify
    STATUS current
    DESCRIPTION
        "Parameter 'ip-source' in event LDAP.15"
    ::= { ldapEventObjects15 2 }

ldap15-ip-destination OBJECT-TYPE
    SYNTAX DisplayString
    MAX-ACCESS accessible-for-notify
    STATUS current
    DESCRIPTION
        "Parameter 'ip-destination' in event LDAP.15"
    ::= { ldapEventObjects15 3 }

ldap15-window-size OBJECT-TYPE
    SYNTAX Integer32
    MAX-ACCESS accessible-for-notify
    STATUS current
    DESCRIPTION
        "Parameter 'window-size' in event LDAP.15"
    ::= { ldapEventObjects15 4 }

ldap15-window-needed OBJECT-TYPE
    SYNTAX Integer32
    MAX-ACCESS accessible-for-notify
    STATUS current
    DESCRIPTION
        "Parameter 'window-needed' in event LDAP.15"
    ::= { ldapEventObjects15 5 }

ldapEventObjects16 OBJECT-IDENTITY
    STATUS current
    DESCRIPTION
        "Event LDAP.16
        For any reason the client sends an Abandon Request to the LDAP Server."
    ::= { ldapEventsGroup 16 }

ldap16-ldap-sequence OBJECT-TYPE
    SYNTAX Integer32
    MAX-ACCESS accessible-for-notify
    STATUS current
    DESCRIPTION
        "Parameter 'ldap-sequence' in event LDAP.16"
    ::= { ldapEventObjects16 1 }

ldap16-reason OBJECT-TYPE
    SYNTAX DisplayString
    MAX-ACCESS accessible-for-notify
    STATUS current
    DESCRIPTION
        "Parameter 'reason' in event LDAP.16"
    ::= { ldapEventObjects16 2 }


ldapNotification1 NOTIFICATION-TYPE
    OBJECTS { 
              ldap1-ldap-sequence, 
              ldap1-ip-source,
              ldap1-ip-destination 
            }
    STATUS current
    DESCRIPTION
        "Notification of Event LDAP.1

        Message: '($1) Connection established between $2 <--> $3. Bind Operation completed successfully.'

        Parameters list:
              $1: ldap1-ldap-sequence
              $2: ldap1-ip-source
              $3: ldap1-ip-destination

        Succesfull Bind Operation. A requested bind operation finished
        with a correct connection establishment."
    ::= { ldapNotificationsPrefix 1 }

ldapNotification2 NOTIFICATION-TYPE
    OBJECTS { 
              ldap2-ldap-sequence, 
              ldap2-ip-source,
              ldap2-ip-destination 
            }
    STATUS current
    DESCRIPTION
        "Notification of Event LDAP.2

        Message: '($1) There is no room in the router to send data between $2 <--> $3. Operation aborted.'

        Parameters list:
              $1: ldap2-ldap-sequence
              $2: ldap2-ip-source
              $3: ldap2-ip-destination

        Unsuccesfull bind operation between a source an a destination returned
        no room available. Bind was right but when trying to send connection
        information the router tell us there is no space left to send it."
    ::= { ldapNotificationsPrefix 2 }

ldapNotification3 NOTIFICATION-TYPE
    OBJECTS { 
              ldap3-ldap-sequence, 
              ldap3-ip-source,
              ldap3-ip-destination 
            }
    STATUS current
    DESCRIPTION
        "Notification of Event LDAP.3

        Message: '($1) Timeout expired for a bind operation between $2 as source IP and $3 as destiny IP'

        Parameters list:
              $1: ldap3-ldap-sequence
              $2: ldap3-ip-source
              $3: ldap3-ip-destination

        Unsuccesfull bind operation between a source an a destination returned
        timeout."
    ::= { ldapNotificationsPrefix 3 }

ldapNotification4 NOTIFICATION-TYPE
    OBJECTS { 
              ldap4-ldap-sequence, 
              ldap4-operation,
              ldap4-ip-source,
              ldap4-ip-destination 
            }
    STATUS current
    DESCRIPTION
        "Notification of Event LDAP.4

        Message: '($1) Data negotiation successfull. $2 sent $3 operation request $4 answered LDAPResult with OK message.'

        Parameters list:
              $1: ldap4-ldap-sequence
              $2: ldap4-operation
              $3: ldap4-ip-source
              $4: ldap4-ip-destination

        An operation was requested by an LDAP client and LDAP Server
        returned OK."
    ::= { ldapNotificationsPrefix 4 }

ldapNotification5 NOTIFICATION-TYPE
    OBJECTS { 
              ldap5-ldap-sequence, 
              ldap5-operation,
              ldap5-ip-source,
              ldap5-ip-destination,
              ldap5-result-desc,
              ldap5-result-code,
              ldap5-dn-affected,
              ldap5-error-message 
            }
    STATUS current
    DESCRIPTION
        "Notification of Event LDAP.5

        Message: '($1) Requested $2 operation was unsuccessfull. $3 requests operation to $4.LDAPResult: $5 ($6).DN        : $7.Message   : $8'

        Parameters list:
              $1: ldap5-ldap-sequence
              $2: ldap5-operation
              $3: ldap5-ip-source
              $4: ldap5-ip-destination
              $5: ldap5-result-desc
              $6: ldap5-result-code
              $7: ldap5-dn-affected
              $8: ldap5-error-message

        An operation was requested by an LDAP client and LDAP Server returned
        any value meaning error."
    ::= { ldapNotificationsPrefix 5 }

ldapNotification6 NOTIFICATION-TYPE
    OBJECTS { 
              ldap6-ldap-sequence, 
              ldap6-actual-state,
              ldap6-expected-state 
            }
    STATUS current
    DESCRIPTION
        "Notification of Event LDAP.6

        Message: '($1) Requested operation finished at this state ($2) when other ($3) was expected. State machine corrupted.'

        Parameters list:
              $1: ldap6-ldap-sequence
              $2: ldap6-actual-state
              $3: ldap6-expected-state

        All operations are composed by a set of sub-operations. The flow of
        this sub-operations is followed through a state machine. In this case
        a sub-operation appears when other was expected."
    ::= { ldapNotificationsPrefix 6 }

ldapNotification7 NOTIFICATION-TYPE
    OBJECTS { 
              ldap7-ldap-sequence, 
              ldap7-ip-source,
              ldap7-ip-destination 
            }
    STATUS current
    DESCRIPTION
        "Notification of Event LDAP.7

        Message: '($1) Disconnection for a bind operation between $2 as source IP and $3 as destiny IP'

        Parameters list:
              $1: ldap7-ldap-sequence
              $2: ldap7-ip-source
              $3: ldap7-ip-destination

        Unsuccesfull unbind operation between a source an a destination
        returned timeout."
    ::= { ldapNotificationsPrefix 7 }

ldapNotification8 NOTIFICATION-TYPE
    OBJECTS { 
              ldap8-ldap-sequence, 
              ldap8-command 
            }
    STATUS current
    DESCRIPTION
        "Notification of Event LDAP.8

        Message: '($1) Error allocating memory for the $2 operation in LDAP ObtenerComando'

        Parameters list:
              $1: ldap8-ldap-sequence
              $2: ldap8-command

        An error occurred when allocating memory for a command buffer."
    ::= { ldapNotificationsPrefix 8 }

ldapNotification9 NOTIFICATION-TYPE
    OBJECTS { 
              ldap9-ldap-sequence, 
              ldap9-ip-source,
              ldap9-ip-destination 
            }
    STATUS current
    DESCRIPTION
        "Notification of Event LDAP.9

        Message: '($1) LDAP Timeout occurred while performing request operation between $2 as client and $3 as server.'

        Parameters list:
              $1: ldap9-ldap-sequence
              $2: ldap9-ip-source
              $3: ldap9-ip-destination

        An LDAP Timeout occurred while performing request operation between
        client and server."
    ::= { ldapNotificationsPrefix 9 }

ldapNotification10 NOTIFICATION-TYPE
    OBJECTS { 
              ldap10-ldap-sequence, 
              ldap10-operation,
              ldap10-ip-source,
              ldap10-ip-destination,
              ldap10-frame-data 
            }
    STATUS current
    DESCRIPTION
        "Notification of Event LDAP.10

        Message: '($1) LDAP Error. Unexpected Frame from LDAP Server at operation $2 between $3 as client and $4 as server.Following data was received from LDAP Server:$5'

        Parameters list:
              $1: ldap10-ldap-sequence
              $2: ldap10-operation
              $3: ldap10-ip-source
              $4: ldap10-ip-destination
              $5: ldap10-frame-data

        After a request operation an unexpected frame is received."
    ::= { ldapNotificationsPrefix 10 }

ldapNotification11 NOTIFICATION-TYPE
    OBJECTS { 
              ldap11-origin, 
              ldap11-destination 
            }
    STATUS current
    DESCRIPTION
        "Notification of Event LDAP.11

        Message: 'FROM STATE $1 ---------> TO STATE $2'

        Parameters list:
              $1: ldap11-origin
              $2: ldap11-destination

        Shows the evolution on the LDAP TCP STATE MACHINE."
    ::= { ldapNotificationsPrefix 11 }

ldapNotification12 NOTIFICATION-TYPE
    OBJECTS { 
              ldap12-bytes 
            }
    STATUS current
    DESCRIPTION
        "Notification of Event LDAP.12

        Message: 'LDAP CLIENT:$1'

        Parameters list:
              $1: ldap12-bytes

        Shows the bytes sent to LDAP Server."
    ::= { ldapNotificationsPrefix 12 }

ldapNotification13 NOTIFICATION-TYPE
    OBJECTS { 
              ldap13-bytes 
            }
    STATUS current
    DESCRIPTION
        "Notification of Event LDAP.13

        Message: 'LDAP SERVER:$1'

        Parameters list:
              $1: ldap13-bytes

        Shows the bytes received from LDAP Server."
    ::= { ldapNotificationsPrefix 13 }

ldapNotification14 NOTIFICATION-TYPE
    OBJECTS { 
              ldap14-ldap-sequence, 
              ldap14-ip-source,
              ldap14-ip-destination 
            }
    STATUS current
    DESCRIPTION
        "Notification of Event LDAP.14

        Message: '($1) Search operation successfull. The operation between $2 and $3 finished OK afer the fullfillment of max results buffer.'

        Parameters list:
              $1: ldap14-ldap-sequence
              $2: ldap14-ip-source
              $3: ldap14-ip-destination

        When a search operation is requested, LDAP Server sends results to
        the client. This results are stored into buffers. Users can establish
        how many buffers are to be filled. When they are reached
        operation is finished OK."
    ::= { ldapNotificationsPrefix 14 }

ldapNotification15 NOTIFICATION-TYPE
    OBJECTS { 
              ldap15-ldap-sequence, 
              ldap15-ip-source,
              ldap15-ip-destination,
              ldap15-window-size,
              ldap15-window-needed 
            }
    STATUS current
    DESCRIPTION
        "Notification of Event LDAP.15

        Message: '($1) Search operation unsuccessfull. The operation between $2 and $3 finished with error because window size is set as $4 bytes and $5 bytes is required.'

        Parameters list:
              $1: ldap15-ldap-sequence
              $2: ldap15-ip-source
              $3: ldap15-ip-destination
              $4: ldap15-window-size
              $5: ldap15-window-needed

        When a search operation is requested, LDAP Server sends results to
        the client. This results are stored into buffers. The size of
        the reception buffer is determined by the window size. If Server sends
        data and client is no able to store it then this error occurs."
    ::= { ldapNotificationsPrefix 15 }

ldapNotification16 NOTIFICATION-TYPE
    OBJECTS { 
              ldap16-ldap-sequence, 
              ldap16-reason 
            }
    STATUS current
    DESCRIPTION
        "Notification of Event LDAP.16

        Message: '($1) LDAP Client sends an Abandon Request to LDAP Server. Reason is $2'

        Parameters list:
              $1: ldap16-ldap-sequence
              $2: ldap16-reason

        For any reason the client sends an Abandon Request to the LDAP Server."
    ::= { ldapNotificationsPrefix 16 }


END
