-- Teldat, S.A.
                                                
                -- Parque Tecnolgico de Madrid
                                                
                -- 28760, Tres Cantos (Madrid)
                                                
                -- Tlf: +34-918076565
                                                
                -- Fax: +34-918076521
                                                
                -- e-mail: id@teldat.es


            -- MIB privada de Teldat
            
            -- MTC1 (Mdulo de Telecontrol-1)
            


    -- Historial: 
    -- 1.0	01/07/04  J. Molina	    Fichero procedente del fichero MTC1.mib
			
			
	-- Historial del fichero MTC1.mib		

    -- 1.0 13/06/03  M.A. Pastor    Implementacin inicial
    -- ======================================================================= 

TELDAT-MON-MTC1-MIB DEFINITIONS ::= BEGIN

    IMPORTS
            OBJECT-TYPE
        FROM RFC-1212
            DisplayString
        FROM RFC1213-MIB
            telproducts 
        FROM TELDAT-MIB;


    -- Grupos en la MIB de TELDAT

    -- teladmin                     OBJECT IDENTIFIER ::= { teldat 1 }
    -- telxface                     OBJECT IDENTIFIER ::= { teldat 2 }
    -- telproto                     OBJECT IDENTIFIER ::= { teldat 3 }
    -- telProducts                  OBJECT IDENTIFIER ::= { teldat 4 }
    -- telDot3ChipSets              OBJECT IDENTIFIER ::= { teldat 5 }


    -- Grupo telproducts
    
    telProductsMTC1                 OBJECT IDENTIFIER ::= { telproducts 76 }

    
    -- Grupo telProductsMTC1

    telProductsMTC1Config           OBJECT IDENTIFIER ::= { telProductsMTC1 1 }
    telProductsMTC1Monit            OBJECT IDENTIFIER ::= { telProductsMTC1 2 }


    -- Grupo telProductsMTC1Monit

    telProductsMTC1MonCmdGroup      OBJECT IDENTIFIER ::= { telProductsMTC1Monit 1 }
    
    
    -- Grupo de variables correspondientes a comandos que se envan al mdulo
    
    telProductsMTC1MonCmdOn OBJECT-TYPE
        SYNTAX INTEGER{
            send(1),
            ok(2),
            error(3),
            undefined(4),
            running(5)
            }
        ACCESS read-write
        STATUS mandatory
        DESCRIPTION
            ""
        ::= { telProductsMTC1MonCmdGroup 1 }
    
    telProductsMTC1MonCmdOff OBJECT-TYPE
        SYNTAX INTEGER{
            send(1),
            ok(2),
            error(3),
            undefined(4),
            running(5)
            }
        ACCESS read-write
        STATUS mandatory
        DESCRIPTION
            ""
        ::= { telProductsMTC1MonCmdGroup 2 }
    
    telProductsMTC1MonCmdReset OBJECT-TYPE
        SYNTAX INTEGER{
            send(1),
            ok(2),
            error(3),
            undefined(4),
            running(5)
            }
        ACCESS read-write
        STATUS mandatory
        DESCRIPTION
            ""
        ::= { telProductsMTC1MonCmdGroup 3 }

    telProductsMTC1MonCmdStatus OBJECT-TYPE
        SYNTAX INTEGER{
            send(1),
            ok(2),
            error(3),
            undefined(4),
            running(5)
            }
        ACCESS read-write
        STATUS mandatory
        DESCRIPTION
            ""
        ::= { telProductsMTC1MonCmdGroup 4 }
    
    telProductsMTC1MonCmdVersion OBJECT-TYPE
        SYNTAX INTEGER{
            send(1),
            ok(2),
            error(3),
            undefined(4),
            running(5)
            }
        ACCESS read-write
        STATUS mandatory
        DESCRIPTION
            ""
        ::= { telProductsMTC1MonCmdGroup 5 }
   
    telProductsMTC1MonCmdOnRes OBJECT-TYPE
        SYNTAX DisplayString(SIZE(0..31))
        ACCESS read-only
        STATUS mandatory
        DESCRIPTION
            ""
        ::= { telProductsMTC1MonCmdGroup 6 }
        
    telProductsMTC1MonCmdOffRes OBJECT-TYPE
        SYNTAX DisplayString(SIZE(0..31))
        ACCESS read-only
        STATUS mandatory
        DESCRIPTION
            ""
        ::= { telProductsMTC1MonCmdGroup 7 }

    telProductsMTC1MonCmdResetRes OBJECT-TYPE
        SYNTAX DisplayString(SIZE(0..31))
        ACCESS read-only
        STATUS mandatory
        DESCRIPTION
            ""
        ::= { telProductsMTC1MonCmdGroup 8 }

    telProductsMTC1MonCmdStatusRes OBJECT-TYPE
        SYNTAX DisplayString(SIZE(0..31))
        ACCESS read-only
        STATUS mandatory
        DESCRIPTION
            ""
        ::= { telProductsMTC1MonCmdGroup 9 }

    telProductsMTC1MonCmdVersionRes OBJECT-TYPE
        SYNTAX DisplayString(SIZE(0..31))
        ACCESS read-only
        STATUS mandatory
        DESCRIPTION
            ""
        ::= { telProductsMTC1MonCmdGroup 10 }

END
