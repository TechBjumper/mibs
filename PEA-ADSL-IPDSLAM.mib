PEA-ADSL-IPDSLAM DEFINITIONS ::= BEGIN

IMPORTS
    peaIpDslam
       FROM DIESEL-SMI
       
    lineIndex
       FROM PEA-BRIDGE-IPDSLAM
       
    messageId, 
    errorCode
       FROM PEA-EQUIPMENT-IPDSLAM

    -- standar X.733 header for the traps       
    managedObjectClass, 
    managedObjectInstance, 
    sequenceNumber, 
    perceivedSeverity, 
    eventTime, 
    eventTypePem, 
    probableCause  
       FROM PEM-STANDARD 

    MODULE-IDENTITY, OBJECT-TYPE, NOTIFICATION-TYPE,
    Gauge32,Integer32,Unsigned32, Counter32
        FROM SNMPv2-SMI
        
    TEXTUAL-CONVENTION,		
    TruthValue
       FROM SNMPv2-TC
       
    OBJECT-GROUP, NOTIFICATION-GROUP   
             FROM SNMPv2-CONF
        
    DisplayString
        FROM RFC1213-MIB
        
    adslAtucIntervalNumber,
    adslAturIntervalNumber,
    adslAtucChanIntervalNumber,
    adslAturChanIntervalNumber,
    adslLineConfProfileEntry,
    adslLineAlarmConfProfileEntry,
    adslAtucThresh15MinESs,
    adslAturThresh15MinESs,
    adslAtucThresh15MinLofs,
    adslAturThresh15MinLofs,
    adslAtucThresh15MinLoss,
    adslAturThresh15MinLoss,
    adslAtucThresh15MinLols,
    adslAturThresh15MinLprs,
    adslAtucChanCurrTxRate,
    adslAturChanCurrTxRate
        FROM ADSL-LINE-MIB
        
    adslAtucThreshold15MinSesL,
    adslAtucThreshold15MinUasL,
    adslAturThreshold15MinSesL,
    adslAturThreshold15MinUasL
        FROM ADSL-LINE-EXT-MIB;
    

peaAdslIpDslam  MODULE-IDENTITY 
    LAST-UPDATED 
         "200405031200Z"  
    ORGANIZATION
         "Ericsson Danmark A/S - Denmark"
    CONTACT-INFO
         "
         Ericsson Danmark A/S
         Faelledvej 17
         DK-7600 Struer
         Denmark

         E-mail: diax.support@ericsson.com
         "       
   DESCRIPTION
         "
         The IP DSLAM software supports a number of standard 
         and proprietary MIBs.
         The MIB module defines objects for the management of a 
         pair of ADSL modems at each end of the ADSL line and is 
         an extension to the ADSL-LINE-MIB (RFC2662). The reason 
         for this MIB module is that the original ADSL-LINE- MIB 
         is not conforming to the G.997.1 standard. The draft 
         extension MIB (RFC2662) is not released yet and is also 
         lacking parameters defined in the G.997.1. 
         One naming convention was added to those from the ADSL-LINE-MIB: 
         an 'X' from 'extension' is added to all names.
         "                                                           
    ::= { peaIpDslam 10 }

adslXObjects              OBJECT IDENTIFIER ::= { peaAdslIpDslam 1 }
adslXTraps                OBJECT IDENTIFIER ::= { peaAdslIpDslam 2 }
adslXObjectsGroups        OBJECT IDENTIFIER ::= { peaAdslIpDslam 3 }
adslXTrapsGroups          OBJECT IDENTIFIER ::= { peaAdslIpDslam 4 }

TonePartIdIndex ::= INTEGER(0..2147483646)

--******************************************************************
-- TEXTUAL-CONVENTIONs are copied instead of imported because of
-- Idbgen tool.
--******************************************************************
PerfCurrentCount ::= TEXTUAL-CONVENTION
      STATUS  current
      DESCRIPTION
         "A counter associated with a
          performance measurement in a current 15
          minute measurement interval. The value
          of this counter starts from zero and is
          increased when associated events occur,
          until the end of the 15 minute interval.
          At that time the value of the counter is
          stored in the first 15 minute history
          interval, and the CurrentCount is
          restarted at zero. In the
          case where the agent has no valid data
          available for the current interval the
          corresponding object instance is not
          available and upon a retrieval request
          a corresponding error message shall be
          returned to indicate that this instance
          does not exist (for example, a noSuchName
          error for SNMPv1 and a noSuchInstance for
          SNMPv2 GET operation)."
       SYNTAX  Gauge32

PerfIntervalCount ::= TEXTUAL-CONVENTION
      STATUS  current
      DESCRIPTION
         "A counter associated with a
          performance measurement in a previous
          15 minute measurement interval. In the
          case where the agent has no valid data
          available for a particular interval the
          corresponding object instance is not
          available and upon a retrieval request
          a corresponding error message shall be
          returned to indicate that this instance
          does not exist (for example, a noSuchName
          error for SNMPv1 and a noSuchInstance for
          SNMPv2 GET operation).
          In a system supporting
          a history of n intervals with
          IntervalCount(1) and IntervalCount(n) the
          most and least recent intervals
          respectively, the following applies at
          the end of a 15 minute interval:
          - discard the value of IntervalCount(n)
          - the value of IntervalCount(i) becomes that
            of IntervalCount(i-1) for n >= i > 1
          - the value of IntervalCount(1) becomes that
            of CurrentCount
          - the TotalCount, if supported, is adjusted."
       SYNTAX  Gauge32 
       
Perf1DayIntervalXCount ::= TEXTUAL-CONVENTION
      STATUS  current
      DESCRIPTION
         "A counter associated with a performance measurement
          in a previous	1-day (24 hour) measurement interval.
          In a system supporting a history of n	intervals is
          IntervalCount(1) and IntervalCount(n) the most and
          least recent intervals respectively, the following
          applies at the end of a 1 day interval:
          - discard the value of IntervalCount(n)
          - the value of IntervalCount(i) becomes that
            of IntervalCount(i-1) for n >= i > 1
          - the value of IntervalCount(1) becomes that
            of CurrentCount."
       SYNTAX  Gauge32 

AdslPerfCurrDayCount ::= TEXTUAL-CONVENTION
      STATUS  current
      DESCRIPTION
         "A counter associated with interface performance
          measurements in a current 1-day (24 hour) measurement
          interval.

          The value of this counter starts at zero at the
          beginning of an interval and is increased when
          associated events occur, until the end of the
          1-day interval.  At that time the value of the
          counter is stored in the previous 1-day history
          interval, if available, and the current interval
          counter is restarted at zero.

          In the case where the agent has no valid data available
          for this interval the corresponding object
          instance is not available and upon a retrieval
          request a corresponding error message shall be
          returned to indicate that this instance does
          not exist (for example, a noSuchName error for
          SNMPv1 and a noSuchInstance for SNMPv2 GET
          operation)."
      SYNTAX  Gauge32

AdslPerfPrevDayCount ::= TEXTUAL-CONVENTION
      STATUS  current
      DESCRIPTION
         "A counter associated with interface performance
          measurements during the most previous 1-day (24 hour)
          measurement interval.  The value of this counter is
          equal to the value of the current day counter at
          the end of its most recent interval.

          In the case where the agent has no valid data available
          for this interval the corresponding object
          instance is not available and upon a retrieval
          request a corresponding error message shall be
          returned to indicate that this instance does
          not exist (for example, a noSuchName error for
          SNMPv1 and a noSuchInstance for SNMPv2 GET
          operation)."
      SYNTAX  Gauge32
                        
AdslTransmissionModeType ::= TEXTUAL-CONVENTION
      STATUS       current
      DESCRIPTION
         "A set of ADSL line transmission modes, with one bit
          per mode.  The notes (F) and (L) denote Full-Rate
          and G.Lite respectively:
          Bit 00 : Regional Std. (ANSI T1.413) (F)
          Bit 01 : Regional Std. (ETSI DTS/TM06006) (F)
          Bit 02 : G.992.1 POTS non-overlapped (F)
          Bit 03 : G.992.1 POTS overlapped (F)
          Bit 04 : G.992.1 ISDN non-overlapped (F)
          Bit 05 : G.992.1 ISDN overlapped (F)
          Bit 06 : G.992.1 TCM-ISDN non-overlapped (F)
          Bit 07 : G.992.1 TCM-ISDN overlapped (F)
          Bit 08 : G.992.2 POTS non-overlapped (L)
          Bit 09 : G.992.2 POTS overlapped (L)
          Bit 10 : G.992.2 with TCM-ISDN non-overlapped (L)
          Bit 11 : G.992.2 with TCM-ISDN overlapped (L)
          Bit 12 : G.992.1 TCM-ISDN symmetric (F)
          "
      SYNTAX      BITS {
                  ansit1413(0),
                  etsi(1),
                  q9921PotsNonOverlapped(2),
                  q9921PotsOverlapped(3),
                  q9921IsdnNonOverlapped(4),
                  q9921isdnOverlapped(5),
                  q9921tcmIsdnNonOverlapped(6),
                  q9921tcmIsdnOverlapped(7),
                  q9922potsNonOverlapeed(8),
                  q9922potsOverlapped(9),
                  q9922tcmIsdnNonOverlapped(10),
                  q9922tcmIsdnOverlapped(11),
                  q9921tcmIsdnSymmetric(12)
                  }

SnmpAdminString ::= TEXTUAL-CONVENTION
    DISPLAY-HINT "255a"
    STATUS       current
    DESCRIPTION
            "An octet string containing administrative
            information, preferably in human-readable form.

            To facilitate internationalization, this
            information is represented using the ISO/IEC
            IS 10646-1 character set, encoded as an octet
            string using the UTF-8 transformation format
            described in [RFC2279].

            Since additional code points are added by
            amendments to the 10646 standard from time
            to time, implementations must be prepared to
            encounter any code point from 0x00000000 to
            0x7fffffff.  Byte sequences that do not
            correspond to the valid UTF-8 encoding of a
            code point or are outside this range are
            prohibited.

            The use of control codes should be avoided.

            When it is necessary to represent a newline,
            the control code sequence CR LF should be used.

            The use of leading or trailing white space should
            be avoided.

            For code points not directly supported by user
            interface hardware or software, an alternative
            means of entry and display, such as hexadecimal,
            may be provided.

            For information encoded in 7-bit US-ASCII,
            the UTF-8 encoding is identical to the
            US-ASCII encoding.

            UTF-8 may require multiple bytes to represent a
            single character / code point; thus the length
            of this object in octets may be different from
            the number of characters encoded.  Similarly,
            size constraints refer to the number of encoded
            octets, not the number of characters represented
            by an encoding.

            Note that when this TC is used for an object that
            is used or envisioned to be used as an index, then
            a SIZE restriction MUST be specified so that the
            number of sub-identifiers for any object instance
            does not exceed the limit of 128, as defined by
            [RFC1905].

            Note that the size of an SnmpAdminString object is
            measured in octets, not characters.
            "
    SYNTAX       OCTET STRING (SIZE (0..255))
        
-- ProtocolMap now defined in adslLineXTransAtucCap, adslLineXTransAtucConfig,
-- adslLineXTransAtucConfig and adslLineXTransAturCap because of
-- browser interpretation.

ProtocolMap ::= TEXTUAL-CONVENTION
    STATUS       current
    DESCRIPTION
        "A set of supported protocols in the Broadcom 
         ADSL chipset:
         Bit[31] : ITU-T ADSL over POTS(G.992.1 Annex A)
         Bit[30] : ITU-T ADSL over ISDN(G.992.1 Annex B)
         Bit[29] : ITU-T ADSL over TCM-ISDN(G.992.1 Annex C)
         Bit[28] : ITU-T ADSL Lite over POTS(G.992.2 Annex A)
         Bit[27] : ITU-T ADSL Lite over TCM-ISDN(G.992.2 Annex C)
         Bit[26] : ITU-T SSDSL over TCM-ISDN(G.992.1 Annex H)
         Bit[25] : ITU-T G.992.1 Annex I
         Bit[25] : ITU-T G.993.2 VDSL2
         Bit[23] : ITU-T SHDSL North America(G.991.2 Annex A)
         Bit[22] : ITU-T SHDSL Europe(G.991.2 Annex B)
         Bit[21] : T1 MCM VDSL
         Bit[19] : ETSI MCM VDSL
         Bit[15] : ITU-T ADSL2 over POTS(G.992.3 Annex A)
         Bit[14] : ITU-T ADSL2 over ISDN(G.992.3 Annex B)
         Bit[13] : ITU-T ADSL2 ADM with POTS(G.992.3 Annex I)
         Bit[12] : ITU-T ADSL2 ADM with ISDN(G.992.3 Annex J)
         Bit[11] : ITU-T ADSL2 Lite over POTS(G.992.4 Annex A)
         Bit[10] : ITU-T ADSL2 Lite ADM with POTS(G.992.4 Annex I)
         Bit[09] : ITU-T ADSL2 RE over POTS(G.992.3 Annex L)
         Bit[07] : ITU-T ADSL2+ over POTS(G.992.5 Annex A)
         Bit[06] : ITU-T ADSL2+ over ISDN(G.992.5 Annex B)
         Bit[05] : ITU-T ADSL2+ over ----(G.992.5 Annex I)
         Bit[02] : SADSL over POTS
         Bit[01] : ANSI ADSL over POTS(ANSI T1.413)
         Bit[00] : ETSI TS 101 388
        "
    SYNTAX      BITS {
        etsiTS101388(0),
        ansiT1413AdslOverPots(1),
        proprietarySadslOverPots(2),
        reserved3(3),
        g9925AnnexMAdsl2PlusOver(4),
        g9925AnnexIAdsl2PlusOver(5),
        g9925AnnexBAdsl2PlusOverIsdn(6),
        g9925AnnexAAdsl2PlusOverPots(7),
        g9923AnnexLAdsl2RENarrowPsdOverPots(8),
        g9923AnnexLAdsl2REOverPots(9),
        g9924AnnexIAdsl2LiteAdmWithPots(10),
        g9924AnnexAAdsl2LiteOverPots(11),
        g9923AnnexMAdsl2AdmWithIsdn(12),
        g9923AnnexIAdsl2AdmWithPots(13),
        g9923AnnexBAdsl2OverIsdn(14),
        g9923AnnexAAdsl2OverPots(15),
        reserved16(16),
        reserved17(17),
        reserved18(18),
        etsiMcmVDSL(19),
        reserved20(20),
        t1McmVDSL(21),
        g99212AnnexBShdslOverTcmIsdnEu(22),
        g99212AnnexAShdslOverTcmIsdnUs(23),
        g9923VDSL2(24),
        g9921AnnexISsdslOverTcmIsdn(25),
        g9921AnnexHSsdslOverTcmIsdn(26),
        g9922AnnexCAdslLiteOverTcmIsdn(27),
        g9922AnnexAAdslLiteOverPots(28),
        g9921AnnexCAdslOverTcmIsdn(29),
        g9921AnnexBAdslOverIsdn(30),
        g9921AnnexAAdslOverPots(31)
    }

--******************************************************************
-- ADSL ATU-C Physical Extension
--******************************************************************
adslAtucPhysXTable OBJECT-TYPE
      SYNTAX     SEQUENCE OF AdslAtucPhysXEntry
      MAX-ACCESS not-accessible
      STATUS     current
      DESCRIPTION
      "This table provides extra information in relation 
       to the adslAtucPhysTable for ADSL lines."
      ::= { adslXObjects 1 }

adslAtucPhysXEntry OBJECT-TYPE
      SYNTAX AdslAtucPhysXEntry
      MAX-ACCESS  not-accessible
      STATUS      current
      DESCRIPTION
      "An entry in adslAtucPhysXTable."
      INDEX { lineIndex }
      ::= { adslAtucPhysXTable 1 }

AdslAtucPhysXEntry ::=
      SEQUENCE {
        adslAtucPhysXPreviousSnrMgn             INTEGER,
        adslAtucPhysXPreviousOutputPwr          INTEGER,
        adslAtucPhysXBitAllocTable              OCTET STRING,
        adslAtucPhysXSnr                        OCTET STRING,
        adslAtucPhysXLoopAtn               		INTEGER
        }

adslAtucPhysXPreviousSnrMgn OBJECT-TYPE
      SYNTAX      INTEGER (-640..640)
      UNITS       "tenth dB"
      MAX-ACCESS  read-only
      STATUS      current
      DESCRIPTION
      "This object contains the previous signal to 
       noise margin for the ATU-C, i.e the total SNR 
       margin recorded when the last synchronisation of 
       the line was carried out."
      ::= { adslAtucPhysXEntry 1 }

adslAtucPhysXPreviousOutputPwr OBJECT-TYPE
      SYNTAX      INTEGER (-310..310)
      UNITS       "tenth dBm"
      MAX-ACCESS  read-only
      STATUS      current
      DESCRIPTION
      "This object contains the previous measured total 
       output power transmitted by the ATU-C, i.e the total 
       output power recorded when the last synchronisation 
       of the line was carried out."
      ::= { adslAtucPhysXEntry 2 } 
      
adslAtucPhysXBitAllocTable OBJECT-TYPE
      SYNTAX      OCTET STRING  (SIZE (64))
      MAX-ACCESS  read-only
      STATUS      deprecated
      DESCRIPTION
      "Upstream bit allocation table.
       Substituted by adslAtucPhysXBitAllocation in HMI 9.x"
      ::= { adslAtucPhysXEntry 3 } 
    
adslAtucPhysXSnr OBJECT-TYPE
      SYNTAX      OCTET STRING (SIZE (128))
      UNITS       "1/256 dB" 
      MAX-ACCESS  read-only
      STATUS      deprecated
      DESCRIPTION
      "SNR measured in the upstream band. There are 64 tones in
       the upstream band and every tone is represented by 4	octets.
       Substituted by adslAtucPhysXToneSnrUs in HMI 9.x"
      ::= { adslAtucPhysXEntry 4 }     

adslAtucPhysXLoopAtn OBJECT-TYPE
      SYNTAX      INTEGER (0..630)
      UNITS       "tenth dB"
      MAX-ACCESS  read-only
      STATUS      current
      DESCRIPTION
      "Upstream loop attenuation. Measured difference in the
      total power transmitted by the peer ATU and the total
      power received by this ATU."
      ::= { adslAtucPhysXEntry 5 }     

      
--******************************************************************
-- ADSL ATU-R Physical Extension
--******************************************************************
adslAturPhysXTable OBJECT-TYPE
      SYNTAX     SEQUENCE OF AdslAturPhysXEntry
      MAX-ACCESS not-accessible
      STATUS     current
      DESCRIPTION
      "This table provides extra information in relation to 
       the adslAturPhysTable for ADSL lines."
      ::= { adslXObjects 2 }

adslAturPhysXEntry OBJECT-TYPE
      SYNTAX AdslAturPhysXEntry
      MAX-ACCESS  not-accessible
      STATUS      current
      DESCRIPTION
      "An entry in adslAturPhysXTable."
      INDEX { lineIndex }
      ::= { adslAturPhysXTable 1 }

AdslAturPhysXEntry ::=
      SEQUENCE {
        -- adslLineTransAturCapabilities            AdslTransmissionModeType,
        adslAturPhysXPreviousSnrMgn             INTEGER,
        adslAturPhysXPreviousOutputPwr          INTEGER,
        adslAturPhysXBitAllocTable              OCTET STRING,
        adslAturPhysXBitAllocTableExt           OCTET STRING,
        adslAturPhysXLoopAtn               		INTEGER
        }

--adslLineTransAturCapabilities OBJECT-TYPE
--      SYNTAX      AdslTransmissionModeType
--      MAX-ACCESS  read-only
--      STATUS      current
--      DESCRIPTION
--      "The transmission modes, represented by a
--       bitmask that the ATU-R is capable of
--       supporting.  The modes available are limited
--       by the design of the equipment."
--      REFERENCE "Section 7.3.2 ITU G.997.1"
--      ::= { adslAturPhysXEntry 1 }

adslAturPhysXPreviousSnrMgn OBJECT-TYPE
      SYNTAX      INTEGER (-640..640)
      UNITS       "tenth dB"
      MAX-ACCESS  read-only
      STATUS      current
      DESCRIPTION
      "This object contains the previous signal to 
       noise margin for the ATU-R, i.e the total SNR 
       margin recorded when the last synchronisation 
       of the line was carried out."
      ::= { adslAturPhysXEntry 2 }

adslAturPhysXPreviousOutputPwr OBJECT-TYPE
      SYNTAX      INTEGER (-310..310)
      UNITS       "tenth dBm"
      MAX-ACCESS  read-only
      STATUS      current
      DESCRIPTION
      "This object contains the previous measured 
       total output power transmitted by the ATU-R, 
       i.e the total output power recorded when the 
       last synchronisation of the line was carried out."
      ::= { adslAturPhysXEntry 3 }

adslAturPhysXBitAllocTable OBJECT-TYPE
      SYNTAX      OCTET STRING (SIZE (256))
      MAX-ACCESS  read-only
      STATUS      deprecated
      DESCRIPTION
      "Downstream bit allocation table, tones 0-255
       Substituted by adslAturPhysXBitAllocation in HMI 9.x"
      ::= { adslAturPhysXEntry 4 }     

adslAturPhysXBitAllocTableExt OBJECT-TYPE
      SYNTAX      OCTET STRING (SIZE (256))
      MAX-ACCESS  read-only
      STATUS      deprecated
      DESCRIPTION
      "Downstream bit allocation table, tones 256-511
       Substituted by adslAturPhysXBitAllocation in HMI 9.x"
      ::= { adslAturPhysXEntry 5 }     

adslAturPhysXLoopAtn OBJECT-TYPE
      SYNTAX      INTEGER (0..630)
      UNITS       "tenth dB"
      MAX-ACCESS  read-only
      STATUS      current
      DESCRIPTION
      "Downstream loop attenuation. Measured difference in the
      total power transmitted by this ATU and the total	power
      received by the peer ATU."
      ::= { adslAturPhysXEntry 6 }     
      
      
--******************************************************************
-- ADSL Line Configuration Profile Extension
--******************************************************************
adslLineConfProfileXTable OBJECT-TYPE
      SYNTAX     SEQUENCE OF AdslLineConfProfileXEntry
      MAX-ACCESS not-accessible
      STATUS     current
      DESCRIPTION
      "This table provides extra information in relation 
       to the adslLineConfProfileTable for ADSL line 
       configuration profile."
      ::= { adslXObjects 3 }

adslLineConfProfileXEntry OBJECT-TYPE
      SYNTAX AdslLineConfProfileXEntry
      MAX-ACCESS  not-accessible
      STATUS      current
      DESCRIPTION
      "Each entry corresponds to an ADSL line 
       configuration profile. Each profile contains a 
       set of ADSL line configuration parameters.  
       The configuration parameters in a profile are
       applied to those lines referencing that profile."
      AUGMENTS { adslLineConfProfileEntry }
      ::= {adslLineConfProfileXTable 1 }

AdslLineConfProfileXEntry ::=
      SEQUENCE {
        adslConfXName                     SnmpAdminString,
        adslConfXAtucFrequencyBins        DisplayString,
        adslConfXAturFrequencyBins        DisplayString,
        adslConfXFrequencyBins            DisplayString,
        adslPowerManagementMode			  INTEGER,
        adslPrmMode			  			  INTEGER,
        adslPrmPower		  			  INTEGER
        }

adslConfXName OBJECT-TYPE
      SYNTAX     SnmpAdminString (SIZE(1..32))
      MAX-ACCESS read-only
      STATUS     current
      DESCRIPTION
      "This object is the unique profile name 
       associated with this profile."
      ::= { adslLineConfProfileXEntry 1}
      
adslConfXAtucFrequencyBins OBJECT-TYPE
      SYNTAX      DisplayString
      MAX-ACCESS  read-write
      STATUS      current
      DESCRIPTION
      "This object consists of a bitmap of 512 bits, 
       where each bit disables or enables one carrier 
       in the downstream (ATU-C) direction. 1 enables 
       the carrier and 0 disables it.
       Each bitmap is represented as a list of 64 bytes, 
       each representing a bitmap of 8 bits. The first 
       byte of the list represents carriers 0-7, the second 
       byte represents carriers 8-15, etc. The last byte 
       represents carriers 504-511. In each byte, the LSB
       represents the lowest carrier in the range, while 
       the MSB represents the highest carrier in the range."
      ::= { adslLineConfProfileXEntry 2 }

adslConfXAturFrequencyBins OBJECT-TYPE
      SYNTAX      DisplayString
      MAX-ACCESS  read-write
      STATUS      current
      DESCRIPTION
      "This object consists of a bitmap of 64 bits, 
       where each bit disables or enables one carrier 
       in the upstream (ATU-R) direction. 1 enables the 
       carrier and 0 disables it.
       Each bitmap is represented as a list of 8 bytes, 
       each representing a bitmap of 8 bits. The first byte 
       of the list represents carriers 0-7, the second byte 
       represents carriers 8-15, etc. The last byte represents 
       carriers 56-63. In each byte, the LSB represents the 
       lowest carrier in the range, while the MSB represents 
       the highest carrier in the range."
      ::= { adslLineConfProfileXEntry 3 }

adslConfXFrequencyBins OBJECT-TYPE
      SYNTAX      DisplayString
      MAX-ACCESS  read-write
      STATUS      obsolete
      DESCRIPTION
      "This object consists of a bitmap of 256 bits,
       where each bit disables or enables one carrier.
       One enables the carrier and zero disables it.
       The distribution between up- and downstream
       carriers is autonomously done in the CO-chipset,
       based upon the selected protocol.
       Each bitmap is represented as a list of 32 bytes, 
       each representing a bitmap of 8 bits. The first 
       byte of the list represents carriers 0-7, the second 
       byte represents carriers 8-15, etc. The last byte 
       represents carriers 248-255. In each byte, the LSB
       represents the lowest carrier in the range, while
       the MSB represents the highest carrier in the range."
      ::= { adslLineConfProfileXEntry 4 }

adslPowerManagementMode OBJECT-TYPE
      SYNTAX      INTEGER { disableL2AndL3(0), enableL3(1), enableL2(2), enableL2AndL3(3) }
      MAX-ACCESS  read-write
      STATUS      current
      DESCRIPTION
      "Power Management State Enabling (PMMode) as defined in
       G.997.1 (7.3.1.1.4). Only L2 mode is supported."
      ::= { adslLineConfProfileXEntry 5 }

adslPrmMode OBJECT-TYPE
      SYNTAX      INTEGER { disablePrmProtect(0), enable12kHzPrmProtect(1), enable16kHzPrmProtect(2) }
      MAX-ACCESS  read-write
      STATUS      current
      DESCRIPTION
      "Disable or enable protection for a specific PRM frequency "
      ::= { adslLineConfProfileXEntry 6 }

adslPrmPower OBJECT-TYPE
      SYNTAX      INTEGER
      MAX-ACCESS  read-write
      STATUS      current
      DESCRIPTION
      "Sets the power level of the PRM signal.
       Approximation: prmPower ~ 1000 * (Vrms^2).
       Valid range: 0 to (2E32)-1."
      ::= { adslLineConfProfileXEntry 7 }
      
--******************************************************************
-- ADSL Line Alarm Configuration Profile Extension
--******************************************************************
adslLineAlarmConfProfileXTable OBJECT-TYPE
      SYNTAX     SEQUENCE OF AdslLineAlarmConfProfileXEntry
      MAX-ACCESS not-accessible
      STATUS     current
      DESCRIPTION
          "This table provides extra information in relation 
      to the adslLineAlarmConfProfileTable for an ADSL
      alarm configuration profile."
      ::= { adslXObjects 4 }

adslLineAlarmConfProfileXEntry OBJECT-TYPE
      SYNTAX AdslLineAlarmConfProfileXEntry
      MAX-ACCESS  not-accessible
      STATUS      current
      DESCRIPTION
      "Each entry corresponds to an ADSL line alarm 
       configuration profile.  Each profile contains a 
       set of ADSL line alarm configuration parameters.  
       The configuration parameters in a profile are
       applied to those lines referencing that profile."
      AUGMENTS { adslLineAlarmConfProfileEntry }
      ::= {adslLineAlarmConfProfileXTable 1 }

AdslLineAlarmConfProfileXEntry ::=
      SEQUENCE {
        adslAlarmConfXName                      SnmpAdminString,
        adslAlarmConfXAtucThres1DayES           INTEGER,
        adslAlarmConfXAturThres1DayES           INTEGER,
        adslAlarmConfXAtucThres1DaySesL         INTEGER,
        adslAlarmConfXAturThres1DaySesL         INTEGER,
        adslAlarmConfXAtucThres1DayUasL         INTEGER,
        adslAlarmConfXAturThres1DayUasL         INTEGER,
        adslAlarmConfXAtucThres1DayLofs         INTEGER,
        adslAlarmConfXAturThres1DayLofs         INTEGER,
        adslAlarmConfXAtucThres1DayLoss         INTEGER,
        adslAlarmConfXAturThres1DayLoss         INTEGER,
        adslAlarmConfXAtucThres1DayLols         INTEGER,
        adslAlarmConfXAturThres1DayLprs         INTEGER
        }

adslAlarmConfXName OBJECT-TYPE
      SYNTAX     SnmpAdminString (SIZE(1..32))
      MAX-ACCESS read-only
      STATUS     current
      DESCRIPTION
      "This object is the unique profile name 
       associated with this profile."
      ::= { adslLineAlarmConfProfileXEntry 1} 
      
adslAlarmConfXAtucThres1DayES OBJECT-TYPE
      SYNTAX      INTEGER (0..86400)
      UNITS       "seconds"
      MAX-ACCESS  read-write
      STATUS      current
      DESCRIPTION
      "The number of Errored Seconds encountered by an
       ADSL interface within the 24 hour (1 day) data 
       collection period, which causes the SNMP agent to send 
       an adslAtucPerfXESsThresh1DayTrap.
       One trap will be sent per interval per interface.
       A value of `0' will disable the trap."
      ::= { adslLineAlarmConfProfileXEntry 2 }

adslAlarmConfXAturThres1DayES OBJECT-TYPE
      SYNTAX      INTEGER (0..86400)
      UNITS       "seconds"
      MAX-ACCESS  read-write
      STATUS      current
      DESCRIPTION
      "The number of Errored Seconds encountered by an
       ADSL interface within the 24 hour (1 day) data 
       collection period, which causes the SNMP agent to send 
       an adslAturPerfXESsThresh1DayTrap.
       One trap will be sent per interval per interface.
       A value of `0' will disable the trap."
      ::= { adslLineAlarmConfProfileXEntry 3 }

adslAlarmConfXAtucThres1DaySesL OBJECT-TYPE
      SYNTAX      INTEGER (0..86400) 
      UNITS       "seconds"
      MAX-ACCESS  read-write
      STATUS      current
      DESCRIPTION
      "The number of Severely Errored Seconds encountered by an
       ADSL interface within the 24 hour (1 day) data 
       collection period, which causes the SNMP agent to send 
       an adslAturPerfXSesThresh1DayTrap.
       One trap will be sent per interval per interface.
       A value of `0' will disable the trap."
      ::= { adslLineAlarmConfProfileXEntry 7 }

adslAlarmConfXAturThres1DaySesL OBJECT-TYPE
      SYNTAX      INTEGER (0..86400)
      UNITS       "seconds"
      MAX-ACCESS  read-write
      STATUS      current
      DESCRIPTION
      "The number of Severely Errored Seconds encountered by an
       ADSL interface within the 24 hour (1 day) data 
       collection period, which causes the SNMP agent to send 
       an adslAturPerfXSesThresh1DayTrap.
       One trap will be sent per interval per interface.
       A value of `0' will disable the trap."
      ::= { adslLineAlarmConfProfileXEntry 8 }

adslAlarmConfXAtucThres1DayUasL OBJECT-TYPE
      SYNTAX      INTEGER (0..86400)
      UNITS       "seconds"
      MAX-ACCESS  read-write
      STATUS      current
      DESCRIPTION
      "The number of Unavailable Seconds encountered by an
       ADSL interface within the 24 hour (1 day) data 
       collection period, which causes the SNMP agent to send 
       an adslAturPerfXUasThresh1DayTrap.
       One trap will be sent per interval per interface.
       A value of `0' will disable the trap."
      ::= { adslLineAlarmConfProfileXEntry 9 }
      
adslAlarmConfXAturThres1DayUasL OBJECT-TYPE
      SYNTAX      INTEGER (0..86400)
      UNITS       "seconds"
      MAX-ACCESS  read-write
      STATUS      current
      DESCRIPTION
      "The number of Unavailable Seconds encountered by an
       ADSL interface within the 24 hour (1 day) data 
       collection period, which causes the SNMP agent to send 
       an adslAturPerfXUasThresh1DayTrap.
       One trap will be sent per interval per interface.
       A value of `0' will disable the trap."
      ::= { adslLineAlarmConfProfileXEntry 10 }

adslAlarmConfXAtucThres1DayLofs OBJECT-TYPE
      SYNTAX      INTEGER (0..86400)
      UNITS       "seconds"
      MAX-ACCESS  read-write
      STATUS      current
      DESCRIPTION
      "The number of Loss of Frame Seconds encountered by an
       ADSL interface within the 24 hour (1 day) data 
       collection period, which causes the SNMP agent to send 
       an adslAtucPerfXLofsThresh1DayTrap.
       One trap will be sent per interval per interface.
       A value of `0' will disable the trap."
      ::= { adslLineAlarmConfProfileXEntry 15 }

adslAlarmConfXAturThres1DayLofs OBJECT-TYPE
      SYNTAX      INTEGER (0..86400)
      UNITS       "seconds"
      MAX-ACCESS  read-write
      STATUS      current
      DESCRIPTION
      "The number of Loss of Frame Seconds encountered by an
       ADSL interface within the 24 hour (1 day) data 
       collection period, which causes the SNMP agent to send 
       an adslAturPerfXLofsThresh1DayTrap.
       One trap will be sent per interval per interface.
       A value of `0' will disable the trap."
      ::= { adslLineAlarmConfProfileXEntry 20 }

adslAlarmConfXAtucThres1DayLoss OBJECT-TYPE
      SYNTAX      INTEGER (0..86400) 
      UNITS       "seconds"
      MAX-ACCESS  read-write
      STATUS      current
      DESCRIPTION
      "The number of Loss of Signal Seconds encountered by an
       ADSL interface within the 24 hour (1 day) data 
       collection period, which causes the SNMP agent to send 
       an adslAtucPerfXLossThresh1DayTrap.
       One trap will be sent per interval per interface.
       A value of `0' will disable the trap."
      ::= { adslLineAlarmConfProfileXEntry 25 }

adslAlarmConfXAturThres1DayLoss OBJECT-TYPE
      SYNTAX      INTEGER (0..86400)
      UNITS       "seconds"
      MAX-ACCESS  read-write
      STATUS      current
      DESCRIPTION
      "The number of Loss of Signal Seconds encountered by an
       ADSL interface within the 24 hour (1 day) data 
       collection period, which causes the SNMP agent to send 
       an adslAturPerfXLossThresh1DayTrap.
       One trap will be sent per interval per interface.
       A value of `0' will disable the trap."
      ::= { adslLineAlarmConfProfileXEntry 30 }

adslAlarmConfXAtucThres1DayLols OBJECT-TYPE
      SYNTAX      INTEGER (0..86400)
      UNITS       "seconds"
      MAX-ACCESS  read-write
      STATUS      current
      DESCRIPTION
      "The number of Loss of Link Seconds encountered by an
       ADSL interface within the 24 hour (1 day) data 
       collection period, which causes the SNMP agent to send 
       an adslAtucPerfXLolsThresh1DayTrap.
       One trap will be sent per interval per interface.
       A value of `0' will disable the trap."
      ::= { adslLineAlarmConfProfileXEntry 35 }
      
adslAlarmConfXAturThres1DayLprs OBJECT-TYPE
      SYNTAX      INTEGER (0..86400)
      UNITS       "seconds"
      MAX-ACCESS  read-write
      STATUS      current
      DESCRIPTION
      "The number of Loss of Power Seconds encountered by an
       ADSL interface within the 24 hour (1 day) data 
       collection period, which causes the SNMP agent to send 
       an adslAturPerfXLprsThresh1DayTrap.
       One trap will be sent per interval per interface.
       A value of `0' will disable the trap."
      ::= { adslLineAlarmConfProfileXEntry 40 }
      
--******************************************************************
-- ADSL ATU-C Performance Data Extension
--******************************************************************
adslAtucPerfDataXTable OBJECT-TYPE
      SYNTAX     SEQUENCE OF AdslAtucPerfDataXEntry
      MAX-ACCESS not-accessible
      STATUS     current
      DESCRIPTION
      "This table provides extra information in relation 
       to the adslAtucPerfDataTable for each ATU-C."
      ::= { adslXObjects 6 }

adslAtucPerfDataXEntry OBJECT-TYPE
      SYNTAX      AdslAtucPerfDataXEntry
      MAX-ACCESS  not-accessible
      STATUS      current
      DESCRIPTION     
      "An entry in adslAtucPerfDataXTable."
      INDEX  { lineIndex }
      ::= { adslAtucPerfDataXTable 1 }

AdslAtucPerfDataXEntry ::=
      SEQUENCE {
        adslAtucPerfXEcs                        PerfCurrentCount,
        adslAtucPerfXCurr15MinEcs               PerfCurrentCount,
        adslAtucPerfXCurr1DayEcs                AdslPerfCurrDayCount,
        adslAtucPerfXPrev1DayEcs                AdslPerfPrevDayCount,
        adslAtucPerfX1DayValidIntervals         INTEGER,
        adslAtucPerfX1DayInvalidIntervals       INTEGER
        }
             
adslAtucPerfXEcs OBJECT-TYPE
      SYNTAX      PerfCurrentCount  
      MAX-ACCESS  read-only
      STATUS      current
      DESCRIPTION
      "Count of forward error correction seconds 
       since agent reset."
      ::= { adslAtucPerfDataXEntry 1 }

adslAtucPerfXCurr15MinEcs OBJECT-TYPE
      SYNTAX      PerfCurrentCount
      UNITS       "seconds"
      MAX-ACCESS  read-only
      STATUS      current
      DESCRIPTION
      "Count of forward error correction seconds 
       in the current 15 minute interval."
      ::= { adslAtucPerfDataXEntry 2 }

adslAtucPerfXCurr1DayEcs OBJECT-TYPE
      SYNTAX      AdslPerfCurrDayCount
      UNITS       "seconds"
      MAX-ACCESS  read-only
      STATUS      current
      DESCRIPTION
      "Count of the number of forward error correction 
       seconds during the current day as measured by 
       adslAtucPerfCurr1DayTimeElapsed."
      ::= { adslAtucPerfDataXEntry 3 }

adslAtucPerfXPrev1DayEcs OBJECT-TYPE
      SYNTAX      AdslPerfPrevDayCount
      UNITS       "seconds"
      MAX-ACCESS  read-only
      STATUS      current
      DESCRIPTION
      "Count of forward error correction seconds in 
       the interval within the most recent previous
       1-day period."
      ::= { adslAtucPerfDataXEntry 4 }

adslAtucPerfX1DayValidIntervals OBJECT-TYPE
      SYNTAX      INTEGER(0..3)
      MAX-ACCESS  read-only
      STATUS      current
      DESCRIPTION
      "The number of previous 1 day intervals in the 1 day
       interval table for which data was collected. Given
       that <n> is the maximum # of intervals supported.
       The value will be <n> unless the measurement was
       (re-)started within the last <n> days, in which
       case the value will be the number of complete 1-day
       intervals for which the agent has at least
       some data."
      ::= { adslAtucPerfDataXEntry 10 }

adslAtucPerfX1DayInvalidIntervals OBJECT-TYPE
      SYNTAX      INTEGER(0..3)
      MAX-ACCESS  read-only
      STATUS      current
      DESCRIPTION
      "The number of intervals in the range from
       0 to the value of adslAtucPerfX1DayValidIntervals
       for which no data is available."
      ::= { adslAtucPerfDataXEntry 15 }

--******************************************************************
-- ADSL ATU-R Performance Data Extension
--******************************************************************
adslAturPerfDataXTable OBJECT-TYPE
      SYNTAX     SEQUENCE OF AdslAturPerfDataXEntry
      MAX-ACCESS not-accessible
      STATUS     current
      DESCRIPTION
      "This table provides extra information in relation 
       to the adslAturPerfDataTable for each ATU-R."
      ::= { adslXObjects 7 }

adslAturPerfDataXEntry OBJECT-TYPE
      SYNTAX      AdslAturPerfDataXEntry
      MAX-ACCESS  not-accessible
      STATUS      current
      DESCRIPTION     
      "An entry in adslAturPerfDataXTable."
      INDEX  { lineIndex }
      ::= { adslAturPerfDataXTable 1 }

AdslAturPerfDataXEntry ::=
      SEQUENCE  {
        adslAturPerfXEcs                        PerfCurrentCount,
        adslAturPerfXCurr15MinEcs               PerfCurrentCount,
        adslAturPerfXCurr1DayEcs                AdslPerfCurrDayCount,
        adslAturPerfXPrev1DayEcs                AdslPerfPrevDayCount,
        adslAturPerfX1DayValidIntervals         INTEGER,
        adslAturPerfX1DayInvalidIntervals       INTEGER
        }

adslAturPerfXEcs OBJECT-TYPE
      SYNTAX      PerfCurrentCount  
      MAX-ACCESS  read-only
      STATUS      current
      DESCRIPTION
      "Count of forward error correction seconds 
       since agent reset."
      ::= { adslAturPerfDataXEntry 1 }

adslAturPerfXCurr15MinEcs OBJECT-TYPE
      SYNTAX      PerfCurrentCount
      UNITS       "seconds"
      MAX-ACCESS  read-only
      STATUS      current
      DESCRIPTION
      "Count of forward error correction seconds 
       in the current 15 minute interval."
      ::= { adslAturPerfDataXEntry 2 }

adslAturPerfXCurr1DayEcs OBJECT-TYPE
      SYNTAX      AdslPerfCurrDayCount
      UNITS       "seconds"
      MAX-ACCESS  read-only
      STATUS      current
      DESCRIPTION
      "Count of the number of forward error correction 
       seconds during the current day as measured by 
       adslAturPerfCurr1DayTimeElapsed."
      ::= { adslAturPerfDataXEntry 3 }

adslAturPerfXPrev1DayEcs OBJECT-TYPE
      SYNTAX      AdslPerfPrevDayCount
      UNITS       "seconds"
      MAX-ACCESS  read-only
      STATUS      current
      DESCRIPTION
      "Count of forward error correction seconds in 
       the interval within the most recent previous
       1-day period."
      ::= { adslAturPerfDataXEntry 4 }

adslAturPerfX1DayValidIntervals OBJECT-TYPE
      SYNTAX      INTEGER(0..3)
      MAX-ACCESS  read-only
      STATUS      current
      DESCRIPTION
      "The number of previous 1 day intervals in the 1 day
       interval table for which data was collected.  Given
       that <n> is the maximum # of intervals supported.
       The value will be <n> unless the measurement was
       (re-)started within the last <n> days, in which
       case the value will be the number of complete 1-day
       intervals for which the agent has at least
       some data."
      ::= { adslAturPerfDataXEntry 10 }

adslAturPerfX1DayInvalidIntervals OBJECT-TYPE
      SYNTAX      INTEGER(0..3)
      MAX-ACCESS  read-only
      STATUS      current
      DESCRIPTION
      "The number of intervals in the range from
       0 to the value of adslAturPerfX1DayValidIntervals
       for which no data is available."
      ::= { adslAturPerfDataXEntry 15 }

--******************************************************************
-- ADSL ATU-C Interval Extension
--******************************************************************
adslAtucIntervalXTable   OBJECT-TYPE
      SYNTAX          SEQUENCE OF AdslAtucIntervalXEntry
      MAX-ACCESS      not-accessible
      STATUS          current
      DESCRIPTION
      "This table provides extra information in 
       relation to the adslAtucIntervalTable for 
       each ATU-C performance collection interval.
       Performance Data Interval number 1 is the
       the most recent previous interval; interval
       96 is 24 hours ago. Intervals 2..96 are
       optional. Interval number 1 is the only
       interval used currently."
      ::= { adslXObjects 8 }

adslAtucIntervalXEntry   OBJECT-TYPE
      SYNTAX          AdslAtucIntervalXEntry
      MAX-ACCESS      not-accessible
      STATUS          current
      DESCRIPTION    
      "An entry in the adslAtucIntervalXTable."
      INDEX  { lineIndex, adslAtucIntervalNumber }
      ::= { adslAtucIntervalXTable 1 }

AdslAtucIntervalXEntry ::=
      SEQUENCE {
        adslAtucIntervalXEcs                        PerfIntervalCount
        }

adslAtucIntervalXEcs OBJECT-TYPE
      SYNTAX      PerfIntervalCount
      MAX-ACCESS  read-only
      STATUS      current
      DESCRIPTION
      "Count of forward error correction seconds 
       in the interval."
      ::= { adslAtucIntervalXEntry 1 }

--******************************************************************
-- ADSL ATU-R Interval Extension
--******************************************************************
adslAturIntervalXTable   OBJECT-TYPE
      SYNTAX          SEQUENCE OF AdslAturIntervalXEntry
      MAX-ACCESS      not-accessible
      STATUS          current
      DESCRIPTION
      "This table provides extra information in 
       relation to the adslAturIntervalTable for 
       each ATU-R performance collection interval.
       Performance Data Interval number 1 is the
       the most recent previous interval; interval
       96 is 24 hours ago. Intervals 2..96 are
       optional. Interval number 1 is the only
       interval used currently."
      ::= { adslXObjects 9 }

adslAturIntervalXEntry   OBJECT-TYPE
      SYNTAX          AdslAturIntervalXEntry
      MAX-ACCESS      not-accessible
      STATUS          current
      DESCRIPTION     
      "An entry in the adslAturIntervalXTable."
      INDEX  { lineIndex, adslAturIntervalNumber }
      ::= { adslAturIntervalXTable 1 }

AdslAturIntervalXEntry ::=
      SEQUENCE {
        adslAturIntervalXEcs                    PerfIntervalCount
        }

adslAturIntervalXEcs OBJECT-TYPE
      SYNTAX      PerfIntervalCount
      MAX-ACCESS  read-only
      STATUS      current
      DESCRIPTION
      "Count of forward error correction seconds 
       in the interval."
      ::= { adslAturIntervalXEntry 1 }

--******************************************************************
-- ADSL ATU-C Channel Performance Data Extension
--******************************************************************
adslAtucChanPerfDataXTable   OBJECT-TYPE
      SYNTAX          SEQUENCE OF AdslAtucChanPerfDataXEntry
      MAX-ACCESS      not-accessible
      STATUS          current
      DESCRIPTION
      "This table provides extra ATU-C channel information 
       in relation to the adslAtucChanPerfDataTable.
       ADSL channel interfaces are those ifEntries where 
       ifType is equal to adslInterleave(124) or 
       adslFast(125)."
      ::= { adslXObjects 10 }

adslAtucChanPerfDataXEntry   OBJECT-TYPE
      SYNTAX          AdslAtucChanPerfDataXEntry
      MAX-ACCESS      not-accessible
      STATUS          current
      DESCRIPTION     
      "An entry in the adslAtucChanPerfDataXTable."
      INDEX  { lineIndex }
      ::= { adslAtucChanPerfDataXTable 1 }

AdslAtucChanPerfDataXEntry ::=
      SEQUENCE  {
        adslAtucChanPerfXCurr15MinHecv              PerfCurrentCount,
        adslAtucChanPerfXCurr15MinTotalCells        PerfCurrentCount,
        adslAtucChanPerfXCurr15MinTotalUserCells    PerfCurrentCount,
        adslAtucChanPerfXCurr15MinOverFlowCells     PerfCurrentCount,
        adslAtucChanPerfXCurr15MinIdleCells         PerfCurrentCount,
        adslAtucChanPerfXCurr15MinIdleCellBitErrors PerfCurrentCount,
        adslAtucChanPerfXCurr1DayHecv               AdslPerfCurrDayCount,
        adslAtucChanPerfXCurr1DayTotalCells         AdslPerfCurrDayCount,
        adslAtucChanPerfXCurr1DayTotalUserCells     AdslPerfCurrDayCount,
        adslAtucChanPerfXCurr1DayOverFlowCells      AdslPerfCurrDayCount,
        adslAtucChanPerfXCurr1DayIdleCells          AdslPerfCurrDayCount,
        adslAtucChanPerfXCurr1DayIdleCellBitErr     AdslPerfCurrDayCount,
        adslAtucChanPerfXPrev1DayHecv               AdslPerfPrevDayCount,
        adslAtucChanPerfXPrev1DayTotalCells         AdslPerfPrevDayCount,
        adslAtucChanPerfXPrev1DayTotalUserCells     AdslPerfPrevDayCount,
        adslAtucChanPerfXPrev1DayOverFlowCells      PerfCurrentCount,
        adslAtucChanPerfXPrev1DayIdleCells          AdslPerfPrevDayCount,
        adslAtucChanPerfXPrev1DayIdleCellBitErr     AdslPerfPrevDayCount
        }

adslAtucChanPerfXCurr15MinHecv OBJECT-TYPE
      SYNTAX      PerfCurrentCount
      MAX-ACCESS  read-only
      STATUS      current
      DESCRIPTION
      "Count of all header error correction violations 
       received on this channel within the current 15 
       minute interval."
      ::= { adslAtucChanPerfDataXEntry 1 }

adslAtucChanPerfXCurr15MinTotalCells OBJECT-TYPE
      SYNTAX      PerfCurrentCount 
      MAX-ACCESS  read-only
      STATUS      current
      DESCRIPTION
      "Count of all ATM cells received on this channel
       within the current 15 minute interval."
      ::= { adslAtucChanPerfDataXEntry 2 }

adslAtucChanPerfXCurr15MinTotalUserCells OBJECT-TYPE
      SYNTAX      PerfCurrentCount 
      MAX-ACCESS  read-only
      STATUS      current
      DESCRIPTION
      "Count of all valid non-idle ATM cells successfuly
       trasmited to the UTOPIA bus within the current 15 
       minute interval."
      ::= { adslAtucChanPerfDataXEntry 3 }    

adslAtucChanPerfXCurr15MinOverFlowCells OBJECT-TYPE
      SYNTAX      PerfCurrentCount 
      MAX-ACCESS  read-only
      STATUS      current
      DESCRIPTION
      "Count the number oc cells discarded due to the
       received UTOPIA FIFO being full within the 
       current 15 minute interval."
      ::= { adslAtucChanPerfDataXEntry 16 }
            
adslAtucChanPerfXCurr15MinIdleCells OBJECT-TYPE
      SYNTAX      PerfCurrentCount 
      MAX-ACCESS  read-only
      STATUS      current
      DESCRIPTION
      "Count of all idle ATM cells received on this channel
       within the current 15 minute interval."
      ::= { adslAtucChanPerfDataXEntry 4 }

adslAtucChanPerfXCurr15MinIdleCellBitErrors OBJECT-TYPE
      SYNTAX      PerfCurrentCount 
      MAX-ACCESS  read-only
      STATUS      current
      DESCRIPTION
      "Count the number of bit errors in the payload of
       the valid idle ATM cells received on this channel
       within the current 15 minute interval.
       An approximate estimate of the BER is given by;
       idleCellBitErrors/(8*48*idleCells)"
      ::= { adslAtucChanPerfDataXEntry 5 }

adslAtucChanPerfXCurr1DayHecv OBJECT-TYPE
      SYNTAX      AdslPerfCurrDayCount
      MAX-ACCESS  read-only
      STATUS      current
      DESCRIPTION
      "Count of all header error correction violations 
       received on this channel during the current day 
       as measured by adslAtucChanPerfCurr1DayTimeElapsed."
      ::= { adslAtucChanPerfDataXEntry 6 }

adslAtucChanPerfXCurr1DayTotalCells OBJECT-TYPE
      SYNTAX      AdslPerfCurrDayCount 
      MAX-ACCESS  read-only
      STATUS      current
      DESCRIPTION
      "Count of all ATM cells received on this channel 
       during the current day."
      ::= { adslAtucChanPerfDataXEntry 7 }

adslAtucChanPerfXCurr1DayTotalUserCells OBJECT-TYPE
      SYNTAX      AdslPerfCurrDayCount 
      MAX-ACCESS  read-only
      STATUS      current
      DESCRIPTION
      "Count of all valid non-idle ATM cells successfuly
       trasmited to the UTOPIA bus during the current day."
      ::= { adslAtucChanPerfDataXEntry 8 }   

adslAtucChanPerfXCurr1DayOverFlowCells OBJECT-TYPE
      SYNTAX      AdslPerfCurrDayCount 
      MAX-ACCESS  read-only
      STATUS      current
      DESCRIPTION
      "Count the number oc cells discarded due to the received
       UTOPIA FIFO being full during the current day."
      ::= { adslAtucChanPerfDataXEntry 17 }

adslAtucChanPerfXCurr1DayIdleCells OBJECT-TYPE
      SYNTAX      AdslPerfCurrDayCount 
      MAX-ACCESS  read-only
      STATUS      current
      DESCRIPTION
      "Count of all idle ATM cells received on this channel
       during the current day."
      ::= { adslAtucChanPerfDataXEntry 9 }

adslAtucChanPerfXCurr1DayIdleCellBitErr OBJECT-TYPE
      SYNTAX      AdslPerfCurrDayCount 
      MAX-ACCESS  read-only
      STATUS      current
      DESCRIPTION
      "Count the number of bit errors in the payload of
       the valid idle ATM cells received on this channel
       during the current day."
      ::= { adslAtucChanPerfDataXEntry 10 }
 
adslAtucChanPerfXPrev1DayHecv OBJECT-TYPE
      SYNTAX      AdslPerfPrevDayCount
      MAX-ACCESS  read-only
      STATUS      current
      DESCRIPTION
          "Count of all header error correction violations 
      blocks received on this channel within the most 
      recent previous 1-day period."
      ::= { adslAtucChanPerfDataXEntry 11 }
 
adslAtucChanPerfXPrev1DayTotalCells OBJECT-TYPE
      SYNTAX      AdslPerfPrevDayCount 
      MAX-ACCESS  read-only
      STATUS      current
      DESCRIPTION
      "Count of all ATM cells received on this channel 
       within the most recent previous 1-day period."
      ::= { adslAtucChanPerfDataXEntry 12 }

adslAtucChanPerfXPrev1DayTotalUserCells OBJECT-TYPE
      SYNTAX      AdslPerfPrevDayCount 
      MAX-ACCESS  read-only
      STATUS      current
      DESCRIPTION
      "Count of all valid non-idle ATM cells successfuly
       trasmited to the UTOPIA bus within the most 
       recent previous 1-day period."
      ::= { adslAtucChanPerfDataXEntry 13 }

adslAtucChanPerfXPrev1DayOverFlowCells OBJECT-TYPE
      SYNTAX      PerfCurrentCount 
      MAX-ACCESS  read-only
      STATUS      current
      DESCRIPTION
      "Count the number oc cells discarded due to the
       received UTOPIA FIFO being full within the most 
       recent previous 1-day period."
      ::= { adslAtucChanPerfDataXEntry 18 }

adslAtucChanPerfXPrev1DayIdleCells OBJECT-TYPE
      SYNTAX      AdslPerfPrevDayCount 
      MAX-ACCESS  read-only
      STATUS      current
      DESCRIPTION
      "Count of all idle ATM cells received on this channel
       within the most recent previous 1-day period."
      ::= { adslAtucChanPerfDataXEntry 14 }

adslAtucChanPerfXPrev1DayIdleCellBitErr OBJECT-TYPE
      SYNTAX      AdslPerfPrevDayCount 
      MAX-ACCESS  read-only
      STATUS      current
      DESCRIPTION
      "Count the number of bit errors in the payload of
       the valid idle ATM cells received on this channel
       within the most recent previous 1-day period."
      ::= { adslAtucChanPerfDataXEntry 15 }

      
--******************************************************************
-- ADSL ATU-R Channel Performance Data Extension
--******************************************************************
adslAturChanPerfDataXTable   OBJECT-TYPE
      SYNTAX          SEQUENCE OF AdslAturChanPerfDataXEntry
      MAX-ACCESS      not-accessible
      STATUS          current
      DESCRIPTION
      "This table provides extra ATU-R channel information 
       in relation to the adslAturChanPerfDataTable.
       ADSL channel interfaces are those ifEntries where 
       ifType is equal to adslInterleave(124) or 
       adslFast(125)."
      ::= { adslXObjects 11 }

adslAturChanPerfDataXEntry   OBJECT-TYPE
      SYNTAX          AdslAturChanPerfDataXEntry
      MAX-ACCESS      not-accessible
      STATUS          current
      DESCRIPTION     
      "An entry in the adslAturChanPerfDataXTable."
      INDEX  { lineIndex }
      ::= { adslAturChanPerfDataXTable 1 }

AdslAturChanPerfDataXEntry ::=
      SEQUENCE  {
        adslAturChanPerfXCurr15MinHecv              PerfCurrentCount,
        adslAturChanPerfXCurr15MinTotalCells        PerfCurrentCount,
        adslAturChanPerfXCurr15MinTotalUserCells    PerfCurrentCount,
        adslAturChanPerfXCurr1DayHecv               AdslPerfCurrDayCount,
        adslAturChanPerfXCurr1DayTotalCells         AdslPerfCurrDayCount,
        adslAturChanPerfXCurr1DayTotalUserCells     AdslPerfCurrDayCount,
        adslAturChanPerfXPrev1DayHecv               AdslPerfPrevDayCount,
        adslAturChanPerfXPrev1DayTotalCells         AdslPerfPrevDayCount,
        adslAturChanPerfXPrev1DayTotalUserCells     AdslPerfPrevDayCount,
        adslAturChanPerfXCurr15MinIdleCellBitErrors PerfCurrentCount,
        adslAturChanPerfXCurr1DayIdleCellBitErr     AdslPerfCurrDayCount,
        adslAturChanPerfXPrev1DayIdleCellBitErr     AdslPerfPrevDayCount
        }

adslAturChanPerfXCurr15MinHecv OBJECT-TYPE
      SYNTAX      PerfCurrentCount
      MAX-ACCESS  read-only
      STATUS      current
      DESCRIPTION
      "Count of all header error correction violations 
       received on this channel within the current 15 
       minute interval."
      ::= { adslAturChanPerfDataXEntry 1 }
    
adslAturChanPerfXCurr15MinTotalCells OBJECT-TYPE
      SYNTAX      PerfCurrentCount 
      MAX-ACCESS  read-only
      STATUS      current
      DESCRIPTION
      "Count of all ATM cells received on this channel
       within the current 15 minute interval."
      ::= { adslAturChanPerfDataXEntry 2 }

adslAturChanPerfXCurr15MinTotalUserCells OBJECT-TYPE
      SYNTAX      PerfCurrentCount 
      MAX-ACCESS  read-only
      STATUS      current
      DESCRIPTION
      "Count of all valid non-idle ATM cells successfuly
       received to the UTOPIA bus within the current 15 
       minute interval."
      ::= { adslAturChanPerfDataXEntry 3 }

adslAturChanPerfXCurr1DayHecv OBJECT-TYPE
      SYNTAX      AdslPerfCurrDayCount
      MAX-ACCESS  read-only
      STATUS      current
      DESCRIPTION
      "Count of all header error correction violations 
       received on this channel during the current day 
       as measured by adslAturChanPerfCurr1DayTimeElapsed."
      ::= { adslAturChanPerfDataXEntry 4 }

adslAturChanPerfXCurr1DayTotalCells OBJECT-TYPE
      SYNTAX      AdslPerfCurrDayCount 
      MAX-ACCESS  read-only
      STATUS      current
      DESCRIPTION
      "Count of all ATM cells received on this channel 
       during the current day."
      ::= { adslAturChanPerfDataXEntry 5 }

adslAturChanPerfXCurr1DayTotalUserCells OBJECT-TYPE
      SYNTAX      AdslPerfCurrDayCount 
      MAX-ACCESS  read-only
      STATUS      current
      DESCRIPTION
      "Count of all valid non-idle ATM cells successfuly
       received to the UTOPIA bus during the current day."
      ::= { adslAturChanPerfDataXEntry 6 }
    
adslAturChanPerfXPrev1DayHecv OBJECT-TYPE
      SYNTAX      AdslPerfPrevDayCount
      MAX-ACCESS  read-only
      STATUS      current
      DESCRIPTION
      "Count of all header error correction violations 
       received on this channel within the most 
       recent previous 1-day period."
      ::= { adslAturChanPerfDataXEntry 7 }

adslAturChanPerfXPrev1DayTotalCells OBJECT-TYPE
      SYNTAX      AdslPerfPrevDayCount 
      MAX-ACCESS  read-only
      STATUS      current
      DESCRIPTION
      "Count of all ATM cells received on this channel 
       within the most recent previous 1-day period."
      ::= { adslAturChanPerfDataXEntry 8 }

adslAturChanPerfXPrev1DayTotalUserCells OBJECT-TYPE
      SYNTAX      AdslPerfPrevDayCount 
      MAX-ACCESS  read-only
      STATUS      current
      DESCRIPTION
      "Count of all valid non-idle ATM cells successfuly
       received to the UTOPIA bus within the most 
       recent previous 1-day period."
      ::= { adslAturChanPerfDataXEntry 9 }

adslAturChanPerfXCurr15MinIdleCellBitErrors OBJECT-TYPE
      SYNTAX      PerfCurrentCount 
      MAX-ACCESS  read-only
      STATUS      current
      DESCRIPTION
      "Count the number of bit errors in the payload of
       the valid idle ATM cells received on this channel
       within the current 15 minute interval.
       An approximate estimate of the BER is given by;
       idleCellBitErrors/(8*48*idleCells)
       Applies to ADSL2 only"
      ::= { adslAturChanPerfDataXEntry 10 }
      
adslAturChanPerfXCurr1DayIdleCellBitErr OBJECT-TYPE
      SYNTAX      AdslPerfCurrDayCount 
      MAX-ACCESS  read-only
      STATUS      current
      DESCRIPTION
      "Count the number of bit errors in the payload of
       the valid idle ATM cells received on this channel
       during the current day. Applies to ADSL2 only."
      ::= { adslAturChanPerfDataXEntry 11 }
      
adslAturChanPerfXPrev1DayIdleCellBitErr OBJECT-TYPE
      SYNTAX      AdslPerfPrevDayCount 
      MAX-ACCESS  read-only
      STATUS      current
      DESCRIPTION
      "Count the number of bit errors in the payload of
       the valid idle ATM cells received on this channel
       within the most recent previous 1-day period.
       Applies to ADSL2 only."
      ::= { adslAturChanPerfDataXEntry 12 }

--******************************************************************
-- ADSL ATU-C Channel Interval Extension
--******************************************************************
adslAtucChanIntervalXTable   OBJECT-TYPE
      SYNTAX          SEQUENCE OF AdslAtucChanIntervalXEntry
      MAX-ACCESS      not-accessible
      STATUS          current
      DESCRIPTION
      "This table provides extra information in 
       relation to the adslAtucChanIntervalTable 
       for each ATU-C channel's performance 
       collection interval.
       ADSL channel interfaces are those ifEntries where 
       ifType is equal to adslInterleave(124) or 
       adslFast(125).
       Performance Data Interval number 1 is the
       the most recent previous interval; interval
       96 is 24 hours ago. Intervals 2..96 are
       optional. Interval number 1 is the only
       interval used currently."
      ::= { adslXObjects 12 }

adslAtucChanIntervalXEntry   OBJECT-TYPE
      SYNTAX          AdslAtucChanIntervalXEntry
      MAX-ACCESS      not-accessible
      STATUS          current
      DESCRIPTION     
     "An entry in the adslAtucChanIntervalXTable."
      INDEX  { lineIndex, adslAtucChanIntervalNumber }
      ::= { adslAtucChanIntervalXTable 1 }

AdslAtucChanIntervalXEntry ::=
      SEQUENCE {
        adslAtucChanIntervalXHecv                 PerfIntervalCount,
        adslAtucChanIntervalXTotalCells           PerfIntervalCount,
        adslAtucChanIntervalXTotalUserCells       PerfIntervalCount,
        adslAtucChanIntervalXOverFlowCells        PerfIntervalCount,
        adslAtucChanIntervalXIdleCells            PerfIntervalCount,
        adslAtucChanIntervalXIdleCellBitErrors    PerfIntervalCount
        }

adslAtucChanIntervalXHecv OBJECT-TYPE
      SYNTAX      PerfIntervalCount
      MAX-ACCESS  read-only
      STATUS      current
      DESCRIPTION
      "Count of all header error correction violations 
       received on this channel during this interval."
      ::= { adslAtucChanIntervalXEntry 1 }

adslAtucChanIntervalXTotalCells OBJECT-TYPE
      SYNTAX      PerfIntervalCount
      MAX-ACCESS  read-only
      STATUS      current
      DESCRIPTION
      "Count of all ATM cells received on this channel 
       this interval."
      ::= { adslAtucChanIntervalXEntry 2 }
 
adslAtucChanIntervalXTotalUserCells OBJECT-TYPE
      SYNTAX      PerfIntervalCount
      MAX-ACCESS  read-only
      STATUS      current
      DESCRIPTION
      "Count of all valid non-idle ATM cells succesfully
       transmitted to the UTOPIA bus on this interval."
      ::= { adslAtucChanIntervalXEntry 3 }  

adslAtucChanIntervalXOverFlowCells OBJECT-TYPE
      SYNTAX      PerfIntervalCount
      MAX-ACCESS  read-only
      STATUS      current
      DESCRIPTION
      "Count the number oc cells discarded due to the received
       UTOPIA FIFO being full on this interval."
      ::= { adslAtucChanIntervalXEntry 6 }

adslAtucChanIntervalXIdleCells OBJECT-TYPE
      SYNTAX      PerfIntervalCount
      MAX-ACCESS  read-only
      STATUS      current
      DESCRIPTION
      "Count of all idle ATM cells received on this channel 
       this interval."
      ::= { adslAtucChanIntervalXEntry 4 }
 
adslAtucChanIntervalXIdleCellBitErrors OBJECT-TYPE
      SYNTAX      PerfIntervalCount
      MAX-ACCESS  read-only
      STATUS      current
      DESCRIPTION
      "Count the number of bit errors in the payload of
       the valid idle ATM cells received on this channel
       on this interval."
      ::= { adslAtucChanIntervalXEntry 5 }

--******************************************************************
-- ADSL ATU-R Channel Interval Extension
--******************************************************************
adslAturChanIntervalXTable   OBJECT-TYPE
      SYNTAX          SEQUENCE OF AdslAturChanIntervalXEntry
      MAX-ACCESS      not-accessible
      STATUS          current
      DESCRIPTION
      "This table provides extra information in 
       relation to the adslAturChanIntervalTable 
       for each ATU-R channel's performance 
       collection interval.
       ADSL channel interfaces are those ifEntries where 
       ifType is equal to adslInterleave(124) or 
       adslFast(125).
       Performance Data Interval number 1 is the
       the most recent previous interval; interval
       96 is 24 hours ago. Intervals 2..96 are
       optional. Interval number 1 is the only
       interval used currently."
      ::= { adslXObjects 13 }

adslAturChanIntervalXEntry   OBJECT-TYPE
      SYNTAX          AdslAturChanIntervalXEntry
      MAX-ACCESS      not-accessible
      STATUS          current
      DESCRIPTION     
      "An entry in the adslAturChanIntervalXTable."
      INDEX  { lineIndex, adslAturChanIntervalNumber }
      ::= { adslAturChanIntervalXTable 1 }

AdslAturChanIntervalXEntry ::=
      SEQUENCE {
        adslAturChanIntervalXHecv                 PerfIntervalCount,
        adslAturChanIntervalXTotalCells           PerfIntervalCount,
        adslAturChanIntervalXTotalUserCells       PerfIntervalCount,     
        adslAturChanIntervalXIdleCellBitErrors    PerfIntervalCount
        }

adslAturChanIntervalXHecv OBJECT-TYPE
      SYNTAX      PerfIntervalCount
      MAX-ACCESS  read-only
      STATUS      current
      DESCRIPTION
      "Count of all header error correction violations 
       received on this channel during this interval."
      ::= { adslAturChanIntervalXEntry 1 }

adslAturChanIntervalXTotalCells OBJECT-TYPE
      SYNTAX      PerfIntervalCount
      MAX-ACCESS  read-only
      STATUS      current
      DESCRIPTION
      "Count of all ATM cells received on this channel 
       this interval."
      ::= { adslAturChanIntervalXEntry 2 }
 
adslAturChanIntervalXTotalUserCells OBJECT-TYPE
      SYNTAX      PerfIntervalCount
      MAX-ACCESS  read-only
      STATUS      current
      DESCRIPTION
      "Count of all valid non-idle ATM cells succesfully
       received on the UTOPIA bus on this interval."
      ::= { adslAturChanIntervalXEntry 3 }

adslAturChanIntervalXIdleCellBitErrors OBJECT-TYPE
      SYNTAX      PerfIntervalCount
      MAX-ACCESS  read-only
      STATUS      current
      DESCRIPTION
      "Count the number of bit errors in the payload of
       the valid idle ATM cells received on this channel
       on this interval. Applies to ADSL2 only"
      ::= { adslAturChanIntervalXEntry 4 }
      
--******************************************************************
-- ADSL ATU-C Proprietary Physical Extension Table
--******************************************************************
adslAtucProprietaryPhysXTable   OBJECT-TYPE
      SYNTAX          SEQUENCE OF AdslAtucProprietaryPhysXEntry
      MAX-ACCESS      not-accessible
      STATUS          current
      DESCRIPTION
      "ADSL ATU-C Proprietary Physical Extension Table."
      ::= { adslXObjects 14 }

adslAtucProprietaryPhysXEntry   OBJECT-TYPE
      SYNTAX          AdslAtucProprietaryPhysXEntry
      MAX-ACCESS      not-accessible
      STATUS          current
      DESCRIPTION     
      "An entry in the adslAtucProprietaryPhysXTable."
      INDEX  { lineIndex }
      ::= { adslAtucProprietaryPhysXTable 1 }

AdslAtucProprietaryPhysXEntry ::=
      SEQUENCE {
        adslAtucProprietaryPhysXLogS                  Integer32,
        adslAtucProprietaryPhysXCodingType            INTEGER,
        adslAtucProprietaryPhysXCurrentFailures       BITS,
        adslAtucProprietaryPhysXChangedFailures       BITS,
        adslAtucProprietaryPhysXActualLineBitRate     Unsigned32,
        adslAtucProprietaryPhysXPreviousLineBitRate   Unsigned32,
        adslAtucProprietaryPhysXMSGc                  Unsigned32,
        adslAtucProprietaryPhysXMSGlp                 Unsigned32,
        adslAtucProprietaryRefPsd            		  INTEGER,
        adslAtucProprietaryPhysXgiNEpart			  OCTET STRING,
        adslAtucProprietaryPhysXtssiNEpart			  OCTET STRING,
        adslAtucProprietaryPhysXLastRetrainCause      OCTET STRING
        }

adslAtucProprietaryPhysXLogS OBJECT-TYPE
    SYNTAX      Integer32 (-255..255)
    MAX-ACCESS  read-only
    STATUS      obsolete
    DESCRIPTION
    "Base 2 logarithm for the number of DMT sysmbols
     per code word in the downstream direction."
    ::= { adslAtucProprietaryPhysXEntry 1 }  
    
adslAtucProprietaryPhysXCodingType OBJECT-TYPE
    SYNTAX      INTEGER { noCoding (0), trellisCoding (1), reedSolomonCoding (2), 
                          trellisAndReedSolomonCoding (3)}
    MAX-ACCESS  read-only
    STATUS      current
    DESCRIPTION
    "Coding used in downstream. The following 
     representation is used:
     0 - No coding
     1 - Trellis coding
     2 - ReedSolomon coding
     3 - Concatenayed trellis coding and ReedSolomon coding."
    ::= { adslAtucProprietaryPhysXEntry 2 }  
    
adslAtucProprietaryPhysXCurrentFailures OBJECT-TYPE
    SYNTAX      BITS {
                        reserved0(0),
                        reserved1(1),
                        reserved2(2),
                        reserved3(3),
                        noDetectionUS(4),
                        communicationProblemUS(5),
                        bitRateTooHighUS(6),
                        noCommonModeInHandshakeUS(7),
                        reserved8(8),
                        reserved9(9),
                        ptmCodingViolationsPreemptiveB1US(10),
                        ptmCodingViolationsB1US(11),
                        ptmOutOfSyncB1US(12),
                        ptmCodingViolationsPreemptiveB0US(13),
                        ptmCodingViolationsB0US(14),
                        ptmOutOfSyncB0US(15),
                        noCellDelineationFastUS(16),
                        noCellDelineationInterleavedUS(17),
                        lossOfFrameUS(18),
                        lossOfSignalUS(19),
                        reserved20(20),
                        reserved21(21),
                        reserved22(22),
                        reserved23(23),
                        lossOfCellDelineationFastPathUS(24), 
                        lossOfCellDelineationInterleavedPathUS(25),
                        reserved26(26),
                        reserved27(27),
                        reserved28(28),
                        notRunningShowTimeStateUS(29),
                        unavailableTimeCountedUS(30)
                      }
    MAX-ACCESS  read-only
    STATUS      current
    DESCRIPTION
    "Bit mask giving the set of current active failures
     on the upstream (bit set => failure is ON).
     A failure is declared when the corresponding defect 
     is active for more than 2.5 (+/-0.5) sec. A failure 
     is cleared when the corresponding defect is off for 
     at least 10.5 (+/-0.5) sec. The bit index and 
     corresponding failure are:
     Bit[30] - Set when unavailable time is counted
     Bit[29] - Set when the modem is not in the Running Showtime state
     Bit[25] - Loss of cell delineation - interleaved path
     Bit[24] - Loss of cell delineation - fast path
     Bit[19] - Loss of signal
     Bit[18] - Loss of frame
     Bit[17] - No cell delineation - interleaved
     Bit[16] - No cell delineation - fast
     Bit[15] - PTM TC Out-Of-Sync Violation for bearer channel B0
     Bit[14] - PTM TC Coding Violation for bearer channel B0, non-preemptive
     Bit[13] - PTM TC Coding Violation for bearer channel B0, preemptive
     Bit[12] - PTM TC Out-Of-Sync Violation for bearer channel B1
     Bit[11] - PTM TC Coding Violation for bearer channel B1, non-preemptive
     Bit[10] - PTM TC Coding Violation for bearer channel B1, preemptive
     Bit[07] - No common mode in Handshake. Set when the test configuration
               prevents the training in the only mode supported by the ATU-R
     Bit[06] - Bit rate is too high. Set when the line quality does allow 
               support for the minimum bit rate configured
     Bit[05] - Communication problem. Sethwne initialisation could not be 
               completed due to time-out or a CRC error in one of the message 
               received from the ATU-R
     Bit[04] - No detection. Set when the ATU-R has not been detected after 
               2.5 seconds of attempts to activate the line.
     Note: The RunningShowtime state is left as soon as unavailable time is 
     counted (10 consecutive severely errored seconds), so bits 1 and 2 are 
     always set together."
    ::= { adslAtucProprietaryPhysXEntry 3 }

adslAtucProprietaryPhysXChangedFailures OBJECT-TYPE
    SYNTAX      BITS {
                        reserved0(0),
                        reserved1(1),
                        reserved2(2),
                        reserved3(3),
                        noDetectionUS(4),
                        communicationProblemUS(5),
                        bitRateTooHighUS(6),
                        noCommonModeInHandshakeUS(7),
                        reserved8(8),
                        reserved9(9),
                        ptmCodingViolationsPreemptiveB1US(10),
                        ptmCodingViolationsB1US(11),
                        ptmOutOfSyncB1US(12),
                        ptmCodingViolationsPreemptiveB0US(13),
                        ptmCodingViolationsB0US(14),
                        ptmOutOfSyncB0US(15),
                        noCellDelineationFastUS(16),
                        noCellDelineationInterleavedUS(17),
                        lossOfFrameUS(18),
                        lossOfSignalUS(19),
                        reserved20(20),
                        reserved21(21),
                        reserved22(22),
                        reserved23(23),
                        lossOfCellDelineationFastPathUS(24), 
                        lossOfCellDelineationInterleavedPathUS(25),
                        reserved26(26),
                        reserved27(27),
                        reserved28(28),
                        notRunningShowTimeStateUS(29),
                        unavailableTimeCountedUS(30)
                      }
    MAX-ACCESS  read-only
    STATUS      current
    DESCRIPTION
    "Bit mask presenting the upstream failures that have
     changed (or at least toggled) since last 
     GetLineStatus invocation."
    ::= { adslAtucProprietaryPhysXEntry 4 }

adslAtucProprietaryPhysXActualLineBitRate     OBJECT-TYPE
    SYNTAX      Unsigned32
    MAX-ACCESS  read-only
    STATUS      current
    DESCRIPTION
    "Actual line bit rate in the downstream direction."
    ::= { adslAtucProprietaryPhysXEntry 5 }  
    
adslAtucProprietaryPhysXPreviousLineBitRate     OBJECT-TYPE
    SYNTAX      Unsigned32
    MAX-ACCESS  read-only
    STATUS      current
    DESCRIPTION
    "Previous line bit rate in the downstream direction."
    ::= { adslAtucProprietaryPhysXEntry 6 }  
    
adslAtucProprietaryPhysXMSGc     OBJECT-TYPE
    SYNTAX      Unsigned32
    MAX-ACCESS  read-only
    STATUS      current
    DESCRIPTION
    "Octets in message based portion of the overhead framing structure."
    ::= { adslAtucProprietaryPhysXEntry 7 }  
    
adslAtucProprietaryPhysXMSGlp     OBJECT-TYPE
    SYNTAX      Unsigned32
    MAX-ACCESS  read-only
    STATUS      current
    DESCRIPTION
    "ID of the latency path carrying the message based overhead."
    ::= { adslAtucProprietaryPhysXEntry 8 }  

adslAtucProprietaryRefPsd OBJECT-TYPE
      SYNTAX      INTEGER (0..65535)
      UNITS       "tenth dBm/Hz"
      MAX-ACCESS  read-only
      STATUS      current
      DESCRIPTION
      "Upstream refPSD. RefPSD = nominal PSD - power cutback.
      Maps to the HMI GetLineStatus.linkStatus[US].refPsd."
      ::= { adslAtucProprietaryPhysXEntry 9 }

adslAtucProprietaryPhysXgiNEpart OBJECT-TYPE
    SYNTAX      OCTET STRING  (SIZE (128))
    MAX-ACCESS  read-only
    STATUS      deprecated
    DESCRIPTION
    "The near-end (US) linear scale carrier gain allocation.
     Granularity: 1/512 relative to the reference gain.
     Range is [4095..0]. 
     Maps to the HMI GetLineCarrierGains.
     Substituded by:	vdsl2SCStatusGainAlloc 
     Deprecated from:	EDA 4.0"
     ::= { adslAtucProprietaryPhysXEntry 10 } 

adslAtucProprietaryPhysXtssiNEpart OBJECT-TYPE
    SYNTAX      OCTET STRING  (SIZE (128))
    MAX-ACCESS  read-only
    STATUS      current
    DESCRIPTION
    "The US linear TSSI. Granularity: 1/32768 relative to the
     reference gain.
     Range is [32768..0].
     Maps to the HMI GetLineLinearTssi"
     ::= { adslAtucProprietaryPhysXEntry 11 } 

adslAtucProprietaryPhysXLastRetrainCause OBJECT-TYPE
    SYNTAX      OCTET STRING (SIZE (1))
    MAX-ACCESS  read-only
    STATUS      current
    DESCRIPTION
    "Bit[3:0] Identifies the cause of the last initialization failure,
	 according to the G.997.1 recommendation.

	 Possible values are:
     1 - Wrong profile (cannot occur in our system)
     2 - Configuration not feasible
     3 - Communication problem (CRC or time-out error)
     4 - No ATU-R detected

	 Bit[7:4] If the last initialization failure is a 'Communication
	 problem', this field identifies the type of
	 communication problem that has occurred.

	 Possible values are:
	 0 - Timeout during initialization
	 1 - CRC error during initialization message
	 2 - Unavailable time declared during Showtime at the near-end
	 3 - Dynamic Rate Adaptation triggered retrain at the near-end
   	 4 - Unavailable time declared during Showtime at the far-end
	 5 - Dynamic Rate Adaptation triggered retrain at the far-end
	 6 - Far-end line counters unavailable.

	 If the last initialization failure is a 'Configuration
	 not feasible' failure, this field indicates whether
	 this applies to the upstream or downstream
	 direction.

     Possible values are:
	 0 - Upstream configuration not feasible.
	 1 - Downstream configuration not feasible.

     Maps to the HMI GetLineStatus.lastRetrainCause"
     ::= { adslAtucProprietaryPhysXEntry 12 }
     
    
--******************************************************************
-- ADSL ATU-R Proprietary Physical Extension Table
--******************************************************************
adslAturProprietaryPhysXTable   OBJECT-TYPE
      SYNTAX          SEQUENCE OF AdslAturProprietaryPhysXEntry
      MAX-ACCESS      not-accessible
      STATUS          current
      DESCRIPTION
      "ADSL ATU-R Proprietary Physical Extension Table."
      ::= { adslXObjects 15 }

adslAturProprietaryPhysXEntry   OBJECT-TYPE
      SYNTAX          AdslAturProprietaryPhysXEntry
      MAX-ACCESS      not-accessible
      STATUS          current
      DESCRIPTION     
      "An entry in the adslAturProprietaryPhysXTable."
      INDEX  { lineIndex }
      ::= { adslAturProprietaryPhysXTable 1 }

AdslAturProprietaryPhysXEntry ::=
      SEQUENCE {
        adslAturProprietaryPhysXLogS               Integer32,
        adslAturProprietaryPhysXCodingType         INTEGER,
        adslAturProprietaryPhysXCurrentFailures     BITS,
        adslAturProprietaryPhysXChangedFailures     BITS,
        adslAturProprietaryPhysXActualLineBitRate     Unsigned32,
        adslAturProprietaryPhysXPreviousLineBitRate   Unsigned32,
        adslAturProprietaryPhysXMSGc                  Unsigned32,
        adslAturProprietaryPhysXMSGlp                 Unsigned32,
        adslAturProprietaryRefPsd            		  INTEGER,
        adslAturProprietaryPhysXgiFELowpart0		  OCTET STRING,
        adslAturProprietaryPhysXgiFEHipart0		      OCTET STRING,
        adslAturProprietaryPhysXgiFELowpart1		  OCTET STRING,
        adslAturProprietaryPhysXgiFEHipart1		      OCTET STRING,
        adslAturProprietaryPhysXgiFELowpart2		  OCTET STRING,
        adslAturProprietaryPhysXgiFEHipart2		      OCTET STRING,
        adslAturProprietaryPhysXgiFELowpart3   	      OCTET STRING,
        adslAturProprietaryPhysXgiFEHipart3		      OCTET STRING,
        adslAturProprietaryPhysXtssiFELowpart0		  OCTET STRING,
        adslAturProprietaryPhysXtssiFEHipart0		  OCTET STRING,
        adslAturProprietaryPhysXtssiFELowpart1		  OCTET STRING,
        adslAturProprietaryPhysXtssiFEHipart1		  OCTET STRING,
        adslAturProprietaryPhysXtssiFELowpart2		  OCTET STRING,
        adslAturProprietaryPhysXtssiFEHipart2		  OCTET STRING,
        adslAturProprietaryPhysXtssiFELowpart3		  OCTET STRING,
        adslAturProprietaryPhysXtssiFEHipart3		  OCTET STRING
        }

adslAturProprietaryPhysXLogS OBJECT-TYPE
    SYNTAX      Integer32 (-255..255)
    MAX-ACCESS  read-only
    STATUS      obsolete
    DESCRIPTION
    "Base 2 logarithm for the number of DMT symbols
     per code word in the upstream direction."
    ::= { adslAturProprietaryPhysXEntry 1 }    
    
adslAturProprietaryPhysXCodingType OBJECT-TYPE
    SYNTAX      INTEGER { noCoding (0), trellisCoding (1), reedSolomonCoding (2), 
                          trellisAndReedSolomonCoding (3)}
    MAX-ACCESS  read-only
    STATUS      current
    DESCRIPTION
    "Coding used in upstream. The following 
     representation is used:
     0 - No coding
     1 - Trellis coding
     2 - ReedSolomon coding
     3 - Concatenayed trellis coding and ReedSolomon coding."
    ::= { adslAturProprietaryPhysXEntry 2 }
    
adslAturProprietaryPhysXCurrentFailures OBJECT-TYPE
    SYNTAX      BITS {
                        reserved0(0),
                        reserved1(1),
                        reserved2(2),
                        reserved3(3),
                        reserved4(4),
                        reserved5(5),
                        reserved6(6),
                        reserved7(7),
                        reserved8(8),
                        reserved9(9),
                        reserved10(10),
                        reserved11(11),
                        reserved12(12),
                        lossOfPowerDS(13),
                        ptmOutOfSyncB0DS(14),
                        ptmOutOfSyncB1DS(15),
                        noCellDelineationFastDS(16),
                        noCellDelineationInterleavedDS(17),
                        lossOfFrameDS(18),
                        lossOfSignalDS(19),
                        reserved20(20),
                        reserved21(21),
                        reserved22(22),
                        reserved23(23),
                        lossOfCellDelineationFastPathDS(24),
                        lossOfCellDelineationInterleavedPathDS(25),
                        reserved26(26),
                        reserved27(27),
                        reserved28(28),
                        notRunningShowTimeStateDS(29),
                        unavailableTimeCountedDS(30)
                      }
    MAX-ACCESS  read-only
    STATUS      current
    DESCRIPTION
    "Bit mask giving the set of current active failures
     on the downstream (bit set => failure is ON).
     A failure is declared when the corresponding defect 
     is active for more than 2.5 (+/-0.5) sec. A failure 
     is cleared when the corresponding defect is off for 
     at least 10.5 (+/-0.5) sec. The bit index and 
     corresponding failure are:
     Bit[30] - Set when unavailable time is counted
     Bit[29] - Set when the modem is not in the Running Showtime state
     Bit[25] - Loss of cell delineation - interleaved path
     Bit[24] - Loss of cell delineation - fast path
     Bit[19] - Loss of Signal
     Bit[18] - Loss of Frame
     Bit[17] - No cell delineation - interleaved
     Bit[16] - No cell delineation - fast
     Bit[15] - PTM remote TC Out-Of-Sync violation for bearer B0
     Bit[14] - PTM remote TC Out-Of-Sync violation for bearer B1
     Bit[13] - Loss of power.
     Note: the Running Showtime state is left as soon as unavailable
     time is counted (10 consecutive severely errored seconds), so 
     bits 1 and 2 are always set together."
    ::= { adslAturProprietaryPhysXEntry 3 }

adslAturProprietaryPhysXChangedFailures OBJECT-TYPE
    SYNTAX      BITS {
                        reserved0(0),
                        reserved1(1),
                        reserved2(2),
                        reserved3(3),
                        reserved4(4),
                        reserved5(5),
                        reserved6(6),
                        reserved7(7),
                        reserved8(8),
                        reserved9(9),
                        reserved10(10),
                        reserved11(11),
                        reserved12(12),
                        lossOfPowerDS(13),
                        reserved14(14),
                        reserved15(15),
                        noCellDelineationInterleavedDS(16),
                        noCellDelineationFastDS(17),
                        lossOfFrameDS(18),
                        lossOfSignalDS(19),
                        reserved20(20),
                        reserved21(21),
                        reserved22(22),
                        reserved23(23),
                        lossOfCellDelineationInterleavedPathDS(24),
                        lossOfCellDelineationFastPathDS(25),
                        reserved26(26),
                        reserved27(27),
                        reserved28(28),
                        notRunningShowTimeStateDS(29),
                        unavailableTimeCountedDS(30)
                      }
    MAX-ACCESS  read-only
    STATUS      current
    DESCRIPTION
    "Bit mask presenting the downstream failures
     that have changed (or at least toggled) 
     since last GetLineStatus invocation."
    ::= { adslAturProprietaryPhysXEntry 4 }

adslAturProprietaryPhysXActualLineBitRate     OBJECT-TYPE
    SYNTAX      Unsigned32
    MAX-ACCESS  read-only
    STATUS      current
    DESCRIPTION
    "Actual line bit rate in the upstream direction."
    ::= { adslAturProprietaryPhysXEntry 5 }  
    
adslAturProprietaryPhysXPreviousLineBitRate     OBJECT-TYPE
    SYNTAX      Unsigned32
    MAX-ACCESS  read-only
    STATUS      current
    DESCRIPTION
    "Previous line bit rate in the upstream direction."
    ::= { adslAturProprietaryPhysXEntry 6 }  
    
adslAturProprietaryPhysXMSGc     OBJECT-TYPE
    SYNTAX      Unsigned32
    MAX-ACCESS  read-only
    STATUS      current
    DESCRIPTION
    "Octets in message based portion of the overhead framing structure."
    ::= { adslAturProprietaryPhysXEntry 7 }  
    
adslAturProprietaryPhysXMSGlp     OBJECT-TYPE
    SYNTAX      Unsigned32
    MAX-ACCESS  read-only
    STATUS      current
    DESCRIPTION
    "ID of the latency path carrying the message based overhead."
    ::= { adslAturProprietaryPhysXEntry 8 }  
    
adslAturProprietaryRefPsd OBJECT-TYPE
      SYNTAX      INTEGER  (0..65535)
      UNITS       "tenth dBm/Hz"
      MAX-ACCESS  read-only
      STATUS      current
      DESCRIPTION
      "Downstream refPSD. RefPSD = nominal PSD - power cutback.
      Maps to the HMI GetLineStatus.linkStatus[DS].refPsd."
      ::= { adslAturProprietaryPhysXEntry 9 }

adslAturProprietaryPhysXgiFELowpart0 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 10 } 

adslAturProprietaryPhysXgiFEHipart0 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 11 } 

adslAturProprietaryPhysXgiFELowpart1 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 12 } 

adslAturProprietaryPhysXgiFEHipart1 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 13 } 

adslAturProprietaryPhysXgiFELowpart2 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 14 } 

adslAturProprietaryPhysXgiFEHipart2 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 15 } 

adslAturProprietaryPhysXgiFELowpart3 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 16 } 

adslAturProprietaryPhysXgiFEHipart3 OBJECT-TYPE
    SYNTAX      OCTET STRING  (SIZE (128))
    MAX-ACCESS  read-only
    STATUS      deprecated
    DESCRIPTION
    "The far-end (DS) linear scale carrier gain allocation.
     Granularity: 1/512 relative to the reference gain.
     Range is [4095..0].
     Maps to the HMI GetLineCarrierGains.
     Substituded by:	vdsl2SCStatusGainAlloc 
     Deprecated from:	EDA 4.0"
    ::= { adslAturProprietaryPhysXEntry 17 } 

adslAturProprietaryPhysXtssiFELowpart0 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 18 } 

adslAturProprietaryPhysXtssiFEHipart0 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 19 } 

adslAturProprietaryPhysXtssiFELowpart1 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 20 } 

adslAturProprietaryPhysXtssiFEHipart1 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 21 } 

adslAturProprietaryPhysXtssiFELowpart2 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 22 } 

adslAturProprietaryPhysXtssiFEHipart2 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 23 } 

adslAturProprietaryPhysXtssiFELowpart3 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 24 } 

adslAturProprietaryPhysXtssiFEHipart3 OBJECT-TYPE
    SYNTAX      OCTET STRING  (SIZE (128))
    MAX-ACCESS  read-only
    STATUS      current
    DESCRIPTION
    "The far-end (DS) linear scale carrier gain allocation.
     Granularity: 1/512 relative to the reference gain.
     Range is [4095..0].
     Maps to the HMI GetLineCarrierGains."
    ::= { adslAturProprietaryPhysXEntry 25 } 

--******************************************************************
-- ADSL ATU-C Proprietary Channel Extension Table
--******************************************************************
adslAtucProprietaryChanXTable   OBJECT-TYPE
      SYNTAX          SEQUENCE OF AdslAtucProprietaryChanXEntry
      MAX-ACCESS      not-accessible
      STATUS          current
      DESCRIPTION
      "ADSL ATU-C Proprietary Channel Extension Table."
      ::= { adslXObjects 16 }

adslAtucProprietaryChanXEntry   OBJECT-TYPE
      SYNTAX          AdslAtucProprietaryChanXEntry
      MAX-ACCESS      not-accessible
      STATUS          current
      DESCRIPTION     
      "An entry in the adslAtucProprietaryChanXEntry."
      INDEX  { lineIndex }
      ::= { adslAtucProprietaryChanXTable 1 }

AdslAtucProprietaryChanXEntry ::=
      SEQUENCE {
        adslAtucProprietaryChanXB        	Integer32,
        adslAtucProprietaryChanXN        	Integer32,
        adslAtucProprietaryChanXR        	Integer32,
        adslAtucProprietaryChanXD        	Integer32,
        adslAtucProprietaryChanXSnum     	Unsigned32,
        adslAtucProprietaryChanXSdenom   	Unsigned32,
        adslAtucProprietaryChanXL        	Unsigned32,
        adslAtucProprietaryChanXM        	Unsigned32,
        adslAtucProprietaryChanXT        	Unsigned32,
        adslAtucProprietaryChanXB0B      	Unsigned32,
        adslAtucProprietaryChanXB1B      	Unsigned32,
        adslAtucProprietaryChanActualInpB0 	Unsigned32,
        adslAtucProprietaryChanActualInpB1 	Unsigned32
        }

adslAtucProprietaryChanXB OBJECT-TYPE
    SYNTAX      Integer32 (-65535..65535)
    MAX-ACCESS  read-only
    STATUS      deprecated
    DESCRIPTION
    "Number of bearer channel bytes per data frame
     allocated to the downstream interleaved/fast buffer,
     summed over all bearer channels.
     Will be substituted by adslAtucProprietaryChanXB0B - and B1B"
    ::= { adslAtucProprietaryChanXEntry 1 }  
    
adslAtucProprietaryChanXN OBJECT-TYPE
    SYNTAX      Integer32 (-65535..65535)
    MAX-ACCESS  read-only
    STATUS      current
    DESCRIPTION
    "Number of bytes in an downstream FEC output
     data frame for the interleaved/fast buffer."
    ::= { adslAtucProprietaryChanXEntry 2 }  
    
adslAtucProprietaryChanXR OBJECT-TYPE
    SYNTAX      Integer32 (-255..255)
    MAX-ACCESS  read-only
    STATUS      current
    DESCRIPTION
    "Number of downstream FEC redundancy bytes per
     ReedSolomon codeword for the interleaved/fast buffer."
    ::= { adslAtucProprietaryChanXEntry 3 } 

adslAtucProprietaryChanXD OBJECT-TYPE
    SYNTAX      Integer32 (-255..255)
    MAX-ACCESS  read-only
    STATUS      current
    DESCRIPTION
    "Downstream interleaved/fast depth."
    ::= { adslAtucProprietaryChanXEntry 4 } 

adslAtucProprietaryChanXSnum     OBJECT-TYPE
    SYNTAX      Unsigned32
    MAX-ACCESS  read-only
    STATUS      current
    DESCRIPTION
    "Numerator of the number of PMD symbols over which the 
     FEC data frame spans.
     Note: This parameter is not supported by VDSL2 protocols."
    ::= { adslAtucProprietaryChanXEntry 5 } 

adslAtucProprietaryChanXSdenom     OBJECT-TYPE
    SYNTAX      Unsigned32
    MAX-ACCESS  read-only
    STATUS      current
    DESCRIPTION
    "Denominator of the number of PMD symbols over which the 
     FEC data frame spans.
     Note: This parameter is not supported by VDSL2 protocols."
    ::= { adslAtucProprietaryChanXEntry 6 } 

adslAtucProprietaryChanXL     OBJECT-TYPE
    SYNTAX      Unsigned32
    MAX-ACCESS  read-only
    STATUS      current
    DESCRIPTION
    "Number of bits per symbol."
    ::= { adslAtucProprietaryChanXEntry 7 } 

adslAtucProprietaryChanXM     OBJECT-TYPE
    SYNTAX      Unsigned32
    MAX-ACCESS  read-only
    STATUS      current
    DESCRIPTION
    "Number of MUX data frames per FEC data frame (codeword).
     Note: This parameter applies to ADSL2 or VDSL2 protocols
     only."
    ::= { adslAtucProprietaryChanXEntry 8 } 

adslAtucProprietaryChanXT     OBJECT-TYPE
    SYNTAX      Unsigned32
    MAX-ACCESS  read-only
    STATUS      current
    DESCRIPTION
    "For ADSL2, T is the number of MUX data frames per sync
     octet. For VDSL2, T is the number of MUX data frames in an
     overhead subframe."
    ::= { adslAtucProprietaryChanXEntry 9 }

adslAtucProprietaryChanXB0B OBJECT-TYPE
    SYNTAX      Unsigned32
    MAX-ACCESS  read-only
    STATUS      current
    DESCRIPTION
    "B[0] is the nominal number of bearer octets per MUX data
     frame from bearer B0. In the case of ADSL2, the actual
     number of bearer octets per MUX data frame is B[0] + 1 if
     the MUX frame count is not a multiple of T. In the case of
     VDSL2, the actual number of bearer octets per MUX data
     frame varies between B[0] and B[0] + 1 if G/T is not an
     integer.
     This param will substitute adslAtucProprietaryChanXB"
    ::= { adslAtucProprietaryChanXEntry 10 }

adslAtucProprietaryChanXB1B OBJECT-TYPE
    SYNTAX      Unsigned32
    MAX-ACCESS  read-only
    STATUS      current
    DESCRIPTION
    "B[1] is the nominal number of bearer octets per MUX data
     frame from bearer B1. This field is only used for VDSL2,
     where the actual number of bearer octets per MUX data
     frame is always B[1], regardless of G/T.
     This param will substitute adslAtucProprietaryChanXB"
    ::= { adslAtucProprietaryChanXEntry 11 }  

adslAtucProprietaryChanActualInpB0 OBJECT-TYPE
    SYNTAX      Unsigned32
    MAX-ACCESS  read-only
    STATUS      current
    DESCRIPTION
    "The parameter gives the actual INP for the channel in
     DS direction. The actual INP is the calculated from
     the protocol dependant formulas:
     -VDSL2 protocol: INP = (4*R*D*I)/(N*L)
     -ADSL protocols: INP = (4*R*D)/L
     -No showtime: 	  INP = 0"
    ::= { adslAtucProprietaryChanXEntry 15 }  
    
adslAtucProprietaryChanActualInpB1 OBJECT-TYPE
    SYNTAX      Unsigned32
    MAX-ACCESS  read-only
    STATUS      current
    DESCRIPTION
    "The parameter gives the actual INP for the channel in
     DS direction. The actual INP is the calculated from
     the protocol dependant formulas:
     -VDSL2 protocol: INP = (4*R*D*I)/(N*L)
     -ADSL protocols: INP = (4*R*D)/L
     -No showtime: 	  INP = 0"
    ::= { adslAtucProprietaryChanXEntry 20 }  
    
--******************************************************************
-- ADSL ATU-R Proprietary Channel Extension Table
--******************************************************************
adslAturProprietaryChanXTable   OBJECT-TYPE
      SYNTAX          SEQUENCE OF AdslAturProprietaryChanXEntry
      MAX-ACCESS      not-accessible
      STATUS          current
      DESCRIPTION
      "ADSL ATU-R Proprietary Channel Extension Table."
      ::= { adslXObjects 17 }

adslAturProprietaryChanXEntry   OBJECT-TYPE
      SYNTAX          AdslAturProprietaryChanXEntry
      MAX-ACCESS      not-accessible
      STATUS          current
      DESCRIPTION     
      "An entry in the adslAturProprietaryChanXTable."
      INDEX  { lineIndex }
      ::= { adslAturProprietaryChanXTable 1 }

AdslAturProprietaryChanXEntry ::=
      SEQUENCE {
        adslAturProprietaryChanXB        	Integer32,
        adslAturProprietaryChanXN        	Integer32,
        adslAturProprietaryChanXR        	Integer32,
        adslAturProprietaryChanXD        	Integer32,
        adslAturProprietaryChanXSnum     	Unsigned32,
        adslAturProprietaryChanXSdenom   	Unsigned32,
        adslAturProprietaryChanXL        	Unsigned32,
        adslAturProprietaryChanXM        	Unsigned32,
        adslAturProprietaryChanXT        	Unsigned32,
        adslAturProprietaryChanXB0B      	Unsigned32,
        adslAturProprietaryChanXB1B      	Unsigned32,
        adslAturProprietaryChanActualInpB0 	Unsigned32,
        adslAturProprietaryChanActualInpB1 	Unsigned32
        }
adslAturProprietaryChanXB OBJECT-TYPE
    SYNTAX      Integer32 (-65535..65535)
    MAX-ACCESS  read-only
    STATUS      deprecated
    DESCRIPTION
    "Number of bearer channel bytes per data frame
     allocated to the upstream interleaved/fast buffer, 
     summed over all bearer channels.
     Will be substituted by adslAturProprietaryChanXB0B - and B1B"
    ::= { adslAturProprietaryChanXEntry 1 } 

adslAturProprietaryChanXN OBJECT-TYPE
    SYNTAX      Integer32 (-65535..65535)
    MAX-ACCESS  read-only
    STATUS      current
    DESCRIPTION
    "Number of bytes in an upstream FEC output data
     frame for the interleaved/fast buffer."
    ::= { adslAturProprietaryChanXEntry 2 } 
 

adslAturProprietaryChanXR OBJECT-TYPE
    SYNTAX      Integer32 (-255..255)
    MAX-ACCESS  read-only
    STATUS      current
    DESCRIPTION
    "Number of upstream FEC redundancy bytes per
     ReedSolomon code word for the interleaved/fast buffer."
    ::= { adslAturProprietaryChanXEntry 3 } 

adslAturProprietaryChanXD OBJECT-TYPE
    SYNTAX      Integer32 (-255..255)
    MAX-ACCESS  read-only
    STATUS      current
    DESCRIPTION
    "Upstream interleave/fast depth."
    ::= { adslAturProprietaryChanXEntry 4 }  
    
adslAturProprietaryChanXSnum     OBJECT-TYPE
    SYNTAX      Unsigned32
    MAX-ACCESS  read-only
    STATUS      current
    DESCRIPTION
    "Numerator of the number of PMD symbols over which the 
     FEC data frame spans.
     Note: This parameter is not supported by VDSL2 protocols."
    ::= { adslAturProprietaryChanXEntry 5 } 

adslAturProprietaryChanXSdenom     OBJECT-TYPE
    SYNTAX      Unsigned32
    MAX-ACCESS  read-only
    STATUS      current
    DESCRIPTION
    "Denominator of the number of PMD symbols over which the 
     FEC data frame spans.
     Note: This parameter is not supported by VDSL2 protocols."
    ::= { adslAturProprietaryChanXEntry 6 } 

adslAturProprietaryChanXL     OBJECT-TYPE
    SYNTAX      Unsigned32
    MAX-ACCESS  read-only
    STATUS      current
    DESCRIPTION
    "Number of bits per symbol."
    ::= { adslAturProprietaryChanXEntry 7 } 

adslAturProprietaryChanXM     OBJECT-TYPE
    SYNTAX      Unsigned32
    MAX-ACCESS  read-only
    STATUS      current
    DESCRIPTION
    "Number of MUX data frames per FEC data frame (codeword).
     Note: This parameter applies to ADSL2 or VDSL2 protocols
     only."
    ::= { adslAturProprietaryChanXEntry 8 } 

adslAturProprietaryChanXT     OBJECT-TYPE
    SYNTAX      Unsigned32
    MAX-ACCESS  read-only
    STATUS      current
    DESCRIPTION
    "For ADSL2, T is the number of MUX data frames per sync
     octet. For VDSL2, T is the number of MUX data frames in an
     overhead subframe."
    ::= { adslAturProprietaryChanXEntry 9 } 

adslAturProprietaryChanXB0B OBJECT-TYPE
    SYNTAX      Unsigned32
    MAX-ACCESS  read-only
    STATUS      current
    DESCRIPTION
    "B[0] is the nominal number of bearer octets per MUX data
     frame from bearer B0. In the case of ADSL2, the actual
     number of bearer octets per MUX data frame is B[0] + 1 if
     the MUX frame count is not a multiple of T. In the case of
     VDSL2, the actual number of bearer octets per MUX data
     frame varies between B[0] and B[0] + 1 if G/T is not an
     integer.
     This param will substitute adslAturProprietaryChanXB"
    ::= { adslAturProprietaryChanXEntry 10 }

adslAturProprietaryChanXB1B OBJECT-TYPE
    SYNTAX      Unsigned32
    MAX-ACCESS  read-only
    STATUS      current
    DESCRIPTION
    "B[1] is the nominal number of bearer octets per MUX data
     frame from bearer B1. This field is only used for VDSL2,
     where the actual number of bearer octets per MUX data
     frame is always B[1], regardless of G/T.
     This param will substitute adslAturProprietaryChanXB"
    ::= { adslAturProprietaryChanXEntry 11 }  
    
adslAturProprietaryChanActualInpB0 OBJECT-TYPE
    SYNTAX      Unsigned32
    MAX-ACCESS  read-only
    STATUS      current
    DESCRIPTION
    "The parameter gives the actual INP for the channel in
     US direction. The actual INP is the calculated from
     the protocol dependant formulas:
     -VDSL2 protocol: INP = (4*R*D*I)/(N*L)
     -ADSL protocols: INP = (4*R*D)/L
     -No showtime: 	  INP = 0"
    ::= { adslAturProprietaryChanXEntry 15 }  
    
adslAturProprietaryChanActualInpB1 OBJECT-TYPE
    SYNTAX      Unsigned32
    MAX-ACCESS  read-only
    STATUS      current
    DESCRIPTION
    "The parameter gives the actual INP for the channel in
     US direction. The actual INP is the calculated from
     the protocol dependant formulas:
     -VDSL2 protocol: INP = (4*R*D*I)/(N*L)
     -ADSL protocols: INP = (4*R*D)/L
     -No showtime: 	  INP = 0"
    ::= { adslAturProprietaryChanXEntry 20 }  
    
--******************************************************************
-- ADSL Proprietary Line Configuration Profile Extention Table
--******************************************************************
adslProprietaryLineConfProfileXTable   OBJECT-TYPE
      SYNTAX          SEQUENCE OF AdslProprietaryLineConfProfileXEntry
      MAX-ACCESS      not-accessible
      STATUS          current
      DESCRIPTION
      "ADSL Proprietary Line Configuration Profile Extention Table."
      ::= { adslXObjects 18 }

adslProprietaryLineConfProfileXEntry   OBJECT-TYPE
      SYNTAX          AdslProprietaryLineConfProfileXEntry
      MAX-ACCESS      not-accessible
      STATUS          current
      DESCRIPTION     
      "An entry in the adslProprietaryLineConfProfileXTable."
      INDEX  { lineIndex }
      ::= { adslProprietaryLineConfProfileXTable 1 }

AdslProprietaryLineConfProfileXEntry ::=
      SEQUENCE {
        adslAtucProprietaryConfXMaxPower                    Integer32,
        adslAtucProprietaryConfXMaxPsd                      Integer32,
        adslAtucProprietaryConfXFixedPsd                    INTEGER,
        adslAtucProprietaryConfXPowerAdaptivity             INTEGER,
        adslAtucProprietaryConfXOptionsFlagBit1             INTEGER,
        adslAtucProprietaryConfXOptionsFlagBit2             INTEGER,
        adslAtucProprietaryConfXDisableTrellis              INTEGER,
        adslAtucProprietaryConfXRestartMode                 INTEGER,
        adslAtucProprietaryConfXMaxFramingMode              INTEGER,
        adslAtucProprietaryConfXDisableBitSwap              INTEGER,
        adslAturProprietaryConfXDisableBitSwap              INTEGER,
        adslAtucProprietaryConfXDisableHighBitRateInGLite   INTEGER,
        adslAtucProprietaryChanConfXOptimiseImpulseNoiseResilienceIlv        INTEGER,
        adslAtucProprietaryChanConfXOptimiseImpulseNoiseResilienceFast       INTEGER,
        adslAtucProprietaryChanConfXTxAtmFlagsFast          Integer32,
        adslAtucProprietaryChanConfXRxAtmFlagsFast          Integer32,
        adslAtucProprietaryChanConfXTxAtmFlagsIlv           Integer32,
        adslAtucProprietaryChanConfXRxAtmFlagsIlv           Integer32,
        adslAturProprietaryConfXMaxPower                    Integer32,
        adslAturProprietaryConfXMaxPsd                      Integer32,
        adslAturProprietaryChanConfXOptimiseImpulseNoiseResilienceIlv        INTEGER,
        adslAturProprietaryChanConfXOptimiseImpulseNoiseResilienceFast       INTEGER,
        adslAtucProprietaryConfXBoostFactor                                  Integer32,
        adslAtucProprietaryConfXMaxRxPower                                   Integer32,
        adslAtucProprietaryConfXDeltaPsdNormal              Integer32,
        adslAtucProprietaryConfXDeltaPsdPlus                Integer32,
        adslAtucProprietaryConfXDeltaPsdReach               Integer32,
        adslAturProprietaryConfXDeltaPsdNormal              Integer32,
        adslAturProprietaryConfXDeltaPsdPlus                Integer32,
        adslAturProprietaryConfXDeltaPsdReach               Integer32,
        adslAtucProprietaryConfXAutomodePIalpha             INTEGER,
        adslAtucProprietaryConfXAutomodePIbeta              INTEGER,
        adslAtucProprietaryConfXOptionsFlagBit4             INTEGER,
        adslAtucProprietaryConfXAdslPlusTxFilterId          INTEGER,
        adslAtucProprietaryConfXDisableUS1bitConst          INTEGER,
        adslAtucProprietaryConfXDisableWindowing            INTEGER,
        adslAtucProprietaryConfXDisableShowtimeExit         INTEGER,
        adslAtucProprietaryConfXDisableNitro                INTEGER,
        adslAtucProprietaryConfXDisableUpdateTestParameters INTEGER,
        adslAtucProprietaryConfXTssiShapeNrOfBreakPoints    INTEGER,
        adslAtucProprietaryConfXTssiShapeAdsl2ProtocolType  OCTET STRING,
        adslAtucProprietaryConfXTssiShapeBreakPoint         OCTET STRING,
        adslAtucProprietaryChanConfXINPminIlvB0             INTEGER,
        adslAtucProprietaryChanConfXINPminFastB0            INTEGER,
        adslAtucProprietaryChanConfXINPminFastB1            INTEGER,
        adslAturProprietaryChanConfXINPminIlvB0             INTEGER,
        adslAturProprietaryChanConfXINPminFastB0            INTEGER,
        adslAturProprietaryChanConfXINPminFastB1            INTEGER,
        adslAtucProprietaryConfXOptionsFlagBit5             INTEGER,
        adslAtucProprietaryConfXDisableShalfOptionBit0      INTEGER,
        adslAtucProprietaryConfXDisableShalfOptionBit1      INTEGER,
        adslAtucProprietaryConfXDisableLargeD      			INTEGER,
        adslAtucProprietaryConfXForceSegmentation      		INTEGER,
        adslAtucProprietaryConfXRelaxInpMinCheck      		INTEGER,
        adslAtucProprietaryConfXhsTxPSD0      				INTEGER,
        adslAtucProprietaryConfXhsTxPSD1      				INTEGER,
        adslAtucProprietaryConfXhsTxPSD2      				INTEGER,
        adslAtucProprietaryChanMinL2BitRateB0  				INTEGER,
        adslAtucProprietaryChanMinL2BitRateB1  				INTEGER,
        adslAtucProprietaryChanL2LowRateSlotsB0				INTEGER,
        adslAtucProprietaryChanL2LowRateSlotsB1				INTEGER,
        adslAtucProprietaryChanL2PacketB0      				INTEGER,
        adslAtucProprietaryChanL2PacketB1      				INTEGER,
        adslAtucProprietaryChanMaxL2BitRateB0      			INTEGER,
        adslAtucProprietaryChanMaxL2BitRateB1      			INTEGER,
        adslAtucProprietaryL2TestConfigBit0      			INTEGER,
        adslAtucProprietaryL2TestConfigBit1      			INTEGER,
        adslAtucProprietaryL2TestConfigBit2      			INTEGER,
        adslAtucProprietaryL2MinAtpr      					INTEGER,
        adslAtucProprietaryL0Time							INTEGER,
        adslAtucProprietaryL2Time							INTEGER,
        adslAtucProprietaryL2Atpr							INTEGER,
        adslAtucProprietaryL2Atprt							INTEGER,
        adslAtucProprietaryRateAdaptationFlagsBit0Upstream	INTEGER,
        adslAtucProprietaryRateAdaptationFlagsBit0Downstream	INTEGER,
        adslAtucValidRateExtension   						INTEGER,
        adslAtucProprietaryConfXMsgMinDS                    INTEGER,
        adslAtucProprietaryConfXMsgMinUS					INTEGER,
        adslAturProprietaryConfXUsBitSwapBehavior			INTEGER,
        adslAtucProprietaryConfXStrictPerCheck				INTEGER,
        adslAtucProprietaryConfXTpsTcType					INTEGER,
        adslAtucProprietaryConfXPsdOptimConfig				INTEGER,
        adslAtucProprietaryConfXPsdMaskSelectUs				Unsigned32,
        adslAtucProprietaryConfXDisableProtocolFallback		TruthValue
        }

adslAtucProprietaryConfXMaxPower OBJECT-TYPE
    SYNTAX      Integer32 (-50..230) 
    UNITS       "0.1 dBm"
    MAX-ACCESS  read-write
    STATUS      current
    DESCRIPTION
    "Maximum allowed DS transmit power. Unit is 0.1 dBm."
    ::= { adslProprietaryLineConfProfileXEntry 1 } 
      
adslAtucProprietaryConfXMaxPsd OBJECT-TYPE
    SYNTAX      Integer32 (-520..-360) 
    UNITS       "0.1 dB/Hz"
    MAX-ACCESS  read-write
    STATUS      obsolete
    DESCRIPTION
    "Maximum allowed PSD expressed in dB: unit is 0.1 dB/Hz.
     The allowed range for the downstream direction is
     -36 to -52 dBm/Hz. Maps into HMI: MaxTxPsd."
    ::= { adslProprietaryLineConfProfileXEntry 2 } 

adslAtucProprietaryConfXFixedPsd OBJECT-TYPE
    SYNTAX      INTEGER { set(1), notSet(0) }
    MAX-ACCESS  read-write
    STATUS      current
    DESCRIPTION
    "When the flag is set (1), the transmit PSD will be fixed to 
     the minimum of -40dBm/Hz and adslAtucProprietaryConfXMaxPsd. 
     When this flag is not set (0), the modem can break the ADSL 
     initialisation sequence and re-initialise at a more optimal 
     PSD level."
    ::= { adslProprietaryLineConfProfileXEntry 3 } 

adslAtucProprietaryConfXPowerAdaptivity OBJECT-TYPE
    SYNTAX      INTEGER { set(1), notSet(0) }
    MAX-ACCESS  read-write
    STATUS      current
    DESCRIPTION
    "Flag only considered if adslAtucProprietaryConfXFixedPsd is notSet(0).
     If set, priority goes to power: the modem attempt
     to achieve the minimum power consumtion as soon 
     as the minimum requested rate is achieved.
     If not set, priority goes to rate: the modem attempt
     to achieve the maximum requested bit rate before 
     reducing the transmit power."
    ::= { adslProprietaryLineConfProfileXEntry 4 } 

adslAtucProprietaryConfXOptionsFlagBit1 OBJECT-TYPE
    SYNTAX      INTEGER { dbm(0), fbm(1) }
    MAX-ACCESS  read-write
    STATUS      obsolete
    DESCRIPTION
    "DBM/FBM flag.
     Possible values are:
     0 - Dual Bit Mode (DBM)
     1 - FEXT Bitmap Mode (FBM)."
    ::= { adslProprietaryLineConfProfileXEntry 5 } 
       
adslAtucProprietaryConfXOptionsFlagBit2 OBJECT-TYPE
    SYNTAX      INTEGER { enabledNTR(0), disabledNTR(1) }
    MAX-ACCESS  read-write
    STATUS      current
    DESCRIPTION
    "NTR support flag. Annex A and Annex B only.
     Possible values are:
     0 - NTR support enabled
     1 - NTR support disabled."
    ::= { adslProprietaryLineConfProfileXEntry 6 } 
    
adslAtucProprietaryConfXDisableTrellis OBJECT-TYPE
    SYNTAX      INTEGER { set (1), notSet (0) }
    MAX-ACCESS  read-write
    STATUS      current
    DESCRIPTION
    "Set this flag to disable trellis coding capability."
    ::= { adslProprietaryLineConfProfileXEntry 7 }  
    
adslAtucProprietaryConfXRestartMode OBJECT-TYPE
    SYNTAX      INTEGER { default(0), restartOption1(1), restartOption2(2) }
    MAX-ACCESS  read-write
    STATUS      current
    DESCRIPTION
    "Possible states are:
    0 - Default behaviour.
    1 - When the Running Showtime state is left due to the presence of ten
        consecutive SES, the modem goes to the Idle Configured state 
        instead of going autonomously to the Running Activation state.
    2 - Do not leave Running Showtime state in case of ten consecutive SES.
        When this option is active, the only way to leave the Running Showtime 
        state is to send the Stop Line message."
    ::= { adslProprietaryLineConfProfileXEntry 8 } 
   
adslAtucProprietaryConfXMaxFramingMode OBJECT-TYPE
    SYNTAX      INTEGER { default(0), reserved1(1), reserved2(2), framingModeOneAndTwoAndThree(3) }
    MAX-ACCESS  read-write
    STATUS      deprecated
    DESCRIPTION
    "Possible states are:
    0 - default behaviour: suports framing modes one, two and three.
    1 - reserved.
    2 - reserved.
    3 - Maximum framing mode is three: modem will only support framing one, two and three.
    The parameter is no longer supported in the DSP.
    Deprecated from:           EDA 4.0"
    ::= { adslProprietaryLineConfProfileXEntry 9 } 

adslAtucProprietaryConfXDisableBitSwap OBJECT-TYPE
    SYNTAX      INTEGER { enableDownstreamBitswaps (0), disableDownstreamBitswaps (1) }
    MAX-ACCESS  read-write
    STATUS      current
    DESCRIPTION
    "0 - Enable downstream bitswaps
     1 - Disable downstream bitswaps."
    ::= { adslProprietaryLineConfProfileXEntry 10 } 

adslAturProprietaryConfXDisableBitSwap OBJECT-TYPE
    SYNTAX      INTEGER { enableUpstreamBitswaps (0), disableUpstreamBitswaps (1) }
    MAX-ACCESS  read-write
    STATUS      current
    DESCRIPTION
    "The value of this Mib object is with respect to adslAturProprietaryConfXUsBitSwapBehavior.
     If the value of adslAturProprietaryConfXUsBitSwapBehavior is classicUpstreamBitswap
     then it will get/set the US bitswap i.e Bit 0 of disableBitSwap.
     If the value of adslAturProprietaryConfXUsBitSwapBehavior is fullBandUpstreamBitswap
     then it will get/set the Full Band US bitswap  i.e Bit 2 of disableBitSwap. 
     0 - Enable upstream bitswaps
     1 - Disable upstream bitswaps."
    ::= { adslProprietaryLineConfProfileXEntry 11 } 


adslAtucProprietaryConfXDisableHighBitRateInGLite OBJECT-TYPE
    SYNTAX      INTEGER { enableUSandDS (0),
    					  limitUS (1),
                          limitDS (2),
                          limitUSandDS (3) }
    MAX-ACCESS  read-write
    STATUS      current
    DESCRIPTION
    "0 - Enable high bit rates in G.Lite
     1 - Limit the upstream bit rate to a maximum of 512 kbps in G.lite.
     2 - Limit the downstream bit rate to a maximum of 1.536 Mbps in G.Lite.
     3 - Limit upstream and downstream bit rate in G.lite
     By default, the rate is not limited in G.lite.
     Maps to the HMI SetlineTestConfiguration.disableHighBitRateInGlite"
    ::= { adslProprietaryLineConfProfileXEntry 12 }
    
adslAtucProprietaryChanConfXOptimiseImpulseNoiseResilienceIlv OBJECT-TYPE
    SYNTAX      INTEGER { impulseNoiseProtection (1), reachMaximumBitRate (0) } 
    MAX-ACCESS  read-write
    STATUS      obsolete
    DESCRIPTION
    "Flag: when set to 1 the modem initialisation algorithm
     gives priority to the impulse noise protection. When 
     set to 0, the modem initialisation algorithm gives 
     priority to reach the maximum bit rate. In this case,
     the algorithm could initialise with a lower delay than
     the one specified with the maxDelay parameter."
    ::= { adslProprietaryLineConfProfileXEntry 13 } 

adslAtucProprietaryChanConfXOptimiseImpulseNoiseResilienceFast OBJECT-TYPE
    SYNTAX      INTEGER { impulseNoiseProtection (1), reachMaximumBitRate (0) } 
    MAX-ACCESS  read-write
    STATUS      obsolete
    DESCRIPTION
    "Flag: when set to 1 the modem initialisation algorithm
     gives priority to the impulse noise protection. When 
     set to 0, the modem initialisation algorithm gives 
     priority to reach the maximum bit rate. In this case,
     the algorithm could initialise with a lower delay than
     the one specified with the maxDelay parameter."
    ::= { adslProprietaryLineConfProfileXEntry 14 } 
 
adslAtucProprietaryChanConfXTxAtmFlagsFast OBJECT-TYPE
    SYNTAX      Integer32  
    MAX-ACCESS  read-write
    STATUS      current
    DESCRIPTION
    "Configure the behaviour of the downstream ATM processor (value is don't care
    if the UTOPIA port is not used for bearer). Normally set to zero.
    This is a bit array controlling the following features
    Bit[0] - Disable ATM payload scrambling.
    Bit[1] - Reserved. Set to 0.
    Bit[2] - Reserved. Set to 0.
    Bit[3] - Disable HEC regeneration. HEC is passed through transparently
             instead of being recomputed.
    Allowed values: 0, 1, 8 and 9."
    ::= { adslProprietaryLineConfProfileXEntry 15 }   

adslAtucProprietaryChanConfXRxAtmFlagsFast OBJECT-TYPE
    SYNTAX      Integer32 (0..63)  
    MAX-ACCESS  read-write
    STATUS      current
    DESCRIPTION
    "Configure the behaviour of the upstream ATM processor (value is don't care
    if the UTOPIA port is not used for bearer). Normally set to zero.
    This is a bit mask controlling the following features:
    Bit[0]- disable descrambler. No ATNM patload descrambling is applied.
    Bit[1]- Output cells during PRE_SYNC state. The ATM cells with correct HEC
            will be output the the PRE_SYNC state.
    Bit[2]- No cells discard on bad HEC. ATM cells with wrong HEC will be sent 
            on the UTOPIA port.
    Bit[3]- No idle cells discard. Idle cells will be sent on UTOPIA port.
    Bit[4]- Disable cell delineation. Forces the delineation state to SYNC.
    Bit[5]- Disable unassigned cell filtering."
    ::= { adslProprietaryLineConfProfileXEntry 16 } 
  
adslAtucProprietaryChanConfXTxAtmFlagsIlv OBJECT-TYPE
    SYNTAX      Integer32  
    MAX-ACCESS  read-write
    STATUS      current
    DESCRIPTION
    "Configure the behaviour of the downstream ATM processor (value is don't care
    if the UTOPIA port is not used for bearer). Normally set to zero.
    This is a bit array controlling the following features
    Bit[0] - Disable ATM payload scrambling.
    Bit[1] - Reserved. Set to 0.
    Bit[2] - Reserved. Set to 0.
    Bit[3] - Disable HEC regeneration. HEC is passed through transparently
             instead of being recomputed.
    Allowed values: 0, 1, 8 and 9."
    ::= { adslProprietaryLineConfProfileXEntry 17 } 

adslAtucProprietaryChanConfXRxAtmFlagsIlv OBJECT-TYPE
    SYNTAX      Integer32 (0..63)  
    MAX-ACCESS  read-write
    STATUS      current
    DESCRIPTION
    "Configure the behaviour of the upstream ATM processor (value is don't care
    if the UTOPIA port is not used for bearer). Normally set to zero.
    This is a bit mask controlling the following features:
    Bit[0]- disable descrambler. No ATNM patload descrambling is applied.
    Bit[1]- Output cells during PRE_SYNC state. The ATM cells with correct HEC
            will be output the the PRE_SYNC state.
    Bit[2]- No cells discard on bad HEC. ATM cells with wrong HEC will be sent 
            on the UTOPIA port.
    Bit[3]- No idle cells discard. Idle cells will be sent on UTOPIA port.
    Bit[4]- Disable cell delineation. Forces the delineation state to SYNC.
    Bit[5]- Disable unassigned cell filtering."
    ::= { adslProprietaryLineConfProfileXEntry 18 } 

adslAturProprietaryConfXMaxPower OBJECT-TYPE
    SYNTAX      Integer32 (-130..200) 
    UNITS       "0.1 dBm"
    MAX-ACCESS  read-write
    STATUS      current
    DESCRIPTION
    "Maximum allowed US transmit power. Unit is 0.1 dBm."
    ::= { adslProprietaryLineConfProfileXEntry 19 } 
      
adslAturProprietaryConfXMaxPsd OBJECT-TYPE
    SYNTAX      Integer32 (-520..-360) 
    UNITS       "0.1 dB/Hz"
    MAX-ACCESS  read-write
    STATUS      obsolete
    DESCRIPTION
    "Maximum allowed PSD expressed in dB: unit is 0.1 dB/Hz.
     This field is not supported in the upstream direction in
     the current release, and must be set to -380 (-38dBm).
     Maps into HMI: MaxTxPsd."
    ::= { adslProprietaryLineConfProfileXEntry 20 } 

adslAturProprietaryChanConfXOptimiseImpulseNoiseResilienceIlv OBJECT-TYPE
    SYNTAX      INTEGER { impulseNoiseProtection (1), reachMaximumBitRate (0) } 
    MAX-ACCESS  read-write
    STATUS      obsolete
    DESCRIPTION
    "Flag: when set to 1 the modem initialisation algorithm
     gives priority to the impulse noise protection. When 
     set to 0, the modem initialisation algorithm gives 
     priority to reach the maximum bit rate. In this case,
     the algorithm could initialise with a lower delay than
     the one specified with the maxDelay parameter."
    ::= { adslProprietaryLineConfProfileXEntry 21 } 

adslAturProprietaryChanConfXOptimiseImpulseNoiseResilienceFast OBJECT-TYPE
    SYNTAX      INTEGER { impulseNoiseProtection (1), reachMaximumBitRate (0) } 
    MAX-ACCESS  read-write
    STATUS      obsolete
    DESCRIPTION
    "Flag: when set to 1 the modem initialisation algorithm
     gives priority to the impulse noise protection. When 
     set to 0, the modem initialisation algorithm gives 
     priority to reach the maximum bit rate. In this case,
     the algorithm could initialise with a lower delay than
     the one specified with the maxDelay parameter."
    ::= { adslProprietaryLineConfProfileXEntry 22 } 

adslAtucProprietaryConfXBoostFactor OBJECT-TYPE
    SYNTAX      Integer32 (192..223)  
    MAX-ACCESS  read-write
    STATUS      current
    DESCRIPTION
    "Applies an additional upstream power boost.
     Bits[4:0] - A five bit value X, indicating the boost factor
     Bits[7:5] - Set to 0x06 to enable, otherwise the boost factor is ignored.
     The applied upstream mean gi in dB expressed by the boost factor X is:
     10log10(1+X/64)"
    ::= { adslProprietaryLineConfProfileXEntry 23 } 

adslAtucProprietaryConfXMaxRxPower OBJECT-TYPE
    SYNTAX      Integer32 (-255..255) 
    UNITS       "0.1 dBm"
    MAX-ACCESS  read-write
    STATUS      current
    DESCRIPTION
    "Maximum receive power at the ATUC. Unit is 0.1 dBm. The ATUC
     will request an Upstream Power Cutback such that the power
     received at the CO modem is not higher than MaxRxPower."
    ::= { adslProprietaryLineConfProfileXEntry 24 } 

adslAtucProprietaryConfXDeltaPsdNormal OBJECT-TYPE
    SYNTAX      Integer32 (-400..40) 
    UNITS       "0.1 dBm/Hz"
    MAX-ACCESS  read-write
    STATUS      current
    DESCRIPTION
    "Delta PSD expressed in dBm: unit is 0.1 dBm/Hz.
     Defines a delta with respect to the protocols
     maximum nominal PSD value in the downstream direction.
     The allowed range is -40 to 4 dBm/Hz.
     Maps into HMI: protocolSpecificLinkConfig[DS].maxTxDeltaPsd[PSD_NORMAL]."
    ::= { adslProprietaryLineConfProfileXEntry 25 } 

adslAtucProprietaryConfXDeltaPsdPlus OBJECT-TYPE
    SYNTAX      Integer32 (-400..40) 
    UNITS       "0.1 dBm/Hz"
    MAX-ACCESS  read-write
    STATUS      current
    DESCRIPTION
    "Delta PSD expressed in dBm: unit is 0.1 dBm/Hz.
     Defines a delta with respect to the protocols
     maximum nominal PSD value in the downstream direction.
     The allowed range is -40 to 4 dBm/Hz.
     Maps into HMI: protocolSpecificLinkConfig[DS].maxTxDeltaPsd[PSD_PLUS]."
    ::= { adslProprietaryLineConfProfileXEntry 26 } 

adslAtucProprietaryConfXDeltaPsdReach OBJECT-TYPE
    SYNTAX      Integer32 (-400..40) 
    UNITS       "0.1 dBm/Hz"
    MAX-ACCESS  read-write
    STATUS      current
    DESCRIPTION
    "Delta PSD expressed in dBm: unit is 0.1 dBm/Hz.
     Defines a delta with respect to the protocols
     maximum nominal PSD value in the downstream direction.
     The allowed range is -40 to 4 dBm/Hz.
     Maps into HMI: protocolSpecificLinkConfig[DS].maxTxDeltaPsd[PSD_REACH]."
    ::= { adslProprietaryLineConfProfileXEntry 27 } 

adslAturProprietaryConfXDeltaPsdNormal OBJECT-TYPE
    SYNTAX      Integer32 (-400..40) 
    UNITS       "0.1 dBm/Hz"
    MAX-ACCESS  read-write
    STATUS      current
    DESCRIPTION
    "Delta PSD expressed in dBm: unit is 0.1 dBm/Hz.
     Defines a delta with respect to the protocols
     maximum nominal PSD value in the upstream direction.
     The allowed range is -40 to 4 dBm/Hz.
     Maps into HMI: protocolSpecificLinkConfig[US].maxTxDeltaPsd[PSD_NORMAL]."
    ::= { adslProprietaryLineConfProfileXEntry 28 } 

adslAturProprietaryConfXDeltaPsdPlus OBJECT-TYPE
    SYNTAX      Integer32 (-400..40) 
    UNITS       "0.1 dBm/Hz"
    MAX-ACCESS  read-write
    STATUS      current
    DESCRIPTION
    "Delta PSD expressed in dBm: unit is 0.1 dBm/Hz.
     Defines a delta with respect to the protocols
     maximum nominal PSD value in the upstream direction.
     The allowed range is -40 to 4 dBm/Hz.
     Maps into HMI: protocolSpecificLinkConfig[US].maxTxDeltaPsd[PSD_PLUS]."
    ::= { adslProprietaryLineConfProfileXEntry 29 } 

adslAturProprietaryConfXDeltaPsdReach OBJECT-TYPE
    SYNTAX      Integer32 (-400..40) 
    UNITS       "0.1 dBm/Hz"
    MAX-ACCESS  read-write
    STATUS      current
    DESCRIPTION
    "Delta PSD expressed in dBm: unit is 0.1 dBm/Hz.
     Defines a delta with respect to the protocols
     maximum nominal PSD value in the upstream direction.
     The allowed range is -40 to 4 dBm/Hz.
     Maps into HMI: protocolSpecificLinkConfig[US].maxTxDeltaPsd[PSD_REACH]."
    ::= { adslProprietaryLineConfProfileXEntry 30 } 

adslAtucProprietaryConfXAutomodePIalpha OBJECT-TYPE
    SYNTAX      INTEGER (1..255)
    MAX-ACCESS  read-write
    STATUS      current
    DESCRIPTION
    "Automode performance index alpha.
     The allowed range is 1 to 255.
     Maps into HMI: PhysicalLayerConfig.automodePIalpha."
    ::= { adslProprietaryLineConfProfileXEntry 31 } 

adslAtucProprietaryConfXAutomodePIbeta OBJECT-TYPE
    SYNTAX      INTEGER (1..255)
    MAX-ACCESS  read-write
    STATUS      current
    DESCRIPTION
    "Automode performance index beta.
     The allowed range is 1 to 255.
     Maps into HMI: PhysicalLayerConfig.automodePIbeta."
    ::= { adslProprietaryLineConfProfileXEntry 32 } 

adslAtucProprietaryConfXOptionsFlagBit4 OBJECT-TYPE
    SYNTAX      INTEGER { disableDiagnosticMode (0), enableDiagnosticMode (1) }
    MAX-ACCESS  read-write
    STATUS      current
    DESCRIPTION
    "Diagnostic mode (ADSL2 only).
     Possible values are:
     0 - Diagnostic mode disabled
     1 - Diagnostic mode enabled.
     Maps into HMI: PhysicalLayerConfig.optionFlags Bit[4]."
    ::= { adslProprietaryLineConfProfileXEntry 33 } 
       
adslAtucProprietaryConfXAdslPlusTxFilterId OBJECT-TYPE
    SYNTAX      INTEGER (0..15)
    MAX-ACCESS  read-write
    STATUS      current
    DESCRIPTION
    "Additional Tx filter setting for G.992.5 (ADSL2+).
     The allowed range is 0 to 15.
     Maps into HMI: PhysicalLayerConfig.adslPlusTxFilterId."
    ::= { adslProprietaryLineConfProfileXEntry 34 } 

adslAtucProprietaryConfXDisableUS1bitConst OBJECT-TYPE
    SYNTAX      INTEGER { enableUS1bitConst (0), disableUS1bitConst (1) }
    MAX-ACCESS  read-write
    STATUS      current
    DESCRIPTION
    "0 - Enable upstream 1 bit constellation
     1 - Disable upstream 1 bit constellation.
     Maps into HMI: TestConfigMessage.disableUS1bitConst."
    ::= { adslProprietaryLineConfProfileXEntry 35 } 

adslAtucProprietaryConfXDisableWindowing OBJECT-TYPE
    SYNTAX      INTEGER { enableWindowing (0), disableWindowing (1) }
    MAX-ACCESS  read-write
    STATUS      current
    DESCRIPTION
    "0 - Enable the transmit windowing
     1 - Disable the transmit windowing.
     Maps into HMI: TestConfigMessage.disableWindowing."
    ::= { adslProprietaryLineConfProfileXEntry 36 } 

adslAtucProprietaryConfXDisableShowtimeExit OBJECT-TYPE
    SYNTAX      INTEGER { enableShowtimeExit (0), disableShowtimeExit (1) }
    MAX-ACCESS  read-write
    STATUS      current
    DESCRIPTION
    "0 - Enable exit from showtime if CPE doesn't reply to GetCounter overhead message
     1 - Disable exit from showtime if CPE doesn't reply to GetCounter overhead message.
     Maps into HMI: TestConfigMessage.disableShowtimeExit."
    ::= { adslProprietaryLineConfProfileXEntry 37 } 

adslAtucProprietaryConfXDisableNitro OBJECT-TYPE
    SYNTAX      INTEGER { enableNitro (0), disableNitro (1) }
    MAX-ACCESS  read-write
    STATUS      current
    DESCRIPTION
    "0 - Enable BCM Nitro feature
     1 - Disable BCM Nitro feature.
     Maps into HMI: TestConfigMessage.disableNitro."
    ::= { adslProprietaryLineConfProfileXEntry 38 } 

adslAtucProprietaryConfXDisableUpdateTestParameters OBJECT-TYPE
    SYNTAX      INTEGER { enableUpdateTestParameters (0), disableUpdateTestParameters (1) }
    MAX-ACCESS  read-write
    STATUS      current
    DESCRIPTION
    "0 - Enable automatic test parameters update
     1 - Disable automatic test parameters update.
     Maps into HMI: TestConfigMessage.disableUpdateTestParameters."
    ::= { adslProprietaryLineConfProfileXEntry 39 } 

adslAtucProprietaryConfXTssiShapeNrOfBreakPoints OBJECT-TYPE
    SYNTAX      INTEGER (0..16)
    MAX-ACCESS  read-write
    STATUS      current
    DESCRIPTION
    "Configuration of custom TssiShape in showtime.
     Number of breakpoints (0 - disables custom TssiShape).
     Maps into HMI: PhysicalLayerConfig.customTssiShape.
     Must be configured while adsl_ifAdminStatus is down"
    ::= { adslProprietaryLineConfProfileXEntry 40 }
    
adslAtucProprietaryConfXTssiShapeAdsl2ProtocolType OBJECT-TYPE
    SYNTAX      OCTET STRING  (SIZE (1))
    MAX-ACCESS  read-write
    STATUS      current
    DESCRIPTION
    "Configuration of custom TssiShape in showtime.
     ADSL2 protocol (0 - disables custom TssiShape).
     bit_0: G.992.3 Annex A/B/J
     bit_1: G.992.5 Annex A/B/M
     bit_2: G.992.3 Annex L
     Maps into HMI: PhysicalLayerConfig.customTssiShape.
     Must be configured while adsl_ifAdminStatus is down"
    ::= { adslProprietaryLineConfProfileXEntry 41 } 
    
adslAtucProprietaryConfXTssiShapeBreakPoint OBJECT-TYPE
    SYNTAX      OCTET STRING  (SIZE (32))
    MAX-ACCESS  read-write
    STATUS      current
    DESCRIPTION
    "Configuration of custom TssiShape for showtime.
     Defines 16 break points which maps into HMI:
     PhysicalLayerConfig.customTssiShape[0-15].
     The bitmap for each breakpoint:
     bit_0-6:   log Tssi in 0.5 db, [0,-62]
     bit_7-15:  ToneIndex, [0,511]
     Must be configured while adsl_ifAdminStatus is down"
    ::= { adslProprietaryLineConfProfileXEntry 42 } 
    
adslAtucProprietaryChanConfXINPminIlvB0 OBJECT-TYPE
    SYNTAX      INTEGER { 	noINP (0),
    						halfDmtSymbolINP(1),
                            oneDmtSymbolINP(2),
                            twoDmtSymbolINP(3),
    					  	fourDmtSymbolINP(4),
                            eightDmtSymbolINP(5),
                            sixteenDmtSymbolINP(6)	} 
    MAX-ACCESS  read-write
    STATUS      current
    DESCRIPTION
    "Impulse Noise Protection in number of DMT symbols
     according to G.992.3.
     Possible values are:
     0	-> 	No protection
     1	->	1/2 DMT symbol protection
     2	->	1 DMT symbol protection
     3	->	2 DMT symbol protection
     4	->	4 DMT symbol protection
     5	->	8 DMT symbol protection
     6	->	16 DMT symbol protection
     Note that the INP value must match the configured
     maximum delay to form a feasible profile"
    ::= { adslProprietaryLineConfProfileXEntry 43 } 

adslAtucProprietaryChanConfXINPminFastB0 OBJECT-TYPE
    SYNTAX      INTEGER { 	noINP (0),
    						halfDmtSymbolINP(1),
                            oneDmtSymbolINP(2),
                            twoDmtSymbolINP(3),
    					  	fourDmtSymbolINP(4),
                            eightDmtSymbolINP(5),
                            sixteenDmtSymbolINP(6)	} 
    MAX-ACCESS  read-write
    STATUS      current
    DESCRIPTION
    "Impulse Noise Protection in number of DMT symbols
     according to G.992.3.
     Possible values are:
     0	-> 	No protection
     1	->	1/2 DMT symbol protection
     2	->	1 DMT symbol protection
     3	->	2 DMT symbol protection
     4	->	4 DMT symbol protection
     5	->	8 DMT symbol protection
     6	->	16 DMT symbol protection
     Note that the INP value must match the configured
     maximum delay to form a feasible profile"
    ::= { adslProprietaryLineConfProfileXEntry 44 } 

adslAtucProprietaryChanConfXINPminFastB1 OBJECT-TYPE
    SYNTAX      INTEGER { 	noINP (0),
    						halfDmtSymbolINP(1),
                            oneDmtSymbolINP(2),
                            twoDmtSymbolINP(3),
    					  	fourDmtSymbolINP(4),
                            eightDmtSymbolINP(5),
                            sixteenDmtSymbolINP(6)	} 
    MAX-ACCESS  read-write
    STATUS      current
    DESCRIPTION
    "Impulse Noise Protection in number of DMT symbols
     according to G.992.3.
     Possible values are:
     0	-> 	No protection
     1	->	1/2 DMT symbol protection
     2	->	1 DMT symbol protection
     3	->	2 DMT symbol protection
     4	->	4 DMT symbol protection
     5	->	8 DMT symbol protection
     6	->	16 DMT symbol protection
     Note that the INP value must match the configured
     maximum delay to form a feasible profile"
    ::= { adslProprietaryLineConfProfileXEntry 45 } 
    
adslAturProprietaryChanConfXINPminIlvB0 OBJECT-TYPE
    SYNTAX      INTEGER { 	noINP (0),
    						halfDmtSymbolINP(1),
                            oneDmtSymbolINP(2),
                            twoDmtSymbolINP(3),
    					  	fourDmtSymbolINP(4),
                            eightDmtSymbolINP(5),
                            sixteenDmtSymbolINP(6)	} 
    MAX-ACCESS  read-write
    STATUS      current
    DESCRIPTION
    "Impulse Noise Protection in number of DMT symbols
     according to G.992.3.
     Possible values are:
     0	-> 	No protection
     1	->	1/2 DMT symbol protection
     2	->	1 DMT symbol protection
     3	->	2 DMT symbol protection
     4	->	4 DMT symbol protection
     5	->	8 DMT symbol protection
     6	->	16 DMT symbol protection
     Note that the INP value must match the configured
     maximum delay to form a feasible profile"
    ::= { adslProprietaryLineConfProfileXEntry 46 } 

adslAturProprietaryChanConfXINPminFastB0 OBJECT-TYPE
    SYNTAX      INTEGER { 	noINP (0),
    						halfDmtSymbolINP(1),
                            oneDmtSymbolINP(2),
                            twoDmtSymbolINP(3),
    					  	fourDmtSymbolINP(4),
                            eightDmtSymbolINP(5),
                            sixteenDmtSymbolINP(6)	} 
    MAX-ACCESS  read-write
    STATUS      current
    DESCRIPTION
    "Impulse Noise Protection in number of DMT symbols
     according to G.992.3.
     Possible values are:
     0	-> 	No protection
     1	->	1/2 DMT symbol protection
     2	->	1 DMT symbol protection
     3	->	2 DMT symbol protection
     4	->	4 DMT symbol protection
     5	->	8 DMT symbol protection
     6	->	16 DMT symbol protection
     Note that the INP value must match the configured
     maximum delay to form a feasible profile"
    ::= { adslProprietaryLineConfProfileXEntry 47 } 
    
adslAturProprietaryChanConfXINPminFastB1 OBJECT-TYPE
    SYNTAX      INTEGER { 	noINP (0),
    						halfDmtSymbolINP(1),
                            oneDmtSymbolINP(2),
                            twoDmtSymbolINP(3),
    					  	fourDmtSymbolINP(4),
                            eightDmtSymbolINP(5),
                            sixteenDmtSymbolINP(6)	} 
    MAX-ACCESS  read-write
    STATUS      current
    DESCRIPTION
    "Impulse Noise Protection in number of DMT symbols
     according to G.992.3.
     Possible values are:
     0	-> 	No protection
     1	->	1/2 DMT symbol protection
     2	->	1 DMT symbol protection
     3	->	2 DMT symbol protection
     4	->	4 DMT symbol protection
     5	->	8 DMT symbol protection
     6	->	16 DMT symbol protection
     Note that the INP value must match the configured
     maximum delay to form a feasible profile"
    ::= { adslProprietaryLineConfProfileXEntry 48 } 

adslAtucProprietaryConfXOptionsFlagBit5 OBJECT-TYPE
    SYNTAX      INTEGER { disableExtraTxLPF (0), enableExtraTxLPF (1) }
    MAX-ACCESS  read-write
    STATUS      deprecated
    DESCRIPTION
    "Custom PSD mask with extra Tx LPF.
     By enabling this feature an extra Tx LPF with a cutoff
     frequency at 950kHz and >27 dB attenuation above 1.5 MHz is
     inserted.
     Made deprecated. Use the adslEnableACIF instead.
     
     Valid from:                EDA 1.3 Rxx
     Deprecated from:           EDA 2.0 SP1
     
     Possible values are:
     0 - Extra TX LPF disabled
     1 - Extra TX LPF enabled.
     Maps into HMI: PhysicalLayerConfig.optionFlags Bit[5]."
    ::= { adslProprietaryLineConfProfileXEntry 49 } 

adslAtucProprietaryConfXDisableShalfOptionBit0 OBJECT-TYPE
    SYNTAX      INTEGER { enableShalfOption (0), disableShalfOption (1) }
    MAX-ACCESS  read-write
    STATUS      current
    DESCRIPTION
    "Possible values are:
     0 - enable S = 1/2 in ADSL1
     1 - disable S = 1/2 in ADSL1
     Maps into HMI: TestConfigMessage.disableShalfOption Bit[0].
     Note that use of this option bit is restricted in EDA due
     to the impact on selected latency mode."
    ::= { adslProprietaryLineConfProfileXEntry 50 } 
    
adslAtucProprietaryConfXDisableShalfOptionBit1 OBJECT-TYPE
    SYNTAX      INTEGER { enableShalfOptionAllCpe (0), disableShalfOptionCertainCpe (1) }
    MAX-ACCESS  read-write
    STATUS      current
    DESCRIPTION
    "Possible values are:
     0 - accept all CPE's 
     1 - ignore certain CPE reporting S = 1/2 support in R-MSG1.
     Maps into HMI: TestConfigMessage.disableShalfOption Bit[1].
     Note that use of this option bit is restricted in EDA due
     to the impact on selected latency mode."
    ::= { adslProprietaryLineConfProfileXEntry 51 }

adslAtucProprietaryConfXDisableLargeD OBJECT-TYPE
    SYNTAX      INTEGER { normal (0), disableLargeD (1) }
    MAX-ACCESS  read-write
    STATUS      current
    DESCRIPTION
    "Disables possible selection of a DS interleaving depth
     (D) greater than 64.
     0 - normal operation
     1 - disable DS interleave depth > 64
     Note: This parameter is used for ADSL protocols only."
    ::= { adslProprietaryLineConfProfileXEntry 52 } 

adslAtucProprietaryConfXForceSegmentation OBJECT-TYPE
    SYNTAX      INTEGER { normal (0), forceSeg (1) }
    MAX-ACCESS  read-write
    STATUS      current
    DESCRIPTION
    "0 - normal operation
     1 - force segmentation of overhead msgs > 10 bytes
     Maps into HMI: TestConfigMessage.forceSegmentation."
    ::= { adslProprietaryLineConfProfileXEntry 53 } 
    
adslAtucProprietaryConfXRelaxInpMinCheck OBJECT-TYPE
    SYNTAX      INTEGER { strictly (0), acceptINP3 (1) }
    MAX-ACCESS  read-write
    STATUS      current
    DESCRIPTION
    "0 - strictly obay the config INP 
     1 - accept INPminDS=3 even if (config) INPmin > 3
     Maps into HMI: TestConfigMessage.relaxInpMinCheck."
    ::= { adslProprietaryLineConfProfileXEntry 54 } 

adslAtucProprietaryConfXhsTxPSD0 OBJECT-TYPE
    SYNTAX      INTEGER (-128..-32)
    UNITS       "1 dBm/Hz"
    MAX-ACCESS  read-write
    STATUS      current
    DESCRIPTION
    "-128 is a special value indicating that this
     carrier set shall not be transmitted.
     Maps into HMI: PhysicalLayerConfig.hsTxPSD[0]."
    ::= { adslProprietaryLineConfProfileXEntry 55 } 

adslAtucProprietaryConfXhsTxPSD1 OBJECT-TYPE
    SYNTAX      INTEGER (-128..-32)
    UNITS       "1 dBm/Hz"
    MAX-ACCESS  read-write
    STATUS      current
    DESCRIPTION
    "-128 is a special value indicating that this
     carrier set shall not be transmitted.
     Maps into HMI: PhysicalLayerConfig.hsTxPSD[1]."
    ::= { adslProprietaryLineConfProfileXEntry 56 } 
                                        
adslAtucProprietaryConfXhsTxPSD2 OBJECT-TYPE
    SYNTAX      INTEGER (-128..-32)
    UNITS       "1 dBm/Hz"
    MAX-ACCESS  read-write
    STATUS      current
    DESCRIPTION
    "-128 is a special value indicating that this
     carrier set shall not be transmitted.
     Maps into HMI: PhysicalLayerConfig.hsTxPSD[2]."
    ::= { adslProprietaryLineConfProfileXEntry 57 } 

adslAtucProprietaryChanMinL2BitRateB0 OBJECT-TYPE	 
    SYNTAX      INTEGER (0..128000)
    UNITS       "kbps"
    MAX-ACCESS  read-write
    STATUS      current
    DESCRIPTION
    "The threshold for L2 entry. If the mean rate is
     below MinL2BitRate for L2LowRateSlots the L2 mode
     is entered (CO side initiated L2 entry).
     Valid range is [0..minBitRateDS]
     Maps into HMI: SetLineTrafficConfig.minL2BitRate."
    ::= { adslProprietaryLineConfProfileXEntry 58 } 
    
adslAtucProprietaryChanMinL2BitRateB1 OBJECT-TYPE	 
    SYNTAX      INTEGER (0..128000)
    UNITS       "kbps"
    MAX-ACCESS  read-write
    STATUS      current
    DESCRIPTION
    "The threshold for L2 entry. If the mean rate is
     below MinL2BitRate for L2LowRateSlots the L2 mode
     is entered (CO side initiated L2 entry).
     Valid range is [0..minBitRateDS]
     Maps into HMI: SetLineTrafficConfig.minL2BitRate."
    ::= { adslProprietaryLineConfProfileXEntry 59 } 
    
adslAtucProprietaryChanL2LowRateSlotsB0 OBJECT-TYPE
    SYNTAX      INTEGER (0..65535)
    UNITS       "seconds"
    MAX-ACCESS  read-write
    STATUS      current
    DESCRIPTION
    "The time interval for L2 entry. If the mean rate is
     below MinL2BitRate for L2LowRateSlots the L2 mode
     is entered (CO side initiated L2 entry).
     Valid range is [0..65535]
     Value 0 disables automatic power management.
     Maps into HMI: SetLineTrafficConfig.L2LowRateSlots."
    ::= { adslProprietaryLineConfProfileXEntry 60 } 
    
adslAtucProprietaryChanL2LowRateSlotsB1 OBJECT-TYPE
    SYNTAX      INTEGER (0..65535)
    UNITS       "seconds"
    MAX-ACCESS  read-write
    STATUS      current
    DESCRIPTION
    "The time interval for L2 entry. If the mean rate is
     below MinL2BitRate for L2LowRateSlots the L2 mode
     is entered (CO side initiated L2 entry).
     Valid range is [0..65535]
     Value 0 disables automatic power management.
     Maps into HMI: SetLineTrafficConfig.L2LowRateSlots."
    ::= { adslProprietaryLineConfProfileXEntry 61 } 
    
adslAtucProprietaryChanL2PacketB0 OBJECT-TYPE
    SYNTAX      INTEGER (0..28)
    UNITS       "ATM cells"
    MAX-ACCESS  read-write
    STATUS      current
    DESCRIPTION
    "The UTOPIA output buffer threshold that triggers
     L0 entry (CO side initiated L0 entry).
     Valid range is [0..28]
     Maps into HMI: SetLineTrafficConfig.L2Packet."
    ::= { adslProprietaryLineConfProfileXEntry 62 } 
    
adslAtucProprietaryChanL2PacketB1 OBJECT-TYPE
    SYNTAX      INTEGER (0..28)
    UNITS       "ATM cells"
    MAX-ACCESS  read-write
    STATUS      current
    DESCRIPTION
    "The UTOPIA output buffer threshold that triggers
     L0 entry (CO side initiated L0 entry).
     Valid range is [0..28]
     Maps into HMI: SetLineTrafficConfig.L2Packet."
    ::= { adslProprietaryLineConfProfileXEntry 63 } 
    
adslAtucProprietaryChanMaxL2BitRateB0 OBJECT-TYPE
    SYNTAX      INTEGER (0..32000)
    UNITS       "kbps"
    MAX-ACCESS  read-write
    STATUS      current
    DESCRIPTION
    "The threshold value for initiating L0 entry. (CPE side
     initiated L0 entry).
     Valid range is [minL2BitRate..maxBitRateDS]
     Maps into HMI: SetLineTrafficConfig.minL2BitRate."
    ::= { adslProprietaryLineConfProfileXEntry 64 } 

adslAtucProprietaryChanMaxL2BitRateB1 OBJECT-TYPE
    SYNTAX      INTEGER (0..32000)
    UNITS       "kbps"
    MAX-ACCESS  read-write
    STATUS      current
    DESCRIPTION
    "The value used for initiating L0 entry. (CPE side
     initiated L0 entry).
     Valid range is [minL2BitRate..maxBitRateDS]
     Maps into HMI: SetLineTrafficConfig.maxL2BitRate."
    ::= { adslProprietaryLineConfProfileXEntry 65 } 
    
adslAtucProprietaryL2TestConfigBit0 OBJECT-TYPE
    SYNTAX      INTEGER { enableAutoL2Entry(0), disableAutoL2Entry(1) }
    MAX-ACCESS  read-write
    STATUS      current
    DESCRIPTION
    "L2TestConfig bit mask:
     	Bit[0]: Disable autonomous L2 entry/exit.
     	Bit[1]: Disable autonomous L2 power trim.
     	Bit[2]: Overrule L2 min/max rate calculation.
     Maps into HMI: SetLineTestConfig.L2TestConfig."
    ::= { adslProprietaryLineConfProfileXEntry 66 } 

adslAtucProprietaryL2TestConfigBit1 OBJECT-TYPE
    SYNTAX      INTEGER { enableAutoL2PwrTrim(0), disableAutoL2PwrTrim(1) }
    MAX-ACCESS  read-write
    STATUS      current
    DESCRIPTION
    "L2TestConfig bit mask:
     	Bit[0]: Disable autonomous L2 entry/exit.
     	Bit[1]: Disable autonomous L2 power trim.
     	Bit[2]: Overrule L2 min/max rate calculation.
     Maps into HMI: SetLineTestConfig.L2TestConfig."
    ::= { adslProprietaryLineConfProfileXEntry 67 } 
    
adslAtucProprietaryL2TestConfigBit2 OBJECT-TYPE
    SYNTAX      INTEGER { useL2RateCalc(0), overruleL2RateCalc(1) }
    MAX-ACCESS  read-write
    STATUS      current
    DESCRIPTION
    "L2TestConfig bit mask:
     	Bit[0]: Disable autonomous L2 entry/exit.
     	Bit[1]: Disable autonomous L2 power trim.
     	Bit[2]: Overrule L2 min/max rate calculation.
     Maps into HMI: SetLineTestConfig.L2TestConfig."
    ::= { adslProprietaryLineConfProfileXEntry 68 } 
    
    
adslAtucProprietaryL2MinAtpr OBJECT-TYPE
    SYNTAX      INTEGER (0..15)
    UNITS       "dB"
    MAX-ACCESS  read-write
    STATUS      current
    DESCRIPTION
    "Minimum power reduction at L2 entry.
     Valid range is [0..15]
     Maps into HMI: SetLineTrafficConfig.L2MinAtpr."
    ::= { adslProprietaryLineConfProfileXEntry 69 }
    
adslAtucProprietaryL0Time OBJECT-TYPE
    SYNTAX      INTEGER (0..65535)
    UNITS       "seconds"
    MAX-ACCESS  read-write
    STATUS      current
    DESCRIPTION
    "Minimum time in L0 before L2 entry.
     Valid range is [0..65535]
     Maps into HMI: SetLinePhysicalConfig.L0Time."
    ::= { adslProprietaryLineConfProfileXEntry 70 }
    
adslAtucProprietaryL2Time OBJECT-TYPE
    SYNTAX      INTEGER (0..65535)
    UNITS       "seconds"
    MAX-ACCESS  read-write
    STATUS      current
    DESCRIPTION
    "Minimum time in L2 before L0 entry.
     Valid range is [0..65535]
     Maps into HMI: SetLinePhysicalConfig.L2Time."
    ::= { adslProprietaryLineConfProfileXEntry 71 }
    
adslAtucProprietaryL2Atpr OBJECT-TYPE
    SYNTAX      INTEGER (0..31)
    UNITS       "dB"
    MAX-ACCESS  read-write
    STATUS      current
    DESCRIPTION
    "Maximum aggregate transmit power reduction per
     L2 trim.
     Valid range is [0..31]
     Maps into HMI: SetLinePhysicalConfig.L2Atpr."
    ::= { adslProprietaryLineConfProfileXEntry 72 }
    
adslAtucProprietaryL2Atprt OBJECT-TYPE
    SYNTAX      INTEGER (0..31)
    UNITS       "dB"
    MAX-ACCESS  read-write
    STATUS      current
    DESCRIPTION
    "Maximum total aggregate transmit power reduction
     in L2 trim mode.
     Valid range is [0..31]
     Maps into HMI: SetLinePhysicalConfig.L2Atprt."
    ::= { adslProprietaryLineConfProfileXEntry 73 }

adslAtucProprietaryRateAdaptationFlagsBit0Upstream OBJECT-TYPE
    SYNTAX      INTEGER { disableSnrMinimum (0), enableSnrMinimum (1) }
    MAX-ACCESS  read-write
    STATUS      current
    DESCRIPTION
    "Possible values are:
     0 - enable minimum SNR margin functionality
     1 - disable minimum SNR margin functionality
     Maps into HMI: SetLinePhysicalConfig.linkconfig[US].rateAdaptationFlags."
    ::= { adslProprietaryLineConfProfileXEntry 74 }
    
adslAtucProprietaryRateAdaptationFlagsBit0Downstream OBJECT-TYPE
    SYNTAX      INTEGER { disableSnrMinimum (0), enableSnrMinimum (1) }
    MAX-ACCESS  read-write
    STATUS      current
    DESCRIPTION
    "Possible values are:
     0 - enable minimum SNR margin functionality
     1 - disable minimum SNR margin functionality
     Maps into HMI: SetLinePhysicalConfig.linkconfig[DS].rateAdaptationFlags."
    ::= { adslProprietaryLineConfProfileXEntry 75 }

adslAtucValidRateExtension OBJECT-TYPE
    SYNTAX      INTEGER (0..255)
    UNITS       "kb/s"
    MAX-ACCESS  read-write
    STATUS      current
    DESCRIPTION
    "Some ADSL2(+) CPE's do not strictly comply to the rate constrains
	 negotiated during G.hs. To avoid initialization failure with those CPE's
     the rate check can be relaxed by a configurable value, allowing to
     extend the allowed rate interval"
    ::= { adslProprietaryLineConfProfileXEntry 76 }

adslAtucProprietaryConfXMsgMinDS OBJECT-TYPE
    SYNTAX		INTEGER (4..28)
    UNITS       "kb/s"
    MAX-ACCESS	read-write
    STATUS		current
    DESCRIPTION
    "This is minimum framing overhead for down stream.Allowed range is 4 to 28 inclusive of them."
    ::= { adslProprietaryLineConfProfileXEntry 77 }

adslAtucProprietaryConfXMsgMinUS OBJECT-TYPE
	SYNTAX		INTEGER (4..28)
    UNITS		"kb/s"
    MAX-ACCESS	read-write
    STATUS 		current
    DESCRIPTION
    "This is minimum framing overhead for up stream.Allowed range is 4 to 28 inclusive of them."
    ::={ adslProprietaryLineConfProfileXEntry 78 }

adslAturProprietaryConfXUsBitSwapBehavior OBJECT-TYPE
    SYNTAX      INTEGER {classicUsBitswaps (0), fullBandUsBitswaps  (1) }
    MAX-ACCESS  read-write
    STATUS      current
    DESCRIPTION
    "The adslAturProprietaryConfXUsBitSwapBehavior has effect only if the 
     upstream bitswap is enabled in adslAturProprietaryConfXDisableBitSwap. The 
     adslAturProprietaryConfXUsBitSwapBehavior controls the behaviour of 
     the upstream bitswap:
     0 - Classic upstream bitswaps
     1 - FullBand upstream bitswaps."
    ::= { adslProprietaryLineConfProfileXEntry 79 } 
    
adslAtucProprietaryConfXStrictPerCheck OBJECT-TYPE
    SYNTAX      INTEGER {disableStrictPerCheck (0), enableStrictPerCheck (1) }
    MAX-ACCESS  read-write
    STATUS      current
    DESCRIPTION
    "When enabled, limit SRA such as to respect the
     15 to 20ms PER constraint. Default disabled."
    ::= { adslProprietaryLineConfProfileXEntry 80 } 

adslAtucProprietaryConfXTpsTcType OBJECT-TYPE
    SYNTAX      INTEGER {atm (2), ptm (4), both (6)}
    MAX-ACCESS  read-write
    STATUS      obsolete
    DESCRIPTION
    "Configure allowed traffic type: ATM, PTM or both.

     Valid from:                EDA 2.2 MA2
     Obsoleted from:            EDA 4.0

     Replaced by vdslVtucProprietaryConfXTpsTcType in PEA-VDSL-IPDSLAM"
    ::= { adslProprietaryLineConfProfileXEntry 85 }

adslAtucProprietaryConfXPsdOptimConfig OBJECT-TYPE
    SYNTAX      INTEGER {noOptimisation (0),
    					 optimizeForPsdMaskFilling (1),
                         optimizeShapeForPerformance (2)}
    MAX-ACCESS  read-write
    STATUS      current
    DESCRIPTION
    "This parameter controls the selected PSD optimization modes:
     0: No optimization. A fixed TSSI shape (either the default of
     	the configured shape) is used.
     1: PSD optimization. The TSSI shape that optimally fills the
     	configured PSD mask is computed dynamically.
	 2: PSD shaping. The TSSI shape the provides optimal downstream
      	performance within the PSD mask constraints is computed
        dynamically.
	 Note: Applies to ADSL-only applications."
    ::= { adslProprietaryLineConfProfileXEntry 90 }

adslAtucProprietaryConfXPsdMaskSelectUs  OBJECT-TYPE
    SYNTAX      Unsigned32(1..9)
    MAX-ACCESS  read-write
    STATUS      current
    DESCRIPTION
      "The selected upstream PSD mask.  This parameter is used only
       for annexes J and M of G.992.3 and G.992.5, and the same
       selection is used for all relevant enabled bits in
       xdsl2LConfProfAtuTransSysEna.
       Value	Annex J		Annex M
       1		ADLU-32		EU-32
       2		ADLU-36		EU-36
       3		ADLU-40		EU-40
       4		ADLU-44		EU-44
       5		ADLU-48		EU-48
       6		ADLU-52		EU-52
       7		ADLU-56		EU-56
       8		ADLU-60		EU-60
       9		ADLU-64		EU-64
       Applies only to lines running G.992.3 or G.992.5
       This parameter is copied from draft-ietf-adslmib-vdsl2-01.txt,
       to secure a smooth migration to the VDSL2-LINE MIB when
       this MIB is approved."
    REFERENCE    "ITU-T G.997.1, paragraph 7.3.1.2.11"
    DEFVAL       { 1 }
    ::= { adslProprietaryLineConfProfileXEntry 95 }

adslAtucProprietaryConfXDisableProtocolFallback OBJECT-TYPE
    SYNTAX 		TruthValue
    MAX-ACCESS  read-write
    STATUS      current
    DESCRIPTION
    "This parameter controls the protocol fallback mechanism.
     If set it disables protocol fallback mechanism.
	 Note: Applies to ADSL-only applications."
    ::= { adslProprietaryLineConfProfileXEntry 100 }
    
 --******************************************************************
-- ADSL Proprietary Line Table
--******************************************************************

adslLineXTable   OBJECT-TYPE
    SYNTAX          SEQUENCE OF AdslLineXEntry
    MAX-ACCESS      not-accessible
    STATUS          current
    DESCRIPTION
        "This table is a proprietary extension of RFC2662.
         It contains ADSL line configuration and
         monitoring information. This includes the ATU-(R/C)
         capabilities and actual ADSL transmission system."
      ::= { adslXObjects 19 }

adslLineXEntry   OBJECT-TYPE
    SYNTAX          AdslLineXEntry
    MAX-ACCESS      not-accessible
    STATUS          current
    DESCRIPTION
        "An entry extends the adslLineEntry defined in
         [RFC2662].  Each entry corresponds to an ADSL
         line."
    INDEX { lineIndex }
    ::= { adslLineXTable 1 }

AdslLineXEntry ::=
    SEQUENCE
    {
      adslLineXTransAtucCap        BITS,
      adslLineXTransAtucConfig     BITS,
      adslLineXTransAtucActual     BITS,
      adslLineXTransAturCap        BITS
    }

adslLineXTransAtucCap  OBJECT-TYPE
    SYNTAX      BITS {
        etsiTS101388(0),
        ansiT1413AdslOverPots(1),
        proprietarySadslOverPots(2),
        reserved3(3),
        g9925AnnexMAdsl2PlusOver(4),
        g9925AnnexIAdsl2PlusOver(5),
        g9925AnnexBAdsl2PlusOverIsdn(6),
        g9925AnnexAAdsl2PlusOverPots(7),
        g9923AnnexLAdsl2RENarrowPsdOverPots(8),
        g9923AnnexLAdsl2REOverPots(9),
        g9924AnnexIAdsl2LiteAdmWithPots(10),
        g9924AnnexAAdsl2LiteOverPots(11),
        g9923AnnexMAdsl2AdmWithIsdn(12),
        g9923AnnexIAdsl2AdmWithPots(13),
        g9923AnnexBAdsl2OverIsdn(14),
        g9923AnnexAAdsl2OverPots(15),
        reserved16(16),
        reserved17(17),
        reserved18(18),
        etsiMcmVDSL(19),
        reserved20(20),
        t1McmVDSL(21),
        g99212AnnexBShdslOverTcmIsdnEu(22),
        g99212AnnexAShdslOverTcmIsdnUs(23),
        g9923VDSL2(24),
        g9921AnnexISsdslOverTcmIsdn(25),
        g9921AnnexHSsdslOverTcmIsdn(26),
        g9922AnnexCAdslLiteOverTcmIsdn(27),
        g9922AnnexAAdslLiteOverPots(28),
        g9921AnnexCAdslOverTcmIsdn(29),
        g9921AnnexBAdslOverIsdn(30),
        g9921AnnexAAdslOverPots(31)
    }
    MAX-ACCESS  read-only
    STATUS      current
    DESCRIPTION
        "The transmission modes, represented by a
         bitmask that the ATU-C is capable of
         supporting.  The modes available are limited
         by the design of the equipment."
    REFERENCE "HMI Definition MCS6430F"
    ::= { adslLineXEntry 1 }

adslLineXTransAtucConfig OBJECT-TYPE
    SYNTAX      BITS {
        etsiTS101388(0),
        ansiT1413AdslOverPots(1),
        proprietarySadslOverPots(2),
        reserved3(3),
        g9925AnnexMAdsl2PlusOver(4),
        g9925AnnexIAdsl2PlusOver(5),
        g9925AnnexBAdsl2PlusOverIsdn(6),
        g9925AnnexAAdsl2PlusOverPots(7),
        g9923AnnexLAdsl2RENarrowPsdOverPots(8),
        g9923AnnexLAdsl2REOverPots(9),
        g9924AnnexIAdsl2LiteAdmWithPots(10),
        g9924AnnexAAdsl2LiteOverPots(11),
        g9923AnnexMAdsl2AdmWithIsdn(12),
        g9923AnnexIAdsl2AdmWithPots(13),
        g9923AnnexBAdsl2OverIsdn(14),
        g9923AnnexAAdsl2OverPots(15),
        reserved16(16),
        reserved17(17),
        reserved18(18),
        etsiMcmVDSL(19),
        reserved20(20),
        t1McmVDSL(21),
        g99212AnnexBShdslOverTcmIsdnEu(22),
        g99212AnnexAShdslOverTcmIsdnUs(23),
        g9923VDSL2(24),
        g9921AnnexISsdslOverTcmIsdn(25),
        g9921AnnexHSsdslOverTcmIsdn(26),
        g9922AnnexCAdslLiteOverTcmIsdn(27),
        g9922AnnexAAdslLiteOverPots(28),
        g9921AnnexCAdslOverTcmIsdn(29),
        g9921AnnexBAdslOverIsdn(30),
        g9921AnnexAAdslOverPots(31)
    }
    MAX-ACCESS  read-write
    STATUS      current
    DESCRIPTION
        "The transmission modes, represented by a bitmask,
         currently enabled by the ATU-C.  The manager can
         only set those modes that are supported by the
         ATU-C.  An ATU-C's supported modes are provided by
         adslLineXTransAtucCap. Setting a bit in the mask
         enables the protocol in question."
    REFERENCE "HMI Definition MCS6430F"
    ::= { adslLineXEntry 2 }

adslLineXTransAtucActual OBJECT-TYPE
    SYNTAX      BITS {
        etsiTS101388(0),
        ansiT1413AdslOverPots(1),
        proprietarySadslOverPots(2),
        reserved3(3),
        g9925AnnexMAdsl2PlusOver(4),
        g9925AnnexIAdsl2PlusOver(5),
        g9925AnnexBAdsl2PlusOverIsdn(6),
        g9925AnnexAAdsl2PlusOverPots(7),
        g9923AnnexLAdsl2RENarrowPsdOverPots(8),
        g9923AnnexLAdsl2REOverPots(9),
        g9924AnnexIAdsl2LiteAdmWithPots(10),
        g9924AnnexAAdsl2LiteOverPots(11),
        g9923AnnexMAdsl2AdmWithIsdn(12),
        g9923AnnexIAdsl2AdmWithPots(13),
        g9923AnnexBAdsl2OverIsdn(14),
        g9923AnnexAAdsl2OverPots(15),
        reserved16(16),
        reserved17(17),
        reserved18(18),
        etsiMcmVDSL(19),
        reserved20(20),
        t1McmVDSL(21),
        g99212AnnexBShdslOverTcmIsdnEu(22),
        g99212AnnexAShdslOverTcmIsdnUs(23),
        g9923VDSL2(24),
        g9921AnnexISsdslOverTcmIsdn(25),
        g9921AnnexHSsdslOverTcmIsdn(26),
        g9922AnnexCAdslLiteOverTcmIsdn(27),
        g9922AnnexAAdslLiteOverPots(28),
        g9921AnnexCAdslOverTcmIsdn(29),
        g9921AnnexBAdslOverIsdn(30),
        g9921AnnexAAdslOverPots(31)
    }
    MAX-ACCESS  read-only
    STATUS      current
    DESCRIPTION
        "The actual transmission mode of the ATU-C.
         During ADSL line initialization, the ADSL
         Transceiver Unit - Remote terminal end (ATU-R)
         will determine the mode used for the link.
         This value will be limited a single transmission
         mode that is a subset of those modes enabled
         by the ATU-C and denoted by adslLineXTransAtucConfig.
         After an initialization has occurred, its mode is
         saved as the 'Current' mode and is persistence
         should the link go down."
    REFERENCE "HMI Definition MCS6430F"
    ::= { adslLineXEntry 3 }

adslLineXTransAturCap  OBJECT-TYPE
    SYNTAX      BITS {
        etsiTS101388(0),
        ansiT1413AdslOverPots(1),
        proprietarySadslOverPots(2),
        reserved3(3),
        g9925AnnexMAdsl2PlusOver(4),
        g9925AnnexIAdsl2PlusOver(5),
        g9925AnnexBAdsl2PlusOverIsdn(6),
        g9925AnnexAAdsl2PlusOverPots(7),
        g9923AnnexLAdsl2RENarrowPsdOverPots(8),
        g9923AnnexLAdsl2REOverPots(9),
        g9924AnnexIAdsl2LiteAdmWithPots(10),
        g9924AnnexAAdsl2LiteOverPots(11),
        g9923AnnexMAdsl2AdmWithIsdn(12),
        g9923AnnexIAdsl2AdmWithPots(13),
        g9923AnnexBAdsl2OverIsdn(14),
        g9923AnnexAAdsl2OverPots(15),
        reserved16(16),
        reserved17(17),
        reserved18(18),
        etsiMcmVDSL(19),
        reserved20(20),
        t1McmVDSL(21),
        g99212AnnexBShdslOverTcmIsdnEu(22),
        g99212AnnexAShdslOverTcmIsdnUs(23),
        g9923VDSL2(24),
        g9921AnnexISsdslOverTcmIsdn(25),
        g9921AnnexHSsdslOverTcmIsdn(26),
        g9922AnnexCAdslLiteOverTcmIsdn(27),
        g9922AnnexAAdslLiteOverPots(28),
        g9921AnnexCAdslOverTcmIsdn(29),
        g9921AnnexBAdslOverIsdn(30),
        g9921AnnexAAdslOverPots(31)
    }
    MAX-ACCESS  read-only
    STATUS      current
    DESCRIPTION
        "The transmission modes, represented by a
         bitmask that the ATU-R is capable of
         supporting.  The modes available are limited
         by the design of the equipment."
    REFERENCE "HMI Definition MCS6430F"
    ::= { adslLineXEntry 4 }


--******************************************************************
-- ADSL Proprietary Performance Data Extension Table
--******************************************************************
adslProprietaryPerfDataXTable OBJECT-TYPE
      SYNTAX     SEQUENCE OF AdslProprietaryPerfDataXEntry
      MAX-ACCESS not-accessible
      STATUS     current
      DESCRIPTION
      "ADSL Proprietary Performance Data Extension Table."
      ::= { adslXObjects 20 }

adslProprietaryPerfDataXEntry OBJECT-TYPE
      SYNTAX AdslProprietaryPerfDataXEntry
      MAX-ACCESS  not-accessible
      STATUS      current
      DESCRIPTION
      "An entry in adslProprietaryPerfDataXTable."
      INDEX { lineIndex }
      ::= { adslProprietaryPerfDataXTable 1 }

AdslProprietaryPerfDataXEntry ::=
      SEQUENCE {
        adslProprietaryPerfDataXReset                    INTEGER,
        adslProprietaryPerfDataXSinceResetTimeElapsed    Unsigned32,
        adslProprietaryPerfDataXFailedInits              Counter32
        }

adslProprietaryPerfDataXReset OBJECT-TYPE
    SYNTAX      INTEGER {reset(1)}
    MAX-ACCESS  read-write
    STATUS      current
    DESCRIPTION
    "When set to 'reset' the ADSL line performance total counters
    are reset to 0."
    ::= { adslProprietaryPerfDataXEntry 1 }    
    
adslProprietaryPerfDataXSinceResetTimeElapsed OBJECT-TYPE
    SYNTAX      Unsigned32
    UNITS       "seconds"
    MAX-ACCESS  read-only
    STATUS      current
    DESCRIPTION
    "Elapsed time in seconds since the last reset of
    the ADSL line performance total counters."
    ::= { adslProprietaryPerfDataXEntry 2 }    

adslProprietaryPerfDataXFailedInits OBJECT-TYPE
    SYNTAX      Counter32
    MAX-ACCESS  read-only
    STATUS      current
    DESCRIPTION
    "Count of failed line initialization attempts since agent reset."
    ::= { adslProprietaryPerfDataXEntry 3 }    
    

--******************************************************************
-- ADSL ATU-C Line Quality Threshold
--******************************************************************
adslAtucLineQualityThresholdTable OBJECT-TYPE
      SYNTAX     SEQUENCE OF AdslAtucLineQualityThresholdEntry
      MAX-ACCESS not-accessible
      STATUS     current
      DESCRIPTION
      "This table contains the downstream line quality alarm thresholds.
      Thresholds can be configured on a per channel basis"
      ::= { adslXObjects 21 }

adslAtucLineQualityThresholdEntry OBJECT-TYPE
      SYNTAX AdslAtucLineQualityThresholdEntry
      MAX-ACCESS  not-accessible
      STATUS      current
      DESCRIPTION
      "An entry in adslAtucLineQualityThresholdTable"
      INDEX { lineIndex }
      ::= { adslAtucLineQualityThresholdTable 1 }

AdslAtucLineQualityThresholdEntry ::=
      SEQUENCE {
        adslAtucLineQualityThresChan0 Unsigned32,
        adslAtucLineQualityThresChan1 Unsigned32
        }

adslAtucLineQualityThresChan0 OBJECT-TYPE
      SYNTAX      Unsigned32 
      UNITS       "bps"
      MAX-ACCESS  read-write
      STATUS      current
      DESCRIPTION
      "Line quality alarm threshold for channel 0"
      ::= { adslAtucLineQualityThresholdEntry 1 }

adslAtucLineQualityThresChan1 OBJECT-TYPE
      SYNTAX      Unsigned32 
      UNITS       "bps"
      MAX-ACCESS  read-write
      STATUS      current
      DESCRIPTION
      "Line quality alarm threshold for channel 1"
      ::= { adslAtucLineQualityThresholdEntry 2 }


--******************************************************************
-- ADSL ATU-R Line Quality Threshold
--******************************************************************
adslAturLineQualityThresholdTable OBJECT-TYPE
      SYNTAX     SEQUENCE OF AdslAturLineQualityThresholdEntry
      MAX-ACCESS not-accessible
      STATUS     current
      DESCRIPTION
      "This table contains the upstream line quality alarm thresholds.
      Thresholds can be configured on a per channel basis"
      ::= { adslXObjects 22 }

adslAturLineQualityThresholdEntry OBJECT-TYPE
      SYNTAX AdslAturLineQualityThresholdEntry
      MAX-ACCESS  not-accessible
      STATUS      current
      DESCRIPTION
      "An entry in adslAturLineQualityThresholdTable"
      INDEX { lineIndex }
      ::= { adslAturLineQualityThresholdTable 1 }

AdslAturLineQualityThresholdEntry ::=
      SEQUENCE {
        adslAturLineQualityThresChan0 Unsigned32,
        adslAturLineQualityThresChan1 Unsigned32
        }

adslAturLineQualityThresChan0 OBJECT-TYPE
      SYNTAX      Unsigned32 
      UNITS       "bps"
      MAX-ACCESS  read-write
      STATUS      current
      DESCRIPTION
      "Line quality alarm threshold for channel 0"
      ::= { adslAturLineQualityThresholdEntry 1 }

adslAturLineQualityThresChan1 OBJECT-TYPE
      SYNTAX      Unsigned32 
      UNITS       "bps"
      MAX-ACCESS  read-write
      STATUS      current
      DESCRIPTION
      "Line quality alarm threshold for channel 1"
      ::= { adslAturLineQualityThresholdEntry 2 }

--******************************************************************
-- ADSL Line Bonding Configuration
--******************************************************************
adslLineBondingConfTable OBJECT-TYPE
      SYNTAX     SEQUENCE OF AdslLineBondingConfEntry
      MAX-ACCESS not-accessible
      STATUS     current
      DESCRIPTION
      "This table contains the Line Bonding configuration."
      ::= { adslXObjects 23 }

adslLineBondingConfEntry OBJECT-TYPE
      SYNTAX AdslLineBondingConfEntry
      MAX-ACCESS  not-accessible
      STATUS      current
      DESCRIPTION
      "An entry in adslLineBondingConfTable"
      INDEX { lineIndex }
      ::= { adslLineBondingConfTable 1 }

AdslLineBondingConfEntry ::=
      SEQUENCE {
        adslLineBondGroupAdminStatus 				INTEGER,
        adslLineBondGroupMembers 					BITS,
        adslLineBondDsGroupRateMax 					Unsigned32,
        adslLineBondDsGroupRateMin 					Unsigned32,
        adslLineBondUsGroupRateMax 					Unsigned32,
        adslLineBondUsGroupRateMin 					Unsigned32,
        adslAtucLineBondLineQualityThres 			Unsigned32,
        adslAturLineBondLineQualityThres 			Unsigned32,
        adslAturLineBondLineNoWaitAllBondingLines	TruthValue
        }

adslLineBondGroupAdminStatus OBJECT-TYPE
	  SYNTAX  INTEGER {up(1),down(2)}
      MAX-ACCESS  read-write
      STATUS      current
      DESCRIPTION
      "The desired state of the bonding group."
      ::= { adslLineBondingConfEntry 1 }

adslLineBondGroupMembers OBJECT-TYPE
    SYNTAX      BITS {
                        line16Ch1(0),
                        line16Ch0(1),
                        line15Ch1(2),
                        line15Ch0(3),
                        line14Ch1(4),
                        line14Ch0(5),
                        line13Ch1(6),
                        line13Ch0(7),
                        line12Ch1(8),
                        line12Ch0(9),
                        line11Ch1(10),
                        line11Ch0(11),
                        line10Ch1(12),
                        line10Ch0(13),
                        line9Ch1(14),
                        line9Ch0(15),
                        line8Ch1(16),
                        line8Ch0(17),
                        line7Ch1(18),
                        line7Ch0(19),
                        line6Ch1(20),
                        line6Ch0(21),
                        line5Ch1(22),
                        line5Ch0(23),
                        line4Ch1(24),
                        line4Ch0(25),
                        line3Ch1(26),
                        line3Ch0(27),
                        line2Ch1(28),
                        line2Ch0(29),
                        line1Ch1(30),
                        line1Ch0(31)
                      }
      MAX-ACCESS  read-write
      STATUS      current
      DESCRIPTION
      "Indicates which lines should be bonded in
       in this bonding group. Include main line
       and ordinary member lines. Note that the
       Channel 1 is not yet supported in IP DSLAM."
      ::= { adslLineBondingConfEntry 2 }
      
adslLineBondDsGroupRateMin OBJECT-TYPE
      SYNTAX      Unsigned32 
      UNITS       "bps"
      MAX-ACCESS  read-write
      STATUS      current
      DESCRIPTION
      "The configured minimum DS group rate."
      ::= { adslLineBondingConfEntry 3 }
      
adslLineBondDsGroupRateMax OBJECT-TYPE
      SYNTAX      Unsigned32 
      UNITS       "bps"
      MAX-ACCESS  read-write
      STATUS      current
      DESCRIPTION
      "The configured maximum DS group rate."
      ::= { adslLineBondingConfEntry 4 }

adslLineBondUsGroupRateMin OBJECT-TYPE
      SYNTAX      Unsigned32 
      UNITS       "bps"
      MAX-ACCESS  read-write
      STATUS      current
      DESCRIPTION
      "The configured minimum US group rate."
      ::= { adslLineBondingConfEntry 5 }
      
adslLineBondUsGroupRateMax OBJECT-TYPE
      SYNTAX      Unsigned32 
      UNITS       "bps"
      MAX-ACCESS  read-write
      STATUS      current
      DESCRIPTION
      "The configured maximum US group rate."
      ::= { adslLineBondingConfEntry 6 }

adslAtucLineBondLineQualityThres OBJECT-TYPE
      SYNTAX      Unsigned32 
      UNITS       "bps"
      MAX-ACCESS  read-write
      STATUS      current
      DESCRIPTION
      "Line quality alarm threshold for the bonding group."
      ::= { adslLineBondingConfEntry 7 }
      
adslAturLineBondLineQualityThres OBJECT-TYPE
      SYNTAX      Unsigned32 
      UNITS       "bps"
      MAX-ACCESS  read-write
      STATUS      current
      DESCRIPTION
      "Line quality alarm threshold for the bonding group."
      ::= { adslLineBondingConfEntry 8 }
      
adslAturLineBondLineNoWaitAllBondingLines OBJECT-TYPE
    SYNTAX 		TruthValue
    MAX-ACCESS  read-write
    STATUS      current
    DESCRIPTION
    "This parameter controls bonding mode behaviour.
     If set, this allows the bonding group to be active
     as soon as at least one line is in Showtime.
     Note: This is a non-standardbehavior.."
      ::= { adslLineBondingConfEntry 10 }
      
--******************************************************************
-- ADSL Line Bonding Status
--******************************************************************
adslLineBondingStatusTable OBJECT-TYPE
      SYNTAX     SEQUENCE OF AdslLineBondingStatusEntry
      MAX-ACCESS not-accessible
      STATUS     current
      DESCRIPTION
      "This table contains the stautus information
       of this bonding group."
      ::= { adslXObjects 24 }

adslLineBondingStatusEntry OBJECT-TYPE
      SYNTAX AdslLineBondingStatusEntry
      MAX-ACCESS  not-accessible
      STATUS      current
      DESCRIPTION
      "An entry in adslLineBondingStatusTable."
      INDEX { lineIndex }
      ::= { adslLineBondingStatusTable 1 }

AdslLineBondingStatusEntry ::=
      SEQUENCE {
        adslLineBondGroupOperStatus 	INTEGER,
        adslLineBondGroupActualRateDs	Unsigned32,
        adslLineBondGroupActualRateUs 	Unsigned32
        }

adslLineBondGroupOperStatus OBJECT-TYPE
	  SYNTAX  INTEGER {up(1),down(2)}
      MAX-ACCESS  read-write
      STATUS      current
      DESCRIPTION
      "The operational state of the bonding group.
       When operational state is down, no data
       traffic can be passed."
      ::= { adslLineBondingStatusEntry 1 }

adslLineBondGroupActualRateDs OBJECT-TYPE
      SYNTAX      Unsigned32 
      UNITS       "bps"
      MAX-ACCESS  read-write
      STATUS      current
      DESCRIPTION
      "The actual DS rate for the bonding group."
      ::= { adslLineBondingStatusEntry 2 }
      
adslLineBondGroupActualRateUs OBJECT-TYPE
      SYNTAX      Unsigned32 
      UNITS       "bps"
      MAX-ACCESS  read-write
      STATUS      current
      DESCRIPTION
      "The actual US rate for the bonding group."
      ::= { adslLineBondingStatusEntry 3 }

--******************************************************************
-- No tables reserved for future use:
-- adslXObjects [?]
--******************************************************************

    
--******************************************************************
-- 
--******************************************************************
    
adslTxFilterConfig OBJECT-TYPE
      SYNTAX      OCTET STRING (SIZE (6))
    MAX-ACCESS  read-write
    STATUS      obsolete
    DESCRIPTION
    "TxFilter in ADSL chipset. The txFilterConfig[1..3]
     parameter for the C0 and B0 version of the chipset.
     Bytes [0..2] for CO version and bytes [3..5] for B0
     version.
     NOTE: This parameter must be set from the
     configuration file to take effect!"
    REFERENCE "HMI definition of SetDeviceConfiguration"
    ::= { adslXObjects 25 }   

--******************************************************************
-- 
--******************************************************************
    
adslTxFilterActual OBJECT-TYPE
      SYNTAX      OCTET STRING (SIZE (3))
    MAX-ACCESS  read-only
    STATUS      obsolete
    DESCRIPTION
    "TxFilter in ADSL chipset. The value of the
     txFilterConfig[1..3] acually used in the ADSL
     chipset."
    REFERENCE "HMI definition of SetDeviceConfiguration"
    ::= { adslXObjects 26 }   
    
--******************************************************************
-- 
--******************************************************************
    
adslPowerModes OBJECT-TYPE
      SYNTAX      OCTET STRING (SIZE (8))
    MAX-ACCESS  read-write
    STATUS      current
    DESCRIPTION
    "Power Modes in DSL chipset. The PowerModeData[] in
     the IP DSLAM uses these indexes:
     	POWERDOWN 		= 0
     	ACTIVATION 		= 1
     	SHOWTIME_256 	= 2
     	LINETEST 		= 3
     	SHOWTIME_512 	= 4
     	SHOWTIME_1024 	= 5
     	SHOWTIME_2048 	= 6
     	SHOWTIME_4096 	= 7
     NOTE: This parameter must be set from the
     configuration file to take effect!"
    REFERENCE "HMI definition of SetLineDriverPowerModes"
    ::= { adslXObjects 27 }   

--******************************************************************
-- 
--******************************************************************
    
adslTxPowerCalibration OBJECT-TYPE
    SYNTAX      Integer32 (-511..767) 
    MAX-ACCESS  read-write
    STATUS      current
    DESCRIPTION
    "Tuning the transmit power in ADSL chipset.
     Unit is 1/256 dB. Range ]-2,+3[ dB which
     corresponds to ]-512,+768[.
     NOTE: This parameter must be set from the
     configuration file to take effect!"
    REFERENCE "HMI definition of SetDeviceConfiguration"
    ::= { adslXObjects 28 }   
    
--******************************************************************
-- 
--******************************************************************
    
adslRxPowerCalibration OBJECT-TYPE
    SYNTAX      Integer32 (-1280..2560) 
    MAX-ACCESS  read-write
    STATUS      deprecated
    DESCRIPTION
    "Tuning the received reference power in ADSL chipset.
     Unit is 1/256 dB. Range [ -5 dB, 10 dB] which
     corresponds to [ -1280, +2560].
     NOTE: This parameter must be set from the
     configuration file to take effect!
     To be substituted by adslRxAfeGains for HMI 9.x"
    REFERENCE "HMI definition of SetDeviceConfiguration"
    ::= { adslXObjects 29 }   
    
--******************************************************************
-- 
--******************************************************************
    
adslLineStateLedControl OBJECT-TYPE
    SYNTAX  INTEGER {
                    enable(1),       -- FW controls the LEDs
                    disable(2)
                    }
    MAX-ACCESS  read-write
    STATUS      current
    DESCRIPTION
    "Line state visualisation functionality
     (green line-LED). If enabled, the chipset
     controls the line state LEDs.
     The feature is avalilable in EDN312 only."
    ::= { adslXObjects 30 }   
    
    --******************************************************************
-- 
--******************************************************************
    
adslTxFilterConfigHmi5 OBJECT-TYPE
    SYNTAX      OCTET STRING (SIZE (4))
    MAX-ACCESS  read-write
    STATUS      deprecated
    DESCRIPTION
    "TxFilter in ADSL chipset. The txFilterConfig1 -
     txFilterConfig2 parameter for the C0 and B0 version
     of the chipset. Bytes [0..1] for CO version and bytes
     [2..3] for B0 version. NOTE: This parameter must be set
     from the configuration file to take effect!"
    REFERENCE "HMI definition of SetDeviceConfiguration"

    ::= { adslXObjects 31 }   

--******************************************************************
-- 
--******************************************************************
    
adslTxFilterActualHmi5 OBJECT-TYPE
    SYNTAX      OCTET STRING (SIZE (2))
    MAX-ACCESS  read-only
    STATUS      current
    DESCRIPTION
    "TxFilter in ADSL chipset. The value of the
     txFilterConfig1 - txFilterConfig2 acually used in
     the ADSL chipset."
    REFERENCE "HMI definition of SetDeviceConfiguration"
    ::= { adslXObjects 32 }   

--******************************************************************
-- 
--******************************************************************
    
adslEnableDspCoreDump OBJECT-TYPE
    SYNTAX      INTEGER { true (1), false (0)}
    MAX-ACCESS  read-write
    STATUS      deprecated
    DESCRIPTION
    "When setting this parameter to 1 (true) the
     the uC does not load firmware image into the
     DSP after the next DSP reset. The DSP will then
     be ready for retrieving the DSP core file. 
     Setting this parameter to 0 (false) for normal
     operation causing the IP DSLAM to autonomously
     recover from a DSP malfunction." 
    ::= { adslXObjects 33 }    
    
--******************************************************************
-- 
--******************************************************************
    
adslEnableACIF OBJECT-TYPE
    SYNTAX      INTEGER { disableACIF (0), enableACIF (1) }
    MAX-ACCESS  read-write
    STATUS      current
    DESCRIPTION
    "Custom PSD mask with ACIF LPF.
     By enabling this feature an extra Tx LPF with a cutoff
     frequency at 950kHz and >27 dB attenuation above 1.5 MHz is
     inserted.
     
     Valid from:                EDA 2.0 SP1
     
     Possible values are:
     0 - ACIF disabled
     1 - ACIF enabled.
     
     Maps into HMI:
     BCM6410: PhysicalLayerConfig.optionFlags Bit[5].
     BCM6411: SetTxFilter(ACIF filter).
     Note: must be set prior to setting adslIfAdminStatus up"
    ::= { adslXObjects 34 }    

    
--******************************************************************
-- 
--******************************************************************
    
adslAtucPhysXAllocTable OBJECT-TYPE
      SYNTAX     SEQUENCE OF AdslAtucPhysXAllocEntry
      MAX-ACCESS not-accessible
      STATUS     current
      DESCRIPTION
      "This table provides extra information in relation 
       to the adslAtucPhysTable for DSL lines."
      ::= { adslXObjects 35 }

adslAtucPhysXAllocEntry OBJECT-TYPE
      SYNTAX AdslAtucPhysXAllocEntry
      MAX-ACCESS  not-accessible
      STATUS      current
      DESCRIPTION
      "An entry in adslAtucPhysXAllocTable."
      INDEX { lineIndex, tonePartIdIndex }
      ::= { adslAtucPhysXAllocTable 1 }

AdslAtucPhysXAllocEntry ::=
      SEQUENCE {
        adslAtucPhysXBitAllocation              OCTET STRING
        }

adslAtucPhysXBitAllocation OBJECT-TYPE
      SYNTAX      OCTET STRING  (SIZE (488))
      MAX-ACCESS  read-only
      STATUS      deprecated
      DESCRIPTION
      "Upstream bit allocation table.Tones are split in several blocks
	  of 488 tones.
      Usage: adslAtucPhysXBitAllocation.lineNo.toneIndexPartId
      I.e. adslAtucPhysXBitAllocation.1.2 contains tones 489-976 on line 1.
      This parameter does not support lines running VDSL2.
      Substituded by:	vdsl2SCStatusBitsAlloc 
      Deprecated from:	EDA 4.0"
      ::= { adslAtucPhysXAllocEntry 1 } 

      
--******************************************************************
-- 
--******************************************************************
      
adslAturPhysXAllocTable OBJECT-TYPE
      SYNTAX     SEQUENCE OF AdslAturPhysXAllocEntry
      MAX-ACCESS not-accessible
      STATUS     current
      DESCRIPTION
      "This table provides extra information in relation 
       to the adslAtucPhysTable for DSL lines."
      ::= { adslXObjects 36 }

adslAturPhysXAllocEntry OBJECT-TYPE
      SYNTAX AdslAturPhysXAllocEntry
      MAX-ACCESS  not-accessible
      STATUS      current
      DESCRIPTION
      "An entry in adslAtucPhysXAllocTable."
      INDEX { lineIndex, tonePartIdIndex }
      ::= { adslAturPhysXAllocTable 1 }

AdslAturPhysXAllocEntry ::=
      SEQUENCE {
        adslAturPhysXBitAllocation              OCTET STRING
        }

adslAturPhysXBitAllocation OBJECT-TYPE
      SYNTAX      OCTET STRING (SIZE (488))
      MAX-ACCESS  read-only
      STATUS      deprecated
      DESCRIPTION
      "Downstream bit allocation table. Tones are split in several blocks
	  of 488 tones.
      Usage: adslAturPhysXBitAllocation.lineNo.toneIndexPartId
      I.e. adslAturPhysXBitAllocation.1.2 contains tones 489-976 on line 1.
      This parameter does not support lines running VDSL2.
      Substituded by:	vdsl2SCStatusBitsAlloc 
      Deprecated from:	EDA 4.0"
      ::= { adslAturPhysXAllocEntry 1 }     

    
--******************************************************************
-- 
--******************************************************************
    
adslAtucPhysXSnrTable OBJECT-TYPE
      SYNTAX     SEQUENCE OF AdslAtucPhysXSnrEntry
      MAX-ACCESS not-accessible
      STATUS     current
      DESCRIPTION
      "This table provides extra information in relation 
       to the adslAtucPhysTable for DSL lines."
      ::= { adslXObjects 37 }

adslAtucPhysXSnrEntry OBJECT-TYPE
      SYNTAX AdslAtucPhysXSnrEntry
      MAX-ACCESS  not-accessible
      STATUS      current
      DESCRIPTION
      "An entry in adslAtucPhysXSnrTable."
      INDEX { lineIndex, tonePartIdIndex }
      ::= { adslAtucPhysXSnrTable 1 }

AdslAtucPhysXSnrEntry ::=
      SEQUENCE {
        adslAtucPhysXToneSnrUs              OCTET STRING
        }

adslAtucPhysXToneSnrUs OBJECT-TYPE
      SYNTAX      OCTET STRING  (SIZE (488))
      MAX-ACCESS  read-only
      STATUS      deprecated
      DESCRIPTION
      "Upstream Snr table. Tones are split in several blocks
	  of 244 tones. Each tone Snr value given in 2 octets (little endian).
      Usage: adslAtucPhysXToneSnrUs.lineNo.toneIndexPartId
      I.e. adslAtucPhysXBitSnrDs.1.2 contains tones 245-488 on line 1.
      Substituded by:	vdsl2SCStatusSnr 
      Deprecated from:	EDA 4.0"
      ::= { adslAtucPhysXSnrEntry 1 } 

--******************************************************************
-- ADSL device config data
--******************************************************************
adslDeviceConfigData 	OBJECT IDENTIFIER ::= { adslXObjects 39 }

adslRxAfeGains		   	 	OBJECT IDENTIFIER ::= { adslDeviceConfigData 1 }
adslAgcGains		   		OBJECT IDENTIFIER ::= { adslDeviceConfigData 2 }


--******************************************************************
-- adslRxAfeGains Table
--******************************************************************

adslRxAfeGains0  OBJECT-TYPE
    SYNTAX      Integer32 (-6400..-2560) 
    MAX-ACCESS  read-write
    STATUS      current
    DESCRIPTION
    "Fine tune received power (1/256 dB). Used to indicate the
     attenuation of the received analog front-end between the
     line and ADC for an AGC gain of 0 dB. Unit is 1/256 dB.
     The allowed range is [-25, -10] dB.
     -rxAfeGains0: attenuation in US0 band over POTS
     -rxAfeGains1: attenuation in US0 band over ISDN
     -rxAfeGains2: attenuation in US1 band (only forG.992.3)
     -rxAfeGains3: attenuation in US2 band (only for G.992.3)
     Substitutes adslRxPowerCalibration."
    ::= { adslRxAfeGains 1 }   

adslRxAfeGains1  OBJECT-TYPE
    SYNTAX      Integer32 (-6400..-2560) 
    MAX-ACCESS  read-write
    STATUS      current
    DESCRIPTION
    "Fine tune received power (1/256 dB). Used to indicate the
     attenuation of the received analog front-end between the
     line and ADC for an AGC gain of 0 dB. Unit is 1/256 dB.
     The allowed range is [-25, -10] dB.
     -rxAfeGains0: attenuation in US0 band over POTS
     -rxAfeGains1: attenuation in US0 band over ISDN
     -rxAfeGains2: attenuation in US1 band (only forG.992.3)
     -rxAfeGains3: attenuation in US2 band (only for G.992.3)
     Substitutes adslRxPowerCalibration."
    ::= { adslRxAfeGains 2 }   

adslRxAfeGains2  OBJECT-TYPE
    SYNTAX      Integer32 (-6400..-2560) 
    MAX-ACCESS  read-write
    STATUS      current
    DESCRIPTION
    "Fine tune received power (1/256 dB). Used to indicate the
     attenuation of the received analog front-end between the
     line and ADC for an AGC gain of 0 dB. Unit is 1/256 dB.
     The allowed range is [-25, -10] dB.
     -rxAfeGains0: attenuation in US0 band over POTS
     -rxAfeGains1: attenuation in US0 band over ISDN
     -rxAfeGains2: attenuation in US1 band (only forG.992.3)
     -rxAfeGains3: attenuation in US2 band (only for G.992.3)
     Substitutes adslRxPowerCalibration."
    ::= { adslRxAfeGains 3 }   

adslRxAfeGains3  OBJECT-TYPE
    SYNTAX      Integer32 (-6400..-2560) 
    MAX-ACCESS  read-write
    STATUS      current
    DESCRIPTION
    "Fine tune received power (1/256 dB). Used to indicate the
     attenuation of the received analog front-end between the
     line and ADC for an AGC gain of 0 dB. Unit is 1/256 dB.
     The allowed range is [-25, -10] dB.
     -rxAfeGains0: attenuation in US0 band over POTS
     -rxAfeGains1: attenuation in US0 band over ISDN
     -rxAfeGains2: attenuation in US1 band (only forG.992.3)
     -rxAfeGains3: attenuation in US2 band (only for G.992.3)
     Substitutes adslRxPowerCalibration."
    ::= { adslRxAfeGains 4 }   

--******************************************************************
-- adslAgcGains
--******************************************************************

adslAgcGains0    OBJECT-TYPE
    SYNTAX      Integer32 (-4608..6144) 
    MAX-ACCESS  read-write
    STATUS      current
    DESCRIPTION
    "Fine tune AGC gains (1/256 dB). The agcGains(i), i = 0..6, is
     used to indicate the real gain of the AGC for a nominal value
     of (6 * i -12) dB with respect to the AGC setting of 0 dB
     (agcGains[2] is always equal to 0).
     Range: [-18, 24] dB"
    ::= { adslAgcGains 1 }   
 
adslAgcGains1    OBJECT-TYPE
    SYNTAX      Integer32 (-4608..6144) 
    MAX-ACCESS  read-write
    STATUS      current
    DESCRIPTION
    "Fine tune AGC gains (1/256 dB). The agcGains[i], i = 0..6, is
     used to indicate the real gain of the AGC for a nominal value
     of (6 * i -12) dB with respect to the AGC setting of 0 dB
     (agcGains[2] is always equal to 0).
     Range: [-18, 24] dB"
    ::= { adslAgcGains 2 }   
 
adslAgcGains2    OBJECT-TYPE
    SYNTAX      Integer32 (-4608..6144) 
    MAX-ACCESS  read-write
    STATUS      current
    DESCRIPTION
    "Fine tune AGC gains (1/256 dB). The agcGains[i], i = 0..6, is
     used to indicate the real gain of the AGC for a nominal value
     of (6 * i -12) dB with respect to the AGC setting of 0 dB
     (agcGains[2] is always equal to 0).
     Range: [-18, 24] dB"
    ::= { adslAgcGains 3 }   
 
adslAgcGains3    OBJECT-TYPE
    SYNTAX      Integer32 (-4608..6144) 
    MAX-ACCESS  read-write
    STATUS      current
    DESCRIPTION
    "Fine tune AGC gains (1/256 dB). The agcGains[i], i = 0..6, is
     used to indicate the real gain of the AGC for a nominal value
     of (6 * i -12) dB with respect to the AGC setting of 0 dB
     (agcGains[2] is always equal to 0).
     Range: [-18, 24] dB"
    ::= { adslAgcGains 4 }   
 
adslAgcGains4    OBJECT-TYPE
    SYNTAX      Integer32 (-4608..6144) 
    MAX-ACCESS  read-write
    STATUS      current
    DESCRIPTION
    "Fine tune AGC gains (1/256 dB). The agcGains[i], i = 0..6, is
     used to indicate the real gain of the AGC for a nominal value
     of (6 * i -12) dB with respect to the AGC setting of 0 dB
     (agcGains[2] is always equal to 0).
     Range: [-18, 24] dB"
    ::= { adslAgcGains 5 }   
 
adslAgcGains5    OBJECT-TYPE
    SYNTAX      Integer32 (-4608..6144) 
    MAX-ACCESS  read-write
    STATUS      current
    DESCRIPTION
    "Fine tune AGC gains (1/256 dB). The agcGains[i], i = 0..6, is
     used to indicate the real gain of the AGC for a nominal value
     of (6 * i -12) dB with respect to the AGC setting of 0 dB
     (agcGains[2] is always equal to 0).
     Range: [-18, 24] dB"
    ::= { adslAgcGains 6 }   
 
adslAgcGains6    OBJECT-TYPE
    SYNTAX      Integer32 (-4608..6144) 
    MAX-ACCESS  read-write
    STATUS      current
    DESCRIPTION
    "Fine tune AGC gains (1/256 dB). The agcGains[i], i = 0..6, is
     used to indicate the real gain of the AGC for a nominal value
     of (6 * i -12) dB with respect to the AGC setting of 0 dB
     (agcGains[2] is always equal to 0).
     Range: [-18, 24] dB"
    ::= { adslAgcGains 7 }   

--******************************************************************
-- ADSL ATU-C Performance Data 1-Day Interval Extension
--******************************************************************
adslAtuc1DayIntervalXTable   OBJECT-TYPE
    SYNTAX          SEQUENCE OF AdslAtuc1DayIntervalXEntry
    MAX-ACCESS      not-accessible
    STATUS          current
    DESCRIPTION
    "This table provides one row for each ATUC performance data
     collection in a 1 day measurement interval.
     ADSL physical interfaces are those ifEntries where ifType
     is equal to adsl(94)."
    ::= { adslXObjects 45 }

adslAtuc1DayIntervalXEntry   OBJECT-TYPE
    SYNTAX          AdslAtuc1DayIntervalXEntry
    MAX-ACCESS      not-accessible
    STATUS          current
    DESCRIPTION     
    "An entry in the adslAtuc1DayIntervalXTable."
    INDEX  { lineIndex, adslAtuc1DayIntervalXNumber }
    ::= { adslAtuc1DayIntervalXTable 1 }

AdslAtuc1DayIntervalXEntry ::=
    SEQUENCE {
      adslAtuc1DayIntervalXNumber      INTEGER,
      adslAtuc1DayIntervalXLofs        Perf1DayIntervalXCount,
      adslAtuc1DayIntervalXLoss        Perf1DayIntervalXCount,
      adslAtuc1DayIntervalXLols        Perf1DayIntervalXCount,
      adslAtuc1DayIntervalXESs         Perf1DayIntervalXCount,
      adslAtuc1DayIntervalXEcs         Perf1DayIntervalXCount,
      adslAtuc1DayIntervalXInits       Perf1DayIntervalXCount,
      adslAtuc1DayIntervalXValidData   TruthValue
      }

adslAtuc1DayIntervalXNumber OBJECT-TYPE
    SYNTAX      INTEGER(1..3)
    MAX-ACCESS  not-accessible
    STATUS      current
    DESCRIPTION
    "Performance Data Interval number 1 is
     the most recent previous 1 day interval."
    ::= { adslAtuc1DayIntervalXEntry 1 }

adslAtuc1DayIntervalXLofs OBJECT-TYPE
    SYNTAX      Perf1DayIntervalXCount
    UNITS       "seconds"
    MAX-ACCESS  read-only
    STATUS      current
    DESCRIPTION
    "Count of seconds in the interval when there was
     Loss of Framing."
    ::= { adslAtuc1DayIntervalXEntry 5 }

adslAtuc1DayIntervalXLoss  OBJECT-TYPE
    SYNTAX      Perf1DayIntervalXCount
    UNITS       "seconds"
    MAX-ACCESS  read-only
    STATUS      current
    DESCRIPTION
    "Count of seconds in the interval when there was
     Loss of Signal."
    ::= { adslAtuc1DayIntervalXEntry 10 }

adslAtuc1DayIntervalXLols  OBJECT-TYPE
    SYNTAX      Perf1DayIntervalXCount
    UNITS       "seconds"
    MAX-ACCESS  read-only
    STATUS      current
    DESCRIPTION
    "Count of seconds in the interval when there was
     Loss of Link."
    ::= { adslAtuc1DayIntervalXEntry 15 }

adslAtuc1DayIntervalXESs OBJECT-TYPE
    SYNTAX      Perf1DayIntervalXCount
    UNITS       "seconds"
    MAX-ACCESS  read-only
    STATUS      current
    DESCRIPTION
    "Count of Errored Seconds in the interval.
     The errored second parameter is a count of
     one-second intervals containing one or more crc
     anomalies, or one or more los or sef defects."
    ::= { adslAtuc1DayIntervalXEntry 20 }

adslAtuc1DayIntervalXEcs OBJECT-TYPE
    SYNTAX      Perf1DayIntervalXCount
    MAX-ACCESS  read-only
    STATUS      current
    DESCRIPTION
    "Count of forward error correction seconds 
     in the interval."
    ::= { adslAtuc1DayIntervalXEntry 25 }

adslAtuc1DayIntervalXInits  OBJECT-TYPE
    SYNTAX      Perf1DayIntervalXCount
    MAX-ACCESS  read-only
    STATUS      current
    DESCRIPTION
    "Count of the line initialization attempts
     during the interval. Includes both successful
     and failed attempts."
    ::= { adslAtuc1DayIntervalXEntry 30 }

adslAtuc1DayIntervalXValidData OBJECT-TYPE
    SYNTAX TruthValue
    MAX-ACCESS read-only
    STATUS current
    DESCRIPTION
    "This variable indicates if the data for this
     interval is valid."
    ::= { adslAtuc1DayIntervalXEntry 35 }

--******************************************************************
-- ADSL ATU-R Performance Data 1-Day Interval Extension
--******************************************************************
adslAtur1DayIntervalXTable   OBJECT-TYPE
    SYNTAX          SEQUENCE OF AdslAtur1DayIntervalXEntry
    MAX-ACCESS      not-accessible
    STATUS          current
    DESCRIPTION
    "This table provides one row for each ATUR performance data
     collection in a 1 day measurement interval.
     ADSL physical interfaces are those ifEntries where ifType
     is equal to adsl(94)."
    ::= { adslXObjects 50 }

adslAtur1DayIntervalXEntry   OBJECT-TYPE
    SYNTAX          AdslAtur1DayIntervalXEntry
    MAX-ACCESS      not-accessible
    STATUS          current
    DESCRIPTION     
    "An entry in the adslAtur1DayIntervalXTable."
    INDEX  { lineIndex, adslAtur1DayIntervalXNumber }
    ::= { adslAtur1DayIntervalXTable 1 }

AdslAtur1DayIntervalXEntry ::=
    SEQUENCE {
      adslAtur1DayIntervalXNumber     INTEGER,
      adslAtur1DayIntervalXLofs       Perf1DayIntervalXCount,
      adslAtur1DayIntervalXLoss       Perf1DayIntervalXCount,
      adslAtur1DayIntervalXLprs       Perf1DayIntervalXCount,
      adslAtur1DayIntervalXESs        Perf1DayIntervalXCount,
      adslAtur1DayIntervalXEcs        Perf1DayIntervalXCount,
      adslAtur1DayIntervalXValidData  TruthValue
      }

adslAtur1DayIntervalXNumber OBJECT-TYPE
    SYNTAX      INTEGER(1..3)
    MAX-ACCESS  not-accessible
    STATUS      current
    DESCRIPTION
    "Performance Data Interval number 1 is
     the most recent previous 1 day interval."
    ::= { adslAtur1DayIntervalXEntry 1 }

adslAtur1DayIntervalXLofs OBJECT-TYPE
    SYNTAX      Perf1DayIntervalXCount
    UNITS       "seconds"
    MAX-ACCESS  read-only
    STATUS      current
    DESCRIPTION
    "Count of seconds in the interval when there was
     Loss of Framing."
    ::= { adslAtur1DayIntervalXEntry 5 }

adslAtur1DayIntervalXLoss  OBJECT-TYPE
    SYNTAX      Perf1DayIntervalXCount
    UNITS       "seconds"
    MAX-ACCESS  read-only
    STATUS      current
    DESCRIPTION
    "Count of seconds in the interval when there was
     Loss of Signal."
    ::= { adslAtur1DayIntervalXEntry 10 }

adslAtur1DayIntervalXLprs  OBJECT-TYPE
    SYNTAX      Perf1DayIntervalXCount
    UNITS       "seconds"
    MAX-ACCESS  read-only
    STATUS      current
    DESCRIPTION
    "Count of seconds in the interval when there was
     Loss of Power."
    ::= { adslAtur1DayIntervalXEntry 15 }

adslAtur1DayIntervalXESs OBJECT-TYPE
    SYNTAX      Perf1DayIntervalXCount
    UNITS       "seconds"
    MAX-ACCESS  read-only
    STATUS      current
    DESCRIPTION
    "Count of Errored Seconds in the interval.
     The errored second parameter is a count of
     one-second intervals containing one or more crc
     anomalies, or one or more los or sef defects."
    ::= { adslAtur1DayIntervalXEntry 20 }

adslAtur1DayIntervalXEcs OBJECT-TYPE
    SYNTAX      Perf1DayIntervalXCount
    MAX-ACCESS  read-only
    STATUS      current
    DESCRIPTION
    "Count of forward error correction seconds 
     in the interval."
    ::= { adslAtur1DayIntervalXEntry 25 }

adslAtur1DayIntervalXValidData OBJECT-TYPE
    SYNTAX TruthValue
    MAX-ACCESS read-only
    STATUS current
    DESCRIPTION
    "This variable indicates if the data for this
     interval is valid."
    ::= { adslAtur1DayIntervalXEntry 30 }


--******************************************************************
-- ADSL ATU-C Channel Performance Data 1-Day Interval Extension
--******************************************************************
adslAtucChan1DayIntervalXTable   OBJECT-TYPE
    SYNTAX          SEQUENCE OF AdslAtucChan1DayIntervalXEntry
    MAX-ACCESS      not-accessible
    STATUS          current
    DESCRIPTION
    "This table provides one row for each ATUC channel's
     performance data collection in a 1 day measurement interval.
     ADSL channel interfaces are those ifEntries
     where ifType is equal to adslInterleave(124)
     or adslFast(125)."
    ::= { adslXObjects 55 }

adslAtucChan1DayIntervalXEntry   OBJECT-TYPE
    SYNTAX          AdslAtucChan1DayIntervalXEntry
    MAX-ACCESS      not-accessible
    STATUS          current
    DESCRIPTION     
    "An entry in the adslAtucChan1DayIntervalXTable."
    INDEX  { lineIndex, adslAtucChan1DayIntervalXNumber }
    ::= { adslAtucChan1DayIntervalXTable 1 }

AdslAtucChan1DayIntervalXEntry ::=
    SEQUENCE {
      adslAtucChan1DayIntervalXNumber               INTEGER,
      adslAtucChan1DayIntervalXCorrectedBlks        Perf1DayIntervalXCount,
      adslAtucChan1DayIntervalXUncorrectBlks        Perf1DayIntervalXCount,
      adslAtucChan1DayIntervalXHecv                 Perf1DayIntervalXCount,
      adslAtucChan1DayIntervalXTotalCells           Perf1DayIntervalXCount,
      adslAtucChan1DayIntervalXTotalUserCells       Perf1DayIntervalXCount,
      adslAtucChan1DayIntervalXOverFlowCells        Perf1DayIntervalXCount,
      adslAtucChan1DayIntervalXIdleCells            Perf1DayIntervalXCount,
      adslAtucChan1DayIntervalXIdleCellBitErrors    Perf1DayIntervalXCount,
      adslAtucChan1DayIntervalXValidData            TruthValue
      }

adslAtucChan1DayIntervalXNumber OBJECT-TYPE
    SYNTAX      INTEGER(1..3)
    MAX-ACCESS  not-accessible
    STATUS      current
    DESCRIPTION
    "Performance Data Interval number 1 is
     the most recent previous 1 day interval."
    ::= { adslAtucChan1DayIntervalXEntry 1 }

adslAtucChan1DayIntervalXCorrectedBlks  OBJECT-TYPE
    SYNTAX      Perf1DayIntervalXCount
    MAX-ACCESS  read-only
    STATUS      current
    DESCRIPTION
    "Count of all blocks received with errors that were
     corrected on this channel during this interval."
    ::= { adslAtucChan1DayIntervalXEntry 5 }

adslAtucChan1DayIntervalXUncorrectBlks  OBJECT-TYPE
    SYNTAX      Perf1DayIntervalXCount
    MAX-ACCESS  read-only
    STATUS      current
    DESCRIPTION
    "Count of all blocks received with uncorrectable
     errors on this channel during this interval."
    ::= { adslAtucChan1DayIntervalXEntry 10 }

adslAtucChan1DayIntervalXHecv OBJECT-TYPE
    SYNTAX      Perf1DayIntervalXCount
    MAX-ACCESS  read-only
    STATUS      current
    DESCRIPTION
    "Count of all header error correction violations 
     received on this channel during this interval."
    ::= { adslAtucChan1DayIntervalXEntry 15 }

adslAtucChan1DayIntervalXTotalCells OBJECT-TYPE
    SYNTAX      Perf1DayIntervalXCount
    MAX-ACCESS  read-only
    STATUS      current
    DESCRIPTION
    "Count of all ATM cells received on this channel 
     during this interval."
    ::= { adslAtucChan1DayIntervalXEntry 20 }
 
adslAtucChan1DayIntervalXTotalUserCells OBJECT-TYPE
    SYNTAX      Perf1DayIntervalXCount
    MAX-ACCESS  read-only
    STATUS      current
    DESCRIPTION
    "Count of all valid non-idle ATM cells succesfully
     transmitted to the UTOPIA bus on this interval."
    ::= { adslAtucChan1DayIntervalXEntry 25 }  

adslAtucChan1DayIntervalXOverFlowCells OBJECT-TYPE
    SYNTAX      Perf1DayIntervalXCount
    MAX-ACCESS  read-only
    STATUS      current
    DESCRIPTION
    "Count the number of cells discarded due to the received
     UTOPIA FIFO being full on this interval."
    ::= { adslAtucChan1DayIntervalXEntry 30 }

adslAtucChan1DayIntervalXIdleCells OBJECT-TYPE
    SYNTAX      Perf1DayIntervalXCount
    MAX-ACCESS  read-only
    STATUS      current
    DESCRIPTION
    "Count of all idle ATM cells received on this channel 
     this interval."
    ::= { adslAtucChan1DayIntervalXEntry 35 }
 
adslAtucChan1DayIntervalXIdleCellBitErrors OBJECT-TYPE
    SYNTAX      Perf1DayIntervalXCount
    MAX-ACCESS  read-only
    STATUS      current
    DESCRIPTION
    "Count the number of bit errors in the payload of
     the valid idle ATM cells received on this channel
     on this interval."
    ::= { adslAtucChan1DayIntervalXEntry 40 }

adslAtucChan1DayIntervalXValidData OBJECT-TYPE
    SYNTAX TruthValue
    MAX-ACCESS read-only
    STATUS current
    DESCRIPTION
    "This variable indicates if the data for this
     interval is valid."
    ::= { adslAtucChan1DayIntervalXEntry 45 }

--******************************************************************
-- ADSL ATU-R Channel Performance Data 1-Day Interval Extension
--******************************************************************
adslAturChan1DayIntervalXTable   OBJECT-TYPE
    SYNTAX          SEQUENCE OF AdslAturChan1DayIntervalXEntry
    MAX-ACCESS      not-accessible
    STATUS          current
    DESCRIPTION
    "This table provides one row for each ATUR channel's
     performance data collection in a 1 day measurement interval.
     ADSL channel interfaces are those ifEntries
     where ifType is equal to adslInterleave(124)
     or adslFast(125)."
    ::= { adslXObjects 60 }

adslAturChan1DayIntervalXEntry   OBJECT-TYPE
    SYNTAX          AdslAturChan1DayIntervalXEntry
    MAX-ACCESS      not-accessible
    STATUS          current
    DESCRIPTION     
    "An entry in the adslAturChan1DayIntervalXTable."
    INDEX  { lineIndex, adslAturChan1DayIntervalXNumber }
    ::= { adslAturChan1DayIntervalXTable 1 }

AdslAturChan1DayIntervalXEntry ::=
    SEQUENCE {
      adslAturChan1DayIntervalXNumber               INTEGER,
      adslAturChan1DayIntervalXCorrectedBlks        Perf1DayIntervalXCount,
      adslAturChan1DayIntervalXUncorrectBlks        Perf1DayIntervalXCount,
      adslAturChan1DayIntervalXHecv                 Perf1DayIntervalXCount,
      adslAturChan1DayIntervalXTotalCells           Perf1DayIntervalXCount,
      adslAturChan1DayIntervalXTotalUserCells       Perf1DayIntervalXCount,     
      adslAturChan1DayIntervalXIdleCellBitErrors    Perf1DayIntervalXCount,
      adslAturChan1DayIntervalXValidData            TruthValue
      }

adslAturChan1DayIntervalXNumber OBJECT-TYPE
    SYNTAX      INTEGER(1..3)
    MAX-ACCESS  not-accessible
    STATUS      current
    DESCRIPTION
    "Performance Data Interval number 1 is
     the most recent previous 1 day interval."
    ::= { adslAturChan1DayIntervalXEntry 1 }

adslAturChan1DayIntervalXCorrectedBlks  OBJECT-TYPE
    SYNTAX      Perf1DayIntervalXCount
    MAX-ACCESS  read-only
    STATUS      current
    DESCRIPTION
    "Count of all blocks received with errors that were
     corrected on this channel during this interval."
    ::= { adslAturChan1DayIntervalXEntry 5 }

adslAturChan1DayIntervalXUncorrectBlks  OBJECT-TYPE
    SYNTAX      Perf1DayIntervalXCount
    MAX-ACCESS  read-only
    STATUS      current
    DESCRIPTION
    "Count of all blocks received with uncorrectable
     errors on this channel during this interval."
    ::= { adslAturChan1DayIntervalXEntry 10 }

adslAturChan1DayIntervalXHecv OBJECT-TYPE
    SYNTAX      Perf1DayIntervalXCount
    MAX-ACCESS  read-only
    STATUS      current
    DESCRIPTION
    "Count of all header error correction violations 
     received on this channel during this interval."
    ::= { adslAturChan1DayIntervalXEntry 15 }

adslAturChan1DayIntervalXTotalCells OBJECT-TYPE
    SYNTAX      Perf1DayIntervalXCount
    MAX-ACCESS  read-only
    STATUS      current
    DESCRIPTION
    "Count of all ATM cells received on this channel 
     this interval."
    ::= { adslAturChan1DayIntervalXEntry 20 }
 
adslAturChan1DayIntervalXTotalUserCells OBJECT-TYPE
    SYNTAX      Perf1DayIntervalXCount
    MAX-ACCESS  read-only
    STATUS      current
    DESCRIPTION
    "Count of all valid non-idle ATM cells succesfully
     received on the UTOPIA bus on this interval."
    ::= { adslAturChan1DayIntervalXEntry 25 }

adslAturChan1DayIntervalXIdleCellBitErrors OBJECT-TYPE
    SYNTAX      Perf1DayIntervalXCount
    MAX-ACCESS  read-only
    STATUS      current
    DESCRIPTION
    "Count the number of bit errors in the payload of
     the valid idle ATM cells received on this channel
     on this interval. Applies to ADSL2 only."
    ::= { adslAturChan1DayIntervalXEntry 30 }
      
adslAturChan1DayIntervalXValidData OBJECT-TYPE
    SYNTAX TruthValue
    MAX-ACCESS read-only
    STATUS current
    DESCRIPTION
    "This variable indicates if the data for this
     interval is valid."
    ::= { adslAturChan1DayIntervalXEntry 35 }
 
tonePartIdIndex OBJECT-TYPE
    SYNTAX      TonePartIdIndex
    MAX-ACCESS  not-accessible
    STATUS      current
    DESCRIPTION
    "The Tone Part ID index."
    ::= { adslXObjects 65 }   
 
--******************************************************************
-- trap definitions
--******************************************************************
adslAtucXTraps          OBJECT IDENTIFIER ::= { adslXTraps 1 }
adslAtucXTrapsEntry     OBJECT IDENTIFIER ::= { adslAtucXTraps 0 }

adslAtucXInitFailureTrap        NOTIFICATION-TYPE
    OBJECTS { managedObjectClass, managedObjectInstance, sequenceNumber, 
              perceivedSeverity, eventTime, eventTypePem, probableCause, errorCode  }
    STATUS  current
    DESCRIPTION
    "Sent if initialisation of the line failed. One likely 
     reason is that requested configuration can't be 
     implemented on the current line conditions. More 
     information about the reason can be fetched from 
     the current line status.

     Valid from:                EDA 1.1R2A
    
     Parameters
      1: Managed object class   IP DSLAM  Port
      2: Managed object ID      (MAC + PortNo)
      3: Sequence number        (Alarm sequence number)
      4: Perceived severity     Major
      5: Event time             (Timestamp is retrieved from a SNTP server)
      6: Event type             ProcessingErrorAlarm
      7: Probable cause         ConfigurationOrCustomisationError
      8: Err Code               (Additional error information)
    "

    --Ericsson Diax additional information:
    --Format: Initialisation of the indicated line failed from: $2;  Probable cause: $7; ErrorCode: $8; Sequence Number: $3;
    
    ::= { adslAtucXTrapsEntry 1 }

adslAtucIncorrectConfigurationTrap       NOTIFICATION-TYPE
    OBJECTS { managedObjectClass, managedObjectInstance, sequenceNumber, 
              perceivedSeverity, eventTime, eventTypePem, probableCause,
              messageId, errorCode }
    STATUS  current
    DESCRIPTION
    "The current configuration is not allowed.
     The operator must change the configuration settings.

     Valid from:                EDA 1.1R2A
    
     Parameters
      1: Managed object class   IP DSLAM  Port
      2: Managed object ID      (MAC + PortNo)
      3: Sequence number        (Alarm sequence number)
      4: Perceived severity     Major
      5: Event time             (Timestamp is retrieved from a SNTP server)
      6: Event type             ProcessingErrorAlarm
      7: Probable cause         ConfigurationOrCustomisationError
      8: Message ID             (Internal message number)
      9: Err Code               (Additional error information)
    "

    --Ericsson Diax additional information:
    --Format: The current configuration is not allowed from: $2; Probable cause: $7; MessageId: $8; ErrorCode: $9; Sequence Number: $3;
    
    ::= { adslAtucXTrapsEntry 2 }

adslAtucPerfXESsThresh15MinTrap       NOTIFICATION-TYPE
    OBJECTS { managedObjectClass, managedObjectInstance, sequenceNumber, 
              perceivedSeverity, eventTime, eventTypePem, probableCause,  
              adslAtucThresh15MinESs }
    STATUS  current
    DESCRIPTION
    "Errored Second 15-minute interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAtucThresh15MinESs threshold value)
    "

    --Ericsson Diax additional information:
    --Format: Errored Second 15-minute interval threshold reached: ATU-C from: $2; Probable cause: $7; Number of Errored Seconds: $8; Sequence Number: $3;

    ::= { adslAtucXTrapsEntry 3 }

adslAtucPerfXESsThresh1DayTrap       NOTIFICATION-TYPE
    OBJECTS { managedObjectClass, managedObjectInstance, sequenceNumber, 
              perceivedSeverity, eventTime, eventTypePem, probableCause,  
              adslAlarmConfXAtucThres1DayES }
    STATUS  current
    DESCRIPTION
    "Errored Second 1 Day interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAtucThres1DayES threshold value)
    "

    --Ericsson Diax additional information:
    --Format: Errored Second 1 Day interval threshold reached: ATU-C from: $2;  Probable cause: $7;  Number of Errored Seconds: $8; Sequence Number: $3;

    ::= { adslAtucXTrapsEntry 4 }

adslAtucPerfXSesThresh15MinTrap       NOTIFICATION-TYPE
    OBJECTS { managedObjectClass, managedObjectInstance, sequenceNumber, 
              perceivedSeverity, eventTime, eventTypePem, probableCause,  
              adslAtucThreshold15MinSesL }
    STATUS  current
    DESCRIPTION
    "Severely Errored Second 15-minute interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAtucThreshold15MinSesL threshold value)
    "

    --Ericsson Diax additional information:
    --Format: Severely Errored Second 15-minute interval threshold reached: ATU-C from: $2; Probable cause: $7; Threshold value: $8; Sequence Number: $3;

    ::= { adslAtucXTrapsEntry 5 }

adslAtucPerfXSesThresh1DayTrap       NOTIFICATION-TYPE
    OBJECTS { managedObjectClass, managedObjectInstance, sequenceNumber, 
              perceivedSeverity, eventTime, eventTypePem, probableCause,  
              adslAlarmConfXAtucThres1DaySesL }
    STATUS  current
    DESCRIPTION
    "Severely Errored Second 1 Day interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAtucThres1DaySesL threshold value)
    "

    --Ericsson Diax additional information:
    --Format: Severely Errored Second 1 Day interval threshold reached: ATU-C from: $2; Probable cause: $7; Number of Severely Errored Seconds: $8; Sequence Number: $3;

    ::= { adslAtucXTrapsEntry 6 }

adslAtucPerfXUasThresh15MinTrap       NOTIFICATION-TYPE
    OBJECTS { managedObjectClass, managedObjectInstance, sequenceNumber, 
              perceivedSeverity, eventTime, eventTypePem, probableCause,  
              adslAtucThreshold15MinUasL }
    STATUS  current
    DESCRIPTION
    "Unavailable Second 15-minute interval threshold reached.

     Valid from:                EDA 1.1R2A
    
     Parameters
      1: Managed object class   IP DSLAM Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAtucThreshold15MinUasL threshold value)
    "

    --Ericsson Diax additional information:
    --Format: Unavailable Second 15-minute interval threshold reached: ATU-C from: $2; Probable cause: $7; Threshold value: $8; Sequence Number: $3;

    ::= { adslAtucXTrapsEntry 7 }

adslAtucPerfXUasThresh1DayTrap       NOTIFICATION-TYPE
    OBJECTS { managedObjectClass, managedObjectInstance, sequenceNumber, 
              perceivedSeverity, eventTime, eventTypePem, probableCause,  
              adslAlarmConfXAtucThres1DayUasL }
    STATUS  current
    DESCRIPTION
    "Unavailable Second 1 Day interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAtucThres1DayUasL threshold value)
    "

    --Ericsson Diax additional information:
    --Format: Unavailable Second 1 Day interval threshold reached: ATU-C from: $2;  Probable cause: $7; Number of Unavailable Seconds: $8; Sequence Number: $3;

    ::= { adslAtucXTrapsEntry 8 }   

adslAtucDspUnexpectedResponseTrap       NOTIFICATION-TYPE
    OBJECTS { managedObjectClass, managedObjectInstance, sequenceNumber, 
              perceivedSeverity, eventTime, eventTypePem, probableCause,
              messageId, errorCode }
    STATUS  current
    DESCRIPTION
    "DSP replies with an unexpected result code such as:
     'unknown application id', 'unknown command id',  
     'wrong message format', 'request data not valid' or 
     'request cannot be performed in current state'. 
     This should not happen and comes from either incompatible 
     SW versions or state mismatch between UC and DSP due 
     to internal SW problems. If necessary a LinkDown should 
     proceed this fault.The line will be reset and possibly 
     taken into service again. In case too many line resets 
     have been performed a DSP Communication Failure shall be 
     triggered and the DSP reset and reloaded.
     The operator must change the configuration settings.

     Valid from:                EDA 1.1R2A
    
     Parameters
      1: Managed object class   IP DSLAM  Port
      2: Managed object ID      (MAC + PortNo)
      3: Sequence number        (Alarm sequence number)
      4: Perceived severity     Minor
      5: Event time             (Timestamp is retrieved from a SNTP server)
      6: Event type             Equipment
      7: Probable cause         UnexpectedInformation
      8: Message ID             (Internal message number)
      9: Err Code               (Additional error information)
    "

    --Ericsson Diax additional information:
    --Format: DSP replies with an unexpected result code from: $2; Probable cause: $7; MessageId: $8; ErrorCode: $9; Sequence Number: $3;
    
    ::= { adslAtucXTrapsEntry 9 }

adslAtucDspLineResetTrap       NOTIFICATION-TYPE
    OBJECTS { managedObjectClass, managedObjectInstance, sequenceNumber, 
              perceivedSeverity, eventTime, eventTypePem, probableCause }
    STATUS  current
    DESCRIPTION
    "The indicated line has autonomously reset itself. 
     This should not occur and can be due to CPU overload 
     or some other internal DSP SW failure. If necessary 
     a LinkDown should proceed this fault. The line will 
     be reset and possibly taken into service again. 
     In case too many line resets have been performed a 
     DSP Communication Failure shall be triggered and the 
     DSP reset and reloaded.

     Valid from:                EDA 1.1R2A
    
     Parameters
      1: Managed object class   IP DSLAM  Port
      2: Managed object ID      (MAC + PortNo)
      3: Sequence number        (Alarm sequence number)
      4: Perceived severity     Minor
      5: Event time             (Timestamp is retrieved from a SNTP server)
      6: Event type             ProcessingErrorAlarm
      7: Probable cause         EquipmentMalfunction
    "

    --Ericsson Diax additional information:
    --Format: The indicated line has autonomously reset itself from: $2; Probable cause: $7; Sequence Number: $3;
    
    ::= { adslAtucXTrapsEntry 10 }

adslAtucLineQualityThreshNotReachedTrap       NOTIFICATION-TYPE
    OBJECTS { managedObjectClass, managedObjectInstance, sequenceNumber, 
              perceivedSeverity, eventTime, eventTypePem, probableCause,  
              adslAtucLineQualityThresChan0 }
    STATUS  current
    DESCRIPTION
    "Line Quality threshold not reached.

     Valid from:                EDA 2.1
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         ThresholdCrossed
      8: Threshold              Line quality alarm threshold
    "

    --Ericsson Diax additional information:
    --Format: Line Quality threshold not reached: ATU-C from: $2; Probable cause: $7; Threshold: $8; Sequence Number: $3;

    ::= { adslAtucXTrapsEntry 11 }

adslAtucLineBondLineQualityThreshNotReachedTrap       NOTIFICATION-TYPE
    OBJECTS { managedObjectClass, managedObjectInstance, sequenceNumber, 
              perceivedSeverity, eventTime, eventTypePem, probableCause,  
              adslAtucLineBondLineQualityThres }
    STATUS  current
    DESCRIPTION
    "Line Quality threshold not reached.

     Valid from:                EDA 2.2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         ThresholdCrossed
      8: Threshold              Line quality alarm threshold
    "

    --Ericsson Diax additional information:
    --Format: Line Quality threshold not reached: ATU-C from: $2; Probable cause: $7; Threshold: $8; Sequence Number: $3;

    ::= { adslAtucXTrapsEntry 12 }

adslAtucPerfXLofsThresh15MinTrap       NOTIFICATION-TYPE
    OBJECTS { managedObjectClass, managedObjectInstance, sequenceNumber, 
              perceivedSeverity, eventTime, eventTypePem, probableCause,  
              adslAtucThresh15MinLofs }
    STATUS  current
    DESCRIPTION
    "Count of Loss of Frame seconds in current 15-minute interval has reached
     the threshold value configured by the adslAtucThresh15MinLofs parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAtucThresh15MinLofs threshold value)
    "

    --Ericsson Diax additional information:
    --Format: Loss of Frame Second 15-minute interval threshold reached: ATU-C from: $2; Probable cause: $7; Threshold value: $8; Sequence Number: $3;

    ::= { adslAtucXTrapsEntry 15 }

adslAtucPerfXLofsThresh1DayTrap       NOTIFICATION-TYPE
    OBJECTS { managedObjectClass, managedObjectInstance, sequenceNumber, 
              perceivedSeverity, eventTime, eventTypePem, probableCause,  
              adslAlarmConfXAtucThres1DayLofs }
    STATUS  current
    DESCRIPTION
    "Count of Loss of Frame seconds in current 1-day interval has reached
     the threshold value configured by adslAlarmConfXAtucThres1DayLofs parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAtucThres1DayLofs threshold value)
    "

    --Ericsson Diax additional information:
    --Format: Loss of Frame Second 1 Day interval threshold reached: ATU-C from: $2;  Probable cause: $7;  Threshold value: $8; Sequence Number: $3;

    ::= { adslAtucXTrapsEntry 20 }

adslAtucPerfXLossThresh15MinTrap       NOTIFICATION-TYPE
    OBJECTS { managedObjectClass, managedObjectInstance, sequenceNumber, 
              perceivedSeverity, eventTime, eventTypePem, probableCause,  
              adslAtucThresh15MinLoss }
    STATUS  current
    DESCRIPTION
    "Count of Loss of Signal seconds in current 15-minute interval has reached
     the threshold value configured by the adslAtucThresh15MinLoss parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAtucThresh15MinLoss threshold value)
    "

    --Ericsson Diax additional information:
    --Format: Loss of Signal Second 15-minute interval threshold reached: ATU-C from: $2; Probable cause: $7; Threshold value: $8; Sequence Number: $3;

    ::= { adslAtucXTrapsEntry 25 }

adslAtucPerfXLossThresh1DayTrap       NOTIFICATION-TYPE
    OBJECTS { managedObjectClass, managedObjectInstance, sequenceNumber, 
              perceivedSeverity, eventTime, eventTypePem, probableCause,  
              adslAlarmConfXAtucThres1DayLoss }
    STATUS  current
    DESCRIPTION
    "Count of Loss of Signal seconds in current 1-day interval has reached
     the threshold value configured by adslAlarmConfXAtucThres1DayLoss parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAtucThres1DayLoss threshold value)
    "

    --Ericsson Diax additional information:
    --Format: Loss of Signal Second 1 Day interval threshold reached: ATU-C from: $2; Probable cause: $7; Threshold value: $8; Sequence Number: $3;

    ::= { adslAtucXTrapsEntry 30 }

adslAtucPerfXLolsThresh15MinTrap       NOTIFICATION-TYPE
    OBJECTS { managedObjectClass, managedObjectInstance, sequenceNumber, 
              perceivedSeverity, eventTime, eventTypePem, probableCause,  
              adslAtucThresh15MinLols }
    STATUS  current
    DESCRIPTION
    "Count of Loss of Link seconds in current 15-minute interval has reached
     the threshold value configured by the adslAtucThresh15MinLols parameter.

     Valid from:                EDA 2.2 MA2
    
     Parameters
      1: Managed object class   IP DSLAM Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAtucThresh15MinLols threshold value)
    "

    --Ericsson Diax additional information:
    --Format: Loss of Link Second 15-minute interval threshold reached: ATU-C from: $2; Probable cause: $7; Threshold value: $8; Sequence Number: $3;

    ::= { adslAtucXTrapsEntry 35 }

adslAtucPerfXLolsThresh1DayTrap       NOTIFICATION-TYPE
    OBJECTS { managedObjectClass, managedObjectInstance, sequenceNumber, 
              perceivedSeverity, eventTime, eventTypePem, probableCause,  
              adslAlarmConfXAtucThres1DayLols }
    STATUS  current
    DESCRIPTION
    "Count of Loss of Link seconds in current 1-day interval has reached
     the threshold value configured by adslAlarmConfXAtucThres1DayLols parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAtucThres1DayLols threshold value)
    "

    --Ericsson Diax additional information:
    --Format: Loss of Link Second 1 Day interval threshold reached: ATU-C from: $2;  Probable cause: $7; Threshold value: $8; Sequence Number: $3;

    ::= { adslAtucXTrapsEntry 40 }   
    
adslAturXTraps      OBJECT IDENTIFIER ::= { adslXTraps 2 }
adslAturXTrapsEntry OBJECT IDENTIFIER ::= { adslAturXTraps 0 }

adslAturPerfXESsThresh15MinTrap       NOTIFICATION-TYPE
    OBJECTS { managedObjectClass, managedObjectInstance, sequenceNumber, 
              perceivedSeverity, eventTime, eventTypePem, probableCause,  
              adslAturThresh15MinESs }
    STATUS  current
    DESCRIPTION
    "Errored Second 15-minute interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAturThresh15MinESs threshold value)
    "

    --Ericsson Diax additional information:
    --Format: Errored Second 15-minute interval threshold reached: ATU-R from: $2;  Probable cause: $7; Number of Errored Seconds: $8; Sequence Number: $3;

    ::= { adslAturXTrapsEntry 2 }

adslAturPerfXESsThresh1DayTrap       NOTIFICATION-TYPE
    OBJECTS { managedObjectClass, managedObjectInstance, sequenceNumber, 
              perceivedSeverity, eventTime, eventTypePem, probableCause,  
              adslAlarmConfXAturThres1DayES }
    STATUS  current
    DESCRIPTION
    "Errored Second 1 Day interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAturThres1DayES threshold value)
    "

    --Ericsson Diax additional information:
    --Format: Errored Second 1 Day interval threshold reached: ATU-R from: $2; Probable cause: $7; Number of Errored Seconds: $8; Sequence Number: $3;

    ::= { adslAturXTrapsEntry 3 }

adslAturPerfXSesThresh15MinTrap       NOTIFICATION-TYPE
    OBJECTS { managedObjectClass, managedObjectInstance, sequenceNumber, 
              perceivedSeverity, eventTime, eventTypePem, probableCause,  
              adslAturThreshold15MinSesL }
    STATUS  current
    DESCRIPTION
    "Severely Errored Second 15-minute interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAturThreshold15MinSesL threshold value)
    "

    --Ericsson Diax additional information:
    --Format: Severely Errored Second 15-minute interval threshold reached: ATU-R from: $2; Probable cause: $7; Threshold value: $8; Sequence Number: $3;

    ::= { adslAturXTrapsEntry 4 }

adslAturPerfXSesThresh1DayTrap       NOTIFICATION-TYPE
    OBJECTS { managedObjectClass, managedObjectInstance, sequenceNumber, 
              perceivedSeverity, eventTime, eventTypePem, probableCause,  
              adslAlarmConfXAturThres1DaySesL }
    STATUS  current
    DESCRIPTION
    "Severely Errored Second 1 Day interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAturThres1DaySesL threshold value)
    "

    --Ericsson Diax additional information:
    --Format: Severely Errored Second 1 Day interval threshold reached: ATU-R from: $2; Probable cause: $7; Number of Severely Errored Seconds: $8; Sequence Number: $3;

    ::= { adslAturXTrapsEntry 5 }

adslAturPerfXUasThresh15MinTrap       NOTIFICATION-TYPE
    OBJECTS { managedObjectClass, managedObjectInstance, sequenceNumber, 
              perceivedSeverity, eventTime, eventTypePem, probableCause,  
              adslAturThreshold15MinUasL }
    STATUS  current
    DESCRIPTION
    "Unavailable Second 15-minute interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAturThreshold15MinUasL threshold value)
    "

    --Ericsson Diax additional information:
    --Format: Unavailable Second 15-minute interval threshold reached: ATU-R from: $2; Probable cause: $7; Threshold value: $8; Sequence Number: $3;

    ::= { adslAturXTrapsEntry 6 }

adslAturPerfXUasThresh1DayTrap       NOTIFICATION-TYPE
    OBJECTS { managedObjectClass, managedObjectInstance, sequenceNumber, 
              perceivedSeverity, eventTime, eventTypePem, probableCause,  
              adslAlarmConfXAturThres1DayUasL }
    STATUS  current
    DESCRIPTION
    "Unavailable Second 1 Day interval threshold reached.

     Valid from:                EDA 1.1R2A
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAturThres1DayUasL threshold value)
    "

    --Ericsson Diax additional information:
    --Format: Unavailable Second 1 Day interval threshold reached: ATU-R from: $2;  Probable cause: $7; Number of Unavailable Seconds: $8; Sequence Number: $3;

    ::= { adslAturXTrapsEntry 7 }   
      
adslAturLineQualityThreshNotReachedTrap       NOTIFICATION-TYPE
    OBJECTS { managedObjectClass, managedObjectInstance, sequenceNumber, 
              perceivedSeverity, eventTime, eventTypePem, probableCause,  
              adslAturLineQualityThresChan0 }
    STATUS  current
    DESCRIPTION
    "Line Quality threshold not reached.

     Valid from:                EDA 2.1
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         ThresholdCrossed
      8: Threshold              Line quality alarm threshold
    "

    --Ericsson Diax additional information:
    --Format: Line Quality threshold not reached: ATU-R from: $2; Probable cause: $7; Threshold: $8; Sequence Number: $3;

    ::= { adslAturXTrapsEntry 8 }


adslAturLineBondLineQualityThreshNotReachedTrap       NOTIFICATION-TYPE
    OBJECTS { managedObjectClass, managedObjectInstance, sequenceNumber, 
              perceivedSeverity, eventTime, eventTypePem, probableCause,  
              adslAturLineBondLineQualityThres }
    STATUS  current
    DESCRIPTION
    "Line Quality threshold not reached.

     Valid from:                EDA 2.2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         ThresholdCrossed
      8: Threshold              Line quality alarm threshold
    "

    --Ericsson Diax additional information:
    --Format: Line Quality threshold not reached: ATU-R from: $2; Probable cause: $7; Threshold: $8; Sequence Number: $3;

    ::= { adslAturXTrapsEntry 9 }
    
adslAturPerfXLofsThresh15MinTrap       NOTIFICATION-TYPE
    OBJECTS { managedObjectClass, managedObjectInstance, sequenceNumber, 
              perceivedSeverity, eventTime, eventTypePem, probableCause,  
              adslAturThresh15MinLofs }
    STATUS  current
    DESCRIPTION
    "Count of Loss of Frame seconds in current 15-minute interval has reached
     the threshold value configured by the adslAturThresh15MinLofs parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAturThresh15MinLofs threshold value)
    "

    --Ericsson Diax additional information:
    --Format: Loss of Frame Second 15-minute interval threshold reached: ATU-R from: $2; Probable cause: $7; Threshold value: $8; Sequence Number: $3;

    ::= { adslAturXTrapsEntry 15 }

adslAturPerfXLofsThresh1DayTrap       NOTIFICATION-TYPE
    OBJECTS { managedObjectClass, managedObjectInstance, sequenceNumber, 
              perceivedSeverity, eventTime, eventTypePem, probableCause,  
              adslAlarmConfXAturThres1DayLofs }
    STATUS  current
    DESCRIPTION
    "Count of Loss of Frame seconds in current 1-day interval has reached
     the threshold value configured by the adslAlarmConfXAturThres1DayLofs parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAturThres1DayLofs threshold value)
    "

    --Ericsson Diax additional information:
    --Format: Loss of Frame Second 1 Day interval threshold reached: ATU-R from: $2;  Probable cause: $7;  Threshold value: $8; Sequence Number: $3;

    ::= { adslAturXTrapsEntry 20 }

adslAturPerfXLossThresh15MinTrap       NOTIFICATION-TYPE
    OBJECTS { managedObjectClass, managedObjectInstance, sequenceNumber, 
              perceivedSeverity, eventTime, eventTypePem, probableCause,  
              adslAturThresh15MinLoss }
    STATUS  current
    DESCRIPTION
    "Count of Loss of Signal seconds in current 15-minute interval has reached
     the threshold value configured by the adslAturThresh15MinLoss parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAturThresh15MinLoss threshold value)
    "

    --Ericsson Diax additional information:
    --Format: Loss of Signal Second 15-minute interval threshold reached: ATU-R from: $2; Probable cause: $7; Threshold value: $8; Sequence Number: $3;

    ::= { adslAturXTrapsEntry 25 }

adslAturPerfXLossThresh1DayTrap       NOTIFICATION-TYPE
    OBJECTS { managedObjectClass, managedObjectInstance, sequenceNumber, 
              perceivedSeverity, eventTime, eventTypePem, probableCause,  
              adslAlarmConfXAturThres1DayLoss }
    STATUS  current
    DESCRIPTION
    "Count of Loss of Signal seconds in current 1-day interval has reached
     the threshold value configured by the adslAlarmConfXAturThres1DayLoss parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAturThres1DayLoss threshold value)
    "

    --Ericsson Diax additional information:
    --Format: Loss of Signal Second 1 Day interval threshold reached: ATU-R from: $2; Probable cause: $7; Threshold value: $8; Sequence Number: $3;

    ::= { adslAturXTrapsEntry 30 }

adslAturPerfXLprsThresh15MinTrap       NOTIFICATION-TYPE
    OBJECTS { managedObjectClass, managedObjectInstance, sequenceNumber, 
              perceivedSeverity, eventTime, eventTypePem, probableCause,  
              adslAturThresh15MinLprs }
    STATUS  current
    DESCRIPTION
    "Count of Loss of Power seconds in current 15-minute interval has reached
     the threshold value configured by the adslAtucThresh15MinLprs parameter.

     Valid from:                EDA 2.2 MA2
    
     Parameters
      1: Managed object class   IP DSLAM Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAturThresh15MinLprs threshold value)
    "

    --Ericsson Diax additional information:
    --Format: Loss of Power Second 15-minute interval threshold reached: ATU-R from: $2; Probable cause: $7; Threshold value: $8; Sequence Number: $3;

    ::= { adslAturXTrapsEntry 35 }

adslAturPerfXLprsThresh1DayTrap       NOTIFICATION-TYPE
    OBJECTS { managedObjectClass, managedObjectInstance, sequenceNumber, 
              perceivedSeverity, eventTime, eventTypePem, probableCause,  
              adslAlarmConfXAturThres1DayLprs }
    STATUS  current
    DESCRIPTION
    "Count of Loss of Power seconds in current 1-day interval has reached
     the threshold value configured by the adslAlarmConfXAturThres1DayLprs parameter.

     Valid from:                EDA 2.2 MA2
    
     Parameters
      1: Managed object class   IP DSLAM  Port
      2: Managed object ID      (MAC + PortNo)
      3: Sequence number        (Alarm sequence number)
      4: Perceived severity     Warning
      5: Event time             (Timestamp is retrieved from a SNTP server)
      6: Event type             QualityOfServiceAlarm
      7: Probable cause         TransmissionError
      8: Threshold parameter    (adslAlarmConfXAturThres1DayLprs threshold value)
    "

    --Ericsson Diax additional information:
    --Format: Loss of Power Second 1 Day interval threshold reached: ATU-R from: $2;  Probable cause: $7; Threshold value: $8; Sequence Number: $3;

    ::= { adslAturXTrapsEntry 40 }   

adslDeviceTraps         OBJECT IDENTIFIER ::= { adslXTraps 3 }
adslDeviceTrapsEntry    OBJECT IDENTIFIER ::= { adslDeviceTraps 0 }

adslDspLoadingFailureTrap       NOTIFICATION-TYPE
    OBJECTS { managedObjectClass, managedObjectInstance, sequenceNumber, 
              perceivedSeverity, eventTime, eventTypePem, probableCause }
    STATUS  current
    DESCRIPTION
    "DSP software could not be loaded and started,
     either incompatible or inoperable HW, damaged 
     or wrong load file. ADSL system inoperable.

     Valid from:                EDA 1.1R2A
    
     Parameters
      1: Managed object class   IP DSLAM
      2: Managed object ID      (MAC)
      3: Sequence number        (Alarm sequence number)
      4: Perceived severity     Critical
      5: Event time             (Timestamp is retrieved from a SNTP server)
      6: Event type             Equipment
      7: Probable cause         EquipmentMalfunction
    "

    --Ericsson Diax additional information:
    --Format: DSP software could not be loaded and started from: $2;  Probable cause: $7; Sequence Number: $3;
    
    ::= { adslDeviceTrapsEntry 1 }  

adslDspCommunicationFailureTrap       NOTIFICATION-TYPE
    OBJECTS { managedObjectClass, managedObjectInstance, sequenceNumber, 
              perceivedSeverity, eventTime, eventTypePem, probableCause }
    STATUS  current
    DESCRIPTION
    "DSP does not reply to a request or too many DSP 
     Unexpected Response Failures have been detected.
     DSP will be reset and reloaded. Affects all lines 
     in the IP DSLAM.

     Valid from:                EDA 1.1R2A
    
     Parameters
      1: Managed object class   IP DSLAM
      2: Managed object ID      (MAC)
      3: Sequence number        (Alarm sequence number)
      4: Perceived severity     Major
      5: Event time             (Timestamp is retrieved from a SNTP server)
      6: Event type             CommunicationsAlarm
      7: Probable cause         SoftwareError
    "

    --Ericsson Diax additional information:
    --Format: DSP does not reply to a request or too many DSP Unexpected Response Failures have been detected from: $2; Probable cause: $7; Sequence Number: $3;
    
    ::= { adslDeviceTrapsEntry 3 }

adslDspInoperableTrap       NOTIFICATION-TYPE
    OBJECTS { managedObjectClass, managedObjectInstance, sequenceNumber, 
              perceivedSeverity, eventTime, eventTypePem, probableCause }
    STATUS  current
    DESCRIPTION
    "The DSP has been reloaded and restarted to many 
     times due to errors. ADSL is considered inoperable.
     In case SW load modules are correct this is most 
     likely a HW problem.

     Valid from:                EDA 1.1R2A
    
     Parameters
      1: Managed object class   IP DSLAM
      2: Managed object ID      (MAC)
      3: Sequence number        (Alarm sequence number)
      4: Perceived severity     Critical
      5: Event time             (Timestamp is retrieved from a SNTP server)
      6: Event type             Equipment
      7: Probable cause         EquipmentMalfunction
    "

    --Ericsson Diax additional information:
    --Format: The DSP has been reloaded and restarted to many times due to errors from: $2; Probable cause: $7; Sequence Number: $3;
    
    ::= { adslDeviceTrapsEntry 4 }  

adslDspHardwareFailureTrap       NOTIFICATION-TYPE
    OBJECTS { managedObjectClass, managedObjectInstance, sequenceNumber, 
              perceivedSeverity, eventTime, eventTypePem, probableCause }
    STATUS  obsolete
    DESCRIPTION
    "HW failure was detected. HW should be replaced.
     ADSL system is inoperable.

     Valid from:                EDA 1.1R2A
     Obsoleted from:            EDA 2.2R1A
    
     Parameters
      1: Managed object class   IP DSLAM
      2: Managed object ID      (MAC)
      3: Sequence number        (Alarm sequence number)
      4: Perceived severity     Critical
      5: Event time             (Timestamp is retrieved from a SNTP server)
      6: Event type             Equipment
      7: Probable cause         EquipmentMalfunction
    "

    --Ericsson Diax additional information:
    --Format: HW failure was detected from: $2; Probable cause: $7; Sequence Number: $3;
    
    ::= { adslDeviceTrapsEntry 5 }


adslXObjectsGroup OBJECT-GROUP
    OBJECTS     {  adslPowerModes, adslTxPowerCalibration, adslRxPowerCalibration, 
                                adslLineStateLedControl, adslTxFilterConfigHmi5, adslTxFilterActualHmi5, 
                                adslEnableACIF,
                          adslAtucPhysXPreviousSnrMgn,adslAtucPhysXPreviousOutputPwr,adslAtucPhysXBitAllocTable,
                              adslAtucPhysXSnr,adslAtucPhysXLoopAtn,
                          adslAturPhysXPreviousSnrMgn, adslAturPhysXPreviousOutputPwr, adslAturPhysXBitAllocTable, 
                              adslAturPhysXBitAllocTableExt, adslAturPhysXLoopAtn,

                         adslConfXName,adslConfXAtucFrequencyBins,adslConfXAturFrequencyBins,
                                adslPowerManagementMode,
 
                        adslAlarmConfXName,adslAlarmConfXAtucThres1DayES,adslAlarmConfXAturThres1DayES,
                               adslAlarmConfXAtucThres1DaySesL,adslAlarmConfXAturThres1DaySesL, 
                               adslAlarmConfXAtucThres1DayUasL,adslAlarmConfXAturThres1DayUasL,
                               adslAlarmConfXAtucThres1DayLofs, adslAlarmConfXAturThres1DayLofs,
                               adslAlarmConfXAtucThres1DayLoss, adslAlarmConfXAturThres1DayLoss,
                               adslAlarmConfXAtucThres1DayLols, adslAlarmConfXAturThres1DayLprs,

                        adslAtucPerfXEcs,adslAtucPerfXCurr15MinEcs,adslAtucPerfXCurr1DayEcs,
                              adslAtucPerfXPrev1DayEcs,
                              adslAtucPerfX1DayValidIntervals, adslAtucPerfX1DayInvalidIntervals,

                       adslAturPerfXEcs,adslAturPerfXCurr15MinEcs,adslAturPerfXCurr1DayEcs,
                              adslAturPerfXPrev1DayEcs,
                              adslAturPerfX1DayValidIntervals, adslAturPerfX1DayInvalidIntervals,
       
                       adslAtucIntervalXEcs,
                       adslAturIntervalXEcs,
                       adslAtucChanPerfXCurr15MinHecv,adslAtucChanPerfXCurr15MinTotalCells,
                             adslAtucChanPerfXCurr15MinTotalUserCells,adslAtucChanPerfXCurr15MinOverFlowCells,
                             adslAtucChanPerfXCurr15MinIdleCells,adslAtucChanPerfXCurr15MinIdleCellBitErrors,
                             adslAtucChanPerfXCurr1DayHecv, adslAtucChanPerfXCurr1DayTotalCells,
                             adslAtucChanPerfXCurr1DayTotalUserCells,adslAtucChanPerfXCurr1DayOverFlowCells,
                             adslAtucChanPerfXCurr1DayIdleCells,adslAtucChanPerfXCurr1DayIdleCellBitErr,
                             adslAtucChanPerfXPrev1DayHecv,adslAtucChanPerfXPrev1DayTotalCells,
                             adslAtucChanPerfXPrev1DayTotalUserCells,adslAtucChanPerfXPrev1DayOverFlowCells,
                             adslAtucChanPerfXPrev1DayIdleCells,adslAtucChanPerfXPrev1DayIdleCellBitErr,
      
                       adslAturChanPerfXCurr15MinHecv,adslAturChanPerfXCurr15MinTotalCells,      
                             adslAturChanPerfXCurr15MinTotalUserCells,adslAturChanPerfXCurr1DayHecv,
                             adslAturChanPerfXCurr1DayTotalCells,adslAturChanPerfXCurr1DayTotalUserCells,
                             adslAturChanPerfXPrev1DayHecv,adslAturChanPerfXPrev1DayTotalCells,
                             adslAturChanPerfXPrev1DayTotalUserCells,
                             adslAturChanPerfXCurr15MinIdleCellBitErrors,
                             adslAturChanPerfXCurr1DayIdleCellBitErr,adslAturChanPerfXPrev1DayIdleCellBitErr,
      

              adslAtucChanIntervalXHecv,adslAtucChanIntervalXTotalCells,
                     adslAtucChanIntervalXTotalUserCells,adslAtucChanIntervalXOverFlowCells,
                     adslAtucChanIntervalXIdleCells,adslAtucChanIntervalXIdleCellBitErrors,

              adslAturChanIntervalXHecv,adslAturChanIntervalXTotalCells,
                     adslAturChanIntervalXTotalUserCells, adslAturChanIntervalXIdleCellBitErrors,
    
                       adslAtucProprietaryPhysXCodingType,
                             adslAtucProprietaryPhysXCurrentFailures,adslAtucProprietaryPhysXChangedFailures,
                             adslAtucProprietaryPhysXActualLineBitRate,adslAtucProprietaryPhysXPreviousLineBitRate,
                             adslAtucProprietaryPhysXMSGc,adslAtucProprietaryPhysXMSGlp,adslAtucProprietaryRefPsd,
 
                       adslAturProprietaryPhysXCodingType,
                            adslAturProprietaryPhysXCurrentFailures,adslAturProprietaryPhysXChangedFailures,
                            adslAturProprietaryPhysXActualLineBitRate,adslAturProprietaryPhysXPreviousLineBitRate,
                            adslAturProprietaryPhysXMSGc,adslAturProprietaryPhysXMSGlp,
                            adslAturProprietaryRefPsd,

                        adslAturProprietaryChanXB,adslAturProprietaryChanXN,adslAturProprietaryChanXR,
                            adslAturProprietaryChanXD,adslAturProprietaryChanXSnum,
                            adslAturProprietaryChanXSdenom,adslAturProprietaryChanXL,
                            adslAturProprietaryChanXM,adslAturProprietaryChanXT,

                     adslAtucProprietaryChanXB,adslAtucProprietaryChanXN,adslAtucProprietaryChanXR,
                             adslAtucProprietaryChanXD,adslAtucProprietaryChanXSnum,
                            adslAtucProprietaryChanXSdenom,adslAtucProprietaryChanXL,
                            adslAtucProprietaryChanXM,adslAtucProprietaryChanXT,

                        adslAtucProprietaryConfXMaxPower,adslAtucProprietaryConfXFixedPsd,
                              adslAtucProprietaryConfXPowerAdaptivity,adslAtucProprietaryConfXOptionsFlagBit2,
                              adslAtucProprietaryConfXDisableTrellis,adslAtucProprietaryConfXRestartMode,adslAtucProprietaryConfXMaxFramingMode,
                              adslAtucProprietaryConfXDisableBitSwap,adslAturProprietaryConfXDisableBitSwap, adslAtucProprietaryConfXDisableHighBitRateInGLite,
                              adslAtucProprietaryChanConfXTxAtmFlagsFast,  adslAtucProprietaryChanConfXRxAtmFlagsFast,
                              adslAtucProprietaryChanConfXTxAtmFlagsIlv,adslAtucProprietaryChanConfXRxAtmFlagsIlv,
                              adslAturProprietaryConfXMaxPower, 
                              adslAtucProprietaryConfXBoostFactor, 
                              adslAtucProprietaryConfXMaxRxPower, adslAtucProprietaryConfXDeltaPsdNormal,
                              adslAtucProprietaryConfXDeltaPsdPlus, adslAtucProprietaryConfXDeltaPsdReach, 
                              adslAturProprietaryConfXDeltaPsdNormal, adslAturProprietaryConfXDeltaPsdPlus, 
                              adslAturProprietaryConfXDeltaPsdReach, adslAtucProprietaryConfXAutomodePIalpha,
                              adslAtucProprietaryConfXAutomodePIbeta, adslAtucProprietaryConfXOptionsFlagBit4, 
                              adslAtucProprietaryConfXAdslPlusTxFilterId, adslAtucProprietaryConfXDisableUS1bitConst,
                              adslAtucProprietaryConfXDisableWindowing, adslAtucProprietaryConfXDisableShowtimeExit,
                              adslAtucProprietaryConfXDisableNitro,  adslAtucProprietaryConfXDisableUpdateTestParameters,
                              adslAtucProprietaryConfXTssiShapeNrOfBreakPoints, adslAtucProprietaryConfXTssiShapeAdsl2ProtocolType, 
                              adslAtucProprietaryConfXTssiShapeBreakPoint,adslAtucProprietaryChanConfXINPminIlvB0,
                              adslAtucProprietaryChanConfXINPminFastB0, adslAtucProprietaryChanConfXINPminFastB1, 
                              adslAturProprietaryChanConfXINPminIlvB0, adslAturProprietaryChanConfXINPminFastB0, 
                              adslAturProprietaryChanConfXINPminFastB1,  
                              adslAtucProprietaryConfXDisableShalfOptionBit0, adslAtucProprietaryConfXDisableShalfOptionBit1, 
                              adslAtucProprietaryConfXDisableLargeD, adslAtucProprietaryConfXForceSegmentation,  
                              adslAtucProprietaryConfXRelaxInpMinCheck,   adslAtucProprietaryConfXhsTxPSD0,  
                              adslAtucProprietaryConfXhsTxPSD1,   adslAtucProprietaryConfXhsTxPSD2,  
                              adslAtucProprietaryChanMinL2BitRateB0, adslAtucProprietaryChanMinL2BitRateB1,  
                              adslAtucProprietaryChanL2LowRateSlotsB0, adslAtucProprietaryChanL2LowRateSlotsB1, 
                              adslAtucProprietaryChanL2PacketB0,  adslAtucProprietaryChanL2PacketB1,   
                              adslAtucProprietaryChanMaxL2BitRateB0, adslAtucProprietaryChanMaxL2BitRateB1,   
                              adslAtucProprietaryL2TestConfigBit0,   adslAtucProprietaryL2TestConfigBit1,    
                              adslAtucProprietaryL2TestConfigBit2,   adslAtucProprietaryL2MinAtpr,  adslAtucProprietaryL0Time,  
                              adslAtucProprietaryL2Time,  adslAtucProprietaryL2Atpr,  adslAtucProprietaryL2Atprt,   
                              adslAtucProprietaryRateAdaptationFlagsBit0Upstream, 
                              adslAtucProprietaryRateAdaptationFlagsBit0Downstream,

                        adslLineXTransAtucCap, adslLineXTransAtucConfig,adslLineXTransAtucActual,adslLineXTransAturCap,
                        adslProprietaryPerfDataXReset, adslProprietaryPerfDataXSinceResetTimeElapsed,
                        adslAtucLineQualityThresChan0,  adslAtucLineQualityThresChan1,  
                        adslAturLineQualityThresChan0, adslAturLineQualityThresChan1,
                        adslAtuc1DayIntervalXLofs, adslAtuc1DayIntervalXLoss,adslAtuc1DayIntervalXLols,
                          adslAtuc1DayIntervalXESs, adslAtuc1DayIntervalXEcs, adslAtuc1DayIntervalXInits, adslAtuc1DayIntervalXValidData,
                          
                        adslAtur1DayIntervalXLofs, adslAtur1DayIntervalXLoss, adslAtur1DayIntervalXLprs,
                          adslAtur1DayIntervalXESs, adslAtur1DayIntervalXEcs, adslAtur1DayIntervalXValidData,

                          adslAtucChan1DayIntervalXCorrectedBlks, adslAtucChan1DayIntervalXUncorrectBlks,
                          adslAtucChan1DayIntervalXHecv, adslAtucChan1DayIntervalXTotalCells,
                          adslAtucChan1DayIntervalXTotalUserCells, adslAtucChan1DayIntervalXOverFlowCells,
                          adslAtucChan1DayIntervalXIdleCells, adslAtucChan1DayIntervalXIdleCellBitErrors,
                          adslAtucChan1DayIntervalXValidData,

                          adslAturChan1DayIntervalXCorrectedBlks, adslAturChan1DayIntervalXUncorrectBlks,
                          adslAturChan1DayIntervalXHecv, adslAturChan1DayIntervalXTotalCells,
                          adslAturChan1DayIntervalXTotalUserCells, adslAturChan1DayIntervalXIdleCellBitErrors,
                          adslAturChan1DayIntervalXValidData
                        } 

    STATUS      current
    DESCRIPTION
        "Current adslXObjects Group"
     ::= { adslXObjectsGroups 1 }

adslXObjectsDeprecatedGroup OBJECT-GROUP
    OBJECTS     { adslAtucProprietaryConfXOptionsFlagBit5, adslEnableDspCoreDump } 
    STATUS      deprecated
    DESCRIPTION
        "Deprecated adslXObjects Group"
     ::= { adslXObjectsGroups 2 }
     
adslXObjectsObsoleteGroup OBJECT-GROUP
    OBJECTS     { adslTxFilterConfig, adslTxFilterActual,adslConfXFrequencyBins,
                              adslAtucProprietaryPhysXLogS, adslAturProprietaryPhysXLogS,
                              adslAtucProprietaryConfXMaxPsd, adslAtucProprietaryConfXOptionsFlagBit1,
                              adslAtucProprietaryChanConfXOptimiseImpulseNoiseResilienceIlv,
                              adslAtucProprietaryChanConfXOptimiseImpulseNoiseResilienceFast,
                              adslAturProprietaryConfXMaxPsd,
                              adslAturProprietaryChanConfXOptimiseImpulseNoiseResilienceIlv,
                              adslAturProprietaryChanConfXOptimiseImpulseNoiseResilienceFast                           
                              
                            } 
    STATUS      obsolete
    DESCRIPTION
        "Deprecated adslXObjects Group"
     ::= { adslXObjectsGroups 3 }     
     
adslXTrapsGroup NOTIFICATION-GROUP
    NOTIFICATIONS     { adslAtucXInitFailureTrap, adslAtucIncorrectConfigurationTrap, adslAtucPerfXESsThresh15MinTrap,
                                      adslAtucPerfXESsThresh1DayTrap, adslAtucPerfXSesThresh15MinTrap, adslAtucPerfXSesThresh1DayTrap, 
                                      adslAtucPerfXUasThresh15MinTrap, adslAtucPerfXUasThresh1DayTrap,
                                      adslAtucPerfXLofsThresh15MinTrap, adslAtucPerfXLofsThresh1DayTrap,
                                      adslAtucPerfXLossThresh15MinTrap, adslAtucPerfXLossThresh1DayTrap,
                                      adslAtucPerfXLolsThresh15MinTrap, adslAtucPerfXLolsThresh1DayTrap,
                                      adslAtucDspUnexpectedResponseTrap, 
                                      adslAtucDspLineResetTrap, adslAtucLineQualityThreshNotReachedTrap, adslAturPerfXESsThresh15MinTrap,
                                      adslAturPerfXESsThresh1DayTrap, adslAturPerfXSesThresh15MinTrap, adslAturPerfXSesThresh1DayTrap, 
                                      adslAturPerfXUasThresh15MinTrap, adslAturPerfXUasThresh1DayTrap,
                                      adslAturPerfXLofsThresh15MinTrap, adslAturPerfXLofsThresh1DayTrap,
                                      adslAturPerfXLossThresh15MinTrap, adslAturPerfXLossThresh1DayTrap,
                                      adslAturPerfXLprsThresh15MinTrap, adslAturPerfXLprsThresh1DayTrap,
                                      adslAturLineQualityThreshNotReachedTrap, 
                                      adslDspLoadingFailureTrap, adslDspCommunicationFailureTrap, adslDspInoperableTrap, 
                                      adslDspHardwareFailureTrap
                                   } 
    STATUS      current
    DESCRIPTION
        "adslX Traps Group"
     ::= { adslXTrapsGroups 1 }
     
END
