-- file automatically created


TELDAT-TRAP-NOE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


noeTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NOE event subsystem."
    REVISION "201401200930Z"
    DESCRIPTION "Initial implementation"
        ::= { telEventTraps 198 }


noeEventsGroup	OBJECT IDENTIFIER	::= { noeTrapsMIB 1 }

noeNotifications	OBJECT IDENTIFIER	::= { noeTrapsMIB 2 }
noeNotificationsPrefix	OBJECT IDENTIFIER	::= { noeNotifications 0 }

noeEventObjects1 OBJECT-IDENTITY
    STATUS current
    DESCRIPTION
        "Event NOE.1
        NOE Application error."
    ::= { noeEventsGroup 1 }

noe1-error OBJECT-TYPE
    SYNTAX DisplayString
    MAX-ACCESS accessible-for-notify
    STATUS current
    DESCRIPTION
        "Parameter 'error' in event NOE.1"
    ::= { noeEventObjects1 1 }

noe1-connetion-id OBJECT-TYPE
    SYNTAX Integer32
    MAX-ACCESS accessible-for-notify
    STATUS current
    DESCRIPTION
        "Parameter 'connetion-id' in event NOE.1"
    ::= { noeEventObjects1 2 }

noeEventObjects2 OBJECT-IDENTITY
    STATUS current
    DESCRIPTION
        "Event NOE.2
        NOE Application information."
    ::= { noeEventsGroup 2 }

noe2-info OBJECT-TYPE
    SYNTAX DisplayString
    MAX-ACCESS accessible-for-notify
    STATUS current
    DESCRIPTION
        "Parameter 'info' in event NOE.2"
    ::= { noeEventObjects2 1 }

noe2-connetion-id OBJECT-TYPE
    SYNTAX Integer32
    MAX-ACCESS accessible-for-notify
    STATUS current
    DESCRIPTION
        "Parameter 'connetion-id' in event NOE.2"
    ::= { noeEventObjects2 2 }

noeEventObjects3 OBJECT-IDENTITY
    STATUS current
    DESCRIPTION
        "Event NOE.3
        NOE Application warning."
    ::= { noeEventsGroup 3 }

noe3-warning OBJECT-TYPE
    SYNTAX DisplayString
    MAX-ACCESS accessible-for-notify
    STATUS current
    DESCRIPTION
        "Parameter 'warning' in event NOE.3"
    ::= { noeEventObjects3 1 }

noe3-connetion-id OBJECT-TYPE
    SYNTAX Integer32
    MAX-ACCESS accessible-for-notify
    STATUS current
    DESCRIPTION
        "Parameter 'connetion-id' in event NOE.3"
    ::= { noeEventObjects3 2 }

noeEventObjects4 OBJECT-IDENTITY
    STATUS current
    DESCRIPTION
        "Event NOE.4
        Terminal connection event."
    ::= { noeEventsGroup 4 }

noe4-event OBJECT-TYPE
    SYNTAX DisplayString
    MAX-ACCESS accessible-for-notify
    STATUS current
    DESCRIPTION
        "Parameter 'event' in event NOE.4"
    ::= { noeEventObjects4 1 }

noe4-description OBJECT-TYPE
    SYNTAX DisplayString
    MAX-ACCESS accessible-for-notify
    STATUS current
    DESCRIPTION
        "Parameter 'description' in event NOE.4"
    ::= { noeEventObjects4 2 }

noe4-connetion-id OBJECT-TYPE
    SYNTAX Integer32
    MAX-ACCESS accessible-for-notify
    STATUS current
    DESCRIPTION
        "Parameter 'connetion-id' in event NOE.4"
    ::= { noeEventObjects4 3 }

noeEventObjects5 OBJECT-IDENTITY
    STATUS current
    DESCRIPTION
        "Event NOE.5
        Event related with application state."
    ::= { noeEventsGroup 5 }

noe5-state OBJECT-TYPE
    SYNTAX DisplayString
    MAX-ACCESS accessible-for-notify
    STATUS current
    DESCRIPTION
        "Parameter 'state' in event NOE.5"
    ::= { noeEventObjects5 1 }

noeEventObjects6 OBJECT-IDENTITY
    STATUS current
    DESCRIPTION
        "Event NOE.6
        UAUDP data message received with sequences <expected-seq> and <sent-seq>
        content size <size> in connection <connection-id>"
    ::= { noeEventsGroup 6 }

noe6-expected-seq OBJECT-TYPE
    SYNTAX Integer32
    MAX-ACCESS accessible-for-notify
    STATUS current
    DESCRIPTION
        "Parameter 'expected-seq' in event NOE.6"
    ::= { noeEventObjects6 1 }

noe6-sent-seq OBJECT-TYPE
    SYNTAX Integer32
    MAX-ACCESS accessible-for-notify
    STATUS current
    DESCRIPTION
        "Parameter 'sent-seq' in event NOE.6"
    ::= { noeEventObjects6 2 }

noe6-size OBJECT-TYPE
    SYNTAX Integer32
    MAX-ACCESS accessible-for-notify
    STATUS current
    DESCRIPTION
        "Parameter 'size' in event NOE.6"
    ::= { noeEventObjects6 3 }

noe6-connection-id OBJECT-TYPE
    SYNTAX Integer32
    MAX-ACCESS accessible-for-notify
    STATUS current
    DESCRIPTION
        "Parameter 'connection-id' in event NOE.6"
    ::= { noeEventObjects6 4 }

noe6-contents OBJECT-TYPE
    SYNTAX DisplayString
    MAX-ACCESS accessible-for-notify
    STATUS current
    DESCRIPTION
        "Parameter 'contents' in event NOE.6"
    ::= { noeEventObjects6 5 }

noeEventObjects7 OBJECT-IDENTITY
    STATUS current
    DESCRIPTION
        "Event NOE.7
        UAUDP NACK message received with expected sequence <expected-seq> in 
        connection <connection-id>"
    ::= { noeEventsGroup 7 }

noe7-expected-seq OBJECT-TYPE
    SYNTAX Integer32
    MAX-ACCESS accessible-for-notify
    STATUS current
    DESCRIPTION
        "Parameter 'expected-seq' in event NOE.7"
    ::= { noeEventObjects7 1 }

noe7-connection-id OBJECT-TYPE
    SYNTAX Integer32
    MAX-ACCESS accessible-for-notify
    STATUS current
    DESCRIPTION
        "Parameter 'connection-id' in event NOE.7"
    ::= { noeEventObjects7 2 }

noeEventObjects8 OBJECT-IDENTITY
    STATUS current
    DESCRIPTION
        "Event NOE.8
        UAUDP KEEPALIVEACK message received in connetion-id."
    ::= { noeEventsGroup 8 }

noe8-connection-id OBJECT-TYPE
    SYNTAX Integer32
    MAX-ACCESS accessible-for-notify
    STATUS current
    DESCRIPTION
        "Parameter 'connection-id' in event NOE.8"
    ::= { noeEventObjects8 1 }

noeEventObjects9 OBJECT-IDENTITY
    STATUS current
    DESCRIPTION
        "Event NOE.9
        UAUDP RELEASE message received in connetion-id."
    ::= { noeEventsGroup 9 }

noe9-connection-id OBJECT-TYPE
    SYNTAX Integer32
    MAX-ACCESS accessible-for-notify
    STATUS current
    DESCRIPTION
        "Parameter 'connection-id' in event NOE.9"
    ::= { noeEventObjects9 1 }

noeEventObjects10 OBJECT-IDENTITY
    STATUS current
    DESCRIPTION
        "Event NOE.10
        UAUDP RELEASE message received in connetion-id."
    ::= { noeEventsGroup 10 }

noe10-connection-id OBJECT-TYPE
    SYNTAX Integer32
    MAX-ACCESS accessible-for-notify
    STATUS current
    DESCRIPTION
        "Parameter 'connection-id' in event NOE.10"
    ::= { noeEventObjects10 1 }

noeEventObjects11 OBJECT-IDENTITY
    STATUS current
    DESCRIPTION
        "Event NOE.11
        UAUDP UNKNOWN message with size received in connetion-id."
    ::= { noeEventsGroup 11 }

noe11-size OBJECT-TYPE
    SYNTAX Integer32
    MAX-ACCESS accessible-for-notify
    STATUS current
    DESCRIPTION
        "Parameter 'size' in event NOE.11"
    ::= { noeEventObjects11 1 }

noe11-connection-id OBJECT-TYPE
    SYNTAX Integer32
    MAX-ACCESS accessible-for-notify
    STATUS current
    DESCRIPTION
        "Parameter 'connection-id' in event NOE.11"
    ::= { noeEventObjects11 2 }

noe11-contents OBJECT-TYPE
    SYNTAX DisplayString
    MAX-ACCESS accessible-for-notify
    STATUS current
    DESCRIPTION
        "Parameter 'contents' in event NOE.11"
    ::= { noeEventObjects11 3 }

noeEventObjects12 OBJECT-IDENTITY
    STATUS current
    DESCRIPTION
        "Event NOE.12
        UAUDP data message sent with sequences <expected-seq> and <sent-seq>
        content size <size> in connection <connection-id>"
    ::= { noeEventsGroup 12 }

noe12-expected-seq OBJECT-TYPE
    SYNTAX Integer32
    MAX-ACCESS accessible-for-notify
    STATUS current
    DESCRIPTION
        "Parameter 'expected-seq' in event NOE.12"
    ::= { noeEventObjects12 1 }

noe12-sent-seq OBJECT-TYPE
    SYNTAX Integer32
    MAX-ACCESS accessible-for-notify
    STATUS current
    DESCRIPTION
        "Parameter 'sent-seq' in event NOE.12"
    ::= { noeEventObjects12 2 }

noe12-size OBJECT-TYPE
    SYNTAX Integer32
    MAX-ACCESS accessible-for-notify
    STATUS current
    DESCRIPTION
        "Parameter 'size' in event NOE.12"
    ::= { noeEventObjects12 3 }

noe12-connection-id OBJECT-TYPE
    SYNTAX Integer32
    MAX-ACCESS accessible-for-notify
    STATUS current
    DESCRIPTION
        "Parameter 'connection-id' in event NOE.12"
    ::= { noeEventObjects12 4 }

noe12-contents OBJECT-TYPE
    SYNTAX DisplayString
    MAX-ACCESS accessible-for-notify
    STATUS current
    DESCRIPTION
        "Parameter 'contents' in event NOE.12"
    ::= { noeEventObjects12 5 }

noeEventObjects13 OBJECT-IDENTITY
    STATUS current
    DESCRIPTION
        "Event NOE.13
        UAUDP NACK message sent with expected sequence <expected-seq> in 
        connection <connection-id>"
    ::= { noeEventsGroup 13 }

noe13-expected-seq OBJECT-TYPE
    SYNTAX Integer32
    MAX-ACCESS accessible-for-notify
    STATUS current
    DESCRIPTION
        "Parameter 'expected-seq' in event NOE.13"
    ::= { noeEventObjects13 1 }

noe13-connection-id OBJECT-TYPE
    SYNTAX Integer32
    MAX-ACCESS accessible-for-notify
    STATUS current
    DESCRIPTION
        "Parameter 'connection-id' in event NOE.13"
    ::= { noeEventObjects13 2 }

noeEventObjects14 OBJECT-IDENTITY
    STATUS current
    DESCRIPTION
        "Event NOE.14
        UAUDP KEEPALIVE message sent in connetion-id."
    ::= { noeEventsGroup 14 }

noe14-connection-id OBJECT-TYPE
    SYNTAX Integer32
    MAX-ACCESS accessible-for-notify
    STATUS current
    DESCRIPTION
        "Parameter 'connection-id' in event NOE.14"
    ::= { noeEventObjects14 1 }

noeEventObjects15 OBJECT-IDENTITY
    STATUS current
    DESCRIPTION
        "Event NOE.15
        UAUDP RELEASEACK message sent in connetion-id."
    ::= { noeEventsGroup 15 }

noe15-connection-id OBJECT-TYPE
    SYNTAX Integer32
    MAX-ACCESS accessible-for-notify
    STATUS current
    DESCRIPTION
        "Parameter 'connection-id' in event NOE.15"
    ::= { noeEventObjects15 1 }

noeEventObjects16 OBJECT-IDENTITY
    STATUS current
    DESCRIPTION
        "Event NOE.16
        UAUDP message with size forwarded in connetion-id with contents. 
        Direction In (towards CS) or Out (towards terminal)"
    ::= { noeEventsGroup 16 }

noe16-direction OBJECT-TYPE
    SYNTAX DisplayString
    MAX-ACCESS accessible-for-notify
    STATUS current
    DESCRIPTION
        "Parameter 'direction' in event NOE.16"
    ::= { noeEventObjects16 1 }

noe16-size OBJECT-TYPE
    SYNTAX Integer32
    MAX-ACCESS accessible-for-notify
    STATUS current
    DESCRIPTION
        "Parameter 'size' in event NOE.16"
    ::= { noeEventObjects16 2 }

noe16-connection-id OBJECT-TYPE
    SYNTAX Integer32
    MAX-ACCESS accessible-for-notify
    STATUS current
    DESCRIPTION
        "Parameter 'connection-id' in event NOE.16"
    ::= { noeEventObjects16 3 }

noe16-contents OBJECT-TYPE
    SYNTAX DisplayString
    MAX-ACCESS accessible-for-notify
    STATUS current
    DESCRIPTION
        "Parameter 'contents' in event NOE.16"
    ::= { noeEventObjects16 4 }

noeEventObjects17 OBJECT-IDENTITY
    STATUS current
    DESCRIPTION
        "Event NOE.17
        UAUDP message from Call Server dropped in connetion-id."
    ::= { noeEventsGroup 17 }

noe17-connection-id OBJECT-TYPE
    SYNTAX Integer32
    MAX-ACCESS accessible-for-notify
    STATUS current
    DESCRIPTION
        "Parameter 'connection-id' in event NOE.17"
    ::= { noeEventObjects17 1 }

noeEventObjects18 OBJECT-IDENTITY
    STATUS current
    DESCRIPTION
        "Event NOE.18
        New event in noe terminal"
    ::= { noeEventsGroup 18 }

noe18-event OBJECT-TYPE
    SYNTAX DisplayString
    MAX-ACCESS accessible-for-notify
    STATUS current
    DESCRIPTION
        "Parameter 'event' in event NOE.18"
    ::= { noeEventObjects18 1 }

noe18-old-state OBJECT-TYPE
    SYNTAX DisplayString
    MAX-ACCESS accessible-for-notify
    STATUS current
    DESCRIPTION
        "Parameter 'old-state' in event NOE.18"
    ::= { noeEventObjects18 2 }

noe18-new-state OBJECT-TYPE
    SYNTAX DisplayString
    MAX-ACCESS accessible-for-notify
    STATUS current
    DESCRIPTION
        "Parameter 'new-state' in event NOE.18"
    ::= { noeEventObjects18 3 }

noe18-cdr OBJECT-TYPE
    SYNTAX Integer32
    MAX-ACCESS accessible-for-notify
    STATUS current
    DESCRIPTION
        "Parameter 'cdr' in event NOE.18"
    ::= { noeEventObjects18 4 }

noe18-connection-id OBJECT-TYPE
    SYNTAX Integer32
    MAX-ACCESS accessible-for-notify
    STATUS current
    DESCRIPTION
        "Parameter 'connection-id' in event NOE.18"
    ::= { noeEventObjects18 5 }

noeEventObjects19 OBJECT-IDENTITY
    STATUS current
    DESCRIPTION
        "Event NOE.19
        UAUDP RELEASE message sent in connetion-id."
    ::= { noeEventsGroup 19 }

noe19-connection-id OBJECT-TYPE
    SYNTAX Integer32
    MAX-ACCESS accessible-for-notify
    STATUS current
    DESCRIPTION
        "Parameter 'connection-id' in event NOE.19"
    ::= { noeEventObjects19 1 }

noeEventObjects20 OBJECT-IDENTITY
    STATUS current
    DESCRIPTION
        "Event NOE.20
        NOE Application trace."
    ::= { noeEventsGroup 20 }

noe20-trace OBJECT-TYPE
    SYNTAX DisplayString
    MAX-ACCESS accessible-for-notify
    STATUS current
    DESCRIPTION
        "Parameter 'trace' in event NOE.20"
    ::= { noeEventObjects20 1 }

noe20-connetion-id OBJECT-TYPE
    SYNTAX Integer32
    MAX-ACCESS accessible-for-notify
    STATUS current
    DESCRIPTION
        "Parameter 'connetion-id' in event NOE.20"
    ::= { noeEventObjects20 2 }

noeEventObjects21 OBJECT-IDENTITY
    STATUS current
    DESCRIPTION
        "Event NOE.21
        UAUDP CONNECT message received in connetion-id."
    ::= { noeEventsGroup 21 }

noe21-size OBJECT-TYPE
    SYNTAX Integer32
    MAX-ACCESS accessible-for-notify
    STATUS current
    DESCRIPTION
        "Parameter 'size' in event NOE.21"
    ::= { noeEventObjects21 1 }

noe21-connection-id OBJECT-TYPE
    SYNTAX Integer32
    MAX-ACCESS accessible-for-notify
    STATUS current
    DESCRIPTION
        "Parameter 'connection-id' in event NOE.21"
    ::= { noeEventObjects21 2 }

noe21-contents OBJECT-TYPE
    SYNTAX DisplayString
    MAX-ACCESS accessible-for-notify
    STATUS current
    DESCRIPTION
        "Parameter 'contents' in event NOE.21"
    ::= { noeEventObjects21 3 }

noeEventObjects22 OBJECT-IDENTITY
    STATUS current
    DESCRIPTION
        "Event NOE.22
        UAUDP CONNECTACK message received in connetion-id."
    ::= { noeEventsGroup 22 }

noe22-connection-id OBJECT-TYPE
    SYNTAX Integer32
    MAX-ACCESS accessible-for-notify
    STATUS current
    DESCRIPTION
        "Parameter 'connection-id' in event NOE.22"
    ::= { noeEventObjects22 1 }

noeEventObjects23 OBJECT-IDENTITY
    STATUS current
    DESCRIPTION
        "Event NOE.23
        UAUDP CONNECT message sent in connetion-id."
    ::= { noeEventsGroup 23 }

noe23-size OBJECT-TYPE
    SYNTAX Integer32
    MAX-ACCESS accessible-for-notify
    STATUS current
    DESCRIPTION
        "Parameter 'size' in event NOE.23"
    ::= { noeEventObjects23 1 }

noe23-connection-id OBJECT-TYPE
    SYNTAX Integer32
    MAX-ACCESS accessible-for-notify
    STATUS current
    DESCRIPTION
        "Parameter 'connection-id' in event NOE.23"
    ::= { noeEventObjects23 2 }

noe23-contents OBJECT-TYPE
    SYNTAX DisplayString
    MAX-ACCESS accessible-for-notify
    STATUS current
    DESCRIPTION
        "Parameter 'contents' in event NOE.23"
    ::= { noeEventObjects23 3 }

noeEventObjects24 OBJECT-IDENTITY
    STATUS current
    DESCRIPTION
        "Event NOE.24
        UAUDP CONNECTACK message sent in connetion-id."
    ::= { noeEventsGroup 24 }

noe24-connection-id OBJECT-TYPE
    SYNTAX Integer32
    MAX-ACCESS accessible-for-notify
    STATUS current
    DESCRIPTION
        "Parameter 'connection-id' in event NOE.24"
    ::= { noeEventObjects24 1 }


noeNotification1 NOTIFICATION-TYPE
    OBJECTS { 
              noe1-error, 
              noe1-connetion-id 
            }
    STATUS current
    DESCRIPTION
        "Notification of Event NOE.1

        Message: 'Noe App error: $1. Id $2'

        Parameters list:
              $1: noe1-error
              $2: noe1-connetion-id

        NOE Application error."
    ::= { noeNotificationsPrefix 1 }

noeNotification2 NOTIFICATION-TYPE
    OBJECTS { 
              noe2-info, 
              noe2-connetion-id 
            }
    STATUS current
    DESCRIPTION
        "Notification of Event NOE.2

        Message: 'Noe App info: $1. Id $2'

        Parameters list:
              $1: noe2-info
              $2: noe2-connetion-id

        NOE Application information."
    ::= { noeNotificationsPrefix 2 }

noeNotification3 NOTIFICATION-TYPE
    OBJECTS { 
              noe3-warning, 
              noe3-connetion-id 
            }
    STATUS current
    DESCRIPTION
        "Notification of Event NOE.3

        Message: 'Noe App warning: $1. Id $2'

        Parameters list:
              $1: noe3-warning
              $2: noe3-connetion-id

        NOE Application warning."
    ::= { noeNotificationsPrefix 3 }

noeNotification4 NOTIFICATION-TYPE
    OBJECTS { 
              noe4-event, 
              noe4-description,
              noe4-connetion-id 
            }
    STATUS current
    DESCRIPTION
        "Notification of Event NOE.4

        Message: 'Terminal: $1 $2. Id $3'

        Parameters list:
              $1: noe4-event
              $2: noe4-description
              $3: noe4-connetion-id

        Terminal connection event."
    ::= { noeNotificationsPrefix 4 }

noeNotification5 NOTIFICATION-TYPE
    OBJECTS { 
              noe5-state 
            }
    STATUS current
    DESCRIPTION
        "Notification of Event NOE.5

        Message: 'Noe App state: $1'

        Parameters list:
              $1: noe5-state

        Event related with application state."
    ::= { noeNotificationsPrefix 5 }

noeNotification6 NOTIFICATION-TYPE
    OBJECTS { 
              noe6-expected-seq, 
              noe6-sent-seq,
              noe6-size,
              noe6-connection-id,
              noe6-contents 
            }
    STATUS current
    DESCRIPTION
        "Notification of Event NOE.6

        Message: 'Rx DATA, exp $1, sent $2, size $3, Id $4: $5'

        Parameters list:
              $1: noe6-expected-seq
              $2: noe6-sent-seq
              $3: noe6-size
              $4: noe6-connection-id
              $5: noe6-contents

        UAUDP data message received with sequences <expected-seq> and <sent-seq>
        content size <size> in connection <connection-id>"
    ::= { noeNotificationsPrefix 6 }

noeNotification7 NOTIFICATION-TYPE
    OBJECTS { 
              noe7-expected-seq, 
              noe7-connection-id 
            }
    STATUS current
    DESCRIPTION
        "Notification of Event NOE.7

        Message: 'Rx NACK, exp $1, Id $2'

        Parameters list:
              $1: noe7-expected-seq
              $2: noe7-connection-id

        UAUDP NACK message received with expected sequence <expected-seq> in 
        connection <connection-id>"
    ::= { noeNotificationsPrefix 7 }

noeNotification8 NOTIFICATION-TYPE
    OBJECTS { 
              noe8-connection-id 
            }
    STATUS current
    DESCRIPTION
        "Notification of Event NOE.8

        Message: 'Rx KEEPALIVEACK, Id $1'

        Parameters list:
              $1: noe8-connection-id

        UAUDP KEEPALIVEACK message received in connetion-id."
    ::= { noeNotificationsPrefix 8 }

noeNotification9 NOTIFICATION-TYPE
    OBJECTS { 
              noe9-connection-id 
            }
    STATUS current
    DESCRIPTION
        "Notification of Event NOE.9

        Message: 'Rx RELEASE, Id $1'

        Parameters list:
              $1: noe9-connection-id

        UAUDP RELEASE message received in connetion-id."
    ::= { noeNotificationsPrefix 9 }

noeNotification10 NOTIFICATION-TYPE
    OBJECTS { 
              noe10-connection-id 
            }
    STATUS current
    DESCRIPTION
        "Notification of Event NOE.10

        Message: 'Rx RELEASEACK, Id $1'

        Parameters list:
              $1: noe10-connection-id

        UAUDP RELEASE message received in connetion-id."
    ::= { noeNotificationsPrefix 10 }

noeNotification11 NOTIFICATION-TYPE
    OBJECTS { 
              noe11-size, 
              noe11-connection-id,
              noe11-contents 
            }
    STATUS current
    DESCRIPTION
        "Notification of Event NOE.11

        Message: 'Rx UNKNOWN, size $1, Id $2: $3'

        Parameters list:
              $1: noe11-size
              $2: noe11-connection-id
              $3: noe11-contents

        UAUDP UNKNOWN message with size received in connetion-id."
    ::= { noeNotificationsPrefix 11 }

noeNotification12 NOTIFICATION-TYPE
    OBJECTS { 
              noe12-expected-seq, 
              noe12-sent-seq,
              noe12-size,
              noe12-connection-id,
              noe12-contents 
            }
    STATUS current
    DESCRIPTION
        "Notification of Event NOE.12

        Message: 'Tx DATA, exp $1, sent $2, size $3, Id $4: $5'

        Parameters list:
              $1: noe12-expected-seq
              $2: noe12-sent-seq
              $3: noe12-size
              $4: noe12-connection-id
              $5: noe12-contents

        UAUDP data message sent with sequences <expected-seq> and <sent-seq>
        content size <size> in connection <connection-id>"
    ::= { noeNotificationsPrefix 12 }

noeNotification13 NOTIFICATION-TYPE
    OBJECTS { 
              noe13-expected-seq, 
              noe13-connection-id 
            }
    STATUS current
    DESCRIPTION
        "Notification of Event NOE.13

        Message: 'Tx NACK, exp $1, Id $2'

        Parameters list:
              $1: noe13-expected-seq
              $2: noe13-connection-id

        UAUDP NACK message sent with expected sequence <expected-seq> in 
        connection <connection-id>"
    ::= { noeNotificationsPrefix 13 }

noeNotification14 NOTIFICATION-TYPE
    OBJECTS { 
              noe14-connection-id 
            }
    STATUS current
    DESCRIPTION
        "Notification of Event NOE.14

        Message: 'Tx KEEPALIVE, Id $1'

        Parameters list:
              $1: noe14-connection-id

        UAUDP KEEPALIVE message sent in connetion-id."
    ::= { noeNotificationsPrefix 14 }

noeNotification15 NOTIFICATION-TYPE
    OBJECTS { 
              noe15-connection-id 
            }
    STATUS current
    DESCRIPTION
        "Notification of Event NOE.15

        Message: 'Tx RELEASEACK, Id $1'

        Parameters list:
              $1: noe15-connection-id

        UAUDP RELEASEACK message sent in connetion-id."
    ::= { noeNotificationsPrefix 15 }

noeNotification16 NOTIFICATION-TYPE
    OBJECTS { 
              noe16-direction, 
              noe16-size,
              noe16-connection-id,
              noe16-contents 
            }
    STATUS current
    DESCRIPTION
        "Notification of Event NOE.16

        Message: 'Packet forwarded, Dir: $1, size $2, Id $3: $4'

        Parameters list:
              $1: noe16-direction
              $2: noe16-size
              $3: noe16-connection-id
              $4: noe16-contents

        UAUDP message with size forwarded in connetion-id with contents. 
        Direction In (towards CS) or Out (towards terminal)"
    ::= { noeNotificationsPrefix 16 }

noeNotification17 NOTIFICATION-TYPE
    OBJECTS { 
              noe17-connection-id 
            }
    STATUS current
    DESCRIPTION
        "Notification of Event NOE.17

        Message: 'Packet from CS dropped, Id $1'

        Parameters list:
              $1: noe17-connection-id

        UAUDP message from Call Server dropped in connetion-id."
    ::= { noeNotificationsPrefix 17 }

noeNotification18 NOTIFICATION-TYPE
    OBJECTS { 
              noe18-event, 
              noe18-old-state,
              noe18-new-state,
              noe18-cdr,
              noe18-connection-id 
            }
    STATUS current
    DESCRIPTION
        "Notification of Event NOE.18

        Message: 'New event $1 old state $2 new state $3, cdr $4, Id $5'

        Parameters list:
              $1: noe18-event
              $2: noe18-old-state
              $3: noe18-new-state
              $4: noe18-cdr
              $5: noe18-connection-id

        New event in noe terminal"
    ::= { noeNotificationsPrefix 18 }

noeNotification19 NOTIFICATION-TYPE
    OBJECTS { 
              noe19-connection-id 
            }
    STATUS current
    DESCRIPTION
        "Notification of Event NOE.19

        Message: 'Tx RELEASE, Id $1'

        Parameters list:
              $1: noe19-connection-id

        UAUDP RELEASE message sent in connetion-id."
    ::= { noeNotificationsPrefix 19 }

noeNotification20 NOTIFICATION-TYPE
    OBJECTS { 
              noe20-trace, 
              noe20-connetion-id 
            }
    STATUS current
    DESCRIPTION
        "Notification of Event NOE.20

        Message: 'Noe App trace: $1. Id $2'

        Parameters list:
              $1: noe20-trace
              $2: noe20-connetion-id

        NOE Application trace."
    ::= { noeNotificationsPrefix 20 }

noeNotification21 NOTIFICATION-TYPE
    OBJECTS { 
              noe21-size, 
              noe21-connection-id,
              noe21-contents 
            }
    STATUS current
    DESCRIPTION
        "Notification of Event NOE.21

        Message: 'Rx CONNECT, size $1, Id $2: $3'

        Parameters list:
              $1: noe21-size
              $2: noe21-connection-id
              $3: noe21-contents

        UAUDP CONNECT message received in connetion-id."
    ::= { noeNotificationsPrefix 21 }

noeNotification22 NOTIFICATION-TYPE
    OBJECTS { 
              noe22-connection-id 
            }
    STATUS current
    DESCRIPTION
        "Notification of Event NOE.22

        Message: 'Rx CONNECTACK, Id $1'

        Parameters list:
              $1: noe22-connection-id

        UAUDP CONNECTACK message received in connetion-id."
    ::= { noeNotificationsPrefix 22 }

noeNotification23 NOTIFICATION-TYPE
    OBJECTS { 
              noe23-size, 
              noe23-connection-id,
              noe23-contents 
            }
    STATUS current
    DESCRIPTION
        "Notification of Event NOE.23

        Message: 'Tx CONNECT, size $1, Id $2: $3'

        Parameters list:
              $1: noe23-size
              $2: noe23-connection-id
              $3: noe23-contents

        UAUDP CONNECT message sent in connetion-id."
    ::= { noeNotificationsPrefix 23 }

noeNotification24 NOTIFICATION-TYPE
    OBJECTS { 
              noe24-connection-id 
            }
    STATUS current
    DESCRIPTION
        "Notification of Event NOE.24

        Message: 'Tx CONNECTACK, Id $1'

        Parameters list:
              $1: noe24-connection-id

        UAUDP CONNECTACK message sent in connetion-id."
    ::= { noeNotificationsPrefix 24 }


END
