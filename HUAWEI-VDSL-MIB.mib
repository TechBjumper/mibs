-- ============================================================================
-- Copyright (C) 2003 by  HUAWEI TECHNOLOGIES. All rights reserved.
--
-- Description:  
-- Reference:  
-- Version: V3.00
-- History:
-- liu chenglong 2003-04-28 Added IPR Decriptions and updated all MIB version to V3.00
-- ============================================================================
	HUAWEI-VDSL-MIB DEFINITIONS ::= BEGIN
 
		IMPORTS
			ifIndex			
				FROM IF-MIB			
			Integer32, Counter32, OBJECT-TYPE			
				FROM SNMPv2-SMI			
			vdslMibObjects, vdslPhysEntry, vdslPhysSide, vdslLineConfProfileEntry, vdslLineConfProfileName			
				FROM VDSL-LINE-MIB;
	
	

		hwVdslActualRate OBJECT-TYPE
			SYNTAX Integer32
			UNITS "bps"
			MAX-ACCESS read-only
			STATUS current
			DESCRIPTION
				"The actual rate of this Vtu.
				
				"
			::= { vdslPhysEntry 65536 }
		
		hwVdslCurrSnr OBJECT-TYPE
			SYNTAX Integer32
			UNITS "tenth dB"
			MAX-ACCESS read-only
			STATUS current
			DESCRIPTION
				"Current Signal to Noise Ratio.
				
				"
			::= { vdslPhysEntry 65537 }
		
		hwVdslMse OBJECT-TYPE
			SYNTAX Integer32
			UNITS "tenth dB"
			MAX-ACCESS read-only
			STATUS current
			DESCRIPTION
				"Minimum Square Error.
				
				"
			::= { vdslPhysEntry 65538 }
		
		hwVdslChipHrdVer OBJECT-TYPE
			SYNTAX Integer32
			MAX-ACCESS read-only
			STATUS current
			DESCRIPTION
				"VDSL chip hardware version
				
				VDSL "
			::= { vdslPhysEntry 65539 }
		
		hwVdslChipSftVer OBJECT-TYPE
			SYNTAX Integer32
			MAX-ACCESS read-only
			STATUS current
			DESCRIPTION
				"VDSL chip software version
				
				"
			::= { vdslPhysEntry 65540 }
		
		hwVdslChipPatchVer OBJECT-TYPE
			SYNTAX Integer32
			MAX-ACCESS read-only
			STATUS current
			DESCRIPTION
				"VDSL chip patch version
				
				"
			::= { vdslPhysEntry 65541 }
		
		hwVdslLineConfAutoTrain OBJECT-TYPE
			SYNTAX INTEGER
				{
				enabled(1),
				disabled(2)
				}
			MAX-ACCESS read-write
			STATUS current
			DESCRIPTION
				"This object specifies if the modem is allowed to train automatically.
				
				"
			DEFVAL { 1 }
			::= { vdslLineConfProfileEntry 65536 }
		
		hwVdslEtherStatsTable OBJECT-TYPE
			SYNTAX SEQUENCE OF HwVdslEtherStatsEntry
			MAX-ACCESS not-accessible
			STATUS current
			DESCRIPTION
				"This table provides one row for each Vtu. Each row 
				contains the ehternet statistic Parameters table for
				that Vtu.
				
					 "
			::= { vdslMibObjects 65536 }
		
		hwVdslEtherStatsEntry OBJECT-TYPE
			SYNTAX HwVdslEtherStatsEntry
			MAX-ACCESS not-accessible
			STATUS current
			DESCRIPTION
				"An entry in the hwVdslEtherStatsTable.
				
				"
			INDEX { ifIndex, vdslPhysSide }
			::= { hwVdslEtherStatsTable 1 }
		
		HwVdslEtherStatsEntry ::=
			SEQUENCE { 
				hwVdslEtherStatsAlignmentErrors
					Counter32,
				hwVdslEtherStatsSingleCollisionFrames
					Counter32,
				hwVdslEtherStatsMultipleCollisionFrames
					Counter32,
				hwVdslEtherStatsDeferredTransmissions
					Counter32,
				hwVdslEtherStatsLateCollisionFrames
					Counter32,
				hwVdslEtherStatsExcessiveCollisionFrames
					Counter32,
				hwVdslEtherStatsReceiveErrors
					Counter32,
				hwVdslEtherStatsCarrierErrors
					Counter32,
				hwVdslEtherStatsTooLongErrors
					Counter32,
				hwVdslEtherStatsSequenceErrors
					Counter32,
				hwVdslEtherStatsTransmitOctets
					Counter32,
				hwVdslEtherStatsReceiveOctets
					Counter32,
				hwVdslEtherStatsReceiveBroadcastFrames
					Counter32,
				hwVdslEtherStatsReceivePauseFrames
					Counter32,
				hwVdslEtherStatsTransmitPauseFrames
					Counter32,
				hwVdslEtherStatsTransmitFrames
					Counter32,
				hwVdslEtherStatsReceiveFrames
					Counter32
			 }

		hwVdslEtherStatsAlignmentErrors OBJECT-TYPE
			SYNTAX Counter32
			MAX-ACCESS read-only
			STATUS current
			DESCRIPTION
				"The total number of frames received with alignment errors (an odd
				number of nibbles).
				
				"
			::= { hwVdslEtherStatsEntry 1 }
		
		hwVdslEtherStatsSingleCollisionFrames OBJECT-TYPE
			SYNTAX Counter32
			MAX-ACCESS read-only
			STATUS current
			DESCRIPTION
				"A count of successfully transmitted frames for which transmission 
				was inhibited by exactly one collision.
				
				"
			::= { hwVdslEtherStatsEntry 2 }
		
		hwVdslEtherStatsMultipleCollisionFrames OBJECT-TYPE
			SYNTAX Counter32
			MAX-ACCESS read-only
			STATUS current
			DESCRIPTION
				"A count of successfully transmitted frames for which transmission
				was inhibited by more than one collision.
				
				"
			::= { hwVdslEtherStatsEntry 3 }
		
		hwVdslEtherStatsDeferredTransmissions OBJECT-TYPE
			SYNTAX Counter32
			MAX-ACCESS read-only
			STATUS current
			DESCRIPTION
				"A count of frames for which the first transmission
				attempt was delayed because the Ethernet media was
				busy.
				
				"
			::= { hwVdslEtherStatsEntry 4 }
		
		hwVdslEtherStatsLateCollisionFrames OBJECT-TYPE
			SYNTAX Counter32
			MAX-ACCESS read-only
			STATUS current
			DESCRIPTION
				"The total number of times that a collision was detected
				on a particular interface later than 512 bit-times into
				the transmission of a packet.
				
				"
			::= { hwVdslEtherStatsEntry 5 }
		
		hwVdslEtherStatsExcessiveCollisionFrames OBJECT-TYPE
			SYNTAX Counter32
			MAX-ACCESS read-only
			STATUS current
			DESCRIPTION
				"A count of frames for which transmission failed due to 
				excessive collisions.
				
				"
			::= { hwVdslEtherStatsEntry 6 }
		
		hwVdslEtherStatsReceiveErrors OBJECT-TYPE
			SYNTAX Counter32
			MAX-ACCESS read-only
			STATUS current
			DESCRIPTION
				"The total number of frames received with less than 64 bytes.
				
				"
			::= { hwVdslEtherStatsEntry 7 }
		
		hwVdslEtherStatsCarrierErrors OBJECT-TYPE
			SYNTAX Counter32
			MAX-ACCESS read-only
			STATUS current
			DESCRIPTION
				"The total number of times that the carrier sense condition was
				lost or never asserted when attempting to transmit a frame on 
				a particular interface.
				
				"
			::= { hwVdslEtherStatsEntry 8 }
		
		hwVdslEtherStatsTooLongErrors OBJECT-TYPE
			SYNTAX Counter32
			MAX-ACCESS read-only
			STATUS current
			DESCRIPTION
				"The total number of frames received with more than maximum length.
				
"
			::= { hwVdslEtherStatsEntry 9 }
		
		hwVdslEtherStatsSequenceErrors OBJECT-TYPE
			SYNTAX Counter32
			MAX-ACCESS read-only
			STATUS current
			DESCRIPTION
				"The total number of frames received that had a bad Frame Check
				Sequence (FCS).
				
					"
			::= { hwVdslEtherStatsEntry 10 }
		
		hwVdslEtherStatsTransmitOctets OBJECT-TYPE
			SYNTAX Counter32
			MAX-ACCESS read-only
			STATUS current
			DESCRIPTION
				"A count of data and padding octets of frames that are successfully
				transmitted.
				
				"
			::= { hwVdslEtherStatsEntry 11 }
		
		hwVdslEtherStatsReceiveOctets OBJECT-TYPE
			SYNTAX Counter32
			MAX-ACCESS read-only
			STATUS current
			DESCRIPTION
				"A count of data and padding octets of frames that are successfully
				received.
				
				"
			::= { hwVdslEtherStatsEntry 12 }
		
		hwVdslEtherStatsReceiveBroadcastFrames OBJECT-TYPE
			SYNTAX Counter32
			MAX-ACCESS read-only
			STATUS current
			DESCRIPTION
				"A count of frames that are successfully received and are directed
				to the broadcast group address.
				
				"
			::= { hwVdslEtherStatsEntry 13 }
		
		hwVdslEtherStatsReceivePauseFrames OBJECT-TYPE
			SYNTAX Counter32
			MAX-ACCESS read-only
			STATUS current
			DESCRIPTION
				"The total number of PAUSE packets received.
				
				 "
			::= { hwVdslEtherStatsEntry 14 }
		
		hwVdslEtherStatsTransmitPauseFrames OBJECT-TYPE
			SYNTAX Counter32
			MAX-ACCESS read-only
			STATUS current
			DESCRIPTION
				"The total number of PAUSE packets transmitted.
				
				 "
			::= { hwVdslEtherStatsEntry 15 }
		
		hwVdslEtherStatsTransmitFrames OBJECT-TYPE
			SYNTAX Counter32
			MAX-ACCESS read-only
			STATUS current
			DESCRIPTION
				"The total number of valid data frames that have been transferred
				over the transmit channel.
				
				 "
			::= { hwVdslEtherStatsEntry 16 }
		
		hwVdslEtherStatsReceiveFrames OBJECT-TYPE
			SYNTAX Counter32
			MAX-ACCESS read-only
			STATUS current
			DESCRIPTION
				"The total number of valid data frames that have been transferred
				over the receive channel.
				
				 "
			::= { hwVdslEtherStatsEntry 17 }
		
	
	END
