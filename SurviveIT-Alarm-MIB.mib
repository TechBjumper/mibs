SurviveIT-Alarm-MIB DEFINITIONS ::= BEGIN

	IMPORTS
		enterprises    FROM RFC1065-SMI
		OBJECT-TYPE    FROM RFC-1212
		TRAP-TYPE      FROM RFC-1215;
		
		cheyenne            OBJECT IDENTIFIER ::= { enterprises 46 }
		surviveIT             OBJECT IDENTIFIER ::= { cheyenne 884 }
        surviveITNLMRev       OBJECT IDENTIFIER ::= { surviveIT 1 }

-- *************************************************************************
-- SurviveIT (1.3.6.1.4.1.46.884)
-- **************************************************************************
surviveITNLMRevMajor OBJECT-TYPE
	SYNTAX INTEGER (0..65535)
	ACCESS read-only
	STATUS mandatory
	DESCRIPTION
		"The major revision level of the NLM (left of the decimal).
		Used for presence checking."
	::= { surviveITNLMRev 1 }

surviveITNLMRevMinor OBJECT-TYPE
	SYNTAX INTEGER (0..65535)
	ACCESS read-only
	STATUS mandatory
	DESCRIPTION
		"The minor revision level of the NLM (right of the decimal)."
	::= { surviveITNLMRev 2 }

surviveITParmsTrapEnable OBJECT-TYPE
	SYNTAX INTEGER (0..1)
	ACCESS read-write
	STATUS mandatory
	DESCRIPTION
		"Indicates whether agent should or should not send traps."
	::= { surviveIT 2 }

surviveITParmsPollTime OBJECT-TYPE
	SYNTAX INTEGER (60..2592000)
	ACCESS read-write
	STATUS mandatory
	DESCRIPTION
		"Seconds between checking for traps."
	::= { surviveIT 3 }

surviveITServerName OBJECT-TYPE
                SYNTAX OCTET STRING
                ACCESS read-only
                STATUS mandatory
                DESCRIPTION
                        "NetWare Server Which Generated Error"
                ::= {surviveIT 4}        
        
surviveITtrapdesc   OBJECT-TYPE
                SYNTAX OCTET STRING
                ACCESS read-only
                STATUS optional
                DESCRIPTION
                        "A description of a specific Cheyenne trap"
                ::= {surviveIT 5}        
        
-- *************************************************************************
-- traps
-- **************************************************************************
surviveITtrapHigh                TRAP-TYPE       
	        		ENTERPRISE	surviveIT
                                VARIABLES       {
                                                surviveITServerName,
                                                surviveITtrapdesc
                                                }
        			DESCRIPTION
                                        "surviveIT Critical Trap."
                                --#TYPE "surviveIT Critical"
                                --#SUMMARY "%s  surviveIT: %s "
                                --#ARGUMENTS {0,1}
                                --#SEVERITY CRITICAL
                                --#STATE   DEGRADED     
	        	        ::= 1
surviveITtrapMed                 TRAP-TYPE       
	        		ENTERPRISE	surviveIT
                                VARIABLES       {
                                                surviveITServerName,
                                                surviveITtrapdesc
                                                }
        			DESCRIPTION
                                        "surviveIT Minor Trap"
                                --#TYPE "surviveIT Warning"
                                --#SUMMARY "%s  surviveIT: %s "
                                --#ARGUMENTS {0,1}
                                --#SEVERITY MINOR
                                --#TIMEINDEX 1
                                --#STATE   OPERATIONAL     
	        	        ::= 2
surviveITtrapLow                 TRAP-TYPE       
	        		ENTERPRISE	surviveIT
                                VARIABLES       {
                                                surviveITServerName,
                                                surviveITtrapdesc
                                                }
        			DESCRIPTION
                                        "surviveIT Informational Trap"
                                --#TYPE "surviveIT Informational"
                                --#SUMMARY "%s  surviveIT: %s "
                                --#ARGUMENTS {0,1}
                                --#SEVERITY INFORMATIONAL
                                --#STATE   OPERATIONAL     
	        	        ::= 3
END
