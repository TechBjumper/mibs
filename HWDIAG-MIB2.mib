HWDIAG-MIB2 DEFINITIONS ::= BEGIN

IMPORTS
    enterprises, MODULE-IDENTITY, Integer32
        FROM SNMPv2-SMI;

hwdiag MODULE-IDENTITY
    LAST-UPDATED "0609201256Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        "Hardware Diagnostic Suite Agent launcher"
    ::= { base 1 }
base 	OBJECT IDENTIFIER ::= { agent 1 }

agent	OBJECT IDENTIFIER ::= { entdiag 1 }

entdiag	OBJECT IDENTIFIER ::= { prod 45 }

prod	OBJECT IDENTIFIER ::= { sun 2 }

sun	OBJECT IDENTIFIER ::= { enterprises 42 }


diagagent	OBJECT IDENTIFIER ::= { hwdiag 1 }

hdscom	OBJECT IDENTIFIER ::= { diagagent 1 }

RowStatus ::= TEXTUAL-CONVENTION
    STATUS       current
    DESCRIPTION
               "RowStatus"
    SYNTAX       INTEGER {
                     -- the following two values are states:
                     -- these values may be read or written
                     active(1),
                     notInService(2),

                     -- the following value is a state:
                     -- this value may be read, but not written
                     notReady(3),

                     -- the following three values are
                     -- actions: these values may be written,
                     --   but are never read
                     createAndGo(4),
                     createAndWait(5),
                     destroy(6)
                 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

startEDA OBJECT-TYPE
    SYNTAX      DisplayString
    MAX-ACCESS  read-write
    STATUS      current
    DESCRIPTION
                "Character string value"
    ::= { diagagent 2 }

hDpatternTable OBJECT-TYPE
    SYNTAX      SEQUENCE OF PatternEntry
    MAX-ACCESS  not-accessible
    STATUS      current
    DESCRIPTION
                "MIB tree branch"
    ::= { diagagent 3 }

patternEntry OBJECT-TYPE
    SYNTAX      PatternEntry
    MAX-ACCESS  not-accessible
    STATUS      current
    DESCRIPTION
                "MIB tree branch"
    INDEX  { inst }
    ::= { hDpatternTable 1 }

PatternEntry ::=
    SEQUENCE {
        rowstatus
            RowStatus,
        inst
            DisplayString,
        patternName
            DisplayString,
        patDesc
            DisplayString,
        hdtotal
            Integer32
    }

rowstatus OBJECT-TYPE
    SYNTAX      RowStatus
    MAX-ACCESS  read-write
    STATUS      current
    DESCRIPTION
                "The row status"
    ::= { patternEntry 1 }

inst OBJECT-TYPE
    SYNTAX      DisplayString
    MAX-ACCESS  read-only
    STATUS      current
    DESCRIPTION
                "The name of Instance"
    ::= { patternEntry 2 }

patternName OBJECT-TYPE
    SYNTAX      DisplayString
    MAX-ACCESS  read-write
    STATUS      current
    DESCRIPTION
                "The regular expression pattern"
    ::= { patternEntry 3 }

patDesc OBJECT-TYPE
    SYNTAX      DisplayString
    MAX-ACCESS  read-write
    STATUS      current
    DESCRIPTION
                "The pattern Descritption"
    ::= { patternEntry 4 }

hdtotal OBJECT-TYPE
    SYNTAX      Integer32
    MAX-ACCESS  read-write
    STATUS      current
    DESCRIPTION
                "The total number of matches in current file"
    ::= { patternEntry 5 }
END
