-- file automatically created


TELDAT-TRAP-ETH-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ethTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ETH event subsystem."
    REVISION "201401200930Z"
    DESCRIPTION "Initial implementation"
        ::= { telEventTraps 81 }


ethEventsGroup	OBJECT IDENTIFIER	::= { ethTrapsMIB 1 }

ethNotifications	OBJECT IDENTIFIER	::= { ethTrapsMIB 2 }
ethNotificationsPrefix	OBJECT IDENTIFIER	::= { ethNotifications 0 }

ethEventObjects1 OBJECT-IDENTITY
    STATUS current
    DESCRIPTION
        "Event ETH.1
        A broadcast packet was received with an unknown or unsupported Ethernet
        type field."
    ::= { ethEventsGroup 1 }

eth1-packet-type OBJECT-TYPE
    SYNTAX Integer32
    MAX-ACCESS accessible-for-notify
    STATUS current
    DESCRIPTION
        "Parameter 'packet-type' in event ETH.1"
    ::= { ethEventObjects1 1 }

eth1-source-Ethernet-address OBJECT-TYPE
    SYNTAX DisplayString
    MAX-ACCESS accessible-for-notify
    STATUS current
    DESCRIPTION
        "Parameter 'source-Ethernet-address' in event ETH.1"
    ::= { ethEventObjects1 2 }

eth1-destination-Ethernet-address OBJECT-TYPE
    SYNTAX DisplayString
    MAX-ACCESS accessible-for-notify
    STATUS current
    DESCRIPTION
        "Parameter 'destination-Ethernet-address' in event ETH.1"
    ::= { ethEventObjects1 3 }

eth1-interface OBJECT-TYPE
    SYNTAX DisplayString
    MAX-ACCESS accessible-for-notify
    STATUS current
    DESCRIPTION
        "Parameter 'interface' in event ETH.1"
    ::= { ethEventObjects1 4 }

ethEventObjects2 OBJECT-IDENTITY
    STATUS current
    DESCRIPTION
        "Event ETH.2
        A non-broadcast packet was received with an unknown or unsupported
        Ethernet type field."
    ::= { ethEventsGroup 2 }

eth2-packet-type OBJECT-TYPE
    SYNTAX Integer32
    MAX-ACCESS accessible-for-notify
    STATUS current
    DESCRIPTION
        "Parameter 'packet-type' in event ETH.2"
    ::= { ethEventObjects2 1 }

eth2-source-Ethernet-address OBJECT-TYPE
    SYNTAX DisplayString
    MAX-ACCESS accessible-for-notify
    STATUS current
    DESCRIPTION
        "Parameter 'source-Ethernet-address' in event ETH.2"
    ::= { ethEventObjects2 2 }

eth2-destination-Ethernet-address OBJECT-TYPE
    SYNTAX DisplayString
    MAX-ACCESS accessible-for-notify
    STATUS current
    DESCRIPTION
        "Parameter 'destination-Ethernet-address' in event ETH.2"
    ::= { ethEventObjects2 3 }

eth2-interface OBJECT-TYPE
    SYNTAX DisplayString
    MAX-ACCESS accessible-for-notify
    STATUS current
    DESCRIPTION
        "Parameter 'interface' in event ETH.2"
    ::= { ethEventObjects2 4 }

ethEventObjects3 OBJECT-IDENTITY
    STATUS current
    DESCRIPTION
        "Event ETH.3
        A broadcast packet was received with a type field that indicated 802.3
        but was shorter than data length claimed in the 802.3 header."
    ::= { ethEventsGroup 3 }

eth3-actual-length OBJECT-TYPE
    SYNTAX Integer32
    MAX-ACCESS accessible-for-notify
    STATUS current
    DESCRIPTION
        "Parameter 'actual-length' in event ETH.3"
    ::= { ethEventObjects3 1 }

eth3-claimed-length OBJECT-TYPE
    SYNTAX Integer32
    MAX-ACCESS accessible-for-notify
    STATUS current
    DESCRIPTION
        "Parameter 'claimed-length' in event ETH.3"
    ::= { ethEventObjects3 2 }

eth3-source-Ethernet-address OBJECT-TYPE
    SYNTAX DisplayString
    MAX-ACCESS accessible-for-notify
    STATUS current
    DESCRIPTION
        "Parameter 'source-Ethernet-address' in event ETH.3"
    ::= { ethEventObjects3 3 }

eth3-destination-Ethernet-address OBJECT-TYPE
    SYNTAX DisplayString
    MAX-ACCESS accessible-for-notify
    STATUS current
    DESCRIPTION
        "Parameter 'destination-Ethernet-address' in event ETH.3"
    ::= { ethEventObjects3 4 }

eth3-interface OBJECT-TYPE
    SYNTAX DisplayString
    MAX-ACCESS accessible-for-notify
    STATUS current
    DESCRIPTION
        "Parameter 'interface' in event ETH.3"
    ::= { ethEventObjects3 5 }

ethEventObjects4 OBJECT-IDENTITY
    STATUS current
    DESCRIPTION
        "Event ETH.4
        A non-broadcast packet was received with a type field that indicated
        802.3 but was shorter than data length claimed in the 802.3 header."
    ::= { ethEventsGroup 4 }

eth4-actual-length OBJECT-TYPE
    SYNTAX Integer32
    MAX-ACCESS accessible-for-notify
    STATUS current
    DESCRIPTION
        "Parameter 'actual-length' in event ETH.4"
    ::= { ethEventObjects4 1 }

eth4-claimed-length OBJECT-TYPE
    SYNTAX Integer32
    MAX-ACCESS accessible-for-notify
    STATUS current
    DESCRIPTION
        "Parameter 'claimed-length' in event ETH.4"
    ::= { ethEventObjects4 2 }

eth4-source-Ethernet-address OBJECT-TYPE
    SYNTAX DisplayString
    MAX-ACCESS accessible-for-notify
    STATUS current
    DESCRIPTION
        "Parameter 'source-Ethernet-address' in event ETH.4"
    ::= { ethEventObjects4 3 }

eth4-destination-Ethernet-address OBJECT-TYPE
    SYNTAX DisplayString
    MAX-ACCESS accessible-for-notify
    STATUS current
    DESCRIPTION
        "Parameter 'destination-Ethernet-address' in event ETH.4"
    ::= { ethEventObjects4 4 }

eth4-interface OBJECT-TYPE
    SYNTAX DisplayString
    MAX-ACCESS accessible-for-notify
    STATUS current
    DESCRIPTION
        "Parameter 'interface' in event ETH.4"
    ::= { ethEventObjects4 5 }

ethEventObjects5 OBJECT-IDENTITY
    STATUS current
    DESCRIPTION
        "Event ETH.5
        A DECnet packet was received with a length field that was larger than
        the actual length of the packet."
    ::= { ethEventsGroup 5 }

eth5-actual-length OBJECT-TYPE
    SYNTAX Integer32
    MAX-ACCESS accessible-for-notify
    STATUS current
    DESCRIPTION
        "Parameter 'actual-length' in event ETH.5"
    ::= { ethEventObjects5 1 }

eth5-claimed-length OBJECT-TYPE
    SYNTAX Integer32
    MAX-ACCESS accessible-for-notify
    STATUS current
    DESCRIPTION
        "Parameter 'claimed-length' in event ETH.5"
    ::= { ethEventObjects5 2 }

eth5-source-Ethernet-address OBJECT-TYPE
    SYNTAX DisplayString
    MAX-ACCESS accessible-for-notify
    STATUS current
    DESCRIPTION
        "Parameter 'source-Ethernet-address' in event ETH.5"
    ::= { ethEventObjects5 3 }

eth5-destination-Ethernet-address OBJECT-TYPE
    SYNTAX DisplayString
    MAX-ACCESS accessible-for-notify
    STATUS current
    DESCRIPTION
        "Parameter 'destination-Ethernet-address' in event ETH.5"
    ::= { ethEventObjects5 4 }

eth5-interface OBJECT-TYPE
    SYNTAX DisplayString
    MAX-ACCESS accessible-for-notify
    STATUS current
    DESCRIPTION
        "Parameter 'interface' in event ETH.5"
    ::= { ethEventObjects5 5 }

ethEventObjects6 OBJECT-IDENTITY
    STATUS current
    DESCRIPTION
        "Event ETH.6
        An ethernet packet was received with protocol identifier not supported.
        It will be discarded."
    ::= { ethEventsGroup 6 }

eth6-protocol OBJECT-TYPE
    SYNTAX DisplayString
    MAX-ACCESS accessible-for-notify
    STATUS current
    DESCRIPTION
        "Parameter 'protocol' in event ETH.6"
    ::= { ethEventObjects6 1 }

eth6-source-Ethernet-address OBJECT-TYPE
    SYNTAX DisplayString
    MAX-ACCESS accessible-for-notify
    STATUS current
    DESCRIPTION
        "Parameter 'source-Ethernet-address' in event ETH.6"
    ::= { ethEventObjects6 2 }

eth6-destination-Ethernet-address OBJECT-TYPE
    SYNTAX Integer32
    MAX-ACCESS accessible-for-notify
    STATUS current
    DESCRIPTION
        "Parameter 'destination-Ethernet-address' in event ETH.6"
    ::= { ethEventObjects6 3 }

eth6-interface OBJECT-TYPE
    SYNTAX DisplayString
    MAX-ACCESS accessible-for-notify
    STATUS current
    DESCRIPTION
        "Parameter 'interface' in event ETH.6"
    ::= { ethEventObjects6 4 }

ethEventObjects7 OBJECT-IDENTITY
    STATUS current
    DESCRIPTION
        "Event ETH.7
        A SNAP 802.3 packet was received with protocol identifier not supported.
        It will be discarded."
    ::= { ethEventsGroup 7 }

eth7-protocol OBJECT-TYPE
    SYNTAX DisplayString
    MAX-ACCESS accessible-for-notify
    STATUS current
    DESCRIPTION
        "Parameter 'protocol' in event ETH.7"
    ::= { ethEventObjects7 1 }

eth7-source-Ethernet-address OBJECT-TYPE
    SYNTAX DisplayString
    MAX-ACCESS accessible-for-notify
    STATUS current
    DESCRIPTION
        "Parameter 'source-Ethernet-address' in event ETH.7"
    ::= { ethEventObjects7 2 }

eth7-destination-Ethernet-address OBJECT-TYPE
    SYNTAX Integer32
    MAX-ACCESS accessible-for-notify
    STATUS current
    DESCRIPTION
        "Parameter 'destination-Ethernet-address' in event ETH.7"
    ::= { ethEventObjects7 3 }

eth7-interface OBJECT-TYPE
    SYNTAX DisplayString
    MAX-ACCESS accessible-for-notify
    STATUS current
    DESCRIPTION
        "Parameter 'interface' in event ETH.7"
    ::= { ethEventObjects7 4 }

ethEventObjects8 OBJECT-IDENTITY
    STATUS current
    DESCRIPTION
        "Event ETH.8
        An ethernet multicast packet was received and it was discarded because
        it not match registered multicast addresses on interface."
    ::= { ethEventsGroup 8 }

eth8-source-Ethernet-address OBJECT-TYPE
    SYNTAX DisplayString
    MAX-ACCESS accessible-for-notify
    STATUS current
    DESCRIPTION
        "Parameter 'source-Ethernet-address' in event ETH.8"
    ::= { ethEventObjects8 1 }

eth8-destination-Ethernet-address OBJECT-TYPE
    SYNTAX DisplayString
    MAX-ACCESS accessible-for-notify
    STATUS current
    DESCRIPTION
        "Parameter 'destination-Ethernet-address' in event ETH.8"
    ::= { ethEventObjects8 2 }

eth8-interface OBJECT-TYPE
    SYNTAX DisplayString
    MAX-ACCESS accessible-for-notify
    STATUS current
    DESCRIPTION
        "Parameter 'interface' in event ETH.8"
    ::= { ethEventObjects8 3 }

ethEventObjects9 OBJECT-IDENTITY
    STATUS current
    DESCRIPTION
        "Event ETH.9
        An ethernet unicast packet was received and it was discarded because
        it not match local unicast addresses."
    ::= { ethEventsGroup 9 }

eth9-source-Ethernet-address OBJECT-TYPE
    SYNTAX DisplayString
    MAX-ACCESS accessible-for-notify
    STATUS current
    DESCRIPTION
        "Parameter 'source-Ethernet-address' in event ETH.9"
    ::= { ethEventObjects9 1 }

eth9-destination-Ethernet-address OBJECT-TYPE
    SYNTAX DisplayString
    MAX-ACCESS accessible-for-notify
    STATUS current
    DESCRIPTION
        "Parameter 'destination-Ethernet-address' in event ETH.9"
    ::= { ethEventObjects9 2 }

eth9-interface OBJECT-TYPE
    SYNTAX DisplayString
    MAX-ACCESS accessible-for-notify
    STATUS current
    DESCRIPTION
        "Parameter 'interface' in event ETH.9"
    ::= { ethEventObjects9 3 }

ethEventObjects10 OBJECT-IDENTITY
    STATUS current
    DESCRIPTION
        "Event ETH.10
        An 802.2 LLC packet was received from the network with an inactive
        (unrecognized) DSAP."
    ::= { ethEventsGroup 10 }

eth10-DSAP OBJECT-TYPE
    SYNTAX Integer32
    MAX-ACCESS accessible-for-notify
    STATUS current
    DESCRIPTION
        "Parameter 'DSAP' in event ETH.10"
    ::= { ethEventObjects10 1 }

eth10-source-Ethernet-address OBJECT-TYPE
    SYNTAX DisplayString
    MAX-ACCESS accessible-for-notify
    STATUS current
    DESCRIPTION
        "Parameter 'source-Ethernet-address' in event ETH.10"
    ::= { ethEventObjects10 2 }

eth10-destination-Ethernet-address OBJECT-TYPE
    SYNTAX DisplayString
    MAX-ACCESS accessible-for-notify
    STATUS current
    DESCRIPTION
        "Parameter 'destination-Ethernet-address' in event ETH.10"
    ::= { ethEventObjects10 3 }

eth10-interface OBJECT-TYPE
    SYNTAX DisplayString
    MAX-ACCESS accessible-for-notify
    STATUS current
    DESCRIPTION
        "Parameter 'interface' in event ETH.10"
    ::= { ethEventObjects10 4 }

ethEventObjects11 OBJECT-IDENTITY
    STATUS current
    DESCRIPTION
        "Event ETH.11
        A packet was received from the network that had an LLC but was not a
        Type 1 LLC."
    ::= { ethEventsGroup 11 }

eth11-LLC-control-type OBJECT-TYPE
    SYNTAX Integer32
    MAX-ACCESS accessible-for-notify
    STATUS current
    DESCRIPTION
        "Parameter 'LLC-control-type' in event ETH.11"
    ::= { ethEventObjects11 1 }

eth11-interface OBJECT-TYPE
    SYNTAX DisplayString
    MAX-ACCESS accessible-for-notify
    STATUS current
    DESCRIPTION
        "Parameter 'interface' in event ETH.11"
    ::= { ethEventObjects11 2 }

ethEventObjects12 OBJECT-IDENTITY
    STATUS current
    DESCRIPTION
        "Event ETH.12
        An LLC response was received from the network."
    ::= { ethEventsGroup 12 }

eth12-LLC-SSAP OBJECT-TYPE
    SYNTAX Integer32
    MAX-ACCESS accessible-for-notify
    STATUS current
    DESCRIPTION
        "Parameter 'LLC-SSAP' in event ETH.12"
    ::= { ethEventObjects12 1 }

eth12-interface OBJECT-TYPE
    SYNTAX DisplayString
    MAX-ACCESS accessible-for-notify
    STATUS current
    DESCRIPTION
        "Parameter 'interface' in event ETH.12"
    ::= { ethEventObjects12 2 }

ethEventObjects13 OBJECT-IDENTITY
    STATUS current
    DESCRIPTION
        "Event ETH.13
        An LLC XID packet was received from the network."
    ::= { ethEventsGroup 13 }

eth13-LLC-SSAP OBJECT-TYPE
    SYNTAX Integer32
    MAX-ACCESS accessible-for-notify
    STATUS current
    DESCRIPTION
        "Parameter 'LLC-SSAP' in event ETH.13"
    ::= { ethEventObjects13 1 }

eth13-interface OBJECT-TYPE
    SYNTAX DisplayString
    MAX-ACCESS accessible-for-notify
    STATUS current
    DESCRIPTION
        "Parameter 'interface' in event ETH.13"
    ::= { ethEventObjects13 2 }

ethEventObjects14 OBJECT-IDENTITY
    STATUS current
    DESCRIPTION
        "Event ETH.14
        An LLC TEST packet was received from the network."
    ::= { ethEventsGroup 14 }

eth14-LLC-SSAP OBJECT-TYPE
    SYNTAX Integer32
    MAX-ACCESS accessible-for-notify
    STATUS current
    DESCRIPTION
        "Parameter 'LLC-SSAP' in event ETH.14"
    ::= { ethEventObjects14 1 }

eth14-interface OBJECT-TYPE
    SYNTAX DisplayString
    MAX-ACCESS accessible-for-notify
    STATUS current
    DESCRIPTION
        "Parameter 'interface' in event ETH.14"
    ::= { ethEventObjects14 2 }

ethEventObjects15 OBJECT-IDENTITY
    STATUS current
    DESCRIPTION
        "Event ETH.15
        A packet was received from the network that had an illegal control
        field or UI."
    ::= { ethEventsGroup 15 }

eth15-LLC-control-field OBJECT-TYPE
    SYNTAX Integer32
    MAX-ACCESS accessible-for-notify
    STATUS current
    DESCRIPTION
        "Parameter 'LLC-control-field' in event ETH.15"
    ::= { ethEventObjects15 1 }

eth15-interface OBJECT-TYPE
    SYNTAX DisplayString
    MAX-ACCESS accessible-for-notify
    STATUS current
    DESCRIPTION
        "Parameter 'interface' in event ETH.15"
    ::= { ethEventObjects15 2 }

ethEventObjects17 OBJECT-IDENTITY
    STATUS current
    DESCRIPTION
        "Event ETH.17
        An Ethernet Loopback Protocol (Configuration Testing Protocol) packet
        was received."
    ::= { ethEventsGroup 17 }

eth17-source-Ethernet-address OBJECT-TYPE
    SYNTAX DisplayString
    MAX-ACCESS accessible-for-notify
    STATUS current
    DESCRIPTION
        "Parameter 'source-Ethernet-address' in event ETH.17"
    ::= { ethEventObjects17 1 }

eth17-destination-Ethernet-address OBJECT-TYPE
    SYNTAX DisplayString
    MAX-ACCESS accessible-for-notify
    STATUS current
    DESCRIPTION
        "Parameter 'destination-Ethernet-address' in event ETH.17"
    ::= { ethEventObjects17 2 }

eth17-interface OBJECT-TYPE
    SYNTAX DisplayString
    MAX-ACCESS accessible-for-notify
    STATUS current
    DESCRIPTION
        "Parameter 'interface' in event ETH.17"
    ::= { ethEventObjects17 3 }

ethEventObjects18 OBJECT-IDENTITY
    STATUS current
    DESCRIPTION
        "Event ETH.18
        An Ethernet Loopback Protocol (Configuration Testing Protocol) packet
        had an odd skip-Count in the packet. It will be discarded."
    ::= { ethEventsGroup 18 }

eth18-count OBJECT-TYPE
    SYNTAX Integer32
    MAX-ACCESS accessible-for-notify
    STATUS current
    DESCRIPTION
        "Parameter 'count' in event ETH.18"
    ::= { ethEventObjects18 1 }

eth18-source-Ethernet-address OBJECT-TYPE
    SYNTAX DisplayString
    MAX-ACCESS accessible-for-notify
    STATUS current
    DESCRIPTION
        "Parameter 'source-Ethernet-address' in event ETH.18"
    ::= { ethEventObjects18 2 }

eth18-destination-Ethernet-address OBJECT-TYPE
    SYNTAX DisplayString
    MAX-ACCESS accessible-for-notify
    STATUS current
    DESCRIPTION
        "Parameter 'destination-Ethernet-address' in event ETH.18"
    ::= { ethEventObjects18 3 }

eth18-interface OBJECT-TYPE
    SYNTAX DisplayString
    MAX-ACCESS accessible-for-notify
    STATUS current
    DESCRIPTION
        "Parameter 'interface' in event ETH.18"
    ::= { ethEventObjects18 4 }

ethEventObjects19 OBJECT-IDENTITY
    STATUS current
    DESCRIPTION
        "Event ETH.19
        An Ethernet Loopback Protocol (Configuration Testing Protocol) packet
        did not have a function code of forward(2). It will be discarded."
    ::= { ethEventsGroup 19 }

eth19-function OBJECT-TYPE
    SYNTAX Integer32
    MAX-ACCESS accessible-for-notify
    STATUS current
    DESCRIPTION
        "Parameter 'function' in event ETH.19"
    ::= { ethEventObjects19 1 }

eth19-source-Ethernet-address OBJECT-TYPE
    SYNTAX DisplayString
    MAX-ACCESS accessible-for-notify
    STATUS current
    DESCRIPTION
        "Parameter 'source-Ethernet-address' in event ETH.19"
    ::= { ethEventObjects19 2 }

eth19-destination-Ethernet-address OBJECT-TYPE
    SYNTAX DisplayString
    MAX-ACCESS accessible-for-notify
    STATUS current
    DESCRIPTION
        "Parameter 'destination-Ethernet-address' in event ETH.19"
    ::= { ethEventObjects19 3 }

eth19-interface OBJECT-TYPE
    SYNTAX DisplayString
    MAX-ACCESS accessible-for-notify
    STATUS current
    DESCRIPTION
        "Parameter 'interface' in event ETH.19"
    ::= { ethEventObjects19 4 }

ethEventObjects20 OBJECT-IDENTITY
    STATUS current
    DESCRIPTION
        "Event ETH.20
        An Ethernet Loopback Protocol (Configuration Testing Protocol) packet
        has a forward address that is a multicast. It will be discarded."
    ::= { ethEventsGroup 20 }

eth20-forward-Ethernet-address OBJECT-TYPE
    SYNTAX DisplayString
    MAX-ACCESS accessible-for-notify
    STATUS current
    DESCRIPTION
        "Parameter 'forward-Ethernet-address' in event ETH.20"
    ::= { ethEventObjects20 1 }

eth20-source-Ethernet-address OBJECT-TYPE
    SYNTAX DisplayString
    MAX-ACCESS accessible-for-notify
    STATUS current
    DESCRIPTION
        "Parameter 'source-Ethernet-address' in event ETH.20"
    ::= { ethEventObjects20 2 }

eth20-destination-Ethernet-address OBJECT-TYPE
    SYNTAX DisplayString
    MAX-ACCESS accessible-for-notify
    STATUS current
    DESCRIPTION
        "Parameter 'destination-Ethernet-address' in event ETH.20"
    ::= { ethEventObjects20 3 }

eth20-interface OBJECT-TYPE
    SYNTAX DisplayString
    MAX-ACCESS accessible-for-notify
    STATUS current
    DESCRIPTION
        "Parameter 'interface' in event ETH.20"
    ::= { ethEventObjects20 4 }

ethEventObjects21 OBJECT-IDENTITY
    STATUS current
    DESCRIPTION
        "Event ETH.21
        An Ethernet Loopback Protocol (Configuration Testing Protocol) packet
        is being forwarded to the specified next hop."
    ::= { ethEventsGroup 21 }

eth21-source-Ethernet-address OBJECT-TYPE
    SYNTAX DisplayString
    MAX-ACCESS accessible-for-notify
    STATUS current
    DESCRIPTION
        "Parameter 'source-Ethernet-address' in event ETH.21"
    ::= { ethEventObjects21 1 }

eth21-destination-Ethernet-address OBJECT-TYPE
    SYNTAX DisplayString
    MAX-ACCESS accessible-for-notify
    STATUS current
    DESCRIPTION
        "Parameter 'destination-Ethernet-address' in event ETH.21"
    ::= { ethEventObjects21 2 }

eth21-interface OBJECT-TYPE
    SYNTAX DisplayString
    MAX-ACCESS accessible-for-notify
    STATUS current
    DESCRIPTION
        "Parameter 'interface' in event ETH.21"
    ::= { ethEventObjects21 3 }

ethEventObjects22 OBJECT-IDENTITY
    STATUS current
    DESCRIPTION
        "Event ETH.22
        An Ethernet Loopback Protocol (Configuration Testing Protocol) packet
        could not be forwarded to the specified address, for reason specified
        by code."
    ::= { ethEventsGroup 22 }

eth22-forward-Ethernet-address OBJECT-TYPE
    SYNTAX DisplayString
    MAX-ACCESS accessible-for-notify
    STATUS current
    DESCRIPTION
        "Parameter 'forward-Ethernet-address' in event ETH.22"
    ::= { ethEventObjects22 1 }

eth22-code OBJECT-TYPE
    SYNTAX Integer32
    MAX-ACCESS accessible-for-notify
    STATUS current
    DESCRIPTION
        "Parameter 'code' in event ETH.22"
    ::= { ethEventObjects22 2 }

eth22-interface OBJECT-TYPE
    SYNTAX DisplayString
    MAX-ACCESS accessible-for-notify
    STATUS current
    DESCRIPTION
        "Parameter 'interface' in event ETH.22"
    ::= { ethEventObjects22 3 }

ethEventObjects23 OBJECT-IDENTITY
    STATUS current
    DESCRIPTION
        "Event ETH.23
        An LLC response (XID or TEST) could not be transmitted to the specified
        address, for the reason specified by code."
    ::= { ethEventsGroup 23 }

eth23-destination-Ethernet-address OBJECT-TYPE
    SYNTAX DisplayString
    MAX-ACCESS accessible-for-notify
    STATUS current
    DESCRIPTION
        "Parameter 'destination-Ethernet-address' in event ETH.23"
    ::= { ethEventObjects23 1 }

eth23-code OBJECT-TYPE
    SYNTAX Integer32
    MAX-ACCESS accessible-for-notify
    STATUS current
    DESCRIPTION
        "Parameter 'code' in event ETH.23"
    ::= { ethEventObjects23 2 }

eth23-interface OBJECT-TYPE
    SYNTAX DisplayString
    MAX-ACCESS accessible-for-notify
    STATUS current
    DESCRIPTION
        "Parameter 'interface' in event ETH.23"
    ::= { ethEventObjects23 3 }

ethEventObjects24 OBJECT-IDENTITY
    STATUS current
    DESCRIPTION
        "Event ETH.24
        A DECnet MOP packet was received with a length field that was larger
        than the actual length of the packet."
    ::= { ethEventsGroup 24 }

eth24-actual-length OBJECT-TYPE
    SYNTAX Integer32
    MAX-ACCESS accessible-for-notify
    STATUS current
    DESCRIPTION
        "Parameter 'actual-length' in event ETH.24"
    ::= { ethEventObjects24 1 }

eth24-claimed-length OBJECT-TYPE
    SYNTAX Integer32
    MAX-ACCESS accessible-for-notify
    STATUS current
    DESCRIPTION
        "Parameter 'claimed-length' in event ETH.24"
    ::= { ethEventObjects24 2 }

eth24-source-Ethernet-address OBJECT-TYPE
    SYNTAX DisplayString
    MAX-ACCESS accessible-for-notify
    STATUS current
    DESCRIPTION
        "Parameter 'source-Ethernet-address' in event ETH.24"
    ::= { ethEventObjects24 3 }

eth24-destination-Ethernet-address OBJECT-TYPE
    SYNTAX DisplayString
    MAX-ACCESS accessible-for-notify
    STATUS current
    DESCRIPTION
        "Parameter 'destination-Ethernet-address' in event ETH.24"
    ::= { ethEventObjects24 4 }

eth24-interface OBJECT-TYPE
    SYNTAX DisplayString
    MAX-ACCESS accessible-for-notify
    STATUS current
    DESCRIPTION
        "Parameter 'interface' in event ETH.24"
    ::= { ethEventObjects24 5 }

ethEventObjects25 OBJECT-IDENTITY
    STATUS current
    DESCRIPTION
        "Event ETH.25
        An Ethernet Loopback Protocol (Configuration Testing Protocol) packet
        had askipCount in the packet that points to beyond the end of the
        packet. It will be discarded."
    ::= { ethEventsGroup 25 }

eth25-count OBJECT-TYPE
    SYNTAX Integer32
    MAX-ACCESS accessible-for-notify
    STATUS current
    DESCRIPTION
        "Parameter 'count' in event ETH.25"
    ::= { ethEventObjects25 1 }

eth25-source-Ethernet-address OBJECT-TYPE
    SYNTAX DisplayString
    MAX-ACCESS accessible-for-notify
    STATUS current
    DESCRIPTION
        "Parameter 'source-Ethernet-address' in event ETH.25"
    ::= { ethEventObjects25 2 }

eth25-destination-Ethernet-address OBJECT-TYPE
    SYNTAX DisplayString
    MAX-ACCESS accessible-for-notify
    STATUS current
    DESCRIPTION
        "Parameter 'destination-Ethernet-address' in event ETH.25"
    ::= { ethEventObjects25 3 }

eth25-interface OBJECT-TYPE
    SYNTAX DisplayString
    MAX-ACCESS accessible-for-notify
    STATUS current
    DESCRIPTION
        "Parameter 'interface' in event ETH.25"
    ::= { ethEventObjects25 4 }

ethEventObjects26 OBJECT-IDENTITY
    STATUS current
    DESCRIPTION
        "Event ETH.26
        A vlan frame has been received whose virtual lan id is not supported.
        Frame is dropped."
    ::= { ethEventsGroup 26 }

eth26-vlan-id OBJECT-TYPE
    SYNTAX Integer32
    MAX-ACCESS accessible-for-notify
    STATUS current
    DESCRIPTION
        "Parameter 'vlan-id' in event ETH.26"
    ::= { ethEventObjects26 1 }

eth26-interface OBJECT-TYPE
    SYNTAX DisplayString
    MAX-ACCESS accessible-for-notify
    STATUS current
    DESCRIPTION
        "Parameter 'interface' in event ETH.26"
    ::= { ethEventObjects26 2 }

ethEventObjects27 OBJECT-IDENTITY
    STATUS current
    DESCRIPTION
        "Event ETH.27
        A QinQ packet was received on a ethernet interface"
    ::= { ethEventsGroup 27 }

eth27-etype-length OBJECT-TYPE
    SYNTAX Integer32
    MAX-ACCESS accessible-for-notify
    STATUS current
    DESCRIPTION
        "Parameter 'etype-length' in event ETH.27"
    ::= { ethEventObjects27 1 }

eth27-vid OBJECT-TYPE
    SYNTAX Integer32
    MAX-ACCESS accessible-for-notify
    STATUS current
    DESCRIPTION
        "Parameter 'vid' in event ETH.27"
    ::= { ethEventObjects27 2 }

eth27-source-Ethernet-address OBJECT-TYPE
    SYNTAX DisplayString
    MAX-ACCESS accessible-for-notify
    STATUS current
    DESCRIPTION
        "Parameter 'source-Ethernet-address' in event ETH.27"
    ::= { ethEventObjects27 3 }

eth27-destination-Ethernet-address OBJECT-TYPE
    SYNTAX DisplayString
    MAX-ACCESS accessible-for-notify
    STATUS current
    DESCRIPTION
        "Parameter 'destination-Ethernet-address' in event ETH.27"
    ::= { ethEventObjects27 4 }

eth27-interface OBJECT-TYPE
    SYNTAX DisplayString
    MAX-ACCESS accessible-for-notify
    STATUS current
    DESCRIPTION
        "Parameter 'interface' in event ETH.27"
    ::= { ethEventObjects27 5 }

ethEventObjects41 OBJECT-IDENTITY
    STATUS current
    DESCRIPTION
        "Event ETH.41
        The selftest for the Ethernet Am79C960 card has reported an error during
        selftest. The phases are 'Inicialization' and 'Operational Test'."
    ::= { ethEventsGroup 41 }

eth41-selftest-phase OBJECT-TYPE
    SYNTAX DisplayString
    MAX-ACCESS accessible-for-notify
    STATUS current
    DESCRIPTION
        "Parameter 'selftest-phase' in event ETH.41"
    ::= { ethEventObjects41 1 }

eth41-error-condition OBJECT-TYPE
    SYNTAX DisplayString
    MAX-ACCESS accessible-for-notify
    STATUS current
    DESCRIPTION
        "Parameter 'error-condition' in event ETH.41"
    ::= { ethEventObjects41 2 }

eth41-interface OBJECT-TYPE
    SYNTAX DisplayString
    MAX-ACCESS accessible-for-notify
    STATUS current
    DESCRIPTION
        "Parameter 'interface' in event ETH.41"
    ::= { ethEventObjects41 3 }

ethEventObjects43 OBJECT-IDENTITY
    STATUS current
    DESCRIPTION
        "Event ETH.43
        The 82596 chip on the interface card has failed to clear the command
        field for this interface. The interface will be re-initialized."
    ::= { ethEventsGroup 43 }

eth43-interface OBJECT-TYPE
    SYNTAX DisplayString
    MAX-ACCESS accessible-for-notify
    STATUS current
    DESCRIPTION
        "Parameter 'interface' in event ETH.43"
    ::= { ethEventObjects43 1 }

ethEventObjects44 OBJECT-IDENTITY
    STATUS current
    DESCRIPTION
        "Event ETH.44
        An incorrect command field has been sent to the driver. The interface
        will be re-initialized."
    ::= { ethEventsGroup 44 }

eth44-command OBJECT-TYPE
    SYNTAX Integer32
    MAX-ACCESS accessible-for-notify
    STATUS current
    DESCRIPTION
        "Parameter 'command' in event ETH.44"
    ::= { ethEventObjects44 1 }

eth44-interface OBJECT-TYPE
    SYNTAX DisplayString
    MAX-ACCESS accessible-for-notify
    STATUS current
    DESCRIPTION
        "Parameter 'interface' in event ETH.44"
    ::= { ethEventObjects44 2 }

ethEventObjects45 OBJECT-IDENTITY
    STATUS current
    DESCRIPTION
        "Event ETH.45
        The selftest for the Ethernet card has reported an error during selftest.
        The phases are:
        'Reset board', 'Check reset done', 'Check reset delay',
        'Init SCB', 'Init SCB delay', 'Init SCB completion',
        'Read hardware address', 'Set bus throttle timers',
        'Internal loopback', 'Set hardware address', 'Enable receive',
        'Internal loopback (output)', 'Check internal loopback data',
        'External loopback', 'External loopback delay',
        'External loopback (output)', 'Check External loopback data',
        'Network loopback', 'Network loopback', Network loopback delay',
        'Network loopback (output)', 'Check network looback data',
        'Clear loopback' and 'Operational test'."
    ::= { ethEventsGroup 45 }

eth45-selftest-phase OBJECT-TYPE
    SYNTAX DisplayString
    MAX-ACCESS accessible-for-notify
    STATUS current
    DESCRIPTION
        "Parameter 'selftest-phase' in event ETH.45"
    ::= { ethEventObjects45 1 }

eth45-error-condition OBJECT-TYPE
    SYNTAX DisplayString
    MAX-ACCESS accessible-for-notify
    STATUS current
    DESCRIPTION
        "Parameter 'error-condition' in event ETH.45"
    ::= { ethEventObjects45 2 }

eth45-interface OBJECT-TYPE
    SYNTAX DisplayString
    MAX-ACCESS accessible-for-notify
    STATUS current
    DESCRIPTION
        "Parameter 'interface' in event ETH.45"
    ::= { ethEventObjects45 3 }

ethEventObjects46 OBJECT-IDENTITY
    STATUS current
    DESCRIPTION
        "Event ETH.46
        This message is generated when an IPX packet is received in a data-link
        encapsulation (frame) other than the one configured for IPX on this
        interface. The packet will be ignored. The received-encapsultaion are
        one of the 'ETHERNET-802.3','ETHERNET-II','ETHERNET-802.2', or
        'ETHERNET-SNAP'. ETHERNET-802.3 is also known as 'Novell', and
        ETHERNET-II is also known as 'Ethernet'."
    ::= { ethEventsGroup 46 }

eth46-received-encapsulation OBJECT-TYPE
    SYNTAX DisplayString
    MAX-ACCESS accessible-for-notify
    STATUS current
    DESCRIPTION
        "Parameter 'received-encapsulation' in event ETH.46"
    ::= { ethEventObjects46 1 }

eth46-configured-encapsulation OBJECT-TYPE
    SYNTAX DisplayString
    MAX-ACCESS accessible-for-notify
    STATUS current
    DESCRIPTION
        "Parameter 'configured-encapsulation' in event ETH.46"
    ::= { ethEventObjects46 2 }

eth46-interface OBJECT-TYPE
    SYNTAX DisplayString
    MAX-ACCESS accessible-for-notify
    STATUS current
    DESCRIPTION
        "Parameter 'interface' in event ETH.46"
    ::= { ethEventObjects46 3 }

ethEventObjects47 OBJECT-IDENTITY
    STATUS current
    DESCRIPTION
        "Event ETH.47
        The self-test for the SCC Ethernet port has reported an error during
        self-test. The phases are 'Reset port', 'Set media selection',
        'Set hardware address', 'Network loopback', 'Enable receive',
        'Network loopback (output)', 'Check network loopback data',
        'Clear loopback', 'Set multicast addresses' and 'Operational Test'."
    ::= { ethEventsGroup 47 }

eth47-selftest-phase OBJECT-TYPE
    SYNTAX DisplayString
    MAX-ACCESS accessible-for-notify
    STATUS current
    DESCRIPTION
        "Parameter 'selftest-phase' in event ETH.47"
    ::= { ethEventObjects47 1 }

eth47-error-condition OBJECT-TYPE
    SYNTAX DisplayString
    MAX-ACCESS accessible-for-notify
    STATUS current
    DESCRIPTION
        "Parameter 'error-condition' in event ETH.47"
    ::= { ethEventObjects47 2 }

eth47-interface OBJECT-TYPE
    SYNTAX DisplayString
    MAX-ACCESS accessible-for-notify
    STATUS current
    DESCRIPTION
        "Parameter 'interface' in event ETH.47"
    ::= { ethEventObjects47 3 }

ethEventObjects48 OBJECT-IDENTITY
    STATUS current
    DESCRIPTION
        "Event ETH.48
        A Ethernet frame was received. Current software does not support
        Ethernet interface. Frame will be discarded."
    ::= { ethEventsGroup 48 }

eth48-source-MAC-address OBJECT-TYPE
    SYNTAX DisplayString
    MAX-ACCESS accessible-for-notify
    STATUS current
    DESCRIPTION
        "Parameter 'source-MAC-address' in event ETH.48"
    ::= { ethEventObjects48 1 }

eth48-destination-MAC-address OBJECT-TYPE
    SYNTAX DisplayString
    MAX-ACCESS accessible-for-notify
    STATUS current
    DESCRIPTION
        "Parameter 'destination-MAC-address' in event ETH.48"
    ::= { ethEventObjects48 2 }

eth48-interface OBJECT-TYPE
    SYNTAX DisplayString
    MAX-ACCESS accessible-for-notify
    STATUS current
    DESCRIPTION
        "Parameter 'interface' in event ETH.48"
    ::= { ethEventObjects48 3 }

ethEventObjects49 OBJECT-IDENTITY
    STATUS current
    DESCRIPTION
        "Event ETH.49
        Error computing LAN interface MAC address due to wrong serial number."
    ::= { ethEventsGroup 49 }

eth49-interface OBJECT-TYPE
    SYNTAX DisplayString
    MAX-ACCESS accessible-for-notify
    STATUS current
    DESCRIPTION
        "Parameter 'interface' in event ETH.49"
    ::= { ethEventObjects49 1 }

ethEventObjects50 OBJECT-IDENTITY
    STATUS current
    DESCRIPTION
        "Event ETH.50
        Switch port up."
    ::= { ethEventsGroup 50 }

eth50-port OBJECT-TYPE
    SYNTAX Integer32
    MAX-ACCESS accessible-for-notify
    STATUS current
    DESCRIPTION
        "Parameter 'port' in event ETH.50"
    ::= { ethEventObjects50 1 }

eth50-speed OBJECT-TYPE
    SYNTAX Integer32
    MAX-ACCESS accessible-for-notify
    STATUS current
    DESCRIPTION
        "Parameter 'speed' in event ETH.50"
    ::= { ethEventObjects50 2 }

eth50-mode OBJECT-TYPE
    SYNTAX Integer32
    MAX-ACCESS accessible-for-notify
    STATUS current
    DESCRIPTION
        "Parameter 'mode' in event ETH.50"
    ::= { ethEventObjects50 3 }

eth50-ifcname OBJECT-TYPE
    SYNTAX DisplayString
    MAX-ACCESS accessible-for-notify
    STATUS current
    DESCRIPTION
        "Parameter 'ifcname' in event ETH.50"
    ::= { ethEventObjects50 4 }

ethEventObjects51 OBJECT-IDENTITY
    STATUS current
    DESCRIPTION
        "Event ETH.51
        Switch port down."
    ::= { ethEventsGroup 51 }

eth51-port OBJECT-TYPE
    SYNTAX Integer32
    MAX-ACCESS accessible-for-notify
    STATUS current
    DESCRIPTION
        "Parameter 'port' in event ETH.51"
    ::= { ethEventObjects51 1 }

eth51-ifcname OBJECT-TYPE
    SYNTAX DisplayString
    MAX-ACCESS accessible-for-notify
    STATUS current
    DESCRIPTION
        "Parameter 'ifcname' in event ETH.51"
    ::= { ethEventObjects51 2 }

ethEventObjects52 OBJECT-IDENTITY
    STATUS current
    DESCRIPTION
        "Event ETH.52
        POE port on."
    ::= { ethEventsGroup 52 }

eth52-port OBJECT-TYPE
    SYNTAX Integer32
    MAX-ACCESS accessible-for-notify
    STATUS current
    DESCRIPTION
        "Parameter 'port' in event ETH.52"
    ::= { ethEventObjects52 1 }

eth52-class-string OBJECT-TYPE
    SYNTAX DisplayString
    MAX-ACCESS accessible-for-notify
    STATUS current
    DESCRIPTION
        "Parameter 'class-string' in event ETH.52"
    ::= { ethEventObjects52 2 }

eth52-ifcname OBJECT-TYPE
    SYNTAX DisplayString
    MAX-ACCESS accessible-for-notify
    STATUS current
    DESCRIPTION
        "Parameter 'ifcname' in event ETH.52"
    ::= { ethEventObjects52 3 }

ethEventObjects53 OBJECT-IDENTITY
    STATUS current
    DESCRIPTION
        "Event ETH.53
        POE port off."
    ::= { ethEventsGroup 53 }

eth53-port OBJECT-TYPE
    SYNTAX Integer32
    MAX-ACCESS accessible-for-notify
    STATUS current
    DESCRIPTION
        "Parameter 'port' in event ETH.53"
    ::= { ethEventObjects53 1 }

eth53-ifcname OBJECT-TYPE
    SYNTAX DisplayString
    MAX-ACCESS accessible-for-notify
    STATUS current
    DESCRIPTION
        "Parameter 'ifcname' in event ETH.53"
    ::= { ethEventObjects53 2 }

ethEventObjects54 OBJECT-IDENTITY
    STATUS current
    DESCRIPTION
        "Event ETH.54
        POE port detection error."
    ::= { ethEventsGroup 54 }

eth54-port OBJECT-TYPE
    SYNTAX Integer32
    MAX-ACCESS accessible-for-notify
    STATUS current
    DESCRIPTION
        "Parameter 'port' in event ETH.54"
    ::= { ethEventObjects54 1 }

eth54-error-string OBJECT-TYPE
    SYNTAX DisplayString
    MAX-ACCESS accessible-for-notify
    STATUS current
    DESCRIPTION
        "Parameter 'error-string' in event ETH.54"
    ::= { ethEventObjects54 2 }

eth54-ifcname OBJECT-TYPE
    SYNTAX DisplayString
    MAX-ACCESS accessible-for-notify
    STATUS current
    DESCRIPTION
        "Parameter 'ifcname' in event ETH.54"
    ::= { ethEventObjects54 3 }


ethNotification1 NOTIFICATION-TYPE
    OBJECTS { 
              eth1-packet-type, 
              eth1-source-Ethernet-address,
              eth1-destination-Ethernet-address,
              eth1-interface 
            }
    STATUS current
    DESCRIPTION
        "Notification of Event ETH.1

        Message: 'broadcast packet received with unknown Ethernet type $1 from host $2 to $3 interface $4'

        Parameters list:
              $1: eth1-packet-type
              $2: eth1-source-Ethernet-address
              $3: eth1-destination-Ethernet-address
              $4: eth1-interface

        A broadcast packet was received with an unknown or unsupported Ethernet
        type field."
    ::= { ethNotificationsPrefix 1 }

ethNotification2 NOTIFICATION-TYPE
    OBJECTS { 
              eth2-packet-type, 
              eth2-source-Ethernet-address,
              eth2-destination-Ethernet-address,
              eth2-interface 
            }
    STATUS current
    DESCRIPTION
        "Notification of Event ETH.2

        Message: 'packet received with unknown Ethernet type field $1 from host $2 to $3 interface $4'

        Parameters list:
              $1: eth2-packet-type
              $2: eth2-source-Ethernet-address
              $3: eth2-destination-Ethernet-address
              $4: eth2-interface

        A non-broadcast packet was received with an unknown or unsupported
        Ethernet type field."
    ::= { ethNotificationsPrefix 2 }

ethNotification3 NOTIFICATION-TYPE
    OBJECTS { 
              eth3-actual-length, 
              eth3-claimed-length,
              eth3-source-Ethernet-address,
              eth3-destination-Ethernet-address,
              eth3-interface 
            }
    STATUS current
    DESCRIPTION
        "Notification of Event ETH.3

        Message: 'broadcast packet received with a bad 802.3 length field actual $1 claimed $2 from $3 to $4 interface $5'

        Parameters list:
              $1: eth3-actual-length
              $2: eth3-claimed-length
              $3: eth3-source-Ethernet-address
              $4: eth3-destination-Ethernet-address
              $5: eth3-interface

        A broadcast packet was received with a type field that indicated 802.3
        but was shorter than data length claimed in the 802.3 header."
    ::= { ethNotificationsPrefix 3 }

ethNotification4 NOTIFICATION-TYPE
    OBJECTS { 
              eth4-actual-length, 
              eth4-claimed-length,
              eth4-source-Ethernet-address,
              eth4-destination-Ethernet-address,
              eth4-interface 
            }
    STATUS current
    DESCRIPTION
        "Notification of Event ETH.4

        Message: 'packet received with a bad 802.3 length field actual $1 claimed $2 from $3 to $4 interface $5'

        Parameters list:
              $1: eth4-actual-length
              $2: eth4-claimed-length
              $3: eth4-source-Ethernet-address
              $4: eth4-destination-Ethernet-address
              $5: eth4-interface

        A non-broadcast packet was received with a type field that indicated
        802.3 but was shorter than data length claimed in the 802.3 header."
    ::= { ethNotificationsPrefix 4 }

ethNotification5 NOTIFICATION-TYPE
    OBJECTS { 
              eth5-actual-length, 
              eth5-claimed-length,
              eth5-source-Ethernet-address,
              eth5-destination-Ethernet-address,
              eth5-interface 
            }
    STATUS current
    DESCRIPTION
        "Notification of Event ETH.5

        Message: 'DECnet packet received with a bad length actual $1 claimed $2 from $3 to $4 interface $5'

        Parameters list:
              $1: eth5-actual-length
              $2: eth5-claimed-length
              $3: eth5-source-Ethernet-address
              $4: eth5-destination-Ethernet-address
              $5: eth5-interface

        A DECnet packet was received with a length field that was larger than
        the actual length of the packet."
    ::= { ethNotificationsPrefix 5 }

ethNotification6 NOTIFICATION-TYPE
    OBJECTS { 
              eth6-protocol, 
              eth6-source-Ethernet-address,
              eth6-destination-Ethernet-address,
              eth6-interface 
            }
    STATUS current
    DESCRIPTION
        "Notification of Event ETH.6

        Message: 'Ethernet packet received from $1 to $2 with protocol $3 not supported.Frame is discarded interface $4'

        Parameters list:
              $1: eth6-protocol
              $2: eth6-source-Ethernet-address
              $3: eth6-destination-Ethernet-address
              $4: eth6-interface

        An ethernet packet was received with protocol identifier not supported.
        It will be discarded."
    ::= { ethNotificationsPrefix 6 }

ethNotification7 NOTIFICATION-TYPE
    OBJECTS { 
              eth7-protocol, 
              eth7-source-Ethernet-address,
              eth7-destination-Ethernet-address,
              eth7-interface 
            }
    STATUS current
    DESCRIPTION
        "Notification of Event ETH.7

        Message: 'SNAP 802.3 packet received from $1 to $2 with protocol $3 not supported.Frame is discarded interface $4'

        Parameters list:
              $1: eth7-protocol
              $2: eth7-source-Ethernet-address
              $3: eth7-destination-Ethernet-address
              $4: eth7-interface

        A SNAP 802.3 packet was received with protocol identifier not supported.
        It will be discarded."
    ::= { ethNotificationsPrefix 7 }

ethNotification8 NOTIFICATION-TYPE
    OBJECTS { 
              eth8-source-Ethernet-address, 
              eth8-destination-Ethernet-address,
              eth8-interface 
            }
    STATUS current
    DESCRIPTION
        "Notification of Event ETH.8

        Message: 'Ethernet multicast packet received from $1 to $2 is filtered interface $3'

        Parameters list:
              $1: eth8-source-Ethernet-address
              $2: eth8-destination-Ethernet-address
              $3: eth8-interface

        An ethernet multicast packet was received and it was discarded because
        it not match registered multicast addresses on interface."
    ::= { ethNotificationsPrefix 8 }

ethNotification9 NOTIFICATION-TYPE
    OBJECTS { 
              eth9-source-Ethernet-address, 
              eth9-destination-Ethernet-address,
              eth9-interface 
            }
    STATUS current
    DESCRIPTION
        "Notification of Event ETH.9

        Message: 'Ethernet unicast packet received from $1 to $2 is filtered interface $3'

        Parameters list:
              $1: eth9-source-Ethernet-address
              $2: eth9-destination-Ethernet-address
              $3: eth9-interface

        An ethernet unicast packet was received and it was discarded because
        it not match local unicast addresses."
    ::= { ethNotificationsPrefix 9 }

ethNotification10 NOTIFICATION-TYPE
    OBJECTS { 
              eth10-DSAP, 
              eth10-source-Ethernet-address,
              eth10-destination-Ethernet-address,
              eth10-interface 
            }
    STATUS current
    DESCRIPTION
        "Notification of Event ETH.10

        Message: '802.2 LLC packet received with unknown DSAP $1 from host $2 to $3 interface $4'

        Parameters list:
              $1: eth10-DSAP
              $2: eth10-source-Ethernet-address
              $3: eth10-destination-Ethernet-address
              $4: eth10-interface

        An 802.2 LLC packet was received from the network with an inactive
        (unrecognized) DSAP."
    ::= { ethNotificationsPrefix 10 }

ethNotification11 NOTIFICATION-TYPE
    OBJECTS { 
              eth11-LLC-control-type, 
              eth11-interface 
            }
    STATUS current
    DESCRIPTION
        "Notification of Event ETH.11

        Message: '802.2 LLC packet received, not Type 1 $1 interface $2'

        Parameters list:
              $1: eth11-LLC-control-type
              $2: eth11-interface

        A packet was received from the network that had an LLC but was not a
        Type 1 LLC."
    ::= { ethNotificationsPrefix 11 }

ethNotification12 NOTIFICATION-TYPE
    OBJECTS { 
              eth12-LLC-SSAP, 
              eth12-interface 
            }
    STATUS current
    DESCRIPTION
        "Notification of Event ETH.12

        Message: 'LLC RESPONSE packet received $1 interface $2'

        Parameters list:
              $1: eth12-LLC-SSAP
              $2: eth12-interface

        An LLC response was received from the network."
    ::= { ethNotificationsPrefix 12 }

ethNotification13 NOTIFICATION-TYPE
    OBJECTS { 
              eth13-LLC-SSAP, 
              eth13-interface 
            }
    STATUS current
    DESCRIPTION
        "Notification of Event ETH.13

        Message: 'LLC XID packet received $1 interface $2'

        Parameters list:
              $1: eth13-LLC-SSAP
              $2: eth13-interface

        An LLC XID packet was received from the network."
    ::= { ethNotificationsPrefix 13 }

ethNotification14 NOTIFICATION-TYPE
    OBJECTS { 
              eth14-LLC-SSAP, 
              eth14-interface 
            }
    STATUS current
    DESCRIPTION
        "Notification of Event ETH.14

        Message: 'LLC TEST packet received $1 interface $2'

        Parameters list:
              $1: eth14-LLC-SSAP
              $2: eth14-interface

        An LLC TEST packet was received from the network."
    ::= { ethNotificationsPrefix 14 }

ethNotification15 NOTIFICATION-TYPE
    OBJECTS { 
              eth15-LLC-control-field, 
              eth15-interface 
            }
    STATUS current
    DESCRIPTION
        "Notification of Event ETH.15

        Message: 'packet received with unrecognized control field $1 interface $2'

        Parameters list:
              $1: eth15-LLC-control-field
              $2: eth15-interface

        A packet was received from the network that had an illegal control
        field or UI."
    ::= { ethNotificationsPrefix 15 }

ethNotification16 NOTIFICATION-TYPE
    STATUS current
    DESCRIPTION
        "Notification of Event ETH.16

        Message: '----'

        Reserved for possible future use."
    ::= { ethNotificationsPrefix 16 }

ethNotification17 NOTIFICATION-TYPE
    OBJECTS { 
              eth17-source-Ethernet-address, 
              eth17-destination-Ethernet-address,
              eth17-interface 
            }
    STATUS current
    DESCRIPTION
        "Notification of Event ETH.17

        Message: 'Loopback Protocol frame received from $1 to $2, interface $3'

        Parameters list:
              $1: eth17-source-Ethernet-address
              $2: eth17-destination-Ethernet-address
              $3: eth17-interface

        An Ethernet Loopback Protocol (Configuration Testing Protocol) packet
        was received."
    ::= { ethNotificationsPrefix 17 }

ethNotification18 NOTIFICATION-TYPE
    OBJECTS { 
              eth18-count, 
              eth18-source-Ethernet-address,
              eth18-destination-Ethernet-address,
              eth18-interface 
            }
    STATUS current
    DESCRIPTION
        "Notification of Event ETH.18

        Message: 'Loopback Protocol, odd skipCount $1 from $2 to $3, interface $4'

        Parameters list:
              $1: eth18-count
              $2: eth18-source-Ethernet-address
              $3: eth18-destination-Ethernet-address
              $4: eth18-interface

        An Ethernet Loopback Protocol (Configuration Testing Protocol) packet
        had an odd skip-Count in the packet. It will be discarded."
    ::= { ethNotificationsPrefix 18 }

ethNotification19 NOTIFICATION-TYPE
    OBJECTS { 
              eth19-function, 
              eth19-source-Ethernet-address,
              eth19-destination-Ethernet-address,
              eth19-interface 
            }
    STATUS current
    DESCRIPTION
        "Notification of Event ETH.19

        Message: 'Loopback Protocol, function $1 not Forward Data from $2 to $3, interface $4'

        Parameters list:
              $1: eth19-function
              $2: eth19-source-Ethernet-address
              $3: eth19-destination-Ethernet-address
              $4: eth19-interface

        An Ethernet Loopback Protocol (Configuration Testing Protocol) packet
        did not have a function code of forward(2). It will be discarded."
    ::= { ethNotificationsPrefix 19 }

ethNotification20 NOTIFICATION-TYPE
    OBJECTS { 
              eth20-forward-Ethernet-address, 
              eth20-source-Ethernet-address,
              eth20-destination-Ethernet-address,
              eth20-interface 
            }
    STATUS current
    DESCRIPTION
        "Notification of Event ETH.20

        Message: 'Loopback Protocol, multicast forward address $1 from $2 to $3, interface $4'

        Parameters list:
              $1: eth20-forward-Ethernet-address
              $2: eth20-source-Ethernet-address
              $3: eth20-destination-Ethernet-address
              $4: eth20-interface

        An Ethernet Loopback Protocol (Configuration Testing Protocol) packet
        has a forward address that is a multicast. It will be discarded."
    ::= { ethNotificationsPrefix 20 }

ethNotification21 NOTIFICATION-TYPE
    OBJECTS { 
              eth21-source-Ethernet-address, 
              eth21-destination-Ethernet-address,
              eth21-interface 
            }
    STATUS current
    DESCRIPTION
        "Notification of Event ETH.21

        Message: 'Loopback Protocol, forwarding from $1 to $2, interface $3'

        Parameters list:
              $1: eth21-source-Ethernet-address
              $2: eth21-destination-Ethernet-address
              $3: eth21-interface

        An Ethernet Loopback Protocol (Configuration Testing Protocol) packet
        is being forwarded to the specified next hop."
    ::= { ethNotificationsPrefix 21 }

ethNotification22 NOTIFICATION-TYPE
    OBJECTS { 
              eth22-forward-Ethernet-address, 
              eth22-code,
              eth22-interface 
            }
    STATUS current
    DESCRIPTION
        "Notification of Event ETH.22

        Message: 'Loopback Protocol, forward to $1 discarded, for reason $2, interface $3'

        Parameters list:
              $1: eth22-forward-Ethernet-address
              $2: eth22-code
              $3: eth22-interface

        An Ethernet Loopback Protocol (Configuration Testing Protocol) packet
        could not be forwarded to the specified address, for reason specified
        by code."
    ::= { ethNotificationsPrefix 22 }

ethNotification23 NOTIFICATION-TYPE
    OBJECTS { 
              eth23-destination-Ethernet-address, 
              eth23-code,
              eth23-interface 
            }
    STATUS current
    DESCRIPTION
        "Notification of Event ETH.23

        Message: 'LLC response to $1 discarded, for reason $2, interface $3'

        Parameters list:
              $1: eth23-destination-Ethernet-address
              $2: eth23-code
              $3: eth23-interface

        An LLC response (XID or TEST) could not be transmitted to the specified
        address, for the reason specified by code."
    ::= { ethNotificationsPrefix 23 }

ethNotification24 NOTIFICATION-TYPE
    OBJECTS { 
              eth24-actual-length, 
              eth24-claimed-length,
              eth24-source-Ethernet-address,
              eth24-destination-Ethernet-address,
              eth24-interface 
            }
    STATUS current
    DESCRIPTION
        "Notification of Event ETH.24

        Message: 'DECnet MOP packet received with a bad length actual $1 claimed $2 from $3 to $4 interface $5'

        Parameters list:
              $1: eth24-actual-length
              $2: eth24-claimed-length
              $3: eth24-source-Ethernet-address
              $4: eth24-destination-Ethernet-address
              $5: eth24-interface

        A DECnet MOP packet was received with a length field that was larger
        than the actual length of the packet."
    ::= { ethNotificationsPrefix 24 }

ethNotification25 NOTIFICATION-TYPE
    OBJECTS { 
              eth25-count, 
              eth25-source-Ethernet-address,
              eth25-destination-Ethernet-address,
              eth25-interface 
            }
    STATUS current
    DESCRIPTION
        "Notification of Event ETH.25

        Message: 'Loopback Protocol, bad skipCount $1 from $2 to $3, interface $4'

        Parameters list:
              $1: eth25-count
              $2: eth25-source-Ethernet-address
              $3: eth25-destination-Ethernet-address
              $4: eth25-interface

        An Ethernet Loopback Protocol (Configuration Testing Protocol) packet
        had askipCount in the packet that points to beyond the end of the
        packet. It will be discarded."
    ::= { ethNotificationsPrefix 25 }

ethNotification26 NOTIFICATION-TYPE
    OBJECTS { 
              eth26-vlan-id, 
              eth26-interface 
            }
    STATUS current
    DESCRIPTION
        "Notification of Event ETH.26

        Message: 'VLAN vid $1 not supported. Frame discarded, interface $2'

        Parameters list:
              $1: eth26-vlan-id
              $2: eth26-interface

        A vlan frame has been received whose virtual lan id is not supported.
        Frame is dropped."
    ::= { ethNotificationsPrefix 26 }

ethNotification27 NOTIFICATION-TYPE
    OBJECTS { 
              eth27-etype-length, 
              eth27-vid,
              eth27-source-Ethernet-address,
              eth27-destination-Ethernet-address,
              eth27-interface 
            }
    STATUS current
    DESCRIPTION
        "Notification of Event ETH.27

        Message: 'QinQ packet received etype/length field $1 vid $2 from $3 to $4 interface $5'

        Parameters list:
              $1: eth27-etype-length
              $2: eth27-vid
              $3: eth27-source-Ethernet-address
              $4: eth27-destination-Ethernet-address
              $5: eth27-interface

        A QinQ packet was received on a ethernet interface"
    ::= { ethNotificationsPrefix 27 }

ethNotification28 NOTIFICATION-TYPE
    STATUS current
    DESCRIPTION
        "Notification of Event ETH.28

        Message: '----'

        Reserved for possible future use."
    ::= { ethNotificationsPrefix 28 }

ethNotification29 NOTIFICATION-TYPE
    STATUS current
    DESCRIPTION
        "Notification of Event ETH.29

        Message: '----'

        Reserved for possible future use."
    ::= { ethNotificationsPrefix 29 }

ethNotification30 NOTIFICATION-TYPE
    STATUS current
    DESCRIPTION
        "Notification of Event ETH.30

        Message: '----'

        Reserved for possible future use."
    ::= { ethNotificationsPrefix 30 }

ethNotification31 NOTIFICATION-TYPE
    STATUS current
    DESCRIPTION
        "Notification of Event ETH.31

        Message: '----'

        Reserved for possible future use."
    ::= { ethNotificationsPrefix 31 }

ethNotification32 NOTIFICATION-TYPE
    STATUS current
    DESCRIPTION
        "Notification of Event ETH.32

        Message: '----'

        Reserved for possible future use."
    ::= { ethNotificationsPrefix 32 }

ethNotification33 NOTIFICATION-TYPE
    STATUS current
    DESCRIPTION
        "Notification of Event ETH.33

        Message: '----'

        Reserved for possible future use."
    ::= { ethNotificationsPrefix 33 }

ethNotification34 NOTIFICATION-TYPE
    STATUS current
    DESCRIPTION
        "Notification of Event ETH.34

        Message: '----'

        Reserved for possible future use."
    ::= { ethNotificationsPrefix 34 }

ethNotification35 NOTIFICATION-TYPE
    STATUS current
    DESCRIPTION
        "Notification of Event ETH.35

        Message: '----'

        Reserved for possible future use."
    ::= { ethNotificationsPrefix 35 }

ethNotification36 NOTIFICATION-TYPE
    STATUS current
    DESCRIPTION
        "Notification of Event ETH.36

        Message: '----'

        Reserved for possible future use."
    ::= { ethNotificationsPrefix 36 }

ethNotification37 NOTIFICATION-TYPE
    STATUS current
    DESCRIPTION
        "Notification of Event ETH.37

        Message: '----'

        Reserved for possible future use."
    ::= { ethNotificationsPrefix 37 }

ethNotification38 NOTIFICATION-TYPE
    STATUS current
    DESCRIPTION
        "Notification of Event ETH.38

        Message: '----'

        Reserved for possible future use."
    ::= { ethNotificationsPrefix 38 }

ethNotification39 NOTIFICATION-TYPE
    STATUS current
    DESCRIPTION
        "Notification of Event ETH.39

        Message: '----'

        Reserved for possible future use."
    ::= { ethNotificationsPrefix 39 }

ethNotification40 NOTIFICATION-TYPE
    STATUS current
    DESCRIPTION
        "Notification of Event ETH.40

        Message: '----'

        Reserved for possible future use."
    ::= { ethNotificationsPrefix 40 }

ethNotification41 NOTIFICATION-TYPE
    OBJECTS { 
              eth41-selftest-phase, 
              eth41-error-condition,
              eth41-interface 
            }
    STATUS current
    DESCRIPTION
        "Notification of Event ETH.41

        Message: 'Ethernet self-test phase $1 failed: $2 interface $3'

        Parameters list:
              $1: eth41-selftest-phase
              $2: eth41-error-condition
              $3: eth41-interface

        The selftest for the Ethernet Am79C960 card has reported an error during
        selftest. The phases are 'Inicialization' and 'Operational Test'."
    ::= { ethNotificationsPrefix 41 }

ethNotification42 NOTIFICATION-TYPE
    STATUS current
    DESCRIPTION
        "Notification of Event ETH.42

        Message: 'Unable to get buf for ethernet packet.'

        A buffer to set an Ethernet, or to copy an Ethernet packet couldn't
        be gotten because a buffer shortage."
    ::= { ethNotificationsPrefix 42 }

ethNotification43 NOTIFICATION-TYPE
    OBJECTS { 
              eth43-interface 
            }
    STATUS current
    DESCRIPTION
        "Notification of Event ETH.43

        Message: 'CMD596 Command Timeout. Interface $1 being restarted.'

        Parameters list:
              $1: eth43-interface

        The 82596 chip on the interface card has failed to clear the command
        field for this interface. The interface will be re-initialized."
    ::= { ethNotificationsPrefix 43 }

ethNotification44 NOTIFICATION-TYPE
    OBJECTS { 
              eth44-command, 
              eth44-interface 
            }
    STATUS current
    DESCRIPTION
        "Notification of Event ETH.44

        Message: 'I5IOCTL Bad Command $1. Interface $2 being restarted.'

        Parameters list:
              $1: eth44-command
              $2: eth44-interface

        An incorrect command field has been sent to the driver. The interface
        will be re-initialized."
    ::= { ethNotificationsPrefix 44 }

ethNotification45 NOTIFICATION-TYPE
    OBJECTS { 
              eth45-selftest-phase, 
              eth45-error-condition,
              eth45-interface 
            }
    STATUS current
    DESCRIPTION
        "Notification of Event ETH.45

        Message: 'Ethernet self-test phase $1 failed: $2 interface $3'

        Parameters list:
              $1: eth45-selftest-phase
              $2: eth45-error-condition
              $3: eth45-interface

        The selftest for the Ethernet card has reported an error during selftest.
        The phases are:
        'Reset board', 'Check reset done', 'Check reset delay',
        'Init SCB', 'Init SCB delay', 'Init SCB completion',
        'Read hardware address', 'Set bus throttle timers',
        'Internal loopback', 'Set hardware address', 'Enable receive',
        'Internal loopback (output)', 'Check internal loopback data',
        'External loopback', 'External loopback delay',
        'External loopback (output)', 'Check External loopback data',
        'Network loopback', 'Network loopback', Network loopback delay',
        'Network loopback (output)', 'Check network looback data',
        'Clear loopback' and 'Operational test'."
    ::= { ethNotificationsPrefix 45 }

ethNotification46 NOTIFICATION-TYPE
    OBJECTS { 
              eth46-received-encapsulation, 
              eth46-configured-encapsulation,
              eth46-interface 
            }
    STATUS current
    DESCRIPTION
        "Notification of Event ETH.46

        Message: 'IPX pkt in $1 encapsulation ignored, using encapsulation $2 on interface $3'

        Parameters list:
              $1: eth46-received-encapsulation
              $2: eth46-configured-encapsulation
              $3: eth46-interface

        This message is generated when an IPX packet is received in a data-link
        encapsulation (frame) other than the one configured for IPX on this
        interface. The packet will be ignored. The received-encapsultaion are
        one of the 'ETHERNET-802.3','ETHERNET-II','ETHERNET-802.2', or
        'ETHERNET-SNAP'. ETHERNET-802.3 is also known as 'Novell', and
        ETHERNET-II is also known as 'Ethernet'."
    ::= { ethNotificationsPrefix 46 }

ethNotification47 NOTIFICATION-TYPE
    OBJECTS { 
              eth47-selftest-phase, 
              eth47-error-condition,
              eth47-interface 
            }
    STATUS current
    DESCRIPTION
        "Notification of Event ETH.47

        Message: 'Ethernet port self-test phase $1 failed: $2 interface $3'

        Parameters list:
              $1: eth47-selftest-phase
              $2: eth47-error-condition
              $3: eth47-interface

        The self-test for the SCC Ethernet port has reported an error during
        self-test. The phases are 'Reset port', 'Set media selection',
        'Set hardware address', 'Network loopback', 'Enable receive',
        'Network loopback (output)', 'Check network loopback data',
        'Clear loopback', 'Set multicast addresses' and 'Operational Test'."
    ::= { ethNotificationsPrefix 47 }

ethNotification48 NOTIFICATION-TYPE
    OBJECTS { 
              eth48-source-MAC-address, 
              eth48-destination-MAC-address,
              eth48-interface 
            }
    STATUS current
    DESCRIPTION
        "Notification of Event ETH.48

        Message: 'Received frame from $1 to $2. Ethernet is not supported so frame is discarded interface $3'

        Parameters list:
              $1: eth48-source-MAC-address
              $2: eth48-destination-MAC-address
              $3: eth48-interface

        A Ethernet frame was received. Current software does not support
        Ethernet interface. Frame will be discarded."
    ::= { ethNotificationsPrefix 48 }

ethNotification49 NOTIFICATION-TYPE
    OBJECTS { 
              eth49-interface 
            }
    STATUS current
    DESCRIPTION
        "Notification of Event ETH.49

        Message: 'Error computing MAC address. Default MAC address is taken interface $1'

        Parameters list:
              $1: eth49-interface

        Error computing LAN interface MAC address due to wrong serial number."
    ::= { ethNotificationsPrefix 49 }

ethNotification50 NOTIFICATION-TYPE
    OBJECTS { 
              eth50-port, 
              eth50-speed,
              eth50-mode,
              eth50-ifcname 
            }
    STATUS current
    DESCRIPTION
        "Notification of Event ETH.50

        Message: 'port $1 up, speed=$2, mode=$3, intf $4'

        Parameters list:
              $1: eth50-port
              $2: eth50-speed
              $3: eth50-mode
              $4: eth50-ifcname

        Switch port up."
    ::= { ethNotificationsPrefix 50 }

ethNotification51 NOTIFICATION-TYPE
    OBJECTS { 
              eth51-port, 
              eth51-ifcname 
            }
    STATUS current
    DESCRIPTION
        "Notification of Event ETH.51

        Message: 'port $1 down, intf $2'

        Parameters list:
              $1: eth51-port
              $2: eth51-ifcname

        Switch port down."
    ::= { ethNotificationsPrefix 51 }

ethNotification52 NOTIFICATION-TYPE
    OBJECTS { 
              eth52-port, 
              eth52-class-string,
              eth52-ifcname 
            }
    STATUS current
    DESCRIPTION
        "Notification of Event ETH.52

        Message: 'port $1 type $2 power on, intf $3'

        Parameters list:
              $1: eth52-port
              $2: eth52-class-string
              $3: eth52-ifcname

        POE port on."
    ::= { ethNotificationsPrefix 52 }

ethNotification53 NOTIFICATION-TYPE
    OBJECTS { 
              eth53-port, 
              eth53-ifcname 
            }
    STATUS current
    DESCRIPTION
        "Notification of Event ETH.53

        Message: 'port $1 power off, intf $2'

        Parameters list:
              $1: eth53-port
              $2: eth53-ifcname

        POE port off."
    ::= { ethNotificationsPrefix 53 }

ethNotification54 NOTIFICATION-TYPE
    OBJECTS { 
              eth54-port, 
              eth54-error-string,
              eth54-ifcname 
            }
    STATUS current
    DESCRIPTION
        "Notification of Event ETH.54

        Message: 'port $1 detection error cause $2 on intf $3'

        Parameters list:
              $1: eth54-port
              $2: eth54-error-string
              $3: eth54-ifcname

        POE port detection error."
    ::= { ethNotificationsPrefix 54 }


END
