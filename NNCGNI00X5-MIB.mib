-- @(#)DS1Extensions.mib	9.1 10/16/98
--------------------------------------------------------------------------------
-- file: DS1Extensions.mib
--
-- contents:
--    This file contains the Newbridge extensions to the Ds1 MIB.  These
--    provide G.821 statistics, configuration information, worst interval 
--    and other statistics above and beyond what is provided in the DS1 MIB.
--
-- history:
--	0.1 / 92.08.25 / J. Watt / Creation
--	0.2 / 92.10.21 / J. Watt / Added nncExtDs1IntervalNumber 
--	0.3 / 93.01.01 / J. Watt / Aligned with "final" DS1 MIB draft
--	0.4 / 93.02.11 / J. Watt / Added nncExtDs1CurrentTable
--      0.5 / 93.04.04 / J. Watt /
--              Added n to ncErroredSeconds, made declare and
--              clear times, first and second codes R/W,
--              removed REFERENCES clauses
--	0.6 / 93.06.25 / B. McEachern /
--              Index nncExtDs1CircuitTable by slot-port-circuit
--              instead of slot-circuit
--	0.7 / 93.07.16 / B. McEachern /
--              Clean up indexing of nncExtDs1IntervalTable and
--              nncExtDs1CircuitTable
--	0.8 / 93.07.16 / B. McEachern /
--              hanged nncExtDs1AlarmDeclareTime, nncExtDs1AlarmClearingTime
--              and DebounceInterval units from 1/100 sec to milliseconds
--
-- Copyright 1992 to 1993 Newbridge Networks Corporation.  All Rights Reserved.
--------------------------------------------------------------------------------
NNCGNI00X5-MIB	DEFINITIONS ::= BEGIN

	IMPORTS
		Counter, Gauge
			FROM RFC1155-SMI
			
		nncExtDs1
			FROM NNCGNI00X1-SMI
		
		PortIndex, CircuitIndex
			FROM NNCGNI00X7-MIB
			
	        OBJECT-TYPE
        	  	 FROM RFC-1212;	
			
	
	Ds1LineIndex     ::= INTEGER (1..'7fffffff'h)
	Ds1IntervalIndex ::= INTEGER (1..96)
	DebounceInterval ::= INTEGER (100..30000) -- in milliseconds
	
--
-- 	Ds1 Config Extensions Table - per-link configuration and status
--	information above and beyond those kept in the Ds1 MIB.
--

	
	nncExtDs1ConfigTable	OBJECT-TYPE
		SYNTAX	SEQUENCE OF NncExtDs1ConfigEntry
		ACCESS	not-accessible
		STATUS	mandatory
DESCRIPTION ""

		::= { nncExtDs1 1}


	nncExtDs1ConfigEntry OBJECT-TYPE
		SYNTAX	NncExtDs1ConfigEntry
		ACCESS	not-accessible
		STATUS	mandatory
DESCRIPTION ""

		INDEX { nncExtDs1ConfigIndex }
		::= { nncExtDs1ConfigTable 1}
		
		
		
	NncExtDs1ConfigEntry
		::= SEQUENCE {
			nncExtDs1ConfigIndex
				Ds1LineIndex,
			nncExtDs1LineLength
				INTEGER,
			nncExtDs1LineStatus
				INTEGER,
			nncExtDs1TrunkCondEnable
				INTEGER,
			nncExtDs1LossOfFrameConditioning
				INTEGER,
			nncExtDs1DistantLossOfFrameConditioning
				INTEGER,
			nncExtDs1FailedStateConditioning
				INTEGER,
			nncExtDs1ErrorRateConditioning
				INTEGER,
			nncExtDs1CSULoopbackConditioning
				INTEGER,
			nncExtDs1AlarmDeclareTime
				DebounceInterval,
			nncExtDs1AlarmClearTime
				DebounceInterval,
			nncExtDs1UseCRCOnReframe
				INTEGER,
			nncExtDs1WorstInterval
				INTEGER,
			nncExtDs1ErrorEvents
				INTEGER,
			nncExtDs181XXCompatibility
				INTEGER,
			nncExtDs1LoopbackConfig
				INTEGER,
			nncExtDs1E1TrunkCondEnable
				INTEGER
		}


	nncExtDs1ConfigIndex	OBJECT-TYPE
		SYNTAX	Ds1LineIndex
		ACCESS	read-only
		STATUS	mandatory
DESCRIPTION ""

		::= {nncExtDs1ConfigEntry 1}
		
		
	nncExtDs1LineLength	OBJECT-TYPE
		SYNTAX	INTEGER { short(1), medium(2), long(3) }
		ACCESS	read-write
		STATUS	mandatory
DESCRIPTION ""

		::= {nncExtDs1ConfigEntry 2}


	nncExtDs1LineStatus	OBJECT-TYPE
		SYNTAX	INTEGER (0..32767)
		ACCESS	read-only
		STATUS	mandatory
DESCRIPTION ""

		::= {nncExtDs1ConfigEntry 3}


	nncExtDs1TrunkCondEnable	OBJECT-TYPE
		SYNTAX	INTEGER (0..63)
		ACCESS	read-only
		STATUS	mandatory
DESCRIPTION ""

		::= {nncExtDs1ConfigEntry 4}


	nncExtDs1LossOfFrameConditioning	OBJECT-TYPE
		SYNTAX	INTEGER { enable(1), disable(2) }
		ACCESS	read-write
		STATUS  mandatory
DESCRIPTION ""

		::= { nncExtDs1ConfigEntry 5}
		
		
	nncExtDs1DistantLossOfFrameConditioning	OBJECT-TYPE
		SYNTAX	INTEGER { enable(1), disable(2) }
		ACCESS	read-write
		STATUS  mandatory
DESCRIPTION ""

		::= { nncExtDs1ConfigEntry 6}


	nncExtDs1FailedStateConditioning	OBJECT-TYPE
		SYNTAX	INTEGER { enable(1), disable(2) }
		ACCESS	read-write
		STATUS  mandatory
DESCRIPTION ""

		::= { nncExtDs1ConfigEntry 7}


	nncExtDs1ErrorRateConditioning	OBJECT-TYPE
		SYNTAX	INTEGER { enable(1), disable(2) }
		ACCESS	read-write
		STATUS  mandatory
DESCRIPTION ""

		::= { nncExtDs1ConfigEntry 8}


	nncExtDs1CSULoopbackConditioning	OBJECT-TYPE
		SYNTAX	INTEGER { enable(1), disable(2) }
		ACCESS	read-write
		STATUS  mandatory
DESCRIPTION ""

		::= { nncExtDs1ConfigEntry 9}


	nncExtDs1AlarmDeclareTime	OBJECT-TYPE
		SYNTAX	DebounceInterval
		ACCESS	read-write
		STATUS	mandatory
DESCRIPTION ""

		::= {nncExtDs1ConfigEntry 10}
		
		
	nncExtDs1AlarmClearTime	OBJECT-TYPE
		SYNTAX	DebounceInterval
		ACCESS	read-write
		STATUS	mandatory
DESCRIPTION ""

		::= {nncExtDs1ConfigEntry 11}


	nncExtDs1UseCRCOnReframe	OBJECT-TYPE
		SYNTAX	INTEGER { enabled(1), disabled(2), notApplicable(3) }
		ACCESS	read-write
		STATUS	mandatory
DESCRIPTION ""

		::= {nncExtDs1ConfigEntry 12}
	
	
	nncExtDs1WorstInterval		OBJECT-TYPE
		SYNTAX	INTEGER (1..96)
		ACCESS	read-only
		STATUS	mandatory
DESCRIPTION ""

		::= {nncExtDs1ConfigEntry 13}
		
		
	nncExtDs1ErrorEvents	OBJECT-TYPE
		SYNTAX	INTEGER (0..65535)
		ACCESS	read-only
		STATUS	mandatory
DESCRIPTION ""

		::= {nncExtDs1ConfigEntry 14}
		
		
	nncExtDs181XXCompatibility	OBJECT-TYPE
		SYNTAX	INTEGER { enabled(1), disabled(2) }
		ACCESS	read-write
		STATUS	mandatory
DESCRIPTION ""

		::= {nncExtDs1ConfigEntry 15}
	

	nncExtDs1LoopbackConfig	OBJECT-TYPE
		SYNTAX	INTEGER { none(1), equipment(2), line(5) }
		ACCESS	read-write
		STATUS	mandatory
DESCRIPTION ""

		::= {nncExtDs1ConfigEntry 16}


	nncExtDs1E1TrunkCondEnable	OBJECT-TYPE
		SYNTAX	INTEGER (0..63)
		ACCESS	read-only
		STATUS	deprecated
DESCRIPTION ""

		::= {nncExtDs1ConfigEntry 17}

--
-- 	Ds1 E1 Extensions Table - Extensions to the Ds1 MIB for E1 links
--

	nncExtDs1E1ConfigTable	OBJECT-TYPE
		SYNTAX	SEQUENCE OF NncExtDs1E1ConfigEntry
		ACCESS	not-accessible
		STATUS	mandatory
DESCRIPTION ""

		::= { nncExtDs1 2}


	nncExtDs1E1ConfigEntry OBJECT-TYPE
		SYNTAX	NncExtDs1E1ConfigEntry
		ACCESS	not-accessible
		STATUS	mandatory
DESCRIPTION ""

		INDEX { nncExtDs1E1Index }
		::= { nncExtDs1E1ConfigTable 1}
		
		
	NncExtDs1E1ConfigEntry
		::= SEQUENCE {
			nncExtDs1E1Index
				Ds1LineIndex,
			nncExtDs1E1TransmitShieldStatus
				INTEGER,
			nncExtDs1E1ReceivedShieldStatus
				INTEGER,
			nncExtDs1E1StatisticsType
				INTEGER
		}


	nncExtDs1E1Index	OBJECT-TYPE
		SYNTAX	Ds1LineIndex
		ACCESS	read-only
		STATUS	mandatory
DESCRIPTION ""

		::= {nncExtDs1E1ConfigEntry 1}


	nncExtDs1E1TransmitShieldStatus	OBJECT-TYPE
		SYNTAX	INTEGER { earthed(1), floating(2), notApplicable(3) }
		ACCESS	read-write
		STATUS	mandatory
DESCRIPTION ""

		::= {nncExtDs1E1ConfigEntry 2}
		
		
	nncExtDs1E1ReceivedShieldStatus	OBJECT-TYPE
		SYNTAX	INTEGER { earthed(1), floating(2), notApplicable(3) }
		ACCESS	read-write
		STATUS	mandatory
DESCRIPTION ""

		::= {nncExtDs1E1ConfigEntry 3}


	nncExtDs1E1StatisticsType	OBJECT-TYPE
		SYNTAX	INTEGER { hdb3(1), crc4(2) }
		ACCESS	read-write
		STATUS	mandatory
DESCRIPTION ""

		::= {nncExtDs1E1ConfigEntry 4}
		
		
--
-- 	Ds1 G.821 Statistics Table - G.821 statistics for each Ds1
--

	
	nncExtDs1G821StatisticsTable	OBJECT-TYPE
		SYNTAX	SEQUENCE OF NncExtDs1G821StatisticsEntry
		ACCESS	not-accessible
		STATUS	mandatory
DESCRIPTION ""

		::= { nncExtDs1 3}


	nncExtDs1G821StatisticsEntry OBJECT-TYPE
		SYNTAX	NncExtDs1G821StatisticsEntry
		ACCESS	not-accessible
		STATUS	mandatory
DESCRIPTION ""

		INDEX { nncG821Index }
		::= { nncExtDs1G821StatisticsTable 1}
		
		
		
	NncExtDs1G821StatisticsEntry
		::= SEQUENCE {
			nncG821Index
				Ds1LineIndex,
			nncG821DegradedMinutes
				Counter,
			nncG821ErroredSeconds
				Counter,
			nncG821SeverelyErroredSeconds
				Counter,
			nncG821UnavailableSeconds
				Counter,
			nncG821TotalSeconds
				Counter
		}


	nncG821Index	OBJECT-TYPE
		SYNTAX	Ds1LineIndex
		ACCESS	read-only
		STATUS	mandatory
DESCRIPTION ""

		::= {nncExtDs1G821StatisticsEntry 1}
		
		
	nncG821DegradedMinutes	OBJECT-TYPE
		SYNTAX	Counter
		ACCESS	read-only
		STATUS	mandatory
DESCRIPTION ""

		::= {nncExtDs1G821StatisticsEntry 2}


	nncG821ErroredSeconds	OBJECT-TYPE
		SYNTAX	Counter
		ACCESS	read-only
		STATUS	mandatory
DESCRIPTION ""

		::= {nncExtDs1G821StatisticsEntry 3}
		
	
	nncG821SeverelyErroredSeconds	OBJECT-TYPE
		SYNTAX	Counter
		ACCESS	read-only
		STATUS	mandatory
DESCRIPTION ""

		::= {nncExtDs1G821StatisticsEntry 4}
		
		
	nncG821UnavailableSeconds	OBJECT-TYPE
		SYNTAX	Counter
		ACCESS	read-only
		STATUS	mandatory
DESCRIPTION ""

		::= {nncExtDs1G821StatisticsEntry 5}
		
		
	nncG821TotalSeconds	OBJECT-TYPE
		SYNTAX	Counter
		ACCESS	read-only
		STATUS	mandatory
DESCRIPTION ""

		::= {nncExtDs1G821StatisticsEntry 6}




--
-- 	Ds1 Interval Extensions Table - per-interval statistics above and
--	beyond those kept in the Ds1 MIB
--

	nncExtDs1IntervalTable	OBJECT-TYPE
		SYNTAX	SEQUENCE OF NncExtDs1IntervalEntry
		ACCESS	not-accessible
		STATUS	mandatory
DESCRIPTION ""

		::= { nncExtDs1 4}


	nncExtDs1IntervalEntry OBJECT-TYPE
		SYNTAX	NncExtDs1IntervalEntry
		ACCESS	not-accessible
		STATUS	mandatory
DESCRIPTION ""

		INDEX { nncExtDs1IntervalIndex, nncExtDs1IntervalNumber }
		::= { nncExtDs1IntervalTable 1}
		
		
		
	NncExtDs1IntervalEntry
		::= SEQUENCE {
			nncExtDs1IntervalIndex
				Ds1LineIndex,
			nncExtDs1IntervalNumber
				Ds1IntervalIndex,
			nncExtDs1IntervalLOFC
				Gauge
		}


	nncExtDs1IntervalIndex	OBJECT-TYPE
		SYNTAX	Ds1LineIndex
		ACCESS	read-only
		STATUS	mandatory
DESCRIPTION ""

		::= {nncExtDs1IntervalEntry 1}
		
		
	nncExtDs1IntervalNumber	OBJECT-TYPE
		SYNTAX	INTEGER (1..96)
		ACCESS	read-only
		STATUS	mandatory
DESCRIPTION ""

		::= {nncExtDs1IntervalEntry 2}

	nncExtDs1IntervalLOFC	OBJECT-TYPE
		SYNTAX	Gauge
		ACCESS	read-only
		STATUS	mandatory
DESCRIPTION ""

		::= {nncExtDs1IntervalEntry 3}

		
		
		
		
--
-- 	Ds1 Totals Extensions Table - total statistics above and
--	beyond those kept in the Ds1 MIB
--


	nncExtDs1TotalTable	OBJECT-TYPE
		SYNTAX	SEQUENCE OF NncExtDs1TotalEntry
		ACCESS	not-accessible
		STATUS	mandatory
DESCRIPTION ""

		::= { nncExtDs1 5}


	nncExtDs1TotalEntry OBJECT-TYPE
		SYNTAX	NncExtDs1TotalEntry
		ACCESS	not-accessible
		STATUS	mandatory
DESCRIPTION ""

		INDEX { nncExtDs1TotalIndex }
		::= { nncExtDs1TotalTable 1}
		
		
		
	NncExtDs1TotalEntry
		::= SEQUENCE {
			nncExtDs1TotalIndex
				Ds1LineIndex,
			nncExtDs1TotalLOFC
				Gauge
		}


	nncExtDs1TotalIndex	OBJECT-TYPE
		SYNTAX	Ds1LineIndex
		ACCESS	read-only
		STATUS	mandatory
DESCRIPTION ""

		::= {nncExtDs1TotalEntry 1}


	nncExtDs1TotalLOFC	OBJECT-TYPE
		SYNTAX	Gauge
		ACCESS	read-only
		STATUS	mandatory
DESCRIPTION ""

		::= {nncExtDs1TotalEntry 2}
		
		
		

--
-- 	Ds1 Current Extensions Table - per-Current statistics above and
--	beyond those kept in the Ds1 MIB
--

	nncExtDs1CurrentTable	OBJECT-TYPE
		SYNTAX	SEQUENCE OF NncExtDs1CurrentEntry
		ACCESS	not-accessible
		STATUS	mandatory
DESCRIPTION ""

		::= { nncExtDs1 8}


	nncExtDs1CurrentEntry OBJECT-TYPE
		SYNTAX	NncExtDs1CurrentEntry
		ACCESS	not-accessible
		STATUS	mandatory
DESCRIPTION ""

		INDEX { nncExtDs1CurrentIndex }
		::= { nncExtDs1CurrentTable 1}
		
		
		
	NncExtDs1CurrentEntry
		::= SEQUENCE {
			nncExtDs1CurrentIndex
				Ds1LineIndex,
			nncExtDs1CurrentLOFC
				Gauge
		}


	nncExtDs1CurrentIndex	OBJECT-TYPE
		SYNTAX	Ds1LineIndex
		ACCESS	read-only
		STATUS	mandatory
DESCRIPTION ""

		::= {nncExtDs1CurrentEntry 1}

	nncExtDs1CurrentLOFC	OBJECT-TYPE
		SYNTAX	Gauge
		ACCESS	read-only
		STATUS	mandatory
DESCRIPTION ""

		::= {nncExtDs1CurrentEntry 2}


--
-- 	Ds1 Worst Interval Table - the interval statistics for the
--	worst interval
--


	nncExtDs1WorstIntervalTable	OBJECT-TYPE
		SYNTAX	SEQUENCE OF NncExtDs1WorstIntervalEntry
		ACCESS	not-accessible
		STATUS	mandatory
DESCRIPTION ""

		::= { nncExtDs1 6}


	nncExtDs1WorstIntervalEntry OBJECT-TYPE
		SYNTAX	NncExtDs1WorstIntervalEntry
		ACCESS	not-accessible
		STATUS	mandatory
DESCRIPTION ""

		INDEX { nncExtDs1WorstIntervalIndex }
		::= { nncExtDs1WorstIntervalTable 1}
		
		
		
	NncExtDs1WorstIntervalEntry
		::= SEQUENCE {
			nncExtDs1WorstIntervalIndex
				Ds1LineIndex,
			nncExtDs1WorstIntervalBESs
				Gauge,
			nncExtDs1WorstIntervalLOFC
				Gauge,
			nncExtDs1WorstIntervalESs
				Gauge,
			nncExtDs1WorstIntervalSESs
				Gauge,
			nncExtDs1WorstIntervalSEFSs
				Gauge,
			nncExtDs1WorstIntervalUASs
				Gauge,
			nncExtDs1WorstIntervalCSSs
				Gauge,
			nncExtDs1WorstIntervalBPVs
				Gauge,
			nncExtDs1WorstIntervalCVs
				Gauge,
			nncExtDs1WorstIntervalLESs
				Gauge
		}


	nncExtDs1WorstIntervalIndex	OBJECT-TYPE
		SYNTAX	Ds1LineIndex
		ACCESS	read-only
		STATUS	mandatory
DESCRIPTION ""

		::= {nncExtDs1WorstIntervalEntry 1}
		
		
	nncExtDs1WorstIntervalBESs	OBJECT-TYPE
		SYNTAX	Gauge
		ACCESS	read-only
		STATUS	mandatory
DESCRIPTION ""

		::= {nncExtDs1WorstIntervalEntry 2}
		
	
	nncExtDs1WorstIntervalLOFC	OBJECT-TYPE
		SYNTAX	Gauge
		ACCESS	read-only
		STATUS	mandatory
DESCRIPTION ""

		::= {nncExtDs1WorstIntervalEntry 3}


         nncExtDs1WorstIntervalESs OBJECT-TYPE
             SYNTAX  Gauge
             ACCESS  read-only
             STATUS  mandatory
DESCRIPTION ""

            ::= { nncExtDs1WorstIntervalEntry 4 }


         nncExtDs1WorstIntervalSESs OBJECT-TYPE
             SYNTAX  Gauge
             ACCESS  read-only
             STATUS  mandatory
DESCRIPTION ""

            ::= { nncExtDs1WorstIntervalEntry 5 }


         nncExtDs1WorstIntervalSEFSs OBJECT-TYPE
             SYNTAX  Gauge
             ACCESS  read-only
             STATUS  mandatory
DESCRIPTION ""

            ::= { nncExtDs1WorstIntervalEntry 6 }


         nncExtDs1WorstIntervalUASs OBJECT-TYPE
             SYNTAX  Gauge
             ACCESS  read-only
             STATUS  mandatory
DESCRIPTION ""

            ::= { nncExtDs1WorstIntervalEntry 7 }


         nncExtDs1WorstIntervalCSSs OBJECT-TYPE
             SYNTAX  Gauge
             ACCESS  read-only
             STATUS  mandatory
DESCRIPTION ""

            ::= { nncExtDs1WorstIntervalEntry 8 }


         nncExtDs1WorstIntervalBPVs OBJECT-TYPE
             SYNTAX  Gauge
             ACCESS  read-only
             STATUS  mandatory
DESCRIPTION ""

            ::= { nncExtDs1WorstIntervalEntry 9 }


         nncExtDs1WorstIntervalCVs OBJECT-TYPE
             SYNTAX  Gauge
             ACCESS  read-only
             STATUS  mandatory
DESCRIPTION ""

            ::= { nncExtDs1WorstIntervalEntry 10 }


         nncExtDs1WorstIntervalLESs OBJECT-TYPE
             SYNTAX  Gauge
             ACCESS  read-only
             STATUS  mandatory
DESCRIPTION ""

            ::= { nncExtDs1WorstIntervalEntry 11 }

--
-- 	Ds1 Circuit Extensions Table - configuration and status information
--	for individual timeslots on the Ds1
--


	nncExtDs1CircuitTable	OBJECT-TYPE
		SYNTAX	SEQUENCE OF NncExtDs1CircuitEntry
		ACCESS	not-accessible
		STATUS	mandatory
DESCRIPTION ""

		::= { nncExtDs1 7}


	nncExtDs1CircuitEntry OBJECT-TYPE
		SYNTAX	NncExtDs1CircuitEntry
		ACCESS	not-accessible
		STATUS	mandatory
DESCRIPTION ""

		INDEX { nncExtDs1CctIndex, nncExtDs1CctPortNumber, nncExtDs1CctNumber }
		::= { nncExtDs1CircuitTable 1}
		
		
		
	NncExtDs1CircuitEntry
		::= SEQUENCE {
			nncExtDs1CctIndex
				Ds1LineIndex,
			nncExtDs1CctPortNumber
				PortIndex,
			nncExtDs1CctNumber
				CircuitIndex,
			nncExtDs1CctUseRBS
				INTEGER,
			nncExtDs1CctDataInversion
				INTEGER,
			nncExtDs1CctDefaultData
				INTEGER,
			nncExtDs1CctFirstCode
				INTEGER,
			nncExtDs1CctSecondCode
				INTEGER,
			nncExtDs1CctBitsToUse
				INTEGER,
			nncExtDs1CctSuperRateMap
				INTEGER,
			nncExtDs1CctFaultSignalling
				INTEGER
		}


	nncExtDs1CctIndex	OBJECT-TYPE
		SYNTAX	Ds1LineIndex
		ACCESS	read-only
		STATUS	mandatory
DESCRIPTION ""

		::= {nncExtDs1CircuitEntry 1}


	nncExtDs1CctPortNumber	OBJECT-TYPE
		SYNTAX	INTEGER (1..4)
		ACCESS	read-only
		STATUS	mandatory
DESCRIPTION ""

		::= {nncExtDs1CircuitEntry 2}

		
	nncExtDs1CctNumber	OBJECT-TYPE
		SYNTAX	INTEGER (1..31)
		ACCESS	read-only
		STATUS	mandatory
DESCRIPTION ""

		::= {nncExtDs1CircuitEntry 3}


	nncExtDs1CctUseRBS	OBJECT-TYPE
		SYNTAX	INTEGER { rbsOn(1), rbsOff(2) }
		ACCESS	read-write
		STATUS	mandatory
DESCRIPTION ""

		::= {nncExtDs1CircuitEntry 4}


	nncExtDs1CctDataInversion	OBJECT-TYPE
		SYNTAX	INTEGER { invertOn(1), invertOff(2) }
		ACCESS	read-write
		STATUS	mandatory
DESCRIPTION ""

		::= {nncExtDs1CircuitEntry 5}
		
		
	nncExtDs1CctDefaultData	OBJECT-TYPE
		SYNTAX	INTEGER (0..'ff'H)
		ACCESS	read-write
		STATUS	mandatory
DESCRIPTION ""

		::= {nncExtDs1CircuitEntry 6}


	nncExtDs1CctFirstCode	OBJECT-TYPE
		SYNTAX	INTEGER (0..'0F'H)
		ACCESS	read-write
		STATUS	mandatory
DESCRIPTION ""

		::= {nncExtDs1CircuitEntry 7}
		
		
	nncExtDs1CctSecondCode	OBJECT-TYPE
		SYNTAX	INTEGER (0..'0F'H)
		ACCESS	read-write
		STATUS	mandatory
DESCRIPTION ""

		::= {nncExtDs1CircuitEntry 8}


	nncExtDs1CctBitsToUse	OBJECT-TYPE
		SYNTAX	INTEGER (0..'FF'H)
		ACCESS	read-write
		STATUS	mandatory
DESCRIPTION ""

		::= {nncExtDs1CircuitEntry 9}
		
		
	nncExtDs1CctSuperRateMap	OBJECT-TYPE
		SYNTAX	INTEGER (0..2147483647)
		ACCESS	read-write
		STATUS	mandatory
DESCRIPTION ""

		::= {nncExtDs1CircuitEntry 10}
		
		
	nncExtDs1CctFaultSignalling	OBJECT-TYPE
		SYNTAX	INTEGER { idle(1), seized(2), none(3) }
		ACCESS	read-write
		STATUS	mandatory
DESCRIPTION ""

		::= {nncExtDs1CircuitEntry 11}

	END
