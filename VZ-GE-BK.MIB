--**********************************************************
-- Generated by LiteEdit
-- Archive ID string: IL-NT-2.6.0 R:24.07.2018
-- Application: Standard-AMF25
-- Archive name: 
-- Controller s.n. 1502564B
--**********************************************************

COMAP-IL-NT-1502564B DEFINITIONS ::= BEGIN

--******************************************************************--
IMPORTS
 enterprises,
 IpAddress,
 Counter,
 Gauge,
 TimeTicks
  FROM RFC1155-SMI

 OBJECT-TYPE
  FROM RFC-1212

 DisplayString
  FROM RFC1213-MIB

 TRAP-TYPE
  FROM RFC-1215;

 Index::=INTEGER

--******************************************************************--

comapProjekt     OBJECT IDENTIFIER ::= { enterprises 28634 }
il-nt           OBJECT IDENTIFIER ::= { comapProjekt 6 }
c1502564B        OBJECT IDENTIFIER ::= { il-nt 1263927829 }

table-rd-fix     OBJECT IDENTIFIER ::= { c1502564B 1 }
table-rd-cfg     OBJECT IDENTIFIER ::= { c1502564B 2 }
table-wr-fix     OBJECT IDENTIFIER ::= { c1502564B 3 }
table-wr-cfg     OBJECT IDENTIFIER ::= { c1502564B 4 }
table-w          OBJECT IDENTIFIER ::= { c1502564B 5 }
table-alarms     OBJECT IDENTIFIER ::= { c1502564B 6 }
trap-data        OBJECT IDENTIFIER ::= { c1502564B 7 }

--******************************************************************--

vGen-V-L1-N	OBJECT-TYPE
	SYNTAX	INTEGER
	ACCESS	read-only
	STATUS	mandatory
	DESCRIPTION	"DEC=0, UNIT='V'"
 ::= { table-rd-cfg 8192 }

vGen-V-L2-N	OBJECT-TYPE
	SYNTAX	INTEGER
	ACCESS	read-only
	STATUS	mandatory
	DESCRIPTION	"DEC=0, UNIT='V'"
 ::= { table-rd-cfg 8193 }

vGen-V-L3-N	OBJECT-TYPE
	SYNTAX	INTEGER
	ACCESS	read-only
	STATUS	mandatory
	DESCRIPTION	"DEC=0, UNIT='V'"
 ::= { table-rd-cfg 8194 }

vMains-V-L1-N	OBJECT-TYPE
	SYNTAX	INTEGER
	ACCESS	read-only
	STATUS	mandatory
	DESCRIPTION	"DEC=0, UNIT='V'"
 ::= { table-rd-cfg 8195 }

vMains-V-L2-N	OBJECT-TYPE
	SYNTAX	INTEGER
	ACCESS	read-only
	STATUS	mandatory
	DESCRIPTION	"DEC=0, UNIT='V'"
 ::= { table-rd-cfg 8196 }

vMains-V-L3-N	OBJECT-TYPE
	SYNTAX	INTEGER
	ACCESS	read-only
	STATUS	mandatory
	DESCRIPTION	"DEC=0, UNIT='V'"
 ::= { table-rd-cfg 8197 }

vLoad-A-L1	OBJECT-TYPE
	SYNTAX	INTEGER
	ACCESS	read-only
	STATUS	mandatory
	DESCRIPTION	"DEC=0, UNIT='A'"
 ::= { table-rd-cfg 8198 }

vLoad-A-L2	OBJECT-TYPE
	SYNTAX	INTEGER
	ACCESS	read-only
	STATUS	mandatory
	DESCRIPTION	"DEC=0, UNIT='A'"
 ::= { table-rd-cfg 8199 }

vLoad-A-L3	OBJECT-TYPE
	SYNTAX	INTEGER
	ACCESS	read-only
	STATUS	mandatory
	DESCRIPTION	"DEC=0, UNIT='A'"
 ::= { table-rd-cfg 8200 }

vLoad-kW	OBJECT-TYPE
	SYNTAX	INTEGER
	ACCESS	read-only
	STATUS	mandatory
	DESCRIPTION	"DEC=0, UNIT='kW'"
 ::= { table-rd-cfg 8202 }

vLoad-kVAr	OBJECT-TYPE
	SYNTAX	INTEGER
	ACCESS	read-only
	STATUS	mandatory
	DESCRIPTION	"DEC=0, UNIT='kVAr'"
 ::= { table-rd-cfg 8203 }

vLoad-PF	OBJECT-TYPE
	SYNTAX	INTEGER
	ACCESS	read-only
	STATUS	mandatory
	DESCRIPTION	"DEC=2, UNIT='-'"
 ::= { table-rd-cfg 8204 }

vGenset-kWh	OBJECT-TYPE
	SYNTAX	INTEGER
	ACCESS	read-only
	STATUS	mandatory
	DESCRIPTION	"DEC=0, UNIT='-'"
 ::= { table-rd-cfg 8205 }

vRun-Hours	OBJECT-TYPE
	SYNTAX	INTEGER
	ACCESS	read-only
	STATUS	mandatory
	DESCRIPTION	"DEC=1, UNIT='h'"
 ::= { table-rd-cfg 8206 }

vNum-Starts	OBJECT-TYPE
	SYNTAX	INTEGER
	ACCESS	read-only
	STATUS	mandatory
	DESCRIPTION	"DEC=0, UNIT='-'"
 ::= { table-rd-cfg 8207 }

vGen-Freq	OBJECT-TYPE
	SYNTAX	INTEGER
	ACCESS	read-only
	STATUS	mandatory
	DESCRIPTION	"DEC=1, UNIT='Hz'"
 ::= { table-rd-cfg 8210 }

vMains-Freq	OBJECT-TYPE
	SYNTAX	INTEGER
	ACCESS	read-only
	STATUS	mandatory
	DESCRIPTION	"DEC=1, UNIT='Hz'"
 ::= { table-rd-cfg 8211 }

vBattery-Volts	OBJECT-TYPE
	SYNTAX	INTEGER
	ACCESS	read-only
	STATUS	mandatory
	DESCRIPTION	"DEC=1, UNIT='V'"
 ::= { table-rd-cfg 8213 }

vOil-Pressure	OBJECT-TYPE
	SYNTAX	INTEGER
	ACCESS	read-only
	STATUS	mandatory
	DESCRIPTION	"DEC=1, UNIT='Bar'"
 ::= { table-rd-cfg 8227 }

vEngine-Temp	OBJECT-TYPE
	SYNTAX	INTEGER
	ACCESS	read-only
	STATUS	mandatory
	DESCRIPTION	"DEC=0, UNIT='-deg-C'"
 ::= { table-rd-cfg 8228 }

vFuel-Level	OBJECT-TYPE
	SYNTAX	INTEGER
	ACCESS	read-only
	STATUS	mandatory
	DESCRIPTION	"DEC=0, UNIT='-percent-'"
 ::= { table-rd-cfg 8229 }

vBin-Inputs	OBJECT-TYPE
	SYNTAX	DisplayString
	ACCESS	read-only
	STATUS	mandatory
	DESCRIPTION	"BINARY, BITS=7"
 ::= { table-rd-cfg 8235 }

vBin-Outputs	OBJECT-TYPE
	SYNTAX	DisplayString
	ACCESS	read-only
	STATUS	mandatory
	DESCRIPTION	"BINARY, BITS=7"
 ::= { table-rd-cfg 8239 }

vEngine-State	OBJECT-TYPE
	SYNTAX	INTEGER
	ACCESS	read-only
	STATUS	mandatory
	DESCRIPTION	"DEC=0, UNIT='-'"
 ::= { table-rd-cfg 8330 }

vLoad-Char	OBJECT-TYPE
	SYNTAX	DisplayString
	ACCESS	read-only
	STATUS	mandatory
	DESCRIPTION	"String"
 ::= { table-rd-cfg 8395 }

vLoad-kW-L1	OBJECT-TYPE
	SYNTAX	INTEGER
	ACCESS	read-only
	STATUS	mandatory
	DESCRIPTION	"DEC=0, UNIT='kW'"
 ::= { table-rd-cfg 8524 }

vLoad-kW-L2	OBJECT-TYPE
	SYNTAX	INTEGER
	ACCESS	read-only
	STATUS	mandatory
	DESCRIPTION	"DEC=0, UNIT='kW'"
 ::= { table-rd-cfg 8525 }

vLoad-kW-L3	OBJECT-TYPE
	SYNTAX	INTEGER
	ACCESS	read-only
	STATUS	mandatory
	DESCRIPTION	"DEC=0, UNIT='kW'"
 ::= { table-rd-cfg 8526 }

vLoad-kVAr-L1	OBJECT-TYPE
	SYNTAX	INTEGER
	ACCESS	read-only
	STATUS	mandatory
	DESCRIPTION	"DEC=0, UNIT='kVAr'"
 ::= { table-rd-cfg 8527 }

vLoad-kVAr-L2	OBJECT-TYPE
	SYNTAX	INTEGER
	ACCESS	read-only
	STATUS	mandatory
	DESCRIPTION	"DEC=0, UNIT='kVAr'"
 ::= { table-rd-cfg 8528 }

vLoad-kVAr-L3	OBJECT-TYPE
	SYNTAX	INTEGER
	ACCESS	read-only
	STATUS	mandatory
	DESCRIPTION	"DEC=0, UNIT='kVAr'"
 ::= { table-rd-cfg 8529 }

vLoad-kVA-L1	OBJECT-TYPE
	SYNTAX	INTEGER
	ACCESS	read-only
	STATUS	mandatory
	DESCRIPTION	"DEC=0, UNIT='kVA'"
 ::= { table-rd-cfg 8530 }

vLoad-kVA-L2	OBJECT-TYPE
	SYNTAX	INTEGER
	ACCESS	read-only
	STATUS	mandatory
	DESCRIPTION	"DEC=0, UNIT='kVA'"
 ::= { table-rd-cfg 8531 }

vLoad-kVA-L3	OBJECT-TYPE
	SYNTAX	INTEGER
	ACCESS	read-only
	STATUS	mandatory
	DESCRIPTION	"DEC=0, UNIT='kVA'"
 ::= { table-rd-cfg 8532 }

vLoad-PF-L1	OBJECT-TYPE
	SYNTAX	INTEGER
	ACCESS	read-only
	STATUS	mandatory
	DESCRIPTION	"DEC=2, UNIT='-'"
 ::= { table-rd-cfg 8533 }

vLoad-PF-L2	OBJECT-TYPE
	SYNTAX	INTEGER
	ACCESS	read-only
	STATUS	mandatory
	DESCRIPTION	"DEC=2, UNIT='-'"
 ::= { table-rd-cfg 8534 }

vLoad-PF-L3	OBJECT-TYPE
	SYNTAX	INTEGER
	ACCESS	read-only
	STATUS	mandatory
	DESCRIPTION	"DEC=2, UNIT='-'"
 ::= { table-rd-cfg 8535 }

vGenset-kVArh	OBJECT-TYPE
	SYNTAX	INTEGER
	ACCESS	read-only
	STATUS	mandatory
	DESCRIPTION	"DEC=0, UNIT='-'"
 ::= { table-rd-cfg 8539 }

vLoad-kVA	OBJECT-TYPE
	SYNTAX	INTEGER
	ACCESS	read-only
	STATUS	mandatory
	DESCRIPTION	"DEC=0, UNIT='kVA'"
 ::= { table-rd-cfg 8565 }

vLoad-Char-L1	OBJECT-TYPE
	SYNTAX	DisplayString
	ACCESS	read-only
	STATUS	mandatory
	DESCRIPTION	"String"
 ::= { table-rd-cfg 8626 }

vLoad-Char-L2	OBJECT-TYPE
	SYNTAX	DisplayString
	ACCESS	read-only
	STATUS	mandatory
	DESCRIPTION	"String"
 ::= { table-rd-cfg 8627 }

vLoad-Char-L3	OBJECT-TYPE
	SYNTAX	DisplayString
	ACCESS	read-only
	STATUS	mandatory
	DESCRIPTION	"String"
 ::= { table-rd-cfg 8628 }

vTotFuelConsum	OBJECT-TYPE
	SYNTAX	Gauge
	ACCESS	read-only
	STATUS	mandatory
	DESCRIPTION	"DEC=0, UNIT='L'"
 ::= { table-rd-cfg 9040 }

vControllerMode	OBJECT-TYPE
	SYNTAX	INTEGER
	ACCESS	read-only
	STATUS	mandatory
	DESCRIPTION	"DEC=0, UNIT='-'"
 ::= { table-rd-cfg 9574 }

vGen-V-L1-L2	OBJECT-TYPE
	SYNTAX	INTEGER
	ACCESS	read-only
	STATUS	mandatory
	DESCRIPTION	"DEC=0, UNIT='V'"
 ::= { table-rd-cfg 9628 }

vGen-V-L2-L3	OBJECT-TYPE
	SYNTAX	INTEGER
	ACCESS	read-only
	STATUS	mandatory
	DESCRIPTION	"DEC=0, UNIT='V'"
 ::= { table-rd-cfg 9629 }

vGen-V-L3-L1	OBJECT-TYPE
	SYNTAX	INTEGER
	ACCESS	read-only
	STATUS	mandatory
	DESCRIPTION	"DEC=0, UNIT='V'"
 ::= { table-rd-cfg 9630 }

vMains-V-L1-L2	OBJECT-TYPE
	SYNTAX	INTEGER
	ACCESS	read-only
	STATUS	mandatory
	DESCRIPTION	"DEC=0, UNIT='V'"
 ::= { table-rd-cfg 9631 }

vMains-V-L2-L3	OBJECT-TYPE
	SYNTAX	INTEGER
	ACCESS	read-only
	STATUS	mandatory
	DESCRIPTION	"DEC=0, UNIT='V'"
 ::= { table-rd-cfg 9632 }

vMains-V-L3-L1	OBJECT-TYPE
	SYNTAX	INTEGER
	ACCESS	read-only
	STATUS	mandatory
	DESCRIPTION	"DEC=0, UNIT='V'"
 ::= { table-rd-cfg 9633 }

vMaintenance	OBJECT-TYPE
	SYNTAX	INTEGER
	ACCESS	read-only
	STATUS	mandatory
	DESCRIPTION	"DEC=0, UNIT='h'"
 ::= { table-rd-cfg 9648 }

vD-plus-	OBJECT-TYPE
	SYNTAX	INTEGER
	ACCESS	read-only
	STATUS	mandatory
	DESCRIPTION	"DEC=1, UNIT='V'"
 ::= { table-rd-cfg 10603 }

vMains-kWh	OBJECT-TYPE
	SYNTAX	INTEGER
	ACCESS	read-only
	STATUS	mandatory
	DESCRIPTION	"DEC=0, UNIT='-'"
 ::= { table-rd-cfg 11025 }

vMains-kVArh	OBJECT-TYPE
	SYNTAX	INTEGER
	ACCESS	read-only
	STATUS	mandatory
	DESCRIPTION	"DEC=0, UNIT='-'"
 ::= { table-rd-cfg 11026 }

vNum-E-Stops	OBJECT-TYPE
	SYNTAX	Gauge
	ACCESS	read-only
	STATUS	mandatory
	DESCRIPTION	"DEC=0, UNIT='-'"
 ::= { table-rd-cfg 11195 }

vShutdowns	OBJECT-TYPE
	SYNTAX	Gauge
	ACCESS	read-only
	STATUS	mandatory
	DESCRIPTION	"DEC=0, UNIT='-'"
 ::= { table-rd-cfg 11196 }

vDate	OBJECT-TYPE
	SYNTAX	DisplayString
	ACCESS	read-only
	STATUS	mandatory
	DESCRIPTION	"Date"
 ::= { table-rd-cfg 24553 }

vTime	OBJECT-TYPE
	SYNTAX	DisplayString
	ACCESS	read-only
	STATUS	mandatory
	DESCRIPTION	"Time"
 ::= { table-rd-cfg 24554 }


--******************************************************************--


vfControllerMode	OBJECT-TYPE
	SYNTAX	INTEGER
	ACCESS	read-only
	STATUS	mandatory
	DESCRIPTION	"None"
 ::= { table-rd-fix 9574 }

--******************************************************************--

alarmTable	OBJECT-TYPE
	SYNTAX	SEQUENCE OF AlarmEntry
	ACCESS	not-accessible
	STATUS	mandatory
	DESCRIPTION	""
 ::= { table-alarms 1 }

alarmEntry  OBJECT-TYPE
	SYNTAX	AlarmEntry
	ACCESS	not-accessible
	STATUS	mandatory
  DESCRIPTION	""
  INDEX  { Index }
 ::= { alarmTable 1 }

AlarmEntry ::= SEQUENCE
{
    alarmText DisplayString
}

alarmText	OBJECT-TYPE
  SYNTAX	DisplayString
	ACCESS	read-only
	STATUS	mandatory
	DESCRIPTION	"Alarm text"
 ::= { alarmEntry 1 }


--******************************************************************--

pControllerMode	OBJECT-TYPE
	SYNTAX	INTEGER
	ACCESS	read-write
	STATUS	mandatory
	DESCRIPTION	"LIST, 0-OFF, 1-MAN, 2-AUT, 3-TEST"
 ::= { table-wr-cfg 8315 }

pWrnMaintenance	OBJECT-TYPE
	SYNTAX	INTEGER
	ACCESS	read-write
	STATUS	mandatory
	DESCRIPTION	"DEC=0, UNIT='h'"
 ::= { table-wr-cfg 9648 }


--******************************************************************--

pfControllerMode	OBJECT-TYPE
	SYNTAX	INTEGER
	ACCESS	read-write
	STATUS	mandatory
	DESCRIPTION	"LIST, 0-OFF, 1-MAN, 2-AUT, 3-TEST"
 ::= { table-wr-fix 8315 }

pfActionArgument	OBJECT-TYPE
	SYNTAX	Gauge
	ACCESS	read-write
	STATUS	mandatory
	DESCRIPTION	""
 ::= { table-wr-fix 24550 }

--******************************************************************--


pfPassword	OBJECT-TYPE
	SYNTAX	INTEGER
	ACCESS	write-only
	STATUS	mandatory
	DESCRIPTION	""
 ::= { table-w 24524 }

pfActionCommand	OBJECT-TYPE
	SYNTAX	INTEGER
	ACCESS	write-only
	STATUS	mandatory
	DESCRIPTION	""
 ::= { table-w 24551 }

--******************************************************************--

pfControllerName  OBJECT-TYPE
	SYNTAX	DisplayString
  ACCESS	read-only
  STATUS	mandatory
  DESCRIPTION	"Name of the controller."
 ::= { trap-data 8637 }

pfSerNum  OBJECT-TYPE
	SYNTAX	DisplayString
  ACCESS	read-only
  STATUS	mandatory
  DESCRIPTION	"Serial number of the controller."
 ::= { trap-data 24548 }

tAlarmText1 OBJECT-TYPE
	SYNTAX	DisplayString
	ACCESS	read-only
	STATUS	mandatory
	DESCRIPTION	"AlarmList Item 1"
 ::= { trap-data 1 }

tAlarmText2 OBJECT-TYPE
	SYNTAX	DisplayString
	ACCESS	read-only
	STATUS	mandatory
	DESCRIPTION	"AlarmList Item 2"
 ::= { trap-data 2 }

tAlarmText3 OBJECT-TYPE
	SYNTAX	DisplayString
	ACCESS	read-only
	STATUS	mandatory
	DESCRIPTION	"AlarmList Item 3"
 ::= { trap-data 3 }

tAlarmText4	OBJECT-TYPE
	SYNTAX	DisplayString
	ACCESS	read-only
	STATUS  mandatory
	DESCRIPTION	"AlarmList Item 4"
 ::= { trap-data 4 }

tAlarmText5	OBJECT-TYPE
	SYNTAX	DisplayString
	ACCESS	read-only
	STATUS	mandatory
	DESCRIPTION	"AlarmList Item 5"
 ::= { trap-data 5 }

tAlarmText6	OBJECT-TYPE
	SYNTAX	DisplayString
	ACCESS	read-only
	STATUS	mandatory
	DESCRIPTION	"AlarmList Item 6"
 ::= { trap-data 6 }

tAlarmText7	OBJECT-TYPE
	SYNTAX	DisplayString
	ACCESS	read-only
	STATUS	mandatory
	DESCRIPTION	"AlarmList Item 7"
 ::= { trap-data 7 }

tAlarmText8	OBJECT-TYPE
	SYNTAX	DisplayString
	ACCESS	read-only
	STATUS	mandatory
	DESCRIPTION	"AlarmList Item 8"
 ::= { trap-data 8 }

tAlarmText9	OBJECT-TYPE
	SYNTAX	DisplayString
	ACCESS	read-only
	STATUS	mandatory
	DESCRIPTION	"AlarmList Item 9"
 ::= { trap-data 9 }

tAlarmText10	OBJECT-TYPE
	SYNTAX	DisplayString
	ACCESS	read-only
	STATUS	mandatory
	DESCRIPTION	"AlarmList Item 10"
 ::= { trap-data 10 }

tAlarmText11	OBJECT-TYPE
	SYNTAX	DisplayString
	ACCESS	read-only
	STATUS	mandatory
	DESCRIPTION	"AlarmList Item 11"
 ::= { trap-data 11 }

tAlarmText12	OBJECT-TYPE
	SYNTAX	DisplayString
	ACCESS	read-only
	STATUS	mandatory
	DESCRIPTION	"AlarmList Item 12"
 ::= { trap-data 12 }

tAlarmText13	OBJECT-TYPE
	SYNTAX	DisplayString
	ACCESS	read-only
	STATUS	mandatory
	DESCRIPTION	"AlarmList Item 13"
 ::= { trap-data 13 }

tAlarmText14	OBJECT-TYPE
	SYNTAX	DisplayString
	ACCESS	read-only
	STATUS	mandatory
	DESCRIPTION	"AlarmList Item 14"
 ::= { trap-data 14 }

tAlarmText15	OBJECT-TYPE
	SYNTAX	DisplayString
	ACCESS	read-only
	STATUS	mandatory
	DESCRIPTION	"AlarmList Item 15"
 ::= { trap-data 15 }

tAlarmText16	OBJECT-TYPE
	SYNTAX	DisplayString
	ACCESS	read-only
	STATUS	mandatory
	DESCRIPTION	"AlarmList Item 16"
 ::= { trap-data 16 }

alarm	TRAP-TYPE
	ENTERPRISE	c1502564B
	VARIABLES	{pfControllerName,
	           pfSerNum,
	           tAlarmText1,
	           tAlarmText2,
	           tAlarmText3,
	           tAlarmText4,
	           tAlarmText5,
	           tAlarmText6,
	           tAlarmText7,
	           tAlarmText8,
	           tAlarmText9,
	           tAlarmText10,
	           tAlarmText11,
	           tAlarmText12,
	           tAlarmText13,
	           tAlarmText14,
	           tAlarmText15,
	           tAlarmText16}
	DESCRIPTION "This trap indicates that there is a new alarm in the controller alarm list."
 ::= 1

END
