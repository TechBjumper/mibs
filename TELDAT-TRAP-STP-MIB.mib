-- file automatically created


TELDAT-TRAP-STP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


stpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the STP event subsystem."
    REVISION "201401200930Z"
    DESCRIPTION "Initial implementation"
        ::= { telEventTraps 73 }


stpEventsGroup	OBJECT IDENTIFIER	::= { stpTrapsMIB 1 }

stpNotifications	OBJECT IDENTIFIER	::= { stpTrapsMIB 2 }
stpNotificationsPrefix	OBJECT IDENTIFIER	::= { stpNotifications 0 }

stpEventObjects1 OBJECT-IDENTITY
    STATUS current
    DESCRIPTION
        "Event STP.1
        A configuration BPDU has been received from the specified MAC address."
    ::= { stpEventsGroup 1 }

stp1-source-address OBJECT-TYPE
    SYNTAX DisplayString
    MAX-ACCESS accessible-for-notify
    STATUS current
    DESCRIPTION
        "Parameter 'source-address' in event STP.1"
    ::= { stpEventObjects1 1 }

stp1-bridge-type OBJECT-TYPE
    SYNTAX DisplayString
    MAX-ACCESS accessible-for-notify
    STATUS current
    DESCRIPTION
        "Parameter 'bridge-type' in event STP.1"
    ::= { stpEventObjects1 2 }

stp1-bridge-instance OBJECT-TYPE
    SYNTAX Integer32
    MAX-ACCESS accessible-for-notify
    STATUS current
    DESCRIPTION
        "Parameter 'bridge-instance' in event STP.1"
    ::= { stpEventObjects1 3 }

stp1-bridge-port OBJECT-TYPE
    SYNTAX Integer32
    MAX-ACCESS accessible-for-notify
    STATUS current
    DESCRIPTION
        "Parameter 'bridge-port' in event STP.1"
    ::= { stpEventObjects1 4 }

stp1-interface OBJECT-TYPE
    SYNTAX DisplayString
    MAX-ACCESS accessible-for-notify
    STATUS current
    DESCRIPTION
        "Parameter 'interface' in event STP.1"
    ::= { stpEventObjects1 5 }

stp1-circuit-name OBJECT-TYPE
    SYNTAX DisplayString
    MAX-ACCESS accessible-for-notify
    STATUS current
    DESCRIPTION
        "Parameter 'circuit-name' in event STP.1"
    ::= { stpEventObjects1 6 }

stpEventObjects2 OBJECT-IDENTITY
    STATUS current
    DESCRIPTION
        "Event STP.2
        A topology change notification BPDU has been received from
        the specified MAC address."
    ::= { stpEventsGroup 2 }

stp2-source-address OBJECT-TYPE
    SYNTAX DisplayString
    MAX-ACCESS accessible-for-notify
    STATUS current
    DESCRIPTION
        "Parameter 'source-address' in event STP.2"
    ::= { stpEventObjects2 1 }

stp2-bridge-type OBJECT-TYPE
    SYNTAX DisplayString
    MAX-ACCESS accessible-for-notify
    STATUS current
    DESCRIPTION
        "Parameter 'bridge-type' in event STP.2"
    ::= { stpEventObjects2 2 }

stp2-bridge-instance OBJECT-TYPE
    SYNTAX Integer32
    MAX-ACCESS accessible-for-notify
    STATUS current
    DESCRIPTION
        "Parameter 'bridge-instance' in event STP.2"
    ::= { stpEventObjects2 3 }

stp2-bridge-port OBJECT-TYPE
    SYNTAX Integer32
    MAX-ACCESS accessible-for-notify
    STATUS current
    DESCRIPTION
        "Parameter 'bridge-port' in event STP.2"
    ::= { stpEventObjects2 4 }

stp2-interface OBJECT-TYPE
    SYNTAX DisplayString
    MAX-ACCESS accessible-for-notify
    STATUS current
    DESCRIPTION
        "Parameter 'interface' in event STP.2"
    ::= { stpEventObjects2 5 }

stp2-circuit-name OBJECT-TYPE
    SYNTAX DisplayString
    MAX-ACCESS accessible-for-notify
    STATUS current
    DESCRIPTION
        "Parameter 'circuit-name' in event STP.2"
    ::= { stpEventObjects2 6 }

stpEventObjects3 OBJECT-IDENTITY
    STATUS current
    DESCRIPTION
        "Event STP.3
        A BPDU with an undefined value in the BPDU Type field was received
        from the specified host. It will be ignored."
    ::= { stpEventsGroup 3 }

stp3-BDPU-type OBJECT-TYPE
    SYNTAX Integer32
    MAX-ACCESS accessible-for-notify
    STATUS current
    DESCRIPTION
        "Parameter 'BDPU-type' in event STP.3"
    ::= { stpEventObjects3 1 }

stp3-source-address OBJECT-TYPE
    SYNTAX DisplayString
    MAX-ACCESS accessible-for-notify
    STATUS current
    DESCRIPTION
        "Parameter 'source-address' in event STP.3"
    ::= { stpEventObjects3 2 }

stp3-bridge-type OBJECT-TYPE
    SYNTAX DisplayString
    MAX-ACCESS accessible-for-notify
    STATUS current
    DESCRIPTION
        "Parameter 'bridge-type' in event STP.3"
    ::= { stpEventObjects3 3 }

stp3-bridge-instance OBJECT-TYPE
    SYNTAX Integer32
    MAX-ACCESS accessible-for-notify
    STATUS current
    DESCRIPTION
        "Parameter 'bridge-instance' in event STP.3"
    ::= { stpEventObjects3 4 }

stp3-bridge-port OBJECT-TYPE
    SYNTAX Integer32
    MAX-ACCESS accessible-for-notify
    STATUS current
    DESCRIPTION
        "Parameter 'bridge-port' in event STP.3"
    ::= { stpEventObjects3 5 }

stp3-interface OBJECT-TYPE
    SYNTAX DisplayString
    MAX-ACCESS accessible-for-notify
    STATUS current
    DESCRIPTION
        "Parameter 'interface' in event STP.3"
    ::= { stpEventObjects3 6 }

stp3-circuit-name OBJECT-TYPE
    SYNTAX DisplayString
    MAX-ACCESS accessible-for-notify
    STATUS current
    DESCRIPTION
        "Parameter 'circuit-name' in event STP.3"
    ::= { stpEventObjects3 7 }

stpEventObjects4 OBJECT-IDENTITY
    STATUS current
    DESCRIPTION
        "Event STP.4
        A configuration BPDU has been received with a Protocol Identifier
        that is not 0000. It will be ignored."
    ::= { stpEventsGroup 4 }

stp4-Protocol-Identifier OBJECT-TYPE
    SYNTAX Integer32
    MAX-ACCESS accessible-for-notify
    STATUS current
    DESCRIPTION
        "Parameter 'Protocol-Identifier' in event STP.4"
    ::= { stpEventObjects4 1 }

stp4-source-address OBJECT-TYPE
    SYNTAX DisplayString
    MAX-ACCESS accessible-for-notify
    STATUS current
    DESCRIPTION
        "Parameter 'source-address' in event STP.4"
    ::= { stpEventObjects4 2 }

stp4-bridge-type OBJECT-TYPE
    SYNTAX DisplayString
    MAX-ACCESS accessible-for-notify
    STATUS current
    DESCRIPTION
        "Parameter 'bridge-type' in event STP.4"
    ::= { stpEventObjects4 3 }

stp4-bridge-instance OBJECT-TYPE
    SYNTAX Integer32
    MAX-ACCESS accessible-for-notify
    STATUS current
    DESCRIPTION
        "Parameter 'bridge-instance' in event STP.4"
    ::= { stpEventObjects4 4 }

stp4-bridge-port OBJECT-TYPE
    SYNTAX Integer32
    MAX-ACCESS accessible-for-notify
    STATUS current
    DESCRIPTION
        "Parameter 'bridge-port' in event STP.4"
    ::= { stpEventObjects4 5 }

stp4-interface OBJECT-TYPE
    SYNTAX DisplayString
    MAX-ACCESS accessible-for-notify
    STATUS current
    DESCRIPTION
        "Parameter 'interface' in event STP.4"
    ::= { stpEventObjects4 6 }

stp4-circuit-name OBJECT-TYPE
    SYNTAX DisplayString
    MAX-ACCESS accessible-for-notify
    STATUS current
    DESCRIPTION
        "Parameter 'circuit-name' in event STP.4"
    ::= { stpEventObjects4 7 }

stpEventObjects5 OBJECT-IDENTITY
    STATUS current
    DESCRIPTION
        "Event STP.5
        A configuration BPDU has been received with a Protocol Version
        Identifier that is not 00. It will be ignored."
    ::= { stpEventsGroup 5 }

stp5-Protocol-Version-Identifier OBJECT-TYPE
    SYNTAX Integer32
    MAX-ACCESS accessible-for-notify
    STATUS current
    DESCRIPTION
        "Parameter 'Protocol-Version-Identifier' in event STP.5"
    ::= { stpEventObjects5 1 }

stp5-source-address OBJECT-TYPE
    SYNTAX DisplayString
    MAX-ACCESS accessible-for-notify
    STATUS current
    DESCRIPTION
        "Parameter 'source-address' in event STP.5"
    ::= { stpEventObjects5 2 }

stp5-bridge-type OBJECT-TYPE
    SYNTAX DisplayString
    MAX-ACCESS accessible-for-notify
    STATUS current
    DESCRIPTION
        "Parameter 'bridge-type' in event STP.5"
    ::= { stpEventObjects5 3 }

stp5-bridge-instance OBJECT-TYPE
    SYNTAX Integer32
    MAX-ACCESS accessible-for-notify
    STATUS current
    DESCRIPTION
        "Parameter 'bridge-instance' in event STP.5"
    ::= { stpEventObjects5 4 }

stp5-bridge-port OBJECT-TYPE
    SYNTAX Integer32
    MAX-ACCESS accessible-for-notify
    STATUS current
    DESCRIPTION
        "Parameter 'bridge-port' in event STP.5"
    ::= { stpEventObjects5 5 }

stp5-interface OBJECT-TYPE
    SYNTAX DisplayString
    MAX-ACCESS accessible-for-notify
    STATUS current
    DESCRIPTION
        "Parameter 'interface' in event STP.5"
    ::= { stpEventObjects5 6 }

stp5-circuit-name OBJECT-TYPE
    SYNTAX DisplayString
    MAX-ACCESS accessible-for-notify
    STATUS current
    DESCRIPTION
        "Parameter 'circuit-name' in event STP.5"
    ::= { stpEventObjects5 7 }

stpEventObjects6 OBJECT-IDENTITY
    STATUS current
    DESCRIPTION
        "Event STP.6
        A configuration BPDU has been received which is less than 35 bytes
        in length. It will be ignored."
    ::= { stpEventsGroup 6 }

stp6-length OBJECT-TYPE
    SYNTAX Integer32
    MAX-ACCESS accessible-for-notify
    STATUS current
    DESCRIPTION
        "Parameter 'length' in event STP.6"
    ::= { stpEventObjects6 1 }

stp6-source-address OBJECT-TYPE
    SYNTAX DisplayString
    MAX-ACCESS accessible-for-notify
    STATUS current
    DESCRIPTION
        "Parameter 'source-address' in event STP.6"
    ::= { stpEventObjects6 2 }

stp6-bridge-type OBJECT-TYPE
    SYNTAX DisplayString
    MAX-ACCESS accessible-for-notify
    STATUS current
    DESCRIPTION
        "Parameter 'bridge-type' in event STP.6"
    ::= { stpEventObjects6 3 }

stp6-bridge-instance OBJECT-TYPE
    SYNTAX Integer32
    MAX-ACCESS accessible-for-notify
    STATUS current
    DESCRIPTION
        "Parameter 'bridge-instance' in event STP.6"
    ::= { stpEventObjects6 4 }

stp6-bridge-port OBJECT-TYPE
    SYNTAX Integer32
    MAX-ACCESS accessible-for-notify
    STATUS current
    DESCRIPTION
        "Parameter 'bridge-port' in event STP.6"
    ::= { stpEventObjects6 5 }

stp6-interface OBJECT-TYPE
    SYNTAX DisplayString
    MAX-ACCESS accessible-for-notify
    STATUS current
    DESCRIPTION
        "Parameter 'interface' in event STP.6"
    ::= { stpEventObjects6 6 }

stp6-circuit-name OBJECT-TYPE
    SYNTAX DisplayString
    MAX-ACCESS accessible-for-notify
    STATUS current
    DESCRIPTION
        "Parameter 'circuit-name' in event STP.6"
    ::= { stpEventObjects6 7 }

stpEventObjects7 OBJECT-IDENTITY
    STATUS current
    DESCRIPTION
        "Event STP.7
        A configuration BPDU has been received which has undefined bits set
        in the flags field. It will be ignored."
    ::= { stpEventsGroup 7 }

stp7-flags OBJECT-TYPE
    SYNTAX Integer32
    MAX-ACCESS accessible-for-notify
    STATUS current
    DESCRIPTION
        "Parameter 'flags' in event STP.7"
    ::= { stpEventObjects7 1 }

stp7-source-address OBJECT-TYPE
    SYNTAX DisplayString
    MAX-ACCESS accessible-for-notify
    STATUS current
    DESCRIPTION
        "Parameter 'source-address' in event STP.7"
    ::= { stpEventObjects7 2 }

stp7-bridge-type OBJECT-TYPE
    SYNTAX DisplayString
    MAX-ACCESS accessible-for-notify
    STATUS current
    DESCRIPTION
        "Parameter 'bridge-type' in event STP.7"
    ::= { stpEventObjects7 3 }

stp7-bridge-instance OBJECT-TYPE
    SYNTAX Integer32
    MAX-ACCESS accessible-for-notify
    STATUS current
    DESCRIPTION
        "Parameter 'bridge-instance' in event STP.7"
    ::= { stpEventObjects7 4 }

stp7-bridge-port OBJECT-TYPE
    SYNTAX Integer32
    MAX-ACCESS accessible-for-notify
    STATUS current
    DESCRIPTION
        "Parameter 'bridge-port' in event STP.7"
    ::= { stpEventObjects7 5 }

stp7-interface OBJECT-TYPE
    SYNTAX DisplayString
    MAX-ACCESS accessible-for-notify
    STATUS current
    DESCRIPTION
        "Parameter 'interface' in event STP.7"
    ::= { stpEventObjects7 6 }

stp7-circuit-name OBJECT-TYPE
    SYNTAX DisplayString
    MAX-ACCESS accessible-for-notify
    STATUS current
    DESCRIPTION
        "Parameter 'circuit-name' in event STP.7"
    ::= { stpEventObjects7 7 }

stpEventObjects8 OBJECT-IDENTITY
    STATUS current
    DESCRIPTION
        "Event STP.8
        A topology change notificaton BPDU has been received that is less than
        4 bytes in length. It will be ignored."
    ::= { stpEventsGroup 8 }

stp8-length OBJECT-TYPE
    SYNTAX Integer32
    MAX-ACCESS accessible-for-notify
    STATUS current
    DESCRIPTION
        "Parameter 'length' in event STP.8"
    ::= { stpEventObjects8 1 }

stp8-source-address OBJECT-TYPE
    SYNTAX DisplayString
    MAX-ACCESS accessible-for-notify
    STATUS current
    DESCRIPTION
        "Parameter 'source-address' in event STP.8"
    ::= { stpEventObjects8 2 }

stp8-bridge-type OBJECT-TYPE
    SYNTAX DisplayString
    MAX-ACCESS accessible-for-notify
    STATUS current
    DESCRIPTION
        "Parameter 'bridge-type' in event STP.8"
    ::= { stpEventObjects8 3 }

stp8-bridge-instance OBJECT-TYPE
    SYNTAX Integer32
    MAX-ACCESS accessible-for-notify
    STATUS current
    DESCRIPTION
        "Parameter 'bridge-instance' in event STP.8"
    ::= { stpEventObjects8 4 }

stp8-bridge-port OBJECT-TYPE
    SYNTAX Integer32
    MAX-ACCESS accessible-for-notify
    STATUS current
    DESCRIPTION
        "Parameter 'bridge-port' in event STP.8"
    ::= { stpEventObjects8 5 }

stp8-interface OBJECT-TYPE
    SYNTAX DisplayString
    MAX-ACCESS accessible-for-notify
    STATUS current
    DESCRIPTION
        "Parameter 'interface' in event STP.8"
    ::= { stpEventObjects8 6 }

stp8-circuit-name OBJECT-TYPE
    SYNTAX DisplayString
    MAX-ACCESS accessible-for-notify
    STATUS current
    DESCRIPTION
        "Parameter 'circuit-name' in event STP.8"
    ::= { stpEventObjects8 7 }

stpEventObjects9 OBJECT-IDENTITY
    STATUS current
    DESCRIPTION
        "Event STP.9
        No packet buffer was available to construct and send a BDPU on the
        specified port."
    ::= { stpEventsGroup 9 }

stp9-bridge-type OBJECT-TYPE
    SYNTAX DisplayString
    MAX-ACCESS accessible-for-notify
    STATUS current
    DESCRIPTION
        "Parameter 'bridge-type' in event STP.9"
    ::= { stpEventObjects9 1 }

stp9-bridge-instance OBJECT-TYPE
    SYNTAX Integer32
    MAX-ACCESS accessible-for-notify
    STATUS current
    DESCRIPTION
        "Parameter 'bridge-instance' in event STP.9"
    ::= { stpEventObjects9 2 }

stp9-bridge-port OBJECT-TYPE
    SYNTAX Integer32
    MAX-ACCESS accessible-for-notify
    STATUS current
    DESCRIPTION
        "Parameter 'bridge-port' in event STP.9"
    ::= { stpEventObjects9 3 }

stp9-interface OBJECT-TYPE
    SYNTAX DisplayString
    MAX-ACCESS accessible-for-notify
    STATUS current
    DESCRIPTION
        "Parameter 'interface' in event STP.9"
    ::= { stpEventObjects9 4 }

stp9-circuit-name OBJECT-TYPE
    SYNTAX DisplayString
    MAX-ACCESS accessible-for-notify
    STATUS current
    DESCRIPTION
        "Parameter 'circuit-name' in event STP.9"
    ::= { stpEventObjects9 5 }

stpEventObjects10 OBJECT-IDENTITY
    STATUS current
    DESCRIPTION
        "Event STP.10
        A Configuration BPDU will be sent on the specified port.
        This is done normally on a periodic basis as part of the
        Spanning Tree Protocol.
        The flags field in this BPDU is zero, e.g., neither the Topology Change
        or the Topology Change Acknowledgement bits are set."
    ::= { stpEventsGroup 10 }

stp10-bridge-type OBJECT-TYPE
    SYNTAX DisplayString
    MAX-ACCESS accessible-for-notify
    STATUS current
    DESCRIPTION
        "Parameter 'bridge-type' in event STP.10"
    ::= { stpEventObjects10 1 }

stp10-bridge-instance OBJECT-TYPE
    SYNTAX Integer32
    MAX-ACCESS accessible-for-notify
    STATUS current
    DESCRIPTION
        "Parameter 'bridge-instance' in event STP.10"
    ::= { stpEventObjects10 2 }

stp10-bridge-port OBJECT-TYPE
    SYNTAX Integer32
    MAX-ACCESS accessible-for-notify
    STATUS current
    DESCRIPTION
        "Parameter 'bridge-port' in event STP.10"
    ::= { stpEventObjects10 3 }

stp10-interface OBJECT-TYPE
    SYNTAX DisplayString
    MAX-ACCESS accessible-for-notify
    STATUS current
    DESCRIPTION
        "Parameter 'interface' in event STP.10"
    ::= { stpEventObjects10 4 }

stp10-circuit-name OBJECT-TYPE
    SYNTAX DisplayString
    MAX-ACCESS accessible-for-notify
    STATUS current
    DESCRIPTION
        "Parameter 'circuit-name' in event STP.10"
    ::= { stpEventObjects10 5 }

stpEventObjects11 OBJECT-IDENTITY
    STATUS current
    DESCRIPTION
        "Event STP.11
        A Configuration BPDU will be sent on the specified port.
        This is done normally on a periodic basis as part of the
        Spanning Tree Protocol. TC will be displayed if the Topology Change bit
        is set in the Flags byte of the BPDU, TCA will be displayed if
        the Topology Change Acknowledge bit is set in the Flags byte."
    ::= { stpEventsGroup 11 }

stp11-TC OBJECT-TYPE
    SYNTAX DisplayString
    MAX-ACCESS accessible-for-notify
    STATUS current
    DESCRIPTION
        "Parameter 'TC' in event STP.11"
    ::= { stpEventObjects11 1 }

stp11-TCA OBJECT-TYPE
    SYNTAX DisplayString
    MAX-ACCESS accessible-for-notify
    STATUS current
    DESCRIPTION
        "Parameter 'TCA' in event STP.11"
    ::= { stpEventObjects11 2 }

stp11-bridge-type OBJECT-TYPE
    SYNTAX DisplayString
    MAX-ACCESS accessible-for-notify
    STATUS current
    DESCRIPTION
        "Parameter 'bridge-type' in event STP.11"
    ::= { stpEventObjects11 3 }

stp11-bridge-instance OBJECT-TYPE
    SYNTAX Integer32
    MAX-ACCESS accessible-for-notify
    STATUS current
    DESCRIPTION
        "Parameter 'bridge-instance' in event STP.11"
    ::= { stpEventObjects11 4 }

stp11-bridge-port OBJECT-TYPE
    SYNTAX Integer32
    MAX-ACCESS accessible-for-notify
    STATUS current
    DESCRIPTION
        "Parameter 'bridge-port' in event STP.11"
    ::= { stpEventObjects11 5 }

stp11-interface OBJECT-TYPE
    SYNTAX DisplayString
    MAX-ACCESS accessible-for-notify
    STATUS current
    DESCRIPTION
        "Parameter 'interface' in event STP.11"
    ::= { stpEventObjects11 6 }

stp11-circuit-name OBJECT-TYPE
    SYNTAX DisplayString
    MAX-ACCESS accessible-for-notify
    STATUS current
    DESCRIPTION
        "Parameter 'circuit-name' in event STP.11"
    ::= { stpEventObjects11 7 }

stpEventObjects12 OBJECT-IDENTITY
    STATUS current
    DESCRIPTION
        "Event STP.12
        A Topology Change Notification BPDU will be sent on the specified port.
        These are sent on the root port of non-root ports when they detect
        a topology change in the spanning tree."
    ::= { stpEventsGroup 12 }

stp12-bridge-type OBJECT-TYPE
    SYNTAX DisplayString
    MAX-ACCESS accessible-for-notify
    STATUS current
    DESCRIPTION
        "Parameter 'bridge-type' in event STP.12"
    ::= { stpEventObjects12 1 }

stp12-bridge-instance OBJECT-TYPE
    SYNTAX Integer32
    MAX-ACCESS accessible-for-notify
    STATUS current
    DESCRIPTION
        "Parameter 'bridge-instance' in event STP.12"
    ::= { stpEventObjects12 2 }

stp12-bridge-port OBJECT-TYPE
    SYNTAX Integer32
    MAX-ACCESS accessible-for-notify
    STATUS current
    DESCRIPTION
        "Parameter 'bridge-port' in event STP.12"
    ::= { stpEventObjects12 3 }

stp12-interface OBJECT-TYPE
    SYNTAX DisplayString
    MAX-ACCESS accessible-for-notify
    STATUS current
    DESCRIPTION
        "Parameter 'interface' in event STP.12"
    ::= { stpEventObjects12 4 }

stp12-circuit-name OBJECT-TYPE
    SYNTAX DisplayString
    MAX-ACCESS accessible-for-notify
    STATUS current
    DESCRIPTION
        "Parameter 'circuit-name' in event STP.12"
    ::= { stpEventObjects12 5 }

stpEventObjects13 OBJECT-IDENTITY
    STATUS current
    DESCRIPTION
        "Event STP.13
        The attempt to queue a BPDU for transmission on the specified port
        failed."
    ::= { stpEventsGroup 13 }

stp13-reason-code OBJECT-TYPE
    SYNTAX Integer32
    MAX-ACCESS accessible-for-notify
    STATUS current
    DESCRIPTION
        "Parameter 'reason-code' in event STP.13"
    ::= { stpEventObjects13 1 }

stp13-bridge-type OBJECT-TYPE
    SYNTAX DisplayString
    MAX-ACCESS accessible-for-notify
    STATUS current
    DESCRIPTION
        "Parameter 'bridge-type' in event STP.13"
    ::= { stpEventObjects13 2 }

stp13-bridge-instance OBJECT-TYPE
    SYNTAX Integer32
    MAX-ACCESS accessible-for-notify
    STATUS current
    DESCRIPTION
        "Parameter 'bridge-instance' in event STP.13"
    ::= { stpEventObjects13 3 }

stp13-bridge-port OBJECT-TYPE
    SYNTAX Integer32
    MAX-ACCESS accessible-for-notify
    STATUS current
    DESCRIPTION
        "Parameter 'bridge-port' in event STP.13"
    ::= { stpEventObjects13 4 }

stp13-interface OBJECT-TYPE
    SYNTAX DisplayString
    MAX-ACCESS accessible-for-notify
    STATUS current
    DESCRIPTION
        "Parameter 'interface' in event STP.13"
    ::= { stpEventObjects13 5 }

stp13-circuit-name OBJECT-TYPE
    SYNTAX DisplayString
    MAX-ACCESS accessible-for-notify
    STATUS current
    DESCRIPTION
        "Parameter 'circuit-name' in event STP.13"
    ::= { stpEventObjects13 6 }

stpEventObjects14 OBJECT-IDENTITY
    STATUS current
    DESCRIPTION
        "Event STP.14
        This port has just been placed in Blocking state. This is a change in
        the topology, so this bridge detects a topology change.
        This will in turn cause topology change notifications to be sent."
    ::= { stpEventsGroup 14 }

stp14-bridge-type OBJECT-TYPE
    SYNTAX DisplayString
    MAX-ACCESS accessible-for-notify
    STATUS current
    DESCRIPTION
        "Parameter 'bridge-type' in event STP.14"
    ::= { stpEventObjects14 1 }

stp14-bridge-instance OBJECT-TYPE
    SYNTAX Integer32
    MAX-ACCESS accessible-for-notify
    STATUS current
    DESCRIPTION
        "Parameter 'bridge-instance' in event STP.14"
    ::= { stpEventObjects14 2 }

stp14-bridge-port OBJECT-TYPE
    SYNTAX Integer32
    MAX-ACCESS accessible-for-notify
    STATUS current
    DESCRIPTION
        "Parameter 'bridge-port' in event STP.14"
    ::= { stpEventObjects14 3 }

stp14-interface OBJECT-TYPE
    SYNTAX DisplayString
    MAX-ACCESS accessible-for-notify
    STATUS current
    DESCRIPTION
        "Parameter 'interface' in event STP.14"
    ::= { stpEventObjects14 4 }

stp14-circuit-name OBJECT-TYPE
    SYNTAX DisplayString
    MAX-ACCESS accessible-for-notify
    STATUS current
    DESCRIPTION
        "Parameter 'circuit-name' in event STP.14"
    ::= { stpEventObjects14 5 }

stpEventObjects15 OBJECT-IDENTITY
    STATUS current
    DESCRIPTION
        "Event STP.15
        A topology change notification has been received on this port, and
        this port is the designated port on its LAN. This causes the protocol
        to enter topology change notification state.
        The topology change will be acknowledged towards the sender, and
        propogated towards the root."
    ::= { stpEventsGroup 15 }

stp15-bridge-type OBJECT-TYPE
    SYNTAX DisplayString
    MAX-ACCESS accessible-for-notify
    STATUS current
    DESCRIPTION
        "Parameter 'bridge-type' in event STP.15"
    ::= { stpEventObjects15 1 }

stp15-bridge-instance OBJECT-TYPE
    SYNTAX Integer32
    MAX-ACCESS accessible-for-notify
    STATUS current
    DESCRIPTION
        "Parameter 'bridge-instance' in event STP.15"
    ::= { stpEventObjects15 2 }

stp15-bridge-port OBJECT-TYPE
    SYNTAX Integer32
    MAX-ACCESS accessible-for-notify
    STATUS current
    DESCRIPTION
        "Parameter 'bridge-port' in event STP.15"
    ::= { stpEventObjects15 3 }

stp15-interface OBJECT-TYPE
    SYNTAX DisplayString
    MAX-ACCESS accessible-for-notify
    STATUS current
    DESCRIPTION
        "Parameter 'interface' in event STP.15"
    ::= { stpEventObjects15 4 }

stp15-circuit-name OBJECT-TYPE
    SYNTAX DisplayString
    MAX-ACCESS accessible-for-notify
    STATUS current
    DESCRIPTION
        "Parameter 'circuit-name' in event STP.15"
    ::= { stpEventObjects15 5 }

stpEventObjects16 OBJECT-IDENTITY
    STATUS current
    DESCRIPTION
        "Event STP.16
        This bridge has just selected itself as the root of the spanning tree
        when it previously had not been. This causes the bridge to enter
        topology change notification state."
    ::= { stpEventsGroup 16 }

stp16-bridge-type OBJECT-TYPE
    SYNTAX DisplayString
    MAX-ACCESS accessible-for-notify
    STATUS current
    DESCRIPTION
        "Parameter 'bridge-type' in event STP.16"
    ::= { stpEventObjects16 1 }

stp16-bridge-instance OBJECT-TYPE
    SYNTAX Integer32
    MAX-ACCESS accessible-for-notify
    STATUS current
    DESCRIPTION
        "Parameter 'bridge-instance' in event STP.16"
    ::= { stpEventObjects16 2 }

stpEventObjects17 OBJECT-IDENTITY
    STATUS current
    DESCRIPTION
        "Event STP.17
        A topology change acknowledgement has been detected on the specified
        port. This port is the root port of the bridge."
    ::= { stpEventsGroup 17 }

stp17-bridge-type OBJECT-TYPE
    SYNTAX DisplayString
    MAX-ACCESS accessible-for-notify
    STATUS current
    DESCRIPTION
        "Parameter 'bridge-type' in event STP.17"
    ::= { stpEventObjects17 1 }

stp17-bridge-instance OBJECT-TYPE
    SYNTAX Integer32
    MAX-ACCESS accessible-for-notify
    STATUS current
    DESCRIPTION
        "Parameter 'bridge-instance' in event STP.17"
    ::= { stpEventObjects17 2 }

stp17-bridge-port OBJECT-TYPE
    SYNTAX Integer32
    MAX-ACCESS accessible-for-notify
    STATUS current
    DESCRIPTION
        "Parameter 'bridge-port' in event STP.17"
    ::= { stpEventObjects17 3 }

stp17-interface OBJECT-TYPE
    SYNTAX DisplayString
    MAX-ACCESS accessible-for-notify
    STATUS current
    DESCRIPTION
        "Parameter 'interface' in event STP.17"
    ::= { stpEventObjects17 4 }

stp17-circuit-name OBJECT-TYPE
    SYNTAX DisplayString
    MAX-ACCESS accessible-for-notify
    STATUS current
    DESCRIPTION
        "Parameter 'circuit-name' in event STP.17"
    ::= { stpEventObjects17 5 }

stpEventObjects18 OBJECT-IDENTITY
    STATUS current
    DESCRIPTION
        "Event STP.18
        A topology change notification is being acknowledged on the
        specified port. This is done when a topology change notification
        is received on a port that is the designated port for that LAN."
    ::= { stpEventsGroup 18 }

stp18-bridge-type OBJECT-TYPE
    SYNTAX DisplayString
    MAX-ACCESS accessible-for-notify
    STATUS current
    DESCRIPTION
        "Parameter 'bridge-type' in event STP.18"
    ::= { stpEventObjects18 1 }

stp18-bridge-instance OBJECT-TYPE
    SYNTAX Integer32
    MAX-ACCESS accessible-for-notify
    STATUS current
    DESCRIPTION
        "Parameter 'bridge-instance' in event STP.18"
    ::= { stpEventObjects18 2 }

stp18-bridge-port OBJECT-TYPE
    SYNTAX Integer32
    MAX-ACCESS accessible-for-notify
    STATUS current
    DESCRIPTION
        "Parameter 'bridge-port' in event STP.18"
    ::= { stpEventObjects18 3 }

stp18-interface OBJECT-TYPE
    SYNTAX DisplayString
    MAX-ACCESS accessible-for-notify
    STATUS current
    DESCRIPTION
        "Parameter 'interface' in event STP.18"
    ::= { stpEventObjects18 4 }

stp18-circuit-name OBJECT-TYPE
    SYNTAX DisplayString
    MAX-ACCESS accessible-for-notify
    STATUS current
    DESCRIPTION
        "Parameter 'circuit-name' in event STP.18"
    ::= { stpEventObjects18 5 }

stpEventObjects19 OBJECT-IDENTITY
    STATUS current
    DESCRIPTION
        "Event STP.19
        The Topology Change timer expired. This bridge will cease sending
        topology change notification BPDU's on its root port."
    ::= { stpEventsGroup 19 }

stp19-bridge-type OBJECT-TYPE
    SYNTAX DisplayString
    MAX-ACCESS accessible-for-notify
    STATUS current
    DESCRIPTION
        "Parameter 'bridge-type' in event STP.19"
    ::= { stpEventObjects19 1 }

stp19-bridge-instance OBJECT-TYPE
    SYNTAX Integer32
    MAX-ACCESS accessible-for-notify
    STATUS current
    DESCRIPTION
        "Parameter 'bridge-instance' in event STP.19"
    ::= { stpEventObjects19 2 }

stpEventObjects20 OBJECT-IDENTITY
    STATUS current
    DESCRIPTION
        "Event STP.20
        The Topology Change timer expired. This bridge, which is the root,
        will cease sending the Topology Change in its Configuration BPDUs."
    ::= { stpEventsGroup 20 }

stp20-bridge-type OBJECT-TYPE
    SYNTAX DisplayString
    MAX-ACCESS accessible-for-notify
    STATUS current
    DESCRIPTION
        "Parameter 'bridge-type' in event STP.20"
    ::= { stpEventObjects20 1 }

stp20-bridge-instance OBJECT-TYPE
    SYNTAX Integer32
    MAX-ACCESS accessible-for-notify
    STATUS current
    DESCRIPTION
        "Parameter 'bridge-instance' in event STP.20"
    ::= { stpEventObjects20 2 }

stpEventObjects21 OBJECT-IDENTITY
    STATUS current
    DESCRIPTION
        "Event STP.21
        The message age timer has expired on this port. The bridge will attempt
        to become the root. It will become the designated port on that LAN."
    ::= { stpEventsGroup 21 }

stp21-bridge-type OBJECT-TYPE
    SYNTAX DisplayString
    MAX-ACCESS accessible-for-notify
    STATUS current
    DESCRIPTION
        "Parameter 'bridge-type' in event STP.21"
    ::= { stpEventObjects21 1 }

stp21-bridge-instance OBJECT-TYPE
    SYNTAX Integer32
    MAX-ACCESS accessible-for-notify
    STATUS current
    DESCRIPTION
        "Parameter 'bridge-instance' in event STP.21"
    ::= { stpEventObjects21 2 }

stp21-bridge-port OBJECT-TYPE
    SYNTAX Integer32
    MAX-ACCESS accessible-for-notify
    STATUS current
    DESCRIPTION
        "Parameter 'bridge-port' in event STP.21"
    ::= { stpEventObjects21 3 }

stp21-interface OBJECT-TYPE
    SYNTAX DisplayString
    MAX-ACCESS accessible-for-notify
    STATUS current
    DESCRIPTION
        "Parameter 'interface' in event STP.21"
    ::= { stpEventObjects21 4 }

stp21-circuit-name OBJECT-TYPE
    SYNTAX DisplayString
    MAX-ACCESS accessible-for-notify
    STATUS current
    DESCRIPTION
        "Parameter 'circuit-name' in event STP.21"
    ::= { stpEventObjects21 5 }

stpEventObjects22 OBJECT-IDENTITY
    STATUS current
    DESCRIPTION
        "Event STP.22
        The hello timer has expired on this port. Configuration BPDUs will be
        sent on all ports."
    ::= { stpEventsGroup 22 }

stp22-bridge-type OBJECT-TYPE
    SYNTAX DisplayString
    MAX-ACCESS accessible-for-notify
    STATUS current
    DESCRIPTION
        "Parameter 'bridge-type' in event STP.22"
    ::= { stpEventObjects22 1 }

stp22-bridge-instance OBJECT-TYPE
    SYNTAX Integer32
    MAX-ACCESS accessible-for-notify
    STATUS current
    DESCRIPTION
        "Parameter 'bridge-instance' in event STP.22"
    ::= { stpEventObjects22 2 }

stpEventObjects23 OBJECT-IDENTITY
    STATUS current
    DESCRIPTION
        "Event STP.23
        Stopping the message age timer on this port because it is
        the designated port on its LAN."
    ::= { stpEventsGroup 23 }

stp23-bridge-type OBJECT-TYPE
    SYNTAX DisplayString
    MAX-ACCESS accessible-for-notify
    STATUS current
    DESCRIPTION
        "Parameter 'bridge-type' in event STP.23"
    ::= { stpEventObjects23 1 }

stp23-bridge-instance OBJECT-TYPE
    SYNTAX Integer32
    MAX-ACCESS accessible-for-notify
    STATUS current
    DESCRIPTION
        "Parameter 'bridge-instance' in event STP.23"
    ::= { stpEventObjects23 2 }

stp23-bridge-port OBJECT-TYPE
    SYNTAX Integer32
    MAX-ACCESS accessible-for-notify
    STATUS current
    DESCRIPTION
        "Parameter 'bridge-port' in event STP.23"
    ::= { stpEventObjects23 3 }

stp23-interface OBJECT-TYPE
    SYNTAX DisplayString
    MAX-ACCESS accessible-for-notify
    STATUS current
    DESCRIPTION
        "Parameter 'interface' in event STP.23"
    ::= { stpEventObjects23 4 }

stp23-circuit-name OBJECT-TYPE
    SYNTAX DisplayString
    MAX-ACCESS accessible-for-notify
    STATUS current
    DESCRIPTION
        "Parameter 'circuit-name' in event STP.23"
    ::= { stpEventObjects23 5 }

stpEventObjects24 OBJECT-IDENTITY
    STATUS current
    DESCRIPTION
        "Event STP.24
        This bridge has just decided that it is no longer the root bridge of
        the spanning tree. The hello timer will also be cancelled."
    ::= { stpEventsGroup 24 }

stp24-bridge-type OBJECT-TYPE
    SYNTAX DisplayString
    MAX-ACCESS accessible-for-notify
    STATUS current
    DESCRIPTION
        "Parameter 'bridge-type' in event STP.24"
    ::= { stpEventObjects24 1 }

stp24-bridge-instance OBJECT-TYPE
    SYNTAX Integer32
    MAX-ACCESS accessible-for-notify
    STATUS current
    DESCRIPTION
        "Parameter 'bridge-instance' in event STP.24"
    ::= { stpEventObjects24 2 }

stpEventObjects25 OBJECT-IDENTITY
    STATUS current
    DESCRIPTION
        "Event STP.25
        Stopping the topology change timer because this bridge is no longer
        the root."
    ::= { stpEventsGroup 25 }

stp25-bridge-type OBJECT-TYPE
    SYNTAX DisplayString
    MAX-ACCESS accessible-for-notify
    STATUS current
    DESCRIPTION
        "Parameter 'bridge-type' in event STP.25"
    ::= { stpEventObjects25 1 }

stp25-bridge-instance OBJECT-TYPE
    SYNTAX Integer32
    MAX-ACCESS accessible-for-notify
    STATUS current
    DESCRIPTION
        "Parameter 'bridge-instance' in event STP.25"
    ::= { stpEventObjects25 2 }

stpEventObjects26 OBJECT-IDENTITY
    STATUS current
    DESCRIPTION
        "Event STP.26
        This bridge has just decided that it is the root bridge of
        the spanning tree. The hello timer will be started."
    ::= { stpEventsGroup 26 }

stp26-bridge-type OBJECT-TYPE
    SYNTAX DisplayString
    MAX-ACCESS accessible-for-notify
    STATUS current
    DESCRIPTION
        "Parameter 'bridge-type' in event STP.26"
    ::= { stpEventObjects26 1 }

stp26-bridge-instance OBJECT-TYPE
    SYNTAX Integer32
    MAX-ACCESS accessible-for-notify
    STATUS current
    DESCRIPTION
        "Parameter 'bridge-instance' in event STP.26"
    ::= { stpEventObjects26 2 }

stpEventObjects27 OBJECT-IDENTITY
    STATUS current
    DESCRIPTION
        "Event STP.27
        Starting the message age timer on this port."
    ::= { stpEventsGroup 27 }

stp27-bridge-type OBJECT-TYPE
    SYNTAX DisplayString
    MAX-ACCESS accessible-for-notify
    STATUS current
    DESCRIPTION
        "Parameter 'bridge-type' in event STP.27"
    ::= { stpEventObjects27 1 }

stp27-bridge-instance OBJECT-TYPE
    SYNTAX Integer32
    MAX-ACCESS accessible-for-notify
    STATUS current
    DESCRIPTION
        "Parameter 'bridge-instance' in event STP.27"
    ::= { stpEventObjects27 2 }

stp27-bridge-port OBJECT-TYPE
    SYNTAX Integer32
    MAX-ACCESS accessible-for-notify
    STATUS current
    DESCRIPTION
        "Parameter 'bridge-port' in event STP.27"
    ::= { stpEventObjects27 3 }

stp27-interface OBJECT-TYPE
    SYNTAX DisplayString
    MAX-ACCESS accessible-for-notify
    STATUS current
    DESCRIPTION
        "Parameter 'interface' in event STP.27"
    ::= { stpEventObjects27 4 }

stp27-circuit-name OBJECT-TYPE
    SYNTAX DisplayString
    MAX-ACCESS accessible-for-notify
    STATUS current
    DESCRIPTION
        "Parameter 'circuit-name' in event STP.27"
    ::= { stpEventObjects27 5 }

stpEventObjects28 OBJECT-IDENTITY
    STATUS current
    DESCRIPTION
        "Event STP.28
        This bridge is attempting to become the root bridge of
        the spanning tree. The hello timer will be started."
    ::= { stpEventsGroup 28 }

stp28-bridge-type OBJECT-TYPE
    SYNTAX DisplayString
    MAX-ACCESS accessible-for-notify
    STATUS current
    DESCRIPTION
        "Parameter 'bridge-type' in event STP.28"
    ::= { stpEventObjects28 1 }

stp28-bridge-instance OBJECT-TYPE
    SYNTAX Integer32
    MAX-ACCESS accessible-for-notify
    STATUS current
    DESCRIPTION
        "Parameter 'bridge-instance' in event STP.28"
    ::= { stpEventObjects28 2 }

stpEventObjects29 OBJECT-IDENTITY
    STATUS current
    DESCRIPTION
        "Event STP.29
        A configuration BPDU has been received from the specified MAC address,
        but the port is not participating in the Spanning Tree Protocol."
    ::= { stpEventsGroup 29 }

stp29-source-address OBJECT-TYPE
    SYNTAX DisplayString
    MAX-ACCESS accessible-for-notify
    STATUS current
    DESCRIPTION
        "Parameter 'source-address' in event STP.29"
    ::= { stpEventObjects29 1 }

stp29-bridge-type OBJECT-TYPE
    SYNTAX DisplayString
    MAX-ACCESS accessible-for-notify
    STATUS current
    DESCRIPTION
        "Parameter 'bridge-type' in event STP.29"
    ::= { stpEventObjects29 2 }

stp29-bridge-instance OBJECT-TYPE
    SYNTAX Integer32
    MAX-ACCESS accessible-for-notify
    STATUS current
    DESCRIPTION
        "Parameter 'bridge-instance' in event STP.29"
    ::= { stpEventObjects29 3 }

stp29-bridge-port OBJECT-TYPE
    SYNTAX Integer32
    MAX-ACCESS accessible-for-notify
    STATUS current
    DESCRIPTION
        "Parameter 'bridge-port' in event STP.29"
    ::= { stpEventObjects29 4 }

stp29-interface OBJECT-TYPE
    SYNTAX DisplayString
    MAX-ACCESS accessible-for-notify
    STATUS current
    DESCRIPTION
        "Parameter 'interface' in event STP.29"
    ::= { stpEventObjects29 5 }

stp29-circuit-name OBJECT-TYPE
    SYNTAX DisplayString
    MAX-ACCESS accessible-for-notify
    STATUS current
    DESCRIPTION
        "Parameter 'circuit-name' in event STP.29"
    ::= { stpEventObjects29 6 }

stpEventObjects30 OBJECT-IDENTITY
    STATUS current
    DESCRIPTION
        "Event STP.30
        A topology change notification BPDU has been received from
        the specified MAC address, but the port is not participating in
        the Spanning Tree Protocol."
    ::= { stpEventsGroup 30 }

stp30-source-address OBJECT-TYPE
    SYNTAX DisplayString
    MAX-ACCESS accessible-for-notify
    STATUS current
    DESCRIPTION
        "Parameter 'source-address' in event STP.30"
    ::= { stpEventObjects30 1 }

stp30-bridge-type OBJECT-TYPE
    SYNTAX DisplayString
    MAX-ACCESS accessible-for-notify
    STATUS current
    DESCRIPTION
        "Parameter 'bridge-type' in event STP.30"
    ::= { stpEventObjects30 2 }

stp30-bridge-instance OBJECT-TYPE
    SYNTAX Integer32
    MAX-ACCESS accessible-for-notify
    STATUS current
    DESCRIPTION
        "Parameter 'bridge-instance' in event STP.30"
    ::= { stpEventObjects30 3 }

stp30-bridge-port OBJECT-TYPE
    SYNTAX Integer32
    MAX-ACCESS accessible-for-notify
    STATUS current
    DESCRIPTION
        "Parameter 'bridge-port' in event STP.30"
    ::= { stpEventObjects30 4 }

stp30-interface OBJECT-TYPE
    SYNTAX DisplayString
    MAX-ACCESS accessible-for-notify
    STATUS current
    DESCRIPTION
        "Parameter 'interface' in event STP.30"
    ::= { stpEventObjects30 5 }

stp30-circuit-name OBJECT-TYPE
    SYNTAX DisplayString
    MAX-ACCESS accessible-for-notify
    STATUS current
    DESCRIPTION
        "Parameter 'circuit-name' in event STP.30"
    ::= { stpEventObjects30 6 }

stpEventObjects31 OBJECT-IDENTITY
    STATUS current
    DESCRIPTION
        "Event STP.31
        This bridge is declaring itself the designated port on the LAN connected
        to this port."
    ::= { stpEventsGroup 31 }

stp31-bridge-type OBJECT-TYPE
    SYNTAX DisplayString
    MAX-ACCESS accessible-for-notify
    STATUS current
    DESCRIPTION
        "Parameter 'bridge-type' in event STP.31"
    ::= { stpEventObjects31 1 }

stp31-bridge-instance OBJECT-TYPE
    SYNTAX Integer32
    MAX-ACCESS accessible-for-notify
    STATUS current
    DESCRIPTION
        "Parameter 'bridge-instance' in event STP.31"
    ::= { stpEventObjects31 2 }

stp31-bridge-port OBJECT-TYPE
    SYNTAX Integer32
    MAX-ACCESS accessible-for-notify
    STATUS current
    DESCRIPTION
        "Parameter 'bridge-port' in event STP.31"
    ::= { stpEventObjects31 3 }

stp31-interface OBJECT-TYPE
    SYNTAX DisplayString
    MAX-ACCESS accessible-for-notify
    STATUS current
    DESCRIPTION
        "Parameter 'interface' in event STP.31"
    ::= { stpEventObjects31 4 }

stp31-circuit-name OBJECT-TYPE
    SYNTAX DisplayString
    MAX-ACCESS accessible-for-notify
    STATUS current
    DESCRIPTION
        "Parameter 'circuit-name' in event STP.31"
    ::= { stpEventObjects31 5 }

stpEventObjects32 OBJECT-IDENTITY
    STATUS current
    DESCRIPTION
        "Event STP.32
        A Source Route Bridge BPDU or IEEE802.1D BPDU has been received,
        but the port is not participating in the SRB or IEEE802.1D Spanning
        Tree Protocol."
    ::= { stpEventsGroup 32 }

stp32-bpdu-type OBJECT-TYPE
    SYNTAX DisplayString
    MAX-ACCESS accessible-for-notify
    STATUS current
    DESCRIPTION
        "Parameter 'bpdu-type' in event STP.32"
    ::= { stpEventObjects32 1 }

stp32-bridge-port OBJECT-TYPE
    SYNTAX Integer32
    MAX-ACCESS accessible-for-notify
    STATUS current
    DESCRIPTION
        "Parameter 'bridge-port' in event STP.32"
    ::= { stpEventObjects32 2 }

stp32-interface OBJECT-TYPE
    SYNTAX DisplayString
    MAX-ACCESS accessible-for-notify
    STATUS current
    DESCRIPTION
        "Parameter 'interface' in event STP.32"
    ::= { stpEventObjects32 3 }

stp32-circuit-name OBJECT-TYPE
    SYNTAX DisplayString
    MAX-ACCESS accessible-for-notify
    STATUS current
    DESCRIPTION
        "Parameter 'circuit-name' in event STP.32"
    ::= { stpEventObjects32 4 }

stpEventObjects33 OBJECT-IDENTITY
    STATUS current
    DESCRIPTION
        "Event STP.33
        A BPDU has been received which is less than the minimum size needed
        in length. It will be ignored."
    ::= { stpEventsGroup 33 }

stp33-bpdu-type OBJECT-TYPE
    SYNTAX DisplayString
    MAX-ACCESS accessible-for-notify
    STATUS current
    DESCRIPTION
        "Parameter 'bpdu-type' in event STP.33"
    ::= { stpEventObjects33 1 }

stp33-length OBJECT-TYPE
    SYNTAX Integer32
    MAX-ACCESS accessible-for-notify
    STATUS current
    DESCRIPTION
        "Parameter 'length' in event STP.33"
    ::= { stpEventObjects33 2 }

stp33-source-address OBJECT-TYPE
    SYNTAX DisplayString
    MAX-ACCESS accessible-for-notify
    STATUS current
    DESCRIPTION
        "Parameter 'source-address' in event STP.33"
    ::= { stpEventObjects33 3 }

stp33-bridge-type OBJECT-TYPE
    SYNTAX DisplayString
    MAX-ACCESS accessible-for-notify
    STATUS current
    DESCRIPTION
        "Parameter 'bridge-type' in event STP.33"
    ::= { stpEventObjects33 4 }

stp33-bridge-instance OBJECT-TYPE
    SYNTAX Integer32
    MAX-ACCESS accessible-for-notify
    STATUS current
    DESCRIPTION
        "Parameter 'bridge-instance' in event STP.33"
    ::= { stpEventObjects33 5 }

stp33-bridge-port OBJECT-TYPE
    SYNTAX Integer32
    MAX-ACCESS accessible-for-notify
    STATUS current
    DESCRIPTION
        "Parameter 'bridge-port' in event STP.33"
    ::= { stpEventObjects33 6 }

stp33-interface OBJECT-TYPE
    SYNTAX DisplayString
    MAX-ACCESS accessible-for-notify
    STATUS current
    DESCRIPTION
        "Parameter 'interface' in event STP.33"
    ::= { stpEventObjects33 7 }

stp33-circuit-name OBJECT-TYPE
    SYNTAX DisplayString
    MAX-ACCESS accessible-for-notify
    STATUS current
    DESCRIPTION
        "Parameter 'circuit-name' in event STP.33"
    ::= { stpEventObjects33 8 }

stpEventObjects34 OBJECT-IDENTITY
    STATUS current
    DESCRIPTION
        "Event STP.34
        A BPDU has been received which is less than 4 bytes in length.
        It will be ignored."
    ::= { stpEventsGroup 34 }

stp34-length OBJECT-TYPE
    SYNTAX Integer32
    MAX-ACCESS accessible-for-notify
    STATUS current
    DESCRIPTION
        "Parameter 'length' in event STP.34"
    ::= { stpEventObjects34 1 }

stp34-source-address OBJECT-TYPE
    SYNTAX DisplayString
    MAX-ACCESS accessible-for-notify
    STATUS current
    DESCRIPTION
        "Parameter 'source-address' in event STP.34"
    ::= { stpEventObjects34 2 }

stp34-bridge-type OBJECT-TYPE
    SYNTAX DisplayString
    MAX-ACCESS accessible-for-notify
    STATUS current
    DESCRIPTION
        "Parameter 'bridge-type' in event STP.34"
    ::= { stpEventObjects34 3 }

stp34-bridge-instance OBJECT-TYPE
    SYNTAX Integer32
    MAX-ACCESS accessible-for-notify
    STATUS current
    DESCRIPTION
        "Parameter 'bridge-instance' in event STP.34"
    ::= { stpEventObjects34 4 }

stp34-bridge-port OBJECT-TYPE
    SYNTAX Integer32
    MAX-ACCESS accessible-for-notify
    STATUS current
    DESCRIPTION
        "Parameter 'bridge-port' in event STP.34"
    ::= { stpEventObjects34 5 }

stp34-interface OBJECT-TYPE
    SYNTAX DisplayString
    MAX-ACCESS accessible-for-notify
    STATUS current
    DESCRIPTION
        "Parameter 'interface' in event STP.34"
    ::= { stpEventObjects34 6 }

stp34-circuit-name OBJECT-TYPE
    SYNTAX DisplayString
    MAX-ACCESS accessible-for-notify
    STATUS current
    DESCRIPTION
        "Parameter 'circuit-name' in event STP.34"
    ::= { stpEventObjects34 7 }

stpEventObjects35 OBJECT-IDENTITY
    STATUS current
    DESCRIPTION
        "Event STP.35
        A BPDU has been received with a message age that is not less than its
        max age parameter. It will be ignored."
    ::= { stpEventsGroup 35 }

stp35-bpdu-type OBJECT-TYPE
    SYNTAX DisplayString
    MAX-ACCESS accessible-for-notify
    STATUS current
    DESCRIPTION
        "Parameter 'bpdu-type' in event STP.35"
    ::= { stpEventObjects35 1 }

stp35-msg-age-sc OBJECT-TYPE
    SYNTAX Integer32
    MAX-ACCESS accessible-for-notify
    STATUS current
    DESCRIPTION
        "Parameter 'msg-age-sc' in event STP.35"
    ::= { stpEventObjects35 2 }

stp35-msg-age-fr OBJECT-TYPE
    SYNTAX Integer32
    MAX-ACCESS accessible-for-notify
    STATUS current
    DESCRIPTION
        "Parameter 'msg-age-fr' in event STP.35"
    ::= { stpEventObjects35 3 }

stp35-max-age-sc OBJECT-TYPE
    SYNTAX Integer32
    MAX-ACCESS accessible-for-notify
    STATUS current
    DESCRIPTION
        "Parameter 'max-age-sc' in event STP.35"
    ::= { stpEventObjects35 4 }

stp35-max-age-fr OBJECT-TYPE
    SYNTAX Integer32
    MAX-ACCESS accessible-for-notify
    STATUS current
    DESCRIPTION
        "Parameter 'max-age-fr' in event STP.35"
    ::= { stpEventObjects35 5 }

stp35-source-address OBJECT-TYPE
    SYNTAX DisplayString
    MAX-ACCESS accessible-for-notify
    STATUS current
    DESCRIPTION
        "Parameter 'source-address' in event STP.35"
    ::= { stpEventObjects35 6 }

stp35-bridge-type OBJECT-TYPE
    SYNTAX DisplayString
    MAX-ACCESS accessible-for-notify
    STATUS current
    DESCRIPTION
        "Parameter 'bridge-type' in event STP.35"
    ::= { stpEventObjects35 7 }

stp35-bridge-instance OBJECT-TYPE
    SYNTAX Integer32
    MAX-ACCESS accessible-for-notify
    STATUS current
    DESCRIPTION
        "Parameter 'bridge-instance' in event STP.35"
    ::= { stpEventObjects35 8 }

stp35-bridge-port OBJECT-TYPE
    SYNTAX Integer32
    MAX-ACCESS accessible-for-notify
    STATUS current
    DESCRIPTION
        "Parameter 'bridge-port' in event STP.35"
    ::= { stpEventObjects35 9 }

stp35-interface OBJECT-TYPE
    SYNTAX DisplayString
    MAX-ACCESS accessible-for-notify
    STATUS current
    DESCRIPTION
        "Parameter 'interface' in event STP.35"
    ::= { stpEventObjects35 10 }

stp35-circuit-name OBJECT-TYPE
    SYNTAX DisplayString
    MAX-ACCESS accessible-for-notify
    STATUS current
    DESCRIPTION
        "Parameter 'circuit-name' in event STP.35"
    ::= { stpEventObjects35 11 }

stpEventObjects36 OBJECT-IDENTITY
    STATUS current
    DESCRIPTION
        "Event STP.36
        A BPDU has been received with a Bridge Identifier and Port Identifier
        that match the values that would be transmitted in a BPDU from the
        port. It will be ignored."
    ::= { stpEventsGroup 36 }

stp36-bpdu-type OBJECT-TYPE
    SYNTAX DisplayString
    MAX-ACCESS accessible-for-notify
    STATUS current
    DESCRIPTION
        "Parameter 'bpdu-type' in event STP.36"
    ::= { stpEventObjects36 1 }

stp36-source-address OBJECT-TYPE
    SYNTAX DisplayString
    MAX-ACCESS accessible-for-notify
    STATUS current
    DESCRIPTION
        "Parameter 'source-address' in event STP.36"
    ::= { stpEventObjects36 2 }

stp36-bridge-type OBJECT-TYPE
    SYNTAX DisplayString
    MAX-ACCESS accessible-for-notify
    STATUS current
    DESCRIPTION
        "Parameter 'bridge-type' in event STP.36"
    ::= { stpEventObjects36 3 }

stp36-bridge-instance OBJECT-TYPE
    SYNTAX Integer32
    MAX-ACCESS accessible-for-notify
    STATUS current
    DESCRIPTION
        "Parameter 'bridge-instance' in event STP.36"
    ::= { stpEventObjects36 4 }

stp36-bridge-port OBJECT-TYPE
    SYNTAX Integer32
    MAX-ACCESS accessible-for-notify
    STATUS current
    DESCRIPTION
        "Parameter 'bridge-port' in event STP.36"
    ::= { stpEventObjects36 5 }

stp36-interface OBJECT-TYPE
    SYNTAX DisplayString
    MAX-ACCESS accessible-for-notify
    STATUS current
    DESCRIPTION
        "Parameter 'interface' in event STP.36"
    ::= { stpEventObjects36 6 }

stp36-circuit-name OBJECT-TYPE
    SYNTAX DisplayString
    MAX-ACCESS accessible-for-notify
    STATUS current
    DESCRIPTION
        "Parameter 'circuit-name' in event STP.36"
    ::= { stpEventObjects36 7 }

stpEventObjects37 OBJECT-IDENTITY
    STATUS current
    DESCRIPTION
        "Event STP.37
        A BPDU has been received from the specified MAC address."
    ::= { stpEventsGroup 37 }

stp37-bpdu-type OBJECT-TYPE
    SYNTAX DisplayString
    MAX-ACCESS accessible-for-notify
    STATUS current
    DESCRIPTION
        "Parameter 'bpdu-type' in event STP.37"
    ::= { stpEventObjects37 1 }

stp37-version OBJECT-TYPE
    SYNTAX Integer32
    MAX-ACCESS accessible-for-notify
    STATUS current
    DESCRIPTION
        "Parameter 'version' in event STP.37"
    ::= { stpEventObjects37 2 }

stp37-flags OBJECT-TYPE
    SYNTAX Integer32
    MAX-ACCESS accessible-for-notify
    STATUS current
    DESCRIPTION
        "Parameter 'flags' in event STP.37"
    ::= { stpEventObjects37 3 }

stp37-flags-str OBJECT-TYPE
    SYNTAX DisplayString
    MAX-ACCESS accessible-for-notify
    STATUS current
    DESCRIPTION
        "Parameter 'flags-str' in event STP.37"
    ::= { stpEventObjects37 4 }

stp37-source-address OBJECT-TYPE
    SYNTAX DisplayString
    MAX-ACCESS accessible-for-notify
    STATUS current
    DESCRIPTION
        "Parameter 'source-address' in event STP.37"
    ::= { stpEventObjects37 5 }

stp37-bridge-type OBJECT-TYPE
    SYNTAX DisplayString
    MAX-ACCESS accessible-for-notify
    STATUS current
    DESCRIPTION
        "Parameter 'bridge-type' in event STP.37"
    ::= { stpEventObjects37 6 }

stp37-bridge-instance OBJECT-TYPE
    SYNTAX Integer32
    MAX-ACCESS accessible-for-notify
    STATUS current
    DESCRIPTION
        "Parameter 'bridge-instance' in event STP.37"
    ::= { stpEventObjects37 7 }

stp37-bridge-port OBJECT-TYPE
    SYNTAX Integer32
    MAX-ACCESS accessible-for-notify
    STATUS current
    DESCRIPTION
        "Parameter 'bridge-port' in event STP.37"
    ::= { stpEventObjects37 8 }

stp37-interface OBJECT-TYPE
    SYNTAX DisplayString
    MAX-ACCESS accessible-for-notify
    STATUS current
    DESCRIPTION
        "Parameter 'interface' in event STP.37"
    ::= { stpEventObjects37 9 }

stp37-circuit-name OBJECT-TYPE
    SYNTAX DisplayString
    MAX-ACCESS accessible-for-notify
    STATUS current
    DESCRIPTION
        "Parameter 'circuit-name' in event STP.37"
    ::= { stpEventObjects37 10 }

stpEventObjects38 OBJECT-IDENTITY
    STATUS current
    DESCRIPTION
        "Event STP.38
        A Rapid Spanning Tree BPDU will be sent on the specified port. This is
        done normally on a periodic basis as part of the Spanning Tree Protocol."
    ::= { stpEventsGroup 38 }

stp38-flags OBJECT-TYPE
    SYNTAX Integer32
    MAX-ACCESS accessible-for-notify
    STATUS current
    DESCRIPTION
        "Parameter 'flags' in event STP.38"
    ::= { stpEventObjects38 1 }

stp38-flags-str OBJECT-TYPE
    SYNTAX DisplayString
    MAX-ACCESS accessible-for-notify
    STATUS current
    DESCRIPTION
        "Parameter 'flags-str' in event STP.38"
    ::= { stpEventObjects38 2 }

stp38-bridge-type OBJECT-TYPE
    SYNTAX DisplayString
    MAX-ACCESS accessible-for-notify
    STATUS current
    DESCRIPTION
        "Parameter 'bridge-type' in event STP.38"
    ::= { stpEventObjects38 3 }

stp38-bridge-instance OBJECT-TYPE
    SYNTAX Integer32
    MAX-ACCESS accessible-for-notify
    STATUS current
    DESCRIPTION
        "Parameter 'bridge-instance' in event STP.38"
    ::= { stpEventObjects38 4 }

stp38-bridge-port OBJECT-TYPE
    SYNTAX Integer32
    MAX-ACCESS accessible-for-notify
    STATUS current
    DESCRIPTION
        "Parameter 'bridge-port' in event STP.38"
    ::= { stpEventObjects38 5 }

stp38-interface OBJECT-TYPE
    SYNTAX DisplayString
    MAX-ACCESS accessible-for-notify
    STATUS current
    DESCRIPTION
        "Parameter 'interface' in event STP.38"
    ::= { stpEventObjects38 6 }

stp38-circuit-name OBJECT-TYPE
    SYNTAX DisplayString
    MAX-ACCESS accessible-for-notify
    STATUS current
    DESCRIPTION
        "Parameter 'circuit-name' in event STP.38"
    ::= { stpEventObjects38 7 }

stpEventObjects39 OBJECT-IDENTITY
    STATUS current
    DESCRIPTION
        "Event STP.39
        State change on a port."
    ::= { stpEventsGroup 39 }

stp39-state OBJECT-TYPE
    SYNTAX DisplayString
    MAX-ACCESS accessible-for-notify
    STATUS current
    DESCRIPTION
        "Parameter 'state' in event STP.39"
    ::= { stpEventObjects39 1 }

stp39-bridge-type OBJECT-TYPE
    SYNTAX DisplayString
    MAX-ACCESS accessible-for-notify
    STATUS current
    DESCRIPTION
        "Parameter 'bridge-type' in event STP.39"
    ::= { stpEventObjects39 2 }

stp39-bridge-instance OBJECT-TYPE
    SYNTAX Integer32
    MAX-ACCESS accessible-for-notify
    STATUS current
    DESCRIPTION
        "Parameter 'bridge-instance' in event STP.39"
    ::= { stpEventObjects39 3 }

stp39-bridge-port OBJECT-TYPE
    SYNTAX Integer32
    MAX-ACCESS accessible-for-notify
    STATUS current
    DESCRIPTION
        "Parameter 'bridge-port' in event STP.39"
    ::= { stpEventObjects39 4 }

stp39-interface OBJECT-TYPE
    SYNTAX DisplayString
    MAX-ACCESS accessible-for-notify
    STATUS current
    DESCRIPTION
        "Parameter 'interface' in event STP.39"
    ::= { stpEventObjects39 5 }

stp39-circuit-name OBJECT-TYPE
    SYNTAX DisplayString
    MAX-ACCESS accessible-for-notify
    STATUS current
    DESCRIPTION
        "Parameter 'circuit-name' in event STP.39"
    ::= { stpEventObjects39 6 }

stpEventObjects40 OBJECT-IDENTITY
    STATUS current
    DESCRIPTION
        "Event STP.40
        Role change on a port."
    ::= { stpEventsGroup 40 }

stp40-role OBJECT-TYPE
    SYNTAX DisplayString
    MAX-ACCESS accessible-for-notify
    STATUS current
    DESCRIPTION
        "Parameter 'role' in event STP.40"
    ::= { stpEventObjects40 1 }

stp40-bridge-type OBJECT-TYPE
    SYNTAX DisplayString
    MAX-ACCESS accessible-for-notify
    STATUS current
    DESCRIPTION
        "Parameter 'bridge-type' in event STP.40"
    ::= { stpEventObjects40 2 }

stp40-bridge-instance OBJECT-TYPE
    SYNTAX Integer32
    MAX-ACCESS accessible-for-notify
    STATUS current
    DESCRIPTION
        "Parameter 'bridge-instance' in event STP.40"
    ::= { stpEventObjects40 3 }

stp40-bridge-port OBJECT-TYPE
    SYNTAX Integer32
    MAX-ACCESS accessible-for-notify
    STATUS current
    DESCRIPTION
        "Parameter 'bridge-port' in event STP.40"
    ::= { stpEventObjects40 4 }

stp40-interface OBJECT-TYPE
    SYNTAX DisplayString
    MAX-ACCESS accessible-for-notify
    STATUS current
    DESCRIPTION
        "Parameter 'interface' in event STP.40"
    ::= { stpEventObjects40 5 }

stp40-circuit-name OBJECT-TYPE
    SYNTAX DisplayString
    MAX-ACCESS accessible-for-notify
    STATUS current
    DESCRIPTION
        "Parameter 'circuit-name' in event STP.40"
    ::= { stpEventObjects40 6 }

stpEventObjects41 OBJECT-IDENTITY
    STATUS current
    DESCRIPTION
        "Event STP.41
        Role change on a port."
    ::= { stpEventsGroup 41 }

stp41-root-vector OBJECT-TYPE
    SYNTAX DisplayString
    MAX-ACCESS accessible-for-notify
    STATUS current
    DESCRIPTION
        "Parameter 'root-vector' in event STP.41"
    ::= { stpEventObjects41 1 }

stp41-bridge-type OBJECT-TYPE
    SYNTAX DisplayString
    MAX-ACCESS accessible-for-notify
    STATUS current
    DESCRIPTION
        "Parameter 'bridge-type' in event STP.41"
    ::= { stpEventObjects41 2 }

stp41-bridge-instance OBJECT-TYPE
    SYNTAX Integer32
    MAX-ACCESS accessible-for-notify
    STATUS current
    DESCRIPTION
        "Parameter 'bridge-instance' in event STP.41"
    ::= { stpEventObjects41 3 }

stp41-bridge-port OBJECT-TYPE
    SYNTAX Integer32
    MAX-ACCESS accessible-for-notify
    STATUS current
    DESCRIPTION
        "Parameter 'bridge-port' in event STP.41"
    ::= { stpEventObjects41 4 }

stp41-interface OBJECT-TYPE
    SYNTAX DisplayString
    MAX-ACCESS accessible-for-notify
    STATUS current
    DESCRIPTION
        "Parameter 'interface' in event STP.41"
    ::= { stpEventObjects41 5 }

stp41-circuit-name OBJECT-TYPE
    SYNTAX DisplayString
    MAX-ACCESS accessible-for-notify
    STATUS current
    DESCRIPTION
        "Parameter 'circuit-name' in event STP.41"
    ::= { stpEventObjects41 6 }

stpEventObjects42 OBJECT-IDENTITY
    STATUS current
    DESCRIPTION
        "Event STP.42
        Role change on a port."
    ::= { stpEventsGroup 42 }

stp42-root-vector OBJECT-TYPE
    SYNTAX DisplayString
    MAX-ACCESS accessible-for-notify
    STATUS current
    DESCRIPTION
        "Parameter 'root-vector' in event STP.42"
    ::= { stpEventObjects42 1 }

stp42-bridge-type OBJECT-TYPE
    SYNTAX DisplayString
    MAX-ACCESS accessible-for-notify
    STATUS current
    DESCRIPTION
        "Parameter 'bridge-type' in event STP.42"
    ::= { stpEventObjects42 2 }

stp42-bridge-instance OBJECT-TYPE
    SYNTAX Integer32
    MAX-ACCESS accessible-for-notify
    STATUS current
    DESCRIPTION
        "Parameter 'bridge-instance' in event STP.42"
    ::= { stpEventObjects42 3 }

stp42-bridge-port OBJECT-TYPE
    SYNTAX Integer32
    MAX-ACCESS accessible-for-notify
    STATUS current
    DESCRIPTION
        "Parameter 'bridge-port' in event STP.42"
    ::= { stpEventObjects42 4 }

stp42-interface OBJECT-TYPE
    SYNTAX DisplayString
    MAX-ACCESS accessible-for-notify
    STATUS current
    DESCRIPTION
        "Parameter 'interface' in event STP.42"
    ::= { stpEventObjects42 5 }

stp42-circuit-name OBJECT-TYPE
    SYNTAX DisplayString
    MAX-ACCESS accessible-for-notify
    STATUS current
    DESCRIPTION
        "Parameter 'circuit-name' in event STP.42"
    ::= { stpEventObjects42 6 }

stpEventObjects43 OBJECT-IDENTITY
    STATUS current
    DESCRIPTION
        "Event STP.43
        Received BPDU discarded because BPDU filtering is enabled on a port."
    ::= { stpEventsGroup 43 }

stp43-bridge-id OBJECT-TYPE
    SYNTAX Integer32
    MAX-ACCESS accessible-for-notify
    STATUS current
    DESCRIPTION
        "Parameter 'bridge-id' in event STP.43"
    ::= { stpEventObjects43 1 }

stp43-bridge-port OBJECT-TYPE
    SYNTAX Integer32
    MAX-ACCESS accessible-for-notify
    STATUS current
    DESCRIPTION
        "Parameter 'bridge-port' in event STP.43"
    ::= { stpEventObjects43 2 }

stp43-interface OBJECT-TYPE
    SYNTAX DisplayString
    MAX-ACCESS accessible-for-notify
    STATUS current
    DESCRIPTION
        "Parameter 'interface' in event STP.43"
    ::= { stpEventObjects43 3 }

stp43-circuit-name OBJECT-TYPE
    SYNTAX DisplayString
    MAX-ACCESS accessible-for-notify
    STATUS current
    DESCRIPTION
        "Parameter 'circuit-name' in event STP.43"
    ::= { stpEventObjects43 4 }

stpEventObjects44 OBJECT-IDENTITY
    STATUS current
    DESCRIPTION
        "Event STP.44
        Transmitted BPDU discarded because BPDU filtering is enabled on a port.
        The BPDU is not sent."
    ::= { stpEventsGroup 44 }

stp44-bridge-id OBJECT-TYPE
    SYNTAX Integer32
    MAX-ACCESS accessible-for-notify
    STATUS current
    DESCRIPTION
        "Parameter 'bridge-id' in event STP.44"
    ::= { stpEventObjects44 1 }

stp44-bridge-port OBJECT-TYPE
    SYNTAX Integer32
    MAX-ACCESS accessible-for-notify
    STATUS current
    DESCRIPTION
        "Parameter 'bridge-port' in event STP.44"
    ::= { stpEventObjects44 2 }

stp44-interface OBJECT-TYPE
    SYNTAX DisplayString
    MAX-ACCESS accessible-for-notify
    STATUS current
    DESCRIPTION
        "Parameter 'interface' in event STP.44"
    ::= { stpEventObjects44 3 }

stp44-circuit-name OBJECT-TYPE
    SYNTAX DisplayString
    MAX-ACCESS accessible-for-notify
    STATUS current
    DESCRIPTION
        "Parameter 'circuit-name' in event STP.44"
    ::= { stpEventObjects44 4 }

stpEventObjects45 OBJECT-IDENTITY
    STATUS current
    DESCRIPTION
        "Event STP.45
        Received BPDU on port with BPDU Guard enabled. The port is disabled"
    ::= { stpEventsGroup 45 }

stp45-bridge-id OBJECT-TYPE
    SYNTAX Integer32
    MAX-ACCESS accessible-for-notify
    STATUS current
    DESCRIPTION
        "Parameter 'bridge-id' in event STP.45"
    ::= { stpEventObjects45 1 }

stp45-bridge-port OBJECT-TYPE
    SYNTAX Integer32
    MAX-ACCESS accessible-for-notify
    STATUS current
    DESCRIPTION
        "Parameter 'bridge-port' in event STP.45"
    ::= { stpEventObjects45 2 }

stp45-interface OBJECT-TYPE
    SYNTAX DisplayString
    MAX-ACCESS accessible-for-notify
    STATUS current
    DESCRIPTION
        "Parameter 'interface' in event STP.45"
    ::= { stpEventObjects45 3 }

stp45-circuit-name OBJECT-TYPE
    SYNTAX DisplayString
    MAX-ACCESS accessible-for-notify
    STATUS current
    DESCRIPTION
        "Parameter 'circuit-name' in event STP.45"
    ::= { stpEventObjects45 4 }

stpEventObjects46 OBJECT-IDENTITY
    STATUS current
    DESCRIPTION
        "Event STP.46
        Received PVST+ BPDU with inconsistent VID. The VID conveyed in the
        BPDU does not match the VID assigned to the frame"
    ::= { stpEventsGroup 46 }

stp46-VID OBJECT-TYPE
    SYNTAX Integer32
    MAX-ACCESS accessible-for-notify
    STATUS current
    DESCRIPTION
        "Parameter 'VID' in event STP.46"
    ::= { stpEventObjects46 1 }

stp46-VID2 OBJECT-TYPE
    SYNTAX Integer32
    MAX-ACCESS accessible-for-notify
    STATUS current
    DESCRIPTION
        "Parameter 'VID2' in event STP.46"
    ::= { stpEventObjects46 2 }

stp46-source-address OBJECT-TYPE
    SYNTAX DisplayString
    MAX-ACCESS accessible-for-notify
    STATUS current
    DESCRIPTION
        "Parameter 'source-address' in event STP.46"
    ::= { stpEventObjects46 3 }

stp46-bridge-id OBJECT-TYPE
    SYNTAX Integer32
    MAX-ACCESS accessible-for-notify
    STATUS current
    DESCRIPTION
        "Parameter 'bridge-id' in event STP.46"
    ::= { stpEventObjects46 4 }

stp46-bridge-port OBJECT-TYPE
    SYNTAX Integer32
    MAX-ACCESS accessible-for-notify
    STATUS current
    DESCRIPTION
        "Parameter 'bridge-port' in event STP.46"
    ::= { stpEventObjects46 5 }

stp46-interface OBJECT-TYPE
    SYNTAX DisplayString
    MAX-ACCESS accessible-for-notify
    STATUS current
    DESCRIPTION
        "Parameter 'interface' in event STP.46"
    ::= { stpEventObjects46 6 }

stp46-circuit-name OBJECT-TYPE
    SYNTAX DisplayString
    MAX-ACCESS accessible-for-notify
    STATUS current
    DESCRIPTION
        "Parameter 'circuit-name' in event STP.46"
    ::= { stpEventObjects46 7 }

stpEventObjects47 OBJECT-IDENTITY
    STATUS current
    DESCRIPTION
        "Event STP.47
        Received malformed PVST+ BPDU"
    ::= { stpEventsGroup 47 }

stp47-VID OBJECT-TYPE
    SYNTAX Integer32
    MAX-ACCESS accessible-for-notify
    STATUS current
    DESCRIPTION
        "Parameter 'VID' in event STP.47"
    ::= { stpEventObjects47 1 }

stp47-source-address OBJECT-TYPE
    SYNTAX DisplayString
    MAX-ACCESS accessible-for-notify
    STATUS current
    DESCRIPTION
        "Parameter 'source-address' in event STP.47"
    ::= { stpEventObjects47 2 }

stp47-bridge-id OBJECT-TYPE
    SYNTAX Integer32
    MAX-ACCESS accessible-for-notify
    STATUS current
    DESCRIPTION
        "Parameter 'bridge-id' in event STP.47"
    ::= { stpEventObjects47 3 }

stp47-bridge-port OBJECT-TYPE
    SYNTAX Integer32
    MAX-ACCESS accessible-for-notify
    STATUS current
    DESCRIPTION
        "Parameter 'bridge-port' in event STP.47"
    ::= { stpEventObjects47 4 }

stp47-interface OBJECT-TYPE
    SYNTAX DisplayString
    MAX-ACCESS accessible-for-notify
    STATUS current
    DESCRIPTION
        "Parameter 'interface' in event STP.47"
    ::= { stpEventObjects47 5 }

stp47-circuit-name OBJECT-TYPE
    SYNTAX DisplayString
    MAX-ACCESS accessible-for-notify
    STATUS current
    DESCRIPTION
        "Parameter 'circuit-name' in event STP.47"
    ::= { stpEventObjects47 6 }

stpEventObjects48 OBJECT-IDENTITY
    STATUS current
    DESCRIPTION
        "Event STP.48
        PVST+ BPDU conveying VLAN 1 received. Silently discarded, since
        the common BPDU is used instead"
    ::= { stpEventsGroup 48 }

stp48-bpdu-type OBJECT-TYPE
    SYNTAX DisplayString
    MAX-ACCESS accessible-for-notify
    STATUS current
    DESCRIPTION
        "Parameter 'bpdu-type' in event STP.48"
    ::= { stpEventObjects48 1 }

stp48-source-address OBJECT-TYPE
    SYNTAX DisplayString
    MAX-ACCESS accessible-for-notify
    STATUS current
    DESCRIPTION
        "Parameter 'source-address' in event STP.48"
    ::= { stpEventObjects48 2 }

stp48-bridge-id OBJECT-TYPE
    SYNTAX Integer32
    MAX-ACCESS accessible-for-notify
    STATUS current
    DESCRIPTION
        "Parameter 'bridge-id' in event STP.48"
    ::= { stpEventObjects48 3 }

stp48-bridge-port OBJECT-TYPE
    SYNTAX Integer32
    MAX-ACCESS accessible-for-notify
    STATUS current
    DESCRIPTION
        "Parameter 'bridge-port' in event STP.48"
    ::= { stpEventObjects48 4 }

stp48-interface OBJECT-TYPE
    SYNTAX DisplayString
    MAX-ACCESS accessible-for-notify
    STATUS current
    DESCRIPTION
        "Parameter 'interface' in event STP.48"
    ::= { stpEventObjects48 5 }

stp48-circuit-name OBJECT-TYPE
    SYNTAX DisplayString
    MAX-ACCESS accessible-for-notify
    STATUS current
    DESCRIPTION
        "Parameter 'circuit-name' in event STP.48"
    ::= { stpEventObjects48 6 }


stpNotification1 NOTIFICATION-TYPE
    OBJECTS { 
              stp1-source-address, 
              stp1-bridge-type,
              stp1-bridge-instance,
              stp1-bridge-port,
              stp1-interface,
              stp1-circuit-name 
            }
    STATUS current
    DESCRIPTION
        "Notification of Event STP.1

        Message: 'Configuration BPDU received frm $1 on $2-$3 port $4, interface $5$6'

        Parameters list:
              $1: stp1-source-address
              $2: stp1-bridge-type
              $3: stp1-bridge-instance
              $4: stp1-bridge-port
              $5: stp1-interface
              $6: stp1-circuit-name

        A configuration BPDU has been received from the specified MAC address."
    ::= { stpNotificationsPrefix 1 }

stpNotification2 NOTIFICATION-TYPE
    OBJECTS { 
              stp2-source-address, 
              stp2-bridge-type,
              stp2-bridge-instance,
              stp2-bridge-port,
              stp2-interface,
              stp2-circuit-name 
            }
    STATUS current
    DESCRIPTION
        "Notification of Event STP.2

        Message: 'Topology change notification BPDU received frm $1 on $2-$3 port $4, interface $5$6'

        Parameters list:
              $1: stp2-source-address
              $2: stp2-bridge-type
              $3: stp2-bridge-instance
              $4: stp2-bridge-port
              $5: stp2-interface
              $6: stp2-circuit-name

        A topology change notification BPDU has been received from
        the specified MAC address."
    ::= { stpNotificationsPrefix 2 }

stpNotification3 NOTIFICATION-TYPE
    OBJECTS { 
              stp3-BDPU-type, 
              stp3-source-address,
              stp3-bridge-type,
              stp3-bridge-instance,
              stp3-bridge-port,
              stp3-interface,
              stp3-circuit-name 
            }
    STATUS current
    DESCRIPTION
        "Notification of Event STP.3

        Message: 'Unkown BPDU type $1 received frm $2 on $3-$4 port $5, interface $6$7'

        Parameters list:
              $1: stp3-BDPU-type
              $2: stp3-source-address
              $3: stp3-bridge-type
              $4: stp3-bridge-instance
              $5: stp3-bridge-port
              $6: stp3-interface
              $7: stp3-circuit-name

        A BPDU with an undefined value in the BPDU Type field was received
        from the specified host. It will be ignored."
    ::= { stpNotificationsPrefix 3 }

stpNotification4 NOTIFICATION-TYPE
    OBJECTS { 
              stp4-Protocol-Identifier, 
              stp4-source-address,
              stp4-bridge-type,
              stp4-bridge-instance,
              stp4-bridge-port,
              stp4-interface,
              stp4-circuit-name 
            }
    STATUS current
    DESCRIPTION
        "Notification of Event STP.4

        Message: 'BPDU bad protocol identifier $1 frm $2 on $3-$4 port $5, interface $6$7'

        Parameters list:
              $1: stp4-Protocol-Identifier
              $2: stp4-source-address
              $3: stp4-bridge-type
              $4: stp4-bridge-instance
              $5: stp4-bridge-port
              $6: stp4-interface
              $7: stp4-circuit-name

        A configuration BPDU has been received with a Protocol Identifier
        that is not 0000. It will be ignored."
    ::= { stpNotificationsPrefix 4 }

stpNotification5 NOTIFICATION-TYPE
    OBJECTS { 
              stp5-Protocol-Version-Identifier, 
              stp5-source-address,
              stp5-bridge-type,
              stp5-bridge-instance,
              stp5-bridge-port,
              stp5-interface,
              stp5-circuit-name 
            }
    STATUS current
    DESCRIPTION
        "Notification of Event STP.5

        Message: 'BPDU bad Version $1 frm $2 on $3-$4 port $5, interface $6$7'

        Parameters list:
              $1: stp5-Protocol-Version-Identifier
              $2: stp5-source-address
              $3: stp5-bridge-type
              $4: stp5-bridge-instance
              $5: stp5-bridge-port
              $6: stp5-interface
              $7: stp5-circuit-name

        A configuration BPDU has been received with a Protocol Version
        Identifier that is not 00. It will be ignored."
    ::= { stpNotificationsPrefix 5 }

stpNotification6 NOTIFICATION-TYPE
    OBJECTS { 
              stp6-length, 
              stp6-source-address,
              stp6-bridge-type,
              stp6-bridge-instance,
              stp6-bridge-port,
              stp6-interface,
              stp6-circuit-name 
            }
    STATUS current
    DESCRIPTION
        "Notification of Event STP.6

        Message: 'Configuration BPDU truncated ($1 bytes) frm $2 on $3-$4 port $5, interface $6$7'

        Parameters list:
              $1: stp6-length
              $2: stp6-source-address
              $3: stp6-bridge-type
              $4: stp6-bridge-instance
              $5: stp6-bridge-port
              $6: stp6-interface
              $7: stp6-circuit-name

        A configuration BPDU has been received which is less than 35 bytes
        in length. It will be ignored."
    ::= { stpNotificationsPrefix 6 }

stpNotification7 NOTIFICATION-TYPE
    OBJECTS { 
              stp7-flags, 
              stp7-source-address,
              stp7-bridge-type,
              stp7-bridge-instance,
              stp7-bridge-port,
              stp7-interface,
              stp7-circuit-name 
            }
    STATUS current
    DESCRIPTION
        "Notification of Event STP.7

        Message: 'Configuration BPDU unknown flags $1 frm $2 on $3-$4 port $5, interface $6$7'

        Parameters list:
              $1: stp7-flags
              $2: stp7-source-address
              $3: stp7-bridge-type
              $4: stp7-bridge-instance
              $5: stp7-bridge-port
              $6: stp7-interface
              $7: stp7-circuit-name

        A configuration BPDU has been received which has undefined bits set
        in the flags field. It will be ignored."
    ::= { stpNotificationsPrefix 7 }

stpNotification8 NOTIFICATION-TYPE
    OBJECTS { 
              stp8-length, 
              stp8-source-address,
              stp8-bridge-type,
              stp8-bridge-instance,
              stp8-bridge-port,
              stp8-interface,
              stp8-circuit-name 
            }
    STATUS current
    DESCRIPTION
        "Notification of Event STP.8

        Message: 'Toplogy change notification BPDU tuncated ($1 bytes) frm $2 on $3-$4 port $5, interface $6$7'

        Parameters list:
              $1: stp8-length
              $2: stp8-source-address
              $3: stp8-bridge-type
              $4: stp8-bridge-instance
              $5: stp8-bridge-port
              $6: stp8-interface
              $7: stp8-circuit-name

        A topology change notificaton BPDU has been received that is less than
        4 bytes in length. It will be ignored."
    ::= { stpNotificationsPrefix 8 }

stpNotification9 NOTIFICATION-TYPE
    OBJECTS { 
              stp9-bridge-type, 
              stp9-bridge-instance,
              stp9-bridge-port,
              stp9-interface,
              stp9-circuit-name 
            }
    STATUS current
    DESCRIPTION
        "Notification of Event STP.9

        Message: 'No buffer to send BDPU on $1-$2 port $3, interface $4$5'

        Parameters list:
              $1: stp9-bridge-type
              $2: stp9-bridge-instance
              $3: stp9-bridge-port
              $4: stp9-interface
              $5: stp9-circuit-name

        No packet buffer was available to construct and send a BDPU on the
        specified port."
    ::= { stpNotificationsPrefix 9 }

stpNotification10 NOTIFICATION-TYPE
    OBJECTS { 
              stp10-bridge-type, 
              stp10-bridge-instance,
              stp10-bridge-port,
              stp10-interface,
              stp10-circuit-name 
            }
    STATUS current
    DESCRIPTION
        "Notification of Event STP.10

        Message: 'Sending Configuration BPDU on $1-$2 port $3, interface $4$5'

        Parameters list:
              $1: stp10-bridge-type
              $2: stp10-bridge-instance
              $3: stp10-bridge-port
              $4: stp10-interface
              $5: stp10-circuit-name

        A Configuration BPDU will be sent on the specified port.
        This is done normally on a periodic basis as part of the
        Spanning Tree Protocol.
        The flags field in this BPDU is zero, e.g., neither the Topology Change
        or the Topology Change Acknowledgement bits are set."
    ::= { stpNotificationsPrefix 10 }

stpNotification11 NOTIFICATION-TYPE
    OBJECTS { 
              stp11-TC, 
              stp11-TCA,
              stp11-bridge-type,
              stp11-bridge-instance,
              stp11-bridge-port,
              stp11-interface,
              stp11-circuit-name 
            }
    STATUS current
    DESCRIPTION
        "Notification of Event STP.11

        Message: 'Sending Configuration BPDU with flags $1 $2 on $3-$4 port $5, interface $6$7'

        Parameters list:
              $1: stp11-TC
              $2: stp11-TCA
              $3: stp11-bridge-type
              $4: stp11-bridge-instance
              $5: stp11-bridge-port
              $6: stp11-interface
              $7: stp11-circuit-name

        A Configuration BPDU will be sent on the specified port.
        This is done normally on a periodic basis as part of the
        Spanning Tree Protocol. TC will be displayed if the Topology Change bit
        is set in the Flags byte of the BPDU, TCA will be displayed if
        the Topology Change Acknowledge bit is set in the Flags byte."
    ::= { stpNotificationsPrefix 11 }

stpNotification12 NOTIFICATION-TYPE
    OBJECTS { 
              stp12-bridge-type, 
              stp12-bridge-instance,
              stp12-bridge-port,
              stp12-interface,
              stp12-circuit-name 
            }
    STATUS current
    DESCRIPTION
        "Notification of Event STP.12

        Message: 'Sending Topology Change Notification BPDU on $1-$2 port $3, interface $4$5'

        Parameters list:
              $1: stp12-bridge-type
              $2: stp12-bridge-instance
              $3: stp12-bridge-port
              $4: stp12-interface
              $5: stp12-circuit-name

        A Topology Change Notification BPDU will be sent on the specified port.
        These are sent on the root port of non-root ports when they detect
        a topology change in the spanning tree."
    ::= { stpNotificationsPrefix 12 }

stpNotification13 NOTIFICATION-TYPE
    OBJECTS { 
              stp13-reason-code, 
              stp13-bridge-type,
              stp13-bridge-instance,
              stp13-bridge-port,
              stp13-interface,
              stp13-circuit-name 
            }
    STATUS current
    DESCRIPTION
        "Notification of Event STP.13

        Message: 'BPDU send failed for reason code $1 on $2-$3 port $4, interface $5$6'

        Parameters list:
              $1: stp13-reason-code
              $2: stp13-bridge-type
              $3: stp13-bridge-instance
              $4: stp13-bridge-port
              $5: stp13-interface
              $6: stp13-circuit-name

        The attempt to queue a BPDU for transmission on the specified port
        failed."
    ::= { stpNotificationsPrefix 13 }

stpNotification14 NOTIFICATION-TYPE
    OBJECTS { 
              stp14-bridge-type, 
              stp14-bridge-instance,
              stp14-bridge-port,
              stp14-interface,
              stp14-circuit-name 
            }
    STATUS current
    DESCRIPTION
        "Notification of Event STP.14

        Message: 'Blocking $1-$2 port $3, interface $4$5, detecting topology change'

        Parameters list:
              $1: stp14-bridge-type
              $2: stp14-bridge-instance
              $3: stp14-bridge-port
              $4: stp14-interface
              $5: stp14-circuit-name

        This port has just been placed in Blocking state. This is a change in
        the topology, so this bridge detects a topology change.
        This will in turn cause topology change notifications to be sent."
    ::= { stpNotificationsPrefix 14 }

stpNotification15 NOTIFICATION-TYPE
    OBJECTS { 
              stp15-bridge-type, 
              stp15-bridge-instance,
              stp15-bridge-port,
              stp15-interface,
              stp15-circuit-name 
            }
    STATUS current
    DESCRIPTION
        "Notification of Event STP.15

        Message: 'Topology change detected on $1-$2 port $3, interface $4$5'

        Parameters list:
              $1: stp15-bridge-type
              $2: stp15-bridge-instance
              $3: stp15-bridge-port
              $4: stp15-interface
              $5: stp15-circuit-name

        A topology change notification has been received on this port, and
        this port is the designated port on its LAN. This causes the protocol
        to enter topology change notification state.
        The topology change will be acknowledged towards the sender, and
        propogated towards the root."
    ::= { stpNotificationsPrefix 15 }

stpNotification16 NOTIFICATION-TYPE
    OBJECTS { 
              stp16-bridge-type, 
              stp16-bridge-instance 
            }
    STATUS current
    DESCRIPTION
        "Notification of Event STP.16

        Message: 'Selected as root on $1-$2, detecting topology change'

        Parameters list:
              $1: stp16-bridge-type
              $2: stp16-bridge-instance

        This bridge has just selected itself as the root of the spanning tree
        when it previously had not been. This causes the bridge to enter
        topology change notification state."
    ::= { stpNotificationsPrefix 16 }

stpNotification17 NOTIFICATION-TYPE
    OBJECTS { 
              stp17-bridge-type, 
              stp17-bridge-instance,
              stp17-bridge-port,
              stp17-interface,
              stp17-circuit-name 
            }
    STATUS current
    DESCRIPTION
        "Notification of Event STP.17

        Message: 'Topology change acknowledged on $1-$2 port $3, interface $4$5'

        Parameters list:
              $1: stp17-bridge-type
              $2: stp17-bridge-instance
              $3: stp17-bridge-port
              $4: stp17-interface
              $5: stp17-circuit-name

        A topology change acknowledgement has been detected on the specified
        port. This port is the root port of the bridge."
    ::= { stpNotificationsPrefix 17 }

stpNotification18 NOTIFICATION-TYPE
    OBJECTS { 
              stp18-bridge-type, 
              stp18-bridge-instance,
              stp18-bridge-port,
              stp18-interface,
              stp18-circuit-name 
            }
    STATUS current
    DESCRIPTION
        "Notification of Event STP.18

        Message: 'Acknowledging topology change on $1-$2 port $3, interface $4$5'

        Parameters list:
              $1: stp18-bridge-type
              $2: stp18-bridge-instance
              $3: stp18-bridge-port
              $4: stp18-interface
              $5: stp18-circuit-name

        A topology change notification is being acknowledged on the
        specified port. This is done when a topology change notification
        is received on a port that is the designated port for that LAN."
    ::= { stpNotificationsPrefix 18 }

stpNotification19 NOTIFICATION-TYPE
    OBJECTS { 
              stp19-bridge-type, 
              stp19-bridge-instance 
            }
    STATUS current
    DESCRIPTION
        "Notification of Event STP.19

        Message: 'Topology Change Notification timer expired on $1-$2'

        Parameters list:
              $1: stp19-bridge-type
              $2: stp19-bridge-instance

        The Topology Change timer expired. This bridge will cease sending
        topology change notification BPDU's on its root port."
    ::= { stpNotificationsPrefix 19 }

stpNotification20 NOTIFICATION-TYPE
    OBJECTS { 
              stp20-bridge-type, 
              stp20-bridge-instance 
            }
    STATUS current
    DESCRIPTION
        "Notification of Event STP.20

        Message: 'Topology Change timer expired on $1-$2'

        Parameters list:
              $1: stp20-bridge-type
              $2: stp20-bridge-instance

        The Topology Change timer expired. This bridge, which is the root,
        will cease sending the Topology Change in its Configuration BPDUs."
    ::= { stpNotificationsPrefix 20 }

stpNotification21 NOTIFICATION-TYPE
    OBJECTS { 
              stp21-bridge-type, 
              stp21-bridge-instance,
              stp21-bridge-port,
              stp21-interface,
              stp21-circuit-name 
            }
    STATUS current
    DESCRIPTION
        "Notification of Event STP.21

        Message: 'Message age timer expired on $1-$2 port $3, interface $4$5, will try and become root'

        Parameters list:
              $1: stp21-bridge-type
              $2: stp21-bridge-instance
              $3: stp21-bridge-port
              $4: stp21-interface
              $5: stp21-circuit-name

        The message age timer has expired on this port. The bridge will attempt
        to become the root. It will become the designated port on that LAN."
    ::= { stpNotificationsPrefix 21 }

stpNotification22 NOTIFICATION-TYPE
    OBJECTS { 
              stp22-bridge-type, 
              stp22-bridge-instance 
            }
    STATUS current
    DESCRIPTION
        "Notification of Event STP.22

        Message: 'Hello timer expired on $1-$2'

        Parameters list:
              $1: stp22-bridge-type
              $2: stp22-bridge-instance

        The hello timer has expired on this port. Configuration BPDUs will be
        sent on all ports."
    ::= { stpNotificationsPrefix 22 }

stpNotification23 NOTIFICATION-TYPE
    OBJECTS { 
              stp23-bridge-type, 
              stp23-bridge-instance,
              stp23-bridge-port,
              stp23-interface,
              stp23-circuit-name 
            }
    STATUS current
    DESCRIPTION
        "Notification of Event STP.23

        Message: 'Stopping message age timer for $1-$2 port $3, interface $4$5'

        Parameters list:
              $1: stp23-bridge-type
              $2: stp23-bridge-instance
              $3: stp23-bridge-port
              $4: stp23-interface
              $5: stp23-circuit-name

        Stopping the message age timer on this port because it is
        the designated port on its LAN."
    ::= { stpNotificationsPrefix 23 }

stpNotification24 NOTIFICATION-TYPE
    OBJECTS { 
              stp24-bridge-type, 
              stp24-bridge-instance 
            }
    STATUS current
    DESCRIPTION
        "Notification of Event STP.24

        Message: 'Not root anymore on $1-$2, stopping hello timer'

        Parameters list:
              $1: stp24-bridge-type
              $2: stp24-bridge-instance

        This bridge has just decided that it is no longer the root bridge of
        the spanning tree. The hello timer will also be cancelled."
    ::= { stpNotificationsPrefix 24 }

stpNotification25 NOTIFICATION-TYPE
    OBJECTS { 
              stp25-bridge-type, 
              stp25-bridge-instance 
            }
    STATUS current
    DESCRIPTION
        "Notification of Event STP.25

        Message: 'Stopping topology change timer for $1-$2'

        Parameters list:
              $1: stp25-bridge-type
              $2: stp25-bridge-instance

        Stopping the topology change timer because this bridge is no longer
        the root."
    ::= { stpNotificationsPrefix 25 }

stpNotification26 NOTIFICATION-TYPE
    OBJECTS { 
              stp26-bridge-type, 
              stp26-bridge-instance 
            }
    STATUS current
    DESCRIPTION
        "Notification of Event STP.26

        Message: 'Selected as root on $1-$2, starting hello timer'

        Parameters list:
              $1: stp26-bridge-type
              $2: stp26-bridge-instance

        This bridge has just decided that it is the root bridge of
        the spanning tree. The hello timer will be started."
    ::= { stpNotificationsPrefix 26 }

stpNotification27 NOTIFICATION-TYPE
    OBJECTS { 
              stp27-bridge-type, 
              stp27-bridge-instance,
              stp27-bridge-port,
              stp27-interface,
              stp27-circuit-name 
            }
    STATUS current
    DESCRIPTION
        "Notification of Event STP.27

        Message: 'Starting message age timer for $1-$2 port $3, interface $4$5'

        Parameters list:
              $1: stp27-bridge-type
              $2: stp27-bridge-instance
              $3: stp27-bridge-port
              $4: stp27-interface
              $5: stp27-circuit-name

        Starting the message age timer on this port."
    ::= { stpNotificationsPrefix 27 }

stpNotification28 NOTIFICATION-TYPE
    OBJECTS { 
              stp28-bridge-type, 
              stp28-bridge-instance 
            }
    STATUS current
    DESCRIPTION
        "Notification of Event STP.28

        Message: 'Attempting to become root on $1-$2, starting hello timer'

        Parameters list:
              $1: stp28-bridge-type
              $2: stp28-bridge-instance

        This bridge is attempting to become the root bridge of
        the spanning tree. The hello timer will be started."
    ::= { stpNotificationsPrefix 28 }

stpNotification29 NOTIFICATION-TYPE
    OBJECTS { 
              stp29-source-address, 
              stp29-bridge-type,
              stp29-bridge-instance,
              stp29-bridge-port,
              stp29-interface,
              stp29-circuit-name 
            }
    STATUS current
    DESCRIPTION
        "Notification of Event STP.29

        Message: 'Configuration BPDU from $1 on $2-$3 ignored, inactive port $4, interface $5$6'

        Parameters list:
              $1: stp29-source-address
              $2: stp29-bridge-type
              $3: stp29-bridge-instance
              $4: stp29-bridge-port
              $5: stp29-interface
              $6: stp29-circuit-name

        A configuration BPDU has been received from the specified MAC address,
        but the port is not participating in the Spanning Tree Protocol."
    ::= { stpNotificationsPrefix 29 }

stpNotification30 NOTIFICATION-TYPE
    OBJECTS { 
              stp30-source-address, 
              stp30-bridge-type,
              stp30-bridge-instance,
              stp30-bridge-port,
              stp30-interface,
              stp30-circuit-name 
            }
    STATUS current
    DESCRIPTION
        "Notification of Event STP.30

        Message: 'Topology change notification BPDU from $1 on $2-$3 ignored, inactive port $4, interface $5$6'

        Parameters list:
              $1: stp30-source-address
              $2: stp30-bridge-type
              $3: stp30-bridge-instance
              $4: stp30-bridge-port
              $5: stp30-interface
              $6: stp30-circuit-name

        A topology change notification BPDU has been received from
        the specified MAC address, but the port is not participating in
        the Spanning Tree Protocol."
    ::= { stpNotificationsPrefix 30 }

stpNotification31 NOTIFICATION-TYPE
    OBJECTS { 
              stp31-bridge-type, 
              stp31-bridge-instance,
              stp31-bridge-port,
              stp31-interface,
              stp31-circuit-name 
            }
    STATUS current
    DESCRIPTION
        "Notification of Event STP.31

        Message: '$1-$2 becoming designated port $3, interface $4$5'

        Parameters list:
              $1: stp31-bridge-type
              $2: stp31-bridge-instance
              $3: stp31-bridge-port
              $4: stp31-interface
              $5: stp31-circuit-name

        This bridge is declaring itself the designated port on the LAN connected
        to this port."
    ::= { stpNotificationsPrefix 31 }

stpNotification32 NOTIFICATION-TYPE
    OBJECTS { 
              stp32-bpdu-type, 
              stp32-bridge-port,
              stp32-interface,
              stp32-circuit-name 
            }
    STATUS current
    DESCRIPTION
        "Notification of Event STP.32

        Message: 'DROP: $1 BPDU frame received on non-participating port $2, interface $3$4'

        Parameters list:
              $1: stp32-bpdu-type
              $2: stp32-bridge-port
              $3: stp32-interface
              $4: stp32-circuit-name

        A Source Route Bridge BPDU or IEEE802.1D BPDU has been received,
        but the port is not participating in the SRB or IEEE802.1D Spanning
        Tree Protocol."
    ::= { stpNotificationsPrefix 32 }

stpNotification33 NOTIFICATION-TYPE
    OBJECTS { 
              stp33-bpdu-type, 
              stp33-length,
              stp33-source-address,
              stp33-bridge-type,
              stp33-bridge-instance,
              stp33-bridge-port,
              stp33-interface,
              stp33-circuit-name 
            }
    STATUS current
    DESCRIPTION
        "Notification of Event STP.33

        Message: '$1 BPDU truncated ($2 bytes) frm $3 on $4-$5 port $6, interface $7$8'

        Parameters list:
              $1: stp33-bpdu-type
              $2: stp33-length
              $3: stp33-source-address
              $4: stp33-bridge-type
              $5: stp33-bridge-instance
              $6: stp33-bridge-port
              $7: stp33-interface
              $8: stp33-circuit-name

        A BPDU has been received which is less than the minimum size needed
        in length. It will be ignored."
    ::= { stpNotificationsPrefix 33 }

stpNotification34 NOTIFICATION-TYPE
    OBJECTS { 
              stp34-length, 
              stp34-source-address,
              stp34-bridge-type,
              stp34-bridge-instance,
              stp34-bridge-port,
              stp34-interface,
              stp34-circuit-name 
            }
    STATUS current
    DESCRIPTION
        "Notification of Event STP.34

        Message: 'BPDU truncated ($1 bytes) frm $2 on $3-$4 port $5, interface $6$7'

        Parameters list:
              $1: stp34-length
              $2: stp34-source-address
              $3: stp34-bridge-type
              $4: stp34-bridge-instance
              $5: stp34-bridge-port
              $6: stp34-interface
              $7: stp34-circuit-name

        A BPDU has been received which is less than 4 bytes in length.
        It will be ignored."
    ::= { stpNotificationsPrefix 34 }

stpNotification35 NOTIFICATION-TYPE
    OBJECTS { 
              stp35-bpdu-type, 
              stp35-msg-age-sc,
              stp35-msg-age-fr,
              stp35-max-age-sc,
              stp35-max-age-fr,
              stp35-source-address,
              stp35-bridge-type,
              stp35-bridge-instance,
              stp35-bridge-port,
              stp35-interface,
              stp35-circuit-name 
            }
    STATUS current
    DESCRIPTION
        "Notification of Event STP.35

        Message: '$1 BPDU discarded Message Age $2.$3 not less than Max Age $4.$5 frm $6 on $7-$8 port $9, interface $10$11'

        Parameters list:
              $1: stp35-bpdu-type
              $2: stp35-msg-age-sc
              $3: stp35-msg-age-fr
              $4: stp35-max-age-sc
              $5: stp35-max-age-fr
              $6: stp35-source-address
              $7: stp35-bridge-type
              $8: stp35-bridge-instance
              $9: stp35-bridge-port
              $10: stp35-interface
              $11: stp35-circuit-name

        A BPDU has been received with a message age that is not less than its
        max age parameter. It will be ignored."
    ::= { stpNotificationsPrefix 35 }

stpNotification36 NOTIFICATION-TYPE
    OBJECTS { 
              stp36-bpdu-type, 
              stp36-source-address,
              stp36-bridge-type,
              stp36-bridge-instance,
              stp36-bridge-port,
              stp36-interface,
              stp36-circuit-name 
            }
    STATUS current
    DESCRIPTION
        "Notification of Event STP.36

        Message: '$1 BPDU discarded parameters match transmitted frm $2 on $3-$4 port $5, interface $6$7'

        Parameters list:
              $1: stp36-bpdu-type
              $2: stp36-source-address
              $3: stp36-bridge-type
              $4: stp36-bridge-instance
              $5: stp36-bridge-port
              $6: stp36-interface
              $7: stp36-circuit-name

        A BPDU has been received with a Bridge Identifier and Port Identifier
        that match the values that would be transmitted in a BPDU from the
        port. It will be ignored."
    ::= { stpNotificationsPrefix 36 }

stpNotification37 NOTIFICATION-TYPE
    OBJECTS { 
              stp37-bpdu-type, 
              stp37-version,
              stp37-flags,
              stp37-flags-str,
              stp37-source-address,
              stp37-bridge-type,
              stp37-bridge-instance,
              stp37-bridge-port,
              stp37-interface,
              stp37-circuit-name 
            }
    STATUS current
    DESCRIPTION
        "Notification of Event STP.37

        Message: '$1 BPDU received version $2 flags 0x$3 ($4) frm $5 on $6-$7 port $8, interface $9$10'

        Parameters list:
              $1: stp37-bpdu-type
              $2: stp37-version
              $3: stp37-flags
              $4: stp37-flags-str
              $5: stp37-source-address
              $6: stp37-bridge-type
              $7: stp37-bridge-instance
              $8: stp37-bridge-port
              $9: stp37-interface
              $10: stp37-circuit-name

        A BPDU has been received from the specified MAC address."
    ::= { stpNotificationsPrefix 37 }

stpNotification38 NOTIFICATION-TYPE
    OBJECTS { 
              stp38-flags, 
              stp38-flags-str,
              stp38-bridge-type,
              stp38-bridge-instance,
              stp38-bridge-port,
              stp38-interface,
              stp38-circuit-name 
            }
    STATUS current
    DESCRIPTION
        "Notification of Event STP.38

        Message: 'Sending Rapid Spanning Tree BPDU with flags 0x$1 ($2) on $3-$4 port $5, interface $6$7'

        Parameters list:
              $1: stp38-flags
              $2: stp38-flags-str
              $3: stp38-bridge-type
              $4: stp38-bridge-instance
              $5: stp38-bridge-port
              $6: stp38-interface
              $7: stp38-circuit-name

        A Rapid Spanning Tree BPDU will be sent on the specified port. This is
        done normally on a periodic basis as part of the Spanning Tree Protocol."
    ::= { stpNotificationsPrefix 38 }

stpNotification39 NOTIFICATION-TYPE
    OBJECTS { 
              stp39-state, 
              stp39-bridge-type,
              stp39-bridge-instance,
              stp39-bridge-port,
              stp39-interface,
              stp39-circuit-name 
            }
    STATUS current
    DESCRIPTION
        "Notification of Event STP.39

        Message: 'state $1 $2-$3 port $4, interface $5$6'

        Parameters list:
              $1: stp39-state
              $2: stp39-bridge-type
              $3: stp39-bridge-instance
              $4: stp39-bridge-port
              $5: stp39-interface
              $6: stp39-circuit-name

        State change on a port."
    ::= { stpNotificationsPrefix 39 }

stpNotification40 NOTIFICATION-TYPE
    OBJECTS { 
              stp40-role, 
              stp40-bridge-type,
              stp40-bridge-instance,
              stp40-bridge-port,
              stp40-interface,
              stp40-circuit-name 
            }
    STATUS current
    DESCRIPTION
        "Notification of Event STP.40

        Message: 'role $1 $2-$3 port $4, interface $5$6'

        Parameters list:
              $1: stp40-role
              $2: stp40-bridge-type
              $3: stp40-bridge-instance
              $4: stp40-bridge-port
              $5: stp40-interface
              $6: stp40-circuit-name

        Role change on a port."
    ::= { stpNotificationsPrefix 40 }

stpNotification41 NOTIFICATION-TYPE
    OBJECTS { 
              stp41-root-vector, 
              stp41-bridge-type,
              stp41-bridge-instance,
              stp41-bridge-port,
              stp41-interface,
              stp41-circuit-name 
            }
    STATUS current
    DESCRIPTION
        "Notification of Event STP.41

        Message: 'rcvd root $1 $2-$3 port $4, interface $5$6'

        Parameters list:
              $1: stp41-root-vector
              $2: stp41-bridge-type
              $3: stp41-bridge-instance
              $4: stp41-bridge-port
              $5: stp41-interface
              $6: stp41-circuit-name

        Role change on a port."
    ::= { stpNotificationsPrefix 41 }

stpNotification42 NOTIFICATION-TYPE
    OBJECTS { 
              stp42-root-vector, 
              stp42-bridge-type,
              stp42-bridge-instance,
              stp42-bridge-port,
              stp42-interface,
              stp42-circuit-name 
            }
    STATUS current
    DESCRIPTION
        "Notification of Event STP.42

        Message: 'rcvd better root $1 $2-$3 port $4, interface $5$6'

        Parameters list:
              $1: stp42-root-vector
              $2: stp42-bridge-type
              $3: stp42-bridge-instance
              $4: stp42-bridge-port
              $5: stp42-interface
              $6: stp42-circuit-name

        Role change on a port."
    ::= { stpNotificationsPrefix 42 }

stpNotification43 NOTIFICATION-TYPE
    OBJECTS { 
              stp43-bridge-id, 
              stp43-bridge-port,
              stp43-interface,
              stp43-circuit-name 
            }
    STATUS current
    DESCRIPTION
        "Notification of Event STP.43

        Message: 'BPDU received filtered on bridge $1 port $2, interface $3$4'

        Parameters list:
              $1: stp43-bridge-id
              $2: stp43-bridge-port
              $3: stp43-interface
              $4: stp43-circuit-name

        Received BPDU discarded because BPDU filtering is enabled on a port."
    ::= { stpNotificationsPrefix 43 }

stpNotification44 NOTIFICATION-TYPE
    OBJECTS { 
              stp44-bridge-id, 
              stp44-bridge-port,
              stp44-interface,
              stp44-circuit-name 
            }
    STATUS current
    DESCRIPTION
        "Notification of Event STP.44

        Message: 'Transmitted BPDU filtered on bridge $1 port $2, interface $3$4'

        Parameters list:
              $1: stp44-bridge-id
              $2: stp44-bridge-port
              $3: stp44-interface
              $4: stp44-circuit-name

        Transmitted BPDU discarded because BPDU filtering is enabled on a port.
        The BPDU is not sent."
    ::= { stpNotificationsPrefix 44 }

stpNotification45 NOTIFICATION-TYPE
    OBJECTS { 
              stp45-bridge-id, 
              stp45-bridge-port,
              stp45-interface,
              stp45-circuit-name 
            }
    STATUS current
    DESCRIPTION
        "Notification of Event STP.45

        Message: 'BPDU Guard, port disabled, on bridge $1 port $2, interface $3$4'

        Parameters list:
              $1: stp45-bridge-id
              $2: stp45-bridge-port
              $3: stp45-interface
              $4: stp45-circuit-name

        Received BPDU on port with BPDU Guard enabled. The port is disabled"
    ::= { stpNotificationsPrefix 45 }

stpNotification46 NOTIFICATION-TYPE
    OBJECTS { 
              stp46-VID, 
              stp46-VID2,
              stp46-source-address,
              stp46-bridge-id,
              stp46-bridge-port,
              stp46-interface,
              stp46-circuit-name 
            }
    STATUS current
    DESCRIPTION
        "Notification of Event STP.46

        Message: 'PVST+ inconsistency detected on VLAN $1, conveyed VLAN $2 from $3 bridge $4 port $5, interface $6$7'

        Parameters list:
              $1: stp46-VID
              $2: stp46-VID2
              $3: stp46-source-address
              $4: stp46-bridge-id
              $5: stp46-bridge-port
              $6: stp46-interface
              $7: stp46-circuit-name

        Received PVST+ BPDU with inconsistent VID. The VID conveyed in the
        BPDU does not match the VID assigned to the frame"
    ::= { stpNotificationsPrefix 46 }

stpNotification47 NOTIFICATION-TYPE
    OBJECTS { 
              stp47-VID, 
              stp47-source-address,
              stp47-bridge-id,
              stp47-bridge-port,
              stp47-interface,
              stp47-circuit-name 
            }
    STATUS current
    DESCRIPTION
        "Notification of Event STP.47

        Message: 'Malformed PVST+ BPDU on VLAN $1 from $2 bridge $3 port $4, interface $5$6'

        Parameters list:
              $1: stp47-VID
              $2: stp47-source-address
              $3: stp47-bridge-id
              $4: stp47-bridge-port
              $5: stp47-interface
              $6: stp47-circuit-name

        Received malformed PVST+ BPDU"
    ::= { stpNotificationsPrefix 47 }

stpNotification48 NOTIFICATION-TYPE
    OBJECTS { 
              stp48-bpdu-type, 
              stp48-source-address,
              stp48-bridge-id,
              stp48-bridge-port,
              stp48-interface,
              stp48-circuit-name 
            }
    STATUS current
    DESCRIPTION
        "Notification of Event STP.48

        Message: '$1 BPDU discarded (VLAN 1) from $2 bridge $3 port $4, interface $5$6'

        Parameters list:
              $1: stp48-bpdu-type
              $2: stp48-source-address
              $3: stp48-bridge-id
              $4: stp48-bridge-port
              $5: stp48-interface
              $6: stp48-circuit-name

        PVST+ BPDU conveying VLAN 1 received. Silently discarded, since
        the common BPDU is used instead"
    ::= { stpNotificationsPrefix 48 }


END
