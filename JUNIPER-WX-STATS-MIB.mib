-- ========================================================================
-- Start - JUNIPER-WX-STATS-MIB Module

JUNIPER-WX-STATS-MIB DEFINITIONS ::= BEGIN

IMPORTS
	OBJECT-IDENTITY,
	OBJECT-TYPE, 
	Counter64
		FROM SNMPv2-SMI
	Counter FROM RFC1155-SMI
	jnxWxGrpStats
		FROM JUNIPER-WX-GLOBAL-MIB
	jnxWxGrpStatusAppId, 
	jnxWxGrpStatusRemoteWxId 
		FROM JUNIPER-WX-STATUS-MIB;

------------------------------------------
-- System Statistics Group --
------------------------------------------
jnxWxGrpStatsSys OBJECT-IDENTITY
    STATUS  current
    DESCRIPTION
      "This group contains statistics at the system level.
      "
    ::= { jnxWxGrpStats 1 }

------------------------------------------
-- System Passthrough Statistics --
------------------------------------------
jnxWxGrpStatsSysPt OBJECT-IDENTITY
    STATUS  current
    DESCRIPTION
      "This group contains passthrough statistics.
      "
    ::= { jnxWxGrpStatsSys 1 }

jnxWxGrpStatsSysPtAppDefMatchBytes OBJECT-TYPE
    SYNTAX  Counter64
    MAX-ACCESS  read-only
    STATUS  current
    DESCRIPTION
      "Passthru byte count because of application definition.
       " 
    ::= { jnxWxGrpStatsSysPt 1 }

jnxWxGrpStatsSysPtAppDefMatchPkts OBJECT-TYPE
    SYNTAX  Counter64
    MAX-ACCESS  read-only
    STATUS  current
    DESCRIPTION
      "Passthru packet count because of application definition.
      "
    ::= { jnxWxGrpStatsSysPt 2 }

jnxWxGrpStatsSysPtNoRemoteWxBytes OBJECT-TYPE
    SYNTAX  Counter64
    MAX-ACCESS  read-only
    STATUS  current
    DESCRIPTION
      "Passthru byte count due to no Remote WX.
      "
    ::= { jnxWxGrpStatsSysPt 3 }

jnxWxGrpStatsSysPtNoRemoteWxPkts OBJECT-TYPE
    SYNTAX  Counter64
    MAX-ACCESS  read-only
    STATUS  current
    DESCRIPTION
      "Passthru packet count due to no Remote WX.
      "
    ::= { jnxWxGrpStatsSysPt 4 }

jnxWxGrpStatsSysPtNonTcpProtoBytes OBJECT-TYPE
    SYNTAX  Counter64
    MAX-ACCESS  read-only
    STATUS  current
    DESCRIPTION
      "Passthru byte count because protocol is non-TCP.
      "
    ::= { jnxWxGrpStatsSysPt 5 }

jnxWxGrpStatsSysPtNonTcpProtoPkts OBJECT-TYPE
    SYNTAX  Counter64
    MAX-ACCESS  read-only
    STATUS  current
    DESCRIPTION
      "Passthru packet count because protocol is non-TCP.
      " 
    ::= { jnxWxGrpStatsSysPt 6 }

jnxWxGrpStatsSysPtNonIpBytes OBJECT-TYPE
    SYNTAX  Counter64
    MAX-ACCESS  read-only
    STATUS  current
    DESCRIPTION
      "Passthru byte count because of non-IP traffic like
       Appletalk, IPX, etc.
      "
    ::= { jnxWxGrpStatsSysPt 7 }

jnxWxGrpStatsSysPtNonIpPkts OBJECT-TYPE
    SYNTAX  Counter64
    MAX-ACCESS  read-only
    STATUS  current
    DESCRIPTION
      "Passthru packet count because of non-IP traffic like
       Appletalk, IPX, etc.
      "
    ::= { jnxWxGrpStatsSysPt 8 }

jnxWxGrpStatsSysPtFragIpBytes OBJECT-TYPE
    SYNTAX  Counter64
    MAX-ACCESS  read-only
    STATUS  current
    DESCRIPTION
      "Passthru because of fragmented IP packets.
      "
    ::= { jnxWxGrpStatsSysPt 9 }

jnxWxGrpStatsSysPtFragIpPkts OBJECT-TYPE
    SYNTAX  Counter64
    MAX-ACCESS  read-only
    STATUS  current
    DESCRIPTION
      "Passthru because of fragmented IP bytes.
      "
    ::= { jnxWxGrpStatsSysPt 10 }

jnxWxGrpStatsSysPtVlanBytes OBJECT-TYPE
    SYNTAX  Counter64
    MAX-ACCESS  read-only
    STATUS  current
    DESCRIPTION
      "Passthru due to VLAN bytes.
      "
    ::= { jnxWxGrpStatsSysPt 11 }

jnxWxGrpStatsSysPtVlanPkts OBJECT-TYPE
    SYNTAX  Counter64
    MAX-ACCESS  read-only
    STATUS  current
    DESCRIPTION
      "Passthru due to VLAN packets.
      "
    ::= { jnxWxGrpStatsSysPt 12 }

jnxWxGrpStatsSysPtMcastBytes OBJECT-TYPE
    SYNTAX  Counter64
    MAX-ACCESS  read-only
    STATUS  current
    DESCRIPTION
      "Passthru due to Multicast bytes.
      "
    ::= { jnxWxGrpStatsSysPt 13 }

jnxWxGrpStatsSysPtMcastPkts OBJECT-TYPE
    SYNTAX  Counter64
    MAX-ACCESS  read-only
    STATUS  current
    DESCRIPTION
      "Passthru due to Multicast packets.
      "
    ::= { jnxWxGrpStatsSysPt 14 }

-----------------------------------
-- System Compression Statistics --
-----------------------------------
jnxWxGrpStatsSysComp OBJECT-IDENTITY
    STATUS  current
    DESCRIPTION
      "This group contains Compression statistics at the system level.
      "
    ::= { jnxWxGrpStatsSys 2 }

jnxWxGrpStatsSysCompFailAppDefDisableBytes OBJECT-TYPE
    SYNTAX  Counter64
    MAX-ACCESS  read-only
    STATUS  current
    DESCRIPTION
      "Byte count when compression failed because application
       definition did not enable compression.
      "
    ::= { jnxWxGrpStatsSysComp 1 }

jnxWxGrpStatsSysCompFailAppDefDisablePkts OBJECT-TYPE
    SYNTAX  Counter64
    MAX-ACCESS  read-only
    STATUS  current
    DESCRIPTION
      "Packet count when compression failed because application
       definition did not enable compression.
      "
    ::= { jnxWxGrpStatsSysComp 2 }

jnxWxGrpStatsSysCompFailTcpAcclToRemoteBytes OBJECT-TYPE
    SYNTAX  Counter64
    MAX-ACCESS  read-only
    STATUS  current
    DESCRIPTION
      "Byte count when compression failed because TCP
       acceleration was not configured to remote WX.
      "
    ::= { jnxWxGrpStatsSysComp 3 }

jnxWxGrpStatsSysCompFailTcpAcclToRemotePkts OBJECT-TYPE
    SYNTAX  Counter64
    MAX-ACCESS  read-only
    STATUS  current
    DESCRIPTION
      "Packet count when compression failed because TCP
       acceleration was not configured to remote WX.
      "
    ::= { jnxWxGrpStatsSysComp 4 }

jnxWxGrpStatsSysCompFailResCrunchBytes OBJECT-TYPE
    SYNTAX  Counter64
    MAX-ACCESS  read-only
    STATUS  current
    DESCRIPTION
      "Byte count when compression failed due to
       resource crunch.
      "
    ::= { jnxWxGrpStatsSysComp 5 }

jnxWxGrpStatsSysCompFailAlgoLimitBytes OBJECT-TYPE
    SYNTAX  Counter64
    MAX-ACCESS  read-only
    STATUS  current
    DESCRIPTION
      "Byte count when compression failed because of
       algorithmic limitations.
      "
    ::= { jnxWxGrpStatsSysComp 6 }

jnxWxGrpStatsSysCompTcpAcclFailedBytes OBJECT-TYPE
    SYNTAX  Counter64
    MAX-ACCESS  read-only
    STATUS  current
    DESCRIPTION
      "Byte count when compression failed because of
       TCP acceleration error.
      "
    ::= { jnxWxGrpStatsSysComp 7 }

jnxWxGrpStatsSysCompTcpAcclFailedPkts OBJECT-TYPE
    SYNTAX  Counter64
    MAX-ACCESS  read-only
    STATUS  current
    DESCRIPTION
      "Packet count when compression failed because of
       TCP acceleration error.
      "
    ::= { jnxWxGrpStatsSysComp 8 }

----------------------------
-- System CIFS Statistics --
----------------------------
jnxWxGrpStatsSysCifs OBJECT-IDENTITY
    STATUS  current
    DESCRIPTION
      "This group contains CIFS statistics at the system level.
      "
    ::= { jnxWxGrpStatsSys 3 }

jnxWxGrpStatsSysCifsFailAppDefBytes OBJECT-TYPE
    SYNTAX  Counter64
    MAX-ACCESS  read-only
    STATUS  current
    DESCRIPTION
      "Byte count when CIFS acceleration failed because
       application definition did not enable CIFS.
      "
    ::= { jnxWxGrpStatsSysCifs 1 }

jnxWxGrpStatsSysCifsFailAppDefPkts OBJECT-TYPE
    SYNTAX  Counter64
    MAX-ACCESS  read-only
    STATUS  current
    DESCRIPTION
      "Packet count when CIFS acceleration failed because
       application definition did not enable CIFS.
      "
    ::= { jnxWxGrpStatsSysCifs 2 }

jnxWxGrpStatsSysCifsFailTcpAcclToRemoteBytes OBJECT-TYPE
    SYNTAX  Counter64
    MAX-ACCESS  read-only
    STATUS  current
    DESCRIPTION
      "Byte count when CIFS failed because TCP
       acceleration was not configured to remote WX.
      "
    ::= { jnxWxGrpStatsSysCifs 3 }

jnxWxGrpStatsSysCifsFailTcpAcclToRemotePkts OBJECT-TYPE
    SYNTAX  Counter64
    MAX-ACCESS  read-only
    STATUS  current
    DESCRIPTION
      "Packet count when CIFS failed because TCP
       acceleration was not configured to remote WX.
      "
    ::= { jnxWxGrpStatsSysCifs 4 }

jnxWxGrpStatsSysCifsFailTcpAcclFailedBytes OBJECT-TYPE
    SYNTAX  Counter64
    MAX-ACCESS  read-only
    STATUS  current
    DESCRIPTION
      "Byte count when CIFS failed because TCP
       acceleration to remote WX failed.
			"
    ::= { jnxWxGrpStatsSysCifs 5 }

jnxWxGrpStatsSysCifsFailTcpAcclFailedPkts OBJECT-TYPE
    SYNTAX  Counter64
    MAX-ACCESS  read-only
    STATUS  current
    DESCRIPTION
      "Packet count when CIFS failed because TCP
       acceleration to remote WX failed.
      "
    ::= { jnxWxGrpStatsSysCifs 6 }

------------------------------
-- System Exchange Statistics 
------------------------------

jnxWxGrpStatsSysExchange OBJECT-IDENTITY
    STATUS  current
    DESCRIPTION
      "This group contains Exchange statistics at the system level.
      "
    ::= { jnxWxGrpStatsSys 4 }

jnxWxGrpStatsSysExchangeFailAppDefBytes OBJECT-TYPE
    SYNTAX  Counter64
    MAX-ACCESS  read-only
    STATUS  current
    DESCRIPTION
      "Byte count when Exchange acceleration failed because
       application definition did not enable CIFS.
      "
    ::= { jnxWxGrpStatsSysExchange 1 }

jnxWxGrpStatsSysExchangeFailAppDefPkts OBJECT-TYPE
    SYNTAX  Counter64
    MAX-ACCESS  read-only
    STATUS  current
    DESCRIPTION
      "Packet count when Exchange acceleration failed because
       application definition did not enable CIFS.
      "
    ::= { jnxWxGrpStatsSysExchange 2 }

jnxWxGrpStatsSysExchangeFailTcpAcclToRemoteBytes OBJECT-TYPE
    SYNTAX  Counter64
    MAX-ACCESS  read-only
    STATUS  current
    DESCRIPTION
      "Byte count when Exchange failed because TCP
       acceleration was not configured to remote WX.
      "
    ::= { jnxWxGrpStatsSysExchange 3 }

jnxWxGrpStatsSysExchangeFailTcpAcclToRemotePkts OBJECT-TYPE
    SYNTAX  Counter64
    MAX-ACCESS  read-only
    STATUS  current
    DESCRIPTION
      "Packet count when Exchange failed because TCP
       acceleration was not configured to remote WX.
      "
    ::= { jnxWxGrpStatsSysExchange 4 }

jnxWxGrpStatsSysExchangeFailTcpAcclFailedBytes OBJECT-TYPE
    SYNTAX  Counter64
    MAX-ACCESS  read-only
    STATUS  current
    DESCRIPTION
      "Byte count when Exchange failed because TCP
       acceleration to remote WX failed.
			"
    ::= { jnxWxGrpStatsSysExchange 5 }

jnxWxGrpStatsSysExchangeFailTcpAcclFailedPkts OBJECT-TYPE
    SYNTAX  Counter64
    MAX-ACCESS  read-only
    STATUS  current
    DESCRIPTION
      "Packet count when Exchange failed because TCP
       acceleration to remote WX failed.
      "
    ::= { jnxWxGrpStatsSysExchange 6 }

jnxWxGrpStatsAccl OBJECT-IDENTITY
    STATUS  current
    DESCRIPTION
      "This group contains general acceleration statistics.
      "
    ::= { jnxWxGrpStats 2 }

------------------------------------------------------------------
-- TCP Acceleration Statistics for each Application and Remote Wx 
------------------------------------------------------------------

jnxWxGrpStatsTcpAcclTable OBJECT-TYPE
    SYNTAX  SEQUENCE OF JnxWxGrpStatsTcpAcclEntry
    MAX-ACCESS  not-accessible
    STATUS  current
    DESCRIPTION
      "This table displays the TCP acceleration statistics
       for each application per remote WX currently being monitored.
      "
    ::= { jnxWxGrpStatsAccl 1 }

jnxWxGrpStatsTcpAcclEntry OBJECT-TYPE
    SYNTAX  JnxWxGrpStatsTcpAcclEntry
    MAX-ACCESS  not-accessible
    STATUS  current
    DESCRIPTION
      "A row in jnxWxGrpStatsTcpAcclTable.
      "
    INDEX   { jnxWxGrpStatusAppId, jnxWxGrpStatusRemoteWxId }
    ::= { jnxWxGrpStatsTcpAcclTable 1 }

JnxWxGrpStatsTcpAcclEntry ::=
    SEQUENCE
    {
      jnxWxGrpStatsTcpAcclPtFlows
        Counter,
      jnxWxGrpStatsTcpAcclProxyFlows
        Counter,
      jnxWxGrpStatsTcpAcclPtFlowsDiff
        Counter,
      jnxWxGrpStatsTcpAcclProxyRequestsDiff
        Counter,
      jnxWxGrpStatsTcpAcclProxyFlowsDiff
        Counter,
      jnxWxGrpStatsTcpAcclFailedToProxyDiff
        Counter
    }

jnxWxGrpStatsTcpAcclPtFlows OBJECT-TYPE
    SYNTAX  Counter
    MAX-ACCESS  read-only
    STATUS  current
    DESCRIPTION
      "The number of flows that are currently passthru.
      "
    ::= { jnxWxGrpStatsTcpAcclEntry 1 }

jnxWxGrpStatsTcpAcclProxyFlows OBJECT-TYPE
    SYNTAX  Counter
    MAX-ACCESS  read-only
    STATUS  current
    DESCRIPTION
      "The number of flows that are currently being proxied.
      "
    ::= { jnxWxGrpStatsTcpAcclEntry 2 }

jnxWxGrpStatsTcpAcclPtFlowsDiff OBJECT-TYPE
    SYNTAX  Counter
    MAX-ACCESS  read-only
    STATUS  current
    DESCRIPTION
      "The number of flows that went passthru for this app in 
       last interval (10 sec). These will be delta stats.
      "
    ::= { jnxWxGrpStatsTcpAcclEntry 3 }

jnxWxGrpStatsTcpAcclProxyRequestsDiff OBJECT-TYPE
    SYNTAX  Counter
    MAX-ACCESS  read-only
    STATUS  current
    DESCRIPTION
      "The number of proxy flow request received in last sampling 
       interval (10 sec). These will be delta stats.
      "
    ::= { jnxWxGrpStatsTcpAcclEntry 4 }

jnxWxGrpStatsTcpAcclProxyFlowsDiff OBJECT-TYPE
    SYNTAX  Counter
    MAX-ACCESS  read-only
    STATUS  current
    DESCRIPTION
      "The number of flows we decided to proxy in last sampling 
       interval (10 sec). These will be delta stats.
      "
    ::= { jnxWxGrpStatsTcpAcclEntry 5 }

jnxWxGrpStatsTcpAcclFailedToProxyDiff OBJECT-TYPE
    SYNTAX  Counter
    MAX-ACCESS  read-only
    STATUS  current
    DESCRIPTION
      "The number of flows that could not be proxied for whatever 
       reasons in last sampling interval (10 sec).
      "
    ::= { jnxWxGrpStatsTcpAcclEntry 6 }

--------------------------------
-- Compression Statistics Group 
--------------------------------

jnxWxGrpStatsComp OBJECT-IDENTITY
    STATUS  current
    DESCRIPTION
      "This group contains compression statistics.
      "
    ::= { jnxWxGrpStats 3 }


jnxWxGrpStatsCompTable OBJECT-TYPE
    SYNTAX  SEQUENCE OF JnxWxGrpStatsCompEntry
    MAX-ACCESS  not-accessible
    STATUS  current
    DESCRIPTION
      "This table displays the compression statistics
       for each application per remote WX currently being monitored.
      "
    ::= { jnxWxGrpStatsComp 1 }

jnxWxGrpStatsCompEntry OBJECT-TYPE
    SYNTAX  JnxWxGrpStatsCompEntry
    MAX-ACCESS  not-accessible
    STATUS  current
    DESCRIPTION
      "A row in jnxWxGrpStatsCompTable.
      "
    INDEX   { jnxWxGrpStatusAppId, jnxWxGrpStatusRemoteWxId }
    ::= { jnxWxGrpStatsCompTable 1 }

JnxWxGrpStatsCompEntry ::=
    SEQUENCE
    {
      jnxWxGrpStatsCompBytesIn
        Counter64,
      jnxWxGrpStatsCompBytesOut
        Counter64,
      jnxWxGrpStatsCompCacheHits
        Counter64,
      jnxWxGrpStatsCompCacheMisses
        Counter64
    }

jnxWxGrpStatsCompBytesIn OBJECT-TYPE
    SYNTAX  Counter64
    MAX-ACCESS  read-only
    STATUS  current
    DESCRIPTION
      "The number of bytes in.
      "
    ::= { jnxWxGrpStatsCompEntry 1 }

jnxWxGrpStatsCompBytesOut OBJECT-TYPE
    SYNTAX  Counter64
    MAX-ACCESS  read-only
    STATUS  current
    DESCRIPTION
      "The number of bytes out.
      "
    ::= { jnxWxGrpStatsCompEntry 2 }

jnxWxGrpStatsCompCacheHits OBJECT-TYPE
    SYNTAX  Counter64
    MAX-ACCESS  read-only
    STATUS  current
    DESCRIPTION
      "The number of cache hits.
      "
    ::= { jnxWxGrpStatsCompEntry 3 }

jnxWxGrpStatsCompCacheMisses OBJECT-TYPE
    SYNTAX  Counter64
    MAX-ACCESS  read-only
    STATUS  current
    DESCRIPTION
      "The number of cache misses.
      "
    ::= { jnxWxGrpStatsCompEntry 4 }


jnxWxGrpStatsWanPerf OBJECT-IDENTITY
    STATUS  current
    DESCRIPTION
      "This group contains WAN performance statistics.
      "
    ::= { jnxWxGrpStats 4 }

jnxWxGrpStatsWanPerfTable OBJECT-TYPE
    SYNTAX  SEQUENCE OF JnxWxGrpStatsWanPerfEntry
    MAX-ACCESS  not-accessible
    STATUS  current
    DESCRIPTION
      "This table displays the WAN performance statistics
       for each application per remote WX currently being monitored.
      "
    ::= { jnxWxGrpStatsWanPerf 1 }

jnxWxGrpStatsWanPerfEntry OBJECT-TYPE
    SYNTAX  JnxWxGrpStatsWanPerfEntry
    MAX-ACCESS  not-accessible
    STATUS  current
    DESCRIPTION
      "A row in jnxWxGrpStatsWanPerfTable.
      "
    INDEX   { jnxWxGrpStatusAppId, jnxWxGrpStatusRemoteWxId }
    ::= { jnxWxGrpStatsWanPerfTable 1 }

JnxWxGrpStatsWanPerfEntry ::=
    SEQUENCE
    {
      jnxWxGrpStatsWanPerfBytesToWan
        Counter64,
      jnxWxGrpStatsWanPerfBytesFromWan
        Counter64
    }

jnxWxGrpStatsWanPerfBytesToWan OBJECT-TYPE
    SYNTAX  Counter64
    MAX-ACCESS  read-only
    STATUS  current
    DESCRIPTION
      "The number of bytes to WAN.
      "
    ::= { jnxWxGrpStatsWanPerfEntry 1 }

jnxWxGrpStatsWanPerfBytesFromWan OBJECT-TYPE
    SYNTAX  Counter64
    MAX-ACCESS  read-only
    STATUS  current
    DESCRIPTION
      "The number of bytes from WAN.
      "
    ::= { jnxWxGrpStatsWanPerfEntry 2 }

END

--End - JUNIPER-WX-STATS-MIB Module
