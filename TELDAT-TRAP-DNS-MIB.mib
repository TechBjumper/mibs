-- file automatically created


TELDAT-TRAP-DNS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


dnsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DNS event subsystem."
    REVISION "201401200930Z"
    DESCRIPTION "Initial implementation"
        ::= { telEventTraps 152 }


dnsEventsGroup	OBJECT IDENTIFIER	::= { dnsTrapsMIB 1 }

dnsNotifications	OBJECT IDENTIFIER	::= { dnsTrapsMIB 2 }
dnsNotificationsPrefix	OBJECT IDENTIFIER	::= { dnsNotifications 0 }

dnsEventObjects3 OBJECT-IDENTITY
    STATUS current
    DESCRIPTION
        "Event DNS.3
        Standard DNS query for a given name to a name server. The identifier of
        the query and the remote ip address of the remote name server are shown."
    ::= { dnsEventsGroup 3 }

dns3-identifier OBJECT-TYPE
    SYNTAX Integer32
    MAX-ACCESS accessible-for-notify
    STATUS current
    DESCRIPTION
        "Parameter 'identifier' in event DNS.3"
    ::= { dnsEventObjects3 1 }

dns3-name OBJECT-TYPE
    SYNTAX DisplayString
    MAX-ACCESS accessible-for-notify
    STATUS current
    DESCRIPTION
        "Parameter 'name' in event DNS.3"
    ::= { dnsEventObjects3 2 }

dns3-ip-address OBJECT-TYPE
    SYNTAX IpAddress
    MAX-ACCESS accessible-for-notify
    STATUS current
    DESCRIPTION
        "Parameter 'ip-address' in event DNS.3"
    ::= { dnsEventObjects3 3 }

dnsEventObjects4 OBJECT-IDENTITY
    STATUS current
    DESCRIPTION
        "Event DNS.4
        A packet too short was received. The packet is discarded without
        processing."
    ::= { dnsEventsGroup 4 }

dns4-length OBJECT-TYPE
    SYNTAX Integer32
    MAX-ACCESS accessible-for-notify
    STATUS current
    DESCRIPTION
        "Parameter 'length' in event DNS.4"
    ::= { dnsEventObjects4 1 }

dnsEventObjects6 OBJECT-IDENTITY
    STATUS current
    DESCRIPTION
        "Event DNS.6
        A response for a query not present was received. The packet is discarded."
    ::= { dnsEventsGroup 6 }

dns6-identifier OBJECT-TYPE
    SYNTAX Integer32
    MAX-ACCESS accessible-for-notify
    STATUS current
    DESCRIPTION
        "Parameter 'identifier' in event DNS.6"
    ::= { dnsEventObjects6 1 }

dns6-name OBJECT-TYPE
    SYNTAX DisplayString
    MAX-ACCESS accessible-for-notify
    STATUS current
    DESCRIPTION
        "Parameter 'name' in event DNS.6"
    ::= { dnsEventObjects6 2 }

dnsEventObjects7 OBJECT-IDENTITY
    STATUS current
    DESCRIPTION
        "Event DNS.7
        A response for a query was received."
    ::= { dnsEventsGroup 7 }

dns7-identifier OBJECT-TYPE
    SYNTAX Integer32
    MAX-ACCESS accessible-for-notify
    STATUS current
    DESCRIPTION
        "Parameter 'identifier' in event DNS.7"
    ::= { dnsEventObjects7 1 }

dns7-name OBJECT-TYPE
    SYNTAX DisplayString
    MAX-ACCESS accessible-for-notify
    STATUS current
    DESCRIPTION
        "Parameter 'name' in event DNS.7"
    ::= { dnsEventObjects7 2 }

dns7-rcode OBJECT-TYPE
    SYNTAX Integer32
    MAX-ACCESS accessible-for-notify
    STATUS current
    DESCRIPTION
        "Parameter 'rcode' in event DNS.7"
    ::= { dnsEventObjects7 3 }

dns7-qdcount OBJECT-TYPE
    SYNTAX Integer32
    MAX-ACCESS accessible-for-notify
    STATUS current
    DESCRIPTION
        "Parameter 'qdcount' in event DNS.7"
    ::= { dnsEventObjects7 4 }

dns7-ancount OBJECT-TYPE
    SYNTAX Integer32
    MAX-ACCESS accessible-for-notify
    STATUS current
    DESCRIPTION
        "Parameter 'ancount' in event DNS.7"
    ::= { dnsEventObjects7 5 }

dns7-nscount OBJECT-TYPE
    SYNTAX Integer32
    MAX-ACCESS accessible-for-notify
    STATUS current
    DESCRIPTION
        "Parameter 'nscount' in event DNS.7"
    ::= { dnsEventObjects7 6 }

dnsEventObjects8 OBJECT-IDENTITY
    STATUS current
    DESCRIPTION
        "Event DNS.8
        A response has an answer field that does not match the query."
    ::= { dnsEventsGroup 8 }

dns8-identifier OBJECT-TYPE
    SYNTAX Integer32
    MAX-ACCESS accessible-for-notify
    STATUS current
    DESCRIPTION
        "Parameter 'identifier' in event DNS.8"
    ::= { dnsEventObjects8 1 }

dnsEventObjects9 OBJECT-IDENTITY
    STATUS current
    DESCRIPTION
        "Event DNS.9
        A response has an answer field with a bad data format."
    ::= { dnsEventsGroup 9 }

dns9-identifier OBJECT-TYPE
    SYNTAX Integer32
    MAX-ACCESS accessible-for-notify
    STATUS current
    DESCRIPTION
        "Parameter 'identifier' in event DNS.9"
    ::= { dnsEventObjects9 1 }

dnsEventObjects10 OBJECT-IDENTITY
    STATUS current
    DESCRIPTION
        "Event DNS.10
        Answer field with CNAME."
    ::= { dnsEventsGroup 10 }

dns10-identifier OBJECT-TYPE
    SYNTAX Integer32
    MAX-ACCESS accessible-for-notify
    STATUS current
    DESCRIPTION
        "Parameter 'identifier' in event DNS.10"
    ::= { dnsEventObjects10 1 }

dns10-cname OBJECT-TYPE
    SYNTAX DisplayString
    MAX-ACCESS accessible-for-notify
    STATUS current
    DESCRIPTION
        "Parameter 'cname' in event DNS.10"
    ::= { dnsEventObjects10 2 }

dnsEventObjects11 OBJECT-IDENTITY
    STATUS current
    DESCRIPTION
        "Event DNS.11
        An answer field with an unexpected qtype has been detected. The answer
        is not processed."
    ::= { dnsEventsGroup 11 }

dns11-qtype OBJECT-TYPE
    SYNTAX Integer32
    MAX-ACCESS accessible-for-notify
    STATUS current
    DESCRIPTION
        "Parameter 'qtype' in event DNS.11"
    ::= { dnsEventObjects11 1 }

dns11-identifier OBJECT-TYPE
    SYNTAX Integer32
    MAX-ACCESS accessible-for-notify
    STATUS current
    DESCRIPTION
        "Parameter 'identifier' in event DNS.11"
    ::= { dnsEventObjects11 2 }

dnsEventObjects12 OBJECT-IDENTITY
    STATUS current
    DESCRIPTION
        "Event DNS.12
        An answer field with an unexpected class has been detected. The answer
        is not processed."
    ::= { dnsEventsGroup 12 }

dns12-qclass OBJECT-TYPE
    SYNTAX Integer32
    MAX-ACCESS accessible-for-notify
    STATUS current
    DESCRIPTION
        "Parameter 'qclass' in event DNS.12"
    ::= { dnsEventObjects12 1 }

dns12-identifier OBJECT-TYPE
    SYNTAX Integer32
    MAX-ACCESS accessible-for-notify
    STATUS current
    DESCRIPTION
        "Parameter 'identifier' in event DNS.12"
    ::= { dnsEventObjects12 2 }

dnsEventObjects13 OBJECT-IDENTITY
    STATUS current
    DESCRIPTION
        "Event DNS.13
        A SOA answer field has been received."
    ::= { dnsEventsGroup 13 }

dns13-identifier OBJECT-TYPE
    SYNTAX Integer32
    MAX-ACCESS accessible-for-notify
    STATUS current
    DESCRIPTION
        "Parameter 'identifier' in event DNS.13"
    ::= { dnsEventObjects13 1 }

dnsEventObjects14 OBJECT-IDENTITY
    STATUS current
    DESCRIPTION
        "Event DNS.14
        A NS answer field has been received."
    ::= { dnsEventsGroup 14 }

dns14-identifier OBJECT-TYPE
    SYNTAX Integer32
    MAX-ACCESS accessible-for-notify
    STATUS current
    DESCRIPTION
        "Parameter 'identifier' in event DNS.14"
    ::= { dnsEventObjects14 1 }

dnsEventObjects15 OBJECT-IDENTITY
    STATUS current
    DESCRIPTION
        "Event DNS.15
        An answer to a non pending query has been received. It is discarded."
    ::= { dnsEventsGroup 15 }

dns15-status OBJECT-TYPE
    SYNTAX DisplayString
    MAX-ACCESS accessible-for-notify
    STATUS current
    DESCRIPTION
        "Parameter 'status' in event DNS.15"
    ::= { dnsEventObjects15 1 }

dns15-identifier OBJECT-TYPE
    SYNTAX Integer32
    MAX-ACCESS accessible-for-notify
    STATUS current
    DESCRIPTION
        "Parameter 'identifier' in event DNS.15"
    ::= { dnsEventObjects15 2 }

dnsEventObjects16 OBJECT-IDENTITY
    STATUS current
    DESCRIPTION
        "Event DNS.16
        A name served is flagged as invalid because of an unexpected answer to
        a query."
    ::= { dnsEventsGroup 16 }

dns16-name-server OBJECT-TYPE
    SYNTAX DisplayString
    MAX-ACCESS accessible-for-notify
    STATUS current
    DESCRIPTION
        "Parameter 'name-server' in event DNS.16"
    ::= { dnsEventObjects16 1 }

dns16-identifier OBJECT-TYPE
    SYNTAX Integer32
    MAX-ACCESS accessible-for-notify
    STATUS current
    DESCRIPTION
        "Parameter 'identifier' in event DNS.16"
    ::= { dnsEventObjects16 2 }

dnsEventObjects17 OBJECT-IDENTITY
    STATUS current
    DESCRIPTION
        "Event DNS.17
        A name served is for a given domain is added to the queue of valid
        name servers for a query."
    ::= { dnsEventsGroup 17 }

dns17-name-server OBJECT-TYPE
    SYNTAX DisplayString
    MAX-ACCESS accessible-for-notify
    STATUS current
    DESCRIPTION
        "Parameter 'name-server' in event DNS.17"
    ::= { dnsEventObjects17 1 }

dns17-domain OBJECT-TYPE
    SYNTAX DisplayString
    MAX-ACCESS accessible-for-notify
    STATUS current
    DESCRIPTION
        "Parameter 'domain' in event DNS.17"
    ::= { dnsEventObjects17 2 }

dns17-identifier OBJECT-TYPE
    SYNTAX Integer32
    MAX-ACCESS accessible-for-notify
    STATUS current
    DESCRIPTION
        "Parameter 'identifier' in event DNS.17"
    ::= { dnsEventObjects17 3 }

dnsEventObjects18 OBJECT-IDENTITY
    STATUS current
    DESCRIPTION
        "Event DNS.18
        There was not memory enough to kill a given query. This may cause
        unexpected behaviour of the equipment."
    ::= { dnsEventsGroup 18 }

dns18-name OBJECT-TYPE
    SYNTAX DisplayString
    MAX-ACCESS accessible-for-notify
    STATUS current
    DESCRIPTION
        "Parameter 'name' in event DNS.18"
    ::= { dnsEventObjects18 1 }

dnsEventObjects19 OBJECT-IDENTITY
    STATUS current
    DESCRIPTION
        "Event DNS.19
        A query has been killed by the user."
    ::= { dnsEventsGroup 19 }

dns19-name OBJECT-TYPE
    SYNTAX DisplayString
    MAX-ACCESS accessible-for-notify
    STATUS current
    DESCRIPTION
        "Parameter 'name' in event DNS.19"
    ::= { dnsEventObjects19 1 }

dnsEventObjects20 OBJECT-IDENTITY
    STATUS current
    DESCRIPTION
        "Event DNS.20
        A response to a query has been detected with the TC (truncated) bit set."
    ::= { dnsEventsGroup 20 }

dns20-identifier OBJECT-TYPE
    SYNTAX Integer32
    MAX-ACCESS accessible-for-notify
    STATUS current
    DESCRIPTION
        "Parameter 'identifier' in event DNS.20"
    ::= { dnsEventObjects20 1 }

dnsEventObjects21 OBJECT-IDENTITY
    STATUS current
    DESCRIPTION
        "Event DNS.21
        Generic DNS CACHE trace."
    ::= { dnsEventsGroup 21 }

dns21-data OBJECT-TYPE
    SYNTAX DisplayString
    MAX-ACCESS accessible-for-notify
    STATUS current
    DESCRIPTION
        "Parameter 'data' in event DNS.21"
    ::= { dnsEventObjects21 1 }

dnsEventObjects22 OBJECT-IDENTITY
    STATUS current
    DESCRIPTION
        "Event DNS.22
        Generic Resource Record received from DNS server."
    ::= { dnsEventsGroup 22 }

dns22-ip-add OBJECT-TYPE
    SYNTAX IpAddress
    MAX-ACCESS accessible-for-notify
    STATUS current
    DESCRIPTION
        "Parameter 'ip-add' in event DNS.22"
    ::= { dnsEventObjects22 1 }

dns22-ttl OBJECT-TYPE
    SYNTAX Integer32
    MAX-ACCESS accessible-for-notify
    STATUS current
    DESCRIPTION
        "Parameter 'ttl' in event DNS.22"
    ::= { dnsEventObjects22 2 }

dns22-type OBJECT-TYPE
    SYNTAX DisplayString
    MAX-ACCESS accessible-for-notify
    STATUS current
    DESCRIPTION
        "Parameter 'type' in event DNS.22"
    ::= { dnsEventObjects22 3 }

dns22-name1 OBJECT-TYPE
    SYNTAX DisplayString
    MAX-ACCESS accessible-for-notify
    STATUS current
    DESCRIPTION
        "Parameter 'name1' in event DNS.22"
    ::= { dnsEventObjects22 4 }

dns22-name2 OBJECT-TYPE
    SYNTAX DisplayString
    MAX-ACCESS accessible-for-notify
    STATUS current
    DESCRIPTION
        "Parameter 'name2' in event DNS.22"
    ::= { dnsEventObjects22 5 }

dnsEventObjects23 OBJECT-IDENTITY
    STATUS current
    DESCRIPTION
        "Event DNS.23
        Resource Record received from DNS server."
    ::= { dnsEventsGroup 23 }

dns23-number OBJECT-TYPE
    SYNTAX Integer32
    MAX-ACCESS accessible-for-notify
    STATUS current
    DESCRIPTION
        "Parameter 'number' in event DNS.23"
    ::= { dnsEventObjects23 1 }

dns23-ip-add OBJECT-TYPE
    SYNTAX IpAddress
    MAX-ACCESS accessible-for-notify
    STATUS current
    DESCRIPTION
        "Parameter 'ip-add' in event DNS.23"
    ::= { dnsEventObjects23 2 }

dns23-port OBJECT-TYPE
    SYNTAX Integer32
    MAX-ACCESS accessible-for-notify
    STATUS current
    DESCRIPTION
        "Parameter 'port' in event DNS.23"
    ::= { dnsEventObjects23 3 }

dns23-id OBJECT-TYPE
    SYNTAX Integer32
    MAX-ACCESS accessible-for-notify
    STATUS current
    DESCRIPTION
        "Parameter 'id' in event DNS.23"
    ::= { dnsEventObjects23 4 }

dns23-type OBJECT-TYPE
    SYNTAX DisplayString
    MAX-ACCESS accessible-for-notify
    STATUS current
    DESCRIPTION
        "Parameter 'type' in event DNS.23"
    ::= { dnsEventObjects23 5 }

dns23-name OBJECT-TYPE
    SYNTAX DisplayString
    MAX-ACCESS accessible-for-notify
    STATUS current
    DESCRIPTION
        "Parameter 'name' in event DNS.23"
    ::= { dnsEventObjects23 6 }

dnsEventObjects24 OBJECT-IDENTITY
    STATUS current
    DESCRIPTION
        "Event DNS.24
        MX type Resource Record received from DNS server."
    ::= { dnsEventsGroup 24 }

dns24-ip-add OBJECT-TYPE
    SYNTAX IpAddress
    MAX-ACCESS accessible-for-notify
    STATUS current
    DESCRIPTION
        "Parameter 'ip-add' in event DNS.24"
    ::= { dnsEventObjects24 1 }

dns24-ttl OBJECT-TYPE
    SYNTAX Integer32
    MAX-ACCESS accessible-for-notify
    STATUS current
    DESCRIPTION
        "Parameter 'ttl' in event DNS.24"
    ::= { dnsEventObjects24 2 }

dns24-name1 OBJECT-TYPE
    SYNTAX DisplayString
    MAX-ACCESS accessible-for-notify
    STATUS current
    DESCRIPTION
        "Parameter 'name1' in event DNS.24"
    ::= { dnsEventObjects24 3 }

dns24-number OBJECT-TYPE
    SYNTAX Integer32
    MAX-ACCESS accessible-for-notify
    STATUS current
    DESCRIPTION
        "Parameter 'number' in event DNS.24"
    ::= { dnsEventObjects24 4 }

dns24-name2 OBJECT-TYPE
    SYNTAX DisplayString
    MAX-ACCESS accessible-for-notify
    STATUS current
    DESCRIPTION
        "Parameter 'name2' in event DNS.24"
    ::= { dnsEventObjects24 5 }

dnsEventObjects25 OBJECT-IDENTITY
    STATUS current
    DESCRIPTION
        "Event DNS.25
        Record found in DNS cache."
    ::= { dnsEventsGroup 25 }

dns25-type OBJECT-TYPE
    SYNTAX DisplayString
    MAX-ACCESS accessible-for-notify
    STATUS current
    DESCRIPTION
        "Parameter 'type' in event DNS.25"
    ::= { dnsEventObjects25 1 }

dns25-name1 OBJECT-TYPE
    SYNTAX DisplayString
    MAX-ACCESS accessible-for-notify
    STATUS current
    DESCRIPTION
        "Parameter 'name1' in event DNS.25"
    ::= { dnsEventObjects25 2 }

dns25-name2 OBJECT-TYPE
    SYNTAX DisplayString
    MAX-ACCESS accessible-for-notify
    STATUS current
    DESCRIPTION
        "Parameter 'name2' in event DNS.25"
    ::= { dnsEventObjects25 3 }

dnsEventObjects26 OBJECT-IDENTITY
    STATUS current
    DESCRIPTION
        "Event DNS.26
        Record found in DNS cache."
    ::= { dnsEventsGroup 26 }

dns26-type OBJECT-TYPE
    SYNTAX DisplayString
    MAX-ACCESS accessible-for-notify
    STATUS current
    DESCRIPTION
        "Parameter 'type' in event DNS.26"
    ::= { dnsEventObjects26 1 }

dns26-name1 OBJECT-TYPE
    SYNTAX DisplayString
    MAX-ACCESS accessible-for-notify
    STATUS current
    DESCRIPTION
        "Parameter 'name1' in event DNS.26"
    ::= { dnsEventObjects26 2 }

dnsEventObjects27 OBJECT-IDENTITY
    STATUS current
    DESCRIPTION
        "Event DNS.27
        Show current DNS statistics."
    ::= { dnsEventsGroup 27 }

dns27-queries OBJECT-TYPE
    SYNTAX Integer32
    MAX-ACCESS accessible-for-notify
    STATUS current
    DESCRIPTION
        "Parameter 'queries' in event DNS.27"
    ::= { dnsEventObjects27 1 }

dns27-cache OBJECT-TYPE
    SYNTAX Integer32
    MAX-ACCESS accessible-for-notify
    STATUS current
    DESCRIPTION
        "Parameter 'cache' in event DNS.27"
    ::= { dnsEventObjects27 2 }

dns27-udp OBJECT-TYPE
    SYNTAX Integer32
    MAX-ACCESS accessible-for-notify
    STATUS current
    DESCRIPTION
        "Parameter 'udp' in event DNS.27"
    ::= { dnsEventObjects27 3 }

dns27-tcp OBJECT-TYPE
    SYNTAX Integer32
    MAX-ACCESS accessible-for-notify
    STATUS current
    DESCRIPTION
        "Parameter 'tcp' in event DNS.27"
    ::= { dnsEventObjects27 4 }

dnsEventObjects28 OBJECT-IDENTITY
    STATUS current
    DESCRIPTION
        "Event DNS.28
        A DNS probe is completed."
    ::= { dnsEventsGroup 28 }

dns28-result OBJECT-TYPE
    SYNTAX DisplayString
    MAX-ACCESS accessible-for-notify
    STATUS current
    DESCRIPTION
        "Parameter 'result' in event DNS.28"
    ::= { dnsEventObjects28 1 }

dns28-identifier OBJECT-TYPE
    SYNTAX Integer32
    MAX-ACCESS accessible-for-notify
    STATUS current
    DESCRIPTION
        "Parameter 'identifier' in event DNS.28"
    ::= { dnsEventObjects28 2 }

dns28-url OBJECT-TYPE
    SYNTAX DisplayString
    MAX-ACCESS accessible-for-notify
    STATUS current
    DESCRIPTION
        "Parameter 'url' in event DNS.28"
    ::= { dnsEventObjects28 3 }

dns28-resolve-time OBJECT-TYPE
    SYNTAX Integer32
    MAX-ACCESS accessible-for-notify
    STATUS current
    DESCRIPTION
        "Parameter 'resolve-time' in event DNS.28"
    ::= { dnsEventObjects28 4 }

dnsEventObjects30 OBJECT-IDENTITY
    STATUS current
    DESCRIPTION
        "Event DNS.30
        Generic trace."
    ::= { dnsEventsGroup 30 }

dns30-string OBJECT-TYPE
    SYNTAX DisplayString
    MAX-ACCESS accessible-for-notify
    STATUS current
    DESCRIPTION
        "Parameter 'string' in event DNS.30"
    ::= { dnsEventObjects30 1 }


dnsNotification1 NOTIFICATION-TYPE
    STATUS current
    DESCRIPTION
        "Notification of Event DNS.1

        Message: 'no memory'

        There was not memory enough to continue with the DNS resolver processing."
    ::= { dnsNotificationsPrefix 1 }

dnsNotification2 NOTIFICATION-TYPE
    STATUS current
    DESCRIPTION
        "Notification of Event DNS.2

        Message: 'no dns servers configured'

        There are not dns servers configured. The DNS resolver will not be
        available."
    ::= { dnsNotificationsPrefix 2 }

dnsNotification3 NOTIFICATION-TYPE
    OBJECTS { 
              dns3-identifier, 
              dns3-name,
              dns3-ip-address 
            }
    STATUS current
    DESCRIPTION
        "Notification of Event DNS.3

        Message: 'sending standard query with identifier=$1 for name=$2 to ip address=$3'

        Parameters list:
              $1: dns3-identifier
              $2: dns3-name
              $3: dns3-ip-address

        Standard DNS query for a given name to a name server. The identifier of
        the query and the remote ip address of the remote name server are shown."
    ::= { dnsNotificationsPrefix 3 }

dnsNotification4 NOTIFICATION-TYPE
    OBJECTS { 
              dns4-length 
            }
    STATUS current
    DESCRIPTION
        "Notification of Event DNS.4

        Message: 'discarded received packet, length=$1'

        Parameters list:
              $1: dns4-length

        A packet too short was received. The packet is discarded without
        processing."
    ::= { dnsNotificationsPrefix 4 }

dnsNotification5 NOTIFICATION-TYPE
    STATUS current
    DESCRIPTION
        "Notification of Event DNS.5

        Message: 'discarded received packet, name error'

        A packet with an incorrect dns name was received. The packet is discarded."
    ::= { dnsNotificationsPrefix 5 }

dnsNotification6 NOTIFICATION-TYPE
    OBJECTS { 
              dns6-identifier, 
              dns6-name 
            }
    STATUS current
    DESCRIPTION
        "Notification of Event DNS.6

        Message: 'query not found, identifier=$1, name=$2, discarded'

        Parameters list:
              $1: dns6-identifier
              $2: dns6-name

        A response for a query not present was received. The packet is discarded."
    ::= { dnsNotificationsPrefix 6 }

dnsNotification7 NOTIFICATION-TYPE
    OBJECTS { 
              dns7-identifier, 
              dns7-name,
              dns7-rcode,
              dns7-qdcount,
              dns7-ancount,
              dns7-nscount 
            }
    STATUS current
    DESCRIPTION
        "Notification of Event DNS.7

        Message: 'received query response with identifier=$1 for name=$2, rcode=$3, qdcount=$4, ancount=$5, nscount=$6'

        Parameters list:
              $1: dns7-identifier
              $2: dns7-name
              $3: dns7-rcode
              $4: dns7-qdcount
              $5: dns7-ancount
              $6: dns7-nscount

        A response for a query was received."
    ::= { dnsNotificationsPrefix 7 }

dnsNotification8 NOTIFICATION-TYPE
    OBJECTS { 
              dns8-identifier 
            }
    STATUS current
    DESCRIPTION
        "Notification of Event DNS.8

        Message: 'received answer does not match query, identifier=$1'

        Parameters list:
              $1: dns8-identifier

        A response has an answer field that does not match the query."
    ::= { dnsNotificationsPrefix 8 }

dnsNotification9 NOTIFICATION-TYPE
    OBJECTS { 
              dns9-identifier 
            }
    STATUS current
    DESCRIPTION
        "Notification of Event DNS.9

        Message: 'answer data error, query identifier=$1'

        Parameters list:
              $1: dns9-identifier

        A response has an answer field with a bad data format."
    ::= { dnsNotificationsPrefix 9 }

dnsNotification10 NOTIFICATION-TYPE
    OBJECTS { 
              dns10-identifier, 
              dns10-cname 
            }
    STATUS current
    DESCRIPTION
        "Notification of Event DNS.10

        Message: 'found cname, query identifier=$1, cname=$2'

        Parameters list:
              $1: dns10-identifier
              $2: dns10-cname

        Answer field with CNAME."
    ::= { dnsNotificationsPrefix 10 }

dnsNotification11 NOTIFICATION-TYPE
    OBJECTS { 
              dns11-qtype, 
              dns11-identifier 
            }
    STATUS current
    DESCRIPTION
        "Notification of Event DNS.11

        Message: 'answer field with qtype=$1 not processed, query identifier=$2'

        Parameters list:
              $1: dns11-qtype
              $2: dns11-identifier

        An answer field with an unexpected qtype has been detected. The answer
        is not processed."
    ::= { dnsNotificationsPrefix 11 }

dnsNotification12 NOTIFICATION-TYPE
    OBJECTS { 
              dns12-qclass, 
              dns12-identifier 
            }
    STATUS current
    DESCRIPTION
        "Notification of Event DNS.12

        Message: 'answer field with qclas=$1 not processed, query identifier=$2'

        Parameters list:
              $1: dns12-qclass
              $2: dns12-identifier

        An answer field with an unexpected class has been detected. The answer
        is not processed."
    ::= { dnsNotificationsPrefix 12 }

dnsNotification13 NOTIFICATION-TYPE
    OBJECTS { 
              dns13-identifier 
            }
    STATUS current
    DESCRIPTION
        "Notification of Event DNS.13

        Message: 'SOA answer field, query identifier=$1'

        Parameters list:
              $1: dns13-identifier

        A SOA answer field has been received."
    ::= { dnsNotificationsPrefix 13 }

dnsNotification14 NOTIFICATION-TYPE
    OBJECTS { 
              dns14-identifier 
            }
    STATUS current
    DESCRIPTION
        "Notification of Event DNS.14

        Message: 'NS answer field, query identifier=$1'

        Parameters list:
              $1: dns14-identifier

        A NS answer field has been received."
    ::= { dnsNotificationsPrefix 14 }

dnsNotification15 NOTIFICATION-TYPE
    OBJECTS { 
              dns15-status, 
              dns15-identifier 
            }
    STATUS current
    DESCRIPTION
        "Notification of Event DNS.15

        Message: 'received response discarded query $1, query identifier=$2'

        Parameters list:
              $1: dns15-status
              $2: dns15-identifier

        An answer to a non pending query has been received. It is discarded."
    ::= { dnsNotificationsPrefix 15 }

dnsNotification16 NOTIFICATION-TYPE
    OBJECTS { 
              dns16-name-server, 
              dns16-identifier 
            }
    STATUS current
    DESCRIPTION
        "Notification of Event DNS.16

        Message: 'invalid server name=$1, query identifier=$2'

        Parameters list:
              $1: dns16-name-server
              $2: dns16-identifier

        A name served is flagged as invalid because of an unexpected answer to
        a query."
    ::= { dnsNotificationsPrefix 16 }

dnsNotification17 NOTIFICATION-TYPE
    OBJECTS { 
              dns17-name-server, 
              dns17-domain,
              dns17-identifier 
            }
    STATUS current
    DESCRIPTION
        "Notification of Event DNS.17

        Message: 'added server name=$1 domain=$2, query identifier=$3'

        Parameters list:
              $1: dns17-name-server
              $2: dns17-domain
              $3: dns17-identifier

        A name served is for a given domain is added to the queue of valid
        name servers for a query."
    ::= { dnsNotificationsPrefix 17 }

dnsNotification18 NOTIFICATION-TYPE
    OBJECTS { 
              dns18-name 
            }
    STATUS current
    DESCRIPTION
        "Notification of Event DNS.18

        Message: 'no memory to kill query, name=$1'

        Parameters list:
              $1: dns18-name

        There was not memory enough to kill a given query. This may cause
        unexpected behaviour of the equipment."
    ::= { dnsNotificationsPrefix 18 }

dnsNotification19 NOTIFICATION-TYPE
    OBJECTS { 
              dns19-name 
            }
    STATUS current
    DESCRIPTION
        "Notification of Event DNS.19

        Message: 'query killed, name=$1'

        Parameters list:
              $1: dns19-name

        A query has been killed by the user."
    ::= { dnsNotificationsPrefix 19 }

dnsNotification20 NOTIFICATION-TYPE
    OBJECTS { 
              dns20-identifier 
            }
    STATUS current
    DESCRIPTION
        "Notification of Event DNS.20

        Message: 'TC bit set, query identifier=$1'

        Parameters list:
              $1: dns20-identifier

        A response to a query has been detected with the TC (truncated) bit set."
    ::= { dnsNotificationsPrefix 20 }

dnsNotification21 NOTIFICATION-TYPE
    OBJECTS { 
              dns21-data 
            }
    STATUS current
    DESCRIPTION
        "Notification of Event DNS.21

        Message: 'CACHE $1'

        Parameters list:
              $1: dns21-data

        Generic DNS CACHE trace."
    ::= { dnsNotificationsPrefix 21 }

dnsNotification22 NOTIFICATION-TYPE
    OBJECTS { 
              dns22-ip-add, 
              dns22-ttl,
              dns22-type,
              dns22-name1,
              dns22-name2 
            }
    STATUS current
    DESCRIPTION
        "Notification of Event DNS.22

        Message: 'CACHE rr ip:$1 ttl:$2 type:$3 name:$4 name:$5'

        Parameters list:
              $1: dns22-ip-add
              $2: dns22-ttl
              $3: dns22-type
              $4: dns22-name1
              $5: dns22-name2

        Generic Resource Record received from DNS server."
    ::= { dnsNotificationsPrefix 22 }

dnsNotification23 NOTIFICATION-TYPE
    OBJECTS { 
              dns23-number, 
              dns23-ip-add,
              dns23-port,
              dns23-id,
              dns23-type,
              dns23-name 
            }
    STATUS current
    DESCRIPTION
        "Notification of Event DNS.23

        Message: 'CACHE query $1 received from ip:$2 port:$3 id:$4 type:$5 name:$6'

        Parameters list:
              $1: dns23-number
              $2: dns23-ip-add
              $3: dns23-port
              $4: dns23-id
              $5: dns23-type
              $6: dns23-name

        Resource Record received from DNS server."
    ::= { dnsNotificationsPrefix 23 }

dnsNotification24 NOTIFICATION-TYPE
    OBJECTS { 
              dns24-ip-add, 
              dns24-ttl,
              dns24-name1,
              dns24-number,
              dns24-name2 
            }
    STATUS current
    DESCRIPTION
        "Notification of Event DNS.24

        Message: 'CACHE rr ip:$1 ttl:$2 type:MX name:$3 number:$4 name:$5'

        Parameters list:
              $1: dns24-ip-add
              $2: dns24-ttl
              $3: dns24-name1
              $4: dns24-number
              $5: dns24-name2

        MX type Resource Record received from DNS server."
    ::= { dnsNotificationsPrefix 24 }

dnsNotification25 NOTIFICATION-TYPE
    OBJECTS { 
              dns25-type, 
              dns25-name1,
              dns25-name2 
            }
    STATUS current
    DESCRIPTION
        "Notification of Event DNS.25

        Message: 'CACHE cached type:$1 name:$2 name:$3'

        Parameters list:
              $1: dns25-type
              $2: dns25-name1
              $3: dns25-name2

        Record found in DNS cache."
    ::= { dnsNotificationsPrefix 25 }

dnsNotification26 NOTIFICATION-TYPE
    OBJECTS { 
              dns26-type, 
              dns26-name1 
            }
    STATUS current
    DESCRIPTION
        "Notification of Event DNS.26

        Message: 'CACHE cached type:$1 name:$2'

        Parameters list:
              $1: dns26-type
              $2: dns26-name1

        Record found in DNS cache."
    ::= { dnsNotificationsPrefix 26 }

dnsNotification27 NOTIFICATION-TYPE
    OBJECTS { 
              dns27-queries, 
              dns27-cache,
              dns27-udp,
              dns27-tcp 
            }
    STATUS current
    DESCRIPTION
        "Notification of Event DNS.27

        Message: 'CACHE statistics queries:$1, cache motion:$2, udp active$3, tcp active:$4'

        Parameters list:
              $1: dns27-queries
              $2: dns27-cache
              $3: dns27-udp
              $4: dns27-tcp

        Show current DNS statistics."
    ::= { dnsNotificationsPrefix 27 }

dnsNotification28 NOTIFICATION-TYPE
    OBJECTS { 
              dns28-result, 
              dns28-identifier,
              dns28-url,
              dns28-resolve-time 
            }
    STATUS current
    DESCRIPTION
        "Notification of Event DNS.28

        Message: 'probe $1, identifier=$2 url=$3 resolve-time=$4'

        Parameters list:
              $1: dns28-result
              $2: dns28-identifier
              $3: dns28-url
              $4: dns28-resolve-time

        A DNS probe is completed."
    ::= { dnsNotificationsPrefix 28 }

dnsNotification29 NOTIFICATION-TYPE
    STATUS current
    DESCRIPTION
        "Notification of Event DNS.29

        Message: '---'

        Reserved for possible future use."
    ::= { dnsNotificationsPrefix 29 }

dnsNotification30 NOTIFICATION-TYPE
    OBJECTS { 
              dns30-string 
            }
    STATUS current
    DESCRIPTION
        "Notification of Event DNS.30

        Message: '$1'

        Parameters list:
              $1: dns30-string

        Generic trace."
    ::= { dnsNotificationsPrefix 30 }


END
