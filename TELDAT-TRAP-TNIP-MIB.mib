-- file automatically created


TELDAT-TRAP-TNIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tnipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TNIP event subsystem."
    REVISION "201401200930Z"
    DESCRIPTION "Initial implementation"
        ::= { telEventTraps 120 }


tnipEventsGroup	OBJECT IDENTIFIER	::= { tnipTrapsMIB 1 }

tnipNotifications	OBJECT IDENTIFIER	::= { tnipTrapsMIB 2 }
tnipNotificationsPrefix	OBJECT IDENTIFIER	::= { tnipNotifications 0 }

tnipEventObjects1 OBJECT-IDENTITY
    STATUS current
    DESCRIPTION
        "Event TNIP.1
        An encapsulated packet for an external protocol was received on
        an interface to be desencapsulated."
    ::= { tnipEventsGroup 1 }

tnip1-str-enc-protocol OBJECT-TYPE
    SYNTAX DisplayString
    MAX-ACCESS accessible-for-notify
    STATUS current
    DESCRIPTION
        "Parameter 'str-enc-protocol' in event TNIP.1"
    ::= { tnipEventObjects1 1 }

tnip1-num-external-protocol OBJECT-TYPE
    SYNTAX Integer32
    MAX-ACCESS accessible-for-notify
    STATUS current
    DESCRIPTION
        "Parameter 'num-external-protocol' in event TNIP.1"
    ::= { tnipEventObjects1 2 }

tnip1-source-ip-address OBJECT-TYPE
    SYNTAX IpAddress
    MAX-ACCESS accessible-for-notify
    STATUS current
    DESCRIPTION
        "Parameter 'source-ip-address' in event TNIP.1"
    ::= { tnipEventObjects1 3 }

tnip1-destination-ip-address OBJECT-TYPE
    SYNTAX IpAddress
    MAX-ACCESS accessible-for-notify
    STATUS current
    DESCRIPTION
        "Parameter 'destination-ip-address' in event TNIP.1"
    ::= { tnipEventObjects1 4 }

tnip1-interface OBJECT-TYPE
    SYNTAX DisplayString
    MAX-ACCESS accessible-for-notify
    STATUS current
    DESCRIPTION
        "Parameter 'interface' in event TNIP.1"
    ::= { tnipEventObjects1 5 }

tnipEventObjects2 OBJECT-IDENTITY
    STATUS current
    DESCRIPTION
        "Event TNIP.2
        A packet for an external protocol and with a certain encapsulation was
        received. There is no tunnel between the encapsulated packet source and
        destination address."
    ::= { tnipEventsGroup 2 }

tnip2-str-enc-protocol OBJECT-TYPE
    SYNTAX DisplayString
    MAX-ACCESS accessible-for-notify
    STATUS current
    DESCRIPTION
        "Parameter 'str-enc-protocol' in event TNIP.2"
    ::= { tnipEventObjects2 1 }

tnip2-external-protocol-num OBJECT-TYPE
    SYNTAX Integer32
    MAX-ACCESS accessible-for-notify
    STATUS current
    DESCRIPTION
        "Parameter 'external-protocol-num' in event TNIP.2"
    ::= { tnipEventObjects2 2 }

tnip2-source-ip-address OBJECT-TYPE
    SYNTAX IpAddress
    MAX-ACCESS accessible-for-notify
    STATUS current
    DESCRIPTION
        "Parameter 'source-ip-address' in event TNIP.2"
    ::= { tnipEventObjects2 3 }

tnip2-destination-ip-address OBJECT-TYPE
    SYNTAX IpAddress
    MAX-ACCESS accessible-for-notify
    STATUS current
    DESCRIPTION
        "Parameter 'destination-ip-address' in event TNIP.2"
    ::= { tnipEventObjects2 4 }

tnipEventObjects3 OBJECT-IDENTITY
    STATUS current
    DESCRIPTION
        "Event TNIP.3
        The tunnel interfaz is down so the interface entry function
        has discarded the packet."
    ::= { tnipEventsGroup 3 }

tnip3-interface OBJECT-TYPE
    SYNTAX DisplayString
    MAX-ACCESS accessible-for-notify
    STATUS current
    DESCRIPTION
        "Parameter 'interface' in event TNIP.3"
    ::= { tnipEventObjects3 1 }

tnipEventObjects4 OBJECT-IDENTITY
    STATUS current
    DESCRIPTION
        "Event TNIP.4
        The tunnel interface has no configuration so the packet is discarded."
    ::= { tnipEventsGroup 4 }

tnip4-interface OBJECT-TYPE
    SYNTAX DisplayString
    MAX-ACCESS accessible-for-notify
    STATUS current
    DESCRIPTION
        "Parameter 'interface' in event TNIP.4"
    ::= { tnipEventObjects4 1 }

tnipEventObjects5 OBJECT-IDENTITY
    STATUS current
    DESCRIPTION
        "Event TNIP.5
        The interface entry function has discarded the packet because the
        interface configuracion has a different encapsulation protocol."
    ::= { tnipEventsGroup 5 }

tnip5-interface OBJECT-TYPE
    SYNTAX DisplayString
    MAX-ACCESS accessible-for-notify
    STATUS current
    DESCRIPTION
        "Parameter 'interface' in event TNIP.5"
    ::= { tnipEventObjects5 1 }

tnipEventObjects6 OBJECT-IDENTITY
    STATUS current
    DESCRIPTION
        "Event TNIP.6
        The packet has activated the routing option so the GRE desencapsulation
        funcion has discarded it."
    ::= { tnipEventsGroup 6 }

tnip6-interface OBJECT-TYPE
    SYNTAX DisplayString
    MAX-ACCESS accessible-for-notify
    STATUS current
    DESCRIPTION
        "Parameter 'interface' in event TNIP.6"
    ::= { tnipEventObjects6 1 }

tnipEventObjects7 OBJECT-IDENTITY
    STATUS current
    DESCRIPTION
        "Event TNIP.7
        This message is generated when a packet has an invalid checksum.
        The received checksum, together with the correct checksum,
        are displayed."
    ::= { tnipEventsGroup 7 }

tnip7-checksum OBJECT-TYPE
    SYNTAX Integer32
    MAX-ACCESS accessible-for-notify
    STATUS current
    DESCRIPTION
        "Parameter 'checksum' in event TNIP.7"
    ::= { tnipEventObjects7 1 }

tnip7-expected-checksum OBJECT-TYPE
    SYNTAX Integer32
    MAX-ACCESS accessible-for-notify
    STATUS current
    DESCRIPTION
        "Parameter 'expected-checksum' in event TNIP.7"
    ::= { tnipEventObjects7 2 }

tnip7-interface OBJECT-TYPE
    SYNTAX DisplayString
    MAX-ACCESS accessible-for-notify
    STATUS current
    DESCRIPTION
        "Parameter 'interface' in event TNIP.7"
    ::= { tnipEventObjects7 3 }

tnipEventObjects8 OBJECT-IDENTITY
    STATUS current
    DESCRIPTION
        "Event TNIP.8
        This message is generated when the key packet is invalid. The received
        key, together with the correct key, are displayed."
    ::= { tnipEventsGroup 8 }

tnip8-key OBJECT-TYPE
    SYNTAX Integer32
    MAX-ACCESS accessible-for-notify
    STATUS current
    DESCRIPTION
        "Parameter 'key' in event TNIP.8"
    ::= { tnipEventObjects8 1 }

tnip8-expected-key OBJECT-TYPE
    SYNTAX Integer32
    MAX-ACCESS accessible-for-notify
    STATUS current
    DESCRIPTION
        "Parameter 'expected-key' in event TNIP.8"
    ::= { tnipEventObjects8 2 }

tnip8-interface OBJECT-TYPE
    SYNTAX DisplayString
    MAX-ACCESS accessible-for-notify
    STATUS current
    DESCRIPTION
        "Parameter 'interface' in event TNIP.8"
    ::= { tnipEventObjects8 3 }

tnipEventObjects9 OBJECT-IDENTITY
    STATUS current
    DESCRIPTION
        "Event TNIP.9
        This message is generated when a packet has no key and the tunnel is
        configured to check identification key."
    ::= { tnipEventsGroup 9 }

tnip9-expected-key OBJECT-TYPE
    SYNTAX Integer32
    MAX-ACCESS accessible-for-notify
    STATUS current
    DESCRIPTION
        "Parameter 'expected-key' in event TNIP.9"
    ::= { tnipEventObjects9 1 }

tnip9-interface OBJECT-TYPE
    SYNTAX DisplayString
    MAX-ACCESS accessible-for-notify
    STATUS current
    DESCRIPTION
        "Parameter 'interface' in event TNIP.9"
    ::= { tnipEventObjects9 2 }

tnipEventObjects10 OBJECT-IDENTITY
    STATUS current
    DESCRIPTION
        "Event TNIP.10
        This message is generated when a packet has a key and the tunnel is
        configured not to check identification key."
    ::= { tnipEventsGroup 10 }

tnip10-key OBJECT-TYPE
    SYNTAX Integer32
    MAX-ACCESS accessible-for-notify
    STATUS current
    DESCRIPTION
        "Parameter 'key' in event TNIP.10"
    ::= { tnipEventObjects10 1 }

tnip10-interface OBJECT-TYPE
    SYNTAX DisplayString
    MAX-ACCESS accessible-for-notify
    STATUS current
    DESCRIPTION
        "Parameter 'interface' in event TNIP.10"
    ::= { tnipEventObjects10 2 }

tnipEventObjects11 OBJECT-IDENTITY
    STATUS current
    DESCRIPTION
        "Event TNIP.11
        This message is generated when a packet has a wrong sequence number.
        The received sequence number, together with the correct sequence number,
        are displayed."
    ::= { tnipEventsGroup 11 }

tnip11-seq-num OBJECT-TYPE
    SYNTAX Integer32
    MAX-ACCESS accessible-for-notify
    STATUS current
    DESCRIPTION
        "Parameter 'seq-num' in event TNIP.11"
    ::= { tnipEventObjects11 1 }

tnip11-expected-seq-num OBJECT-TYPE
    SYNTAX Integer32
    MAX-ACCESS accessible-for-notify
    STATUS current
    DESCRIPTION
        "Parameter 'expected-seq-num' in event TNIP.11"
    ::= { tnipEventObjects11 2 }

tnip11-interface OBJECT-TYPE
    SYNTAX DisplayString
    MAX-ACCESS accessible-for-notify
    STATUS current
    DESCRIPTION
        "Parameter 'interface' in event TNIP.11"
    ::= { tnipEventObjects11 3 }

tnipEventObjects12 OBJECT-IDENTITY
    STATUS current
    DESCRIPTION
        "Event TNIP.12
        The packet has the recursion option active so the desencaptulation
        GRE function has discarded it. Multiple encapsulation is not accepted."
    ::= { tnipEventsGroup 12 }

tnip12-interface OBJECT-TYPE
    SYNTAX DisplayString
    MAX-ACCESS accessible-for-notify
    STATUS current
    DESCRIPTION
        "Parameter 'interface' in event TNIP.12"
    ::= { tnipEventObjects12 1 }

tnipEventObjects13 OBJECT-IDENTITY
    STATUS current
    DESCRIPTION
        "Event TNIP.13
        The packet has an unknown version so the desencaptulation GRE function
        has discarded it."
    ::= { tnipEventsGroup 13 }

tnip13-version OBJECT-TYPE
    SYNTAX Integer32
    MAX-ACCESS accessible-for-notify
    STATUS current
    DESCRIPTION
        "Parameter 'version' in event TNIP.13"
    ::= { tnipEventObjects13 1 }

tnip13-interface OBJECT-TYPE
    SYNTAX DisplayString
    MAX-ACCESS accessible-for-notify
    STATUS current
    DESCRIPTION
        "Parameter 'interface' in event TNIP.13"
    ::= { tnipEventObjects13 2 }

tnipEventObjects14 OBJECT-IDENTITY
    STATUS current
    DESCRIPTION
        "Event TNIP.14
        Successful packet GRE desencapsulation. Internal protocol of the
        GRE packet, source and destination address, together with the interface
        are displayed."
    ::= { tnipEventsGroup 14 }

tnip14-protocol-num OBJECT-TYPE
    SYNTAX Integer32
    MAX-ACCESS accessible-for-notify
    STATUS current
    DESCRIPTION
        "Parameter 'protocol-num' in event TNIP.14"
    ::= { tnipEventObjects14 1 }

tnip14-source-ip-address OBJECT-TYPE
    SYNTAX IpAddress
    MAX-ACCESS accessible-for-notify
    STATUS current
    DESCRIPTION
        "Parameter 'source-ip-address' in event TNIP.14"
    ::= { tnipEventObjects14 2 }

tnip14-destination-ip-address OBJECT-TYPE
    SYNTAX IpAddress
    MAX-ACCESS accessible-for-notify
    STATUS current
    DESCRIPTION
        "Parameter 'destination-ip-address' in event TNIP.14"
    ::= { tnipEventObjects14 3 }

tnip14-interface OBJECT-TYPE
    SYNTAX DisplayString
    MAX-ACCESS accessible-for-notify
    STATUS current
    DESCRIPTION
        "Parameter 'interface' in event TNIP.14"
    ::= { tnipEventObjects14 4 }

tnip14-seq-num OBJECT-TYPE
    SYNTAX Integer32
    MAX-ACCESS accessible-for-notify
    STATUS current
    DESCRIPTION
        "Parameter 'seq-num' in event TNIP.14"
    ::= { tnipEventObjects14 5 }

tnipEventObjects15 OBJECT-IDENTITY
    STATUS current
    DESCRIPTION
        "Event TNIP.15
        Unknown protocol of the desencapsulated GRE packet."
    ::= { tnipEventsGroup 15 }

tnip15-protocol-num OBJECT-TYPE
    SYNTAX Integer32
    MAX-ACCESS accessible-for-notify
    STATUS current
    DESCRIPTION
        "Parameter 'protocol-num' in event TNIP.15"
    ::= { tnipEventObjects15 1 }

tnip15-interface OBJECT-TYPE
    SYNTAX DisplayString
    MAX-ACCESS accessible-for-notify
    STATUS current
    DESCRIPTION
        "Parameter 'interface' in event TNIP.15"
    ::= { tnipEventObjects15 2 }

tnipEventObjects16 OBJECT-IDENTITY
    STATUS current
    DESCRIPTION
        "Event TNIP.16
        The interface is down so the outgoing packet has been discarded."
    ::= { tnipEventsGroup 16 }

tnip16-interface OBJECT-TYPE
    SYNTAX DisplayString
    MAX-ACCESS accessible-for-notify
    STATUS current
    DESCRIPTION
        "Parameter 'interface' in event TNIP.16"
    ::= { tnipEventObjects16 1 }

tnipEventObjects17 OBJECT-IDENTITY
    STATUS current
    DESCRIPTION
        "Event TNIP.17
        The interface is no configured so the outging packet has been discarded."
    ::= { tnipEventsGroup 17 }

tnip17-interface OBJECT-TYPE
    SYNTAX DisplayString
    MAX-ACCESS accessible-for-notify
    STATUS current
    DESCRIPTION
        "Parameter 'interface' in event TNIP.17"
    ::= { tnipEventObjects17 1 }

tnipEventObjects18 OBJECT-IDENTITY
    STATUS current
    DESCRIPTION
        "Event TNIP.18
        The internal protocol (payload protocol) has been rejected so
        the outgoing packet has been discarded."
    ::= { tnipEventsGroup 18 }

tnip18-protocol-num OBJECT-TYPE
    SYNTAX Integer32
    MAX-ACCESS accessible-for-notify
    STATUS current
    DESCRIPTION
        "Parameter 'protocol-num' in event TNIP.18"
    ::= { tnipEventObjects18 1 }

tnip18-interface OBJECT-TYPE
    SYNTAX DisplayString
    MAX-ACCESS accessible-for-notify
    STATUS current
    DESCRIPTION
        "Parameter 'interface' in event TNIP.18"
    ::= { tnipEventObjects18 2 }

tnipEventObjects19 OBJECT-IDENTITY
    STATUS current
    DESCRIPTION
        "Event TNIP.19
        Successfully encapsulated GRE packet. The protocol, source and
        destination of the encapsulated packet are displayed."
    ::= { tnipEventsGroup 19 }

tnip19-protocol-num OBJECT-TYPE
    SYNTAX Integer32
    MAX-ACCESS accessible-for-notify
    STATUS current
    DESCRIPTION
        "Parameter 'protocol-num' in event TNIP.19"
    ::= { tnipEventObjects19 1 }

tnip19-source-ip-address OBJECT-TYPE
    SYNTAX IpAddress
    MAX-ACCESS accessible-for-notify
    STATUS current
    DESCRIPTION
        "Parameter 'source-ip-address' in event TNIP.19"
    ::= { tnipEventObjects19 2 }

tnip19-destination-ip-address OBJECT-TYPE
    SYNTAX IpAddress
    MAX-ACCESS accessible-for-notify
    STATUS current
    DESCRIPTION
        "Parameter 'destination-ip-address' in event TNIP.19"
    ::= { tnipEventObjects19 3 }

tnip19-interface OBJECT-TYPE
    SYNTAX DisplayString
    MAX-ACCESS accessible-for-notify
    STATUS current
    DESCRIPTION
        "Parameter 'interface' in event TNIP.19"
    ::= { tnipEventObjects19 4 }

tnipEventObjects20 OBJECT-IDENTITY
    STATUS current
    DESCRIPTION
        "Event TNIP.20
        A packet is sent. The encapsulation protocol, the external protocol
        (delivery protocol), source, destination and the interface that
        encapsulated the packet are displayed."
    ::= { tnipEventsGroup 20 }

tnip20-str-enc-protocol OBJECT-TYPE
    SYNTAX DisplayString
    MAX-ACCESS accessible-for-notify
    STATUS current
    DESCRIPTION
        "Parameter 'str-enc-protocol' in event TNIP.20"
    ::= { tnipEventObjects20 1 }

tnip20-protocol-num OBJECT-TYPE
    SYNTAX Integer32
    MAX-ACCESS accessible-for-notify
    STATUS current
    DESCRIPTION
        "Parameter 'protocol-num' in event TNIP.20"
    ::= { tnipEventObjects20 2 }

tnip20-source-ip-address OBJECT-TYPE
    SYNTAX IpAddress
    MAX-ACCESS accessible-for-notify
    STATUS current
    DESCRIPTION
        "Parameter 'source-ip-address' in event TNIP.20"
    ::= { tnipEventObjects20 3 }

tnip20-destination-ip-address OBJECT-TYPE
    SYNTAX IpAddress
    MAX-ACCESS accessible-for-notify
    STATUS current
    DESCRIPTION
        "Parameter 'destination-ip-address' in event TNIP.20"
    ::= { tnipEventObjects20 4 }

tnip20-interface OBJECT-TYPE
    SYNTAX DisplayString
    MAX-ACCESS accessible-for-notify
    STATUS current
    DESCRIPTION
        "Parameter 'interface' in event TNIP.20"
    ::= { tnipEventObjects20 5 }

tnip20-num-sec OBJECT-TYPE
    SYNTAX Integer32
    MAX-ACCESS accessible-for-notify
    STATUS current
    DESCRIPTION
        "Parameter 'num-sec' in event TNIP.20"
    ::= { tnipEventObjects20 6 }

tnipEventObjects21 OBJECT-IDENTITY
    STATUS current
    DESCRIPTION
        "Event TNIP.21
        A free dinamic tunnel has taken to set up the new tunnel."
    ::= { tnipEventsGroup 21 }

tnip21-interface OBJECT-TYPE
    SYNTAX DisplayString
    MAX-ACCESS accessible-for-notify
    STATUS current
    DESCRIPTION
        "Parameter 'interface' in event TNIP.21"
    ::= { tnipEventObjects21 1 }

tnip21-source-ip-address OBJECT-TYPE
    SYNTAX IpAddress
    MAX-ACCESS accessible-for-notify
    STATUS current
    DESCRIPTION
        "Parameter 'source-ip-address' in event TNIP.21"
    ::= { tnipEventObjects21 2 }

tnip21-destination-ip-address OBJECT-TYPE
    SYNTAX IpAddress
    MAX-ACCESS accessible-for-notify
    STATUS current
    DESCRIPTION
        "Parameter 'destination-ip-address' in event TNIP.21"
    ::= { tnipEventObjects21 3 }

tnipEventObjects22 OBJECT-IDENTITY
    STATUS current
    DESCRIPTION
        "Event TNIP.22
        A dinamic tunnel is released because there are no static nor RIP routes
        or because keepalive failed."
    ::= { tnipEventsGroup 22 }

tnip22-interface OBJECT-TYPE
    SYNTAX DisplayString
    MAX-ACCESS accessible-for-notify
    STATUS current
    DESCRIPTION
        "Parameter 'interface' in event TNIP.22"
    ::= { tnipEventObjects22 1 }

tnipEventObjects23 OBJECT-IDENTITY
    STATUS current
    DESCRIPTION
        "Event TNIP.23
        A new tunnel is set up. It has the same IP address than a previous
        tunnel. At this moment the release conditions are attained."
    ::= { tnipEventsGroup 23 }

tnip23-interface OBJECT-TYPE
    SYNTAX DisplayString
    MAX-ACCESS accessible-for-notify
    STATUS current
    DESCRIPTION
        "Parameter 'interface' in event TNIP.23"
    ::= { tnipEventObjects23 1 }

tnip23-ip-address OBJECT-TYPE
    SYNTAX IpAddress
    MAX-ACCESS accessible-for-notify
    STATUS current
    DESCRIPTION
        "Parameter 'ip-address' in event TNIP.23"
    ::= { tnipEventObjects23 2 }

tnipEventObjects24 OBJECT-IDENTITY
    STATUS current
    DESCRIPTION
        "Event TNIP.24
        A packet that will cause an infinite loop has been detected."
    ::= { tnipEventsGroup 24 }

tnip24-interface OBJECT-TYPE
    SYNTAX DisplayString
    MAX-ACCESS accessible-for-notify
    STATUS current
    DESCRIPTION
        "Parameter 'interface' in event TNIP.24"
    ::= { tnipEventObjects24 1 }

tnipEventObjects25 OBJECT-IDENTITY
    STATUS current
    DESCRIPTION
        "Event TNIP.25
        The payload of a GRE packet has been ciphered successfully.
        The protocol, source and destination of the encapsulated packet
        are displayed."
    ::= { tnipEventsGroup 25 }

tnip25-protocol-num OBJECT-TYPE
    SYNTAX Integer32
    MAX-ACCESS accessible-for-notify
    STATUS current
    DESCRIPTION
        "Parameter 'protocol-num' in event TNIP.25"
    ::= { tnipEventObjects25 1 }

tnip25-source-ip-address OBJECT-TYPE
    SYNTAX IpAddress
    MAX-ACCESS accessible-for-notify
    STATUS current
    DESCRIPTION
        "Parameter 'source-ip-address' in event TNIP.25"
    ::= { tnipEventObjects25 2 }

tnip25-destination-ip-address OBJECT-TYPE
    SYNTAX IpAddress
    MAX-ACCESS accessible-for-notify
    STATUS current
    DESCRIPTION
        "Parameter 'destination-ip-address' in event TNIP.25"
    ::= { tnipEventObjects25 3 }

tnip25-interface OBJECT-TYPE
    SYNTAX DisplayString
    MAX-ACCESS accessible-for-notify
    STATUS current
    DESCRIPTION
        "Parameter 'interface' in event TNIP.25"
    ::= { tnipEventObjects25 4 }

tnipEventObjects26 OBJECT-IDENTITY
    STATUS current
    DESCRIPTION
        "Event TNIP.26
        The payload of a GRE packet has been deciphered successfully.
        The internal protocol, source and destination of the GRE packet and
        the interface are displayed."
    ::= { tnipEventsGroup 26 }

tnip26-protocol-num OBJECT-TYPE
    SYNTAX Integer32
    MAX-ACCESS accessible-for-notify
    STATUS current
    DESCRIPTION
        "Parameter 'protocol-num' in event TNIP.26"
    ::= { tnipEventObjects26 1 }

tnip26-source-ip-address OBJECT-TYPE
    SYNTAX IpAddress
    MAX-ACCESS accessible-for-notify
    STATUS current
    DESCRIPTION
        "Parameter 'source-ip-address' in event TNIP.26"
    ::= { tnipEventObjects26 2 }

tnip26-destination-ip-address OBJECT-TYPE
    SYNTAX IpAddress
    MAX-ACCESS accessible-for-notify
    STATUS current
    DESCRIPTION
        "Parameter 'destination-ip-address' in event TNIP.26"
    ::= { tnipEventObjects26 3 }

tnip26-interface OBJECT-TYPE
    SYNTAX DisplayString
    MAX-ACCESS accessible-for-notify
    STATUS current
    DESCRIPTION
        "Parameter 'interface' in event TNIP.26"
    ::= { tnipEventObjects26 4 }

tnipEventObjects27 OBJECT-IDENTITY
    STATUS current
    DESCRIPTION
        "Event TNIP.27
        A deciphered packet has an invalid cipher checksum or the protocol
        is not ciphered."
    ::= { tnipEventsGroup 27 }

tnip27-interface OBJECT-TYPE
    SYNTAX DisplayString
    MAX-ACCESS accessible-for-notify
    STATUS current
    DESCRIPTION
        "Parameter 'interface' in event TNIP.27"
    ::= { tnipEventObjects27 1 }

tnipEventObjects28 OBJECT-IDENTITY
    STATUS current
    DESCRIPTION
        "Event TNIP.28
        Successful packet GRE desencapsulation. The internal protocol of the
        GRE packet together with the interface are displayed."
    ::= { tnipEventsGroup 28 }

tnip28-protocol-num OBJECT-TYPE
    SYNTAX Integer32
    MAX-ACCESS accessible-for-notify
    STATUS current
    DESCRIPTION
        "Parameter 'protocol-num' in event TNIP.28"
    ::= { tnipEventObjects28 1 }

tnip28-interface OBJECT-TYPE
    SYNTAX DisplayString
    MAX-ACCESS accessible-for-notify
    STATUS current
    DESCRIPTION
        "Parameter 'interface' in event TNIP.28"
    ::= { tnipEventObjects28 2 }

tnip28-seq-num OBJECT-TYPE
    SYNTAX Integer32
    MAX-ACCESS accessible-for-notify
    STATUS current
    DESCRIPTION
        "Parameter 'seq-num' in event TNIP.28"
    ::= { tnipEventObjects28 3 }

tnipEventObjects29 OBJECT-IDENTITY
    STATUS current
    DESCRIPTION
        "Event TNIP.29
        The payload of a GRE packet has been ciphered successfully. The protocol
        of the encapsulated packet is displayed."
    ::= { tnipEventsGroup 29 }

tnip29-protocol-num OBJECT-TYPE
    SYNTAX Integer32
    MAX-ACCESS accessible-for-notify
    STATUS current
    DESCRIPTION
        "Parameter 'protocol-num' in event TNIP.29"
    ::= { tnipEventObjects29 1 }

tnip29-interface OBJECT-TYPE
    SYNTAX DisplayString
    MAX-ACCESS accessible-for-notify
    STATUS current
    DESCRIPTION
        "Parameter 'interface' in event TNIP.29"
    ::= { tnipEventObjects29 2 }

tnipEventObjects30 OBJECT-IDENTITY
    STATUS current
    DESCRIPTION
        "Event TNIP.30
        Successfully encapsulated GRE packet. The protocol of the encapsulated
        packet is displayed."
    ::= { tnipEventsGroup 30 }

tnip30-protocol-num OBJECT-TYPE
    SYNTAX Integer32
    MAX-ACCESS accessible-for-notify
    STATUS current
    DESCRIPTION
        "Parameter 'protocol-num' in event TNIP.30"
    ::= { tnipEventObjects30 1 }

tnip30-interface OBJECT-TYPE
    SYNTAX DisplayString
    MAX-ACCESS accessible-for-notify
    STATUS current
    DESCRIPTION
        "Parameter 'interface' in event TNIP.30"
    ::= { tnipEventObjects30 2 }

tnipEventObjects31 OBJECT-IDENTITY
    STATUS current
    DESCRIPTION
        "Event TNIP.31
        Successful packet GRE desencapsulation. The internal protocol of the
        GRE packet, the MAC source and the MAC destination, together with the
        interface and the sequence number are displayed."
    ::= { tnipEventsGroup 31 }

tnip31-protocol-num OBJECT-TYPE
    SYNTAX Integer32
    MAX-ACCESS accessible-for-notify
    STATUS current
    DESCRIPTION
        "Parameter 'protocol-num' in event TNIP.31"
    ::= { tnipEventObjects31 1 }

tnip31-source-mac-address OBJECT-TYPE
    SYNTAX DisplayString
    MAX-ACCESS accessible-for-notify
    STATUS current
    DESCRIPTION
        "Parameter 'source-mac-address' in event TNIP.31"
    ::= { tnipEventObjects31 2 }

tnip31-destination-mac-address OBJECT-TYPE
    SYNTAX DisplayString
    MAX-ACCESS accessible-for-notify
    STATUS current
    DESCRIPTION
        "Parameter 'destination-mac-address' in event TNIP.31"
    ::= { tnipEventObjects31 3 }

tnip31-interface OBJECT-TYPE
    SYNTAX DisplayString
    MAX-ACCESS accessible-for-notify
    STATUS current
    DESCRIPTION
        "Parameter 'interface' in event TNIP.31"
    ::= { tnipEventObjects31 4 }

tnip31-seq-num OBJECT-TYPE
    SYNTAX Integer32
    MAX-ACCESS accessible-for-notify
    STATUS current
    DESCRIPTION
        "Parameter 'seq-num' in event TNIP.31"
    ::= { tnipEventObjects31 5 }

tnipEventObjects32 OBJECT-IDENTITY
    STATUS current
    DESCRIPTION
        "Event TNIP.32
        The payload of a GRE packet has been ciphered successfully.
        The protocol, MAC source and destination of the encapsulated packet,
        together with the interface are displayed."
    ::= { tnipEventsGroup 32 }

tnip32-protocol-num OBJECT-TYPE
    SYNTAX Integer32
    MAX-ACCESS accessible-for-notify
    STATUS current
    DESCRIPTION
        "Parameter 'protocol-num' in event TNIP.32"
    ::= { tnipEventObjects32 1 }

tnip32-source-mac-address OBJECT-TYPE
    SYNTAX DisplayString
    MAX-ACCESS accessible-for-notify
    STATUS current
    DESCRIPTION
        "Parameter 'source-mac-address' in event TNIP.32"
    ::= { tnipEventObjects32 2 }

tnip32-destination-mac-address OBJECT-TYPE
    SYNTAX DisplayString
    MAX-ACCESS accessible-for-notify
    STATUS current
    DESCRIPTION
        "Parameter 'destination-mac-address' in event TNIP.32"
    ::= { tnipEventObjects32 3 }

tnip32-interface OBJECT-TYPE
    SYNTAX DisplayString
    MAX-ACCESS accessible-for-notify
    STATUS current
    DESCRIPTION
        "Parameter 'interface' in event TNIP.32"
    ::= { tnipEventObjects32 4 }

tnipEventObjects33 OBJECT-IDENTITY
    STATUS current
    DESCRIPTION
        "Event TNIP.33
        Successfully encapsulated GRE packet. The protocol, MAC source and
        destination of the encapsulated packet, together with the interface are
        displayed."
    ::= { tnipEventsGroup 33 }

tnip33-protocol-num OBJECT-TYPE
    SYNTAX Integer32
    MAX-ACCESS accessible-for-notify
    STATUS current
    DESCRIPTION
        "Parameter 'protocol-num' in event TNIP.33"
    ::= { tnipEventObjects33 1 }

tnip33-source-mac-address OBJECT-TYPE
    SYNTAX DisplayString
    MAX-ACCESS accessible-for-notify
    STATUS current
    DESCRIPTION
        "Parameter 'source-mac-address' in event TNIP.33"
    ::= { tnipEventObjects33 2 }

tnip33-destination-mac-address OBJECT-TYPE
    SYNTAX DisplayString
    MAX-ACCESS accessible-for-notify
    STATUS current
    DESCRIPTION
        "Parameter 'destination-mac-address' in event TNIP.33"
    ::= { tnipEventObjects33 3 }

tnip33-interface OBJECT-TYPE
    SYNTAX DisplayString
    MAX-ACCESS accessible-for-notify
    STATUS current
    DESCRIPTION
        "Parameter 'interface' in event TNIP.33"
    ::= { tnipEventObjects33 4 }

tnipEventObjects34 OBJECT-IDENTITY
    STATUS current
    DESCRIPTION
        "Event TNIP.34
        A buffer could not be allocated when needed for keepalive request."
    ::= { tnipEventsGroup 34 }

tnip34-interface OBJECT-TYPE
    SYNTAX DisplayString
    MAX-ACCESS accessible-for-notify
    STATUS current
    DESCRIPTION
        "Parameter 'interface' in event TNIP.34"
    ::= { tnipEventObjects34 1 }

tnipEventObjects35 OBJECT-IDENTITY
    STATUS current
    DESCRIPTION
        "Event TNIP.35
        A keepalive is going to be sent on specified interface to test tunnel
        endpoint reachability."
    ::= { tnipEventsGroup 35 }

tnip35-interface OBJECT-TYPE
    SYNTAX DisplayString
    MAX-ACCESS accessible-for-notify
    STATUS current
    DESCRIPTION
        "Parameter 'interface' in event TNIP.35"
    ::= { tnipEventObjects35 1 }

tnipEventObjects36 OBJECT-IDENTITY
    STATUS current
    DESCRIPTION
        "Event TNIP.36
        A keepalive was received on specified interface with an unexpected
        identification number. The received and the expected identification
        numbers are shown, as well as incoming interface name."
    ::= { tnipEventsGroup 36 }

tnip36-received-id OBJECT-TYPE
    SYNTAX Integer32
    MAX-ACCESS accessible-for-notify
    STATUS current
    DESCRIPTION
        "Parameter 'received-id' in event TNIP.36"
    ::= { tnipEventObjects36 1 }

tnip36-expected-id OBJECT-TYPE
    SYNTAX Integer32
    MAX-ACCESS accessible-for-notify
    STATUS current
    DESCRIPTION
        "Parameter 'expected-id' in event TNIP.36"
    ::= { tnipEventObjects36 2 }

tnip36-interface OBJECT-TYPE
    SYNTAX DisplayString
    MAX-ACCESS accessible-for-notify
    STATUS current
    DESCRIPTION
        "Parameter 'interface' in event TNIP.36"
    ::= { tnipEventObjects36 3 }

tnipEventObjects37 OBJECT-IDENTITY
    STATUS current
    DESCRIPTION
        "Event TNIP.37
        A keepalive response was received on specified interface."
    ::= { tnipEventsGroup 37 }

tnip37-interface OBJECT-TYPE
    SYNTAX DisplayString
    MAX-ACCESS accessible-for-notify
    STATUS current
    DESCRIPTION
        "Parameter 'interface' in event TNIP.37"
    ::= { tnipEventObjects37 1 }

tnipEventObjects38 OBJECT-IDENTITY
    STATUS current
    DESCRIPTION
        "Event TNIP.38
        An unexpected keepalive response was received on specified interface."
    ::= { tnipEventsGroup 38 }

tnip38-interface OBJECT-TYPE
    SYNTAX DisplayString
    MAX-ACCESS accessible-for-notify
    STATUS current
    DESCRIPTION
        "Parameter 'interface' in event TNIP.38"
    ::= { tnipEventObjects38 1 }

tnipEventObjects39 OBJECT-IDENTITY
    STATUS current
    DESCRIPTION
        "Event TNIP.39
        The router received an ICMP Path MTU 'too big' message (RFC 1191),
        indicating that a sent packet was too big and was unable
        to be fragmented for some reason. The 'source' IP address indicates
        the router whose next hop MTU is too small for the packet."
    ::= { tnipEventsGroup 39 }

tnip39-rmtu OBJECT-TYPE
    SYNTAX Integer32
    MAX-ACCESS accessible-for-notify
    STATUS current
    DESCRIPTION
        "Parameter 'rmtu' in event TNIP.39"
    ::= { tnipEventObjects39 1 }

tnip39-src-ip-addr OBJECT-TYPE
    SYNTAX IpAddress
    MAX-ACCESS accessible-for-notify
    STATUS current
    DESCRIPTION
        "Parameter 'src-ip-addr' in event TNIP.39"
    ::= { tnipEventObjects39 2 }

tnip39-dest-ip-addr OBJECT-TYPE
    SYNTAX IpAddress
    MAX-ACCESS accessible-for-notify
    STATUS current
    DESCRIPTION
        "Parameter 'dest-ip-addr' in event TNIP.39"
    ::= { tnipEventObjects39 3 }

tnip39-interface OBJECT-TYPE
    SYNTAX DisplayString
    MAX-ACCESS accessible-for-notify
    STATUS current
    DESCRIPTION
        "Parameter 'interface' in event TNIP.39"
    ::= { tnipEventObjects39 4 }

tnipEventObjects40 OBJECT-IDENTITY
    STATUS current
    DESCRIPTION
        "Event TNIP.40
        A keepalive received on specified interface is being forwarded."
    ::= { tnipEventsGroup 40 }

tnip40-interface OBJECT-TYPE
    SYNTAX DisplayString
    MAX-ACCESS accessible-for-notify
    STATUS current
    DESCRIPTION
        "Parameter 'interface' in event TNIP.40"
    ::= { tnipEventObjects40 1 }


tnipNotification1 NOTIFICATION-TYPE
    OBJECTS { 
              tnip1-str-enc-protocol, 
              tnip1-num-external-protocol,
              tnip1-source-ip-address,
              tnip1-destination-ip-address,
              tnip1-interface 
            }
    STATUS current
    DESCRIPTION
        "Notification of Event TNIP.1

        Message: 'Packet received with encapsulation $1, external protocol 0x$2, (source $3 y destination $4), on interface $5'

        Parameters list:
              $1: tnip1-str-enc-protocol
              $2: tnip1-num-external-protocol
              $3: tnip1-source-ip-address
              $4: tnip1-destination-ip-address
              $5: tnip1-interface

        An encapsulated packet for an external protocol was received on
        an interface to be desencapsulated."
    ::= { tnipNotificationsPrefix 1 }

tnipNotification2 NOTIFICATION-TYPE
    OBJECTS { 
              tnip2-str-enc-protocol, 
              tnip2-external-protocol-num,
              tnip2-source-ip-address,
              tnip2-destination-ip-address 
            }
    STATUS current
    DESCRIPTION
        "Notification of Event TNIP.2

        Message: 'Received packet with encapsulation $1, external protocol 0x$2, (source $3 y destination $4). There is no tunnel for it'

        Parameters list:
              $1: tnip2-str-enc-protocol
              $2: tnip2-external-protocol-num
              $3: tnip2-source-ip-address
              $4: tnip2-destination-ip-address

        A packet for an external protocol and with a certain encapsulation was
        received. There is no tunnel between the encapsulated packet source and
        destination address."
    ::= { tnipNotificationsPrefix 2 }

tnipNotification3 NOTIFICATION-TYPE
    OBJECTS { 
              tnip3-interface 
            }
    STATUS current
    DESCRIPTION
        "Notification of Event TNIP.3

        Message: 'Incoming packet discarded. The interfaz is down. Interface $1'

        Parameters list:
              $1: tnip3-interface

        The tunnel interfaz is down so the interface entry function
        has discarded the packet."
    ::= { tnipNotificationsPrefix 3 }

tnipNotification4 NOTIFICATION-TYPE
    OBJECTS { 
              tnip4-interface 
            }
    STATUS current
    DESCRIPTION
        "Notification of Event TNIP.4

        Message: 'Incoming packet discarded. The interfaz has no configuration. Interface $1'

        Parameters list:
              $1: tnip4-interface

        The tunnel interface has no configuration so the packet is discarded."
    ::= { tnipNotificationsPrefix 4 }

tnipNotification5 NOTIFICATION-TYPE
    OBJECTS { 
              tnip5-interface 
            }
    STATUS current
    DESCRIPTION
        "Notification of Event TNIP.5

        Message: 'Incoming packet has been discarded because the interface configuration has a different encapsulation protocol, interface $1'

        Parameters list:
              $1: tnip5-interface

        The interface entry function has discarded the packet because the
        interface configuracion has a different encapsulation protocol."
    ::= { tnipNotificationsPrefix 5 }

tnipNotification6 NOTIFICATION-TYPE
    OBJECTS { 
              tnip6-interface 
            }
    STATUS current
    DESCRIPTION
        "Notification of Event TNIP.6

        Message: 'Error in GRE header. Flags have the routing option, interface $1'

        Parameters list:
              $1: tnip6-interface

        The packet has activated the routing option so the GRE desencapsulation
        funcion has discarded it."
    ::= { tnipNotificationsPrefix 6 }

tnipNotification7 NOTIFICATION-TYPE
    OBJECTS { 
              tnip7-checksum, 
              tnip7-expected-checksum,
              tnip7-interface 
            }
    STATUS current
    DESCRIPTION
        "Notification of Event TNIP.7

        Message: 'Error in GRE header, checksum 0x$1 (des 0x$2), interface $3'

        Parameters list:
              $1: tnip7-checksum
              $2: tnip7-expected-checksum
              $3: tnip7-interface

        This message is generated when a packet has an invalid checksum.
        The received checksum, together with the correct checksum,
        are displayed."
    ::= { tnipNotificationsPrefix 7 }

tnipNotification8 NOTIFICATION-TYPE
    OBJECTS { 
              tnip8-key, 
              tnip8-expected-key,
              tnip8-interface 
            }
    STATUS current
    DESCRIPTION
        "Notification of Event TNIP.8

        Message: 'Packet GRE discarded, key $1 (expected $2), interface $3'

        Parameters list:
              $1: tnip8-key
              $2: tnip8-expected-key
              $3: tnip8-interface

        This message is generated when the key packet is invalid. The received
        key, together with the correct key, are displayed."
    ::= { tnipNotificationsPrefix 8 }

tnipNotification9 NOTIFICATION-TYPE
    OBJECTS { 
              tnip9-expected-key, 
              tnip9-interface 
            }
    STATUS current
    DESCRIPTION
        "Notification of Event TNIP.9

        Message: 'Packet GRE with no key discarded (expected $1), interface $2'

        Parameters list:
              $1: tnip9-expected-key
              $2: tnip9-interface

        This message is generated when a packet has no key and the tunnel is
        configured to check identification key."
    ::= { tnipNotificationsPrefix 9 }

tnipNotification10 NOTIFICATION-TYPE
    OBJECTS { 
              tnip10-key, 
              tnip10-interface 
            }
    STATUS current
    DESCRIPTION
        "Notification of Event TNIP.10

        Message: 'Packet GRE with key discarded, key $1 (not expected key), interface $2'

        Parameters list:
              $1: tnip10-key
              $2: tnip10-interface

        This message is generated when a packet has a key and the tunnel is
        configured not to check identification key."
    ::= { tnipNotificationsPrefix 10 }

tnipNotification11 NOTIFICATION-TYPE
    OBJECTS { 
              tnip11-seq-num, 
              tnip11-expected-seq-num,
              tnip11-interface 
            }
    STATUS current
    DESCRIPTION
        "Notification of Event TNIP.11

        Message: 'Packet GRE discarded, sequence number $1 less than expected $2, interface $3'

        Parameters list:
              $1: tnip11-seq-num
              $2: tnip11-expected-seq-num
              $3: tnip11-interface

        This message is generated when a packet has a wrong sequence number.
        The received sequence number, together with the correct sequence number,
        are displayed."
    ::= { tnipNotificationsPrefix 11 }

tnipNotification12 NOTIFICATION-TYPE
    OBJECTS { 
              tnip12-interface 
            }
    STATUS current
    DESCRIPTION
        "Notification of Event TNIP.12

        Message: 'Error in GRE header. Recursion option active, interface $1'

        Parameters list:
              $1: tnip12-interface

        The packet has the recursion option active so the desencaptulation
        GRE function has discarded it. Multiple encapsulation is not accepted."
    ::= { tnipNotificationsPrefix 12 }

tnipNotification13 NOTIFICATION-TYPE
    OBJECTS { 
              tnip13-version, 
              tnip13-interface 
            }
    STATUS current
    DESCRIPTION
        "Notification of Event TNIP.13

        Message: 'Error in GRE header, encapsulation version $1 invalid, interface $2'

        Parameters list:
              $1: tnip13-version
              $2: tnip13-interface

        The packet has an unknown version so the desencaptulation GRE function
        has discarded it."
    ::= { tnipNotificationsPrefix 13 }

tnipNotification14 NOTIFICATION-TYPE
    OBJECTS { 
              tnip14-protocol-num, 
              tnip14-source-ip-address,
              tnip14-destination-ip-address,
              tnip14-interface,
              tnip14-seq-num 
            }
    STATUS current
    DESCRIPTION
        "Notification of Event TNIP.14

        Message: 'Desencapsulated GRE packet successfully, internal protocol 0x$1, (source $2 and destination $3), interface $4 sequence number $5'

        Parameters list:
              $1: tnip14-protocol-num
              $2: tnip14-source-ip-address
              $3: tnip14-destination-ip-address
              $4: tnip14-interface
              $5: tnip14-seq-num

        Successful packet GRE desencapsulation. Internal protocol of the
        GRE packet, source and destination address, together with the interface
        are displayed."
    ::= { tnipNotificationsPrefix 14 }

tnipNotification15 NOTIFICATION-TYPE
    OBJECTS { 
              tnip15-protocol-num, 
              tnip15-interface 
            }
    STATUS current
    DESCRIPTION
        "Notification of Event TNIP.15

        Message: 'Error in desencapsulated GRE packet, unknown internal protocol 0x$1, interface $2'

        Parameters list:
              $1: tnip15-protocol-num
              $2: tnip15-interface

        Unknown protocol of the desencapsulated GRE packet."
    ::= { tnipNotificationsPrefix 15 }

tnipNotification16 NOTIFICATION-TYPE
    OBJECTS { 
              tnip16-interface 
            }
    STATUS current
    DESCRIPTION
        "Notification of Event TNIP.16

        Message: 'The interface is down so the outgoing packet has been discarded, interface $1'

        Parameters list:
              $1: tnip16-interface

        The interface is down so the outgoing packet has been discarded."
    ::= { tnipNotificationsPrefix 16 }

tnipNotification17 NOTIFICATION-TYPE
    OBJECTS { 
              tnip17-interface 
            }
    STATUS current
    DESCRIPTION
        "Notification of Event TNIP.17

        Message: 'The interface is no configured so the outging packet has been discarded, interface $1'

        Parameters list:
              $1: tnip17-interface

        The interface is no configured so the outging packet has been discarded."
    ::= { tnipNotificationsPrefix 17 }

tnipNotification18 NOTIFICATION-TYPE
    OBJECTS { 
              tnip18-protocol-num, 
              tnip18-interface 
            }
    STATUS current
    DESCRIPTION
        "Notification of Event TNIP.18

        Message: 'The internal protocol 0x$1 has been rejected so the outgoing packet has been discarded, interface $2'

        Parameters list:
              $1: tnip18-protocol-num
              $2: tnip18-interface

        The internal protocol (payload protocol) has been rejected so
        the outgoing packet has been discarded."
    ::= { tnipNotificationsPrefix 18 }

tnipNotification19 NOTIFICATION-TYPE
    OBJECTS { 
              tnip19-protocol-num, 
              tnip19-source-ip-address,
              tnip19-destination-ip-address,
              tnip19-interface 
            }
    STATUS current
    DESCRIPTION
        "Notification of Event TNIP.19

        Message: 'Successfully encapsulated GRE packet, internal protocol 0x$1, (source $2 destination $3), interface $4'

        Parameters list:
              $1: tnip19-protocol-num
              $2: tnip19-source-ip-address
              $3: tnip19-destination-ip-address
              $4: tnip19-interface

        Successfully encapsulated GRE packet. The protocol, source and
        destination of the encapsulated packet are displayed."
    ::= { tnipNotificationsPrefix 19 }

tnipNotification20 NOTIFICATION-TYPE
    OBJECTS { 
              tnip20-str-enc-protocol, 
              tnip20-protocol-num,
              tnip20-source-ip-address,
              tnip20-destination-ip-address,
              tnip20-interface,
              tnip20-num-sec 
            }
    STATUS current
    DESCRIPTION
        "Notification of Event TNIP.20

        Message: 'Sendind packet $1, ext prt 0x$2, (source $3 destination $4), interface $5 sequence number $6'

        Parameters list:
              $1: tnip20-str-enc-protocol
              $2: tnip20-protocol-num
              $3: tnip20-source-ip-address
              $4: tnip20-destination-ip-address
              $5: tnip20-interface
              $6: tnip20-num-sec

        A packet is sent. The encapsulation protocol, the external protocol
        (delivery protocol), source, destination and the interface that
        encapsulated the packet are displayed."
    ::= { tnipNotificationsPrefix 20 }

tnipNotification21 NOTIFICATION-TYPE
    OBJECTS { 
              tnip21-interface, 
              tnip21-source-ip-address,
              tnip21-destination-ip-address 
            }
    STATUS current
    DESCRIPTION
        "Notification of Event TNIP.21

        Message: 'Interface $1 sets up a tunnel with source address $2 and destination $3'

        Parameters list:
              $1: tnip21-interface
              $2: tnip21-source-ip-address
              $3: tnip21-destination-ip-address

        A free dinamic tunnel has taken to set up the new tunnel."
    ::= { tnipNotificationsPrefix 21 }

tnipNotification22 NOTIFICATION-TYPE
    OBJECTS { 
              tnip22-interface 
            }
    STATUS current
    DESCRIPTION
        "Notification of Event TNIP.22

        Message: 'Error tunnel release, interface $1'

        Parameters list:
              $1: tnip22-interface

        A dinamic tunnel is released because there are no static nor RIP routes
        or because keepalive failed."
    ::= { tnipNotificationsPrefix 22 }

tnipNotification23 NOTIFICATION-TYPE
    OBJECTS { 
              tnip23-interface, 
              tnip23-ip-address 
            }
    STATUS current
    DESCRIPTION
        "Notification of Event TNIP.23

        Message: 'Release tunnel interface $1 set up another tunnel with the same address $2'

        Parameters list:
              $1: tnip23-interface
              $2: tnip23-ip-address

        A new tunnel is set up. It has the same IP address than a previous
        tunnel. At this moment the release conditions are attained."
    ::= { tnipNotificationsPrefix 23 }

tnipNotification24 NOTIFICATION-TYPE
    OBJECTS { 
              tnip24-interface 
            }
    STATUS current
    DESCRIPTION
        "Notification of Event TNIP.24

        Message: 'Error loop in tunnel, interface $1'

        Parameters list:
              $1: tnip24-interface

        A packet that will cause an infinite loop has been detected."
    ::= { tnipNotificationsPrefix 24 }

tnipNotification25 NOTIFICATION-TYPE
    OBJECTS { 
              tnip25-protocol-num, 
              tnip25-source-ip-address,
              tnip25-destination-ip-address,
              tnip25-interface 
            }
    STATUS current
    DESCRIPTION
        "Notification of Event TNIP.25

        Message: 'Successfully ciphered GRE packet, internal protocol 0x$1, (source $2 and destination $3), interface $4'

        Parameters list:
              $1: tnip25-protocol-num
              $2: tnip25-source-ip-address
              $3: tnip25-destination-ip-address
              $4: tnip25-interface

        The payload of a GRE packet has been ciphered successfully.
        The protocol, source and destination of the encapsulated packet
        are displayed."
    ::= { tnipNotificationsPrefix 25 }

tnipNotification26 NOTIFICATION-TYPE
    OBJECTS { 
              tnip26-protocol-num, 
              tnip26-source-ip-address,
              tnip26-destination-ip-address,
              tnip26-interface 
            }
    STATUS current
    DESCRIPTION
        "Notification of Event TNIP.26

        Message: 'Successfully deciphered GRE packet, internal protocol 0x$1, (source $2 and destination $3), interface $4'

        Parameters list:
              $1: tnip26-protocol-num
              $2: tnip26-source-ip-address
              $3: tnip26-destination-ip-address
              $4: tnip26-interface

        The payload of a GRE packet has been deciphered successfully.
        The internal protocol, source and destination of the GRE packet and
        the interface are displayed."
    ::= { tnipNotificationsPrefix 26 }

tnipNotification27 NOTIFICATION-TYPE
    OBJECTS { 
              tnip27-interface 
            }
    STATUS current
    DESCRIPTION
        "Notification of Event TNIP.27

        Message: 'Error deciphering GRE, interface $1'

        Parameters list:
              $1: tnip27-interface

        A deciphered packet has an invalid cipher checksum or the protocol
        is not ciphered."
    ::= { tnipNotificationsPrefix 27 }

tnipNotification28 NOTIFICATION-TYPE
    OBJECTS { 
              tnip28-protocol-num, 
              tnip28-interface,
              tnip28-seq-num 
            }
    STATUS current
    DESCRIPTION
        "Notification of Event TNIP.28

        Message: 'Desencapsulated GRE packet successfully, internal protocol 0x$1, interface $2 sequence number $3'

        Parameters list:
              $1: tnip28-protocol-num
              $2: tnip28-interface
              $3: tnip28-seq-num

        Successful packet GRE desencapsulation. The internal protocol of the
        GRE packet together with the interface are displayed."
    ::= { tnipNotificationsPrefix 28 }

tnipNotification29 NOTIFICATION-TYPE
    OBJECTS { 
              tnip29-protocol-num, 
              tnip29-interface 
            }
    STATUS current
    DESCRIPTION
        "Notification of Event TNIP.29

        Message: 'Successful ciphered GRE packet, internal protocol 0x$1, interface $2'

        Parameters list:
              $1: tnip29-protocol-num
              $2: tnip29-interface

        The payload of a GRE packet has been ciphered successfully. The protocol
        of the encapsulated packet is displayed."
    ::= { tnipNotificationsPrefix 29 }

tnipNotification30 NOTIFICATION-TYPE
    OBJECTS { 
              tnip30-protocol-num, 
              tnip30-interface 
            }
    STATUS current
    DESCRIPTION
        "Notification of Event TNIP.30

        Message: 'Successfully encapsulated GRE packet, internal protocol 0x$1, interface $2'

        Parameters list:
              $1: tnip30-protocol-num
              $2: tnip30-interface

        Successfully encapsulated GRE packet. The protocol of the encapsulated
        packet is displayed."
    ::= { tnipNotificationsPrefix 30 }

tnipNotification31 NOTIFICATION-TYPE
    OBJECTS { 
              tnip31-protocol-num, 
              tnip31-source-mac-address,
              tnip31-destination-mac-address,
              tnip31-interface,
              tnip31-seq-num 
            }
    STATUS current
    DESCRIPTION
        "Notification of Event TNIP.31

        Message: 'Desencapsulated GRE packet successfully, internal protocol 0x$1, (source $2 and destination $3), interface $4 sequence number $5'

        Parameters list:
              $1: tnip31-protocol-num
              $2: tnip31-source-mac-address
              $3: tnip31-destination-mac-address
              $4: tnip31-interface
              $5: tnip31-seq-num

        Successful packet GRE desencapsulation. The internal protocol of the
        GRE packet, the MAC source and the MAC destination, together with the
        interface and the sequence number are displayed."
    ::= { tnipNotificationsPrefix 31 }

tnipNotification32 NOTIFICATION-TYPE
    OBJECTS { 
              tnip32-protocol-num, 
              tnip32-source-mac-address,
              tnip32-destination-mac-address,
              tnip32-interface 
            }
    STATUS current
    DESCRIPTION
        "Notification of Event TNIP.32

        Message: 'Successfully ciphered GRE packet, internal protocol 0x$1, (source $2 and destination $3), interface $4'

        Parameters list:
              $1: tnip32-protocol-num
              $2: tnip32-source-mac-address
              $3: tnip32-destination-mac-address
              $4: tnip32-interface

        The payload of a GRE packet has been ciphered successfully.
        The protocol, MAC source and destination of the encapsulated packet,
        together with the interface are displayed."
    ::= { tnipNotificationsPrefix 32 }

tnipNotification33 NOTIFICATION-TYPE
    OBJECTS { 
              tnip33-protocol-num, 
              tnip33-source-mac-address,
              tnip33-destination-mac-address,
              tnip33-interface 
            }
    STATUS current
    DESCRIPTION
        "Notification of Event TNIP.33

        Message: 'Successfully encapsulated GRE packet, internal protocol 0x$1, (source $2 destination $3), interface $4'

        Parameters list:
              $1: tnip33-protocol-num
              $2: tnip33-source-mac-address
              $3: tnip33-destination-mac-address
              $4: tnip33-interface

        Successfully encapsulated GRE packet. The protocol, MAC source and
        destination of the encapsulated packet, together with the interface are
        displayed."
    ::= { tnipNotificationsPrefix 33 }

tnipNotification34 NOTIFICATION-TYPE
    OBJECTS { 
              tnip34-interface 
            }
    STATUS current
    DESCRIPTION
        "Notification of Event TNIP.34

        Message: 'No packet for keepalive interface $1'

        Parameters list:
              $1: tnip34-interface

        A buffer could not be allocated when needed for keepalive request."
    ::= { tnipNotificationsPrefix 34 }

tnipNotification35 NOTIFICATION-TYPE
    OBJECTS { 
              tnip35-interface 
            }
    STATUS current
    DESCRIPTION
        "Notification of Event TNIP.35

        Message: 'Sending keepalive packet on interface $1'

        Parameters list:
              $1: tnip35-interface

        A keepalive is going to be sent on specified interface to test tunnel
        endpoint reachability."
    ::= { tnipNotificationsPrefix 35 }

tnipNotification36 NOTIFICATION-TYPE
    OBJECTS { 
              tnip36-received-id, 
              tnip36-expected-id,
              tnip36-interface 
            }
    STATUS current
    DESCRIPTION
        "Notification of Event TNIP.36

        Message: 'Unexpected keepalive identification number $1 (expected $2) received on interface $3'

        Parameters list:
              $1: tnip36-received-id
              $2: tnip36-expected-id
              $3: tnip36-interface

        A keepalive was received on specified interface with an unexpected
        identification number. The received and the expected identification
        numbers are shown, as well as incoming interface name."
    ::= { tnipNotificationsPrefix 36 }

tnipNotification37 NOTIFICATION-TYPE
    OBJECTS { 
              tnip37-interface 
            }
    STATUS current
    DESCRIPTION
        "Notification of Event TNIP.37

        Message: 'Received keepalive on interface $1'

        Parameters list:
              $1: tnip37-interface

        A keepalive response was received on specified interface."
    ::= { tnipNotificationsPrefix 37 }

tnipNotification38 NOTIFICATION-TYPE
    OBJECTS { 
              tnip38-interface 
            }
    STATUS current
    DESCRIPTION
        "Notification of Event TNIP.38

        Message: 'Discarded keepalive on interface $1'

        Parameters list:
              $1: tnip38-interface

        An unexpected keepalive response was received on specified interface."
    ::= { tnipNotificationsPrefix 38 }

tnipNotification39 NOTIFICATION-TYPE
    OBJECTS { 
              tnip39-rmtu, 
              tnip39-src-ip-addr,
              tnip39-dest-ip-addr,
              tnip39-interface 
            }
    STATUS current
    DESCRIPTION
        "Notification of Event TNIP.39

        Message: 'Rcvd ICMP PMTU: Next-hop mtu = $1 bytes, pkt $2 -> $3, on interface $4'

        Parameters list:
              $1: tnip39-rmtu
              $2: tnip39-src-ip-addr
              $3: tnip39-dest-ip-addr
              $4: tnip39-interface

        The router received an ICMP Path MTU 'too big' message (RFC 1191),
        indicating that a sent packet was too big and was unable
        to be fragmented for some reason. The 'source' IP address indicates
        the router whose next hop MTU is too small for the packet."
    ::= { tnipNotificationsPrefix 39 }

tnipNotification40 NOTIFICATION-TYPE
    OBJECTS { 
              tnip40-interface 
            }
    STATUS current
    DESCRIPTION
        "Notification of Event TNIP.40

        Message: 'Forwarding keepalive on interface $1'

        Parameters list:
              $1: tnip40-interface

        A keepalive received on specified interface is being forwarded."
    ::= { tnipNotificationsPrefix 40 }


END
