-- file automatically created


TELDAT-TRAP-X253-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


x253TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the X253 event subsystem."
    REVISION "201401200930Z"
    DESCRIPTION "Initial implementation"
        ::= { telEventTraps 98 }


x253EventsGroup	OBJECT IDENTIFIER	::= { x253TrapsMIB 1 }

x253Notifications	OBJECT IDENTIFIER	::= { x253TrapsMIB 2 }
x253NotificationsPrefix	OBJECT IDENTIFIER	::= { x253Notifications 0 }

x253EventObjects1 OBJECT-IDENTITY
    STATUS current
    DESCRIPTION
        "Event X253.1
        Data packet received on lcn of the indicated port."
    ::= { x253EventsGroup 1 }

x2531-bit-q OBJECT-TYPE
    SYNTAX DisplayString
    MAX-ACCESS accessible-for-notify
    STATUS current
    DESCRIPTION
        "Parameter 'bit-q' in event X253.1"
    ::= { x253EventObjects1 1 }

x2531-bit-m OBJECT-TYPE
    SYNTAX DisplayString
    MAX-ACCESS accessible-for-notify
    STATUS current
    DESCRIPTION
        "Parameter 'bit-m' in event X253.1"
    ::= { x253EventObjects1 2 }

x2531-lcn OBJECT-TYPE
    SYNTAX Integer32
    MAX-ACCESS accessible-for-notify
    STATUS current
    DESCRIPTION
        "Parameter 'lcn' in event X253.1"
    ::= { x253EventObjects1 3 }

x2531-port OBJECT-TYPE
    SYNTAX DisplayString
    MAX-ACCESS accessible-for-notify
    STATUS current
    DESCRIPTION
        "Parameter 'port' in event X253.1"
    ::= { x253EventObjects1 4 }

x2531-bytes-rx OBJECT-TYPE
    SYNTAX Integer32
    MAX-ACCESS accessible-for-notify
    STATUS current
    DESCRIPTION
        "Parameter 'bytes-rx' in event X253.1"
    ::= { x253EventObjects1 5 }

x2531-buffer OBJECT-TYPE
    SYNTAX DisplayString
    MAX-ACCESS accessible-for-notify
    STATUS current
    DESCRIPTION
        "Parameter 'buffer' in event X253.1"
    ::= { x253EventObjects1 6 }

x253EventObjects2 OBJECT-IDENTITY
    STATUS current
    DESCRIPTION
        "Event X253.2
        Incomming call received on lcn port."
    ::= { x253EventsGroup 2 }

x2532-lcn OBJECT-TYPE
    SYNTAX Integer32
    MAX-ACCESS accessible-for-notify
    STATUS current
    DESCRIPTION
        "Parameter 'lcn' in event X253.2"
    ::= { x253EventObjects2 1 }

x2532-port OBJECT-TYPE
    SYNTAX DisplayString
    MAX-ACCESS accessible-for-notify
    STATUS current
    DESCRIPTION
        "Parameter 'port' in event X253.2"
    ::= { x253EventObjects2 2 }

x2532-buffer OBJECT-TYPE
    SYNTAX DisplayString
    MAX-ACCESS accessible-for-notify
    STATUS current
    DESCRIPTION
        "Parameter 'buffer' in event X253.2"
    ::= { x253EventObjects2 3 }

x253EventObjects3 OBJECT-IDENTITY
    STATUS current
    DESCRIPTION
        "Event X253.3
        Call connected packet received on lcn of the indicated port."
    ::= { x253EventsGroup 3 }

x2533-lcn OBJECT-TYPE
    SYNTAX Integer32
    MAX-ACCESS accessible-for-notify
    STATUS current
    DESCRIPTION
        "Parameter 'lcn' in event X253.3"
    ::= { x253EventObjects3 1 }

x2533-port OBJECT-TYPE
    SYNTAX DisplayString
    MAX-ACCESS accessible-for-notify
    STATUS current
    DESCRIPTION
        "Parameter 'port' in event X253.3"
    ::= { x253EventObjects3 2 }

x2533-buffer OBJECT-TYPE
    SYNTAX DisplayString
    MAX-ACCESS accessible-for-notify
    STATUS current
    DESCRIPTION
        "Parameter 'buffer' in event X253.3"
    ::= { x253EventObjects3 3 }

x253EventObjects4 OBJECT-IDENTITY
    STATUS current
    DESCRIPTION
        "Event X253.4
        Clear indication packet received on lcn of the indicated port."
    ::= { x253EventsGroup 4 }

x2534-lcn OBJECT-TYPE
    SYNTAX Integer32
    MAX-ACCESS accessible-for-notify
    STATUS current
    DESCRIPTION
        "Parameter 'lcn' in event X253.4"
    ::= { x253EventObjects4 1 }

x2534-port OBJECT-TYPE
    SYNTAX DisplayString
    MAX-ACCESS accessible-for-notify
    STATUS current
    DESCRIPTION
        "Parameter 'port' in event X253.4"
    ::= { x253EventObjects4 2 }

x2534-cause OBJECT-TYPE
    SYNTAX Integer32
    MAX-ACCESS accessible-for-notify
    STATUS current
    DESCRIPTION
        "Parameter 'cause' in event X253.4"
    ::= { x253EventObjects4 3 }

x2534-diagnostic OBJECT-TYPE
    SYNTAX Integer32
    MAX-ACCESS accessible-for-notify
    STATUS current
    DESCRIPTION
        "Parameter 'diagnostic' in event X253.4"
    ::= { x253EventObjects4 4 }

x253EventObjects5 OBJECT-IDENTITY
    STATUS current
    DESCRIPTION
        "Event X253.5
        Clear confirmation packet received on lcn of the indicated port."
    ::= { x253EventsGroup 5 }

x2535-lcn OBJECT-TYPE
    SYNTAX Integer32
    MAX-ACCESS accessible-for-notify
    STATUS current
    DESCRIPTION
        "Parameter 'lcn' in event X253.5"
    ::= { x253EventObjects5 1 }

x2535-port OBJECT-TYPE
    SYNTAX DisplayString
    MAX-ACCESS accessible-for-notify
    STATUS current
    DESCRIPTION
        "Parameter 'port' in event X253.5"
    ::= { x253EventObjects5 2 }

x253EventObjects6 OBJECT-IDENTITY
    STATUS current
    DESCRIPTION
        "Event X253.6
        Interrupt indication on lcn of the indicated port."
    ::= { x253EventsGroup 6 }

x2536-lcn OBJECT-TYPE
    SYNTAX Integer32
    MAX-ACCESS accessible-for-notify
    STATUS current
    DESCRIPTION
        "Parameter 'lcn' in event X253.6"
    ::= { x253EventObjects6 1 }

x2536-port OBJECT-TYPE
    SYNTAX DisplayString
    MAX-ACCESS accessible-for-notify
    STATUS current
    DESCRIPTION
        "Parameter 'port' in event X253.6"
    ::= { x253EventObjects6 2 }

x253EventObjects7 OBJECT-IDENTITY
    STATUS current
    DESCRIPTION
        "Event X253.7
        Interrupt confirmation on lcn of the indicated port."
    ::= { x253EventsGroup 7 }

x2537-lcn OBJECT-TYPE
    SYNTAX Integer32
    MAX-ACCESS accessible-for-notify
    STATUS current
    DESCRIPTION
        "Parameter 'lcn' in event X253.7"
    ::= { x253EventObjects7 1 }

x2537-port OBJECT-TYPE
    SYNTAX DisplayString
    MAX-ACCESS accessible-for-notify
    STATUS current
    DESCRIPTION
        "Parameter 'port' in event X253.7"
    ::= { x253EventObjects7 2 }

x253EventObjects8 OBJECT-IDENTITY
    STATUS current
    DESCRIPTION
        "Event X253.8
        Reset indication packet received on lcn of the indicated port."
    ::= { x253EventsGroup 8 }

x2538-lcn OBJECT-TYPE
    SYNTAX Integer32
    MAX-ACCESS accessible-for-notify
    STATUS current
    DESCRIPTION
        "Parameter 'lcn' in event X253.8"
    ::= { x253EventObjects8 1 }

x2538-port OBJECT-TYPE
    SYNTAX DisplayString
    MAX-ACCESS accessible-for-notify
    STATUS current
    DESCRIPTION
        "Parameter 'port' in event X253.8"
    ::= { x253EventObjects8 2 }

x2538-cause OBJECT-TYPE
    SYNTAX Integer32
    MAX-ACCESS accessible-for-notify
    STATUS current
    DESCRIPTION
        "Parameter 'cause' in event X253.8"
    ::= { x253EventObjects8 3 }

x2538-diagnostic OBJECT-TYPE
    SYNTAX Integer32
    MAX-ACCESS accessible-for-notify
    STATUS current
    DESCRIPTION
        "Parameter 'diagnostic' in event X253.8"
    ::= { x253EventObjects8 4 }

x253EventObjects9 OBJECT-IDENTITY
    STATUS current
    DESCRIPTION
        "Event X253.9
        Reset confirmation packet received on lcn of the indicated port."
    ::= { x253EventsGroup 9 }

x2539-lcn OBJECT-TYPE
    SYNTAX Integer32
    MAX-ACCESS accessible-for-notify
    STATUS current
    DESCRIPTION
        "Parameter 'lcn' in event X253.9"
    ::= { x253EventObjects9 1 }

x2539-port OBJECT-TYPE
    SYNTAX DisplayString
    MAX-ACCESS accessible-for-notify
    STATUS current
    DESCRIPTION
        "Parameter 'port' in event X253.9"
    ::= { x253EventObjects9 2 }

x253EventObjects10 OBJECT-IDENTITY
    STATUS current
    DESCRIPTION
        "Event X253.10
        Restart indication packet received on lcn of the indicated port."
    ::= { x253EventsGroup 10 }

x25310-lcn OBJECT-TYPE
    SYNTAX Integer32
    MAX-ACCESS accessible-for-notify
    STATUS current
    DESCRIPTION
        "Parameter 'lcn' in event X253.10"
    ::= { x253EventObjects10 1 }

x25310-port OBJECT-TYPE
    SYNTAX DisplayString
    MAX-ACCESS accessible-for-notify
    STATUS current
    DESCRIPTION
        "Parameter 'port' in event X253.10"
    ::= { x253EventObjects10 2 }

x25310-cause OBJECT-TYPE
    SYNTAX Integer32
    MAX-ACCESS accessible-for-notify
    STATUS current
    DESCRIPTION
        "Parameter 'cause' in event X253.10"
    ::= { x253EventObjects10 3 }

x25310-diagnostic OBJECT-TYPE
    SYNTAX Integer32
    MAX-ACCESS accessible-for-notify
    STATUS current
    DESCRIPTION
        "Parameter 'diagnostic' in event X253.10"
    ::= { x253EventObjects10 4 }

x253EventObjects11 OBJECT-IDENTITY
    STATUS current
    DESCRIPTION
        "Event X253.11
        Restart confirmation packet received on lcn of the indicated port."
    ::= { x253EventsGroup 11 }

x25311-lcn OBJECT-TYPE
    SYNTAX Integer32
    MAX-ACCESS accessible-for-notify
    STATUS current
    DESCRIPTION
        "Parameter 'lcn' in event X253.11"
    ::= { x253EventObjects11 1 }

x25311-port OBJECT-TYPE
    SYNTAX DisplayString
    MAX-ACCESS accessible-for-notify
    STATUS current
    DESCRIPTION
        "Parameter 'port' in event X253.11"
    ::= { x253EventObjects11 2 }

x253EventObjects12 OBJECT-IDENTITY
    STATUS current
    DESCRIPTION
        "Event X253.12
        Data packet transmitted on lcn of the indicated port."
    ::= { x253EventsGroup 12 }

x25312-bit-q OBJECT-TYPE
    SYNTAX DisplayString
    MAX-ACCESS accessible-for-notify
    STATUS current
    DESCRIPTION
        "Parameter 'bit-q' in event X253.12"
    ::= { x253EventObjects12 1 }

x25312-bit-m OBJECT-TYPE
    SYNTAX DisplayString
    MAX-ACCESS accessible-for-notify
    STATUS current
    DESCRIPTION
        "Parameter 'bit-m' in event X253.12"
    ::= { x253EventObjects12 2 }

x25312-lcn OBJECT-TYPE
    SYNTAX Integer32
    MAX-ACCESS accessible-for-notify
    STATUS current
    DESCRIPTION
        "Parameter 'lcn' in event X253.12"
    ::= { x253EventObjects12 3 }

x25312-port OBJECT-TYPE
    SYNTAX DisplayString
    MAX-ACCESS accessible-for-notify
    STATUS current
    DESCRIPTION
        "Parameter 'port' in event X253.12"
    ::= { x253EventObjects12 4 }

x25312-bytes-tx OBJECT-TYPE
    SYNTAX Integer32
    MAX-ACCESS accessible-for-notify
    STATUS current
    DESCRIPTION
        "Parameter 'bytes-tx' in event X253.12"
    ::= { x253EventObjects12 5 }

x25312-buffer OBJECT-TYPE
    SYNTAX DisplayString
    MAX-ACCESS accessible-for-notify
    STATUS current
    DESCRIPTION
        "Parameter 'buffer' in event X253.12"
    ::= { x253EventObjects12 6 }

x253EventObjects13 OBJECT-IDENTITY
    STATUS current
    DESCRIPTION
        "Event X253.13
        Call Request on lcn of the indicated port."
    ::= { x253EventsGroup 13 }

x25313-lcn OBJECT-TYPE
    SYNTAX Integer32
    MAX-ACCESS accessible-for-notify
    STATUS current
    DESCRIPTION
        "Parameter 'lcn' in event X253.13"
    ::= { x253EventObjects13 1 }

x25313-port OBJECT-TYPE
    SYNTAX DisplayString
    MAX-ACCESS accessible-for-notify
    STATUS current
    DESCRIPTION
        "Parameter 'port' in event X253.13"
    ::= { x253EventObjects13 2 }

x25313-buffer OBJECT-TYPE
    SYNTAX DisplayString
    MAX-ACCESS accessible-for-notify
    STATUS current
    DESCRIPTION
        "Parameter 'buffer' in event X253.13"
    ::= { x253EventObjects13 3 }

x253EventObjects14 OBJECT-IDENTITY
    STATUS current
    DESCRIPTION
        "Event X253.14
        Call Accept on lcn of the indicated port."
    ::= { x253EventsGroup 14 }

x25314-lcn OBJECT-TYPE
    SYNTAX Integer32
    MAX-ACCESS accessible-for-notify
    STATUS current
    DESCRIPTION
        "Parameter 'lcn' in event X253.14"
    ::= { x253EventObjects14 1 }

x25314-port OBJECT-TYPE
    SYNTAX DisplayString
    MAX-ACCESS accessible-for-notify
    STATUS current
    DESCRIPTION
        "Parameter 'port' in event X253.14"
    ::= { x253EventObjects14 2 }

x25314-buffer OBJECT-TYPE
    SYNTAX DisplayString
    MAX-ACCESS accessible-for-notify
    STATUS current
    DESCRIPTION
        "Parameter 'buffer' in event X253.14"
    ::= { x253EventObjects14 3 }

x253EventObjects15 OBJECT-IDENTITY
    STATUS current
    DESCRIPTION
        "Event X253.15
        Clear Request packet transmitted on lcn of the indicated port."
    ::= { x253EventsGroup 15 }

x25315-lcn OBJECT-TYPE
    SYNTAX Integer32
    MAX-ACCESS accessible-for-notify
    STATUS current
    DESCRIPTION
        "Parameter 'lcn' in event X253.15"
    ::= { x253EventObjects15 1 }

x25315-port OBJECT-TYPE
    SYNTAX DisplayString
    MAX-ACCESS accessible-for-notify
    STATUS current
    DESCRIPTION
        "Parameter 'port' in event X253.15"
    ::= { x253EventObjects15 2 }

x25315-cause OBJECT-TYPE
    SYNTAX Integer32
    MAX-ACCESS accessible-for-notify
    STATUS current
    DESCRIPTION
        "Parameter 'cause' in event X253.15"
    ::= { x253EventObjects15 3 }

x25315-diagnostic OBJECT-TYPE
    SYNTAX Integer32
    MAX-ACCESS accessible-for-notify
    STATUS current
    DESCRIPTION
        "Parameter 'diagnostic' in event X253.15"
    ::= { x253EventObjects15 4 }

x253EventObjects16 OBJECT-IDENTITY
    STATUS current
    DESCRIPTION
        "Event X253.16
        Clear confirmation packed transmitted on lcn of the indicated port."
    ::= { x253EventsGroup 16 }

x25316-lcn OBJECT-TYPE
    SYNTAX Integer32
    MAX-ACCESS accessible-for-notify
    STATUS current
    DESCRIPTION
        "Parameter 'lcn' in event X253.16"
    ::= { x253EventObjects16 1 }

x25316-port OBJECT-TYPE
    SYNTAX DisplayString
    MAX-ACCESS accessible-for-notify
    STATUS current
    DESCRIPTION
        "Parameter 'port' in event X253.16"
    ::= { x253EventObjects16 2 }

x253EventObjects17 OBJECT-IDENTITY
    STATUS current
    DESCRIPTION
        "Event X253.17
        Restart Request packet transmitted on lcn of the indicated port."
    ::= { x253EventsGroup 17 }

x25317-lcn OBJECT-TYPE
    SYNTAX Integer32
    MAX-ACCESS accessible-for-notify
    STATUS current
    DESCRIPTION
        "Parameter 'lcn' in event X253.17"
    ::= { x253EventObjects17 1 }

x25317-port OBJECT-TYPE
    SYNTAX DisplayString
    MAX-ACCESS accessible-for-notify
    STATUS current
    DESCRIPTION
        "Parameter 'port' in event X253.17"
    ::= { x253EventObjects17 2 }

x25317-cause OBJECT-TYPE
    SYNTAX Integer32
    MAX-ACCESS accessible-for-notify
    STATUS current
    DESCRIPTION
        "Parameter 'cause' in event X253.17"
    ::= { x253EventObjects17 3 }

x25317-diagnostic OBJECT-TYPE
    SYNTAX Integer32
    MAX-ACCESS accessible-for-notify
    STATUS current
    DESCRIPTION
        "Parameter 'diagnostic' in event X253.17"
    ::= { x253EventObjects17 4 }

x253EventObjects18 OBJECT-IDENTITY
    STATUS current
    DESCRIPTION
        "Event X253.18
        Restart confirmation packed transmitted on lcn of the indicated port."
    ::= { x253EventsGroup 18 }

x25318-lcn OBJECT-TYPE
    SYNTAX Integer32
    MAX-ACCESS accessible-for-notify
    STATUS current
    DESCRIPTION
        "Parameter 'lcn' in event X253.18"
    ::= { x253EventObjects18 1 }

x25318-port OBJECT-TYPE
    SYNTAX DisplayString
    MAX-ACCESS accessible-for-notify
    STATUS current
    DESCRIPTION
        "Parameter 'port' in event X253.18"
    ::= { x253EventObjects18 2 }

x253EventObjects19 OBJECT-IDENTITY
    STATUS current
    DESCRIPTION
        "Event X253.19
        Reset Request packet transmitted on lcn of the indicated port."
    ::= { x253EventsGroup 19 }

x25319-lcn OBJECT-TYPE
    SYNTAX Integer32
    MAX-ACCESS accessible-for-notify
    STATUS current
    DESCRIPTION
        "Parameter 'lcn' in event X253.19"
    ::= { x253EventObjects19 1 }

x25319-port OBJECT-TYPE
    SYNTAX DisplayString
    MAX-ACCESS accessible-for-notify
    STATUS current
    DESCRIPTION
        "Parameter 'port' in event X253.19"
    ::= { x253EventObjects19 2 }

x25319-cause OBJECT-TYPE
    SYNTAX Integer32
    MAX-ACCESS accessible-for-notify
    STATUS current
    DESCRIPTION
        "Parameter 'cause' in event X253.19"
    ::= { x253EventObjects19 3 }

x25319-diagnostic OBJECT-TYPE
    SYNTAX Integer32
    MAX-ACCESS accessible-for-notify
    STATUS current
    DESCRIPTION
        "Parameter 'diagnostic' in event X253.19"
    ::= { x253EventObjects19 4 }

x253EventObjects20 OBJECT-IDENTITY
    STATUS current
    DESCRIPTION
        "Event X253.20
        Reset confirmation packed transmitted on lcn of the indicated port."
    ::= { x253EventsGroup 20 }

x25320-lcn OBJECT-TYPE
    SYNTAX Integer32
    MAX-ACCESS accessible-for-notify
    STATUS current
    DESCRIPTION
        "Parameter 'lcn' in event X253.20"
    ::= { x253EventObjects20 1 }

x25320-port OBJECT-TYPE
    SYNTAX DisplayString
    MAX-ACCESS accessible-for-notify
    STATUS current
    DESCRIPTION
        "Parameter 'port' in event X253.20"
    ::= { x253EventObjects20 2 }

x253EventObjects21 OBJECT-IDENTITY
    STATUS current
    DESCRIPTION
        "Event X253.21
        Interrupt Request packet transmitted on lcn of the indicated port."
    ::= { x253EventsGroup 21 }

x25321-lcn OBJECT-TYPE
    SYNTAX Integer32
    MAX-ACCESS accessible-for-notify
    STATUS current
    DESCRIPTION
        "Parameter 'lcn' in event X253.21"
    ::= { x253EventObjects21 1 }

x25321-port OBJECT-TYPE
    SYNTAX DisplayString
    MAX-ACCESS accessible-for-notify
    STATUS current
    DESCRIPTION
        "Parameter 'port' in event X253.21"
    ::= { x253EventObjects21 2 }

x253EventObjects22 OBJECT-IDENTITY
    STATUS current
    DESCRIPTION
        "Event X253.22
        Interrupt confirmation packed transmitted on lcn of the indicated port."
    ::= { x253EventsGroup 22 }

x25322-lcn OBJECT-TYPE
    SYNTAX Integer32
    MAX-ACCESS accessible-for-notify
    STATUS current
    DESCRIPTION
        "Parameter 'lcn' in event X253.22"
    ::= { x253EventObjects22 1 }

x25322-port OBJECT-TYPE
    SYNTAX DisplayString
    MAX-ACCESS accessible-for-notify
    STATUS current
    DESCRIPTION
        "Parameter 'port' in event X253.22"
    ::= { x253EventObjects22 2 }

x253EventObjects23 OBJECT-IDENTITY
    STATUS current
    DESCRIPTION
        "Event X253.23
        RR Packet transmitted on lcn of the indicated port."
    ::= { x253EventsGroup 23 }

x25323-lcn OBJECT-TYPE
    SYNTAX Integer32
    MAX-ACCESS accessible-for-notify
    STATUS current
    DESCRIPTION
        "Parameter 'lcn' in event X253.23"
    ::= { x253EventObjects23 1 }

x25323-port OBJECT-TYPE
    SYNTAX DisplayString
    MAX-ACCESS accessible-for-notify
    STATUS current
    DESCRIPTION
        "Parameter 'port' in event X253.23"
    ::= { x253EventObjects23 2 }

x253EventObjects24 OBJECT-IDENTITY
    STATUS current
    DESCRIPTION
        "Event X253.24
        RR Packet received on lcn of the indicated port."
    ::= { x253EventsGroup 24 }

x25324-lcn OBJECT-TYPE
    SYNTAX Integer32
    MAX-ACCESS accessible-for-notify
    STATUS current
    DESCRIPTION
        "Parameter 'lcn' in event X253.24"
    ::= { x253EventObjects24 1 }

x25324-port OBJECT-TYPE
    SYNTAX DisplayString
    MAX-ACCESS accessible-for-notify
    STATUS current
    DESCRIPTION
        "Parameter 'port' in event X253.24"
    ::= { x253EventObjects24 2 }

x253EventObjects25 OBJECT-IDENTITY
    STATUS current
    DESCRIPTION
        "Event X253.25
        X.25 event code:
        0x01 Receipt of a packet that is shorter then the X.25 minimum header length
        0x04 Receipt of a packet which is too short
        0x05 Receipt of a packet which has an incorrect GFI
        0x06 Receipt of a packet which an unassigned logical channel
        0x0c Timeout for the restart procedure
        0x0f Timeout for the reset procedure."
    ::= { x253EventsGroup 25 }

x25325-code OBJECT-TYPE
    SYNTAX Integer32
    MAX-ACCESS accessible-for-notify
    STATUS current
    DESCRIPTION
        "Parameter 'code' in event X253.25"
    ::= { x253EventObjects25 1 }

x25325-port OBJECT-TYPE
    SYNTAX DisplayString
    MAX-ACCESS accessible-for-notify
    STATUS current
    DESCRIPTION
        "Parameter 'port' in event X253.25"
    ::= { x253EventObjects25 2 }

x253EventObjects26 OBJECT-IDENTITY
    STATUS current
    DESCRIPTION
        "Event X253.26
        Diagnostic packet received on lcn of the indicated port."
    ::= { x253EventsGroup 26 }

x25326-lcn OBJECT-TYPE
    SYNTAX Integer32
    MAX-ACCESS accessible-for-notify
    STATUS current
    DESCRIPTION
        "Parameter 'lcn' in event X253.26"
    ::= { x253EventObjects26 1 }

x25326-port OBJECT-TYPE
    SYNTAX DisplayString
    MAX-ACCESS accessible-for-notify
    STATUS current
    DESCRIPTION
        "Parameter 'port' in event X253.26"
    ::= { x253EventObjects26 2 }

x25326-buffer OBJECT-TYPE
    SYNTAX DisplayString
    MAX-ACCESS accessible-for-notify
    STATUS current
    DESCRIPTION
        "Parameter 'buffer' in event X253.26"
    ::= { x253EventObjects26 3 }

x253EventObjects27 OBJECT-IDENTITY
    STATUS current
    DESCRIPTION
        "Event X253.27
        X.25 ERROR message."
    ::= { x253EventsGroup 27 }

x25327-msg OBJECT-TYPE
    SYNTAX DisplayString
    MAX-ACCESS accessible-for-notify
    STATUS current
    DESCRIPTION
        "Parameter 'msg' in event X253.27"
    ::= { x253EventObjects27 1 }


x253Notification1 NOTIFICATION-TYPE
    OBJECTS { 
              x2531-bit-q, 
              x2531-bit-m,
              x2531-lcn,
              x2531-port,
              x2531-bytes-rx,
              x2531-buffer 
            }
    STATUS current
    DESCRIPTION
        "Notification of Event X253.1

        Message: 'Data packet $1$2 received on lcn $3 port $4 Received $5 bytesHexadecimal data: $6'

        Parameters list:
              $1: x2531-bit-q
              $2: x2531-bit-m
              $3: x2531-lcn
              $4: x2531-port
              $5: x2531-bytes-rx
              $6: x2531-buffer

        Data packet received on lcn of the indicated port."
    ::= { x253NotificationsPrefix 1 }

x253Notification2 NOTIFICATION-TYPE
    OBJECTS { 
              x2532-lcn, 
              x2532-port,
              x2532-buffer 
            }
    STATUS current
    DESCRIPTION
        "Notification of Event X253.2

        Message: 'Incomming call on lcn $1 port $2Hexadecimal data: $3'

        Parameters list:
              $1: x2532-lcn
              $2: x2532-port
              $3: x2532-buffer

        Incomming call received on lcn port."
    ::= { x253NotificationsPrefix 2 }

x253Notification3 NOTIFICATION-TYPE
    OBJECTS { 
              x2533-lcn, 
              x2533-port,
              x2533-buffer 
            }
    STATUS current
    DESCRIPTION
        "Notification of Event X253.3

        Message: 'Call connected on lcn $1 port $2Hexadecimal data: $3'

        Parameters list:
              $1: x2533-lcn
              $2: x2533-port
              $3: x2533-buffer

        Call connected packet received on lcn of the indicated port."
    ::= { x253NotificationsPrefix 3 }

x253Notification4 NOTIFICATION-TYPE
    OBJECTS { 
              x2534-lcn, 
              x2534-port,
              x2534-cause,
              x2534-diagnostic 
            }
    STATUS current
    DESCRIPTION
        "Notification of Event X253.4

        Message: 'Clear indication on lcn $1 port $2 cause 0x$3 diagnostic 0x$4'

        Parameters list:
              $1: x2534-lcn
              $2: x2534-port
              $3: x2534-cause
              $4: x2534-diagnostic

        Clear indication packet received on lcn of the indicated port."
    ::= { x253NotificationsPrefix 4 }

x253Notification5 NOTIFICATION-TYPE
    OBJECTS { 
              x2535-lcn, 
              x2535-port 
            }
    STATUS current
    DESCRIPTION
        "Notification of Event X253.5

        Message: 'Clear confirmation on lcn $1 port $2'

        Parameters list:
              $1: x2535-lcn
              $2: x2535-port

        Clear confirmation packet received on lcn of the indicated port."
    ::= { x253NotificationsPrefix 5 }

x253Notification6 NOTIFICATION-TYPE
    OBJECTS { 
              x2536-lcn, 
              x2536-port 
            }
    STATUS current
    DESCRIPTION
        "Notification of Event X253.6

        Message: 'Interrupt indication on lcn $1 port $2'

        Parameters list:
              $1: x2536-lcn
              $2: x2536-port

        Interrupt indication on lcn of the indicated port."
    ::= { x253NotificationsPrefix 6 }

x253Notification7 NOTIFICATION-TYPE
    OBJECTS { 
              x2537-lcn, 
              x2537-port 
            }
    STATUS current
    DESCRIPTION
        "Notification of Event X253.7

        Message: 'Interrupt confirmation on lcn $1 port $2'

        Parameters list:
              $1: x2537-lcn
              $2: x2537-port

        Interrupt confirmation on lcn of the indicated port."
    ::= { x253NotificationsPrefix 7 }

x253Notification8 NOTIFICATION-TYPE
    OBJECTS { 
              x2538-lcn, 
              x2538-port,
              x2538-cause,
              x2538-diagnostic 
            }
    STATUS current
    DESCRIPTION
        "Notification of Event X253.8

        Message: 'Reset indication on lcn $1 port $2 cause 0x$3 diagnostic 0x$4'

        Parameters list:
              $1: x2538-lcn
              $2: x2538-port
              $3: x2538-cause
              $4: x2538-diagnostic

        Reset indication packet received on lcn of the indicated port."
    ::= { x253NotificationsPrefix 8 }

x253Notification9 NOTIFICATION-TYPE
    OBJECTS { 
              x2539-lcn, 
              x2539-port 
            }
    STATUS current
    DESCRIPTION
        "Notification of Event X253.9

        Message: 'Reset confirmation on lcn $1 port $2'

        Parameters list:
              $1: x2539-lcn
              $2: x2539-port

        Reset confirmation packet received on lcn of the indicated port."
    ::= { x253NotificationsPrefix 9 }

x253Notification10 NOTIFICATION-TYPE
    OBJECTS { 
              x25310-lcn, 
              x25310-port,
              x25310-cause,
              x25310-diagnostic 
            }
    STATUS current
    DESCRIPTION
        "Notification of Event X253.10

        Message: 'Restart indication on lcn $1 port $2 cause 0x$3 diagnostic 0x$4'

        Parameters list:
              $1: x25310-lcn
              $2: x25310-port
              $3: x25310-cause
              $4: x25310-diagnostic

        Restart indication packet received on lcn of the indicated port."
    ::= { x253NotificationsPrefix 10 }

x253Notification11 NOTIFICATION-TYPE
    OBJECTS { 
              x25311-lcn, 
              x25311-port 
            }
    STATUS current
    DESCRIPTION
        "Notification of Event X253.11

        Message: 'Restart confirmation on lcn $1 port $2'

        Parameters list:
              $1: x25311-lcn
              $2: x25311-port

        Restart confirmation packet received on lcn of the indicated port."
    ::= { x253NotificationsPrefix 11 }

x253Notification12 NOTIFICATION-TYPE
    OBJECTS { 
              x25312-bit-q, 
              x25312-bit-m,
              x25312-lcn,
              x25312-port,
              x25312-bytes-tx,
              x25312-buffer 
            }
    STATUS current
    DESCRIPTION
        "Notification of Event X253.12

        Message: 'Data packet transmitted $1$2 on lcn $3 port $4 Transmitted $5 bytesHexadecimal data: $6'

        Parameters list:
              $1: x25312-bit-q
              $2: x25312-bit-m
              $3: x25312-lcn
              $4: x25312-port
              $5: x25312-bytes-tx
              $6: x25312-buffer

        Data packet transmitted on lcn of the indicated port."
    ::= { x253NotificationsPrefix 12 }

x253Notification13 NOTIFICATION-TYPE
    OBJECTS { 
              x25313-lcn, 
              x25313-port,
              x25313-buffer 
            }
    STATUS current
    DESCRIPTION
        "Notification of Event X253.13

        Message: 'Call Request on lcn $1 port $2Hexadecimal data: $3'

        Parameters list:
              $1: x25313-lcn
              $2: x25313-port
              $3: x25313-buffer

        Call Request on lcn of the indicated port."
    ::= { x253NotificationsPrefix 13 }

x253Notification14 NOTIFICATION-TYPE
    OBJECTS { 
              x25314-lcn, 
              x25314-port,
              x25314-buffer 
            }
    STATUS current
    DESCRIPTION
        "Notification of Event X253.14

        Message: 'Call Accept on lcn $1 port $2Hexadecimal data: $3'

        Parameters list:
              $1: x25314-lcn
              $2: x25314-port
              $3: x25314-buffer

        Call Accept on lcn of the indicated port."
    ::= { x253NotificationsPrefix 14 }

x253Notification15 NOTIFICATION-TYPE
    OBJECTS { 
              x25315-lcn, 
              x25315-port,
              x25315-cause,
              x25315-diagnostic 
            }
    STATUS current
    DESCRIPTION
        "Notification of Event X253.15

        Message: 'Clear Request on lcn $1 port $2 cause 0x$3 diagnostic 0x$4'

        Parameters list:
              $1: x25315-lcn
              $2: x25315-port
              $3: x25315-cause
              $4: x25315-diagnostic

        Clear Request packet transmitted on lcn of the indicated port."
    ::= { x253NotificationsPrefix 15 }

x253Notification16 NOTIFICATION-TYPE
    OBJECTS { 
              x25316-lcn, 
              x25316-port 
            }
    STATUS current
    DESCRIPTION
        "Notification of Event X253.16

        Message: 'Clear confirmation transmitted on lcn $1 port $2'

        Parameters list:
              $1: x25316-lcn
              $2: x25316-port

        Clear confirmation packed transmitted on lcn of the indicated port."
    ::= { x253NotificationsPrefix 16 }

x253Notification17 NOTIFICATION-TYPE
    OBJECTS { 
              x25317-lcn, 
              x25317-port,
              x25317-cause,
              x25317-diagnostic 
            }
    STATUS current
    DESCRIPTION
        "Notification of Event X253.17

        Message: 'Restart Request on lcn $1 port $2 cause 0x$3 diagnostic 0x$4'

        Parameters list:
              $1: x25317-lcn
              $2: x25317-port
              $3: x25317-cause
              $4: x25317-diagnostic

        Restart Request packet transmitted on lcn of the indicated port."
    ::= { x253NotificationsPrefix 17 }

x253Notification18 NOTIFICATION-TYPE
    OBJECTS { 
              x25318-lcn, 
              x25318-port 
            }
    STATUS current
    DESCRIPTION
        "Notification of Event X253.18

        Message: 'Restart confirmation transmitted on lcn $1 port $2'

        Parameters list:
              $1: x25318-lcn
              $2: x25318-port

        Restart confirmation packed transmitted on lcn of the indicated port."
    ::= { x253NotificationsPrefix 18 }

x253Notification19 NOTIFICATION-TYPE
    OBJECTS { 
              x25319-lcn, 
              x25319-port,
              x25319-cause,
              x25319-diagnostic 
            }
    STATUS current
    DESCRIPTION
        "Notification of Event X253.19

        Message: 'Reset Request on lcn $1 port $2 cause 0x$3 diagnostic 0x$4'

        Parameters list:
              $1: x25319-lcn
              $2: x25319-port
              $3: x25319-cause
              $4: x25319-diagnostic

        Reset Request packet transmitted on lcn of the indicated port."
    ::= { x253NotificationsPrefix 19 }

x253Notification20 NOTIFICATION-TYPE
    OBJECTS { 
              x25320-lcn, 
              x25320-port 
            }
    STATUS current
    DESCRIPTION
        "Notification of Event X253.20

        Message: 'Reset confirmation transmitted on lcn $1 port $2'

        Parameters list:
              $1: x25320-lcn
              $2: x25320-port

        Reset confirmation packed transmitted on lcn of the indicated port."
    ::= { x253NotificationsPrefix 20 }

x253Notification21 NOTIFICATION-TYPE
    OBJECTS { 
              x25321-lcn, 
              x25321-port 
            }
    STATUS current
    DESCRIPTION
        "Notification of Event X253.21

        Message: 'Interrupt Request on lcn $1 port $2'

        Parameters list:
              $1: x25321-lcn
              $2: x25321-port

        Interrupt Request packet transmitted on lcn of the indicated port."
    ::= { x253NotificationsPrefix 21 }

x253Notification22 NOTIFICATION-TYPE
    OBJECTS { 
              x25322-lcn, 
              x25322-port 
            }
    STATUS current
    DESCRIPTION
        "Notification of Event X253.22

        Message: 'Interrupt confirmation transmitted on lcn $1 port $2'

        Parameters list:
              $1: x25322-lcn
              $2: x25322-port

        Interrupt confirmation packed transmitted on lcn of the indicated port."
    ::= { x253NotificationsPrefix 22 }

x253Notification23 NOTIFICATION-TYPE
    OBJECTS { 
              x25323-lcn, 
              x25323-port 
            }
    STATUS current
    DESCRIPTION
        "Notification of Event X253.23

        Message: 'RR Packet transmitted on lcn $1 port $2'

        Parameters list:
              $1: x25323-lcn
              $2: x25323-port

        RR Packet transmitted on lcn of the indicated port."
    ::= { x253NotificationsPrefix 23 }

x253Notification24 NOTIFICATION-TYPE
    OBJECTS { 
              x25324-lcn, 
              x25324-port 
            }
    STATUS current
    DESCRIPTION
        "Notification of Event X253.24

        Message: 'RR Packet received on lcn $1 port $2'

        Parameters list:
              $1: x25324-lcn
              $2: x25324-port

        RR Packet received on lcn of the indicated port."
    ::= { x253NotificationsPrefix 24 }

x253Notification25 NOTIFICATION-TYPE
    OBJECTS { 
              x25325-code, 
              x25325-port 
            }
    STATUS current
    DESCRIPTION
        "Notification of Event X253.25

        Message: 'X.25 event code $1 port $2'

        Parameters list:
              $1: x25325-code
              $2: x25325-port

        X.25 event code:
        0x01 Receipt of a packet that is shorter then the X.25 minimum header length
        0x04 Receipt of a packet which is too short
        0x05 Receipt of a packet which has an incorrect GFI
        0x06 Receipt of a packet which an unassigned logical channel
        0x0c Timeout for the restart procedure
        0x0f Timeout for the reset procedure."
    ::= { x253NotificationsPrefix 25 }

x253Notification26 NOTIFICATION-TYPE
    OBJECTS { 
              x25326-lcn, 
              x25326-port,
              x25326-buffer 
            }
    STATUS current
    DESCRIPTION
        "Notification of Event X253.26

        Message: 'Diagnostic packet received on lcn $1 port $2Hexadecimal data: $3'

        Parameters list:
              $1: x25326-lcn
              $2: x25326-port
              $3: x25326-buffer

        Diagnostic packet received on lcn of the indicated port."
    ::= { x253NotificationsPrefix 26 }

x253Notification27 NOTIFICATION-TYPE
    OBJECTS { 
              x25327-msg 
            }
    STATUS current
    DESCRIPTION
        "Notification of Event X253.27

        Message: 'X.25 ERROR message: $1 '

        Parameters list:
              $1: x25327-msg

        X.25 ERROR message."
    ::= { x253NotificationsPrefix 27 }


END
