-- "@(#)NEC-MIB.txt 7.1.2.2 98/03/11 18:15:10"	sccs ident
-- NEC-MIB { iso org(3) dod(6) internet(1) private(4) enterprises(1) 119 }

NEC-MIB DEFINITIONS ::= BEGIN
	IMPORTS
        enterprises,  Counter,  IpAddress,  Opaque
                FROM RFC1155-SMI
        OBJECT-TYPE
                FROM RFC-1212
        DisplayString,  ifIndex
                FROM RFC1213-MIB
	DateAndTime,  TruthValue
		FROM SNMPv2-TC-v1;

	nec		OBJECT IDENTIFIER ::= { enterprises 119 }
	necProduct	OBJECT IDENTIFIER ::= { nec 1 }
	atomis		OBJECT IDENTIFIER ::= { necProduct 14 }
	m7-phase2	OBJECT IDENTIFIER ::= { atomis 9 }
	m7-corporate	OBJECT IDENTIFIER ::= { atomis 12 }
	nec-mib			OBJECT IDENTIFIER ::= { nec 2 }
	necProductDepend        OBJECT IDENTIFIER ::= { nec-mib 3 }
	atomis-mib          	OBJECT IDENTIFIER ::= { necProductDepend 14 }
	m7-phase2-mib		OBJECT IDENTIFIER ::= { atomis-mib 9 }
		node		OBJECT IDENTIFIER ::= { m7-phase2-mib 1 }
		slot		OBJECT IDENTIFIER ::= { m7-phase2-mib 2 }
		linf		OBJECT IDENTIFIER ::= { m7-phase2-mib 3 }
		conn		OBJECT IDENTIFIER ::= { m7-phase2-mib 4 }
		perf		OBJECT IDENTIFIER ::= { m7-phase2-mib 5 }
		scale		OBJECT IDENTIFIER ::= { m7-phase2-mib 6 }
		card		OBJECT IDENTIFIER ::= { m7-phase2-mib 7 }
		clock		OBJECT IDENTIFIER ::= { m7-phase2-mib 8 }
		diag		OBJECT IDENTIFIER ::= { m7-phase2-mib 9 }
		pnni		OBJECT IDENTIFIER ::= { m7-phase2-mib 10 }
		matCmd		OBJECT IDENTIFIER ::= { m7-phase2-mib 11 }
--		bill		OBJECT IDENTIFIER ::= { m7-phase2-mib 100 }
--		user		OBJECT IDENTIFIER ::= { m7-phase2-mib 101 }
	m7-corporate-mib	OBJECT IDENTIFIER ::= { atomis-mib 12 }

--	The Node Group

nodeStatus	OBJECT IDENTIFIER ::= { node 1 }

nodeStatusOperStatus OBJECT-TYPE
	SYNTAX  INTEGER {
			down (1), 
			active (2), 
			installing(3)
		}
	ACCESS  read-only
	STATUS  mandatory
	DESCRIPTION
		"Indicate operational status of the equipment."
	--	
	::= { nodeStatus 1 }

nodeStatusStartTime OBJECT-TYPE
	SYNTAX	DateAndTime
	ACCESS	read-only
	STATUS	mandatory
	DESCRIPTION
		"Date and Time when the equipment was last restarted"
	--	
	::= { nodeStatus 2 }

nodeStatusNodeId OBJECT-TYPE
	SYNTAX  OCTET STRING
	ACCESS  read-only
	STATUS  mandatory
	DESCRIPTION
		"Node ID of the equipment"
	--	
	::= { nodeStatus 3 }

nodeStatusSelfSystem OBJECT-TYPE
	SYNTAX	INTEGER {
			system-0 (1), 
			system-1 (2)
		} 
	ACCESS	read-only
	STATUS	mandatory 
	DESCRIPTION 
		"Indicate which system of the SW-Engine the NMS is
		connected with."
	--
	::= { nodeStatus 4  }
  
nodeStatusSwitchType OBJECT-TYPE
	SYNTAX	INTEGER {
			sw-Engine-5G (1), 
			sw-Engine-10G (2)
		}
	ACCESS	read-only
	STATUS	mandatory 
	DESCRIPTION 
		"Indicate the type of SW-Engine."
	--
	::= { nodeStatus 5 } 
  
nodeStatusFan OBJECT-TYPE
	SYNTAX	INTEGER {
			normal (1), 
			failure (2)
		}
	ACCESS	read-only
	STATUS	mandatory
	DESCRIPTION
		"Indicate operational status of the FAN of the equipment."
	--
	::= { nodeStatus 6 }
  
nodeStatusEnvironment OBJECT-TYPE
	SYNTAX  INTEGER {
			good (1), 
			noGood (2)
		}
	ACCESS  read-only
	STATUS  mandatory
	DESCRIPTION
		"Peripheral temperature environment of the equipment.
		If the peripheral temperature exceeds 50 C,  this object
		enters noGood(2)."
	--
	--
	::= { nodeStatus 7 } 

nodeStatusTable OBJECT-TYPE
	SYNTAX	SEQUENCE OF NodeStatusEntry
	ACCESS	not-accessible
	STATUS	mandatory 
	DESCRIPTION	
		"Table which indicates the status of each part of the
		equipment."
	--
	::= { node 2 }
  
nodeStatusEntry OBJECT-TYPE
	SYNTAX	NodeStatusEntry
	ACCESS	not-accessible
	STATUS	mandatory
	DESCRIPTION 
		"Entry of the configuration of the table. "
	--
	INDEX	{ nodeStatusIndex }
	::= { nodeStatusTable 1 }
  
NodeStatusEntry ::=
	SEQUENCE { 
		nodeStatusIndex
			INTEGER,  
		nodeStatusPower 
			INTEGER,  
		nodeStatusSwitchMode
			INTEGER,  
		nodeStatusSwitch
			INTEGER 
	} 
  
nodeStatusIndex OBJECT-TYPE
	SYNTAX	INTEGER
	ACCESS	not-accessible
	STATUS	mandatory
	DESCRIPTION 
		"Index of the system configuration of the equipment "
	--
	::= { nodeStatusEntry 1 }	
	
nodeStatusPower OBJECT-TYPE	
	SYNTAX	INTEGER {   
			normal (1),  
			failure (2), 
			notInstalled (99)
		} 
	ACCESS  read-only 
	STATUS  mandatory	
	DESCRIPTION	
		"Indicate the status of the Power Unit of the equipment."
	--
	::= { nodeStatusEntry 2 }
   
nodeStatusSwitchMode OBJECT-TYPE
	SYNTAX  INTEGER {	
			act (1), 
			sby (2), 
			notInstalled (99)
		}	
	ACCESS  read-only 
	STATUS  mandatory 
	DESCRIPTION 
		"Indicate operational mode of SW-Engine of the equipment."
	--
	::= { nodeStatusEntry 3 }
   
nodeStatusSwitch OBJECT-TYPE
	SYNTAX  INTEGER {   
			normal (1),   
			failure (2), 
			diagnostics (3), 
			diagnosis-status-NG (4), 
			initializing (5), 
			notInstalled (99)
		}     
	ACCESS  read-only	
	STATUS  mandatory	
	DESCRIPTION		
		"Indicate the status of the SW-Engine of the equipment."
	--
	::= { nodeStatusEntry 4 }
	
nodePCMCIATable OBJECT-TYPE
	SYNTAX  SEQUENCE OF NodePCMCIAEntry
	ACCESS  not-accessible
	STATUS  mandatory
	DESCRIPTION
		"Table which indicates the status of the PCMCIA card.
		Every PCMCIA slot is provided with an entry."
	--
	--
	::= { node 3 }

nodePCMCIAEntry OBJECT-TYPE
	SYNTAX  NodePCMCIAEntry
	ACCESS  not-accessible
	STATUS  mandatory
	DESCRIPTION
		"Entry of nodePCMCIATable"
	--
	INDEX	{ nodeStatusIndex,  nodePCMCIAIndex }
	::= { nodePCMCIATable 1 }

NodePCMCIAEntry ::=
	SEQUENCE {
		nodePCMCIAIndex
			INTEGER, 
		nodePCMCIAStatus
			INTEGER, 
		nodePCMCIAType
			INTEGER
	}

nodePCMCIAIndex OBJECT-TYPE
	SYNTAX  INTEGER (1..2)
	ACCESS  not-accessible
	STATUS  mandatory
	DESCRIPTION
		"PCMCIA slot number per SW-Engine"
	--
	::= { nodePCMCIAEntry 1 }

nodePCMCIAStatus OBJECT-TYPE
	SYNTAX  INTEGER {
			normal (1), 
			failure (2), 
			initializing (3), 
			busy (4), 		-- Access in progress
			unknown (5), 
			notInstalled (99)
		}
	ACCESS  read-only
	STATUS  mandatory
	DESCRIPTION
		"Status of PCMCIA card"
	--
	::= { nodePCMCIAEntry 2 }

nodePCMCIAType OBJECT-TYPE
	SYNTAX  INTEGER {
			lan-card (1), 
			ata-card (2), 
			unknown (3), 
			notInstalled (99)
	}
	ACCESS  read-only
	STATUS  mandatory
	DESCRIPTION
		"Type of installed PCMCIA card"
	--
	::= { nodePCMCIAEntry 3 }

nodeOpe		OBJECT IDENTIFIER ::= { node 4 }

nodeOpeSave OBJECT-TYPE
	SYNTAX	INTEGER {
			noOperation(1), 	--	None
			save(2)		--	Save processing
		}
	ACCESS	read-write
	STATUS  mandatory
	DESCRIPTION
		"Save processing.
		Save System Configuration information in FROM.
		The result is indicated in nodeOpeSaveResult.
		The value at read is always noOperation (1)."
	--
	--
	--
	--
	::= { nodeOpe 1 }

nodeOpeSaveResult OBJECT-TYPE
	SYNTAX	INTEGER {			-- ACT/SBY
			succeed (1), 		-- OK/OK
			succeed-0 (2), 		-- OK/NG
			succeed-1 (3), 		-- NG/OK
			temporaryFailure (4), 	-- NG/NG
			nearend (5), 		-- OK(NearEND)/OK(NearEND)
			nearend-0 (6), 		-- OK(NearEND)/OK
			nearend-0-failure-1 (7), -- OK(NearEND)/NG
			nearend-1 (8), 		-- OK/OK(NearEND)
			nearend-1-failure-0 (9), -- NG/OK(NearEND)
			notReady (10), 		-- SAVE cannot be performed
			ready (11)		-- SAVE is in preparation
		} 
	ACCESS	read-only 
	STATUS	mandatory 
	DESCRIPTION 
		"The result of SAVE processing
		OK/NG indicate that SAVE processing completed/failed, 
		respectively.
		(NearEND) indicates that the number of write counts
		approaches to the limit."
	--
	--
	--
	--
	::= { nodeOpe 2 }

nodeOpeCopy OBJECT-TYPE 
	SYNTAX  INTEGER	{
			noOperation (1), 	-- None.
			copy-all-from-act (2), 	-- ACT->SBY
						-- Copy office data and LM.
			copy-all-from-sby (3), 	-- SBY->ACT
						-- Copy office data and LM.
			copy-config-from-act (4), -- ACT->SBY Copy office data.
			copy-config-from-sby (5), -- SBY->ACT Copy office data.
			copy-system-from-act (6), -- ACT->SBY Copy LM.
			copy-system-from-sby (7) -- SBY->ACT Copy LM.
		} 
	ACCESS	read-write 
	STATUS  mandatory 
	DESCRIPTION 
		"Copy the system configuration information/LM to the FROM
		of other system.
		The result is indicated in nodeOpeCopyResult.
		The value at read is always noOperation(1)."
	--
	--
	--
	::= { nodeOpe 3 } 
  
nodeOpeCopyResult OBJECT-TYPE
	SYNTAX	INTEGER { 
			succeed (1),  		-- COPY completed.
			temporaryFailure (2),  	-- COPY failed.
			nearend (3),  		-- The number of write counts
						-- into FROM at the copy
						-- destination approaches to
						-- the limit.
			notReady (4),  		-- COPY cannot be performed.
			ready (5) 		-- Copy is in preparation.
		} 
	ACCESS	read-only 
	STATUS  mandatory 
	DESCRIPTION 
		"Result of the copy processing."
	--
	::= { nodeOpe 4 }
    
nodeOpeReset OBJECT-TYPE 
	SYNTAX	INTEGER { 
			noOperation (1),  	-- None.
			reset-act (2), 		-- Restart ACT system SW-Engine.
			reset-sby (3), 		-- Restart SBY system SW-Engine.
			ach (4)			-- Switch ACT system.
		} 
	ACCESS	read-write 
	STATUS  mandatory 
	DESCRIPTION 
		"System Reset processing
		The value at read is always noOperation(1)."
	--
	--
	::= { nodeOpe 5 }

--	The Slot Group

slotIfConfTable OBJECT-TYPE
        SYNTAX  SEQUENCE OF SlotIfConfEntry
        ACCESS  not-accessible
        STATUS  mandatory
        DESCRIPTION
                "Table which indicates the line card configuration
		of the equipment"
	--
        ::= { slot 1 }

slotIfConfEntry OBJECT-TYPE
        SYNTAX  SlotIfConfEntry
        ACCESS  not-accessible
        STATUS  mandatory
        DESCRIPTION
                "Entry of the line card configuration"
	--
        INDEX   { slotIfConfIndex }
        ::= { slotIfConfTable 1 }

SlotIfConfEntry ::=
        SEQUENCE {
                slotIfConfIndex
                        INTEGER, 
                slotIfConfPhysType
                        INTEGER, 
                slotIfConfRev
                        DisplayString, 
                slotIfConfStatus
                        INTEGER, 
                slotIfConfBufferType
                        INTEGER, 
                slotIfConfBufferRev
                        DisplayString, 
		slotIfConfReset
			INTEGER, 
		slotIfConfResetResult
			INTEGER
        }

slotIfConfIndex OBJECT-TYPE
        SYNTAX  INTEGER (1..16)
        ACCESS  read-only
        STATUS  mandatory
        DESCRIPTION
                "Index of line card configuration"
	--
	::= { slotIfConfEntry 1 } 

slotIfConfPhysType OBJECT-TYPE
        SYNTAX  INTEGER {
                        other (1), 
                        taxi-100M (2), 
                        oc3c-SMF-Long (3), 
                        oc3c-SMF-Short (4), 
                        oc3c-MMF (5), 
                        relay-6Mcel (6), 
                        j2-6M-4M-3M (7), 
                        utp-5 (8), 
                        oc12c-SMF-Type-A (9), 
                        oc12c-SMF-Type-B (10), 
                        ds3 (11), 
                        e3 (12), 
                        bts-1 (13), 
                        bts-4 (14), 
			primary-1536K-1152K-768K-512K-384K-256K-192K (15), 
			ds1 (16), 
			e1 (17), 
			oc3c-POF (18), 
			sts3c-COAXIAL (19), 
                        vod-RxHFC4M (50), 
                        vod-TxHFC27M (51), 
			svr (52), 
			fr-ds1 (53), 
			fr-e1 (54), 
			dcs (55), 
			ce-ds3 (56), 
			ce-ds1 (57), 
			ce-e1 (58), 
			ce-J2 (59), 
			svr2 (60), 
			notInstalled (99)
                }
        ACCESS  read-only
        STATUS  mandatory
        DESCRIPTION
                "PMD layer/physical layer format of the line card.
		Above stated [oc3c],  [oc12c] are ATM Form conformed names.
		They are corresponding to the ITU-T conformed names as follows:
		oc3c - STM1
		oc12 - STM4
		sts3c - STM1"
	--
	--
	--
	--	oc3c - STM1
	--	oc12 - STM4
	--	sts3c - STM1
        ::= { slotIfConfEntry 2 }

slotIfConfRev OBJECT-TYPE
        SYNTAX  DisplayString
        ACCESS  read-only
        STATUS  mandatory
        DESCRIPTION
                "The revision of the line cards."
	--
	--
        ::= { slotIfConfEntry 3 }

slotIfConfStatus OBJECT-TYPE
        SYNTAX  INTEGER {
                        other (1), 
                        inService (2), 
                        outOfService (3), 
                        testing (4), 
                        initializing (5), 
                        installing (6), 
                        notInstalled (99)
                }
        ACCESS  read-only
        STATUS  mandatory
        DESCRIPTION
                "Operational status of the line cards."
	--
        ::= { slotIfConfEntry 4 }

slotIfConfBufferType OBJECT-TYPE
        SYNTAX  INTEGER {
			other (1), 
			ph1-buffer (2), 
			ph2-buffer (3), 
			fr-buffer (4), 
			fr-buffer2 (5), 
			notInstalled (99)
                }
        ACCESS  read-only
        STATUS  mandatory
        DESCRIPTION
                "The Buffer ID of the line cards."
	--
        ::= { slotIfConfEntry 5 }

slotIfConfBufferRev OBJECT-TYPE
        SYNTAX  DisplayString
        ACCESS  read-only
        STATUS  mandatory
        DESCRIPTION
                "The revision of the line card's buffers."
	--
	--
        ::= { slotIfConfEntry 6 }

slotIfConfReset OBJECT-TYPE
	SYNTAX  INTEGER {
			noOperation(1), 	-- None
			reset(2), 	-- Reset order
			notInstalled(99)
		}
	ACCESS  read-write
	STATUS  mandatory
	DESCRIPTION
		"Line card reset.
		The result of the reset order is indicated in
		slotIfConfResetResult."
	--
	--
	--
	::= { slotIfConfEntry 7 }

slotIfConfResetResult OBJECT-TYPE
	SYNTAX  INTEGER {
			succeed(1), 	-- Normal end (initial value).
			other(2), 	-- NG other than below stated values.
			diagnostics (3), 	-- Diagnostic test in progress. 
			unchangeableSlaveLine (4), 	-- Slave line cannot
							-- be switched.
			notInstalled(99)
		}
	ACCESS  read-only
	STATUS  mandatory
	DESCRIPTION
		"The current result of the reset order by slotIfConfReset."
	--
	::= { slotIfConfEntry 8 }

--	The Linf Group

LinfFilterMaskVpi	::= INTEGER (-1|0..12)
	--	Filter mask VPI.
	--
	--

LinfFilterMaskVci	::= INTEGER (-1|0..14)
	--	Filter mask VCI.
	--
	--

LinfCellMappingMode	::= INTEGER { direct(1),  plcp(2) }
	--	Cell mapping mode.

LinfScramble		::= INTEGER { on(1),  off(2) }
	--	Scramble.

LinfLBO			::= INTEGER {
					low(1), 
					hi(2), 
					length-0-110(3), 
					length-110-220(4), 
					length-220-330(5), 
					length-330-440(6), 
					length-440-550(7), 
					length-550-660(8), 
					length-over660(9)
				}
	--	Line Build Out.

LinfFrameMode		::= INTEGER {
					c-bit(1), 
					m23(2), 
					g832-g804(3), 
					g751(4), 
					m13(5), 
					esf(6), 
					sf(7)
				}
	--	Frame mode.

LinfMinVci		::= INTEGER (0..16383)
	--
	--

LinfMaxVci		::= INTEGER (0..16383)
	--
	--

LinfService		::= INTEGER { unstructured(1),  structured(2) }
	--	Service.

LinfInterWorking	::= INTEGER { network(1),  service(2) }
	--	Type of Interworking.

LinfVendor		::= INTEGER {
					notApplicable(1), 
					stratacom(2), 
					digital-equipment(3), 
					northan-telecom(4), 
					cisco-systems(5)
				}
	--
	--
	--
	--

LinfFractionalType	::= INTEGER { unstructured(1),  fractional(2) }
	--	Fractional type.
	--
	--

LinfFractionalSet	::= INTEGER
	--
	--
	--
	--
	--
	--
	--

LinfCasMode		::= INTEGER { notApplicable(1),  basic(2),  cas(3) }
	--	This parameter selects which AAL1 Format shoud be used.
	--	Basic dose not carry CAS bits,  and use a single 125 usec frame.
	--	cas(3) carry CAS bits in a multiframe structure for E1, 
	--	DS1 SF and DS1 ESF respoectively.
	--	This applies to structured interface only.
	--	Default is basic(2).
	--
	--
	--

LinfCodingMode		::= INTEGER { hdb3(1),  ami(2) }
	--
	--

LinfUnUsedParam	::= INTEGER { unused(-1) }
	--	Unused parameter.
	--

	--
	--
	--

	--
	--
	--
	--
	--
	--
	--
	--

	--
	--
	--
	--
	--
	--
	--
	--

	--
	--
	--
	--
	--
	--
	--
	--

	--
	--
	--
	--
	--
	--
	--
	--

	--
	--
	--
	--
	--
	--
	--
	--

linfStatusTable OBJECT-TYPE
	SYNTAX	SEQUENCE OF LinfStatusEntry
	ACCESS	not-accessible
	STATUS	mandatory
	DESCRIPTION
		"Table related to the ATM specific lines which could not be
		defined by MIB-II.
		The table includes the configuration information, 
		operational status and error types of lines."
	--
	--
	::= { linf 1 }

linfStatusEntry OBJECT-TYPE
	SYNTAX	LinfStatusEntry
	ACCESS	not-accessible
	STATUS	mandatory
	DESCRIPTION
		"Entry of the line interface status indication."
	--
	INDEX	{ linfIndex }
	::= { linfStatusTable 1 }

LinfStatusEntry ::=
	SEQUENCE {
		linfIndex
			INTEGER , 
		linfStatus
			INTEGER, 
		linfLoopBack
			INTEGER, 
		linfConf
			INTEGER, 
		linfFwdAvailableBandWidth
			INTEGER, 
		linfBkwdAvailableBandWidth
			INTEGER, 
                linfJ2Rate
                        INTEGER, 
                linfCacFactor
                        INTEGER, 
                linfLoopBackCause
                        INTEGER, 
		linfBandWidth
                        INTEGER, 
		linfRecommendation
			INTEGER, 
		linfUnassignedIdle
			INTEGER, 
		linfMaxActiveVpiBits
			INTEGER, 
		linfMaxActiveVciBits
			INTEGER, 
		linfPhysType
			INTEGER, 
		linfParam1
			INTEGER, 
		linfParam2
			INTEGER, 
		linfParam3
			INTEGER, 
		linfParam4
			INTEGER, 
		linfParam5
			INTEGER, 
		linfParam6
			INTEGER, 
		linfParam7
			INTEGER
	}

linfIndex OBJECT-TYPE
	SYNTAX	INTEGER(1..64)
	ACCESS	read-only
	STATUS	mandatory
	DESCRIPTION
		"Index of the line interface status indication"
	--
	::= { linfStatusEntry 1 }
		
linfStatus OBJECT-TYPE
	SYNTAX	INTEGER {
			normal (1), 
			los (2), 
			lof (3), 
			loc (4), 
			ais-path (5), 
			ais-section (6), 
			yellow-section (7), 
			yellow-path (8), 
			lop (9), 
			ais (10), 
			payload-all-one (11), 
			rai (12), 
			oof (13) , 
			idle (14), 
			rdi (15), 
			plcp-oof (16), 
			plcp-lof (17), 
			plcp-yellow (18), 
			red(19), 
			loss-of-64K-clock(80), 
			loss-of-8K-clock(81), 
			frequency-out-of-range(82), 
			failure(97), 
			administratively-down (98), 
			notInstalled (99)
		}
	ACCESS	read-only
	STATUS	mandatory
	DESCRIPTION
		"Status of the line interface or the receive clock"
	--
	::= { linfStatusEntry 2 }

linfLoopBack OBJECT-TYPE
	SYNTAX	INTEGER {
			others (1), 	-- not used
			normal (2), 
			localLoopBack (3), 
			remoteLoopBack (4), 
			notInstalled (99)
		}
	ACCESS	read-write
	STATUS	mandatory
	DESCRIPTION
		"Loop back status"
	--
	::= { linfStatusEntry 3 }

linfConf OBJECT-TYPE
	SYNTAX	INTEGER {
			others (1), 
			private-UNI (2), 
			private-NNI (3), 
			public-UNI  (4), 
--			gate-NNI    (5), 
--		Only interface customized version is used.
--		Line interface type Add gate_NNI so that SW would be
--		considered as Gateway in the customized configuration.
--
--
			uni	    (6), 
			nni	    (7), 
			notInstalled (99)
		}
	ACCESS	read-only
	STATUS	mandatory
	DESCRIPTION
		"Line card type."
	--
	::= {  linfStatusEntry  4 }

linfFwdAvailableBandWidth OBJECT-TYPE
	SYNTAX	INTEGER
	ACCESS	read-only
	STATUS	mandatory
	DESCRIPTION
		"Forward Available BandWidth(Mbps)."
	--
	--
	::= {  linfStatusEntry  5 }

linfBkwdAvailableBandWidth OBJECT-TYPE
	SYNTAX	INTEGER
	ACCESS	read-only
	STATUS	mandatory
	DESCRIPTION
		"Backward Available BandWidth(Mbps)."
	--
	--
	::= {  linfStatusEntry  6 }

linfJ2Rate OBJECT-TYPE
	SYNTAX	INTEGER {
			not-leased-line (1), 
			type-3-Mbps (2), 
			type-4point5-Mbps (3), 
			type-6point3-Mbps (4), 
			notInstalled (99)
		}
	ACCESS	not-accessible
	STATUS	mandatory
	DESCRIPTION
		"Indicate the line rate of the J2-dedicated line service."
	--
	::= { linfStatusEntry  7 }

linfCacFactor OBJECT-TYPE
	SYNTAX  INTEGER(0|10..1000)
	ACCESS  read-write
	STATUS  mandatory
	DESCRIPTION
		""
	--
	--
	--
	--
	--
	--
	--
	::= { linfStatusEntry 8 }

linfLoopBackCause OBJECT-TYPE
	SYNTAX  INTEGER {
			succeed (1), 
			diagnosis (2),           -- Diagnostic test in progress.
			failure (3),             --
			notSupportedByPkg (4),   --
			alreadyRegistered (5),   --
			adminDown (6),           -- admin down
			initializing (7),         --
			notInstalled (99)
		}
	ACCESS  read-only
	STATUS  mandatory
	DESCRIPTION
		""
	--
	::= { linfStatusEntry 9 }

linfBandWidth OBJECT-TYPE
	SYNTAX	INTEGER
	ACCESS	read-only
	STATUS	mandatory
	DESCRIPTION
		""
	--
	::= {  linfStatusEntry  10 }

linfRecommendation	OBJECT-TYPE
	SYNTAX	INTEGER {
			other (1), 
			atmForum (2), 
			itu (3), 
			ttc (4), 
			frameRelayForum (5), 
			itu-t (6), 
			ansi (7), 
			fourVendor (8), 
			notInstalled (99)
		}
	ACCESS	read-only
	STATUS	mandatory
	DESCRIPTION
	 	""
	 --
	::= { linfStatusEntry 11 }

linfUnassignedIdle	OBJECT-TYPE
	SYNTAX	INTEGER {
			notApplicable (1), 
			unAssigned (2), 
			idle (3), 
			notInstalled (99)
		}
	ACCESS	read-only
	STATUS	mandatory
	DESCRIPTION 	
		"Unassigned/Idle"
	::= { linfStatusEntry 12 }

linfMaxActiveVpiBits	OBJECT-TYPE
	SYNTAX	INTEGER (0..12)
	ACCESS	read-only
	STATUS	mandatory
	DESCRIPTION
	 	"The length of valid VPI bits."
	--
	::= { linfStatusEntry 13 }

linfMaxActiveVciBits	OBJECT-TYPE
	SYNTAX	INTEGER (0..14)
	ACCESS	read-only
	STATUS	mandatory
	DESCRIPTION 
	 	"The length of valid VCI bits."
	--
	::= { linfStatusEntry 14 }

linfPhysType	OBJECT-TYPE
	SYNTAX	INTEGER
	ACCESS	read-only
	STATUS	mandatory
	DESCRIPTION 
		""
	--
	::= { linfStatusEntry 15 }

linfParam1		OBJECT-TYPE
	SYNTAX	INTEGER
	ACCESS	read-only
	STATUS	mandatory
	DESCRIPTION
		""
	--
	--
	::= { linfStatusEntry 16 }

linfParam2		OBJECT-TYPE
	SYNTAX	INTEGER
	ACCESS	read-only
	STATUS	mandatory
	DESCRIPTION
		""
	--
	--
	::= { linfStatusEntry 17 }

linfParam3		OBJECT-TYPE
	SYNTAX	INTEGER
	ACCESS	read-only
	STATUS	mandatory
	DESCRIPTION
		""
	--
	--
	::= { linfStatusEntry 18 }

linfParam4		OBJECT-TYPE
	SYNTAX	INTEGER
	ACCESS	read-only
	STATUS	mandatory
	DESCRIPTION
		""
	--
	--
	::= { linfStatusEntry 19 }

linfParam5		OBJECT-TYPE
	SYNTAX	INTEGER
	ACCESS	read-only
	STATUS	mandatory
	DESCRIPTION
		""
	--
	--
	::= { linfStatusEntry 20 }

linfParam6		OBJECT-TYPE
	SYNTAX	INTEGER
	ACCESS	read-only
	STATUS	mandatory
	DESCRIPTION
		""
	--
	--
	::= { linfStatusEntry 21 }

linfParam7		OBJECT-TYPE
	SYNTAX	INTEGER
	ACCESS	read-only
	STATUS	mandatory
	DESCRIPTION
		""
	--
	--
	::= { linfStatusEntry 22 }

linfFifoConfTable OBJECT-TYPE
        SYNTAX  SEQUENCE OF LinfFifoConfEntry
        ACCESS  not-accessible
        STATUS  mandatory
        DESCRIPTION
                "Indicate status of FIFO on the shaper-line card.
 	         	* 
                              
                  	* Relationship between PCR,  SCR and MBS value.
				PCR >= SCR
				PCR >= MBS "
	--
	--
	--
	--
	--
	--
	--
	--
	--
        ::= { linf 2 }

linfFifoConfEntry OBJECT-TYPE
        SYNTAX  LinfFifoConfEntry
        ACCESS  not-accessible
        STATUS  mandatory
        DESCRIPTION
                "Entry of FIFO status indication "
	--
        INDEX   { linfFifoConfifIndex ,  linfFifoConfIndex }
        ::= { linfFifoConfTable 1 }

LinfFifoConfEntry ::=
        SEQUENCE {
                linfFifoConfifIndex
                        INTEGER , 
                linfFifoConfIndex
                        INTEGER , 
                linfFifoConfStatus
                        INTEGER, 
                linfFifoConfPeekRate
                        INTEGER, 
                linfFifoConfSustainRate
                        INTEGER, 
                linfFifoConfMaxBurstSize
                        INTEGER, 
		linfFifoConfRowStatus
			INTEGER
        }

linfFifoConfifIndex OBJECT-TYPE
        SYNTAX  INTEGER
        ACCESS  not-accessible
        STATUS  mandatory
        DESCRIPTION
                " Line Interface Index "
	--
        ::= { linfFifoConfEntry 1 }

linfFifoConfIndex OBJECT-TYPE
        SYNTAX  INTEGER
        ACCESS  not-accessible
        STATUS  mandatory
        DESCRIPTION
                " Index of FIFO "
	--
        ::= { linfFifoConfEntry 2 }

linfFifoConfStatus OBJECT-TYPE
        SYNTAX  INTEGER {
                        normal (1), 
                        overflow (2)
                }
        ACCESS  not-accessible
        STATUS  mandatory
        DESCRIPTION
                " Status of FIFO "
	--
        ::= { linfFifoConfEntry 3 }

linfFifoConfPeekRate OBJECT-TYPE
        SYNTAX  INTEGER (1..1412830)
        ACCESS  not-accessible
        STATUS  mandatory
        DESCRIPTION
                "Peak Cell rate (PCR) for shaper-line card."
	--
        ::= { linfFifoConfEntry 4 }

linfFifoConfSustainRate OBJECT-TYPE
        SYNTAX  INTEGER (1..1412830)
        ACCESS  not-accessible
        STATUS  mandatory
        DESCRIPTION
              " Sustainable Cell Rate ( SCR)  for shaper-line card."
	--
        ::= { linfFifoConfEntry 5 }

linfFifoConfMaxBurstSize OBJECT-TYPE
        SYNTAX  INTEGER (1..1412830)
        ACCESS  not-accessible
        STATUS  mandatory
        DESCRIPTION
              "Maximum Burst Size (MBS) for the shaper-line card."
	--
        ::= { linfFifoConfEntry 6 }

linfFifoConfRowStatus OBJECT-TYPE
        SYNTAX  INTEGER {
                        active(1), 
                        notInService(2), 
                        notReady(3), 
                        createAndGo(4),          -- notSupported
                        createAndWait(5), 
                        destroy(6)
                }
        ACCESS  not-accessible
        STATUS  mandatory
        DESCRIPTION
            " This object is used to designate the setting method for 
		the shaping rate from the manager.
		Also,  this object returns the reply to the shaping rate 
		setting request from the agent side.

                           - 'active',  which indicates that the
                           conceptual row is available for use by the
                           managed device;

                           - 'notInService',  which indicates that the
                           conceptual row exists in the agent,  but is
                           unavailable for use by the managed device;

                           - 'notReady',  which indicates that the
                           conceptual row exists in the agent,  but is
                           missing information necessary in order to be
                           available for use by the managed device;

                           - 'createAndGo',  which is supplied by a
                           management station wishing to create a new
                           instance of a conceptual row and to have it
                           available for use by the managed device;

                           - 'createAndWait',  which is supplied by a
                           management station wishing to create a new
                           instance of a conceptual row but not to have
                           it available for use by the managed device;
                           and, 

                           - 'destroy',  which is supplied by a
                           management station wishing to delete all of
                           the instances associated with an existing
                           conceptual row.
			"
	--
	--
	--
        ::= { linfFifoConfEntry 7 }

--	The Conn (Connection & Traffic for accounting) Group

--	connPvc			OBJECT IDENTIFIER ::= { conn  1 }
--	connConf		OBJECT IDENTIFIER ::= { conn  2 }
--	connRoute		OBJECT IDENTIFIER ::= { conn  3 }
--	connSoftPvcIndexNext	OBJECT IDENTIFIER ::= { conn  4 }
--	connSoftPvcTable	OBJECT IDENTIFIER ::= { conn  5 }
--	connSoftPvcEstablishedSrcInfTable
--				OBJECT IDENTIFIER ::= { conn  6 }
--	connOam			OBJECT IDENTIFIER ::= { conn  7 }
--	connLoop		OBJECT IDENTIFIER ::= { conn  8 }
--	connProfile		OBJECT IDENTIFIER ::= { conn  9 }
--	connSvcTable		OBJECT IDENTIFIER ::= { conn 10 }
--	connCe			OBJECT IDENTIFIER ::= { conn 11 }
--	connFr			OBJECT IDENTIFIER ::= { conn 12 }


connPvc		OBJECT IDENTIFIER ::= { conn 1 }

connPvcOpe	OBJECT IDENTIFIER ::= { connPvc 1 }

	--
	--
	--
	--
	--
	--

connPvcOpeLowPort	OBJECT-TYPE
	SYNTAX	INTEGER (1..65|-1)	--
	ACCESS	read-write
	STATUS	mandatory
	DESCRIPTION
		"Low-side line port number. "
	--
	::= { connPvcOpe 1 }

connPvcOpeLowVpi	OBJECT-TYPE
	SYNTAX	INTEGER (0..16383|-1)	-- default value is -1.
	ACCESS	read-write
	STATUS	mandatory
	DESCRIPTION
		" Low-side VPI number."
	--
	::= { connPvcOpe 2 }

connPvcOpeLowVci	OBJECT-TYPE
	SYNTAX	INTEGER (0..16383|-1)	--
	ACCESS	read-write
	STATUS	mandatory
	DESCRIPTION
		" Low-side VCI number."
	--
	::= { connPvcOpe 3 }

connPvcOpeHighPort	OBJECT-TYPE
	SYNTAX	INTEGER (1..65|-1)	-- default value is -1.
	ACCESS	read-write
	STATUS	mandatory
	DESCRIPTION
		" High-side line port number."
	--
	::= { connPvcOpe 4 }

connPvcOpeHighVpi	OBJECT-TYPE
	SYNTAX	INTEGER (0..16383|-1)	-- default value is -1.
	ACCESS	read-write
	STATUS	mandatory
	DESCRIPTION
		" High-side VPI number."
	--
	::= { connPvcOpe 5 }

connPvcOpeHighVci	OBJECT-TYPE
	SYNTAX	INTEGER (0..16383|-1)	-- default value is -1.
	ACCESS	read-write
	STATUS	mandatory
	DESCRIPTION
		" High-side VCI number."
	--
	::= { connPvcOpe 6 }

connPvcOpeTopology	OBJECT-TYPE
	SYNTAX	INTEGER {
			uni-directional-VCC (1), 	-- default value
			bi-directional-VCC  (2), 
			uni-directional-VPC (3), 
			bi-directional-VPC  (4), 
			broadcast-VPC       (5), 
			broadcast-VCC       (6)
		}
	ACCESS  read-write
	STATUS  mandatory
	DESCRIPTION
		"Topology of the Connection."
	--
	::= { connPvcOpe 7 }

connPvcOpeTrafficType OBJECT-TYPE
	SYNTAX  INTEGER {
		traffic-CBR (1), 
		traffic-rt-VBR (2), 
		traffic-nrt-VBR (3), 
		traffic-ABR (4), 
		traffic-UBR (5)		-- default value
	}
	ACCESS  read-write
	STATUS  mandatory
	DESCRIPTION
		"Traffic Type."
	--
	::= { connPvcOpe 8 }

connPvcOpeStatus OBJECT-TYPE
	SYNTAX	INTEGER {
			allocate(1), 	--
					--
			establish(2), 	-- JpnToEng[point-to-point, 
					--
			add(3), 		--
					--
			delete(4), 	--
					--
			remove(5), 	--
					--
			free(6)		--
					--
					-- default value

		}
	ACCESS	read-write
	STATUS	mandatory
	DESCRIPTION
		""
	--
	::= { connPvcOpe 9 }

connPvcOpeCause OBJECT-TYPE
	SYNTAX	INTEGER {
			rowExisting(1), 		-- default value
			allocateSucceed(2), 
			vpivciLowBusy(3), 
			vpivciHighBusy(4), 
			vpivciOutOfRange(5), 
			rateLowOverFlow(6), 
			rateHighOverFlow(7), 
			broadcastTableFull(8), 
			inconsistentVPVC(9), 
			lineDiagnosis(10), 
			missMatchTrfType(11), 
			illegalLowFileName(12), 
			illegalHighFileName(13), 
			illegalLowShaper(14), 
			illegalHighShaper(15), 
			illegalOperation(16), 
			parameterIsNotEnough(17), 
			diagnostics(18), 
			otherFailure(19), 
 			illegalLowRateForUPC(20), 
 			illegalHighRateForUPC(21), 
			noSpecifiedConnection(22), 
			noCevc(23), 
			noDlci(24), 
			illegalTopology(25), 
			noLowShaperForGateway(26), 
			noHighShaperForGateway(27), 
			noPvcLowShaperForGateway(28), 
			noPvcHighShaperForGateway(29), 
			missMatchTrfTypeLowShaperForGateway(30), 
			missMatchTrfTypeHighShaperForGateway(31), 
			leafSetAnotherLine(32), 
			insusfficientPCRofProfile(33)
		}
	ACCESS	read-only
	STATUS	mandatory
	DESCRIPTION
		"The result of the connection operation."
	--
	::= { connPvcOpe 10 }

connPvcOpeLowFifoIndex		OBJECT-TYPE
	SYNTAX	INTEGER (0..16)		-- default value is 0.
	ACCESS	read-write
	STATUS	mandatory
	DESCRIPTION
		"Shaper number of Forward.
		If shaping is not performed,  designate 0."
	--
	--
        ::= { connPvcOpe 11 }

connPvcOpeHighFifoIndex		OBJECT-TYPE
	SYNTAX	INTEGER (0..16)		-- default value is 0.
	ACCESS	read-write
	STATUS	mandatory
	DESCRIPTION
		"Shaper number of Backward.
		If shaping is not performed,  designate 0."
	--
	--
        ::= { connPvcOpe 12 }

connPvcOpeLowParam1	OBJECT-TYPE
	SYNTAX	INTEGER {
			off(1), 		-- default value
			mode1(2), 
			mode2(3), 
			mode3(4), 
			mode4(5), 
			mode5(6)
	}
	ACCESS	read-write
	STATUS	mandatory
	DESCRIPTION
		"UPC mode of Forward."
	--
	::= { connPvcOpe 13 }

connPvcOpeHighParam1	OBJECT-TYPE
	SYNTAX	INTEGER {
			off(1), 		-- default value
			mode1(2), 
			mode2(3), 
			mode3(4), 
			mode4(5), 
			mode5(6)
	}
	ACCESS	read-write
	STATUS	mandatory
	DESCRIPTION
		"UPC mode of Backward."
	--
	::= { connPvcOpe 14 }

--
--
--
--
--
--
--
--
--
--
--
--
--
--
--

connPvcOpeLowParam2	OBJECT-TYPE
	SYNTAX	DisplayString (SIZE(1..10|0))	-- default value is size(0).
	ACCESS	read-write
	STATUS	mandatory
	DESCRIPTION
		"Profile name of Forward.
		If nothing is designated,  the string of size(0) is designated."
	--
	--
	::= { connPvcOpe 15 }

connPvcOpeHighParam2	OBJECT-TYPE
	SYNTAX	DisplayString (SIZE(1..10|0))	-- default value is size(0).
	ACCESS	read-write
	STATUS	mandatory
	DESCRIPTION
		"Profile name of Backward.
		If nothing is designated,  the string of size(0) is designated."
	--
	--
	::= { connPvcOpe 16 }

connPvcTable	OBJECT-TYPE
	SYNTAX	SEQUENCE OF ConnPvcEntry
	ACCESS	not-accessible
	STATUS	mandatory
	DESCRIPTION
		""
	--
	--
	--
	--
	::= { connPvc 2 }

connPvcEntry	OBJECT-TYPE
	SYNTAX	ConnPvcEntry
	ACCESS	not-accessible	
	STATUS	mandatory
	DESCRIPTION
		"Entry of connPvcTable.
		e.g.
		receive +----------------------------------+transmit
		=======>|   ---- uni-directional-VCC ----  |=======>
		(1/0/32)|                                  |(2/0/32)
		=======>|   ---- bi-directional-VCC  ----  |=======>
		(1/0/33)|                                  |(2/0/33)
		=======>|   ---- broadcast - VCC ---+----  |=======>
		(1/0/34)|                           |      |(2/0/34)
		        |                           +----  |=======>
		        |                                  |(3/0/34)
		        +----------------------------------+
		                                            (line/vpi/vci)
		 connPvcContrastPort.1.0.32.1.1=2
		 connPvcContrastPort.2.0.32.2.1=1
		 connPvcContrastPort.1.0.33.3.1=2
		 connPvcContrastPort.2.0.33.3.1=1
		 connPvcContrastPort.1.0.34.5.1=2
		 connPvcContrastPort.1.0.34.5.2=3
		 connPvcContrastPort.2.0.34.4.1=1
		 connPvcContrastPort.3.0.34.4.1=1"
	INDEX{ connPvcPort,  connPvcVpi,  connPvcVci,  connPvcDirection,  connPvcIndex }
	::=	{ connPvcTable 1 }

ConnPvcEntry ::=
	SEQUENCE	{
		connPvcPort
			INTEGER, 
		connPvcVpi
			INTEGER, 
		connPvcVci
			INTEGER, 
		connPvcDirection
			INTEGER, 
		connPvcIndex
			INTEGER, 
		connPvcContrastPort
			INTEGER, 
		connPvcContrastVpi
			INTEGER, 
		connPvcContrastVci
			INTEGER, 
		connPvcTopology
			INTEGER, 
		connPvcTrafficType
			INTEGER, 
		connPvcFifoIndex
			INTEGER, 
		connPvcContrastFifoIndex
			INTEGER, 
		connPvcTrfConf
			INTEGER, 
		connPvcTrfResult
			INTEGER, 
		connPvcParam1
			INTEGER, 
		connPvcContrastParam1
			INTEGER, 
		connPvcParam2
			DisplayString, 
		connPvcContrastParam2
			DisplayString, 
		connPvcParam3
			INTEGER, 
		connPvcContrastParam3
			INTEGER, 
		connPvcParam4
			INTEGER, 
		connPvcContrastParam4
			INTEGER, 
		connPvcParam5
			INTEGER, 
		connPvcContrastParam5
			INTEGER, 
		connPvcParam6
			INTEGER, 
		connPvcContrastParam6
			INTEGER, 
		connPvcParam7
			INTEGER, 
		connPvcContrastParam7
			INTEGER
	}

connPvcPort	OBJECT-TYPE
	SYNTAX	INTEGER
	ACCESS	not-accessible
	STATUS	mandatory
	DESCRIPTION
		"Line port number"
	--
	::= { connPvcEntry 1 }

connPvcVpi	OBJECT-TYPE
	SYNTAX	INTEGER
	ACCESS	not-accessible
	STATUS	mandatory
	DESCRIPTION
		"VPI number"
	--
	::= { connPvcEntry 2 }

connPvcVci	OBJECT-TYPE
	SYNTAX	INTEGER
	ACCESS	not-accessible
	STATUS	mandatory
	DESCRIPTION
		"VCI number"
	--
	::= { connPvcEntry 3 }

connPvcDirection	OBJECT-TYPE
	SYNTAX	INTEGER {
			in(1), 		-- On the low side of UNI/Gateway.
			out(2), 		-- On the high side of UNI/Gateway.
			in-out(3), 	-- Bi.
			multi-out(4), 	-- On the high side of multicast.
			multi-in(5)	-- On the low side of multicast.
	}
	ACCESS  not-accessible
	STATUS  mandatory
	DESCRIPTION
		"Indicate cell flow."
	--
	::= { connPvcEntry 4 }

connPvcIndex	OBJECT-TYPE
	SYNTAX	INTEGER
	ACCESS	not-accessible
	STATUS	mandatory
	DESCRIPTION
		""
	--
	::= { connPvcEntry 5 }

connPvcContrastPort	OBJECT-TYPE
	SYNTAX	INTEGER
	ACCESS	read-only
	STATUS	mandatory
	DESCRIPTION
		""
	--
	::= { connPvcEntry 6 }

connPvcContrastVpi	OBJECT-TYPE
	SYNTAX	INTEGER
	ACCESS	read-only
	STATUS	mandatory
	DESCRIPTION
		""
	--
	::= { connPvcEntry 7 }

connPvcContrastVci	OBJECT-TYPE
	SYNTAX	INTEGER
	ACCESS	read-only
	STATUS	mandatory
	DESCRIPTION
		""
	--
	::= { connPvcEntry 8 }

connPvcTopology	OBJECT-TYPE
	SYNTAX	INTEGER {
			uni-directional-VCC (1), 
			bi-directional-VCC  (2), 
			uni-directional-VPC (3), 
			bi-directional-VPC  (4), 
			broadcast-VPC       (5), 
			broadcast-VCC       (6), 
			gateway             (7)
		}
	ACCESS  read-only
	STATUS  mandatory
	DESCRIPTION
		"Topology of the Connection."
	--
	::= { connPvcEntry 9 }

connPvcTrafficType	OBJECT-TYPE
	SYNTAX	INTEGER {
				traffic-CBR (1), 
				traffic-rt-VBR (2), 
				traffic-nrt-VBR (3), 
				traffic-ABR (4), 
				traffic-UBR (5)
	}
	ACCESS  read-only
	STATUS  mandatory
	DESCRIPTION
		"Traffic Type."
	--
	::= { connPvcEntry 10 }

connPvcFifoIndex	OBJECT-TYPE
	SYNTAX	INTEGER (0..16)
	ACCESS	read-only
	STATUS	mandatory
	DESCRIPTION
		"The Shaper numbers of the direction from this endpoint to
		the endpoint to be switched.
		Value 0 means that Shaping will not be performed."
	--
	--
	--
	::= { connPvcEntry 11 }

connPvcContrastFifoIndex	OBJECT-TYPE
	SYNTAX	INTEGER (0..16)
	ACCESS	read-only
	STATUS	mandatory
	DESCRIPTION
		"The Shaper number of the direction from the endpoint to
		be switched to this end point.
		Value 0 means that Shaping will not be performed."
	--
	--
	--
	::= { connPvcEntry 12 }

connPvcTrfConf OBJECT-TYPE
	SYNTAX  INTEGER {
			entry(1), 
			remove(2)
		}
	ACCESS  read-write
	STATUS  mandatory
	DESCRIPTION
		" Indicate Traffic control/status.
		 If a path does not exist,  noSuchName.
		 1. Indicate Traffic status
		    1) entry...registered
 		    2) remove...not registered(initial status)	
	 	 2. Register Traffic
		    1) Set connPvcTrfConf to 'entry',  to perform the
			registration process.
		    2) Then,  get connPvcTrfResult. For normal end,  
		       it contains entrySucceed,  for abnormal end, 
		       it contains other value.
		 3. Delete Traffic
		    1) Set connPvcTrfConf to 'remove',  to perform the
			deletion process.
		    2) Then,  get connPvTrfResult.  For normal end,  it 
			contains entrySucceed,  for abnormal end,  it contains 
			other value. "
	--
	--
	--
	--
	--
	--
	--
	--
	--
	--
	--
	--
	--
	--
	--
	::= { connPvcEntry 13 }

connPvcTrfResult OBJECT-TYPE
	SYNTAX  INTEGER {
			other(1), 
			entrySucceed(2), 	-- entry
			alreadyEntry(3), 	-- entry
			tableOverflow(4), 	-- entry
			removeSucceed(5), 	-- remove
			notEntry(6) 		-- remove
		}
	ACCESS  read-only
	STATUS  mandatory
	DESCRIPTION
		"Indicate the processing result after Traffic control.
		 If the path does not exist,  noSuchName.
		 The result of the registration
			EntrySucceed  (2) --- Normal end of the registration
			AlreadyEntry  (3) --- Double registration
			tableOverflow (4) --- The number of registration is
					      over the limit.
		The result of the deletion
			RemoveSucceed (5) --- Normal end of the deletion
			notEntry      (6) --- Non-registration
		Normally,  other (1) is indicated.  It is the current status 
		just after the traffic control.  Once,  the traffic control 
		is got,  then it returns to other (1). "
	--
	--
	--
	--
	--
	--
	--
	--
	--
	--
	--
	::= { connPvcEntry 14 }

connPvcParam1	OBJECT-TYPE
	SYNTAX	INTEGER {
			off(1), 
			mode1(2), 
			mode2(3), 
			mode3(4), 
			mode4(5), 
			mode5(6)
	}
	ACCESS	read-only
	STATUS	mandatory
	DESCRIPTION
		"UPC mode of the direction from this endpoint to
		the endpoint to be switched.
		If nothing is designated,  or the designation is invalid, 
		off (1) is indicated."
	--
	--
	--
	::= { connPvcEntry 15 }

connPvcContrastParam1	OBJECT-TYPE
	SYNTAX	INTEGER {
			off(1), 
			mode1(2), 
			mode2(3), 
			mode3(4), 
			mode4(5), 
			mode5(6)
	}
	ACCESS	read-only
	STATUS	mandatory
	DESCRIPTION
		"UPC mode of the direction from the endpoint to
		be switched to this end point.
		If nothing is designated,  or the designation is invalid, 
		off (1) is indicated."
	--
	--
	--
	::= { connPvcEntry 16 }

connPvcParam2	OBJECT-TYPE
	SYNTAX	DisplayString (SIZE(1..10|0))
	ACCESS	read-only
	STATUS	mandatory
	DESCRIPTION
		"Profile name of the direction from this endpoint to
		the endpoint to be switched.
		If nothing is designated,  or the designation is invalid, 
		the string of size(0) is indicated."
	--
	--
	--
	--
	::= { connPvcEntry 17 }

connPvcContrastParam2	OBJECT-TYPE
	SYNTAX	DisplayString (SIZE(1..10|0))
	ACCESS	read-only
	STATUS	mandatory
	DESCRIPTION
		"Profile name of the direction from the endpoint to
		be switched to this end point.
		If nothing is designated,  or the designation is invalid, 
		the string of size(0) is indicated."
	--
	--
	--
	--
	::= { connPvcEntry 18 }

connPvcParam3	OBJECT-TYPE
	SYNTAX	INTEGER
	ACCESS	read-only
	STATUS	mandatory
	DESCRIPTION
		"PCR[cell/s] of the direction from this endpoint to
		the endpoint to be switched.
		If the value is invalid,  -1 is indicated."
	--
	--
	--
	::= { connPvcEntry 19 }

connPvcContrastParam3	OBJECT-TYPE
	SYNTAX	INTEGER
	ACCESS	read-only
	STATUS	mandatory
	DESCRIPTION
		"PCR[cell/s] of the direction from the endpoint to
		be switched to this end point.
		If the value is invalid,  -1 is indicated."
	--
	--
	--
	::= { connPvcEntry 20 }

connPvcParam4	OBJECT-TYPE
	SYNTAX	INTEGER
	ACCESS	read-only
	STATUS	mandatory
	DESCRIPTION
		"SCR[cell/s] of the direction from this endpoint to
		the endpoint to be switched.
		If the value is invalid,  -1 is indicated."
	--
	--
	--
	::= { connPvcEntry 21 }

connPvcContrastParam4	OBJECT-TYPE
	SYNTAX	INTEGER
	ACCESS	read-only
	STATUS	mandatory
	DESCRIPTION
		"SCR[cell/s] of the direction from the endpoint to
		be switched to this end point.
		If the value is invalid,  -1 is indicated."
	--
	--
	--
	::= { connPvcEntry 22 }

connPvcParam5	OBJECT-TYPE
	SYNTAX	INTEGER
	ACCESS	read-only
	STATUS	mandatory
	DESCRIPTION
		"MBS[cell] of the direction from this endpoint to
		the endpoint to be switched.
		If the value is invalid,  -1 is indicated."
	--
	--
	--
	::= { connPvcEntry 23 }

connPvcContrastParam5	OBJECT-TYPE
	SYNTAX	INTEGER
	ACCESS	read-only
	STATUS	mandatory
	DESCRIPTION
		"MBS[cell] of the direction from the endpoint to
		be switched to this end point.
		If the value is invalid,  -1 is indicated."
	--
	--
	--
	::= { connPvcEntry 24 }

connPvcParam6	OBJECT-TYPE
	SYNTAX	INTEGER {
			off(1), 
			on(2)
	}
	ACCESS	read-only 
	STATUS	mandatory 
	DESCRIPTION
		"EPD(Early Packet Discard) of the direction from this endpoint
		to the endpoint to be switched.
		Indicate if the discard processing in the unit of AAL5
		packet should be performed or not when the threshold is
		exceeded.
		If the value is invalid,  off(1) is indicated."
	--
	--
	--
	--
	--
	::= { connPvcEntry 25 }

connPvcContrastParam6	OBJECT-TYPE
	SYNTAX	INTEGER {
			off(1), 
			on(2)
	}
	ACCESS	read-only 
	STATUS	mandatory 
	DESCRIPTION
		"EPD(Early Packet Discard) of the direction from the endpoint
		to be switched to this end point.
		Indicate if the discard processing in the unit of AAL5
		packet should be performed or not when the threshold is
		exceeded.
		If the value is invalid,  off(1) is indicated."
	--
	--
	--
	--
	--
	::= { connPvcEntry 26 }

connPvcParam7	OBJECT-TYPE
	SYNTAX	INTEGER	
	ACCESS	not-accessible
	STATUS	mandatory
	DESCRIPTION
		"MCR[cell/s]. Not supported here."
	--
	::= { connPvcEntry 27 }

connPvcContrastParam7	OBJECT-TYPE
	SYNTAX	INTEGER	
	ACCESS	not-accessible
	STATUS	mandatory
	DESCRIPTION
		"MCR[cell/s]. Not supported here."
	--
	::= { connPvcEntry 28 }

connPvcTrfTable	OBJECT-TYPE
	SYNTAX	SEQUENCE OF ConnPvcTrfEntry
	ACCESS	not-accessible
	STATUS	mandatory
	DESCRIPTION
		" Indicate traffic counter information per connection."
	--
	::= { connPvc 3 }
 
connPvcTrfEntry	OBJECT-TYPE
 	SYNTAX	ConnPvcTrfEntry
 	ACCESS	not-accessible	
 	STATUS	mandatory
 	DESCRIPTION
 		" Entry of traffic per connection.
		  Every INDEX is equivalent to the one defined in connPvcEntry."
	--
	--
 	INDEX{ connPvcPort,  connPvcVpi,  connPvcVci,  connPvcDirection,  connPvcIndex }
 	::= { connPvcTrfTable 1 }

ConnPvcTrfEntry ::=
	SEQUENCE	{
		connPvcTrfInCells
			OCTET STRING, 
		connPvcTrfInCellsCounters
			Counter, 
		connPvcTrfOutCells
			OCTET STRING, 
		connPvcTrfOutCellsCounters
			Counter, 
		connPvcTrfInDropCells
			OCTET STRING, 
		connPvcTrfInDropCellsCounters
			Counter
 	}

connPvcTrfInCells	OBJECT-TYPE
	SYNTAX	OCTET STRING
	ACCESS	read-only
	STATUS	mandatory
	DESCRIPTION
		" The number of receive cells  64 bit counter"
	--
	::= { connPvcTrfEntry 1 }

connPvcTrfInCellsCounters	OBJECT-TYPE
	SYNTAX	Counter
	ACCESS	read-only
	STATUS	mandatory
	DESCRIPTION
		" The number of receive cells  32 bit counter"
	--
	::= { connPvcTrfEntry 2 }

connPvcTrfOutCells	OBJECT-TYPE
	SYNTAX	OCTET STRING
	ACCESS  read-only
	STATUS  mandatory
	DESCRIPTION
		" The number of transmit cells  64 bit counter"
	--
	::= { connPvcTrfEntry 3 }

connPvcTrfOutCellsCounters	OBJECT-TYPE
	SYNTAX  Counter
	ACCESS  read-only
	STATUS  mandatory
	DESCRIPTION
		" The number of transmit cells  32 bit counter"
	--
	::= { connPvcTrfEntry 4 }

connPvcTrfInDropCells	OBJECT-TYPE
	SYNTAX  OCTET STRING
	ACCESS  read-only
	STATUS  mandatory
	DESCRIPTION
		" The number of receive drop cells  64 bit counter "
	--
	::= { connPvcTrfEntry 5 }

connPvcTrfInDropCellsCounters	OBJECT-TYPE
	SYNTAX  Counter
	ACCESS  read-only
	STATUS  mandatory
	DESCRIPTION
		" The number of receive drop cells  32 bit counter"
	--
	::= { connPvcTrfEntry 6 }

connConf	OBJECT IDENTIFIER ::= { conn 2 }

connConfNode	OBJECT IDENTIFIER ::= { connConf 1 }

connConfNodePvcs	OBJECT-TYPE
	SYNTAX  INTEGER (0..32000)
	ACCESS	read-only
	STATUS	mandatory
	DESCRIPTION
		"The number of current established PVCs in this switch."
	--
	::= { connConfNode 1 }

connConfNodeSvcs	OBJECT-TYPE
	SYNTAX  INTEGER (0..4096)
	ACCESS	read-only
	STATUS	mandatory
	DESCRIPTION
		"The number of current established SVCs in this switch."
	--
	::= { connConfNode 2 }

connConfNodeSoftPvcs	OBJECT-TYPE
	SYNTAX  INTEGER (0..4096)
	ACCESS	read-only
	STATUS	mandatory
	DESCRIPTION
		"The number of current established Soft PVPCs/PVCCs in
		 this switch."
	--
	::= { connConfNode 3 }

connConfNodeTrafClear	OBJECT-TYPE
	SYNTAX	INTEGER {
			allClear(1), 
			noOperation(2)
		}
	ACCESS	read-write
	STATUS	mandatory
	DESCRIPTION
		"Set allClear (1) to clear all traffic registration information.
		If noOperation (2) is written,  nothing will be performed.
		The value at read is always noOperation (2)."
	--
	--
	--
	::= { connConfNode 4 }

connConfNodeTrafs	OBJECT-TYPE
	SYNTAX	INTEGER (0..1024)
	ACCESS	read-only
	STATUS	mandatory
	DESCRIPTION
		" The number of traffic registrations which are being set 
		in the switch. "
	--
	::= { connConfNode 5 }

connConfNodeCompleteSvcs	OBJECT-TYPE
	SYNTAX	Counter
	ACCESS	read-only
	STATUS	mandatory
	DESCRIPTION
		" The number of SVC complete calls "
	--
	::= { connConfNode 6 }

connConfNodeUnCompleteSvcs	OBJECT-TYPE
	SYNTAX	Counter
	ACCESS	read-only
	STATUS	mandatory
	DESCRIPTION
		" The number of SVC incomplete calls "
	--
	::= { connConfNode 7 }

connConfIfTable	OBJECT-TYPE
	SYNTAX	SEQUENCE OF ConnConfIfEntry
	ACCESS	not-accessible
	STATUS	mandatory
	DESCRIPTION
		" The table is used to show the information of current
		 established connections on the interface."
	::= { connConf 2 }

connConfIfEntry OBJECT-TYPE
	SYNTAX	ConnConfIfEntry
	ACCESS	not-accessible
	STATUS	mandatory
	DESCRIPTION
		"Entry of connConfIfTable."
	INDEX	{ ifIndex }
	::= { connConfIfTable 1}

ConnConfIfEntry ::=
	SEQUENCE {
		connConfIfPvcs		INTEGER, 
		connConfIfSvcs		INTEGER, 
		connConfIfSoftPvcs	INTEGER
	}

connConfIfPvcs	OBJECT-TYPE
	SYNTAX  INTEGER (0..16384)
	ACCESS	read-only
	STATUS	mandatory
	DESCRIPTION
		" The number of current established PVCs
		on the interface."
	::= { connConfIfEntry 1 }

connConfIfSvcs	OBJECT-TYPE
	SYNTAX  INTEGER (0..4096)
	ACCESS	read-only
	STATUS	mandatory
	DESCRIPTION
		" The number of current established SVCs
		on the interface."
	::= { connConfIfEntry 2 }

connConfIfSoftPvcs	OBJECT-TYPE
	SYNTAX  INTEGER (0..4096)
	ACCESS	read-only
	STATUS	mandatory
	DESCRIPTION
		" The number of current established Soft PVPCs/PVCCs
		on the interface."
	::= { connConfIfEntry 3 }


connRoute	OBJECT IDENTIFIER ::= { conn 3 }

DstAtmAddressFormat ::= INTEGER	{
				noWriting(-1), 	-- read only
				e-164	(1), 
				nsap	(2)
			}
	--	DstAtmAddress format.

DstAtmAddressLength ::= INTEGER(4..160|-1)
	--	The valid bit length of DstAtmAddress.
	--	The value(-1) is read-only.
	--	The value(4..160) must be a multiple of 4.

DstAtmAddress ::= OCTET STRING(SIZE(0..20))
	--	Called Party Address.
	--	Its maximum length is either 20 bytes (NSAP) or 8
	--	bytes (E.164).
	--	If the last semi OCTET is invalid,  it is padded
	--	with 0xf.
	--	The value of size(0) is read-only.

DstPrimaryIfIndex ::= INTEGER(1..99|-1)
	--	The outgoing port number selected first.
	--	The value(-1) is read-only.

DstPrimaryVPI ::= INTEGER(0..4095|-1)
	--	The outgoing VPI number for tunneling selected first.
	--	The value(-1) shows that this is not used for routing.

DstSecondaryIfIndex ::= INTEGER(1..99|-1)
	--	The outgoing port number selected secondly or after.
	--	The value(-1) shows that this is not used for routing.

DstSecondaryVPI ::= INTEGER(0..4095|-1)
	--	The outgoing VPI number for tunneling selected secondly or
	--	after.
	--	The value(-1) shows that this is not used for routing.

connRouteOpe	OBJECT IDENTIFIER ::= { connRoute 1 }

	--	The connRouteOpe module defines the way to operate(add or
	--	delete) the static routing information which connRouteTable
	--	shows.

	--	the Procedure of operating the static routing information

	--	1.Get connRouteOpeStatus

	--		Get connRouteOpeStatus to check if it is "free".

	--		If it is,  managers can set "allocate" to it.

	--		If not,  try again after a while.
	--		If it has been the same value other than "free" for a
	--		long time,  set it "free" judging that the allocating
	--		manager failed. But the other managers which did set
	--		"allocate" cannot set "free" for 60sec after the
	--		allocating manager has last requested the agent to
	--		set objects under connRouteOpe module.
	--		
	--	2.Set "allocate" to connRouteOpeStatus.

	--		Set "allocate" to connRouteOpeStatus,  then 
	--		the agent sets the default value to the parameter
	--		objects.

	--		i)The default values of parameters

	--		connRouteOpeAddressFormat	-1
	--		connRouteOpeAddressLength	-1
	--		connRouteOpeAddress		 0 length string
	--		connRouteOpePrimaryIfIndex	-1
	--		connRouteOpePrimaryVPI		-1
	--		connRouteOpeSecondaryIfIndex	-1
	--		connRouteOpeSecondaryVPI	-1
	--		connRouteOpeTertiaryIfIndex	-1
	--		connRouteOpeTertiaryVPI		-1
	--		connRouteOpeFourthryIfIndex	-1
	--		connRouteOpeFourthryVPI		-1
	--		connRouteOpeFifthryIfIndex	-1
	--		connRouteOpeFifthryVPI		-1
	--		connRouteOpeSixthryIfIndex	-1
	--		connRouteOpeSixthryVPI		-1
	--		connRouteOpeSeventhryIfIndex	-1
	--		connRouteOpeSeventhryVPI	-1

	--	In 3. and 4.,  parameter objects cannot be set by the managers
	--	which have not set "allocate".

	--	3.Set the value to parameter objects.

	--		i)"add" parameters

	--		connRouteOpeAddressFormat	
	--		connRouteOpeAddressLength
	--		connRouteOpeAddress
	--		connRouteOpePrimaryIfIndex
	--		connRouteOpePrimaryVPI		*
	--		connRouteOpeSecondaryIfIndex	*
	--		connRouteOpeSecondaryVPI	*
	--		connRouteOpeTertiaryIfIndex	*
	--		connRouteOpeTertiaryVPI		*
	--		connRouteOpeFourthryIfIndex	*
	--		connRouteOpeFourthryVPI		*
	--		connRouteOpeFifthryIfIndex	*
	--		connRouteOpeFifthryVPI		*
	--		connRouteOpeSixthryIfIndex	*
	--		connRouteOpeSixthryVPI		*
	--		connRouteOpeSeventhryIfIndex	*
	--		connRouteOpeSeventhryVPI	*

	--		*)If these parameters are not necessary
	--		a manager does not have to set them( or
	--		sets the value(-1) to them).
	--		But the following pattern of parameters	is not allowed.

	--		connRouteOpeSecondary(Seventhry)IfIndex   - not set
	--				(i.e This object value is(-1))
	--		connRouteOpeSecondary(Seventhry)VPI	- set
	--				(i.e This object value is not (-1))

	--		ii)"delete" parameters

	--		connRouteOpeAddressFormat
	--		connRouteOpeAddressLength
	--		connRouteOpeAddress

	--	4.Set "add"/"delete" to connRouteOpeStatus.
	--		( No other objects should be set together with 
	--		connRouteOpeStatus in this operation.)

	--		If the error status of the response is "noError",  it
	--		means that connRouteOpeStatus is set successfully.
	--		Otherwise,  get connRouteOpeFailureCause to see the
	--		cause.

	--	5.Set "free" to connRouteOpeStatus
	--		Set "free" to connRouteOpeStatus for the next
	--		operation.

connRouteOpeStatus	OBJECT-TYPE
		SYNTAX  INTEGER {
				allocate(1), 	
				add	(2), 
				delete	(3), 
				free	(4)
			}
		ACCESS  read-write
		STATUS  mandatory
		DESCRIPTION
			"
		allocate	: allocate the right to operate the routing 
				information to a manager.

		add		: add the routing information
				to static routing table.
				

		delete		: delete the routing information
				from static routing table.

		free		: free the right to operate the routing
				information from a manager.

			    +-------------+	
			    |		  |
			    +---+----+<---+
		    ----------->|free|<-----------------
		   |		+----+   		|
		   |	    		     		|
		   |     +--------+        +----------+	|
		    ---->|allocate| -----> |add/delete|-
			 +--------+        +----------+
			"
		::= { connRouteOpe 1 }

ConnRouteOpeFailureCause ::= INTEGER	{
			noWriting			 (-1), 
			other				  (1),  -- add, delete
			allocateSucceed			  (2), 
			tableIsFull			  (3),  -- add
			parameterIsNotEnough		  (4),  -- add, delete
			specifiedAddressIsIllegal	  (5),  -- add, delete
			specifiedAddressIsAlreadyExisting (6),  -- add
			specifiedAddressIsNotExisting	  (7)  -- delete
			}

connRouteOpeFailureCause OBJECT-TYPE
		SYNTAX	ConnRouteOpeFailureCause
		ACCESS  read-only
		STATUS  mandatory
		DESCRIPTION
			"The result of the operation."
		::= { connRouteOpe 2 }

connRouteOpeAddressFormat OBJECT-TYPE
		SYNTAX  DstAtmAddressFormat
		ACCESS	read-write
		STATUS	mandatory
DESCRIPTION ""
		::= { connRouteOpe 3 }

connRouteOpeAddressLength OBJECT-TYPE
		SYNTAX  DstAtmAddressLength
		ACCESS	read-write
		STATUS	mandatory
DESCRIPTION ""
		::= { connRouteOpe 4 }

connRouteOpeAddress	OBJECT-TYPE
		SYNTAX	DstAtmAddress
		ACCESS  read-write
		STATUS  mandatory
DESCRIPTION ""
		::= { connRouteOpe 5 }

connRouteOpePrimaryIfIndex OBJECT-TYPE
		SYNTAX  DstPrimaryIfIndex
		ACCESS  read-write
		STATUS  mandatory
DESCRIPTION ""
		::= { connRouteOpe 6 }

connRouteOpePrimaryVPI OBJECT-TYPE
		SYNTAX  DstPrimaryVPI
		ACCESS  read-write
		STATUS	mandatory
DESCRIPTION ""
		::= { connRouteOpe 7 }

connRouteOpeSecondaryIfIndex OBJECT-TYPE
		SYNTAX  DstSecondaryIfIndex
		ACCESS  read-write
		STATUS  mandatory
DESCRIPTION ""
		::= { connRouteOpe 8 }

connRouteOpeSecondaryVPI OBJECT-TYPE
		SYNTAX	DstSecondaryVPI
		ACCESS  read-write
		STATUS  mandatory
DESCRIPTION ""
		::= { connRouteOpe 9 }

connRouteOpeTertiaryIfIndex OBJECT-TYPE
                SYNTAX  DstSecondaryIfIndex
                ACCESS  read-write
                STATUS  mandatory
DESCRIPTION ""
                ::= { connRouteOpe 10 }

connRouteOpeTertiaryVPI OBJECT-TYPE
                SYNTAX  DstSecondaryVPI
                ACCESS  read-write
                STATUS  mandatory
DESCRIPTION ""
                ::= { connRouteOpe 11 }

connRouteOpeFourthryIfIndex OBJECT-TYPE
                SYNTAX  DstSecondaryIfIndex
                ACCESS  read-write
                STATUS  mandatory
DESCRIPTION ""
                ::= { connRouteOpe 12 }

connRouteOpeFourthryVPI OBJECT-TYPE
                SYNTAX  DstSecondaryVPI
                ACCESS  read-write
                STATUS  mandatory
DESCRIPTION ""
                ::= { connRouteOpe 13 }

connRouteOpeFifthryIfIndex OBJECT-TYPE
                SYNTAX  DstSecondaryIfIndex
                ACCESS  read-write
                STATUS  mandatory
DESCRIPTION ""
                ::= { connRouteOpe 14 }

connRouteOpeFifthryVPI OBJECT-TYPE
                SYNTAX  DstSecondaryVPI
                ACCESS  read-write
                STATUS  mandatory
DESCRIPTION ""
                ::= { connRouteOpe 15 }

connRouteOpeSixthryIfIndex OBJECT-TYPE
                SYNTAX  DstSecondaryIfIndex
                ACCESS  read-write
                STATUS  mandatory
DESCRIPTION ""
                ::= { connRouteOpe 16 }

connRouteOpeSixthryVPI OBJECT-TYPE
                SYNTAX  DstSecondaryVPI
                ACCESS  read-write
                STATUS  mandatory
DESCRIPTION ""
                ::= { connRouteOpe 17 }

connRouteOpeSeventhryIfIndex OBJECT-TYPE
                SYNTAX  DstSecondaryIfIndex
                ACCESS  read-write
                STATUS  mandatory
DESCRIPTION ""
                ::= { connRouteOpe 18 }

connRouteOpeSeventhryVPI OBJECT-TYPE
                SYNTAX  DstSecondaryVPI
                ACCESS  read-write
                STATUS  mandatory
DESCRIPTION ""
                ::= { connRouteOpe 19 }

connRouteTable	OBJECT-TYPE
	SYNTAX	SEQUENCE OF ConnRouteEntry
	ACCESS	not-accessible
	STATUS  mandatory
	DESCRIPTION
		"This table is used to show the static routing table for SVC."
	::= { connRoute 2 }

connRouteEntry	OBJECT-TYPE
	SYNTAX	ConnRouteEntry
	ACCESS	not-accessible
	STATUS	mandatory
	DESCRIPTION
		"Entry of connRouteTable."
	--
	INDEX	{ connRouteAtmAddressFormat, 
			connRouteAtmAddressLength,  connRouteAtmAddress }
	::= { connRouteTable 1}

ConnRouteEntry ::=
	SEQUENCE {
		connRouteType
			INTEGER, 
		connRoutePrimaryIfIndex
			INTEGER, 
		connRoutePrimaryVPI
			INTEGER, 
		connRouteSecondaryIfIndex
			INTEGER, 
		connRouteSecondaryVPI
			INTEGER, 
                connRouteTertiaryIfIndex
                        INTEGER, 
                connRouteTertiaryVPI
                        INTEGER, 
                connRouteFourthryIfIndex
                        INTEGER, 
                connRouteFourthryVPI
                        INTEGER, 
                connRouteFifthryIfIndex
                        INTEGER, 
                connRouteFifthryVPI
                        INTEGER, 
                connRouteSixthryIfIndex
                        INTEGER, 
                connRouteSixthryVPI
                        INTEGER, 
                connRouteSeventhryIfIndex
                        INTEGER, 
                connRouteSeventhryVPI
                        INTEGER, 
                connRoutePrimaryStatus
                        INTEGER, 
                connRoutePrimaryCause
                        INTEGER, 
		connRouteAtmAddressFormat
			DstAtmAddressFormat, 
		connRouteAtmAddressLength
			DstAtmAddressLength, 
		connRouteAtmAddress
			DstAtmAddress
	}

connRouteType OBJECT-TYPE
		SYNTAX  INTEGER {
				static	(1), 
				dynamic	(2)
			}
		ACCESS	read-only
		STATUS	mandatory
		DESCRIPTION
			"The value of this object shows the routing type."
		::= { connRouteEntry 1 }

connRoutePrimaryIfIndex OBJECT-TYPE
		SYNTAX  DstPrimaryIfIndex
		ACCESS  read-only
		STATUS  mandatory
DESCRIPTION ""
		::= { connRouteEntry 2 }

connRoutePrimaryVPI OBJECT-TYPE
		SYNTAX  DstPrimaryVPI
		ACCESS  read-only
		STATUS	mandatory
DESCRIPTION ""
		::= { connRouteEntry 3 }

connRouteSecondaryIfIndex OBJECT-TYPE
		SYNTAX  DstSecondaryIfIndex
		ACCESS  read-only
		STATUS  mandatory
DESCRIPTION ""
		::= { connRouteEntry 4 }

connRouteSecondaryVPI OBJECT-TYPE
		SYNTAX	DstSecondaryVPI
		ACCESS  read-only
		STATUS  mandatory
DESCRIPTION ""
		::= { connRouteEntry 5 }

connRouteTertiaryIfIndex OBJECT-TYPE
                SYNTAX  DstSecondaryIfIndex
                ACCESS  read-only
                STATUS  mandatory
DESCRIPTION ""
                ::= { connRouteEntry 6 }

connRouteTertiaryVPI OBJECT-TYPE
                SYNTAX  DstSecondaryVPI
                ACCESS  read-only
                STATUS  mandatory
DESCRIPTION ""
                ::= { connRouteEntry 7 }

connRouteFourthryIfIndex OBJECT-TYPE
                SYNTAX  DstSecondaryIfIndex
                ACCESS  read-only
                STATUS  mandatory
DESCRIPTION ""
                ::= { connRouteEntry 8 }

connRouteFourthryVPI OBJECT-TYPE
                SYNTAX  DstSecondaryVPI
                ACCESS  read-only
                STATUS  mandatory
DESCRIPTION ""
                ::= { connRouteEntry 9 }

connRouteFifthryIfIndex OBJECT-TYPE
                SYNTAX  DstSecondaryIfIndex
                ACCESS  read-only
                STATUS  mandatory
DESCRIPTION ""
                ::= { connRouteEntry 10 }

connRouteFifthryVPI OBJECT-TYPE
                SYNTAX  DstSecondaryVPI
                ACCESS  read-only
                STATUS  mandatory
DESCRIPTION ""
                ::= { connRouteEntry 11 }

connRouteSixthryIfIndex OBJECT-TYPE
                SYNTAX  DstSecondaryIfIndex
                ACCESS  read-only
                STATUS  mandatory
DESCRIPTION ""
                ::= { connRouteEntry 12 }

connRouteSixthryVPI OBJECT-TYPE
                SYNTAX  DstSecondaryVPI
                ACCESS  read-only
                STATUS  mandatory
DESCRIPTION ""
                ::= { connRouteEntry 13 }

connRouteSeventhryIfIndex OBJECT-TYPE
                SYNTAX  DstSecondaryIfIndex
                ACCESS  read-only
                STATUS  mandatory
DESCRIPTION ""
                ::= { connRouteEntry 14 }

connRouteSeventhryVPI OBJECT-TYPE
                SYNTAX  DstSecondaryVPI
                ACCESS  read-only
                STATUS  mandatory
DESCRIPTION ""
                ::= { connRouteEntry 15 }

connRoutePrimaryStatus OBJECT-TYPE
                SYNTAX  INTEGER {
                        disable (1), 
                        enable  (2)
                        }
                ACCESS  read-only
                STATUS  mandatory
                DESCRIPTION
		"Operational status of the primary routing.
		If the primary route of the routing table of the
		equipment is valid,  enable(2),  if not valid,  disable(1)."
	--
	--
                ::= { connRouteEntry 16 }

connRoutePrimaryCause OBJECT-TYPE
                SYNTAX  INTEGER {
                                normal (0), 
                                other (1), 
                                outOfService (2), 
                                testing (3), 
                                lineInterface-Down  (4), 
                                lineInterface-Failure (5), 
                                sw-Engine-Failure (6), 
                                sw-Engine-SwapOUT (7), 
                                notInstalled (99)
                        }
                ACCESS  read-only
                STATUS  mandatory
                DESCRIPTION
		"Cause of the switching from the primary route."
	--
                ::= { connRouteEntry 17 }

connRouteAtmAddressFormat	OBJECT-TYPE
		SYNTAX	DstAtmAddressFormat
		ACCESS	not-accessible
		STATUS	mandatory
DESCRIPTION ""
		::= { connRouteEntry 18 }

connRouteAtmAddressLength	OBJECT-TYPE
		SYNTAX	DstAtmAddressLength
		ACCESS	not-accessible
		STATUS	mandatory
DESCRIPTION ""
		::= { connRouteEntry 19 }

connRouteAtmAddress	OBJECT-TYPE
		SYNTAX	DstAtmAddress
		ACCESS	not-accessible
		STATUS	mandatory
DESCRIPTION ""
		::= { connRouteEntry 20 }

connSoftPvcIndexNext	OBJECT-TYPE
	SYNTAX  INTEGER (1..128)
	ACCESS	read-only
	STATUS	mandatory
	DESCRIPTION
		"This object returns the empty index of the call management 
		table,  required to access to connSoftPvcTable. "
	--
	--
	::= { conn 4 }

connSoftPvcTable OBJECT-TYPE
	SYNTAX	SEQUENCE OF ConnSoftPvcEntry
	ACCESS	not-accessible
	STATUS	mandatory
	DESCRIPTION
		" This table include all entries to Soft-PVPC/PVCC 
		currently available between the lines or the line and 
		CPU port of the switch.  Also,  this table is used to 
		set or delete Soft-PVPC/PVCC.  The operable 
		connection form between Soft-PVPC/PVCC is bi-
		directional point-to-point only.

	The procedure to set the connection is as follows:

		1. Acquire connSoftPvcIndex
		To set the connection,  read connSoftPvcIndexNext and 
		obtain an index of the Soft-PVPC/PVCC table.  The 
		index must be managed by NMS. (The index is required 
		to take an action to the connection.)

		2. Set createAndWait
		Set connSoftPvcRowStatus to CreateAndWait,  using the 
		obtained connSoftPvcIndex as index.  If the agent 
		will set the parameter for the Soft-PVPC/PVCC 
		setting to the default value and make 
		connSoftRowStatus to notReady.

		However,  the same manager cannot create another row 
		while creating a row (the status of the row is notRedy 
		or notInService).

		3. Get the default value
		Get the default value of the object which serves as 
		parameter for the connection setting. (The agent 
		shall return -1 if it does not have a default value.)

		Default values are as follows:

			connSoftPvcTopology		bi-directional-VCC(2)
			connSoftPvcTrafficType		traffic-UBR(5)
			connSoftPvcEndpointType		calling(1)
			connSoftPvcRetry		2
			connSoftPvcSrcAtmAddressFormat	nsap(2)
			connSoftPvcSrcAtmAddressLength	None
			connSoftPvcSrcAtmAddress	0 length string
			connSoftPvcSrcIfIndex		None
			connSoftPvcSrcVPI		None
			connSoftPvcSrcVCI		None
			connSoftPvcDstAtmAddressFormat	nsap(2)
			connSoftPvcDstAtmAddressLength	None
			connSoftPvcDstAtmAddress	0 length string
			connSoftPvcDstIfIndex		None
			connSoftPvcDstVPI		None
			connSoftPvcDstVCI		None
			connSoftPvcSrcFifoIndex		0
			connSoftPvcDstFifoIndex		0
			connSoftPvcNodeKind		model5(1)
			connSoftPvcSrcParam1		off(1)
			connSoftPvcDstParam1		off(1)
			connSoftPvcSrcParam2		0 length string
			connSoftPvcDstParam2		0 length string
			connSoftPvcSrcParam3		-1
			connSoftPvcDstParam3		-1
			connSoftPvcSrcParam4		-1
			connSoftPvcDstParam4		-1
			connSoftPvcSrcParam5		-1
			connSoftPvcDstParam5		-1
			connSoftPvcSrcParam6		off(2)
			connSoftPvcDstParam6		off(2)
			connSoftPvcSrcParam7		None (not installed)
			connSoftPvcDstParam7		None (not installed)

		4. Set parameter
		If a parameter does not have a default value,  or the 
		default value should not be used,  set the parameter to 
		a value.
		If all parameters are set,  the agent shall make 
		connSoftPvcRowStatus to notInService.

		5. Set active
		By doing so,  the agent checks parameters,  resources and 
		establishes the connection.

		6. Get connSoftPvcRowStatus
		If connSoftPvcRowStatus is active,  the connection 
		setting completed successfully,  if notInService, the 
		connection setting failed.  For the cause,  refer to 
		connSoftPvcCause.
		(Note) When the connection setting has failed,  if the 
		connection is not released,  the row will remain.

		7. Get connSoftPvcRestRetry
		Remaining counts of retry are contained.  If it is 
		positive value,  the retry is in progress.  If 
		connSoftPvcRestRetry is 0,  the retry completed.  The 
		result of the connection setting should be seen,  when 
		this object is 0.
		-1 means that infinite retry is in progress.

		***Special pattern***
		(1) If connSoftPvcTopology is bi-directional-VPC,  set 
		connSoftPvcSrcVCI,  connSoftPvcDstVCI to 0.

	The procedure to release the connection is as follows:

		1. Set 'destroy'
		Set connSoftPvcRowStatus to 'destroy',  using 
		connSoftPvcIndex of the connection to be deleted as 
		index.
		The agent will delete the connection,  referring to 
		it.
		(Note) 'destroy' can also be set during the bypass 
		processing.

		2. Get the result
		If the connection is deleted,  'get' of 
		connSoftPvcTable of the designated index becomes 
		NoSuchName.

	The bypass processing of connection

		1. Set notInService
		When the agent executes the bypass processing of 
		connection,  set connSoftPvcRowStatus to 
		notInService,  and then establish the connection.

		2. Get connSoftPvcRowStatus
		If connSoftPvcRowStatus is 'active',  the bypass 
		connection setting has completed successfully.
		If connSoftPvcRowStatus remains 'notInService',  
		the connection setting has failed.

	Others

		1. The cut and recovery processing of connection is 
		performed,  following the delete and set procedures 
		of the concerned connection.
		Each procedure is as stated before."

	--
	--
	--
	--
	--
	--
	--
	--
	--
	--
	--
	--
	--
	--
	--
	--
	--
	--
	--
	--
	--
	--
	--
	--
	--
	--
	--
	--
	--
	--	  
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--	
	--
	--
	--
	--
	--
	--
	--
	--
	--
	--
	--
	--
	--
	--
	--
	::= { conn 5 }

connSoftPvcEntry OBJECT-TYPE
	SYNTAX	ConnSoftPvcEntry
	ACCESS	not-accessible
	STATUS	mandatory
	DESCRIPTION
		" Entry of ATMSoft-PVPC/PVCC connection "
	--
	INDEX	{ connSoftPvcIndex }
	::= { connSoftPvcTable 1 }

ConnSoftPvcEntry ::=
	SEQUENCE {
		connSoftPvcIndex
			INTEGER, 
		connSoftPvcTopology
			INTEGER, 
		connSoftPvcTrafficType
			INTEGER, 
		connSoftPvcEndpointType
			INTEGER, 
		connSoftPvcRetry
			INTEGER, 
		connSoftPvcSrcAtmAddressFormat
			INTEGER, 
		connSoftPvcSrcAtmAddressLength
			INTEGER, 
		connSoftPvcSrcAtmAddress
			OCTET STRING, 
		connSoftPvcSrcIfIndex
			INTEGER, 
		connSoftPvcSrcVPI
			INTEGER, 
		connSoftPvcSrcVCI
			INTEGER, 
		connSoftPvcDstAtmAddressFormat
			INTEGER, 
		connSoftPvcDstAtmAddressLength
			INTEGER, 
		connSoftPvcDstAtmAddress
			OCTET STRING, 
		connSoftPvcDstIfIndex
			INTEGER, 
		connSoftPvcDstVPI
			INTEGER, 
		connSoftPvcDstVCI
			INTEGER, 
		connSoftPvcRowStatus
			INTEGER, 
		connSoftPvcCause
			INTEGER, 
		connSoftPvcRestRetry
			INTEGER, 
		connSoftPvcSrcFifoIndex	
			INTEGER, 
		connSoftPvcDstFifoIndex	
			INTEGER, 
		connSoftPvcNodeKind
			INTEGER, 
		connSoftPvcSrcParam1
			INTEGER, 
		connSoftPvcDstParam1
			INTEGER, 
		connSoftPvcSrcParam2
			DisplayString, 
		connSoftPvcDstParam2
			DisplayString, 
		connSoftPvcSrcParam3
			INTEGER, 
		connSoftPvcDstParam3
			INTEGER, 
		connSoftPvcSrcParam4
			INTEGER, 
		connSoftPvcDstParam4
			INTEGER, 
		connSoftPvcSrcParam5
			INTEGER, 
		connSoftPvcDstParam5
			INTEGER, 
		connSoftPvcSrcParam6
			INTEGER, 
		connSoftPvcDstParam6
			INTEGER, 
		connSoftPvcSrcParam7
			INTEGER, 
		connSoftPvcDstParam7
			INTEGER
	}

connSoftPvcIndex	OBJECT-TYPE
	SYNTAX  INTEGER (1..128)
	ACCESS	read-only
	STATUS	mandatory
	DESCRIPTION
		"The value of this object is equal to the
		 connSoftPvcIndexNext.
		1	-	128	:	Soft PVPCs/PVCCs"
	::= { connSoftPvcEntry 1 }

connSoftPvcTopology OBJECT-TYPE
	SYNTAX	INTEGER {
			bi-directional-VCC  (2), 
			bi-directional-VPC  (4)
		}
	ACCESS	read-write
	STATUS	mandatory
	DESCRIPTION
		"Topology of the Connection."
	--
	::= { connSoftPvcEntry 2 }

connSoftPvcTrafficType OBJECT-TYPE
	SYNTAX	INTEGER {
			traffic-CBR (1), 
			traffic-rt-VBR (2), 
			traffic-nrt-VBR (3), 
			traffic-ABR (4), 
			traffic-UBR (5)
		}
	ACCESS	read-write
	STATUS	mandatory
	DESCRIPTION
		"Traffic Type."
	--
	::= { connSoftPvcEntry 3 }

connSoftPvcEndpointType OBJECT-TYPE
	SYNTAX	INTEGER {
			calling(1), 	-- Calling side.
			called(2)	-- Called side. notSupported.
		}
	ACCESS	read-only
	STATUS	mandatory
	DESCRIPTION
		"Type of Endpoint."
	--
	::= { connSoftPvcEntry 4 }

connSoftPvcRetry OBJECT-TYPE
	SYNTAX  INTEGER (0..15|-1)
	ACCESS	read-write
	STATUS	mandatory
	DESCRIPTION
		"Number of retry.
		0	-	15	:	Number of retry
		-1			:	Infinite retry"
	--
	::= { connSoftPvcEntry 5 }

ConnSoftPvcSrcAtmAddressFormat ::= INTEGER	{
		noWriting(-1), 	-- read only
		e-164	 (1), 
		nsap	 (2)
	}

connSoftPvcSrcAtmAddressFormat OBJECT-TYPE
	SYNTAX  ConnSoftPvcSrcAtmAddressFormat
	ACCESS	read-write
	STATUS	mandatory
	DESCRIPTION
		"AtmAdress format. "
	::= { connSoftPvcEntry 6 }

connSoftPvcSrcAtmAddressLength OBJECT-TYPE
	SYNTAX  INTEGER (4..160|-1)
	ACCESS	read-write
	STATUS	mandatory
	DESCRIPTION
		"The valid bit length of connSoftPvcSrcAtmAddress.
		 The value(-1) is read-only.
		 The value(4..160) must be a multiple of 4."
	::= { connSoftPvcEntry 7 }

connSoftPvcSrcAtmAddress OBJECT-TYPE
	SYNTAX  OCTET STRING (SIZE(0..20))
	ACCESS	read-write
	STATUS	mandatory
	DESCRIPTION
		"NodeId of source node.
		 Its maximum length is 13 bytes.
		 This object length is 20 bytes in case AtmAddress is
		 setting.
		 If the last semi OCTET is invalid,  it is padded
		 with 0xf.
		 The value of size(0) is read-only."
	::= { connSoftPvcEntry 8 }

connSoftPvcSrcIfIndex OBJECT-TYPE
	SYNTAX	INTEGER (1..99|-1)
	ACCESS	read-write
	STATUS	mandatory
	DESCRIPTION
		"The number of the calling line.
		(ifIndex of ifEntry)"
	--
	::= { connSoftPvcEntry 9 }

connSoftPvcSrcVPI OBJECT-TYPE
	SYNTAX	INTEGER
	ACCESS	read-write
	STATUS	mandatory
	DESCRIPTION
		"VPI value of the calling line."
	--
	::= { connSoftPvcEntry 10 }

connSoftPvcSrcVCI OBJECT-TYPE
	SYNTAX	INTEGER
	ACCESS	read-write
	STATUS	mandatory
	DESCRIPTION
		"VCI value of the calling line."
	--
	::= { connSoftPvcEntry 11 }

ConnSoftPvcDstAtmAddressFormat ::= INTEGER {
		noWriting(-1),     -- read only
		e-164    (1), 
		nsap     (2)
		}

connSoftPvcDstAtmAddressFormat OBJECT-TYPE
	SYNTAX  ConnSoftPvcDstAtmAddressFormat
	ACCESS	read-write
	STATUS	mandatory
	DESCRIPTION
		"AtmAdress format. "
	::= { connSoftPvcEntry 12 }

connSoftPvcDstAtmAddressLength OBJECT-TYPE
	SYNTAX  INTEGER (4..160|-1)
	ACCESS	read-write
	STATUS	mandatory
	DESCRIPTION
		"The valid bit length of connSoftPvcDstAtmAddress.
		 The value(-1) is read-only.
		 The value(4..160) must be a multiple of 4."
	::= { connSoftPvcEntry 13 }

connSoftPvcDstAtmAddress OBJECT-TYPE
	SYNTAX  OCTET STRING (SIZE(0..20))
	ACCESS	read-write
	STATUS	mandatory
	DESCRIPTION
		"NodeId of destination node.
		 Its maximum length is 13 bytes.
		 This object length is 20 bytes in case AtmAddress is
		 setting.
		 If the last semi OCTET is invalid,  it is padded
		 with 0xf.
		 The value of size(0) is read-only."
	::= { connSoftPvcEntry 14 }

connSoftPvcDstIfIndex OBJECT-TYPE
	SYNTAX	INTEGER (1..99|-1)
	ACCESS	read-write
	STATUS	mandatory
	DESCRIPTION
		"The number of the called line.
		(ifIndex of ifEntry)65 is GateWay."
	--
	--
	::= { connSoftPvcEntry 15 }

connSoftPvcDstVPI OBJECT-TYPE
	SYNTAX	INTEGER
	ACCESS	read-write
	STATUS	mandatory
	DESCRIPTION
		"VPI value of the called line."
	--
	::= { connSoftPvcEntry 16 }

connSoftPvcDstVCI OBJECT-TYPE
	SYNTAX	INTEGER
	ACCESS	read-write
	STATUS	mandatory
	DESCRIPTION
		"VCI value of the called line."
	--
	::= { connSoftPvcEntry 17 }

connSoftPvcRowStatus OBJECT-TYPE
	SYNTAX	INTEGER {
			active(1), 
			notInService(2), 
			notReady(3), 
			createAndGo(4), 		-- notSupported
			createAndWait(5), 
			destroy(6)
		}
	ACCESS	read-write
	STATUS	mandatory
	DESCRIPTION
		"It is used from the manager to order the setting method
		of the Soft PVC connection.  It is used from the agent side
		to return the result of the connection setting request.

			   - 'active',  which indicates that the
			   conceptual row is available for use by the
			   managed device;

			   - 'notInService',  which indicates that the
			   conceptual row exists in the agent,  but is
			   unavailable for use by the managed device;

			   - 'notReady',  which indicates that the
			   conceptual row exists in the agent,  but is
			   missing information necessary in order to be
			   available for use by the managed device;

			   - 'createAndGo',  which is supplied by a
			   management station wishing to create a new
			   instance of a conceptual row and to have it
			   available for use by the managed device;

			   - 'createAndWait',  which is supplied by a
			   management station wishing to create a new
			   instance of a conceptual row but not to have
			   it available for use by the managed device;
			   and, 

			   - 'destroy',  which is supplied by a
			   management station wishing to delete all of
			   the instances associated with an existing
			   conceptual row.
			"
	--
	--
	--
	::= { connSoftPvcEntry 18 }

connSoftPvcCause OBJECT-TYPE
	SYNTAX	INTEGER {
			rowExisting(1), 		-- default value
			vpivciSrcBusy(2), 
			vpivciDstBusy(3), 
			vpivciOutOfRange(4), 
			rateSrcOverFlow(5), 
			rateDstOverFlow(6), 
			dataTableFull(7), 
			inconsistentVPVC(8), 
			lineDiagnosis(9), 
			missMatchTrfType(10), 
			illegalSrcFileName(11), 
			illegalDstFileName(12), 
			lineOutOfOrder(13), 
			illegalSrcShaper(14), 
			illegalOperation(15), 
			parameterIsNotEnough(16), 
			diagnostics(17), 
			otherFailure(18), 
			illegalSrcRateForUPC(19), 
			noCevc(20), 
			noDlci(21), 
			noSrcShaperForGateway(22), 
			noPvcSrcShaperForGateway(23), 
			missMatchTrfTypeSrcShaperForGateway(24), 
			insusfficientPCRofProfile(25)
		}
	ACCESS	read-only
	STATUS	mandatory
	DESCRIPTION
		"Object to indicate the result of the connection setting."
	--
	::= { connSoftPvcEntry 19 }

connSoftPvcRestRetry OBJECT-TYPE
	SYNTAX	INTEGER (0..15|-1)
	ACCESS	read-only
	STATUS	mandatory
	DESCRIPTION
		"Remaining number of retry
		 0  -  15  :  Remaining number of retry
		 -1        :  Infinite retry in progress"
	--
	::= { connSoftPvcEntry 20 }

connSoftPvcSrcFifoIndex		OBJECT-TYPE
	SYNTAX	INTEGER (0..16)
	ACCESS  read-write
	STATUS  mandatory
	DESCRIPTION
		" Designate the Shaper number of the calling line.
		 If the Shaping is not performed,  designate 0. "
	--
	--
	::= { connSoftPvcEntry 21 }

connSoftPvcDstFifoIndex		OBJECT-TYPE
	SYNTAX	INTEGER (0..16)
	ACCESS  read-write
	STATUS  mandatory
	DESCRIPTION
		" Designate the Shaper number of the called line.
		  If the Shaping is not performed,  designate 0.
		  However,  if the called sw is not furnished with the shaping 
		  function,  this value has no meaning.
		  Since it cannot be recognized if this value is set on the 
		  called side,  the value is regarded as 'the value set by 
		  the calling side'."
	--
	--
	--
	--
	--
	--
	::= { connSoftPvcEntry 22 }

connSoftPvcNodeKind	OBJECT-TYPE
	SYNTAX	INTEGER {
			model5(1), 
			model7(2), 
			model5E(3)
	}
	ACCESS	read-write
	STATUS	mandatory
	DESCRIPTION
		"Designate/indicate the machine type on the called side. "
	--
	::= { connSoftPvcEntry 23 }

connSoftPvcSrcParam1	OBJECT-TYPE
	SYNTAX	INTEGER {
			off(1), 
			mode1(2), 
			mode2(3), 
			mode3(4), 
			mode4(5), 
			mode5(6)
	}
	ACCESS	read-write
	STATUS	mandatory
	DESCRIPTION
		"UPC mode of the calling line."
	--
	::= { connSoftPvcEntry 24 }

connSoftPvcDstParam1	OBJECT-TYPE
	SYNTAX	INTEGER {
			off(1), 
			mode1(2), 
			mode2(3), 
			mode3(4), 
			mode4(5), 
			mode5(6)
	}
	ACCESS	read-write
	STATUS	mandatory
	DESCRIPTION
		"UPC mode of the called line."
	--
	::= { connSoftPvcEntry 25 }

--	connSoftPvcSrcParam1/connSoftPvcDstParam1
--	The restrictions of UPC mode settings
--	If ABR is designated,  only off/mode1 can be designated.
--	If UBR is designated,  only mode1/mode5/off can be 
--	designated.
--	If nrt-VBR is designated,  only mode2/mode3/mode4/off
--	can be designated.
--	If rt-VBR is designated,  only mode2/mode3/mode4/off can 
--	be designated.
--	If CBR is designated,  only mode1/off can be designated.
--
--
--
--
--
--
--
--

connSoftPvcSrcParam2	OBJECT-TYPE
	SYNTAX	DisplayString (SIZE(1..10|0))
	ACCESS	read-write
	STATUS	mandatory
	DESCRIPTION
		"Profile name of Forward.
		If nothing is designated,  the string of size(0) is designated."
	--
	--
	::= { connSoftPvcEntry 26 }

connSoftPvcDstParam2	OBJECT-TYPE
	SYNTAX	DisplayString (SIZE(1..10|0))
	ACCESS	read-write
	STATUS	mandatory
	DESCRIPTION
		"Profile name of Backward.
		If nothing is designated,  the string of size(0) is designated."
	--
	--
	::= { connSoftPvcEntry 27 }

connSoftPvcSrcParam3	OBJECT-TYPE
	SYNTAX	INTEGER
	ACCESS	read-only
	STATUS	mandatory
	DESCRIPTION
		"PCR[cell/s] of Forward.
		If the value is invalid,  -1 is indicated."
	--
	--
	::= { connSoftPvcEntry 28 }

connSoftPvcDstParam3	OBJECT-TYPE
	SYNTAX	INTEGER
	ACCESS	read-only
	STATUS	mandatory
	DESCRIPTION
		"PCR[cell/s] of Backward.
		If the value is invalid,  -1 is indicated."
	--
	--
	::= { connSoftPvcEntry 29 }

connSoftPvcSrcParam4	OBJECT-TYPE
	SYNTAX	INTEGER
	ACCESS	read-only
	STATUS	mandatory
	DESCRIPTION
		"SCR[cell/s] of Forward.
		If the value is invalid,  -1 is indicated."
	--
	--
	::= { connSoftPvcEntry 30 }

connSoftPvcDstParam4	OBJECT-TYPE
	SYNTAX	INTEGER
	ACCESS	read-only
	STATUS	mandatory
	DESCRIPTION
		"SCR[cell/s] of Backward.
		If the value is invalid,  -1 is indicated."
	--
	--
	::= { connSoftPvcEntry 31 }

connSoftPvcSrcParam5	OBJECT-TYPE
	SYNTAX	INTEGER
	ACCESS	read-only
	STATUS	mandatory
	DESCRIPTION
		"MBS[cell] of Forward.
		If the value is invalid,  -1 is indicated."
	--
	--
	::= { connSoftPvcEntry 32 }

connSoftPvcDstParam5	OBJECT-TYPE
	SYNTAX	INTEGER
	ACCESS	read-only
	STATUS	mandatory
	DESCRIPTION
		"MBS[cell] of Backward.
		If the value is invalid,  -1 is indicated."
	--
	--
	::= { connSoftPvcEntry 33 }

connSoftPvcSrcParam6	OBJECT-TYPE
	SYNTAX	INTEGER {
			on(1), 
			off(2)
	}
	ACCESS	read-only 
	STATUS	mandatory 
	DESCRIPTION
		"EPD(Early Packet Discard) of Forward.
		Indicate if the discard processing in the unit of AAL5
		packet should be performed or not when the threshold is
		exceeded.
		If the value is invalid,  off(2) is indicated."
	--
	--
	--
	--
	::= { connSoftPvcEntry 34 }

connSoftPvcDstParam6	OBJECT-TYPE
	SYNTAX	INTEGER {
			on(1), 
			off(2)
	}
	ACCESS	read-only
	STATUS	mandatory
	DESCRIPTION
		"EPD(Early Packet Discard) of Backward.
		Indicate if the discard processing in the unit of AAL5
		packet should be performed or not when the threshold is
		exceeded.
		If the value is invalid,  off(2) is indicated."
	--
	--
	--
	--
	::= { connSoftPvcEntry 35 }

connSoftPvcSrcParam7	OBJECT-TYPE
	SYNTAX	INTEGER
	ACCESS	not-accessible
	STATUS	mandatory
	DESCRIPTION
		"MCR[cell/s]. Not supported here."
	--
	::= { connSoftPvcEntry 36 }

connSoftPvcDstParam7	OBJECT-TYPE
	SYNTAX	INTEGER
	ACCESS	not-accessible
	STATUS	mandatory
	DESCRIPTION
		"MCR[cell/s]. Not supported here."
	--
	::= { connSoftPvcEntry 37 }

ConnSoftPvcEstSrcInfIndex ::= INTEGER (1..128)

connSoftPvcEstablishedSrcInfTable OBJECT-TYPE
	SYNTAX	SEQUENCE OF ConnSoftPvcEstablishedSrcInfEntry
	ACCESS	not-accessible
	STATUS	mandatory
	DESCRIPTION
		" The table regarding the calling node of the Soft 
		PVPC/PVCC established as called side office by the local node"
	--
	--
	::= { conn 6 }

connSoftPvcEstablishedSrcInfEntry OBJECT-TYPE
	SYNTAX	ConnSoftPvcEstablishedSrcInfEntry
	ACCESS	not-accessible
	STATUS	mandatory
	DESCRIPTION
		" The entry of the calling side node information of the 
		Soft PVPC/PVCC established as the called side office by 
		the local node"
	--
	--
	INDEX	{ connSoftPvcEstSrcInfIndex }
	::= { connSoftPvcEstablishedSrcInfTable 1 }

ConnSoftPvcEstablishedSrcInfEntry ::=
	SEQUENCE {
		connSoftPvcEstablishedSrcInf
			Opaque, 
		connSoftPvcEstSrcInfIndex
			ConnSoftPvcEstSrcInfIndex
	}

connSoftPvcEstablishedSrcInf OBJECT-TYPE
	SYNTAX	Opaque
	ACCESS	read-only
	STATUS	mandatory
	DESCRIPTION
	" The calling node information of the Soft PVPC/PVCC 
	  established as called side office by the node.
	  The structure of the entry is as follows
			 struct {
				long	SrcAtmAddressFormat;
				long	SrcAtmAddressLength;
				char	SrcAtmAddress[20];
			 };
	(*1) 'long' data should be stored with 'big endian'.
	(*2) For SrcAtmAddress data,  if it is less than 20 byte,  
	the data padded by '0xf' shall be stored.
	This information is divided into up to 32 pieces,  and each 
	piece is put into the head 4 bytes (count) of an entry.  The 
	data which contains the number of the entries is described 
	below.

			+-----------------+
			|      count      | (= n)
			+-----------------+
			|   EstSrcInf 1   |
			|.................|
			|   EstSrcInf 2   |
			|.................|
			|        .        |
			|        .        |
			|        .        |
			|.................|
			|   EstSrcInf n   | ( 1 <= n <= 32 )
			+-----------------+
		"
	--
	--
	--
	--
	--
	--
	--
	--
	--
	--
	--
	--
	--
	--
	--
	::= { connSoftPvcEstablishedSrcInfEntry 1 }

connSoftPvcEstSrcInfIndex	OBJECT-TYPE
	SYNTAX	ConnSoftPvcEstSrcInfIndex
	ACCESS	not-accessible
	STATUS	mandatory
DESCRIPTION ""
	::= { connSoftPvcEstablishedSrcInfEntry 2 }


connOam			OBJECT IDENTIFIER ::= { conn 7 }

	--	<< OAM-END-Point/connection-point setting/procedure of delete >>

	-- 1. Set allocate
  	-- 	The manager acquires the right to set OAM 
	--	End-point/Connecting-point,  by setting 
	--	connOamOpeStatus to 'allocate'.  Then,  the agent 
	--	sets each parameter to the default value.
	--	The default values are described below.

	--		connOamOpeCause    : succeed(2)
	--		connOamOpePoint    : end-point(1)
	--		connOamOpeMode     : f4(1)
	--		connOamOpeSection  : segment(1)
	--		connOamOpePort1    : None (-1)
	--		connOamOpePort2    : None (-1)
	--		connOamOpeVpi1     : None (-1)
	--		connOamOpeVpi2     : None (-1)
	--		connOamOpeVci1     : None (-1)
	--		connOamOpeVci2     : None (-1)

	--	2. Set each parameter
	--		Set each parameter to a proper value.

	--	3. Set add/delete
	--	Set connOamOpeStatus to 'add'/'delete'.
	--	Then,  the agent checks each parameter and sets/deletes 
	--	End-point/Connecting-point.  Also the result will be 
	--	reflected in connOamOpeCause.

	--	4. Get the result
	--		The manager gets connOamOpeCause.

	--	5. Set 'free'
	--		When the above states processing ends,  the manager must 
	--		set connOamOpeStatus to 'free' and release the right to 
	--		set/delete.

	--

	--
	--
	--
	--
	--

	--
	--
	--
	--
	--
	--
	--
	--
	--
	--
	--

	--
	--

	--
	--
	--
	--
	--

	--
	--

	--
	--
	--
	--

connOamOpe	OBJECT IDENTIFIER ::= { connOam 1 }

connOamOpeStatus	OBJECT-TYPE
	SYNTAX	INTEGER {
			allocate (1), 	-- acquire the right to set/delete.
			add      (2), 	-- order to add.
			delete   (3), 	-- order to delete.
			free     (4)	-- release the right to set/delete.
		}
	ACCESS	read-write
	STATUS	mandatory
	DESCRIPTION
		" Used to set/delete OAM End-point,  Connecting-point."
	--
	::= { connOamOpe 1 }

connOamOpeCause	OBJECT-TYPE
	SYNTAX	INTEGER {
			other                (1),  -- Error other than
						  -- below stated.
			succeed              (2),  -- Set/delete processing
						  -- completed successfully.
			parameterIsNotEnough (3),  -- Parameter is not enough.
			tableIsFull          (4),  -- Table overflow.
			illegalPoint         (5),  -- Illegal point.
			illegalMode          (6),  -- Illegal mode.
			illegalSection       (7),  -- Illegal section.
						  -- notSupported.
			illegalPort          (8),  -- Illegal line number.
			illegalVpiVci        (9),  -- Illegal VPI/VCI.
			invalidBufferType   (10),  -- Buffer of the designated
						  -- line is no supported in
						  -- this function.
			noSuchConnection    (11),  -- Designated connection does
						  -- not exist.
			alreadyRegistered   (12),  -- Already registered.
			notExisting         (13)  -- Not registered.
		}
	ACCESS	read-only
	STATUS	mandatory DESCRIPTION
		" The result of the processing to set/delete OAM End-point,  
		Connecting-point."
	--
	::= { connOamOpe 2 }

connOamOpePoint	OBJECT-TYPE
	SYNTAX	INTEGER {
			end-point        (1), 
			connecting-point (2)
		}
	ACCESS	read-write
	STATUS	mandatory
	DESCRIPTION
		"End-point / Connecting-point."
	::= { connOamOpe 3 }

connOamOpeMode	OBJECT-TYPE
	SYNTAX	INTEGER {
			f4 (1), 
			f5 (2)
		}
	ACCESS	read-write
	STATUS	mandatory
	DESCRIPTION
		" Mode. F4 (VP level)/f5 (VC level) "
	--
	::= { connOamOpe 4 }

connOamOpeSection	OBJECT-TYPE
	SYNTAX	INTEGER {
			segment    (1), 
			end-to-end (2)
		}
	ACCESS	read-write
	STATUS	mandatory
	DESCRIPTION
		" Point between segments/End-to-End point."
	--
	::= { connOamOpe 5 }

connOamOpePort1	OBJECT-TYPE
	SYNTAX	INTEGER
	ACCESS	read-write
	STATUS	mandatory
	DESCRIPTION
		" Line number"
	--
	::= { connOamOpe 6 }

connOamOpePort2	OBJECT-TYPE
	SYNTAX	INTEGER
	ACCESS	read-write
	STATUS	mandatory
	DESCRIPTION
		" Line number.  Upon setting/deleting end-point,  don't 
		care about it."
	--
	::= { connOamOpe 7 }

connOamOpeVpi1	OBJECT-TYPE
	SYNTAX	INTEGER
	ACCESS	read-write
	STATUS	mandatory
	DESCRIPTION
		"VPI."
	::= { connOamOpe 8 }

connOamOpeVpi2	OBJECT-TYPE
	SYNTAX	INTEGER
	ACCESS	read-write
	STATUS	mandatory
	DESCRIPTION
		" VPI.  Upon setting/deleting end-point,  don't care about it. "
	--
	::= { connOamOpe 9 }

connOamOpeVci1	OBJECT-TYPE
	SYNTAX	INTEGER
	ACCESS	read-write
	STATUS	mandatory
	DESCRIPTION
		" VCI."
	--
	::= { connOamOpe 10 }

connOamOpeVci2	OBJECT-TYPE
	SYNTAX	INTEGER
	ACCESS	read-write
	STATUS	mandatory
	DESCRIPTION
		" VCI. "
	--
	::= { connOamOpe 11 }

connOamTable	OBJECT-TYPE
	SYNTAX	SEQUENCE OF ConnOamEntry
	ACCESS	not-accessible
	STATUS	mandatory
	DESCRIPTION
		" OAM End-point,  Connecting-point indication table "
	--
	::= { connOam 2 }

connOamEntry	OBJECT-TYPE
	SYNTAX	ConnOamEntry
	ACCESS	not-accessible
	STATUS	mandatory
	DESCRIPTION
		" OAM End-point,  Connecting-point indication entry "
	--
	INDEX	{ connOamPort,  connOamIndex }
	::= { connOamTable 1 }

ConnOamEntry ::=
	SEQUENCE {
		connOamPort		INTEGER, 
		connOamIndex		INTEGER, 
		connOamContrastPort	INTEGER, 
		connOamVpi		INTEGER, 
		connOamContrastVpi	INTEGER, 
		connOamVci		INTEGER, 
		connOamContrastVci	INTEGER, 
		connOamPoint		INTEGER, 
		connOamMode		INTEGER, 
		connOamSection		INTEGER, 
		connOamStatus		INTEGER, 
		connOamDefectType	INTEGER, 
		connOamDefectNodeID	OCTET STRING
	}

connOamPort	OBJECT-TYPE
	SYNTAX	INTEGER
	ACCESS	not-accessible
	STATUS	mandatory
	DESCRIPTION
		" Line number"
	--
	::= { connOamEntry 1 }

connOamIndex	OBJECT-TYPE
	SYNTAX	INTEGER (1..144)
	ACCESS	not-accessible
	STATUS	mandatory
	DESCRIPTION
		"OAM End-point / Connecting-point Index."
	::= { connOamEntry 2 }

connOamContrastPort	OBJECT-TYPE
	SYNTAX	INTEGER
	ACCESS	read-only
	STATUS	mandatory
	DESCRIPTION
		" Line number of the opposite line. For End-point,  -1."
	--
	::= { connOamEntry 3 }

connOamVpi	OBJECT-TYPE
	SYNTAX	INTEGER
	ACCESS	read-only
	STATUS	mandatory
	DESCRIPTION
		"VPI."
	::= { connOamEntry 4 }

connOamContrastVpi	OBJECT-TYPE
	SYNTAX	INTEGER
	ACCESS	read-only
	STATUS	mandatory
	DESCRIPTION
		" Opposite VPI.  For End-point,  -1. "
	--
	::= { connOamEntry 5 }

connOamVci	OBJECT-TYPE
	SYNTAX	INTEGER
	ACCESS	read-only
	STATUS	mandatory
	DESCRIPTION
		" VCI.  For the f4 level,  -1."
	--
	::= { connOamEntry 6 }

connOamContrastVci	OBJECT-TYPE
	SYNTAX	INTEGER
	ACCESS	read-only
	STATUS	mandatory
	DESCRIPTION
		" Opposite VCI."
	--
	::= { connOamEntry 7 }

connOamPoint	OBJECT-TYPE
	SYNTAX	INTEGER {
			end-point        (1), 
			connecting-point (2)
		}
	ACCESS	read-only
	STATUS	mandatory
	DESCRIPTION
		"End-point / Connecting-point."
	::= { connOamEntry 8 }

connOamMode	OBJECT-TYPE
	SYNTAX	INTEGER {
			f4 (1), 
			f5 (2)
		}
	ACCESS	read-only
	STATUS	mandatory
	DESCRIPTION
		" Mode. F4 (VP level)/f5 (VC level). "
	--
	::= { connOamEntry 9 }

connOamSection	OBJECT-TYPE
	SYNTAX	INTEGER {
			segment    (1), 
			end-to-end (2)
		}
	ACCESS	read-only
	STATUS	mandatory
	DESCRIPTION
		" Point between segments/End-to-End point."
	--
	::= { connOamEntry 10 }

connOamStatus	OBJECT-TYPE
	SYNTAX	INTEGER {
			other (1), 	-- Not related status indication.
					-- (The connection is connecting-point)
			normal (2), 	-- Normal line.
			receive-AIS (3), -- AIS cell is received.
			receive-RDI (4), -- RDI cell is received.
			failure (5)	-- Receive fault occurred.
		}
	ACCESS	read-only
	STATUS	mandatory
	DESCRIPTION
		" Receive status of end-point."
	--
	::= { connOamEntry 11 }

connOamDefectType	OBJECT-TYPE
	SYNTAX	INTEGER {
			normal (1), 
			los (2), 
			lof (3), 
			loc (4), 
			ais-path (5), 
			ais-section (6), 
			yellow-section (7), 	-- notSupported
			yellow-path (8), 	-- notSupported
			lop (9), 
			ais (10), 
			payload-all-one (11), 
			rai (12), 		-- notSupported
			oof (13) , 
			idle (14), 		-- notSupported
			rdi (15), 		-- notSupported
			plcp-oof (16), 
			plcp-lof (17), 
			plcp-yellow (18), 	-- notSupported
			red(19)
		}
	ACCESS	read-only
	STATUS	mandatory
	DESCRIPTION
		" Fault cause in the receive cell.
		For Connecting-point,  return 'normal (1)'."
	--
	--
	::= { connOamEntry 12 }

connOamDefectNodeID	OBJECT-TYPE
	SYNTAX	OCTET STRING( SIZE (13) )
	ACCESS	read-only
	STATUS	mandatory
	DESCRIPTION
		" Node ID of the Switch which sends alarm transfer cells.
		For connecting-point,  return '0 length string'."
	--
	--
	::= { connOamEntry 13 }

connLoop		OBJECT IDENTIFIER ::= { conn 8 }

connLoopOpe	OBJECT IDENTIFIER ::= { connLoop 1 }

	--
	--

	--
	--
	--
	--
	--
	--
	--
	--
	--
	--
	--
	--
	--
	--
	--
	--
	--
	--
	--
	--

	--
	--

	--
	--
	--
	--
	--
	--
	--

	--
	--
	--
	--
	--
	--
	--

	--
	--
	--
	--
	--
	--
	--
	--
	--

	--

	--
	--
	--
	--

	--

	--

	--
	--

	--

	--
	--

	--
	--
	--
	--
	--
	--
	--
	--
	--
	--
	--
	--
	--
	--
	--
	--
	--

	--

	--
	--

connLoopOpeStatus	OBJECT-TYPE
	SYNTAX	INTEGER	{
			allocate (1), 	--
			action   (2), 	--
			endtest  (3), 	--
			free     (4)	--
		}
	ACCESS	read-write
	STATUS	mandatory
	DESCRIPTION
		""
	--
	::= { connLoopOpe 1 }

connLoopOpeCause	OBJECT-TYPE
	SYNTAX	INTEGER	{
			succeed          (1),  --
			abort            (2),  --
			other            (3),  --
			vpivciOutOfRange (4),  --
			parameterFailed  (5),  --
			admindown        (6),  --
			nonePkg          (7),  --
			noneBuffer2      (8),  --
			lineLoopback     (9),  --
			resetSlot        (10),  --
			noneLoopBackId   (11),  --
			execute          (12) --
		}
	ACCESS	read-only
	STATUS	mandatory
	DESCRIPTION
		""
	--
	::= { connLoopOpe 2 }

connLoopOpeMode	OBJECT-TYPE
	SYNTAX	INTEGER	{
			f4 (1), 
			f5 (2)
		}
	ACCESS	read-write
	STATUS	mandatory
	DESCRIPTION
		"F4 (VP level)/f5 (VC level)."
	--
	::= { connLoopOpe 3 }

connLoopOpeBase	OBJECT-TYPE
	SYNTAX	INTEGER	{
			segment (1), 
			end-end (2)
		}
	ACCESS	read-write
	STATUS	mandatory
	DESCRIPTION
		""
	--
	::= { connLoopOpe 4 }

connLoopOpeLoopBackPointNodeId	OBJECT-TYPE
	SYNTAX	OCTET STRING ( SIZE (16) )
	ACCESS	read-write
	STATUS	mandatory
	DESCRIPTION
		""
	--
	::= { connLoopOpe 5 }

connLoopOpeCorrelationTag	OBJECT-TYPE
	SYNTAX	OCTET STRING ( SIZE (4) )
	ACCESS	read-write
	STATUS	mandatory
	DESCRIPTION
		""
	--
	::= { connLoopOpe 6 }

connLoopOpeCount	OBJECT-TYPE
	SYNTAX	INTEGER (1..16)
	ACCESS	read-write
	STATUS	mandatory
	DESCRIPTION
		""
	--
	::= { connLoopOpe 7 }

connLoopOpePort	OBJECT-TYPE
	SYNTAX	INTEGER
	ACCESS	read-write
	STATUS	mandatory
	DESCRIPTION
		""
	--
	::= { connLoopOpe 8 }

connLoopOpeVpi	OBJECT-TYPE
	SYNTAX	INTEGER
	ACCESS	read-write
	STATUS	mandatory
	DESCRIPTION
		""
	--
	::= { connLoopOpe 9 }

connLoopOpeVci	OBJECT-TYPE
	SYNTAX	INTEGER
	ACCESS	read-write
	STATUS	mandatory
	DESCRIPTION
		""
	--
	--
	::= { connLoopOpe 10 }

connLoopOpeNormalEndCount	OBJECT-TYPE
	SYNTAX	INTEGER
	ACCESS	read-only
	STATUS	mandatory
	DESCRIPTION
		""
	--
	::= { connLoopOpe 11 }

connLoopOpeAbnormalEndCount	OBJECT-TYPE
	SYNTAX	INTEGER
	ACCESS	read-only
	STATUS	mandatory
	DESCRIPTION
		""
	--
	::= { connLoopOpe 12 }

connLoopOpeAbortCount	OBJECT-TYPE
	SYNTAX	INTEGER
	ACCESS	read-only
	STATUS	mandatory
	DESCRIPTION
		""
	--
	::= { connLoopOpe 13 }

connLoopOpeLoopBackPointIdLength	OBJECT-TYPE
	SYNTAX	INTEGER
	ACCESS	read-write
	STATUS	mandatory
	DESCRIPTION
		""
	--
	--
	::= { connLoopOpe 14 }

connProfile		OBJECT IDENTIFIER ::= { conn 9 }

	--	Type used for connProfile.

		ConnProfileIndex ::= INTEGER
		--	Index of connProfileTable.
		--

	--	<>

	--	1. Get connProfileIndex
        --	The manager obtains the Index of connProfileTable 
	--	(connProfileIndex),  by getting connProfileIndexNext.

	--	2. Set createAndWait
	--	Set connProfileRowStatus to createAndWait,  using the 
	--	obtained connProfileIndex as Index.  Then,  the agent set 
	--	each parameter to the default value and make 
	--	connProfileRowStatus to notRedy.
	--	Default values are stated below.
	--		connProfileTrafficType : traffic-UBR(5)
	--		connProfileName        : None (0 length string)
	--		connProfileParam1      : None (-1)
	--		connProfileParam2      : None (-1)
	--		connProfileParam3      : None (-1)
	--		connProfileParam4      : off(1)
	--		In this table,  only one non-active row (i.e.,  a row 
	--		whose status is notReady or notInservice) can exist
	--		at a time.
	--	3. Set each parameter
	--	For parameters which don't have default values or default 
	--	values should not be set to,  set them to proper values.
	--	The agent changes connProfileRowStatus to notInService,  if 
	--	connProfileTrafficType,  connProfileName and 
	--	connProfileParam4 have been set.
	--	Required parameters differ according to the traffic type.
	--	The traffic types and the required parameters are stated
	--	as below.
	--	("connProfile" part is omitted.)

	--	 =======================================================
	--	|TrafficType	||Name	|Param1	|Param2	|Param3	|Param4	|
	--	|=======================================================|
	--	|CBR		||  *	|   *	|	|	|   *	|
	--	|- - - - - - - - - - - - - - - - - - - - - - - - - - - -|
	--	|rt-VBR		||  *	|   *	|   *	|   *	|   *	|
	--	|- - - - - - - - - - - - - - - - - - - - - - - - - - - -|
	--	|nrt-VBR	||  *	|   *	|   *	|   *	|   *	|
	--	|- - - - - - - - - - - - - - - - - - - - - - - - - - - -|
	--	|ABR		||  *	|   *	|	|	|   *   |
	--	|- - - - - - - - - - - - - - - - - - - - - - - - - - - -|
	--	|UBR		||  *	|   *	|	|	|   *	|
	--	 =======================================================
	--


	--	4. Set active
	--	The manager sets connProfileRowStatus to active.  Then,  
	--	the agent checks parameters and resources and registers
	--	the profiles.
 
	--	5. Get the result
	--	Get connProfileRowStatus,  and if it is active,  the profile 
	--	setting has successfully completed.  If it is notInService,  
	--	the setting has failed.  Get connProfileCause and see the cause.

	--	<>

	--	1. Set "destroy"
	--	Set connProfileRowStatus of the profile to be deleted, 
	--	to "destroy".
	--	Then,  the agent will delete the profile.

	--	2. Get the result
	--	If the deletion has successfully completed,  the object of 
	--	"get" subordinate to the connProfileTable of the designated 
	--	index becomes noSuchName.

	--	

	--
	--
	--
	--

	--
	--
	--
	--
	--

	--
	--
	--
	--
	--
	--
	--

	--
	--
	--

	--
	--
	--
	--
	--
	--

	--
	--

	--
	--
	--	 =======================================================
	--	|TrafficType	||Name	|Param1	|Param2	|Param3	|Param4	|
	--	|=======================================================|
	--	|CBR		||  *	|   *	|	|	|   *	|
	--	|- - - - - - - - - - - - - - - - - - - - - - - - - - - -|
	--	|rt-VBR		||  *	|   *	|   *	|   *	|   *	|
	--	|- - - - - - - - - - - - - - - - - - - - - - - - - - - -|
	--	|nrt-VBR	||  *	|   *	|   *	|   *	|   *	|
	--	|- - - - - - - - - - - - - - - - - - - - - - - - - - - -|
	--	|ABR		||  *	|   *	|	|	|   *   |
	--	|- - - - - - - - - - - - - - - - - - - - - - - - - - - -|
	--	|UBR		||  *	|   *	|	|	|   *	|
	--	 =======================================================
	--

	--
	--
	--
	--

	--
	--
	--
	--

	--

	--
	--
	--
	--

	--
	--
	--

connProfileIndexNext	OBJECT-TYPE
		SYNTAX	ConnProfileIndex
		ACCESS	read-only
		STATUS	mandatory
		DESCRIPTION
		"Shows the empty index value of connProfileTable(including 
		row of notReady,  notInService).
		If the number of profiles reaches the registration limit,  0. "
	--
	--
	--
	::= { connProfile 1 }

connProfileTable	OBJECT-TYPE
	SYNTAX	SEQUENCE OF ConnProfileEntry
	ACCESS	not-accessible
	STATUS	mandatory
	DESCRIPTION
		" Table to set/indicate the profile. "
	--
	::= { connProfile 2 }

connProfileEntry	OBJECT-TYPE
	SYNTAX	ConnProfileEntry
	ACCESS	not-accessible
	STATUS	mandatory
	DESCRIPTION
		" Entry of connProfileTable."
	--
	INDEX	{ connProfileIndex }
	::= { connProfileTable 1 }

ConnProfileEntry ::=
	SEQUENCE {
		connProfileIndex        ConnProfileIndex, 
		connProfileRowStatus    INTEGER, 
		connProfileCause        INTEGER, 
		connProfileTrafficType  INTEGER, 
		connProfileName         DisplayString, 
		connProfileParam1       INTEGER, 
		connProfileParam2       INTEGER, 
		connProfileParam3       INTEGER, 
		connProfileParam4       INTEGER
	}

connProfileIndex	OBJECT-TYPE
	SYNTAX	ConnProfileIndex
	ACCESS	not-accessible
	STATUS	mandatory
	DESCRIPTION
		" Index value of connProfileTable."
	--
	::= { connProfileEntry 1 }

connProfileRowStatus	OBJECT-TYPE
	SYNTAX	INTEGER	{
			active        (1), 
			notInService  (2), 	-- read-only
			notReady      (3), 	-- read-only
			createAndGo   (4), 	-- notSupported
			createAndWait (5), 
			destroy       (6)
		}
	ACCESS	read-write
	STATUS	mandatory
	DESCRIPTION
		" Used to control rows of the table."
	--
	::= { connProfileEntry 2 }

connProfileCause	OBJECT-TYPE
	SYNTAX	INTEGER	{
			rowExisting(1), 	    -- default value
			otherFailure(2),     -- NG cause other than stated below.
			inconsistentEpd(3),  -- Traffic type is inconsistent
					    -- with EPD value.
			parameterNotEnough(4),  -- Parameter is not enough.
			alreadyExist(5),     -- Duplicate profile name exist.
					    -- (content is same)	
			duplicateName(6),    -- Duplicate profile name exist.
					    -- (content is different)
			inconsistentRate(7) -- Rate designation is inconsistent.
		}
	ACCESS	read-only
	STATUS	mandatory
	DESCRIPTION
		" The result of Profile setting processing."
	--
	::= { connProfileEntry 3 }

connProfileTrafficType	OBJECT-TYPE
	SYNTAX	INTEGER	{
			traffic-CBR     (1), 
			traffic-rt-VBR  (2), 
			traffic-nrt-VBR (3), 
			traffic-ABR     (4), 
			traffic-UBR     (5)
		}
	ACCESS	read-write
	STATUS	mandatory
	DESCRIPTION
		"Traffic Type."
	::= { connProfileEntry 4 }

connProfileName	OBJECT-TYPE
	SYNTAX	DisplayString (SIZE(0|1..10))
	ACCESS	read-write
	STATUS	mandatory
	DESCRIPTION
		" Profile name.
		Available characters: alphanumeric characters
		0 length string is only read."
	--
	--
	--
	::= { connProfileEntry 5 }

--
--
--

--
--
--

connProfileParam1	OBJECT-TYPE
	SYNTAX	INTEGER (-1|1..1412830)
	ACCESS	read-write
	STATUS	mandatory
	DESCRIPTION
		" For ph1/2-buffer,  peek cell rate [cell/sec].
		If it is invalid,  -1.
		"
	--
	--
	--
	::= { connProfileEntry 6 }

connProfileParam2	OBJECT-TYPE
	SYNTAX	INTEGER (-1|1..1412830)
	ACCESS	read-write
	STATUS	mandatory
	DESCRIPTION
		" For ph1/2-buffer,  Sustainable cell rate [cell/sec].
		Only nrt-VBR,  and rt-VBR are valid.
		If it is invalid,  -1. "
	--
	--
	--
	::= { connProfileEntry 7 }

connProfileParam3	OBJECT-TYPE
	SYNTAX	INTEGER (-1|1..1412830)
	ACCESS	read-write
	STATUS	mandatory
	DESCRIPTION
		" For ph1/2-buffer,  Maximum burst size [cell].
		Only nrt-VBR,  and rt-VBR are valid.
		If it is invalid,  -1. "
	--
	--
	--
	::= { connProfileEntry 8 }

connProfileParam4	OBJECT-TYPE
	SYNTAX	INTEGER	{
			off  (1), 
			on (2)
		}
	ACCESS	read-write
	STATUS	mandatory 
	DESCRIPTION
		" For ph1/2-buffer,  EPD function flag.
		  If it is other than ABR,  UBR,  off,  only. "
	--
	--
	::= { connProfileEntry 9 }

connProfileName2Index	OBJECT-TYPE
	SYNTAX	DisplayString (SIZE(0|1..10))
	ACCESS	read-write
	STATUS	mandatory
	DESCRIPTION
		" Equivalent to connProfileName "
	--
	::= { connProfile 3 }

connProfileName2IndexResult	OBJECT-TYPE
	SYNTAX	ConnProfileIndex
	ACCESS	read-only
	STATUS	mandatory
	DESCRIPTION
		" Shows the index of the row whose connProfileRowStatus in 
		connProfileTable,  corresponding to connProfileName2Index,  
		is active.  If the corresponding row does not exist,  0. "
	--
	--
	--
	::= { connProfile 4 }

connSvcTable	OBJECT-TYPE
	SYNTAX	SEQUENCE OF ConnSvcEntry
	ACCESS	not-accessible
	STATUS	mandatory
	DESCRIPTION
		""
	--
	::= { conn 10 }

connSvcEntry	OBJECT-TYPE
	SYNTAX	ConnSvcEntry
	ACCESS	not-accessible
	STATUS	mandatory
	DESCRIPTION
		""
	--
	INDEX	{ ifIndex,  connSvcIndex }
	::= { connSvcTable 1 }

ConnSvcEntry ::=
	SEQUENCE {
		connSvcIndex
			INTEGER, 
		connSvcInf
			Opaque
	}

connSvcIndex	OBJECT-TYPE
	SYNTAX	INTEGER
	ACCESS	not-accessible
	STATUS	mandatory
	DESCRIPTION
		""
	--
	::= { connSvcEntry 1 }

connSvcInf	OBJECT-TYPE
	SYNTAX	Opaque 
	ACCESS	read-only 
	STATUS	mandatory
	DESCRIPTION
		""

	::= { connSvcEntry 2 }


connCe			OBJECT IDENTIFIER ::= { conn 11 }

connCeVc		OBJECT IDENTIFIER ::= { connCe 1 }

	--
--

	--

	--
	--
	--
	--

	--
	--
	--

	--
	--
	--
	--
	--
	--
	--

	--
	--
	--

	--
	--
	--
	--
	--
	--
	--
	--
	--
	--
	--
	--
	--
	--
	--
	--
	--
	--
	--
	--
	--
	--
	--
	--
	--
	--
	--
	--
	--
	--
	--
	--
	--
	--
	--
	--
	--
	--
	--
	--
	--

	--
	--
	--

	--
	--
	--
	--

	--
	--
	--
	--
	--
	--
	--
	--
	--
	--
	--
	--

	--
	--
	--
	--

	--

	--
	--
	--
	--

	--
	--
	--


connCeVcTable			OBJECT-TYPE
	SYNTAX SEQUENCE OF ConnCeVcEntry
	ACCESS not-accessible
	STATUS mandatory
	DESCRIPTION
		""
	--
	::= { connCeVc 1 }

connCeVcEntry			OBJECT-TYPE
	SYNTAX ConnCeVcEntry
	ACCESS not-accessible
	STATUS mandatory
	DESCRIPTION
		""
	--
	INDEX{ connCeVcPort,  connCeVcVci }
	::= { connCeVcTable 1 }

ConnCeVcEntry ::=
	SEQUENCE	{
		connCeVcPort			INTEGER, 
		connCeVcVci			INTEGER, 
		connCeVcRowStatus		INTEGER, 
		connCeVcCause			INTEGER, 
		connCeVcDirection		INTEGER, 
		connCeVcUpPartialFillSize	INTEGER, 
		connCeVcDownPartialFillSize	INTEGER, 
		connCeVcCondition		INTEGER, 
		connCeVcCDVT			INTEGER, 
		connCeVcUpPCR			INTEGER, 
		connCeVcDownPCR			INTEGER, 
		connCeVcUpTimeSlot1		INTEGER, 
		connCeVcDownTimeSlot1		INTEGER, 
		connCeVcUpTimeSlot2		INTEGER, 
		connCeVcDownTimeSlot2		INTEGER, 
		connCeVcUpTimeSlot3		INTEGER, 
		connCeVcDownTimeSlot3		INTEGER
	}

connCeVcPort			OBJECT-TYPE
	SYNTAX INTEGER
	ACCESS not-accessible
	STATUS mandatory
	DESCRIPTION
		"Line number."
	--
	::= { connCeVcEntry 1 }

connCeVcVci			OBJECT-TYPE
	SYNTAX INTEGER	(32..383)
	ACCESS not-accessible
	STATUS mandatory
	DESCRIPTION
		"VCI value.
		"
	--
	--
	::= { connCeVcEntry 2 }

connCeVcRowStatus			OBJECT-TYPE
	SYNTAX INTEGER	{
			active		(1), 
			notInService	(2), 	-- read-only
			notReady	(3), 	-- read-only
			createAndGo	(4), 	-- notSupported
			createAndWait	(5), 
			destroy		(6)
	}
	ACCESS read-write
	STATUS mandatory
	DESCRIPTION
		" Used to control rows of the table."
	--
	::= { connCeVcEntry 3 }

connCeVcCause			OBJECT-TYPE
	SYNTAX INTEGER	{
		rowExisting(1), 		-- default
		otherFailure(2), 	-- NG cause other than stated below.
		parameterNotEnough(3), 	-- Parameter is not enough.
		illegalpkg(4), 		-- pkg other than CES.
		vcsOverFllow(5), 	-- The number of registration of Vc is
                                        -- over the limit.
		tssOverFllow(6), 	-- The number of registration of TS is
                                        -- over the limit.
		alreadyAssignedTs(7), 	--
		inconsistentTss(8), 	--
					--
		illegalTimeslot(9), 	--
					--
		illegalPort(10), 	--
		illegalVci(11), 		-- Illegal VCI value.
		illegalUpPartialFillSize(12), 	--
						--
		illegalDownPartialFillSize(13), 	--
						--
		illegalCdvt(14)		--
	}
	ACCESS read-only
	STATUS mandatory
	DESCRIPTION
		" The result of CEVC setting processing."
	--
	::= { connCeVcEntry 4 }

connCeVcDirection		OBJECT-TYPE
	SYNTAX INTEGER {
			bi	(1), 	-- default
			up	(2), 
			down	(3)
	}
	ACCESS read-write
	STATUS mandatory
	DESCRIPTION
		""
	--
	::= { connCeVcEntry 5 }

connCeVcUpPartialFillSize	OBJECT-TYPE
	SYNTAX INTEGER (-1|0..47)	-- default -1
	ACCESS read-write
	STATUS mandatory
	DESCRIPTION
		""
	--
	--
	--
	::= { connCeVcEntry 6 }

connCeVcDownPartialFillSize	OBJECT-TYPE
	SYNTAX INTEGER (-1|0..47)	-- default -1
	ACCESS read-write
	STATUS mandatory
	DESCRIPTION
		""
	--
	--
	--
	::= { connCeVcEntry 7 }

connCeVcCondition		OBJECT-TYPE
	SYNTAX INTEGER	(-1|0..255)	-- default -1
	ACCESS read-write
	STATUS mandatory
	DESCRIPTION
		"Condtion date."
	--
	::= { connCeVcEntry 8 }

connCeVcCDVT			OBJECT-TYPE
	SYNTAX INTEGER	(-1|1..7218)	-- default -1
	ACCESS read-write
	STATUS mandatory
	DESCRIPTION
		"CDVT value.
			
		+----------------------+----------+------------+
		|pkg type| str mode    |CDVT range| unit of    |
		|        |             |          |  setting   |
		================================================
		| CE-J2  | unstructure | 1..73    | 125sec   |
		|        +-------------+----------+------------+
		|        | structure   | 1..7218  | 125sec   |
		+--------+-------------+----------+------------+
		| CE-DS1 | unstructure | 1..255   | 165.8sec |
		|        +-------------+----------+------------+
		|        | structure   | 1..191   | 125sec   |
		+--------+-------------+----------+------------+
		| CE-E1  | unstructure | 1..255   | 124.5sec |
		|        +-------------+----------+------------+
		|        | structure   | 1..255   | 125sec   |
		+--------+-------------+----------+------------+
		| CE-DS3 | unstructure | 1..255   | 5.7sec   |
		+--------+-------------+----------+------------+
		"
	--
	::= { connCeVcEntry 9 }

connCeVcUpPCR			OBJECT-TYPE
	SYNTAX INTEGER	(-1|0..118979)	-- default -1
	ACCESS read-only
	STATUS mandatory
	DESCRIPTION
		""
	--
	::= { connCeVcEntry 10 }

connCeVcDownPCR			OBJECT-TYPE
	SYNTAX INTEGER	(-1|0..118979)	--
	ACCESS read-only
	STATUS mandatory
	DESCRIPTION
		""
	--
	::= { connCeVcEntry 11 }

connCeVcUpTimeSlot1		OBJECT-TYPE
	SYNTAX INTEGER
	ACCESS read-write
	STATUS mandatory
	DESCRIPTION
		""
	--
	--
	--
	--
	--
	--
	--
	--
	--
        --
        --
        --
	::= { connCeVcEntry 12 }

connCeVcDownTimeSlot1		OBJECT-TYPE
	SYNTAX INTEGER
	ACCESS read-write
	STATUS mandatory
	DESCRIPTION
		""
	--
	--
	::= { connCeVcEntry 13 }

connCeVcUpTimeSlot2		OBJECT-TYPE
	SYNTAX INTEGER
	ACCESS read-write
	STATUS mandatory
	DESCRIPTION
		""
	--
	--
	::= { connCeVcEntry 14 }

connCeVcDownTimeSlot2		OBJECT-TYPE
	SYNTAX INTEGER
	ACCESS read-write
	STATUS mandatory
	DESCRIPTION
		""
	--
	--
	::= { connCeVcEntry 15 }

connCeVcUpTimeSlot3		OBJECT-TYPE
	SYNTAX INTEGER
	ACCESS read-write
	STATUS mandatory
	DESCRIPTION
		""
	--
	--
	::= { connCeVcEntry 16 }

connCeVcDownTimeSlot3		OBJECT-TYPE
	SYNTAX INTEGER
	ACCESS read-write
	STATUS mandatory
	DESCRIPTION
		""
	--
	--
	::= { connCeVcEntry 17 }



connFr			OBJECT IDENTIFIER ::= { conn 12 }

connFrDlci		OBJECT IDENTIFIER ::= { connFr 1 }

	--
	--
	--
	--
	--
	--
	--
	--
	--
	--
	--
	--
	--
	--
	--
	--
	--
	--
	--
	--
	--
	--
	--
	--
	--
	--
	--
	--
	--
	--
	--
	--
	--
	--
	--
	--
	--
	--
	--
	--

connFrDlciTable		OBJECT-TYPE
	SYNTAX	SEQUENCE OF ConnFrDlciEntry
	ACCESS	not-accessible
	STATUS	mandatory
	DESCRIPTION
		""
	--
	--
	::= { connFrDlci 1 }

connFrDlciEntry		OBJECT-TYPE
	SYNTAX ConnFrDlciEntry
	ACCESS not-accessible
	STATUS mandatory
	DESCRIPTION
		"Entry of connFrDlciTable."
	--
	INDEX{ connFrDlciPort ,  connFrDlciIndex }
	::= { connFrDlciTable 1 }

ConnFrDlciEntry ::=
	SEQUENCE	{
		connFrDlciPort		INTEGER, 
		connFrDlciIndex		INTEGER, 
		connFrDlciRowStatus	INTEGER, 
		connFrDlciCause		INTEGER, 
		connFrDlciFrProfile	DisplayString, 
		connFrDlciPCR		INTEGER, 
		connFrDlciSCR		INTEGER, 
		connFrDlciMBS		INTEGER
	}

connFrDlciPort		OBJECT-TYPE
	SYNTAX	INTEGER (1..64)
	ACCESS	not-accessible
	STATUS	mandatory
	DESCRIPTION
		"Line number."
	--
	::= { connFrDlciEntry 1 }

connFrDlciIndex		OBJECT-TYPE
	SYNTAX	INTEGER (16..1007)
	ACCESS	not-accessible
	STATUS	mandatory
	DESCRIPTION
		"DLCI number."
	--
	::= { connFrDlciEntry 2 }

connFrDlciRowStatus	OBJECT-TYPE
	SYNTAX	INTEGER {
		active (1), 
		notInService (2), 	--
		notReady (3), 		--
		createAndGo(4), 		--
		createAndWait(5), 
		destroy(6)
	}
	ACCESS	read-write
	STATUS	mandatory
	DESCRIPTION
		" Used to control rows of the table."
	--
	::= { connFrDlciEntry 3 }

connFrDlciCause		OBJECT-TYPE
	SYNTAX	INTEGER {
		rowExisting (1), 	--
		otherFailure (2), 	--
		noFrProfile (3), 	--
		inconsistentInterWorking (4), 	
					--
					--
		totalCIROverFlow (5), 	--
					--
		lineDiagnosticsFailure (6), 
					--
		illegalPort (7), 	--
		illegalDlci (8), 	--
		pvcsOverFlow (9)	--
	}
	ACCESS	read-only
	STATUS	mandatory
	DESCRIPTION
		""
	--
	::= { connFrDlciEntry 4 }

connFrDlciFrProfile	OBJECT-TYPE
	SYNTAX	DisplayString (SIZE(0|1..10))
	ACCESS	read-write
	STATUS	mandatory
	DESCRIPTION
		""
	--
	--
	::= { connFrDlciEntry 5 }

connFrDlciPCR	OBJECT-TYPE
	SYNTAX	INTEGER
	ACCESS	read-only
	STATUS	mandatory
	DESCRIPTION
		"Peak Cell Rate[cell/sec].
		"
	--
	::= { connFrDlciEntry 6 }

connFrDlciSCR	OBJECT-TYPE
	SYNTAX	INTEGER
	ACCESS	read-only
	STATUS	mandatory
	DESCRIPTION
		"Sustainable Cell Rate[cell/sec].
		"
	--
	::= { connFrDlciEntry 7 }

connFrDlciMBS	OBJECT-TYPE
	SYNTAX	INTEGER
	ACCESS	read-only
	STATUS	mandatory
	DESCRIPTION
		"Maximum Burst Size[cell].
		"
	--
	::= { connFrDlciEntry 8 }


--

connFrProfile		OBJECT IDENTIFIER ::= { connFr 2 }

	ConnFrProfileIndex ::= INTEGER
	--


	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--


connFrProfileIndexNext	OBJECT-TYPE
	SYNTAX ConnFrProfileIndex
	ACCESS read-only
	STATUS mandatory
	DESCRIPTION
		""
	--
	--
	::= { connFrProfile 1 }

connFrProfileTable		OBJECT-TYPE
	SYNTAX SEQUENCE  OF  ConnFrProfileEntry
	ACCESS not-accessible
	STATUS mandatory
	DESCRIPTION
		""
	--
	::= { connFrProfile 2 }

connFrProfileEntry		OBJECT-TYPE
	SYNTAX ConnFrProfileEntry
	ACCESS not-accessible
	STATUS mandatory
	DESCRIPTION
		"Entry of connFrProfileTable."
	--
	INDEX { connFrProfileIndex }
	::= { connFrProfileTable 1 }

ConnFrProfileEntry ::=
	SEQUENCE {
		connFrProfileIndex		ConnFrProfileIndex, 
		connFrProfileRowStatus		INTEGER, 
		connFrProfileCause		INTEGER, 
		connFrProfileName		DisplayString, 
		connFrProfileInterworkingType	INTEGER, 
		connFrProfileCIR		INTEGER, 
		connFrProfileDEtoCLP		INTEGER, 
		connFrProfileCLPValue		INTEGER, 
		connFrProfileCLPtoDE		INTEGER, 
		connFrProfileDEValue		INTEGER, 
		connFrProfileCapsulationMode	INTEGER, 
		connFrProfileCongestionMode	INTEGER
	}

connFrProfileIndex			OBJECT-TYPE
	SYNTAX ConnFrProfileIndex 
	ACCESS not-accessible
	STATUS mandatory
	DESCRIPTION
		"Index of connFrProfileTable."
	--
	::= { connFrProfileEntry 1 }

connFrProfileRowStatus		OBJECT-TYPE
	SYNTAX INTEGER {
			active		(1), 
			notInService	(2), 	--
			notReady	(3), 	--
			createAndGo	(4), 	--
			createAndWait	(5), 
			destroy		(6)
	}
	ACCESS read-write
	STATUS mandatory
	DESCRIPTION
		" Used to control rows of the table."
	--
	::= { connFrProfileEntry 2 }

connFrProfileCause		OBJECT-TYPE
	SYNTAX INTEGER {
			rowExisting(1), 	--
			otherFailure(2),  --
			parameterNotEnough(3),  --
			alreadyExist(4),  --
						--
			duplicateName(5) --
						--
		}
	ACCESS	read-only
	STATUS	mandatory
	DESCRIPTION
		" The result of Frprofile setting processing."
	--
	::= { connFrProfileEntry 3 }

connFrProfileName		OBJECT-TYPE
	SYNTAX DisplayString (SIZE(0|1..10)) --
	ACCESS read-write
	STATUS mandatory
	DESCRIPTION
		"Frprofile name.
		Available characters: alphanumeric characters
		0 length string is only read."
	--
	--
	--
	::= { connFrProfileEntry 4 }

connFrProfileInterworkingType	OBJECT-TYPE
	SYNTAX INTEGER {
		network	(1), 	--
		service	(2)
	}
	ACCESS read-write
	STATUS mandatory
	DESCRIPTION
		"Interworking Type"
	::= { connFrProfileEntry 5 }

connFrProfileCIR		OBJECT-TYPE
	SYNTAX INTEGER (-1|1..1984)	--
	ACCESS read-write
	STATUS mandatory
	DESCRIPTION
		"CIR value."
	--
	::= { connFrProfileEntry 6 }

connFrProfileDEtoCLP		OBJECT-TYPE
	SYNTAX INTEGER {
		mode1		(1), 	--
		mode2		(2)
	}
	ACCESS read-write
	STATUS mandatory
	DESCRIPTION
		"DE to CLP mapping mode"
	--
	::= { connFrProfileEntry 7 }

connFrProfileCLPValue		OBJECT-TYPE
	SYNTAX INTEGER {
		notApplicable	(1), 	--
		on		(2), 
		off		(3)
	}
	ACCESS read-write
	STATUS mandatory
	DESCRIPTION
		"CLP Value.
		It's valid when connFrProfileDEtoCLP is mode2."
	--
	::= { connFrProfileEntry 8 }

connFrProfileCLPtoDE		OBJECT-TYPE
	SYNTAX INTEGER {
		mode1		(1), 	--
		mode2		(2)
	}
	ACCESS read-write
	STATUS mandatory
	DESCRIPTION
		"CLP to DE mapping mode."
	--
	::= { connFrProfileEntry 9 }

connFrProfileDEValue		OBJECT-TYPE
	SYNTAX INTEGER {
		notApplicable	(1), 	--
		on		(2), 
		off		(3)
	}
	ACCESS read-write
	STATUS mandatory
	DESCRIPTION
		"DE Value.
		It's valid when connFrProfileInterworkingType is service
		and connFrProfileCLPtoDE is mode2."
	--
	--
	::= { connFrProfileEntry 10 }

connFrProfileCapsulationMode	OBJECT-TYPE
	SYNTAX INTEGER {
		notApplicable	(1), 	--
		transparent 	(2), 
		translation	(3)
	}
	ACCESS read-write
	STATUS mandatory
	DESCRIPTION
		"Protocol encapsulation mode.
		It's valid when connFrProfileInterworkingType is service."
	--
	--
	::= { connFrProfileEntry 11 }

connFrProfileCongestionMode	OBJECT-TYPE
	SYNTAX INTEGER {
		notApplicable	(1), 	--
		mode1		(2), 
		mode2		(3)
	}
	ACCESS read-write
	STATUS mandatory
	DESCRIPTION
		"Congestion indication(Forward) mode.
		It's valid when connFrProfileInterworkingType is service."
	--
	--
	::= { connFrProfileEntry 12 }

connFrProfileName2Index           OBJECT-TYPE
	SYNTAX	DisplayString (SIZE(0|1..10))
	ACCESS	read-write
	STATUS	mandatory
	DESCRIPTION
		"Equivalent to connProfileName."
	--
	::= { connFrProfile 3 }

connFrProfileName2IndexResult           OBJECT-TYPE
	SYNTAX	ConnFrProfileIndex
	ACCESS	read-only
	STATUS	mandatory
	DESCRIPTION
		" Shows the index of the row whose connFrProfileRowStatus in 
		connFrProfileTable,  corresponding to connFrProfileName2Index,  
		is active.  If the corresponding row does not exist,  0. "
	--
	--
	--
	::= { connFrProfile 4 }

--

perfTrapEnable OBJECT-TYPE
	SYNTAX	INTEGER {
			enable(1), 	--
			disable(2)
		}
	ACCESS	read-write
	STATUS	mandatory
	DESCRIPTION
		"This object is used for disabling/enabling trap messages
		regarding the enterprise specific traps."
	--
	--
	::= { perf 1 }

perfIfTable OBJECT-TYPE
	SYNTAX	SEQUENCE OF PerfIfEntry
	ACCESS	not-accessible
	STATUS	mandatory
	DESCRIPTION
		"Table for showing the result of the performance monitoring 
		per line of the equipment. Up to 64 tables are available for 
		entry.
		Every line whose traffic is managed per line is provided with 
		an entry. "
	--
	--
	--
	::= { perf 2 }

perfIfEntry OBJECT-TYPE
	SYNTAX	PerfIfEntry
	ACCESS	not-accessible
	STATUS	mandatory
	DESCRIPTION
		"Entry of the line performance monitoring."
	--
	INDEX	{ perfIfIndex }
	::= { perfIfTable 1 }

PerfIfEntry ::=
	SEQUENCE {
		perfIfIndex
			INTEGER, 
		perfIfReceivedCells
			OCTET STRING, 
		perfIfReceivedCellsCounters
			Counter, 
		perfIfTransmittedCells
			OCTET STRING, 
		perfIfTransmittedCellsCounters
			Counter, 
		perfIfMisDelivdCells
			OCTET STRING, 
		perfIfMisDelivdCellsCounters
			Counter, 
		perfIfThresholdExcessCells
			OCTET STRING, 
		perfIfThresholdExcessCellsCounters
			Counter, 
		perfIfUpcErrorCells
			OCTET STRING, 
		perfIfUpcErrorCellsCounters
			Counter
	}

perfIfIndex OBJECT-TYPE
	SYNTAX	INTEGER
	ACCESS	not-accessible
	STATUS	mandatory
	DESCRIPTION
		"Line number."
	--
	::= { perfIfEntry 1 }

perfIfReceivedCells OBJECT-TYPE
        SYNTAX  OCTET STRING (SIZE(8))
        ACCESS  read-only
        STATUS  mandatory
        DESCRIPTION
                "The Number of the receive cells of line port.
		(64 bit applicable)"
	--
        ::= { perfIfEntry 2 }

perfIfReceivedCellsCounters OBJECT-TYPE
        SYNTAX  Counter
        ACCESS  read-only
        STATUS  mandatory
        DESCRIPTION
                "The Number of the receive cells of line port.
		(32 bit applicable)."
	--
        ::= { perfIfEntry 3 }

perfIfTransmittedCells OBJECT-TYPE
        SYNTAX  OCTET STRING (SIZE(8))
        ACCESS  read-only
        STATUS  mandatory
        DESCRIPTION
                "The Number of the transmit cells of line port.
		(64 bit applicable)."
	--
        ::= { perfIfEntry 4 }

perfIfTransmittedCellsCounters OBJECT-TYPE
        SYNTAX  Counter
        ACCESS  read-only
        STATUS  mandatory
        DESCRIPTION
                "The Number of the transmit cells of line port.
		(32 bit applicable)."
	--
        ::= { perfIfEntry 5 }

perfIfMisDelivdCells OBJECT-TYPE
        SYNTAX  OCTET STRING (SIZE(8))
        ACCESS  read-only
        STATUS  mandatory
        DESCRIPTION
		"The Number of the undefined cells of line port.
		(64 bit applicable)."
	--
        ::= { perfIfEntry 8 }

perfIfMisDelivdCellsCounters OBJECT-TYPE
        SYNTAX  Counter
        ACCESS  read-only
        STATUS  mandatory
        DESCRIPTION
		"The Number of the undefined cells of line port.
		(32 bit applicable)."
	--
        ::= { perfIfEntry 9 }

perfIfThresholdExcessCells OBJECT-TYPE
        SYNTAX  OCTET STRING (SIZE(8))
        ACCESS  read-only
        STATUS  mandatory
        DESCRIPTION
                "Number of the threshold excess cells (64 bit applicable)."
	--
        ::= { perfIfEntry 10 }

perfIfThresholdExcessCellsCounters OBJECT-TYPE
        SYNTAX  Counter
        ACCESS  read-only
        STATUS  mandatory
        DESCRIPTION
                "Number of the threshold excess cells (32 bit applicable)."
	--
        ::= { perfIfEntry 11 }

perfIfUpcErrorCells OBJECT-TYPE
        SYNTAX  OCTET STRING (SIZE(8))
        ACCESS  read-only
        STATUS  mandatory
        DESCRIPTION
                "Number of the UPC error cells (64 bit applicable)."
	--
        ::= { perfIfEntry 12 }

perfIfUpcErrorCellsCounters OBJECT-TYPE
        SYNTAX  Counter
        ACCESS  read-only
        STATUS  mandatory
        DESCRIPTION
                "Number of the UPC error cells (32 bit applicable)."
	--
        ::= { perfIfEntry 13 }

perfIfSlotTable	OBJECT-TYPE
	SYNTAX	SEQUENCE OF PerfIfSlotEntry
	ACCESS	not-accessible
	STATUS	mandatory
	DESCRIPTION
		 "Table for showing the number of cells of the traffic and 
		 performance per line card of the equipment.
		 Up to 16 tables are available for entry.
		 Every line whose traffic is managed per slot is provided 
		 with an entry.
		 The object which becomes invalid by the line card is always 0."
	--
	--
	--
	--
	--
	--
	::= { perf 3 }

perfIfSlotEntry	OBJECT-TYPE
	SYNTAX	PerfIfSlotEntry
	ACCESS	not-accessible
	STATUS	mandatory
	DESCRIPTION
		"Entry of traffic/performance per line card."
	--
	INDEX	{ slotIfConfIndex }
	::= { perfIfSlotTable 1 }

PerfIfSlotEntry ::=
	SEQUENCE {
		perfIfSlotReceivedCells
			OCTET STRING, 
		perfIfSlotTransmittedCells
			OCTET STRING, 
		perfIfSlotInDropCells
			OCTET STRING, 
		perfIfSlotReceivedCellsCounters
			Counter, 
		perfIfSlotTransmittedCellsCounters
			Counter, 
		perfIfSlotInDropCellsCounters
			Counter, 
		perfIfSlotHCThresholdExcessCells
			OCTET STRING, 
		perfIfSlotThresholdExcessCells
			Counter, 
		perfIfSlotHCUpcErrorCells
			OCTET STRING, 
		perfIfSlotUpcErrorCells
			Counter

	}

perfIfSlotReceivedCells OBJECT-TYPE
	SYNTAX	OCTET STRING (SIZE(8))
	ACCESS	read-only
	STATUS	mandatory
	DESCRIPTION
		"The number of receive cells."
	--
	::= { perfIfSlotEntry 1 }

perfIfSlotTransmittedCells OBJECT-TYPE
	SYNTAX	OCTET STRING (SIZE(8))
	ACCESS	read-only
	STATUS	mandatory
	DESCRIPTION
		"The number of transmit cells."
	--
	::= { perfIfSlotEntry 2 }

perfIfSlotInDropCells OBJECT-TYPE
	SYNTAX	OCTET STRING (SIZE(8))
	ACCESS	read-only
	STATUS	mandatory
	DESCRIPTION
		"The number of receive drop cells."
	--
	::= { perfIfSlotEntry 3 }

	--
	--

perfIfSlotReceivedCellsCounters OBJECT-TYPE
	SYNTAX	Counter
	ACCESS	read-only
	STATUS	mandatory
	DESCRIPTION
		"The number of receive cells."
	--
	::= { perfIfSlotEntry 5 }

perfIfSlotTransmittedCellsCounters OBJECT-TYPE
	SYNTAX	Counter
	ACCESS	read-only
	STATUS	mandatory
	DESCRIPTION
		"The number of transmit cells."
	--
	::= { perfIfSlotEntry 6 }

perfIfSlotInDropCellsCounters OBJECT-TYPE
	SYNTAX	Counter
	ACCESS	read-only
	STATUS	mandatory
	DESCRIPTION
		"The number of receive drop cells."
	--
	::= { perfIfSlotEntry 7 }

	--
	--

perfIfSlotHCThresholdExcessCells OBJECT-TYPE
        SYNTAX  OCTET STRING (SIZE(8))
        ACCESS  read-only
        STATUS  mandatory
        DESCRIPTION
		"The number of threshold excess cells"
	--
        ::= { perfIfSlotEntry 9 }

perfIfSlotThresholdExcessCells OBJECT-TYPE
        SYNTAX  Counter
        ACCESS  read-only
        STATUS  mandatory
        DESCRIPTION
		"The number of threshold excess cells"
	--
        ::= { perfIfSlotEntry 10 }

perfIfSlotHCUpcErrorCells OBJECT-TYPE
        SYNTAX  OCTET STRING (SIZE(8))
        ACCESS  read-only
        STATUS  mandatory
        DESCRIPTION
		"Number of UPC error cells."
	--
        ::= { perfIfSlotEntry 11 }

perfIfSlotUpcErrorCells OBJECT-TYPE
        SYNTAX  Counter
        ACCESS  read-only
        STATUS  mandatory
        DESCRIPTION
		"Number of UPC error cells."
	--
        ::= { perfIfSlotEntry 12 }

perfIfPhysTable	OBJECT-TYPE
	SYNTAX	SEQUENCE OF PerfIfPhysEntry
	ACCESS	not-accessible
	STATUS	mandatory
	DESCRIPTION
		""
	--
	::= { perf 4 }
 
perfIfPhysEntry	OBJECT-TYPE
	SYNTAX	PerfIfPhysEntry
	ACCESS	not-accessible
	STATUS	mandatory
	DESCRIPTION
		""
	--
	INDEX	{ perfIfPhysPort }
	::= { perfIfPhysTable 1 }
 
PerfIfPhysEntry ::=
	SEQUENCE {
		perfIfPhysPort
			INTEGER, 
		perfIfPhysHCHecErorrs
			OCTET STRING, 
		perfIfPhysHecErorrs
			INTEGER, 
		perfIfPhysHCHecDropCells
			OCTET STRING, 
		perfIfPhysHecDropCells
			INTEGER, 
		perfIfPhysHCB1Errors
			OCTET STRING, 
		perfIfPhysB1Errors
			INTEGER, 
		perfIfPhysHCB2Errors
			OCTET STRING, 
		perfIfPhysB2Errors
			INTEGER, 
		perfIfPhysHCB3Errors
			OCTET STRING, 
		perfIfPhysHCB3Errors
			INTEGER, 
		perfIfPhysHCPathFEBEs
			OCTET STRING, 
		perfIfPhysPathFEBEs
			INTEGER, 
		perfIfPhysHCLineFEBEs
			OCTET STRING, 
		perfIfPhysLineFEBEs
			INTEGER, 
		perfIfPhysHCFramingErrors
			OCTET STRING, 
		perfIfPhysFramingErrors
			INTEGER, 
		perfIfPhysHCReceivedCells
			OCTET STRING, 
		perfIfPhysReceivedCells
			INTEGER, 
		perfIfPhysHCTransmittedCells
			OCTET STRING, 
		perfIfPhysTransmittedCells
			INTEGER, 
		perfIfPhysHCIdelUnassignedCells
			OCTET STRING, 
		perfIfPhysIdelUnassignedCells
			INTEGER, 
		perfIfPhysHCFEBEErrors
			OCTET STRING, 
		perfIfPhysFEBEErrors
			INTEGER, 
		perfIfPhysHCFEBEs
			OCTET STRING, 
		perfIfPhysFEBEs
			INTEGER, 
		perfIfPhysHCPathParityErrors
			OCTET STRING, 
		perfIfPhysPathParityErrors
			INTEGER, 
		perfIfPhysHCParityErrors
			OCTET STRING, 
		perfIfPhysParityErrors
			INTEGER, 
		perfIfPhysHCSEZs
			OCTET STRING, 
		perfIfPhysSEZs
			INTEGER, 
		perfIfPhysHCBitErrors
			OCTET STRING, 
		perfIfPhysBitErrors
			INTEGER, 
		perfIfPhysHCLcvErrors
			OCTET STRING, 
		perfIfPhysLcvErrors
			INTEGER, 
		perfIfPhysHCBip8Errors
			OCTET STRING, 
		perfIfPhysBip8Errors
			INTEGER, 
		perfIfPhysHCIecErrors
			OCTET STRING, 
		perfIfPhysIecErrors
			INTEGER, 
		perfIfPhysHCFramingPatternErrors
			OCTET STRING, 
		perfIfPhysFramingPatternErrors
			INTEGER, 
		perfIfPhysHCFramingBitErrors
			OCTET STRING, 
		perfIfPhysFramingBitErrors
			INTEGER, 
		perfIfPhysHCCrcErrors
			OCTET STRING, 
		perfIfPhysCrcErrors
			INTEGER
	}
 
perfIfPhysPort	OBJECT-TYPE
	SYNTAX	INTEGER
	ACCESS	not-accessible
	STATUS	mandatory
	DESCRIPTION
		"Line number."
	--
	::= { perfIfPhysEntry 1 }
 
perfIfPhysHCHecErorrs	OBJECT-TYPE
	SYNTAX	OCTET STRING
	ACCESS	read-only
	STATUS	mandatory
	DESCRIPTION
		"Number of HEC error cells(64 bit applicable).
		On the line card other than OC12,  J2 and PR-1.5M, 
		the value of this object is 0."	
	--
	--
	::= { perfIfPhysEntry 2 }
 
perfIfPhysHecErorrs	OBJECT-TYPE
	SYNTAX	INTEGER
	ACCESS	read-only
	STATUS	mandatory
	DESCRIPTION
		"Number of HEC error cells(32 bit applicable).
		On the line card other than OC12,  J2 and PR-1.5M, 
		the value of this object is 0."	
	--
	--
	::= { perfIfPhysEntry 3 }
 
perfIfPhysHCHecDropCells	OBJECT-TYPE
	SYNTAX	OCTET STRING
	ACCESS	read-only
	STATUS	mandatory
	DESCRIPTION
		"Number of uncorrectable HEC error cells(64 bit applicable).
		On the line card other than OC3,  OC12,  OC12PMC,  J2, 
		PR-1.5,  DS3,  E3,  DS1 and E1,  the value of this object is 0."
	--
	--
	--
	::= { perfIfPhysEntry 4 }
 
perfIfPhysHecDropCells	OBJECT-TYPE
	SYNTAX	INTEGER
	ACCESS	read-only
	STATUS	mandatory
	DESCRIPTION
		"Number of uncorrectable HEC error cells(32 bit applicable).
		On the line card other than OC3,  OC12,  OC12PMC,  J2, 
		PR-1.5,  DS3,  E3,  DS1 and E1,  the value of this object is 0."
	--
	--
	--
	::= { perfIfPhysEntry 5 }
 
perfIfPhysHCB1Errors	OBJECT-TYPE
	SYNTAX	OCTET STRING
	ACCESS	read-only
	STATUS	mandatory
	DESCRIPTION
		"Number of B1 errors(64 bit applicable).
		On the line card other than OC3,  OC12,  OC12PMC, 
		DS3,  E3,  DS1 and E1, 
		the value of this object is 0."
	--
	--
	--
	::= { perfIfPhysEntry 6 }
 
perfIfPhysB1Errors	OBJECT-TYPE
	SYNTAX	INTEGER
	ACCESS	read-only
	STATUS	mandatory
	DESCRIPTION
		"Number of B1 errors(32 bit applicable).
		On the line card other than OC3,  OC12,  OC12PMC, 
		DS3,  E3,  DS1 and E1, 
		the value of this object is 0."
	--
	--
	--
	::= { perfIfPhysEntry 7 }
 
perfIfPhysHCB2Errors	OBJECT-TYPE
	SYNTAX	OCTET STRING
	ACCESS	read-only
	STATUS	mandatory
	DESCRIPTION
		"Number of B2 errors(64 bit applicable).
		On the line card other than OC3,  OC12 and OC12PMC, 
		the value of this object is 0."
	--
	--
	--
	::= { perfIfPhysEntry 8 }
 
perfIfPhysB2Errors	OBJECT-TYPE
	SYNTAX	INTEGER
	ACCESS	read-only
	STATUS	mandatory
	DESCRIPTION
		"Number of B2 errors(32 bit applicable).
		On the line card other than OC3,  OC12 and OC12PMC, 
		the value of this object is 0."
	--
	--
	--
	::= { perfIfPhysEntry 9 }
 
perfIfPhysHCB3Errors	OBJECT-TYPE
	SYNTAX	OCTET STRING
	ACCESS	read-only
	STATUS	mandatory
	DESCRIPTION
		"Number of B3 errors(64 bit applicable).
		On the line card other than OC3,  OC12 and OC12PMC, 
		the value of this object is 0."
	--
	--
	--
	::= { perfIfPhysEntry 10 }
 
perfIfPhysB3Errors	OBJECT-TYPE
	SYNTAX	INTEGER
	ACCESS	read-only
	STATUS	mandatory
	DESCRIPTION
		"Number of B3 errors(32 bit applicable).
		On the line card other than OC3,  OC12 and OC12PMC, 
		the value of this object is 0."
	--
	--
	--
	::= { perfIfPhysEntry 11 }
 
perfIfPhysHCPathFEBEs	OBJECT-TYPE
	SYNTAX	OCTET STRING
	ACCESS	read-only
	STATUS	mandatory
	DESCRIPTION
		"Number of Path FEBEs(64 bit applicable).
		On the line card other than OC3,  OC12 and OC12PMC, 
		the value of this object is 0."
	--
	--
	--
	::= { perfIfPhysEntry 12 }
 
perfIfPhysPathFEBEs	OBJECT-TYPE
	SYNTAX	INTEGER
	ACCESS	read-only
	STATUS	mandatory
	DESCRIPTION
		"Number of Path FEBEs(32 bit applicable).
		On the line card other than OC3,  OC12 and OC12PMC, 
		the value of this object is 0."
	--
	--
	--
	::= { perfIfPhysEntry 13 }
 
perfIfPhysHCLineFEBEs	OBJECT-TYPE
	SYNTAX	OCTET STRING
	ACCESS	read-only
	STATUS	mandatory
	DESCRIPTION
		"Number of Line (Section) FEBEs(64 bit applicable).
		On the line card other than OC3,  OC12 and OC12PMC, 
		the value of this object is 0."
	--
	--
	--
	::= { perfIfPhysEntry 14 }
 
perfIfPhysLineFEBEs	OBJECT-TYPE
	SYNTAX	INTEGER
	ACCESS	read-only
	STATUS	mandatory
	DESCRIPTION
		"Number of Line (Section) FEBEs(32 bit applicable).
		On the line card other than OC3,  OC12 and OC12PMC, 
		the value of this object is 0."
	--
	--
	--
	::= { perfIfPhysEntry 15 }
 
perfIfPhysHCFramingErrors	OBJECT-TYPE
	SYNTAX	OCTET STRING
	ACCESS	read-only
	STATUS	mandatory
	DESCRIPTION
		"Number of Framing errors(64 bit applicable).
		On the line card other than DS1,  E1,  DS3 and E3, 
		the value of this object is 0."
	--
	--
	::= { perfIfPhysEntry 16 }
 
perfIfPhysFramingErrors	OBJECT-TYPE
	SYNTAX	INTEGER
	ACCESS	read-only
	STATUS	mandatory
	DESCRIPTION
		"Number of Framing errors(32 bit applicable).
		On the line card other than DS1,  E1,  DS3 and E3, 
		the value of this object is 0."
	--
	--
	::= { perfIfPhysEntry 17 }
 
perfIfPhysHCReceivedCells	OBJECT-TYPE
	SYNTAX	OCTET STRING
	ACCESS	read-only
	STATUS	mandatory
	DESCRIPTION
		"The Number of the receive cells(64 bit applicable).
		On the line card other than DS3,  E3 and OC12PMC, 
		the value of this object is 0."
	--
	--
	::= { perfIfPhysEntry 18 }
 
perfIfPhysReceivedCells	OBJECT-TYPE
	SYNTAX	INTEGER	
	ACCESS	read-only
	STATUS	mandatory
	DESCRIPTION
		"The Number of the receive cells(32 bit applicable).
		On the line card other than DS3,  E3 and OC12PMC, 
		the value of this object is 0."
	--
	--
	::= { perfIfPhysEntry 19 }
 
perfIfPhysHCTransmittedCells	OBJECT-TYPE
	SYNTAX	OCTET STRING
	ACCESS	read-only
	STATUS	mandatory
	DESCRIPTION
		"The Number of the transmit cells(64 bit applicable).
		On the line card other than DS3,  E3 and OC12PMC, 
		the value of this object is 0."
	--
	--
	::= { perfIfPhysEntry 20 }

perfIfPhysTransmittedCells	OBJECT-TYPE
	SYNTAX	INTEGER
	ACCESS	read-only
	STATUS	mandatory
	DESCRIPTION
		"The Number of the transmit cells(32 bit applicable).
		On the line card other than DS3,  E3 and OC12PMC, 
		the value of this object is 0."
	--
	--
	::= { perfIfPhysEntry 21 }

perfIfPhysHCIdelUnassignedCells	OBJECT-TYPE
	SYNTAX	OCTET STRING
	ACCESS	read-only
	STATUS	mandatory
	DESCRIPTION
		"The Number of Idle/Unassigned cells(64 bit applicable).
		On the line card other than DS3 and E3, 
		the value of this object is 0."	
	--
	--
	::= { perfIfPhysEntry 22 }

perfIfPhysIdelUnassignedCells	OBJECT-TYPE
	SYNTAX	INTEGER
	ACCESS	read-only
	STATUS	mandatory
	DESCRIPTION
		"The Number of Idle/Unassigned cells(32 bit applicable).
		On the line card other than DS3 and E3, 
		the value of this object is 0."	
	--
	--
	::= { perfIfPhysEntry 23 }

perfIfPhysHCFEBEErrors	OBJECT-TYPE
	SYNTAX	OCTET STRING
	ACCESS	read-only
	STATUS	mandatory
	DESCRIPTION
		"Number of FEBE errors(64 bit applicable).
		On the line card other than DS3,  E3,  DS1 and E1, 
		the value of this object is 0."
	--
	--
	::= { perfIfPhysEntry 24 }

perfIfPhysFEBEErrors	OBJECT-TYPE
	SYNTAX	INTEGER
	ACCESS	read-only
	STATUS	mandatory
	DESCRIPTION
		"Number of FEBEs errors(32 bit applicable).
		On the line card other than DS3,  E3,  DS1 and E1, 
		the value of this object is 0."
	--
	--
	::= { perfIfPhysEntry 25 }

perfIfPhysHCFEBEs	OBJECT-TYPE
	SYNTAX	OCTET STRING
	ACCESS	read-only
	STATUS	mandatory
	DESCRIPTION
		"Number of FEBEs(64 bit applicable).
		On the line card other than DS3,  E3,  E1 and CE-E1, 
		the value of this object is 0."
	--
	--
	::= { perfIfPhysEntry 26 }

perfIfPhysFEBEs	OBJECT-TYPE
	SYNTAX	INTEGER
	ACCESS	read-only
	STATUS	mandatory
	DESCRIPTION
		"Number of FEBEs(32 bit applicable).
		On the line card other than DS3,  E3,  E1 and CE-E1, 
		the value of this object is 0."
	--
	--
	::= { perfIfPhysEntry 27 }

perfIfPhysHCPathParityErrors	OBJECT-TYPE
	SYNTAX	OCTET STRING
	ACCESS	read-only
	STATUS	mandatory
	DESCRIPTION
		"Number of path parity errors(64 bit applicable).
		On the line card other than DS3, 
		the value of this object is 0."
	--
	--
	::= { perfIfPhysEntry 28 }

perfIfPhysPathParityErrors	OBJECT-TYPE
	SYNTAX	INTEGER
	ACCESS	read-only
	STATUS	mandatory
	DESCRIPTION
		"Number of path parity errors(32 bit applicable).
		On the line card other than DS3, 
		the value of this object is 0."
	--
	--
	::= { perfIfPhysEntry 29 }

perfIfPhysHCParityErrors	OBJECT-TYPE
	SYNTAX	OCTET STRING
	ACCESS	read-only
	STATUS	mandatory
	DESCRIPTION
		"Number of parity errors(64 bit applicable).
		On the line card other than DS3, 
		the value of this object is 0."
	--
	--
	::= { perfIfPhysEntry 30 }

perfIfPhysParityErrors	OBJECT-TYPE
	SYNTAX	INTEGER
	ACCESS	read-only
	STATUS	mandatory
	DESCRIPTION
		"Number of parity errors(32 bit applicable).
		On the line card other than DS3, 
		the value of this object is 0."
	--
	--
	::= { perfIfPhysEntry 31 }

perfIfPhysHCSEZs	OBJECT-TYPE
	SYNTAX	OCTET STRING
	ACCESS	read-only
	STATUS	mandatory
	DESCRIPTION
		"Number of detections of Summed excessive Zero
		(64 bit applicable).
		On the line card other than DS3, 
		the value of this object is 0."
	--
	--
	::= { perfIfPhysEntry 32 }

perfIfPhysSEZs	OBJECT-TYPE
	SYNTAX	INTEGER
	ACCESS	read-only
	STATUS	mandatory
	DESCRIPTION
		"Number of detections of Summed excessive Zero
		(32 bit applicable).
		On the line card other than DS3, 
		the value of this object is 0."
	--
	--
	::= { perfIfPhysEntry 33 }

perfIfPhysHCBitErrors	OBJECT-TYPE
	SYNTAX	OCTET STRING
	ACCESS	read-only
	STATUS	mandatory
	DESCRIPTION
		"Number of Bit errors(64 bit applicable).
		On the line card other than DS3 and CE-DS1(SF mode), 
		the value of this object is 0."
	--
	--
	::= { perfIfPhysEntry 34 }

perfIfPhysBitErrors	OBJECT-TYPE
	SYNTAX	INTEGER
	ACCESS	read-only
	STATUS	mandatory
	DESCRIPTION
		"Number of Bit errors(32 bit applicable).
		On the line card other than DS3 and CE-DS1(SF mode), 
		the value of this object is 0."
	--
	--
	::= { perfIfPhysEntry 35 }

perfIfPhysHCLcvErrors	OBJECT-TYPE
	SYNTAX	OCTET STRING
	ACCESS	read-only
	STATUS	mandatory
	DESCRIPTION
		"Number of LCV errors(64 bit applicable).
		On the line card other than DS3,  E3,  DS1,  E1, 
		FR-E1,  CE-DS1,  FR-DS1 and CE-E1, 
		the value of this object is 0."
	--
	--
	--
	::= { perfIfPhysEntry 36 }

perfIfPhysLcvErrors	OBJECT-TYPE
	SYNTAX	INTEGER
	ACCESS	read-only
	STATUS	mandatory
	DESCRIPTION
		"Number of LCV errors(32 bit applicable).
		On the line card other than DS3,  E3,  DS1,  E1, 
		FR-E1,  CE-DS1,  FR-DS1 and CE-E1, 
		the value of this object is 0."
	--
	--
	--
	::= { perfIfPhysEntry 37 }

perfIfPhysHCBip8Errors	OBJECT-TYPE
	SYNTAX	OCTET STRING
	ACCESS	read-only
	STATUS	mandatory
	DESCRIPTION
		"Number of BIP-8 errors(64 bit applicable).
		On the line card other than E3, 
		the value of this object is 0."
	--
	--
	::= { perfIfPhysEntry 38 }

perfIfPhysBip8Errors	OBJECT-TYPE
	SYNTAX	INTEGER
	ACCESS	read-only
	STATUS	mandatory
	DESCRIPTION
		"Number of BIP-8 errors(32 bit applicable).
		On the line card other than E3, 
		the value of this object is 0."
	--
	--
	::= { perfIfPhysEntry 39 }

perfIfPhysHCIecErrors	OBJECT-TYPE
	SYNTAX	OCTET STRING
	ACCESS	read-only
	STATUS	mandatory
	DESCRIPTION
		"Number of IEC errors(64 bit applicable).
		On the line card other than E3, 
		the value of this object is 0."
	--
	--
	::= { perfIfPhysEntry 40 }

perfIfPhysIecErrors	OBJECT-TYPE
	SYNTAX	INTEGER
	ACCESS	read-only
	STATUS	mandatory
	DESCRIPTION
		"Number of IEC errors(32 bit applicable).
		On the line card other than E3, 
		the value of this object is 0."
	--
	--
	::= { perfIfPhysEntry 41 }

perfIfPhysHCFramingPatternErrors	OBJECT-TYPE
	SYNTAX	OCTET STRING
	ACCESS	read-only
	STATUS	mandatory
	DESCRIPTION
		"Number of Framing pattern errors(64 bit applicable).
		On the line card other than E3, 
		the value of this object is 0."
	--
	--
	::= { perfIfPhysEntry 42 }

perfIfPhysFramingPatternErrors	OBJECT-TYPE
	SYNTAX	INTEGER
	ACCESS	read-only
	STATUS	mandatory
	DESCRIPTION
		"Number of Framing pattern errors(32 bit applicable).
		On the line card other than E3, 
		the value of this object is 0."
	--
	--
	::= { perfIfPhysEntry 43 }

perfIfPhysHCFramingBitErrors	OBJECT-TYPE
	SYNTAX	OCTET STRING
	ACCESS	read-only
	STATUS	mandatory
	DESCRIPTION
		"Number of Framing bit errors(64 bit applicable).
		On the line card other than DS1,  E1,  FR-E1,  CE-DS1,  FR-DS1
		and CE-E1,  the value of this object is 0."
	--
	--
	--
	::= { perfIfPhysEntry 44 }

perfIfPhysFramingBitErrors	OBJECT-TYPE
	SYNTAX	INTEGER
	ACCESS	read-only
	STATUS	mandatory
	DESCRIPTION
		"Number of Framing bit errors(32 bit applicable).
		On the line card other than DS1,  E1,  FR-E1,  CE-DS1,  FR-DS1
		and CE-E1,  the value of this object is 0."
	--
	--
	--
	::= { perfIfPhysEntry 45 }

perfIfPhysHCCrcErrors	OBJECT-TYPE
	SYNTAX	OCTET STRING
	ACCESS	read-only
	STATUS	mandatory
	DESCRIPTION
		"Number of CRC errors(64 bit applicable).
		On the line card other than DS1,  E1,  FR-E1,  FR-DS1, 
		CE-DS1(ESF mode) and CE-E1,  the value of this object is 0."
	--
	--
	--
	::= { perfIfPhysEntry 46 }

perfIfPhysCrcErrors	OBJECT-TYPE
	SYNTAX	INTEGER
	ACCESS	read-only
	STATUS	mandatory
	DESCRIPTION
		"Number of CRC errors(32 bit applicable).
		On the line card other than DS1,  E1,  FR-E1,  FR-DS1,  
		CE-DS1(ESF mode) and CE-E1,  the value of this object is 0."
	--
	--
	--
	::= { perfIfPhysEntry 47 }



--

--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--

scaleStatus	OBJECT-TYPE
	SYNTAX	INTEGER {
			allocate (1), 	--
			install  (2), 	--
			backup   (3), 	--
			free     (4)	--
		}
	ACCESS	read-write
	STATUS	mandatory
	DESCRIPTION
		"Order to execute and state."
	--
	::= { scale 1 }

scaleCause	OBJECT-TYPE
	SYNTAX	INTEGER {
			other         (1), 	--
			start         (2), 	--
			succeed       (3), 	--
			nearend       (4), 	--
						--
						--
			timeOut       (5), 	--
			fileNotFound  (6), 	--
			accessViolate (7), 	--
			checksumError (8), 	--
			noData        (9), 	--
						--
                        sbyAccessError(10)      --
		}
	ACCESS	read-only
	STATUS	mandatory
	DESCRIPTION
		"The result of execution."
	--
	::= { scale 2 }

scaleDataType	OBJECT-TYPE
	SYNTAX	INTEGER {
			system   (1), 	--
			config   (2), 	--
			bill-cdr (3)	--
					--
		}
	ACCESS	read-write
	STATUS	mandatory
	DESCRIPTION
		"Data type."
	--
	::= { scale 3 }

scaleTarget	OBJECT-TYPE
	SYNTAX	IpAddress
	ACCESS	read-write
	STATUS	mandatory
	DESCRIPTION
		"IP address of the target."
	--
	::= { scale 4 }

scaleFileName	OBJECT-TYPE
	SYNTAX	DisplayString
	ACCESS	read-write
	STATUS	mandatory
	DESCRIPTION
		"File name(up to 127 characters)."
	--
	::= { scale 5 }

scaleSwSide     OBJECT-TYPE
	SYNTAX  INTEGER {
			act   (1), 	--
			sby   (2)	--
	}
	ACCESS  read-write
	STATUS  mandatory
	DESCRIPTION
		"Indicate which system of the SW-Engine."
	--
	::= { scale 6 }

--

cardStatusTable	OBJECT-TYPE
	SYNTAX	SEQUENCE OF CardStatusEntry
	ACCESS	not-accessible
	STATUS	mandatory
	DESCRIPTION
		"Table showing the configuration information of the line
		card with CPU."
	--
	::= { card 1 }

cardStatusEntry	OBJECT-TYPE
	SYNTAX	CardStatusEntry
	ACCESS	not-accessible
	STATUS	mandatory
	DESCRIPTION
		"Entry of the configuration nformation of the line card
		with CPU."
	--
	INDEX	{ slotIfConfIndex }
	::= { cardStatusTable 1 }

CardStatusEntry ::=
	SEQUENCE {
		cardStatusServerType            INTEGER, 
		cardStatusRevision              DisplayString, 
		cardStatusMateSlotNumber        INTEGER, 
		cardStatusMode                  INTEGER, 
		cardStatusPriority		INTEGER, 
		cardStatusAtmAddr		OCTET STRING, 
		cardStatusMateAtmAddr		OCTET STRING
	}

cardStatusServerType	OBJECT-TYPE
	SYNTAX	INTEGER
	ACCESS	read-only
	STATUS	mandatory
	DESCRIPTION
		"Indicate the types of the server installed in
		the line card with CPU:
			other (1) ...other than the below stated types
			LANE  (2)
			ARP   (4)
			NHRP  (8)
			MPOA  (16)
		If more than one server type is installed,  return the sum
		of their values.
		e.g.
			Only NHRP           is installed --
			ARP and NHRP       are installed --
			LANE,  ARP and NHRP are installed --
	--
	--
	--"
	::= { cardStatusEntry 1 }

cardStatusRevision	OBJECT-TYPE
	SYNTAX	DisplayString
	ACCESS	read-only
	STATUS	mandatory
	DESCRIPTION
		"The revision of the software installed in the line card
		with CPU.
		e.g.,  ...X means the number of revision.
		Software Version X.X(X)  Boot ROM Version KXX"
	--
	::= { cardStatusEntry 2 }

cardStatusMateSlotNumber	OBJECT-TYPE
	SYNTAX	INTEGER (0..16)
	ACCESS	read-only
	STATUS	mandatory
	DESCRIPTION
		"The slot number of the card with double configuration
		(including itself).
		If it is single configuration/although it is of double
		configuration,  SBY system is not implemented,  return zero."
	--
	--
	--
	::= { cardStatusEntry 3 }

cardStatusMode	OBJECT-TYPE
	SYNTAX	INTEGER	{
			act (1), 
			sby (2), 
			single (3), 
			other (4)
		}
	ACCESS	read-only
	STATUS	mandatory
	DESCRIPTION
		"Operational mode of the card."
	--
	::= { cardStatusEntry 4 }

cardStatusPriority	OBJECT-TYPE	
	SYNTAX	INTEGER	{
			local (1), 		--
			remotePrimary (2), 	--
			remoteSecoundary (3)	--
		}
	ACCESS	read-only
	STATUS	mandatory
	DESCRIPTION
		""
	--
	::= { cardStatusEntry 5 }

cardStatusAtmAddr	OBJECT-TYPE
	SYNTAX	OCTET STRING(SIZE(0 | 20))
	ACCESS	read-only
	STATUS	mandatory
	DESCRIPTION
		""
	--
	--
	::= { cardStatusEntry 6 }

cardStatusMateAtmAddr	OBJECT-TYPE
	SYNTAX	OCTET STRING(SIZE(0 | 20))
	ACCESS	read-only
	STATUS	mandatory
	DESCRIPTION
		""
	--
	--
	::= { cardStatusEntry 7 }

cardOpeTable	OBJECT-TYPE
	SYNTAX	SEQUENCE OF CardOpeEntry
	ACCESS	not-accessible
	STATUS	mandatory
	DESCRIPTION
		"The table showing the command operations to the line
		card with CPU.
		If the card configured on SBY system is indicated, 
		return noSuchName."
	--
	--
	--
	::= { card 2 }

cardOpeEntry	OBJECT-TYPE
	SYNTAX	CardOpeEntry
	ACCESS	not-accessible
	STATUS	mandatory
	DESCRIPTION
		"Entry of command operation to the line card with CPU."
	--
	INDEX	{ slotIfConfIndex }
	::= { cardOpeTable 1 }

CardOpeEntry ::=
	SEQUENCE {
		cardOpeReset            INTEGER, 
		cardOpeDiagnosis        INTEGER, 
		cardOpeSave             INTEGER, 
		cardOpeSaveResult       INTEGER, 
		cardOpeCopy             INTEGER, 
		cardOpeCopyResult       INTEGER
	}

cardOpeReset	OBJECT-TYPE
	SYNTAX	INTEGER {
			noOperation (1), 	--
			reset (2), 		--
			ach (3)			--
		}
	ACCESS	read-write
	STATUS	mandatory
	DESCRIPTION
		"Card Reset processing.
		Return noOperation(1) at read.
		"
	--
	--
	--
	::= { cardOpeEntry 1 }

cardOpeDiagnosis	OBJECT-TYPE
	SYNTAX	INTEGER {
			noOperation (1), 
			diagnosis (2)
		}
	ACCESS	not-accessible
	STATUS	mandatory
	DESCRIPTION
		"Card diagnostic processing.
		Diagnose the SBY system card of double configuration with
		(the ACT system card).
		Return noOperation (1) at read.
		"
	--
	--
	--
	--
	--
	::= { cardOpeEntry 2 }

cardOpeSave	OBJECT-TYPE
	SYNTAX	INTEGER {
			noOperation (1), 
			save (2)
		}
	ACCESS	read-write
	STATUS	mandatory
	DESCRIPTION
		"Card Save processing.
		Save the system configuration information in FROM.
		If it is of double configuration,  save it in SBY
		system FROM as well.
		Return noOperation (1) at read."
	--
	--
	--
	--
	--
	::= { cardOpeEntry 3 }

cardOpeSaveResult	OBJECT-TYPE
	SYNTAX	INTEGER {			    --
			succeed (1), 		    --
			succeed-act (2), 	    --
			succeed-sby (3), 	    --
			temporaryFailure (4), 	    --
			nearend (5), 		    --
			nearend-act (6), 	    --
			nearend-act-failure-sby (7), --
			nearend-sby (8), 	    --
			nearend-sby-failure-act (9), --
			notReady (10), 		    --
			ready (11)		    --
		}
	ACCESS	read-only
	STATUS	mandatory
	DESCRIPTION
		"The result of card save processing.
		OK /NG indicate that SAVE processing completed/failed, 
		respectively.
		(NearEND) indicates that the number of writes into FROM
		approaches to the limit."
	--
	--
	--
	--
	::= { cardOpeEntry 4 }

cardOpeCopy	OBJECT-TYPE
	SYNTAX	INTEGER {
			noOperation (1), 
			copy-all-from-act (2), 
			copy-all-from-sby (3), 
			copy-config-from-act (4), 
			copy-config-from-sby (5), 
			copy-system-from-act (6), 
			copy-system-from-sby (7)
		}
	ACCESS	read-write
	STATUS	mandatory
	DESCRIPTION
		"Card Copy processing.
		Return noOperation (1) at read."
	--
	--
	::= { cardOpeEntry 5 }

cardOpeCopyResult	OBJECT-TYPE
	SYNTAX	INTEGER {
			succeed (1), 	--
			temporaryFailure (2), 	--
			nearend (3), 	--
					--
					--
			notReady (4), 	--
			ready (5)	--
		}
	ACCESS	read-only
	STATUS	mandatory
	DESCRIPTION
		"Result of Card Copy processing."
	--
	::= { cardOpeEntry 6 }

--

clockOpe	OBJECT IDENTIFIER ::= { clock 1 }
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--


clockOpeStatus	OBJECT-TYPE
	SYNTAX	INTEGER	{
			allocate (1), 	--
			set      (2), 	--
			free     (3)	--
		}
	ACCESS	read-write
	STATUS	mandatory
	DESCRIPTION
		"Used to control Clock setting processing."
	--
	::= { clockOpe 1 }

clockOpeCause	OBJECT-TYPE
	SYNTAX	INTEGER	{
			noWriting          (1), 	--
			other              (2), 	--
			succeed            (3), 	--
			setWarning         (4), 	--
						--
			parameterNotEnough (5), 	--
						--
			portNotExist       (6), 	--
			portOutOfRange     (7), 	--
			allPortFailure     (8)	--
		}
	ACCESS	read-only
	STATUS	mandatory
	DESCRIPTION
		"Result of Clock setting processing."
	--
	::= { clockOpe 2 }

clockOpeMode	OBJECT-TYPE
	SYNTAX	INTEGER	{
			master (1), 	--
			slave  (2)
		}
	ACCESS	read-write	
	STATUS	mandatory
	DESCRIPTION
		"Clock Mode."
	::= { clockOpe 3 }

clockOpeAccuracy	OBJECT-TYPE
	SYNTAX	INTEGER (0..255|-1)
	ACCESS	read-write	
	STATUS	mandatory
	DESCRIPTION
		"Accuracy[ppm] of clock.
		
		If no set,  value is -1."
	--
	--
	--
	::= { clockOpe 4 }

clockOpeSlaveLine1	OBJECT-TYPE
	SYNTAX	INTEGER	(1..32|-1)
	ACCESS	read-write
	STATUS	mandatory
	DESCRIPTION
		"Slave line number 1.
		
		If no set,  value is -1."
	--
	--
	--
	::= { clockOpe 5 }

clockOpeSlaveLine2	OBJECT-TYPE
	SYNTAX	INTEGER	(1..32|-1)
	ACCESS	read-write	
	STATUS	mandatory
	DESCRIPTION
		"Slave line number 2.
		
		Slave line number 1 shall be set already.
		If no set,  value is -1."
	--
	--
	--
	--
	::= { clockOpe 6 }

clockOpeSlaveLine3	OBJECT-TYPE
	SYNTAX	INTEGER	(1..32|-1)
	ACCESS	read-write
	STATUS	mandatory
	DESCRIPTION
		"Slave line number 3.
		
		Slave line number 1~2 shall be set already.
		If no set,  value is -1."
	--
	--
	--
	--
	::= { clockOpe 7 }

clockOpeSlaveLine4	OBJECT-TYPE
	SYNTAX	INTEGER (1..32|-1)
	ACCESS	read-write
	STATUS	mandatory
	DESCRIPTION
		"Slave line number 4.
		
		Slave line number 1~3 shall be set already.
		If no set,  value is -1."
	--
	--
	--
	--
	::= { clockOpe 8 }

ClockSlaveLineStatus	::= INTEGER {
			notApplicable        (1),  --
						  --
			active               (2),  --
			standby              (3),  --
			hardError            (4),  --
			adminDown            (5),  --
			notExist             (6),  --
			linfDown             (7),  --
			testing              (8),  --
			notSupported         (9),  --
			syncronizedFailure  (10),  --
			lossOf64kClock      (11),  --
			lossOf8kClock       (12),  --
			frequencyOutOfRange (13)  --
		}
	--
	--

clockMode	OBJECT-TYPE
	SYNTAX	INTEGER	{
			master (1), 
			slave  (2)
		}
	ACCESS	read-only
	STATUS	mandatory
	DESCRIPTION
		"Clock Mode."
	::= { clock 2 }

clockAccuracy	OBJECT-TYPE
	SYNTAX	INTEGER (0..255|-1)
	ACCESS	read-only
	STATUS	mandatory
	DESCRIPTION
		"Accuracy[ppm] of clock."
	--
	::= { clock 3 }

clockSlaveLine	OBJECT-TYPE
	SYNTAX	INTEGER
	ACCESS	read-only
	STATUS	mandatory
	DESCRIPTION
		"The number of the actually slaved line.
		If mode is master (1),  it is -1. "
	--
	--
	::= { clock 4 }

clockSlaveLine1	OBJECT-TYPE
	SYNTAX	INTEGER
	ACCESS	read-only
	STATUS	mandatory
	DESCRIPTION
		"Slave line number 1.
		If no set,  value is -1."
	--
	--
	::= { clock 5 }

clockSlaveLine1Status	OBJECT-TYPE
	SYNTAX	ClockSlaveLineStatus
	ACCESS	read-only
	STATUS	mandatory
	DESCRIPTION
		"State of slave line 1."
	--
	::= { clock 6 }

clockSlaveLine2	OBJECT-TYPE
	SYNTAX	INTEGER
	ACCESS	read-only
	STATUS	mandatory
	DESCRIPTION
		"Slave line number 2.
		If no set,  value is -1."
	--
	--
	::= { clock 7 }

clockSlaveLine2Status	OBJECT-TYPE
	SYNTAX	ClockSlaveLineStatus
	ACCESS	read-only
	STATUS	mandatory
	DESCRIPTION
		"State of slave line 2."
	--
	::= { clock 8 }

clockSlaveLine3	OBJECT-TYPE
	SYNTAX	INTEGER
	ACCESS	read-only
	STATUS	mandatory
	DESCRIPTION
		"Slave line number 3.
		If no set,  value is -1."
	--
	--
	::= { clock 9 }

clockSlaveLine3Status	OBJECT-TYPE
	SYNTAX	ClockSlaveLineStatus
	ACCESS	read-only
	STATUS	mandatory
	DESCRIPTION
		"State of slave line 3."
	--
	::= { clock 10 }

clockSlaveLine4	OBJECT-TYPE
	SYNTAX	INTEGER
	ACCESS	read-only
	STATUS	mandatory
	DESCRIPTION
		"Slave line number 4.
		If no set,  value is -1."
	--
	--
	::= { clock 11 }

clockSlaveLine4Status	OBJECT-TYPE
	SYNTAX	ClockSlaveLineStatus
	ACCESS	read-only
	STATUS	mandatory
	DESCRIPTION
		"State of slave line 4."
	--
	::= { clock 12 }

--

	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--
	--

diagActionStatus	OBJECT-TYPE
	SYNTAX	INTEGER	{
			allocate (1), 	--
			start    (2), 	--
			execute  (3), 	--
			end      (4), 	--
			free     (5)	--
		}
	ACCESS	read-write
	STATUS	mandatory
	DESCRIPTION
		"Used to control diagnostics test processing."
	--
	::= { diag 1 }

diagActionKind	OBJECT-TYPE
	SYNTAX	INTEGER	{
			switch (1), 
			cpu    (2), 
			slot   (3)
		}
	ACCESS	read-write
	STATUS	mandatory
	DESCRIPTION
		""
	--
	--
	--
	--
	::= { diag 2 }

diagPreCause	OBJECT-TYPE
	SYNTAX	INTEGER	{
			other              (1), 	--
			succeed            (2), 	--
			parameterNotEnough (3), 	--
			notInstalled       (4), 	--
						--
			notSupport	   (5),  --
						--
			diagnostics	   (6),  --
			clkChgError	   (7),  --
						--
			initializing	   (8),  --
						--
			sbyAccessError	   (9)  --
						--
		}
	ACCESS	read-only
	STATUS	mandatory
	DESCRIPTION
		""
	--
	::= { diag 3 }

diagCause	OBJECT-TYPE
	SYNTAX	INTEGER	{
			normal   (1), 
--
			diagNG-SC  (1020004), 
			diagNG-BF  (1030004), 
			diagNG-ES0 (1040007), 
			diagNG-ES1 (1040107), 
			diagNG-SAR (1050005), 
			diagNG-DI  (1060010), 
			diagNG-CPU (1070002), 
			diagNG-CPU-Register           (1600201), 
			diagNG-CPU-Timer-Test         (1600202), 
			diagNG-CPU-MM-Test            (1600203), 
			diagNG-CPU-DRAM-Partial-Write (1600204), 
			diagNG-CPU-Memory-Machining   (1600205), 
			diagNG-CPU-Cash-Test          (1600206), 
			diagNG-CPU-BSN-Parity         (1600207), 
			diagNG-CPU-LANCE-LoopBack     (1600208), 
			diagNG-Local-Memory       (1600301), 
			diagNG-DMAC-Register      (1600302), 
			diagNG-MISCEMA-Register   (1600303), 
			diagNG-XACK-Interrupt     (1600304), 
			diagNG-ASW-Register       (1600401), 
			diagNG-BMT                (1600402), 
			diagNG-Failer-Detect      (1600403), 
			diagNG-SAR-Register       (1600501), 
			diagNG-SAR-Control-Memory (1600502), 
			diagNG-SAR-Packet-Memory  (1600503), 
			diagNG-DI-Register        (1600504), 
			diagNG-DI-Memory          (1600505), 
			diagNG-ES-LoopBack                 (1600601), 
			diagNG-ES-Own-LoopBack             (1600602), 
			diagNG-ES-Other-LoopBack           (1600603), 
			diagNG-ES-Own-Broadcast-LoopBack   (1600604), 
			diagNG-ES-Other-Broadcast-LoopBack (1600605), 
			diagNG-ES-Nto1-Test                (1600606), 
			diagNG-ATOM-Buffer-OVF     (1600607), 
			diagNG-BackPressure        (1600608), 
			diagNG-RICEtoCell-Compete  (1600609), 
			diagNG-SAR-LoopBack        (1600701), 
			diagNG-DI-LoopBack         (1600702), 
			diagNG-SW-Own-LoopBack     (1600703), 
			diagNG-SW-Other-LoopBack   (1600704), 
			diagNG-Illegal-Cell-Detect (1600705), 
			diagNG-SARtoPacket-Compete (1600706), 
			diagNG-PCMCIA-Register     (1601101), 
--
			diagNG-IXB-Register   (2010002), 
			diagNG-OXB-Register   (2020003), 
			diagNG-UHT-Register   (2030003), 
			diagNG-IBC-Register   (2040008), 
			diagNG-IBC-RIRO-SGRAM (2040009), 
			diagNG-IBC-HT-i-SGRAM (2040010), 
			diagNG-IBC-RIRO-SRAM  (2040011), 
			diagNG-OBC-Register   (2040012), 
			diagNG-OBC-CellBuffer (2040013), 
			diagNG-OBC-HT-o       (2040014), 
			diagNG-OBC-BCI-BMT    (2040015), 
			diagNG-FR-SDRAM       (2090006), 
--
			diagNG-PHY0         (3010002), 
			diagNG-PHY1         (3010102), 
			diagNG-PHY2         (3010202), 
			diagNG-PHY3         (3010302), 
			diagNG-MUX          (3020012), 
			diagNG-CU2INF       (3030002), 
			diagNG-UNIC         (3040003), 
			diagNG-CFAD         (3050003), 
			diagNG-PLD          (3060003), 
			diagNG-FPGA         (3070004), 
			diagNG-FRM0         (3080004), 
			diagNG-FRM1         (3080104), 
			diagNG-S-UNI622     (3120004), 
			diagNG-TAC0         (3130001), 
			diagNG-TAC1         (3130101), 
			diagNG-TAC2         (3130201), 
			diagNG-TAC3         (3130301), 
			diagNG-LCA-Common   (3150001), 
			diagNG-LCA-Separate (3150002), 
			diagNG-UCFAD2       (3160001), 
			diagNG-PM7345-0     (3140005), 
			diagNG-PM7345-1     (3140105), 
			diagNG-PM7345-2     (3140205), 
			diagNG-PM7345-3     (3140305), 
			diagNG-PM4341A-0    (3170001), 
			diagNG-PM4341A-1    (3170101), 
			diagNG-PM4341A-2    (3170201), 
			diagNG-PM4341A-3    (3170301), 
			diagNG-PM6341-0     (3180001), 
			diagNG-PM6341-1     (3180101), 
			diagNG-PM6341-2     (3180201), 
			diagNG-PM6341-3     (3180301), 
			diagNG-DCS-LCA      (3230003), 
			diagNG-ALARM        (3190001), 
			diagNG-FRAME        (3190002), 
			diagNG-TS-CTL       (3190003), 
			diagNG-FIFO-CTL     (3190004), 
			diagNG-AAL1-SAR     (3200001), 
			diagNG-FPGA-CE-DS1  (3210003), 
			diagNG-FPGA-CE-E1   (3220004), 
			diagNG-WAC-021      (3240001), 
			diagNG-CPU-DRAM     (3250001), 
			diagNG-CPU-Tout     (3250002)
		}
	ACCESS	read-only
	STATUS	mandatory
	DESCRIPTION
		"Result of diagnostics test processing."
	--
	::= { diag 4 }

diagParam1	OBJECT-TYPE
	SYNTAX	INTEGER
	ACCESS	read-write
	STATUS	mandatory
	DESCRIPTION
		""
	--
	--
	::= { diag 5 }

--

--

	PnniAtmAddr ::= OCTET STRING (SIZE(20))
	--

	PnniNodeId ::= OCTET STRING (SIZE(22))
	--

	PnniPeerGroupId ::= OCTET STRING (SIZE(14))
	--

	PnniLevel ::= INTEGER (0..104)
	--


--

pnniNode	OBJECT IDENTIFIER ::= { pnni 1 }

pnniNodeOpe	OBJECT IDENTIFIER ::= { pnniNode 1 }
	--
	--

pnniNodeTable	OBJECT-TYPE
	SYNTAX	SEQUENCE OF PnniNodeEntry
	ACCESS	not-accessible
	STATUS	mandatory
	DESCRIPTION
		"Table of PNNI Logical node attributes.
		A row exist every PNNI peer group which the managed system
		belongs to."
	--
	--
	--
	::= { pnniNode 2 }

pnniNodeEntry	OBJECT-TYPE
	SYNTAX	PnniNodeEntry
	ACCESS	not-accessible
	STATUS	mandatory
	DESCRIPTION
		"Entry of pnniNodeTable."
	--
	INDEX	{ pnniNodeLevel }
	::= { pnniNodeTable 1 }

PnniNodeEntry ::=
	SEQUENCE {
		pnniNodeLevel			PnniLevel, 
		pnniNodeId			PnniNodeId, 
		pnniNodeAtmAddress		PnniAtmAddr, 
		pnniNodePeerGroupId		PnniPeerGroupId, 
		pnniNodeRestrictedTransit	TruthValue, 
		pnniNodeRestrictedBranching	TruthValue, 
		pnniNodeLeadershipPriority	INTEGER
	}

pnniNodeLevel OBJECT-TYPE
	SYNTAX	PnniLevel
	ACCESS	not-accessible
	STATUS	mandatory
	DESCRIPTION
		"PNNI hierarchy level where node(s) reside."
	--
	::= { pnniNodeEntry 1 }

pnniNodeId OBJECT-TYPE
	SYNTAX	PnniNodeId
	ACCESS	read-only
	STATUS	mandatory
	DESCRIPTION
		"Node ID."
	--
	::= { pnniNodeEntry 2 }

pnniNodeAtmAddress OBJECT-TYPE
	SYNTAX	PnniAtmAddr
	ACCESS	read-only
	STATUS	mandatory
	DESCRIPTION
		"ATM End System Address of node."
	--
	::= { pnniNodeEntry 3 }

pnniNodePeerGroupId OBJECT-TYPE
	SYNTAX	PnniPeerGroupId
	ACCESS	read-only
	STATUS	mandatory
	DESCRIPTION
		"Peer Group Identifier of the peer group which a node
		belongs to."
	--
	::= { pnniNodeEntry 4 }

pnniNodeRestrictedTransit OBJECT-TYPE
	SYNTAX	TruthValue
	ACCESS	read-only
	STATUS	mandatory
	DESCRIPTION
		"Restrict a node to be used as a transit route."
	--
	::= { pnniNodeEntry 5 }

pnniNodeRestrictedBranching OBJECT-TYPE
	SYNTAX	TruthValue
	ACCESS	read-only
	STATUS	mandatory
	DESCRIPTION
		"Restrict a node to be used as a branch point of
		point-to-multipoint."
	--
	::= { pnniNodeEntry 6 }

pnniNodeLeadershipPriority OBJECT-TYPE
	SYNTAX	INTEGER (0..255)
	ACCESS	read-only
	STATUS	mandatory
	DESCRIPTION
		"Leadership priority which a node notifies of."
	--
	::= { pnniNodeEntry 7 }

--

matCmdStatus	OBJECT-TYPE
	SYNTAX	INTEGER	{
			allocate (1), 
			inActive (2), 	--
			active (3), 	--
			free (4)
		}
	ACCESS	read-write
	STATUS	mandatory
	DESCRIPTION
		""
	--
	--
	--
	--
	--
	::= { matCmd 1 }

matCmdInput	OBJECT-TYPE
	SYNTAX	DisplayString
	ACCESS	read-write
	STATUS	mandatory
	DESCRIPTION
		""
	--
	::= { matCmd 2 }

matCmdOutput	OBJECT-TYPE
	SYNTAX	DisplayString
	ACCESS	read-only
	STATUS	mandatory
	DESCRIPTION
		""
	--	
	::= { matCmd 3 }

matCmdOutputType	OBJECT-TYPE
	SYNTAX	INTEGER	{
			normal (1), 
			continued (2), 
			interactive (3)
		}
	ACCESS	read-only
	STATUS	mandatory
	DESCRIPTION
		""
	--
	--
	--
	--
	::= { matCmd 4 }

matCmdStop	OBJECT-TYPE
	SYNTAX	INTEGER	{
			noOperation (1), 
			stop (2)
		}
	ACCESS	read-write
	STATUS	mandatory
	DESCRIPTION
		"When the value is set to 'stop',  the MAT command is stopped.
		When the value is set to 'noOperation',  no operation is
		performed. When read,  the value 'noOperation' is returned."
	::= { matCmd 5 }

matCmdTimeOut	OBJECT-TYPE
	SYNTAX	INTEGER(1..180)
--
--
	ACCESS	read-write
	STATUS	mandatory
	DESCRIPTION
		""
	--
	DEFVAL	{ 60 }
	::= { matCmd 6 }
END
