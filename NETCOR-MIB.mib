-- netcor.mib
-- 24 August, 1992
-- Dave Chapman


	NETCOR-MIB DEFINITIONS ::= BEGIN
	
	IMPORTS
		IpAddress, NetworkAddress, Counter, Gauge, TimeTicks, OBJECT-TYPE FROM RFC1155-SMI;

            internet      	OBJECT IDENTIFIER ::= { iso org(3) dod(6) 1 }
            mgmt          	OBJECT IDENTIFIER ::= { internet 2 }
            mib-2		OBJECT IDENTIFIER ::= { mgmt 1 }
	    private		OBJECT IDENTIFIER ::= { internet 4 }
	    enterprises		OBJECT IDENTIFIER ::= { private 1 }
	    netcor		OBJECT IDENTIFIER ::= { enterprises 329 }
	    nc007  		OBJECT IDENTIFIER ::= { netcor 1 }

-- textual conventions

          DisplayString ::=
              OCTET STRING

          PhysAddress ::=
              OCTET STRING

-- groups in MIB-II

          system       OBJECT IDENTIFIER ::= { mib-2 1 }

          interfaces   OBJECT IDENTIFIER ::= { mib-2 2 }

          at           OBJECT IDENTIFIER ::= { mib-2 3 }

          ip           OBJECT IDENTIFIER ::= { mib-2 4 }

          icmp         OBJECT IDENTIFIER ::= { mib-2 5 }

          tcp          OBJECT IDENTIFIER ::= { mib-2 6 }

          udp          OBJECT IDENTIFIER ::= { mib-2 7 }

          egp          OBJECT IDENTIFIER ::= { mib-2 8 }

          transmission OBJECT IDENTIFIER ::= { mib-2 10 }

          snmp         OBJECT IDENTIFIER ::= { mib-2 11 }


-- the System group

          sysDescr OBJECT-TYPE
              	SYNTAX  DisplayString (SIZE (0..255))
              	ACCESS  read-only
              	STATUS  mandatory
DESCRIPTION ""
              	::= { system 1 }

          sysObjectID OBJECT-TYPE
              	SYNTAX  OBJECT IDENTIFIER
              	ACCESS  read-only
              	STATUS  mandatory
DESCRIPTION ""
              	::= { system 2 }
	      	
          sysUpTime OBJECT-TYPE
              	SYNTAX  TimeTicks
              	ACCESS  read-only
              	STATUS  mandatory
DESCRIPTION ""
              	::= { system 3 }

          sysContact OBJECT-TYPE
              	SYNTAX  DisplayString (SIZE (0..255))
              	ACCESS  read-write
              	STATUS  mandatory
DESCRIPTION ""
              	::= { system 4 }
	      	
          sysName OBJECT-TYPE
              	SYNTAX  DisplayString (SIZE (0..255))
              	ACCESS  read-write
              	STATUS  mandatory
DESCRIPTION ""
              	::= { system 5 }
	      	
          sysLocation OBJECT-TYPE
              	SYNTAX  DisplayString (SIZE (0..255))
              	ACCESS  read-write
              	STATUS  mandatory
DESCRIPTION ""
              	::= { system 6 }
	      	
          sysServices OBJECT-TYPE
              	SYNTAX  INTEGER (0..127)
              	ACCESS  read-only
              	STATUS  mandatory
DESCRIPTION ""
              	::= { system 7 }
	      	
-- the Interfaces group

          ifNumber OBJECT-TYPE
              	SYNTAX  INTEGER
              	ACCESS  read-only
              	STATUS  mandatory
DESCRIPTION ""
              	::= { interfaces 1 }
	      	
-- the Interfaces table

          ifTable OBJECT-TYPE
              	SYNTAX  SEQUENCE OF IfEntry
              	ACCESS  not-accessible
              	STATUS  mandatory
DESCRIPTION ""
              	::= { interfaces 2 }

          ifEntry OBJECT-TYPE
              	SYNTAX  IfEntry
              	ACCESS  not-accessible
              	STATUS  mandatory
DESCRIPTION ""
              	INDEX   { ifIndex }
              	::= { ifTable 1 }
	      	
          IfEntry ::=
              SEQUENCE	{
                 	ifIndex
                      		INTEGER,
                  	ifDescr
                      		DisplayString,
                  	ifType
                      		INTEGER,
                  	ifMtu
                      		INTEGER,
                  	ifSpeed
                      		Gauge,
                  	ifPhysAddress
                      		PhysAddress,
                  	ifAdminStatus
                      		INTEGER,
                  	ifOperStatus
                      		INTEGER,
                  	ifLastChange
                      		TimeTicks,
                  	ifInOctets
                      		Counter,
                  	ifInUcastPkts
                      		Counter,
                  	ifInNUcastPkts
                      		Counter,
                  	ifInDiscards
                      		Counter,
                  	ifInErrors
                      		Counter,
                  	ifInUnknownProtos
                      		Counter,
                  	ifOutOctets
                      		Counter,
                  	ifOutUcastPkts
                      		Counter,
                  	ifOutNUcastPkts
                      		Counter,
                  	ifOutDiscards
                      		Counter,
                  	ifOutErrors
                      		Counter,
                  	ifOutQLen
                      		Gauge,
                  	ifSpecific
                      		OBJECT IDENTIFIER
              		}

          ifIndex OBJECT-TYPE
              	SYNTAX  INTEGER
              	ACCESS  read-only
              	STATUS  mandatory
DESCRIPTION ""
              	::= { ifEntry 1 }
	      	
          ifDescr OBJECT-TYPE
              	SYNTAX  DisplayString (SIZE (0..255))
              	ACCESS  read-only
              	STATUS  mandatory
DESCRIPTION ""
              	::= { ifEntry 2 }
	      	
          ifType OBJECT-TYPE
              	SYNTAX  INTEGER {
              	            	other(1),          -- none of the following
              	            	regular1822(2),
              	            	hdh1822(3),
              	            	ddn-x25(4),
              	           	rfc877-x25(5),
                          	ethernet-csmacd(6),
                          	iso88023-csmacd(7),
                          	iso88024-tokenBus(8),
                          	iso88025-tokenRing(9),
                          	iso88026-man(10),
                          	starLan(11),
                          	proteon-10Mbit(12),
                          	proteon-80Mbit(13),
                          	hyperchannel(14),
                          	fddi(15),
                          	lapb(16),
                          	sdlc(17),
                          	ds1(18),           -- T-1
                          	e1(19),            -- european equiv. of T-1
                          	basicISDN(20),
                          	primaryISDN(21),   -- proprietary serial
                          	propPointToPointSerial(22),
                          	ppp(23),
                          	softwareLoopback(24),
                          	eon(25),            -- CLNP over IP [11]
                          	ethernet-3Mbit(26),
                          	nsip(27),           -- XNS over IP
                          	slip(28),           -- generic SLIP
                          	ultra(29),          -- ULTRA technologies
                          	ds3(30),            -- T-3
                          	sip(31),            -- SMDS
                          	frame-relay(32)
                      		}
              	ACCESS  read-only
              	STATUS  mandatory
DESCRIPTION ""
              	::= { ifEntry 3 }

          ifMtu OBJECT-TYPE
              	SYNTAX  INTEGER
              	ACCESS  read-only
              	STATUS  mandatory
DESCRIPTION ""
              	::= { ifEntry 4 }
	      	
          ifSpeed OBJECT-TYPE
              	SYNTAX  Gauge
              	ACCESS  read-only
              	STATUS  mandatory
DESCRIPTION ""
              	::= { ifEntry 5 }
	      	
          ifPhysAddress OBJECT-TYPE
              	SYNTAX  PhysAddress
              	ACCESS  read-only
              	STATUS  mandatory
DESCRIPTION ""
              	::= { ifEntry 6 }
	      	
          ifAdminStatus OBJECT-TYPE
              	SYNTAX  INTEGER {
              	            	up(1),       -- ready to pass packets
              	            	down(2),
              	            	testing(3)   -- in some test mode
              	        	}
              	ACCESS  read-write
              	STATUS  mandatory
DESCRIPTION ""
              	::= { ifEntry 7 }

          ifOperStatus OBJECT-TYPE
              	SYNTAX  INTEGER {
              	            	up(1),       -- ready to pass packets
              	            	down(2),
              	            	testing(3)   -- in some test mode
              	        	}
              	ACCESS  read-only
              	STATUS  mandatory
DESCRIPTION ""
              	::= { ifEntry 8 }

          ifLastChange OBJECT-TYPE
              	SYNTAX  TimeTicks
              	ACCESS  read-only
              	STATUS  mandatory
DESCRIPTION ""
              	::= { ifEntry 9 }
	      	
          ifInOctets OBJECT-TYPE
              	SYNTAX  Counter
              	ACCESS  read-only
              	STATUS  mandatory
DESCRIPTION ""
              	::= { ifEntry 10 }
	      	
          ifInUcastPkts OBJECT-TYPE
              	SYNTAX  Counter
              	ACCESS  read-only
              	STATUS  mandatory
DESCRIPTION ""
              	::= { ifEntry 11 }
	      	
          ifInNUcastPkts OBJECT-TYPE
              	SYNTAX  Counter
              	ACCESS  read-only
              	STATUS  mandatory
DESCRIPTION ""
              	::= { ifEntry 12 }
	      	
          ifInDiscards OBJECT-TYPE
              	SYNTAX  Counter
              	ACCESS  read-only
              	STATUS  mandatory
DESCRIPTION ""
              	::= { ifEntry 13 }
	      	
          ifInErrors OBJECT-TYPE
              	SYNTAX  Counter
              	ACCESS  read-only
              	STATUS  mandatory
DESCRIPTION ""
              	::= { ifEntry 14 }
	      	
          ifInUnknownProtos OBJECT-TYPE
              	SYNTAX  Counter
              	ACCESS  read-only
              	STATUS  mandatory
DESCRIPTION ""
              	::= { ifEntry 15 }
	      	
          ifOutOctets OBJECT-TYPE
              	SYNTAX  Counter
              	ACCESS  read-only
              	STATUS  mandatory
DESCRIPTION ""
              	::= { ifEntry 16 }
	      	
          ifOutUcastPkts OBJECT-TYPE
              	SYNTAX  Counter
              	ACCESS  read-only
              	STATUS  mandatory
DESCRIPTION ""
              	::= { ifEntry 17 }
	      	
          ifOutNUcastPkts OBJECT-TYPE
              	SYNTAX  Counter
              	ACCESS  read-only
              	STATUS  mandatory
DESCRIPTION ""
              	::= { ifEntry 18 }
	      	
          ifOutDiscards OBJECT-TYPE
              	SYNTAX  Counter
              	ACCESS  read-only
              	STATUS  mandatory
DESCRIPTION ""
              	::= { ifEntry 19 }
	      	
          ifOutErrors OBJECT-TYPE
              	SYNTAX  Counter
              	ACCESS  read-only
              	STATUS  mandatory
DESCRIPTION ""
              	::= { ifEntry 20 }
	      	
          ifOutQLen OBJECT-TYPE
              	SYNTAX  Gauge
              	ACCESS  read-only
              	STATUS  mandatory
DESCRIPTION ""
              	::= { ifEntry 21 }
	      	
          ifSpecific OBJECT-TYPE
              	SYNTAX  OBJECT IDENTIFIER
              	ACCESS  read-only
              	STATUS  mandatory
DESCRIPTION ""
              	::= { ifEntry 22 }
	      	
	      	
-- the Address Translation group

          atTable OBJECT-TYPE
              	SYNTAX  SEQUENCE OF AtEntry
              	ACCESS  not-accessible
              	STATUS  deprecated
DESCRIPTION ""
              	::= { at 1 }

          atEntry OBJECT-TYPE
              	SYNTAX  AtEntry
              	ACCESS  not-accessible
              	STATUS  deprecated
DESCRIPTION ""
              	INDEX   { atIfIndex,
              	          atNetAddress }
              	::= { atTable 1 }

          AtEntry ::= SEQUENCE {
                  		atIfIndex
                      			INTEGER,
                  		atPhysAddress
                      			PhysAddress,
                  		atNetAddress
                      			NetworkAddress
              			}

          atIfIndex OBJECT-TYPE
              	SYNTAX  INTEGER
              	ACCESS  read-only
             --	ACCESS  read-write
              	STATUS  deprecated
DESCRIPTION ""
              	::= { atEntry 1 }
	      	
          atPhysAddress OBJECT-TYPE
              	SYNTAX  PhysAddress
              	ACCESS  read-write
              	STATUS  deprecated
DESCRIPTION ""
              	::= { atEntry 2 }
	      	
          atNetAddress OBJECT-TYPE
              	SYNTAX  NetworkAddress
              	ACCESS  read-write
              	STATUS  deprecated
DESCRIPTION ""
              	::= { atEntry 3 }
	      	
-- the IP group

          ipForwarding OBJECT-TYPE
              	SYNTAX  INTEGER {
              	            	hub(1), -- entity forwards datagrams
              	            	host(2)     -- entity does NOT forward datagrams
              	        	}
              	ACCESS  read-only
              	STATUS  mandatory
DESCRIPTION ""
              	::= { ip 1 }

          ipDefaultTTL OBJECT-TYPE
              	SYNTAX  INTEGER
              	ACCESS  read-write
              	STATUS  mandatory
DESCRIPTION ""
              	::= { ip 2 }
	      	
          ipInReceives OBJECT-TYPE
              	SYNTAX  Counter
              	ACCESS  read-only
              	STATUS  mandatory
DESCRIPTION ""
              	::= { ip 3 }
	      	
          ipInHdrErrors OBJECT-TYPE
              	SYNTAX  Counter
              	ACCESS  read-only
              	STATUS  mandatory
DESCRIPTION ""
              	::= { ip 4 }
	      	
          ipInAddrErrors OBJECT-TYPE
              	SYNTAX  Counter
              	ACCESS  read-only
              	STATUS  mandatory
DESCRIPTION ""
              	::= { ip 5 }
	      	
          ipForwDatagrams OBJECT-TYPE
              	SYNTAX  Counter
              	ACCESS  read-only
              	STATUS  mandatory
DESCRIPTION ""
              	::= { ip 6 }
	      	
          ipInUnknownProtos OBJECT-TYPE
              	SYNTAX  Counter
              	ACCESS  read-only
              	STATUS  mandatory
DESCRIPTION ""
              	::= { ip 7 }
	      	
          ipInDiscards OBJECT-TYPE
              	SYNTAX  Counter
              	ACCESS  read-only
              	STATUS  mandatory
DESCRIPTION ""
              	::= { ip 8 }
	      	
          ipInDelivers OBJECT-TYPE
              	SYNTAX  Counter
              	ACCESS  read-only
              	STATUS  mandatory
DESCRIPTION ""
              	::= { ip 9 }
	      	
          ipOutRequests OBJECT-TYPE
              	SYNTAX  Counter
              	ACCESS  read-only
              	STATUS  mandatory
DESCRIPTION ""
              	::= { ip 10 }
	      	
          ipOutDiscards OBJECT-TYPE
              	SYNTAX  Counter
              	ACCESS  read-only
              	STATUS  mandatory
DESCRIPTION ""
              	::= { ip 11 }
	      	
          ipOutNoRoutes OBJECT-TYPE
              	SYNTAX  Counter
              	ACCESS  read-only
              	STATUS  mandatory
DESCRIPTION ""
              	::= { ip 12 }
	      	
          ipReasmTimeout OBJECT-TYPE
              	SYNTAX  INTEGER
              	ACCESS  read-only
              	STATUS  mandatory
DESCRIPTION ""
              	::= { ip 13 }
	      	
          ipReasmReqds OBJECT-TYPE
              	SYNTAX  Counter
              	ACCESS  read-only
              	STATUS  mandatory
DESCRIPTION ""
              	::= { ip 14 }
	      	
          ipReasmOKs OBJECT-TYPE
              	SYNTAX  Counter
              	ACCESS  read-only
              	STATUS  mandatory
DESCRIPTION ""
              	::= { ip 15 }
	      	
          ipReasmFails OBJECT-TYPE
              	SYNTAX  Counter
              	ACCESS  read-only
              	STATUS  mandatory
DESCRIPTION ""
              	::= { ip 16 }
	      	
          ipFragOKs OBJECT-TYPE
              	SYNTAX  Counter
              	ACCESS  read-only
              	STATUS  mandatory
DESCRIPTION ""
              	::= { ip 17 }
	      	
          ipFragFails OBJECT-TYPE
              	SYNTAX  Counter
              	ACCESS  read-only
              	STATUS  mandatory
DESCRIPTION ""
              	::= { ip 18 }
	      	
          ipFragCreates OBJECT-TYPE
              	SYNTAX  Counter
              	ACCESS  read-only
              	STATUS  mandatory
DESCRIPTION ""
              	::= { ip 19 }
	      	
-- the IP address table

          ipAddrTable OBJECT-TYPE
              	SYNTAX  SEQUENCE OF IpAddrEntry
              	ACCESS  not-accessible
              	STATUS  mandatory
DESCRIPTION ""
              	::= { ip 20 }
	      	
          ipAddrEntry OBJECT-TYPE
              	SYNTAX  IpAddrEntry
              	ACCESS  not-accessible
              	STATUS  mandatory
DESCRIPTION ""
              	INDEX   { ipAdEntAddr }
              	::= { ipAddrTable 1 }

          IpAddrEntry ::=
              	SEQUENCE {
                  	 ipAdEntAddr
                      		IpAddress,
                  	 ipAdEntIfIndex
                      		INTEGER,
                  	 ipAdEntNetMask
                      		IpAddress,
                  	 ipAdEntBcastAddr
                      		INTEGER,
                  	 ipAdEntReasmMaxSiz
                      		INTEGER (0..65535)
              		 }

          ipAdEntAddr OBJECT-TYPE
              	SYNTAX  IpAddress
              	ACCESS  read-only
              	STATUS  mandatory
DESCRIPTION ""
              	::= { ipAddrEntry 1 }
	      	
	      	
          ipAdEntIfIndex OBJECT-TYPE
              	SYNTAX  INTEGER
              	ACCESS  read-only
              	STATUS  mandatory
DESCRIPTION ""
              	::= { ipAddrEntry 2 }
	      	
          ipAdEntNetMask OBJECT-TYPE
              	SYNTAX  IpAddress
              	ACCESS  read-only
              	STATUS  mandatory
DESCRIPTION ""
              	::= { ipAddrEntry 3 }
	      	
          ipAdEntBcastAddr OBJECT-TYPE
              	SYNTAX  INTEGER
              	ACCESS  read-only
              	STATUS  mandatory
DESCRIPTION ""
              	::= { ipAddrEntry 4 }
	      	
          ipAdEntReasmMaxSiz  OBJECT-TYPE
              	SYNTAX  INTEGER (0..65535)
              	ACCESS  read-only
              	STATUS  mandatory
DESCRIPTION ""
              	::= { ipAddrEntry 5 }
	      	
-- the IP routing table

          ipRouteTable OBJECT-TYPE
              	SYNTAX  SEQUENCE OF IpRouteEntry
              	ACCESS  not-accessible
              	STATUS  mandatory
DESCRIPTION ""
              	::= { ip 21 }

          ipRouteEntry OBJECT-TYPE
              	SYNTAX  IpRouteEntry
              	ACCESS  not-accessible
              	STATUS  mandatory
DESCRIPTION ""
              	INDEX   { ipRouteDest }
              	::= { ipRouteTable 1 }
	      	
          IpRouteEntry ::=
              SEQUENCE {
                  	ipRouteDest
                      		IpAddress,
                  	ipRouteIfIndex
                      		INTEGER,
                  	ipRouteMetric1
                      		INTEGER,
                  	ipRouteMetric2
                      		INTEGER,
                  	ipRouteMetric3
                      		INTEGER,
                  	ipRouteMetric4
                      		INTEGER,
                  	ipRouteNextHop
                      		IpAddress,
                  	ipRouteType
                      		INTEGER,
                  	ipRouteProto
                      		INTEGER,
                  	ipRouteAge
                      		INTEGER,
                  	ipRouteMask
                      		IpAddress,
                  	ipRouteMetric5
                      		INTEGER,
                  	ipRouteInfo
                      		OBJECT IDENTIFIER
              		}

          ipRouteDest OBJECT-TYPE
              	SYNTAX  IpAddress
              	ACCESS  read-write
              	STATUS  mandatory
DESCRIPTION ""
              	::= { ipRouteEntry 1 }
	      	
          ipRouteIfIndex OBJECT-TYPE
              	SYNTAX  INTEGER
              	ACCESS  read-write
              	STATUS  mandatory
DESCRIPTION ""
              	::= { ipRouteEntry 2 }
	      	
          ipRouteMetric1 OBJECT-TYPE
              	SYNTAX  INTEGER
              	ACCESS  read-write
              	STATUS  mandatory
DESCRIPTION ""
              	::= { ipRouteEntry 3 }
	      	
          ipRouteMetric2 OBJECT-TYPE
              	SYNTAX  INTEGER
              	ACCESS  read-write
              	STATUS  mandatory
DESCRIPTION ""
              	::= { ipRouteEntry 4 }

          ipRouteMetric3 OBJECT-TYPE
              	SYNTAX  INTEGER
              	ACCESS  read-write
              	STATUS  mandatory
DESCRIPTION ""
              	::= { ipRouteEntry 5 }

          ipRouteMetric4 OBJECT-TYPE
              	SYNTAX  INTEGER
              	ACCESS  read-write
              	STATUS  mandatory
DESCRIPTION ""
              	::= { ipRouteEntry 6 }

          ipRouteNextHop OBJECT-TYPE
              	SYNTAX  IpAddress
              	ACCESS  read-write
              	STATUS  mandatory
DESCRIPTION ""
              	::= { ipRouteEntry 7 }
	      	
          ipRouteType OBJECT-TYPE
              	SYNTAX  INTEGER {
              	            	other(1),	-- none of the following
              	            	invalid(2),	-- an invalidated route
              	                	   	-- route to directly
              	            	direct(3),	-- connected (sub-)network
              	                          	-- route to a non-local
                          	indirect(4)	-- host/network/sub-network
                      		}
              	ACCESS  read-write
              	STATUS  mandatory
DESCRIPTION ""
              	::= { ipRouteEntry 8 }

          ipRouteProto OBJECT-TYPE
              	SYNTAX  INTEGER {
              	            	other(1),	-- none of the following
	      	
              	                        	-- non-protocol information,
              	                       		-- e.g., manually configured
              	            	local(2), 	-- entries

                                         	-- set via a network
                          	netmgmt(3),	-- management protocol

                                       		-- obtained via ICMP,
                          	icmp(4),	-- e.g., Redirect

                                        	-- the remaining values are
                                          	-- all gateway routing
                                          	-- protocols
                          	egp(5),
                          	ggp(6),
                          	hello(7),
                          	rip(8),
                          	is-is(9),
                          	es-is(10),
                          	ciscoIgrp(11),
                          	bbnSpfIgp(12),
                          	ospf(13),
                          	bgp(14)
                      		}
              	ACCESS  read-only
              	STATUS  mandatory
DESCRIPTION ""
              	::= { ipRouteEntry 9 }

          ipRouteAge OBJECT-TYPE
              	SYNTAX  INTEGER
              	ACCESS  read-write
              	STATUS  mandatory
DESCRIPTION ""
              	::= { ipRouteEntry 10 }
	      	
          ipRouteMask OBJECT-TYPE
              	SYNTAX  IpAddress
              	ACCESS  read-write
              	STATUS  mandatory
DESCRIPTION ""
              	::= { ipRouteEntry 11 }
	      	
          ipRouteMetric5 OBJECT-TYPE
              	SYNTAX  INTEGER
              	ACCESS  read-write
              	STATUS  mandatory
DESCRIPTION ""
              	::= { ipRouteEntry 12 }

          ipRouteInfo OBJECT-TYPE
              	SYNTAX  OBJECT IDENTIFIER
              	ACCESS  read-only
              	STATUS  mandatory
DESCRIPTION ""
              	::= { ipRouteEntry 13 }
	      	

          -- the IP Address Translation table

          ipNetToMediaTable OBJECT-TYPE
              	SYNTAX  SEQUENCE OF IpNetToMediaEntry
              	ACCESS  not-accessible
              	STATUS  mandatory
DESCRIPTION ""
              	::= { ip 22 }

          ipNetToMediaEntry OBJECT-TYPE
              	SYNTAX  IpNetToMediaEntry
              	ACCESS  not-accessible
              	STATUS  mandatory
DESCRIPTION ""
              	INDEX   { ipNetToMediaIfIndex,
              	          ipNetToMediaNetAddress }
              	::= { ipNetToMediaTable 1 }

          IpNetToMediaEntry ::=
              SEQUENCE {
                  	ipNetToMediaIfIndex
                      		INTEGER,
                  	ipNetToMediaPhysAddress
                      		PhysAddress,
                  	ipNetToMediaNetAddress
                      		IpAddress,
                  	ipNetToMediaType
                      		INTEGER
              		}

          ipNetToMediaIfIndex OBJECT-TYPE
              	SYNTAX  INTEGER
           -- 	ACCESS  read-write
              	ACCESS  read-only
              	STATUS  mandatory
DESCRIPTION ""
              	::= { ipNetToMediaEntry 1 }
	      	
          ipNetToMediaPhysAddress OBJECT-TYPE
              	SYNTAX  PhysAddress
              	ACCESS  read-write
              	STATUS  mandatory
DESCRIPTION ""
              	::= { ipNetToMediaEntry 2 }
	      	
          ipNetToMediaNetAddress OBJECT-TYPE
              	SYNTAX  IpAddress
              	ACCESS  read-write
              	STATUS  mandatory
DESCRIPTION ""
              	::= { ipNetToMediaEntry 3 }
	      	
          ipNetToMediaType OBJECT-TYPE
              	SYNTAX  INTEGER {
              	            	other(1),        -- none of the following
              	            	invalid(2),      -- an invalidated mapping
              	            	dynamic(3),
              	            	static(4)
              	        	}
              	ACCESS  read-write
              	STATUS  mandatory
DESCRIPTION ""
              	::= { ipNetToMediaEntry 4 }

-- additional IP objects

          ipRoutingDiscards OBJECT-TYPE
              	SYNTAX  Counter
              	ACCESS  read-only
              	STATUS  mandatory
DESCRIPTION ""
              	::= { ip 23 }
	      	
	      	
-- the ICMP group

          icmpInMsgs OBJECT-TYPE
              	SYNTAX  Counter
              	ACCESS  read-only
              	STATUS  mandatory
DESCRIPTION ""
              	::= { icmp 1 }
	      	
          icmpInErrors OBJECT-TYPE
              	SYNTAX  Counter
              	ACCESS  read-only
              	STATUS  mandatory
DESCRIPTION ""
              	::= { icmp 2 }
	      	
          icmpInDestUnreachs OBJECT-TYPE
              	SYNTAX  Counter
              	ACCESS  read-only
              	STATUS  mandatory
DESCRIPTION ""
              	::= { icmp 3 }
	      	
          icmpInTimeExcds OBJECT-TYPE
              	SYNTAX  Counter
              	ACCESS  read-only
              	STATUS  mandatory
DESCRIPTION ""
              	::= { icmp 4 }
	      	
	      	
          icmpInParmProbs OBJECT-TYPE
              	SYNTAX  Counter
              	ACCESS  read-only
              	STATUS  mandatory
DESCRIPTION ""
              	::= { icmp 5 }
	      	
          icmpInSrcQuenchs OBJECT-TYPE
              	SYNTAX  Counter
              	ACCESS  read-only
              	STATUS  mandatory
DESCRIPTION ""
              	::= { icmp 6 }
	      	
          icmpInRedirects OBJECT-TYPE
              	SYNTAX  Counter
              	ACCESS  read-only
              	STATUS  mandatory
DESCRIPTION ""
              	::= { icmp 7 }
	      	
          icmpInEchos OBJECT-TYPE
              	SYNTAX  Counter
              	ACCESS  read-only
              	STATUS  mandatory
DESCRIPTION ""
              	::= { icmp 8 }
	      	
          icmpInEchoReps OBJECT-TYPE
              	SYNTAX  Counter
              	ACCESS  read-only
              	STATUS  mandatory
DESCRIPTION ""
              	::= { icmp 9 }
	      	
          icmpInTimestamps OBJECT-TYPE
              	SYNTAX  Counter
              	ACCESS  read-only
              	STATUS  mandatory
DESCRIPTION ""
              	::= { icmp 10 }
	      	
          icmpInTimestampReps OBJECT-TYPE
              	SYNTAX  Counter
              	ACCESS  read-only
              	STATUS  mandatory
DESCRIPTION ""
              	::= { icmp 11 }
	      	
          icmpInAddrMasks OBJECT-TYPE
              	SYNTAX  Counter
              	ACCESS  read-only
              	STATUS  mandatory
DESCRIPTION ""
              	::= { icmp 12 }
	      	
          icmpInAddrMaskReps OBJECT-TYPE
              	SYNTAX  Counter
              	ACCESS  read-only
              	STATUS  mandatory
DESCRIPTION ""
              	::= { icmp 13 }
	      	
          icmpOutMsgs OBJECT-TYPE
              	SYNTAX  Counter
              	ACCESS  read-only
              	STATUS  mandatory
DESCRIPTION ""
              	::= { icmp 14 }
	      	
          icmpOutErrors OBJECT-TYPE
              	SYNTAX  Counter
              	ACCESS  read-only
              	STATUS  mandatory
DESCRIPTION ""
              	::= { icmp 15 }
	      	
          icmpOutDestUnreachs OBJECT-TYPE
              	SYNTAX  Counter
              	ACCESS  read-only
              	STATUS  mandatory
DESCRIPTION ""
              	::= { icmp 16 }
	      	
          icmpOutTimeExcds OBJECT-TYPE
              	SYNTAX  Counter
              	ACCESS  read-only
              	STATUS  mandatory
DESCRIPTION ""
              	::= { icmp 17 }
	      	
          icmpOutParmProbs OBJECT-TYPE
              	SYNTAX  Counter
              	ACCESS  read-only
              	STATUS  mandatory
DESCRIPTION ""
              	::= { icmp 18 }
	      	
          icmpOutSrcQuenchs OBJECT-TYPE
              	SYNTAX  Counter
              	ACCESS  read-only
              	STATUS  mandatory
DESCRIPTION ""
              	::= { icmp 19 }
	      	
          icmpOutRedirects OBJECT-TYPE
              	SYNTAX  Counter
              	ACCESS  read-only
              	STATUS  mandatory
DESCRIPTION ""
              	::= { icmp 20 }
	      	
          icmpOutEchos OBJECT-TYPE
              	SYNTAX  Counter
              	ACCESS  read-only
              	STATUS  mandatory
DESCRIPTION ""
              	::= { icmp 21 }
	      	
          icmpOutEchoReps OBJECT-TYPE
              	SYNTAX  Counter
              	ACCESS  read-only
              	STATUS  mandatory
DESCRIPTION ""
              	::= { icmp 22 }
	      	
          icmpOutTimestamps OBJECT-TYPE
              	SYNTAX  Counter
              	ACCESS  read-only
              	STATUS  mandatory
DESCRIPTION ""
              	::= { icmp 23 }
	      	
          icmpOutTimestampReps OBJECT-TYPE
              	SYNTAX  Counter
              	ACCESS  read-only
              	STATUS  mandatory
DESCRIPTION ""
              	::= { icmp 24 }
	      	
          icmpOutAddrMasks OBJECT-TYPE
              	SYNTAX  Counter
              	ACCESS  read-only
              	STATUS  mandatory
DESCRIPTION ""
              	::= { icmp 25 }
	      	
	      	
          icmpOutAddrMaskReps OBJECT-TYPE
              	SYNTAX  Counter
              	ACCESS  read-only
              	STATUS  mandatory
DESCRIPTION ""
              	::= { icmp 26 }
	      	
	      	
-- the TCP group not supported

-- the UDP group

          udpInDatagrams OBJECT-TYPE
              	SYNTAX  Counter
              	ACCESS  read-only
              	STATUS  mandatory
DESCRIPTION ""
              	::= { udp 1 }
	      	
          udpNoPorts OBJECT-TYPE
              	SYNTAX  Counter
              	ACCESS  read-only
              	STATUS  mandatory
DESCRIPTION ""
              	::= { udp 2 }
	      	
          udpInErrors OBJECT-TYPE
              	SYNTAX  Counter
              	ACCESS  read-only
              	STATUS  mandatory
DESCRIPTION ""
              	::= { udp 3 }
          udpOutDatagrams OBJECT-TYPE
              	SYNTAX  Counter
              	ACCESS  read-only
              	STATUS  mandatory
DESCRIPTION ""
              	::= { udp 4 }
	      	
	      	
-- the UDP Listener table

          udpTable OBJECT-TYPE
              	SYNTAX  SEQUENCE OF UdpEntry
              	ACCESS  not-accessible
              	STATUS  mandatory
DESCRIPTION ""
              	::= { udp 5 }
	      	
          udpEntry OBJECT-TYPE
              	SYNTAX  UdpEntry
              	ACCESS  not-accessible
              	STATUS  mandatory
DESCRIPTION ""
              	INDEX   { udpLocalAddress, udpLocalPort }
              	::= { udpTable 1 }

          UdpEntry ::=
              SEQUENCE {
                  	udpLocalAddress
                      		IpAddress,
                  	udpLocalPort
                      		INTEGER (0..65535)
              		}

          udpLocalAddress OBJECT-TYPE
              	SYNTAX  IpAddress
              	ACCESS  read-only
              	STATUS  mandatory
DESCRIPTION ""
              	::= { udpEntry 1 }
	      	
          udpLocalPort OBJECT-TYPE
              	SYNTAX  INTEGER (0..65535)
              	ACCESS  read-only
              	STATUS  mandatory
DESCRIPTION ""
              	::= { udpEntry 2 }
	      	
	      	
-- the EGP group not supported
-- the Transmission group not supported

-- the SNMP group

          snmpInPkts OBJECT-TYPE
              	SYNTAX  Counter
              	ACCESS  read-only
              	STATUS  mandatory
DESCRIPTION ""
              	::= { snmp 1 }

          snmpOutPkts OBJECT-TYPE
              	SYNTAX  Counter
              	ACCESS  read-only
              	STATUS  mandatory
DESCRIPTION ""
              	::= { snmp 2 }

          snmpInBadVersions OBJECT-TYPE
              	SYNTAX  Counter
              	ACCESS  read-only
              	STATUS  mandatory
DESCRIPTION ""
              	::= { snmp 3 }

          snmpInBadCommunityNames OBJECT-TYPE
              	SYNTAX  Counter
              	ACCESS  read-only
              	STATUS  mandatory
DESCRIPTION ""
              	::= { snmp 4 }

          snmpInBadCommunityUses OBJECT-TYPE
              	SYNTAX  Counter
              	ACCESS  read-only
              	STATUS  mandatory
DESCRIPTION ""
              	::= { snmp 5 }

          snmpInASNParseErrs OBJECT-TYPE
              	SYNTAX  Counter
              	ACCESS  read-only
              	STATUS  mandatory
DESCRIPTION ""
              	::= { snmp 6 }

       -- snmpInBadTypes OBJECT-TYPE
             -- SYNTAX  Counter
             -- ACCESS  read-only
             -- STATUS  mandatory
             -- ::=  { snmp 7 }

          snmpInTooBigs OBJECT-TYPE
              	SYNTAX  Counter
              	ACCESS  read-only
              	STATUS  mandatory
DESCRIPTION ""
              	::= { snmp 8 }

          snmpInNoSuchNames OBJECT-TYPE
              	SYNTAX  Counter
              	ACCESS  read-only
              	STATUS  mandatory
DESCRIPTION ""
              	::= { snmp 9 }

          snmpInBadValues OBJECT-TYPE
              	SYNTAX  Counter
              	ACCESS  read-only
              	STATUS  mandatory
DESCRIPTION ""
              	::= { snmp 10 }

          snmpInReadOnlys OBJECT-TYPE
              	SYNTAX  Counter
              	ACCESS  read-only
              	STATUS  mandatory
DESCRIPTION ""
              	::= { snmp 11 }

          snmpInGenErrs OBJECT-TYPE
              	SYNTAX  Counter
              	ACCESS  read-only
              	STATUS  mandatory
DESCRIPTION ""
              	::= { snmp 12 }

          snmpInTotalReqVars OBJECT-TYPE
              	SYNTAX  Counter
              	ACCESS  read-only
              	STATUS  mandatory
DESCRIPTION ""
              	::= { snmp 13 }

          snmpInTotalSetVars OBJECT-TYPE
              	SYNTAX  Counter
              	ACCESS  read-only
              	STATUS  mandatory
DESCRIPTION ""
              	::= { snmp 14 }

          snmpInGetRequests OBJECT-TYPE
              	SYNTAX  Counter
              	ACCESS  read-only
              	STATUS  mandatory
DESCRIPTION ""
              	::= { snmp 15 }

          snmpInGetNexts OBJECT-TYPE
              	SYNTAX  Counter
              	ACCESS  read-only
              	STATUS  mandatory
DESCRIPTION ""
              	::= { snmp 16 }

          snmpInSetRequests OBJECT-TYPE
              	SYNTAX  Counter
              	ACCESS  read-only
              	STATUS  mandatory
DESCRIPTION ""
              	::= { snmp 17 }
	      	
          snmpInGetResponses OBJECT-TYPE
              	SYNTAX  Counter
              	ACCESS  read-only
              	STATUS  mandatory
DESCRIPTION ""
              	::= { snmp 18 }
	      	
          snmpInTraps OBJECT-TYPE
              	SYNTAX  Counter
              	ACCESS  read-only
              	STATUS  mandatory
DESCRIPTION ""
              	::= { snmp 19 }
	      	
          snmpOutTooBigs OBJECT-TYPE
              	SYNTAX  Counter
              	ACCESS  read-only
              	STATUS  mandatory
DESCRIPTION ""
              	::= { snmp 20 }
	      	
          snmpOutNoSuchNames OBJECT-TYPE
              	SYNTAX  Counter
              	ACCESS  read-only
              	STATUS  mandatory
DESCRIPTION ""
              	::= { snmp 21 }
	      	
          snmpOutBadValues OBJECT-TYPE
              	SYNTAX  Counter
              	ACCESS  read-only
              	STATUS  mandatory
DESCRIPTION ""
              	::= { snmp 22 }
	      	
       -- snmpOutReadOnlys OBJECT-TYPE
             -- SYNTAX  Counter
             -- ACCESS  read-only
             -- STATUS  mandatory
             -- ::=  { snmp 23 }

          snmpOutGenErrs OBJECT-TYPE
              	SYNTAX  Counter
              	ACCESS  read-only
              	STATUS  mandatory
DESCRIPTION ""
              	::= { snmp 24 }
	      	
          snmpOutGetRequests OBJECT-TYPE
              	SYNTAX  Counter
              	ACCESS  read-only
              	STATUS  mandatory
DESCRIPTION ""
              	::= { snmp 25 }
	      	
          snmpOutGetNexts OBJECT-TYPE
              	SYNTAX  Counter
              	ACCESS  read-only
              	STATUS  mandatory
DESCRIPTION ""
              	::= { snmp 26 }
	      	
          snmpOutSetRequests OBJECT-TYPE
              	SYNTAX  Counter
              	ACCESS  read-only
              	STATUS  mandatory
DESCRIPTION ""
              	::= { snmp 27 }
	      	
          snmpOutGetResponses OBJECT-TYPE
              	SYNTAX  Counter
              	ACCESS  read-only
              	STATUS  mandatory
DESCRIPTION ""
              	::= { snmp 28 }
	      	
          snmpOutTraps  OBJECT-TYPE
              	SYNTAX  Counter
              	ACCESS  read-only
              	STATUS  mandatory
DESCRIPTION ""
              	::= { snmp 29 }
	      	
          snmpEnableAuthenTraps OBJECT-TYPE
              	SYNTAX  INTEGER { enabled(1), disabled(2) }
              	ACCESS  read-write
              	STATUS  mandatory
DESCRIPTION ""
              	::= { snmp 30 }

-- Netcor NC007 Group

--	BUG:  Sadly, while the ACCESS type may be not-accessible,
--	read-write, or read-only, the write-only access type does
--	not work.  In fact, it makes the output mib.c file no good.

-- Requires BoxNo Only.

	  netcorResetBox OBJECT-TYPE 
        	SYNTAX  INTEGER
              	ACCESS  read-write
              	STATUS  mandatory
DESCRIPTION ""
              	::= { nc007 1 }

-- Requires BoxNo and Twisted Pair Port Number.

	  netcorDsLnkTst OBJECT-TYPE
        	SYNTAX  INTEGER 
              	ACCESS  read-write
              	STATUS  mandatory
DESCRIPTION ""
              	::= { nc007 2 }

	  netcorEnLnkTst OBJECT-TYPE
        	SYNTAX  INTEGER 
              	ACCESS  read-write
              	STATUS  mandatory
DESCRIPTION ""
              	::= { nc007 3 }

	  netcorLnkTstStat OBJECT-TYPE
        	SYNTAX  INTEGER 
              	ACCESS  read-only
              	STATUS  mandatory
DESCRIPTION ""
              	::= { nc007 4 }

	  netcorDsAutRxPolRev OBJECT-TYPE
        	SYNTAX  INTEGER 
              	ACCESS  read-write
              	STATUS  mandatory
DESCRIPTION ""
              	::= { nc007 5 }

	  netcorEnAutRxPolRev OBJECT-TYPE
        	SYNTAX  INTEGER 
              	ACCESS  read-write
              	STATUS  mandatory
DESCRIPTION ""
              	::= { nc007 6 }

	  netcorPolarityStat OBJECT-TYPE
        	SYNTAX  INTEGER 
              	ACCESS  read-only
              	STATUS  mandatory
DESCRIPTION ""
              	::= { nc007 7 }

-- Requires BoxNo Only.

	  netcorAltRecntAlg  OBJECT-TYPE
        	SYNTAX  INTEGER 
              	ACCESS  read-write
              	STATUS  mandatory
DESCRIPTION ""
              	::= { nc007 8 }

-- Requires BoxNo and Twisted Pair or AUI Port Number.

	  netcorPartitionStat	OBJECT-TYPE
        	SYNTAX  INTEGER 
              	ACCESS  read-only
              	STATUS  mandatory
DESCRIPTION ""
              	::= { nc007 9 }

	  netcorPortDisable OBJECT-TYPE
        	SYNTAX  INTEGER 
              	ACCESS  read-write
              	STATUS  mandatory
DESCRIPTION ""
              	::= { nc007 10 }

	  netcorPortEnable OBJECT-TYPE
        	SYNTAX  INTEGER 
              	ACCESS  read-write
              	STATUS  mandatory
DESCRIPTION ""
              	::= { nc007 11 }


          END
