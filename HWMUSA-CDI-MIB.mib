-- =================================================================
-- Copyright (C) 2003 by  HUAWEI TECHNOLOGIES. All rights reserved.
--
-- Description: Demonstrates how to maintain and config ATI ports
-- Reference:   None
-- Version:     V1.0    
-- History:
-- wangxinran, 2003-05-28, ATI MIB first define
-- =================================================================

    HWMUSA-CDI-MIB DEFINITIONS ::= BEGIN
 
        IMPORTS
            huaweiUtility            
                FROM HUAWEI-MIB            
            ifIndex            
                FROM IF-MIB            
            OBJECT-TYPE, MODULE-IDENTITY, NOTIFICATION-TYPE            
                FROM SNMPv2-SMI;
    
    
        hwCDI MODULE-IDENTITY 
           LAST-UPDATED "0305280900Z"
	     ORGANIZATION "Fix-Net Dep, Huawei Technologies Co.,Ltd."
	     CONTACT-INFO 
		"Floot 5 ,Block 4, R&D Building,
		Huawei Longgang Production Base,
		Shenzhen,  P.R.C.
		http://www.huawei.com
		Zip:518057
		"
            DESCRIPTION 
                "The HUAWEI-CDI-MIB demonstrates how to maintain and config CDI ports"
            ::= { huaweiUtility 26 }
        
    
    

    
        hwCDIPortObjects OBJECT IDENTIFIER ::= { hwCDI 1 }
        

        hwCDIPortTable OBJECT-TYPE
            SYNTAX SEQUENCE OF HwCDIPortEntry
            MAX-ACCESS not-accessible
            STATUS current
            DESCRIPTION
                "CDI port data table, the table supports port maintain and configure functions, 
                for example port attribute configuration , modification and query, port physical and service state query, port reset operation etc."
            ::= { hwCDIPortObjects 1 }
        
        hwCDIPortEntry OBJECT-TYPE
            SYNTAX HwCDIPortEntry
            MAX-ACCESS not-accessible
            STATUS current
            DESCRIPTION
                "CDI port data table, the table supports port maintain and configure functions, 
                for example port attribute configuration , modification and query, port physical and service state query, port reset operation etc."
            INDEX { ifIndex }
            ::= { hwCDIPortTable 1 }
        
        HwCDIPortEntry ::=
            SEQUENCE { 
                hwCDIRecvGain
                    INTEGER,
                hwCDITransGain
                    INTEGER,
                hwCDIDialMode
                    INTEGER,
                hwCDIDelayDial
                    INTEGER,
                hwCDIWorkMode
                    INTEGER,
                hwCDIRingMode
                    INTEGER,
                hwCDIUserName
                    OCTET STRING,
                hwCDIOperStatus
                    INTEGER,
                hwCDIServiceState
                    INTEGER,
                hwCDIAdminStatus
                    INTEGER
             }

        hwCDIRecvGain OBJECT-TYPE
            SYNTAX INTEGER
                {
            rg1 (1)  ,  -- -22.5DB(1) 
	    rg2 (2)  ,  -- -22.0DB(2) 
            rg3 (3)  ,  -- -21.5DB(3) 
            rg4 (4)  ,  -- -21.0DB(4) 
            rg5 (5)  ,  -- -20.5DB(5) 
	    rg6 (6)  ,  -- -20.0DB(6) 
            rg7 (7)  ,  -- -19.5DB(7) 
            rg8 (8)  ,  -- -19.0DB(8) 
            rg9 (9)  ,  -- -18.5DB(9) 
	    rg10(10) ,  -- -18.0DB(10)
            rg11(11) ,  -- -17.5DB(11)
            rg12(12) ,  -- -17.0DB(12)
            rg13(13) ,  -- -16.5DB(13)
	    rg14(14) ,  -- -16.0DB(14)
            rg15(15) ,  -- -15.5DB(15)
            rg16(16) ,  -- -15.0DB(16)
            rg17(17) ,  -- -14.5DB(17)
	    rg18(18) ,  -- -14.0DB(18)
            rg19(19) ,  -- -13.5DB(19)
            rg20(20) ,  -- -13.0DB(20)
            rg21(21) ,  -- -12.5DB(21)
	    rg22(22) ,  -- -12.0DB(22)
            rg23(23) ,  -- -11.5DB(23)
            rg24(24) ,  -- -11.0DB(24)
            rg25(25) ,  -- -10.5DB(25)
	    rg26(26) ,  -- -10.0DB(26)
            rg27(27) ,  -- - 9.5DB(27)
            rg28(28) ,  -- - 9.0DB(28)
            rg29(29) ,  -- - 8.5DB(29)
	    rg30(30) ,  -- - 8.0DB(30)
            rg31(31) ,  -- - 7.5DB(31)
            rg32(32) ,  -- - 7.0DB(32)
            rg33(33) ,  -- - 6.5DB(33)
	    rg34(34) ,  -- - 6.0DB(34)
            rg35(35) ,  -- - 5.5DB(35)
            rg36(36) ,  -- - 5.0DB(36)
            rg37(37) ,  -- - 4.5DB(37)
            rg38(38) ,  -- - 4.0DB(38)
            rg39(39) ,  -- - 3.5DB(39)
	    rg40(40)    -- - 3.0DB(40)
                }
            MAX-ACCESS read-write
            STATUS current
            DESCRIPTION
                " Recieve Gain  "
            DEFVAL { 11 }
            ::= { hwCDIPortEntry 1 }
        
        hwCDITransGain OBJECT-TYPE
            SYNTAX INTEGER
                {
            tg1 (1)  ,  -- - 8.5DB(1) 
            tg2 (2)  ,  -- - 8.0DB(2) 
            tg3 (3)  ,  -- - 7.5DB(3) 
            tg4 (4)  ,  -- - 7.0DB(4) 
            tg5 (5)  ,  -- - 6.5DB(5) 
            tg6 (6)  ,  -- - 6.0DB(6) 
            tg7 (7)  ,  -- - 5.5DB(7) 
            tg8 (8)  ,  -- - 5.0DB(8) 
            tg9 (9)  ,  -- - 4.5DB(9) 
            tg10(10) ,  -- - 4.0DB(10)
            tg11(11) ,  -- - 3.5DB(11)
            tg12(12) ,  -- - 3.0DB(12)
            tg13(13) ,  -- - 2.5DB(13)
            tg14(14) ,  -- - 2.0DB(14)
            tg15(15) ,  -- - 1.5DB(15)
            tg16(16) ,  -- - 1.0DB(16)
            tg17(17) ,  -- - 0.5DB(17)
            tg18(18) ,  --     0DB(18)
            tg19(19) ,  -- + 0.5DB(19)
            tg20(20) ,  -- + 1.0DB(20)
            tg21(21) ,  -- + 1.5DB(21)
            tg22(22) ,  -- + 2.0DB(22)
            tg23(23) ,  -- + 2.5DB(23)
            tg24(24) ,  -- + 3.0DB(24)
            tg25(25) ,  -- + 3.5DB(25)
            tg26(26) ,  -- + 4.0DB(26)
            tg27(27) ,  -- + 4.5DB(27)
            tg28(28) ,  -- + 5.0DB(28)
            tg29(29) ,  -- + 5.5DB(29)
            tg30(30) ,  -- + 6.0DB(30)
            tg31(31) ,  -- + 6.5DB(31)
            tg32(32) ,  -- + 7.0DB(32)
            tg33(33) ,  -- + 7.5DB(33)
            tg34(34) ,  -- + 8.0DB(34)
            tg35(35) ,  -- + 8.5DB(35)
            tg36(36) ,  -- + 9.0DB(36)
            tg37(37) ,  -- + 9.5DB(37)
            tg38(38) ,  -- +10.0DB(38)
            tg39(39) ,  -- +10.5DB(39)
            tg40(40) ,  -- +11.0DB(40)
            tg41(41) ,  -- +11.5DB(41)
            tg42(42) ,  -- +12.0DB(42)
            tg43(43) ,  -- +12.5DB(43)
            tg44(44)    -- +13.0DB(44)      
                }
            MAX-ACCESS read-write
            STATUS current
            DESCRIPTION
                " Transmit Gain "
            DEFVAL { 11 }
            ::= { hwCDIPortEntry 2 }
        
        hwCDIDialMode OBJECT-TYPE
            SYNTAX INTEGER
                {
            pulse(1),  -- Pulse dial mode
            dtmf(2)    -- Dtmf dial mode
                }
            MAX-ACCESS read-write
            STATUS current
            DESCRIPTION
                " Dial Mode "
            DEFVAL { 2 }
            ::= { hwCDIPortEntry 3 }
        
        hwCDIDelayDial OBJECT-TYPE
            SYNTAX INTEGER
                {
            noneDelayDial(1), -- None delay dial
            delayDial(2)      -- Delay dial
                }
            MAX-ACCESS read-write
            STATUS current
            DESCRIPTION
                " Delay Dial Mode"
            DEFVAL { 1 }
            ::= { hwCDIPortEntry 4 }
        
        hwCDIWorkMode OBJECT-TYPE
            SYNTAX INTEGER
                {
            at0(1),    -- AT0 workmode
            ddi(2)     -- DDI workmode
                }
            MAX-ACCESS read-write
            STATUS current
            DESCRIPTION
                " Work Mode  "
            DEFVAL { 2 }
            ::= { hwCDIPortEntry 5 }
        
        hwCDIRingMode OBJECT-TYPE
            SYNTAX INTEGER
                {
            r1 (1)  ,  -- NULL
            r2 (2)  ,  -- Normal 1:4 
            r3 (3)  ,  -- Special 1:2
            r4 (4)  ,  -- Hk 0.4:0.2:0.4:4
            r5 (5)  ,  -- LongRing  
            r6 (6)  ,  -- Special 1.2:2
            r7 (7)  ,  -- HKRing 1:3
            r8 (8)  ,  -- HK CNTRX 0.4:0.2:0.4:0.2:0.4:3.0
            r9 (9)  ,  -- HK DN-A 0.4:0.2:0.4:3.0
            r10(10) ,  -- HK ACB 0.4:0.2
            r11(11) ,  -- HK Reminder 0.4s Ring(only one)
            r12(12) ,  -- HK DN-B 1.2:3
            r13(13) ,  -- CNTRX_IN 0.4:0.2:0.4:0.2:2.6
            r14(14) ,  -- Egypt Ring 2:1
            r15(15) ,  -- User Self-define 0
            r16(16) ,  -- User Self-define 1
            r17(17) ,  -- User Self-define 2
            r18(18) ,  -- User Self-define 3
            r19(19) ,  -- User Self-define 4
            r20(20) ,  -- User Self-define 5
            r21(21) ,  -- User Self-define 6
            r22(22) ,  -- User Self-define 7
            r23(23) ,  -- User Self-define 8
            r24(24) ,  -- User Self-define 9
            r25(25) ,  -- User Self-define 10
            r26(26) ,  -- User Self-define 11
            r27(27) ,  -- User Self-define 12
            r28(28) ,  -- User Self-define 13
            r29(29) ,  -- User Self-define 14
            r30(30)    -- User Self-define 15      
                }
            MAX-ACCESS read-write
            STATUS current
            DESCRIPTION
                " Ring Mode "
            DEFVAL { 1 }
            ::= { hwCDIPortEntry 6 }
        
        hwCDIUserName OBJECT-TYPE
            SYNTAX OCTET STRING (SIZE (0..10))
            MAX-ACCESS read-write
            STATUS current
            DESCRIPTION
                " Port identification  "
            ::= { hwCDIPortEntry 7 }
        
        hwCDIOperStatus OBJECT-TYPE
            SYNTAX INTEGER
                {
            idle(1),   -- idle
            fault(2),  -- fault
            busy(3)    -- busy
                }
            MAX-ACCESS read-only
            STATUS current
            DESCRIPTION
                " Port state "
            ::= { hwCDIPortEntry 8 }
        
        hwCDIServiceState OBJECT-TYPE
            SYNTAX INTEGER
                {
            normal(1),   -- service is normal
            abnormal(2)  -- service is abnormal
                }
            MAX-ACCESS read-only
            STATUS current
            DESCRIPTION
                " Port service state "
            ::= { hwCDIPortEntry 9 }
        
        hwCDIAdminStatus OBJECT-TYPE
            SYNTAX INTEGER { reset(1) }
            MAX-ACCESS read-write
            STATUS current
            DESCRIPTION
                " Port admin status   "
            ::= { hwCDIPortEntry 10 }
        
        hwCDIPortTraps OBJECT IDENTIFIER ::= { hwCDI 2 }
        
        hwCDIPortAlarmVbOids OBJECT IDENTIFIER ::= { hwCDIPortTraps 1 }
        
        hwCDIPortTrapVbOidsReason OBJECT IDENTIFIER ::= { hwCDIPortAlarmVbOids 1 }
        

        hwCauseCDIPortNoPower OBJECT-TYPE
            SYNTAX INTEGER { userLineFault(1) }
            MAX-ACCESS read-only
            STATUS current
            DESCRIPTION
                " CDI Port nopower alarms reasons "
            ::= { hwCDIPortTrapVbOidsReason 1 }
        
        hwCDIPortAlarmTrap OBJECT IDENTIFIER ::= { hwCDIPortTraps 2 }
        
        hwCDIPortAlarmTraps OBJECT IDENTIFIER ::= { hwCDIPortAlarmTrap 0 }
        
        hwAlarmCDIPortNoPower NOTIFICATION-TYPE
            OBJECTS { ifIndex, hwCauseCDIPortNoPower }
            STATUS current
            DESCRIPTION 
                " CDI Port is no power or userline is fault "
            ::= { hwCDIPortAlarmTraps 1 }
        
    
    END
