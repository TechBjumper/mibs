-- ============================================================================
-- Copyright (C) 2012 by HUAWEI TECHNOLOGIES. All rights reserved.
--
-- Description: This mib is used for defining huawei's PBX MIB objects, which provides PBX management.
-- Reference:
-- Version: V1.0
-- History:
-- ============================================================================

HUAWEI-ENT-VOICE-PBX-MIB DEFINITIONS ::= BEGIN
    IMPORTS
        MODULE-IDENTITY, OBJECT-TYPE, NOTIFICATION-TYPE, private
            FROM SNMPv2-SMI
        MODULE-COMPLIANCE, OBJECT-GROUP, NOTIFICATION-GROUP
            FROM SNMPv2-CONF
        TEXTUAL-CONVENTION
            FROM SNMPv2-TC
        IpAddress, TimeTicks, Counter32, Integer32, Unsigned32, Counter64
            FROM SNMPv2-SMI
        RowStatus, DisplayString
            FROM SNMPv2-TC
        hwDatacomm
            FROM HUAWEI-MIB;

hwEntVoicePbxMIB MODULE-IDENTITY
    LAST-UPDATED "201203060000Z"
    ORGANIZATION 
              "Huawei Technologies Co.,Ltd."
    CONTACT-INFO 
              "Huawei Industrial Base                
              Bantian, Longgang                     
              Shenzhen 518129                       
              People's Republic of China            
              Website: http://www.huawei.com        
              Email: support@huawei.com             
              "   
    DESCRIPTION
        "This mib is used for defining huawei's PBX MIB objects, which provides PBX management."

    -- Revision history

    REVISION     "201203070000Z"
    DESCRIPTION  "V1.0, create this file."

::= { hwDatacomm 313 }

  --========================================================================

   hwEntPbxEnterpriseTable OBJECT-TYPE
     SYNTAX      SEQUENCE OF HwEntPbxEnterpriseEntry
     MAX-ACCESS  not-accessible
     STATUS      current
     DESCRIPTION
       "
       A list of hwEntPbxEnterpriseEntry objects.
       "
     ::= { hwEntVoicePbxMIB 1 }

   hwEntPbxEnterpriseEntry OBJECT-TYPE
     SYNTAX      HwEntPbxEnterpriseEntry
     MAX-ACCESS  not-accessible
     STATUS      current
     DESCRIPTION
       "A list of hwEntPbxEnterpriseEntry objects."
     INDEX    {
               hwEntPbxEnterpriseName
              }
     ::= { hwEntPbxEnterpriseTable 1 }

   HwEntPbxEnterpriseEntry ::=
     SEQUENCE
     {
       hwEntPbxEnterpriseName            DisplayString,
       hwEntPbxEnterpriseRowStatus       RowStatus,
       hwEntPbxEnterpriseDesc            DisplayString,
       hwEntPbxEnterpriseCentrexNum      Integer32,
       hwEntPbxEnterpriseDnsetNum        Integer32,
       hwEntPbxEnterpriseSvrRightCrbt    INTEGER
     }

   hwEntPbxEnterpriseName OBJECT-TYPE
     SYNTAX      DisplayString(SIZE(1..32))
     MAX-ACCESS  not-accessible
     STATUS      current
     DESCRIPTION
         "
         Indicates the Enterprise Name.
         "
     ::= { hwEntPbxEnterpriseEntry 1 }

   hwEntPbxEnterpriseRowStatus OBJECT-TYPE
     SYNTAX      RowStatus
     MAX-ACCESS  read-create
     STATUS      current
     DESCRIPTION
         "
             Indicates row status of table.
         "
     ::= { hwEntPbxEnterpriseEntry 2 }

   hwEntPbxEnterpriseDesc OBJECT-TYPE
     SYNTAX      DisplayString(SIZE(0..64))
     MAX-ACCESS  read-create
     STATUS      current
     DESCRIPTION
         "
         Indicates the description of Enterprise.
         "
     ::= { hwEntPbxEnterpriseEntry 3 }

   hwEntPbxEnterpriseCentrexNum OBJECT-TYPE
     SYNTAX      Integer32(1..65535)
     MAX-ACCESS  read-create
     STATUS      current
     DESCRIPTION
         "
         Indicates the Centrex Number of Enterprise.
         default: 4
         "
     ::= { hwEntPbxEnterpriseEntry 4 }

   hwEntPbxEnterpriseDnsetNum OBJECT-TYPE
     SYNTAX      Integer32(1..65535)
     MAX-ACCESS  read-only
     STATUS      current
     DESCRIPTION
         "
         Indicates the Dnset Number of Enterprise.
         "
     ::= { hwEntPbxEnterpriseEntry 5 }

   hwEntPbxEnterpriseSvrRightCrbt OBJECT-TYPE
     SYNTAX      INTEGER{disable(1), enable(2)}
     MAX-ACCESS  read-create
     STATUS      current
     DESCRIPTION
         "
         Indicates the crbt service right of Enterprise.
         disable(1)   - have no right
         enable(2)    - have right
         "
     ::= { hwEntPbxEnterpriseEntry 6 }

 --==================================================================

 hwEntPbxDnsetTable OBJECT-TYPE
     SYNTAX      SEQUENCE OF HwEntPbxDnsetEntry
     MAX-ACCESS  not-accessible
     STATUS      current
     DESCRIPTION
       "
       A list of hwEntPbxDnsetEntry objects.
       "
     ::= { hwEntVoicePbxMIB 2 }

   hwEntPbxDnsetEntry OBJECT-TYPE
     SYNTAX      HwEntPbxDnsetEntry
     MAX-ACCESS  not-accessible
     STATUS      current
     DESCRIPTION
       "A list of hwEntPbxDnsetEntry objects."
     INDEX    {
                hwEntPbxDnsetEnterpriseName,
                hwEntPbxDnsetName
              }
     ::= { hwEntPbxDnsetTable 1 }

   HwEntPbxDnsetEntry ::=
     SEQUENCE
     {
       hwEntPbxDnsetEnterpriseName     DisplayString,
       hwEntPbxDnsetName               DisplayString,
       hwEntPbxDnsetRowStatus          RowStatus,
       hwEntPbxDnsetDesc               DisplayString
     }

   hwEntPbxDnsetEnterpriseName OBJECT-TYPE
     SYNTAX      DisplayString(SIZE(1..32))
     MAX-ACCESS  not-accessible
     STATUS      current
     DESCRIPTION
         "
         Indicates the Enterprise Name.
         "
     ::= { hwEntPbxDnsetEntry 1 }

   hwEntPbxDnsetName OBJECT-TYPE
     SYNTAX      DisplayString(SIZE (1..32))
     MAX-ACCESS  not-accessible
     STATUS      current
     DESCRIPTION
         "
         Indicates the name of DN set.
         "
     ::= { hwEntPbxDnsetEntry 2 }

   hwEntPbxDnsetRowStatus OBJECT-TYPE
     SYNTAX      RowStatus
     MAX-ACCESS  read-create
     STATUS      current
     DESCRIPTION
         "
             Indicates row status of table.
         "
     ::= { hwEntPbxDnsetEntry 3 }

   hwEntPbxDnsetDesc OBJECT-TYPE
     SYNTAX      DisplayString(SIZE (0..64))
     MAX-ACCESS  read-create
     STATUS      current
     DESCRIPTION
         "
         Indicates the description of Dnset.
         "
     ::= { hwEntPbxDnsetEntry 4 }

 --==================================================================

   hwEntPbxCentrexTable OBJECT-TYPE
     SYNTAX      SEQUENCE OF HwEntPbxCentrexEntry
     MAX-ACCESS  not-accessible
     STATUS      current
     DESCRIPTION
       "
       A list of hwEntPbxCentrexEntry objects.
       "
     ::= { hwEntVoicePbxMIB 3 }

   hwEntPbxCentrexEntry OBJECT-TYPE
     SYNTAX      HwEntPbxCentrexEntry
     MAX-ACCESS  not-accessible
     STATUS      current
     DESCRIPTION
       "A list of hwEntPbxCentrexEntry objects."
     INDEX    {
               hwEntPbxCentrexEnterpriseName,
               hwEntPbxCentrexName
              }
     ::= { hwEntPbxCentrexTable 1 }

   HwEntPbxCentrexEntry ::=
     SEQUENCE
     {
       hwEntPbxCentrexEnterpriseName     DisplayString,
       hwEntPbxCentrexName               DisplayString,
       hwEntPbxCentrexRowStatus          RowStatus,
       hwEntPbxCentrexDesc               DisplayString
     }

   hwEntPbxCentrexEnterpriseName OBJECT-TYPE
     SYNTAX      DisplayString(SIZE(1..32))
     MAX-ACCESS  not-accessible
     STATUS      current
     DESCRIPTION
         "
         Indicates the Enterprise Name.
         "
     ::= { hwEntPbxCentrexEntry 1 }

   hwEntPbxCentrexName OBJECT-TYPE
     SYNTAX      DisplayString(SIZE (1..32))
     MAX-ACCESS  not-accessible
     STATUS      current
     DESCRIPTION
         "
         Indicates the name of Centrex Group .
         "
     ::= { hwEntPbxCentrexEntry 2 }

   hwEntPbxCentrexRowStatus OBJECT-TYPE
     SYNTAX      RowStatus
     MAX-ACCESS  read-create
     STATUS      current
     DESCRIPTION
         "
             Indicates row status of table.
         "
     ::= { hwEntPbxCentrexEntry 3 }

   hwEntPbxCentrexDesc OBJECT-TYPE
     SYNTAX      DisplayString(SIZE (0..64))
     MAX-ACCESS  read-create
     STATUS      current
     DESCRIPTION
         "
         Indicates the description of Centrex Group.
         "
     ::= { hwEntPbxCentrexEntry 4 }

 --==================================================================

   hwEntPbxCountryCodeTable OBJECT-TYPE
     SYNTAX      SEQUENCE OF HwEntPbxCountryCodeEntry
     MAX-ACCESS  not-accessible
     STATUS      current
     DESCRIPTION
       "
       A list of hwEntPbxCountryCodeEntry objects.
       "
     ::= { hwEntVoicePbxMIB 4 }

   hwEntPbxCountryCodeEntry OBJECT-TYPE
     SYNTAX      HwEntPbxCountryCodeEntry
     MAX-ACCESS  not-accessible
     STATUS      current
     DESCRIPTION
       "A list of hwEntPbxCountryCodeEntry objects."
     INDEX    {
               hwEntPbxCountryCode
              }
     ::= { hwEntPbxCountryCodeTable 1 }
  HwEntPbxCountryCodeEntry ::=
     SEQUENCE
     {
       hwEntPbxCountryCode                   DisplayString,
       hwEntPbxCountryCodeRowStatus          RowStatus,
       hwEntPbxCountryName                   DisplayString,
       hwEntPbxInternationalPrefix           DisplayString,
       hwEntPbxNationalPrefix                DisplayString

     }

   hwEntPbxCountryCode OBJECT-TYPE
     SYNTAX      DisplayString(SIZE (1..4))
     MAX-ACCESS  not-accessible
     STATUS      current
     DESCRIPTION
         "
         Indicates the country/region code.
         "
     ::= { hwEntPbxCountryCodeEntry 1 }

   hwEntPbxCountryCodeRowStatus OBJECT-TYPE
     SYNTAX      RowStatus
     MAX-ACCESS  read-create
     STATUS      current
     DESCRIPTION
         "
             Indicates row status of table.
         "
     ::= { hwEntPbxCountryCodeEntry 2 }

   hwEntPbxCountryName OBJECT-TYPE
     SYNTAX      DisplayString(SIZE (0..32))
     MAX-ACCESS  read-create
     STATUS      current
     DESCRIPTION
         "
         Indicates the country/region name.
         "
     ::= { hwEntPbxCountryCodeEntry 3 }

   hwEntPbxInternationalPrefix OBJECT-TYPE
     SYNTAX      DisplayString(SIZE (0..5))
     MAX-ACCESS  read-create
     STATUS      current
     DESCRIPTION
         "
         Indicates the international prefix.
         "
     ::= { hwEntPbxCountryCodeEntry 4 }

   hwEntPbxNationalPrefix OBJECT-TYPE
     SYNTAX      DisplayString(SIZE (0..5))
     MAX-ACCESS  read-create
     STATUS      current
     DESCRIPTION
         "
         Indicates the national prefix.
         "
     ::= { hwEntPbxCountryCodeEntry 5 }

 --==================================================================

 hwEntPbxAreaCodeTable OBJECT-TYPE
     SYNTAX      SEQUENCE OF HwEntPbxAreaCodeEntry
     MAX-ACCESS  not-accessible
     STATUS      current
     DESCRIPTION
       "
       A list of hwEntPbxAreaCodeEntry objects.
       "
     ::= { hwEntVoicePbxMIB 5 }

   hwEntPbxAreaCodeEntry OBJECT-TYPE
     SYNTAX      HwEntPbxAreaCodeEntry
     MAX-ACCESS  not-accessible
     STATUS      current
     DESCRIPTION
       "A list of hwEntPbxAreaCodeEntry objects."
     INDEX    {
               hwEntPbxAreaCodeCountryCode,
               hwEntPbxAreaCode
              }
     ::= { hwEntPbxAreaCodeTable 1 }
  HwEntPbxAreaCodeEntry ::=
     SEQUENCE
     {
       hwEntPbxAreaCodeCountryCode       DisplayString,
       hwEntPbxAreaCode                  DisplayString,
       hwEntPbxAreaCodeRowStatus         RowStatus,
       hwEntPbxAreaName                  DisplayString
     }

   hwEntPbxAreaCodeCountryCode OBJECT-TYPE
     SYNTAX      DisplayString(SIZE (1..4))
     MAX-ACCESS  not-accessible
     STATUS      current
     DESCRIPTION
         "
         Indicates the country/region code.
         "
     ::= { hwEntPbxAreaCodeEntry 1 }

   hwEntPbxAreaCode OBJECT-TYPE
     SYNTAX      DisplayString(SIZE (1..8))
     MAX-ACCESS  not-accessible
     STATUS      current
     DESCRIPTION
         "
         Indicates the Area code.
         "
     ::= { hwEntPbxAreaCodeEntry 2 }

   hwEntPbxAreaCodeRowStatus OBJECT-TYPE
     SYNTAX      RowStatus
     MAX-ACCESS  read-create
     STATUS      current
     DESCRIPTION
         "
             Indicates row status of table.
         "
     ::= { hwEntPbxAreaCodeEntry 3 }

   hwEntPbxAreaName OBJECT-TYPE
     SYNTAX      DisplayString(SIZE (0..32))
     MAX-ACCESS  read-create
     STATUS      current
     DESCRIPTION
         "
         Indicates the Area name.
         "
     ::= { hwEntPbxAreaCodeEntry 4 }

--=============================================================

  hwEntPbxDefaultCodeTable OBJECT IDENTIFIER  ::= { hwEntVoicePbxMIB 6 }

  hwEntDefaultCountryCode  OBJECT-TYPE
        SYNTAX DisplayString(SIZE (1..4))
        MAX-ACCESS read-write
        STATUS current
        DESCRIPTION
              "
              Indicates the default country code.
              "
    ::= { hwEntPbxDefaultCodeTable 1 }

   hwEntDefaultAreaCode  OBJECT-TYPE
        SYNTAX DisplayString(SIZE (1..8))
        MAX-ACCESS read-write
        STATUS current
        DESCRIPTION
              "
              Indicates the default area code.
              "
    ::= { hwEntPbxDefaultCodeTable 2 }

 --=============================================================

  hwEntPbxCallprefixTable OBJECT-TYPE
     SYNTAX      SEQUENCE OF HwEntPbxCallprefixEntry
     MAX-ACCESS  not-accessible
     STATUS      current
     DESCRIPTION
       "
       A list of HwEntPbxCallprefixEntry objects.
       "
     ::= { hwEntVoicePbxMIB 7 }

  hwEntPbxCallprefixEntry OBJECT-TYPE
     SYNTAX      HwEntPbxCallprefixEntry
     MAX-ACCESS  not-accessible
     STATUS      current
     DESCRIPTION
       "A list of hwEntPbxCallprefixEntry objects."
     INDEX    {
               hwEntPbxCallprefixName
              }
     ::= { hwEntPbxCallprefixTable 1 }

  HwEntPbxCallprefixEntry ::=
     SEQUENCE
     {
       hwEntPbxCallprefixName                DisplayString,
       hwEntPbxCallprefixRowStatus           RowStatus,
       hwEntPbxCallprefixPrefix              DisplayString,
       hwEntPbxCallprefixEnterprise          DisplayString,
       hwEntPbxCallprefixDnset               DisplayString,
       hwEntPbxCallprefixCentrex             DisplayString,
       hwEntPbxCallprefixcallCategory        INTEGER,
       hwEntPbxCallprefixCallAttribute       Integer32,
       hwEntPbxCallprefixMaxLen              Integer32,
       hwEntPbxCallprefixMinLen              Integer32,
       hwEntPbxCallprefixDstLocation         INTEGER,
       hwEntPbxCallprefixRingDelay           Integer32,
       hwEntPbxCallprefixLongCaller          INTEGER,
       hwEntPbxCallprefixCallerMap           INTEGER,
       hwEntPbxCallprefixCalledMap           INTEGER,
       hwEntPbxCallprefixCallRoute           DisplayString,
       hwEntPbxCallprefixVuServiceName       DisplayString,
       hwEntPbxCallprefixVuLoopCount         Integer32,
       hwEntPbxCallprefixVuOutGoingRightDdd  INTEGER,
       hwEntPbxCallprefixVuOutGoingRightIdd  INTEGER,
       hwEntPbxCallprefixVuOutGoingRightInter  INTEGER,
       hwEntPbxCallprefixVuOutGoingRightLocal  INTEGER,
       hwEntPbxCallprefixPwdCallLimit          INTEGER
     }

   hwEntPbxCallprefixName OBJECT-TYPE
     SYNTAX      DisplayString(SIZE (1..32))
     MAX-ACCESS  not-accessible
     STATUS      current
     DESCRIPTION
         "
         Indicates the Callprefix name.
         "
     ::= { hwEntPbxCallprefixEntry 1 }

   hwEntPbxCallprefixRowStatus OBJECT-TYPE
     SYNTAX      RowStatus
     MAX-ACCESS  read-create
     STATUS      current
     DESCRIPTION
         "
             Indicates row status of table.
         "
     ::= { hwEntPbxCallprefixEntry 2 }

   hwEntPbxCallprefixPrefix OBJECT-TYPE
     SYNTAX      DisplayString(SIZE (1..24))
     MAX-ACCESS  read-create
     STATUS      current
     DESCRIPTION
         "
         Indicates the Callprefix.
         "
     ::= { hwEntPbxCallprefixEntry 3 }

   hwEntPbxCallprefixEnterprise OBJECT-TYPE
     SYNTAX      DisplayString(SIZE (1..32))
     MAX-ACCESS  read-create
     STATUS      current
     DESCRIPTION
         "
         Indicates the enterprise name of Callprefix.
         "
     ::= { hwEntPbxCallprefixEntry 4 }

   hwEntPbxCallprefixDnset OBJECT-TYPE
     SYNTAX      DisplayString(SIZE (1..32))
     MAX-ACCESS  read-create
     STATUS      current
     DESCRIPTION
         "
         Indicates the Dnset of Callprefix.
         "
     ::= { hwEntPbxCallprefixEntry 5 }

  hwEntPbxCallprefixCentrex OBJECT-TYPE
     SYNTAX      DisplayString(SIZE (1..32))
     MAX-ACCESS  read-create
     STATUS      current
     DESCRIPTION
         "
         Indicates the Centrex name of Callprefix.
         "
     ::= { hwEntPbxCallprefixEntry 6 }

  hwEntPbxCallprefixcallCategory OBJECT-TYPE
     SYNTAX      INTEGER{basic(1), newSupMan(2), supp(3), vu(4)}
     MAX-ACCESS  read-create
     STATUS      current
     DESCRIPTION
         "
         Indicates the Call Category.
         basic(1)      - basic-service,
         newSupMan(2)  - new/supplementary service management,
         supp(3)       - supplementary service,
         vu(4)         - vu-service
         "
     ::= { hwEntPbxCallprefixEntry 7 }

   hwEntPbxCallprefixCallAttribute OBJECT-TYPE
     SYNTAX      Integer32(1..192)
     MAX-ACCESS  read-create
     STATUS      current
     DESCRIPTION
         "
         Indicates the Call Attribute.
         1:local,
         2:national-toll,
         3:international-toll,
         4:InnerCentrex,
         5:OutCentrex,
         6:Selection-Enterprise,
         7-20:Basic service reserve,
         22:RCFU,
         23:CCFU,
         24:RCFB,
         25:CCFB,
         26:RCFNR,
         27:CCFNR,
         28:RCFO,
         29:CCFO,
         30:Reserve,
         31:Reserve,
         32:RCW,
         33:CCW,
         34:Reserve,
         35:Reserve,
         36:RDND,
         37:CDND,
         38:RADI,
         39:CADI,
         40:RRAC,
         41:CRAC,
         42:RWakeUp,
         43:CWakeUp,
         44:Reserve,
         45:Reserve,
         46:QCFU,
         47:QCFB,
         48:QCFNR,
         49:QCFO,
         50:RRCS-by-caller,
         51:CRCS-by-caller,
         52:RRCS-by-time,
         53:CRCS-by-time,
         54:RRCS-by-week,
         55:CRCS-by-week,
         56:Active RCS,
         57:DeActive RCS,
         58:QRCS,
         59:CRCS-all,
         60:RSCA-by-caller,
         61:CSCA-by-caller,
         62:RSCA-by-time,
         63:CSCA-by-time,
         64:RSCA-by-week,
         65:CSCA-by-week,
         66:Active SCA,
         67:DeActive SCA,
         68:QSCA,
         69:CSCA-all,
         70:RRMTOFFICE,
         71:CRMTOFFICE,
         72:QRMTOFFICE,
         73:RSCR,
         74:CSCR,
         75:QSCR,
         76:CSCC,
         77:CSCC-PWD,
         78:CFX-PWD
         79:RRCFU,
         80:CRCFU,
         81:RRCFB,
         82:CRCFB,
         83:RRCFNR,
         84:CRCFNR,
         85:RRCFO,
         86:CRCFO,
         87:DLC-PWD,
         88:QDLC,
         89:RDLC,
         90:CDLC,
         91:Active DLC,
         92:DeActive DLC,
         93:CDLCA,
         94:Set-Grp-Online,
         95:Set-Grp-Offline,
         96:Active-Pwcb,
         97:Deactive-Pwcb,
         98:PWCB-PWD,
         99:RCBA,
         100:MCBA-PWD,
         101:QCBA,
         102:CCBA,
         103:Reg-MSN-Index,
         104:rccbs,
         105:cccbs,
         106:qccbs,
         107:rccnr,
         108:cccnr,
         109:qccnr,
         110:rvcfu,
         111:cvcfu,
         112:qvcfu,
         113:rvcfb,
         114:cvcfb,
         115:qvcfb,
         116:rvcfnr,
         117:cvcfnr,
         118:qvcfnr,
         119:rvcfo,
         120:cvcfo,
         121:qvcfo,
         122-170: new/supplementary service management reserved,
         172:GRPANSWER,
         173:SPECANSWER
         174:local telno query,
         175:ADI
         176:Active CLIR,
         177:Cancel CLIR
         178:Park Start,
         179:Park Recover,
         180:PWCB,
         181:MSN Index Select,
         182:callreturn,
         183:outgoing-call-memory,
         184:incoming-call-memory
         185:ums-get-message,
         186:ums-uniform-fax,
         187:ums-faxmail,
         188:Conference,
         189:Select-group-num,
         190:Select-user-num,
         191:Select-group-index
         192:Instant-conference
         "
     ::= { hwEntPbxCallprefixEntry 8 }

   hwEntPbxCallprefixDstLocation OBJECT-TYPE
     SYNTAX      INTEGER{intraOffice(1), interOffice(2)}
     MAX-ACCESS  read-create
     STATUS      current
     DESCRIPTION
         "
         Indicates the Call Category.
         intraOffice(1)   - intra-office call,
         interOffice(2)   - inter-office call,
         "
     ::= { hwEntPbxCallprefixEntry 9 }


  hwEntPbxCallprefixMaxLen OBJECT-TYPE
     SYNTAX      Integer32(1..44)
     MAX-ACCESS  read-create
     STATUS      current
     DESCRIPTION
         "
         Indicates maximum length of the Callprefix.
         "
     ::= { hwEntPbxCallprefixEntry 10 }

  hwEntPbxCallprefixMinLen OBJECT-TYPE
     SYNTAX      Integer32(1..44)
     MAX-ACCESS  read-create
     STATUS      current
     DESCRIPTION
         "
         Indicates minimum length of the Callprefix.
         "
     ::= { hwEntPbxCallprefixEntry 11 }

  hwEntPbxCallprefixRingDelay OBJECT-TYPE
     SYNTAX      Integer32(0..255)
     MAX-ACCESS  read-create
     STATUS      current
     DESCRIPTION
         "
         Indicates Ring Delay of Callprefix.
         default: 0
         "
     ::= { hwEntPbxCallprefixEntry 12 }
          
   hwEntPbxCallprefixLongCaller OBJECT-TYPE
     SYNTAX      INTEGER{disable(1), enable(2)}
     MAX-ACCESS  read-create
     STATUS      current
     DESCRIPTION
         "
         Indicates the long caller of call prefix.
         disable(1)   - disable long caller,
         enable(2)   - enable long caller,
         "
     ::= { hwEntPbxCallprefixEntry 13 }

   hwEntPbxCallprefixCallerMap OBJECT-TYPE
     SYNTAX      INTEGER{disable(1), enable(2)}
     MAX-ACCESS  read-create
     STATUS      current
     DESCRIPTION
         "
         Indicates the caller map of call prefix.
         disable(1)   - disable caller map,
         enable(2)   - enable caller map,
         "
     ::= { hwEntPbxCallprefixEntry 14 }

   hwEntPbxCallprefixCalledMap OBJECT-TYPE
     SYNTAX      INTEGER{disable(1), enable(2)}
     MAX-ACCESS  read-create
     STATUS      current
     DESCRIPTION
         "
         disable the called map of call prefix.
         disable(1)   - disable called map,
         enable(2)   - enable called map,
         "
     ::= { hwEntPbxCallprefixEntry 15 }

   hwEntPbxCallprefixCallRoute OBJECT-TYPE
     SYNTAX      DisplayString(SIZE (1..32))
     MAX-ACCESS  read-create
     STATUS      current
     DESCRIPTION
         "
         Indicates the Callroute of Callprefix.
         "
     ::= { hwEntPbxCallprefixEntry 16 }

   hwEntPbxCallprefixVuServiceName OBJECT-TYPE
     SYNTAX      DisplayString(SIZE (1..32))
     MAX-ACCESS  read-create
     STATUS      current
     DESCRIPTION
         "
         Indicates the Vu service-name bond to Callprefix.
         "
     ::= { hwEntPbxCallprefixEntry 17 }

   hwEntPbxCallprefixVuLoopCount OBJECT-TYPE
     SYNTAX      Integer32(0..6)
     MAX-ACCESS  read-create
     STATUS      current
     DESCRIPTION
         "
         Indicates the Vu loop count of Vu Callprefix.
         "
     ::= { hwEntPbxCallprefixEntry 18 }

   hwEntPbxCallprefixVuOutGoingRightDdd OBJECT-TYPE
     SYNTAX      INTEGER{disable(1), enable(2)}
     MAX-ACCESS  read-create
     STATUS      current
     DESCRIPTION
         "
         Indicates the outgoing right (ddd) of VU Callprefix.
         "
     ::= { hwEntPbxCallprefixEntry 19 }

   hwEntPbxCallprefixVuOutGoingRightIdd OBJECT-TYPE
     SYNTAX      INTEGER{disable(1), enable(2)}
     MAX-ACCESS  read-create
     STATUS      current
     DESCRIPTION
         "
         Indicates the outgoing right (idd) of VU Callprefix.
         "
     ::= { hwEntPbxCallprefixEntry 20 }

   hwEntPbxCallprefixVuOutGoingRightInter OBJECT-TYPE
     SYNTAX      INTEGER{disable(1), enable(2)}
     MAX-ACCESS  read-create
     STATUS      current
     DESCRIPTION
         "
         Indicates the outgoing right (inter) of VU Callprefix.
         "
     ::= { hwEntPbxCallprefixEntry 21 }

   hwEntPbxCallprefixVuOutGoingRightLocal OBJECT-TYPE
     SYNTAX      INTEGER{disable(1), enable(2)}
     MAX-ACCESS  read-create
     STATUS      current
     DESCRIPTION
         "
         Indicates the outgoing right (local) of VU Callprefix.
         "
     ::= { hwEntPbxCallprefixEntry 22 }

   hwEntPbxCallprefixPwdCallLimit OBJECT-TYPE
     SYNTAX      INTEGER{disable(1), enable(2)}
     MAX-ACCESS  read-create
     STATUS      current
     DESCRIPTION
         "
         Indicates the Passwordd-CallLimit right of Callprefix.
         "
     ::= { hwEntPbxCallprefixEntry 23 }

                                
  --==============================================================
    hwEntPbxSIPServerConfigTable OBJECT-TYPE
     SYNTAX      SEQUENCE OF HwEntPbxSIPServerConfigEntry
     MAX-ACCESS  not-accessible
     STATUS      current
     DESCRIPTION
       "
       A list of HwEntPbxSIPServerConfigEntry objects.
       "
     ::= { hwEntVoicePbxMIB 8 }

   hwEntPbxSIPServerConfigEntry OBJECT-TYPE
     SYNTAX      HwEntPbxSIPServerConfigEntry
     MAX-ACCESS  not-accessible
     STATUS      current
     DESCRIPTION
       "A list of hwEntPbxSIPServerConfigEntry objects."
     INDEX    {
               hwEntPbxSIPServerIndex
              }
     ::= { hwEntPbxSIPServerConfigTable 1 }

   HwEntPbxSIPServerConfigEntry ::=
     SEQUENCE
     {
       hwEntPbxSIPServerIndex                     Integer32,
       hwEntPbxSIPServerRowStatus                 RowStatus,
       hwEntPbxSIPServerSignallingIP              IpAddress,
       hwEntPbxSIPServerSignallingPort            Integer32,
       hwEntPbxSIPServerMediaIP                   IpAddress,
       hwEntPbxSIPServerRegUri                    DisplayString,
       hwEntPbxSIPServerHomeDomain                DisplayString,
       hwEntPbxSipServerSignallingDomain          DisplayString,
       hwEntPbxSipServerDdnsClientName            DisplayString,
       hwEntPbxSipServerDynSignallingIPName       DisplayString,
       hwEntPbxSipServerDynMediaIPName            DisplayString,
       hwEntPbxSIPServerTransfer                  INTEGER,
       hwEntPbxSIPServerCSmode                    INTEGER,
       hwEntPbxSIPServerSignallingProxy           INTEGER,
       hwEntPbxSIPServerMediaProxy                INTEGER,
       hwEntPbxSIPServerMappedSignallingIP        IpAddress,
       hwEntPbxSIPServerMappedSignallingPort      Integer32,
       hwEntPbxSIPServerMappedMediaIP             IpAddress,
       hwEntPbxSIPServerMappedMediaPortStart      Integer32,
       hwEntPbxSIPServerMappedMediaProxyPortStart Integer32,
       hwEntPbxSIPServerAdminStatus               INTEGER
     }

   hwEntPbxSIPServerIndex OBJECT-TYPE
     SYNTAX      Integer32
     MAX-ACCESS  not-accessible
     STATUS      current
     DESCRIPTION
         "
         Indicates the index of sip server.
         index must be 0 now.
         "
     ::= { hwEntPbxSIPServerConfigEntry 1 }

   hwEntPbxSIPServerRowStatus OBJECT-TYPE
     SYNTAX      RowStatus
     MAX-ACCESS  read-create
     STATUS      current
     DESCRIPTION
         "
         Indicates the row status.
         "
     ::= { hwEntPbxSIPServerConfigEntry 2 }

   hwEntPbxSIPServerSignallingIP OBJECT-TYPE
     SYNTAX      IpAddress
     MAX-ACCESS  read-create
     STATUS      current
     DESCRIPTION
         "
         Indicates the signalling IP of sip server.
         "
     ::= { hwEntPbxSIPServerConfigEntry 3 }

   hwEntPbxSIPServerSignallingPort OBJECT-TYPE
     SYNTAX      Integer32(5000..5999)
     MAX-ACCESS  read-create
     STATUS      current
     DESCRIPTION
         "
         Indicates the signalling port of sip server.
         "
     ::= { hwEntPbxSIPServerConfigEntry 4 }

   hwEntPbxSIPServerMediaIP OBJECT-TYPE
     SYNTAX      IpAddress
     MAX-ACCESS  read-create
     STATUS      current
     DESCRIPTION
         "
         Indicates the media IP of sip server.
         "
     ::= { hwEntPbxSIPServerConfigEntry 5 }

   hwEntPbxSIPServerRegUri OBJECT-TYPE
     SYNTAX      DisplayString(SIZE (1..64))
     MAX-ACCESS  read-create
     STATUS      current
     DESCRIPTION
         "
         Indicates the register URI of sip server.
         "
     ::= { hwEntPbxSIPServerConfigEntry 6 }

   hwEntPbxSIPServerHomeDomain OBJECT-TYPE
     SYNTAX      DisplayString(SIZE (1..64))
     MAX-ACCESS  read-create
     STATUS      current
     DESCRIPTION
         "
         Indicates the home domain of sip server.
         "
     ::= { hwEntPbxSIPServerConfigEntry 7 }


   hwEntPbxSipServerSignallingDomain OBJECT-TYPE
     SYNTAX      DisplayString(SIZE (1..64))
     MAX-ACCESS  read-create
     STATUS      current
     DESCRIPTION
         "
         Indicates the signalling domain of sip server.
         "
     ::= { hwEntPbxSIPServerConfigEntry 8 }

   hwEntPbxSipServerDdnsClientName OBJECT-TYPE
     SYNTAX      DisplayString(SIZE (0..64))
     MAX-ACCESS  read-create
     STATUS      current
     DESCRIPTION
         "
         Indicates the ddns-client name of sip server.
         "
     ::= { hwEntPbxSIPServerConfigEntry 9 }

   hwEntPbxSipServerDynSignallingIPName OBJECT-TYPE
     SYNTAX      DisplayString(SIZE (0..64))
     MAX-ACCESS  read-create
     STATUS      current
     DESCRIPTION
         "
         Indicates the dynamic aignalling IP name of sip server.
         "
     ::= { hwEntPbxSIPServerConfigEntry 10 }

   hwEntPbxSipServerDynMediaIPName OBJECT-TYPE
     SYNTAX      DisplayString(SIZE (0..64))
     MAX-ACCESS  read-create
     STATUS      current
     DESCRIPTION
         "
         Indicates the dynamic media IP name of sip server.
         "
     ::= { hwEntPbxSIPServerConfigEntry 11 }

   hwEntPbxSIPServerTransfer OBJECT-TYPE
     SYNTAX      INTEGER{tcp(1), udp(2), sctp(3), tls(4)}
     MAX-ACCESS  read-create
     STATUS      current
     DESCRIPTION
         "
         Indicates the trans mode of sip server.
         tcp(1)
         udp(2)
         sctp(3)
         tls(4)
         default: udp(2)
         "
     ::= { hwEntPbxSIPServerConfigEntry 12 }

   hwEntPbxSIPServerCSmode OBJECT-TYPE
     SYNTAX      INTEGER{server(1), clientServer(2)}
     MAX-ACCESS  read-create
     STATUS      current
     DESCRIPTION
         "
         Indicates the client server mode of sip server.
         server(1)
         clientServer(2)
         "
     ::= { hwEntPbxSIPServerConfigEntry 13 }

   hwEntPbxSIPServerSignallingProxy OBJECT-TYPE
     SYNTAX      INTEGER{disable(1), enable(2), auto(3)}
     MAX-ACCESS  read-create
     STATUS      current
     DESCRIPTION
         "
         Indicates the type of signalling proxy.
         disable(1)
         enable(2)
         auto(3)
         default: disable(1)
         "
     ::= { hwEntPbxSIPServerConfigEntry 14 }

   hwEntPbxSIPServerMediaProxy OBJECT-TYPE
     SYNTAX      INTEGER{disable(1), enable(2), auto(3)}
     MAX-ACCESS  read-create
     STATUS      current
     DESCRIPTION
         "
         Indicates the type of media proxy.
         disable(1)
         enable(2)
         auto(3)
         default: disable(1)
         "
     ::= { hwEntPbxSIPServerConfigEntry 15 }

   hwEntPbxSIPServerMappedSignallingIP OBJECT-TYPE
     SYNTAX      IpAddress
     MAX-ACCESS  read-create
     STATUS      current
     DESCRIPTION
         "
         Indicates the mapped signalling IP of sip server.
         "
     ::= { hwEntPbxSIPServerConfigEntry 16 }

   hwEntPbxSIPServerMappedSignallingPort OBJECT-TYPE
     SYNTAX      Integer32(1..65535)
     MAX-ACCESS  read-create
     STATUS      current
     DESCRIPTION
         "
         Indicates the mapped signalling port of sip server.
         "
     ::= { hwEntPbxSIPServerConfigEntry 17 }

   hwEntPbxSIPServerMappedMediaIP OBJECT-TYPE
     SYNTAX      IpAddress
     MAX-ACCESS  read-create
     STATUS      current
     DESCRIPTION
         "
         Indicates the mapped meida IP of sip server.
         "
     ::= { hwEntPbxSIPServerConfigEntry 18 }

   hwEntPbxSIPServerMappedMediaPortStart OBJECT-TYPE
     SYNTAX      Integer32(1..65535)
     MAX-ACCESS  read-create
     STATUS      current
     DESCRIPTION
         "
         Indicates the mapped meida start port of sip server.
         "
     ::= { hwEntPbxSIPServerConfigEntry 19 }

   hwEntPbxSIPServerMappedMediaProxyPortStart OBJECT-TYPE
     SYNTAX      Integer32(1..65535)
     MAX-ACCESS  read-create
     STATUS      current
     DESCRIPTION
         "
         Indicates the media proxy start port of sip server.
         "
     ::= { hwEntPbxSIPServerConfigEntry 20 }

   hwEntPbxSIPServerAdminStatus OBJECT-TYPE
     SYNTAX      INTEGER{reset(1),shutDown(2)}
     MAX-ACCESS  read-write
     STATUS      current
     DESCRIPTION
         "
         Indicates the adminstatus of sip server.
         reset(1)
         shutDown(2)
         "
     ::= { hwEntPbxSIPServerConfigEntry 21 }

  --==============================================================

  hwEntPbxSIPServerRunningTable OBJECT-TYPE
     SYNTAX      SEQUENCE OF HwEntPbxSIPServerRunningEntry
     MAX-ACCESS  not-accessible
     STATUS      current
     DESCRIPTION
       "
       A list of hwEntPbxSIPServerRunningEntry objects.
       "
     ::= { hwEntVoicePbxMIB 9 }

   hwEntPbxSIPServerRunningEntry OBJECT-TYPE
     SYNTAX      HwEntPbxSIPServerRunningEntry
     MAX-ACCESS  not-accessible
     STATUS      current
     DESCRIPTION
       "A list of hwEntPbxSIPServerRunningEntry objects."
     INDEX    {
               hwEntPbxSIPServerRunningSIPServerIndex
              }
     ::= { hwEntPbxSIPServerRunningTable 1 }

   HwEntPbxSIPServerRunningEntry ::=
     SEQUENCE
     {
       hwEntPbxSIPServerRunningSIPServerIndex            Integer32,
       hwEntPbxSIPServerRunningSignallingIP              IpAddress,
       hwEntPbxSIPServerRunningSignallingPort            Integer32,
       hwEntPbxSIPServerRunningMediaIP                   IpAddress,
       hwEntPbxSIPServerRunningRegUri                    DisplayString,
       hwEntPbxSIPServerRunningHomeDomain                DisplayString,
       hwEntPbxSIPServerRunningSignalDomain              DisplayString,
       hwEntPbxSIPServerRunningDdnsClientName            DisplayString,
       hwEntPbxSIPServerRunningDynSignallingIPName       DisplayString,
       hwEntPbxSIPServerRunningDynMediaIPName            DisplayString,
       hwEntPbxSIPServerRunningTransfer                  INTEGER,
       hwEntPbxSIPServerRunningCSmode                    INTEGER,
       hwEntPbxSIPServerRunningSignallingProxy           INTEGER,
       hwEntPbxSIPServerRunningMediaProxy                INTEGER,
       hwEntPbxSIPServerRunningMappedSignallingIP        IpAddress,
       hwEntPbxSIPServerRunningMappedSignallingPort      Integer32,
       hwEntPbxSIPServerRunningMappedMediaIP             IpAddress,
       hwEntPbxSIPServerRunningMappedMediaPortStart      Integer32,
       hwEntPbxSIPServerRunningMappedMediaProxyPortStart Integer32,
       hwEntPbxSIPServerRunningState                     INTEGER
     }

   hwEntPbxSIPServerRunningSIPServerIndex OBJECT-TYPE
     SYNTAX      Integer32
     MAX-ACCESS  not-accessible
     STATUS      current
     DESCRIPTION
         "
         Indicates the index of sip server.
         index must be 0 now.
         "
     ::= { hwEntPbxSIPServerRunningEntry 1 }

   hwEntPbxSIPServerRunningSignallingIP OBJECT-TYPE
     SYNTAX      IpAddress
     MAX-ACCESS  read-only
     STATUS      current
     DESCRIPTION
         "
         Indicates the signalling IP of sip server.
         "
     ::= { hwEntPbxSIPServerRunningEntry 2 }

   hwEntPbxSIPServerRunningSignallingPort OBJECT-TYPE
     SYNTAX      Integer32(5000..5999)
     MAX-ACCESS  read-only
     STATUS      current
     DESCRIPTION
         "
         Indicates the signalling port of sip server.
         "
     ::= { hwEntPbxSIPServerRunningEntry 3 }

   hwEntPbxSIPServerRunningMediaIP OBJECT-TYPE
     SYNTAX      IpAddress
     MAX-ACCESS  read-only
     STATUS      current
     DESCRIPTION
         "
         Indicates the media IP of sip server.
         "
     ::= { hwEntPbxSIPServerRunningEntry 4 }

   hwEntPbxSIPServerRunningRegUri OBJECT-TYPE
     SYNTAX      DisplayString(SIZE (1..64))
     MAX-ACCESS  read-only
     STATUS      current
     DESCRIPTION
         "
         Indicates the register URI of sip server.
         "
     ::= { hwEntPbxSIPServerRunningEntry 5 }

   hwEntPbxSIPServerRunningHomeDomain OBJECT-TYPE
     SYNTAX      DisplayString(SIZE (1..64))
     MAX-ACCESS  read-only
     STATUS      current
     DESCRIPTION
         "
         Indicates the home domain of sip server.
         "
     ::= { hwEntPbxSIPServerRunningEntry 6 }

   hwEntPbxSIPServerRunningSignalDomain OBJECT-TYPE
     SYNTAX      DisplayString(SIZE (0..64))
     MAX-ACCESS  read-only
     STATUS      current
     DESCRIPTION
         "
         Indicates the signalling domain of sip server.
         "
     ::= { hwEntPbxSIPServerRunningEntry 7 }

   hwEntPbxSIPServerRunningDdnsClientName OBJECT-TYPE
     SYNTAX      DisplayString(SIZE (0..64))
     MAX-ACCESS  read-only
     STATUS      current
     DESCRIPTION
         "
         Indicates the ddns-client name of sip server.
         "
     ::= { hwEntPbxSIPServerRunningEntry 8 }

   hwEntPbxSIPServerRunningDynSignallingIPName OBJECT-TYPE
     SYNTAX      DisplayString(SIZE (0..64))
     MAX-ACCESS  read-only
     STATUS      current
     DESCRIPTION
         "
         Indicates the dynamic signalling IP name of sip server.
         "
     ::= { hwEntPbxSIPServerRunningEntry 9 }

   hwEntPbxSIPServerRunningDynMediaIPName OBJECT-TYPE
     SYNTAX      DisplayString(SIZE (0..64))
     MAX-ACCESS  read-only
     STATUS      current
     DESCRIPTION
         "
         Indicates the dynamic media IP name of sip server.
         "
     ::= { hwEntPbxSIPServerRunningEntry 10 }

   hwEntPbxSIPServerRunningTransfer OBJECT-TYPE
     SYNTAX      INTEGER{tcp(1), udp(2), sctp(3), tls(4)}
     MAX-ACCESS  read-only
     STATUS      current
     DESCRIPTION
         "
         Indicates the trans mode of sip server.
         tcp(1),
         udp(2),
         sctp(3),
         tls(4),
         default: udp(2)
         "
     ::= { hwEntPbxSIPServerRunningEntry 11 }

   hwEntPbxSIPServerRunningCSmode OBJECT-TYPE
     SYNTAX      INTEGER{server(1), clientServer(2)}
     MAX-ACCESS  read-only
     STATUS      current
     DESCRIPTION
         "
         Indicates the client server mode of the server.
         server(1),
         clientServer(2)
         "
     ::= { hwEntPbxSIPServerRunningEntry 12 }

   hwEntPbxSIPServerRunningSignallingProxy OBJECT-TYPE
     SYNTAX      INTEGER{disable(1), enable(2), auto(3)}
     MAX-ACCESS  read-only
     STATUS      current
     DESCRIPTION
         "
         Indicates the type of signalling proxy.
         disable(1),
         enable(2),
         auto(3),
         default: disable(1)
         "
     ::= { hwEntPbxSIPServerRunningEntry 13 }

   hwEntPbxSIPServerRunningMediaProxy OBJECT-TYPE
     SYNTAX      INTEGER{disable(1), enable(2), auto(3)}
     MAX-ACCESS  read-only
     STATUS      current
     DESCRIPTION
         "
         Indicates the type of media proxy.
         disable(1),
         enable(2),
         auto(3),
         default: disable(1)
         "
     ::= { hwEntPbxSIPServerRunningEntry 14 }

   hwEntPbxSIPServerRunningMappedSignallingIP OBJECT-TYPE
     SYNTAX      IpAddress
     MAX-ACCESS  read-only
     STATUS      current
     DESCRIPTION
         "
         Indicates the mapped signalling IP of sip server.
         "
     ::= { hwEntPbxSIPServerRunningEntry 15 }

   hwEntPbxSIPServerRunningMappedSignallingPort OBJECT-TYPE
     SYNTAX      Integer32(1..65535)
     MAX-ACCESS  read-only
     STATUS      current
     DESCRIPTION
         "
         Indicates the mapped signalling port of sip server.
         "
     ::= { hwEntPbxSIPServerRunningEntry 16 }

   hwEntPbxSIPServerRunningMappedMediaIP OBJECT-TYPE
     SYNTAX      IpAddress
     MAX-ACCESS  read-only
     STATUS      current
     DESCRIPTION
         "
         Indicates the mapped meida IP of sip server.
         "
     ::= { hwEntPbxSIPServerRunningEntry 17 }

   hwEntPbxSIPServerRunningMappedMediaPortStart OBJECT-TYPE
     SYNTAX      Integer32(1..65535)
     MAX-ACCESS  read-only
     STATUS      current
     DESCRIPTION
         "
         Indicates the mapped media start port of sip server.
         "
     ::= { hwEntPbxSIPServerRunningEntry 18 }

   hwEntPbxSIPServerRunningMappedMediaProxyPortStart OBJECT-TYPE
     SYNTAX      Integer32(1..65535)
     MAX-ACCESS  read-only
     STATUS      current
     DESCRIPTION
         "
         Indicates the  media proxy start port of sip server.
         "
     ::= { hwEntPbxSIPServerRunningEntry 19 }

   hwEntPbxSIPServerRunningState OBJECT-TYPE
     SYNTAX      INTEGER{normal(1),wait-ack(2),closed(3),fail(4),unknown(5)}
     MAX-ACCESS  read-only
     STATUS      current
     DESCRIPTION
         "
         Indicates the state of sip server.
         normal(1),
         wait-ack(2),
         closed(3),
         fail(4),
         unknown(5)
         "
     ::= { hwEntPbxSIPServerRunningEntry 20 }

  --==============================================================

   hwEntPbxUserTable OBJECT-TYPE
     SYNTAX      SEQUENCE OF HwEntPbxUserEntry
     MAX-ACCESS  not-accessible
     STATUS      current
     DESCRIPTION
       "
       A list of HwEntPbxUserEntry objects.
       "
     ::= { hwEntVoicePbxMIB 10 }

   hwEntPbxUserEntry OBJECT-TYPE
     SYNTAX      HwEntPbxUserEntry
     MAX-ACCESS  not-accessible
     STATUS      current
     DESCRIPTION
       "A list of hwEntPbxUserEntry objects."
     INDEX    {
               hwEntPbxUserName
              }
     ::= { hwEntPbxUserTable 1 }

   HwEntPbxUserEntry ::=
     SEQUENCE
     {
       hwEntPbxUserName                  DisplayString,
       hwEntPbxUserRowStatus             RowStatus,
       hwEntPbxUserType                  INTEGER,
       hwEntPbxUserPrivateId             DisplayString,
       hwEntPbxUserEnterprise            DisplayString,
       hwEntPbxUserCountryCode           DisplayString,
       hwEntPbxUserAreaCode              DisplayString,
       hwEntPbxUserTelno                 DisplayString,
       hwEntPbxUserKind                  INTEGER,
       hwEntPbxUserStatus                INTEGER,
       hwEntPbxUserCentrex               DisplayString,
       hwEntPbxUserCentrexNumber         DisplayString,
       hwEntPbxUserDnSet                 DisplayString,
       hwEntPbxUserInRight               INTEGER,
       hwEntPbxUserOutRight              INTEGER,
       hwEntPbxUserNewServiceRight       BITS,
       hwEntPbxUserNewServiceActive      BITS,
       hwEntPbxUserMsnIndex              Integer32,
       hwEntPbxUserPasswordType          INTEGER,
       hwEntPbxUserPassword              DisplayString,
       hwEntPbxUserRegState              INTEGER,
       hwEntPbxUserSrvState              INTEGER,
       hwEntPbxUserLongDn                DisplayString,
       hwEntPbxUserPwd                   DisplayString,
       hwEntPbxUserInRightInner          INTEGER,
       hwEntPbxUserInRightLocal          INTEGER,
       hwEntPbxUserInRightDdd            INTEGER,
       hwEntPbxUserInRightIdd            INTEGER,
       hwEntPbxUserOutRightInner         INTEGER,
       hwEntPbxUserOutRightLocal         INTEGER,
       hwEntPbxUserOutRightDdd           INTEGER,
       hwEntPbxUserOutRightIdd           INTEGER,
       hwEntPbxUserTelnoPassword         DisplayString,
       hwEntPbxUserPriorityValue         INTEGER
     }

   hwEntPbxUserName OBJECT-TYPE
     SYNTAX      DisplayString(SIZE (1..32))
     MAX-ACCESS  not-accessible
     STATUS      current
     DESCRIPTION
         "
         Indicates the name of the pbx user.
         "
     ::= { hwEntPbxUserEntry 1 }

   hwEntPbxUserRowStatus OBJECT-TYPE
     SYNTAX      RowStatus
     MAX-ACCESS  read-create
     STATUS      current
     DESCRIPTION
         "
             Indicates row status of table.
         "
     ::= { hwEntPbxUserEntry 2 }

   hwEntPbxUserType OBJECT-TYPE
     SYNTAX      INTEGER{sipue(1),sipueSub(2),pots(3),potsSub(4), bra(5), braSub(6)}
     MAX-ACCESS  read-create
     STATUS      current
     DESCRIPTION
         "
         Indicates the termination type of user.
         sipue(1),
         sipueSub(2),
         pots(3),
         potsSub(4),
         bra(5),
         braSub(6)
                  "
     ::= { hwEntPbxUserEntry 3 }

   hwEntPbxUserPrivateId OBJECT-TYPE
     SYNTAX      DisplayString(SIZE (1..64))
     MAX-ACCESS  read-create
     STATUS      current
     DESCRIPTION
         "
         Indicates the private ID of user.
         "
     ::= { hwEntPbxUserEntry 4 }

   hwEntPbxUserEnterprise OBJECT-TYPE
     SYNTAX      DisplayString(SIZE (1..32))
     MAX-ACCESS  read-create
     STATUS      current
     DESCRIPTION
         "
         Indicates the device enterprise name of user.
         "
     ::= { hwEntPbxUserEntry 5 }

  hwEntPbxUserCountryCode OBJECT-TYPE
     SYNTAX      DisplayString(SIZE (0..4))
     MAX-ACCESS  read-create
     STATUS      current
     DESCRIPTION
         "
         Indicates the country code of user.
         "
     ::= { hwEntPbxUserEntry 6 }

   hwEntPbxUserAreaCode OBJECT-TYPE
     SYNTAX      DisplayString(SIZE (0..8))
     MAX-ACCESS  read-create
     STATUS      current
     DESCRIPTION
         "
         Indicates the area code of user.
         "
     ::= { hwEntPbxUserEntry 7 }

   hwEntPbxUserTelno OBJECT-TYPE
     SYNTAX      DisplayString(SIZE (1..24))
     MAX-ACCESS  read-create
     STATUS      current
     DESCRIPTION
         "
         Indicates the telephone number of user.
         "
     ::= { hwEntPbxUserEntry 8 }

   hwEntPbxUserKind OBJECT-TYPE
     SYNTAX      INTEGER{commonUser(1),telephonist(2),priorityUser(3),voiceData(4),
                         testUser(5),payUser(6),prepayUser(7)}
     MAX-ACCESS  read-create
     STATUS      current
     DESCRIPTION
         "
         Indicates the type of user.
          commonUser(1)
          telephonist(2)
          priorityUser(3)
          voiceData(4)
          testUser(5)
          payUser(6)
          prepayUser(7)
          default: commonUser(1)
         "
     ::= { hwEntPbxUserEntry 9 }

    hwEntPbxUserStatus OBJECT-TYPE
     SYNTAX      INTEGER{normal(1),arrear(2),forbidden(3),arrearForbidden(4)}
     MAX-ACCESS  read-create
     STATUS      current
     DESCRIPTION
         "
          Indicates the service status of user.
          normal(1)
          arrear(2)
          forbidden(3)
          arrearForbidden(4)
          default: normal(1)
         "
     ::= { hwEntPbxUserEntry 10 }

   hwEntPbxUserCentrex OBJECT-TYPE
     SYNTAX      DisplayString(SIZE (1..32))
     MAX-ACCESS  read-create
     STATUS      current
     DESCRIPTION
         "
         Indicates the centrex name of user.
         "
     ::= { hwEntPbxUserEntry 11 }

   hwEntPbxUserCentrexNumber OBJECT-TYPE
     SYNTAX      DisplayString(SIZE (1..8))
     MAX-ACCESS  read-create
     STATUS      current
     DESCRIPTION
         "
         Indicates the short number of user in centrex group.
         "
     ::= { hwEntPbxUserEntry 12 }

   hwEntPbxUserDnSet OBJECT-TYPE
     SYNTAX      DisplayString(SIZE (1..32))
     MAX-ACCESS  read-create
     STATUS      current
     DESCRIPTION
         "
         Indicates the dnset of user.
         "
     ::= { hwEntPbxUserEntry 13 }

   hwEntPbxUserInRight OBJECT-TYPE
     SYNTAX      INTEGER{internal(1),local(2),nationalToll(3),
                         internationalToll(4),noRight(5)}
     MAX-ACCESS  read-create
     STATUS      current
     DESCRIPTION
         "
         Indicates the user's incoming call authority.
         internal(1),
         local(2),
         national toll(3),
         internationalToll(4),
         noRight(5)
         "
     ::= { hwEntPbxUserEntry 14 }

   hwEntPbxUserOutRight OBJECT-TYPE
     SYNTAX      INTEGER{internal(1),local(2),nationalToll(3),
                         internationalToll(4),noRight(5)}
     MAX-ACCESS  read-create
     STATUS      current
     DESCRIPTION
         "
         Indicates the user's outgoing call authority.
         internal(1),
         local(2),
         national toll(3),
         internationalToll(4),
         noRight(5)
         "
     ::= { hwEntPbxUserEntry 15 }

   hwEntPbxUserNewServiceRight OBJECT-TYPE
     SYNTAX      BITS{bit0(0),bit1(1),bit2(2),bit3(3),bit4(4),bit5(5),
                      bit6(6),bit7(7),bit8(8),bit9(9),bit10(10),
                      bit11(11),bit12(12),bit13(13),bit14(14),bit15(15),
                      bit16(16),bit17(17),bit18(18),bit19(19),bit20(20),
                      bit21(21),bit22(22),bit23(23),bit24(24),bit25(25),
                      bit26(26),bit27(27),bit28(28),bit29(29),bit30(30),
                      bit31(31),bit32(32),bit33(33),bit34(34),bit35(35),
                      bit36(36),bit37(37),bit38(38),bit39(39),bit40(40),
                      bit41(41),bit42(42),bit43(43),bit44(44),bit45(45),
                      bit46(46),bit47(47),bit48(48),bit49(49),bit50(50),
                      bit51(51),bit52(52),bit53(53),bit54(54),bit55(55),
                      bit56(56),bit57(57),bit58(58),bit59(59),bit60(60),
                      bit61(61),bit62(62),bit63(63),bit64(64),btt65(65),
                      bit66(66),bit67(67),bit68(68),bit69(69),bit70(70),
                      bit71(71),bit72(72),bit73(73),bit74(74),btt75(75),
                      bit76(76),bit77(77),bit78(78),bit79(79)}
     MAX-ACCESS  read-create
     STATUS      current
     DESCRIPTION
         "
          Indicates the user's supplementary service rights , from left to right, each bit indicates whether support the supplementary service (order as below) or not,
          0 means the service right is disable, 1 means the service right is enalbe. For sipue user callhold, conf, threeParty and CT doesn't need to be config.
          bit0: CLIP   
          bit1: CLIR   
          bit2: CFU    
          bit3: CFB    
          bit4: CFNA   
          bit5: CFS    
          bit6: CFO    
          bit7: CW     
          bit8: CALLLIMIT 
          bit9: CALLTRANSFER 
          bit10: CALLHOLD,   
          bit11:CALLBACK,    
          bit12:THREEPARTY,  
          bit13:CONF,        
          bit14:CALLINSERT,  
          bit15:CALLREDIAL,  
          bit16:QUERYDN,     
          bit17:DDS,         
          bit18:ABBDIAL,     
          bit19:WAKECALL,    
          bit20:ROMA,        
          bit21:PICKUPINGROUP,
          bit22:PICKUPSPECIAL,
          bit23:RINGSERVICE,  
          bit24:SCA,          
          bit25:RCS,          
          bit26:RAC,          
          bit27:DISCLIR,      
          bit28:ICS,          
          bit29:IVR,          
          bit30:PRNG,         
          bit31:SRNG,         
          bit32:UNC,          
          bit33:REMOTEOFFICE, 
          bit34:SCCCANCEL,    
          bit35:SCR,          
          bit36:PARK,         
          bit37:BEREMOTED,    
          bit38:DLC,          
          bit39:CIPHERCALL,   
          bit40:CIPHERCALL-LIMIT,
          bit41:MSN,             
          bit42:CRBT,            
          bit43:SELECT,          
          bit44:CR,              
          bit45:OCM,             
          bit46:ICM,             
          bit47:CCBS,            
          bit48:CCNR,            
          bit49:VCFU,            
          bit50:VCFB,            
          bit51:VCFNA,           
          bit52:VCFS,            
          bit53:VCFO,            
          bit54:FAXMAIL,         
          bit55:MWI,             
          bit56:INSTANT-CONF,    
          bit57:HOTLINE,         
          bit58:HOTLINE-NOUSE,   
          bit59:CFC,             
          bit60:VOICEMAILCFU,    
          bit61:VOICEMAILCFNR,   
          bit62:VOICEMAILCFB,    
          bit63:VOICEMAILCF0,    
          bit64:COLP,            
          bit65:COLR,
          bit66-bit79: reserved
         "
     ::= { hwEntPbxUserEntry 16 }

   hwEntPbxUserNewServiceActive OBJECT-TYPE
     SYNTAX      BITS{bit0(0),bit1(1),bit2(2),bit3(3),bit4(4),bit5(5),
                      bit6(6),bit7(7),bit8(8),bit9(9),bit10(10),
                      bit11(11),bit12(12),bit13(13),bit14(14),bit15(15),
                      bit16(16),bit17(17),bit18(18),bit19(19),bit20(20),
                      bit21(21),bit22(22),bit23(23),bit24(24),bit25(25),
                      bit26(26),bit27(27),bit28(28),bit29(29),bit30(30),
                      bit31(31)}
     MAX-ACCESS  read-create
     STATUS      current
     DESCRIPTION
         "
          Indicates the user's supplementary service active state , from left to right, each bit indicates whether the supplementary service (order as below) is actived,
          0 means the service active state is disable, 1 means the service active state is enalbe.
          Supplementary service:
          bit0: PWCB
          bit1: CW
          bit2: DLC
          bit3-bit31: reserved
         "
     ::= { hwEntPbxUserEntry 17 }

   hwEntPbxUserMsnIndex OBJECT-TYPE
     SYNTAX      Integer32(0..255)
     MAX-ACCESS  read-create
     STATUS      current
     DESCRIPTION
         "
         Indicates the MSN index of user.
         "
     ::= { hwEntPbxUserEntry 18 }

   hwEntPbxUserPasswordType OBJECT-TYPE
     SYNTAX      INTEGER{simple(1),cipher(2)}
     MAX-ACCESS  read-create
     STATUS      current
     DESCRIPTION
         "
         Indicates the display type of user password.
         1:simple(1),
         2:cipher(2)
         "
     ::= { hwEntPbxUserEntry 19 }

   hwEntPbxUserPassword OBJECT-TYPE
     SYNTAX      DisplayString(SIZE (0..64))
     MAX-ACCESS  read-create
     STATUS      current
     DESCRIPTION
         "
         Indicates the password of user.
         "
     ::= { hwEntPbxUserEntry 20 }

   hwEntPbxUserRegState OBJECT-TYPE
     SYNTAX      INTEGER{outService(1), inService(2)}
     MAX-ACCESS  read-only
     STATUS      current
     DESCRIPTION
         "
         Indicates the Indicates register state of the user.
         outService(1),
         inService(2)
         "
     ::= { hwEntPbxUserEntry 21 }

   hwEntPbxUserSrvState OBJECT-TYPE
     SYNTAX      INTEGER{idle(1), busy(2), block(3)}
     MAX-ACCESS  read-only
     STATUS      current
     DESCRIPTION
         "
         Indicates the Indicates register state of the user.
         idle(1),
         inService(2),
         block(3)
         "
     ::= { hwEntPbxUserEntry 22 }

   hwEntPbxUserLongDn OBJECT-TYPE
     SYNTAX      DisplayString(SIZE (1..32))
     MAX-ACCESS  read-create
     STATUS      current
     DESCRIPTION
         "
         Indicates the long telephone number of user.
         "
     ::= { hwEntPbxUserEntry 23 }
        
   hwEntPbxUserPwd OBJECT-TYPE
     SYNTAX      DisplayString(SIZE (1..32))
     MAX-ACCESS  read-create
     STATUS      current
     DESCRIPTION
         "
         Indicates the user's password of self service entry.
         "
     ::= { hwEntPbxUserEntry 24 } 

   hwEntPbxUserInRightInner OBJECT-TYPE
     SYNTAX      INTEGER{false(1), true(2)}
     MAX-ACCESS  read-create
     STATUS      current
     DESCRIPTION
         "
         Indicates if have the callright-in-inner .
         false(1),
         true(2)
         "
     ::= { hwEntPbxUserEntry 25 }

   hwEntPbxUserInRightLocal OBJECT-TYPE
     SYNTAX      INTEGER{false(1), true(2)}
     MAX-ACCESS  read-create
     STATUS      current
     DESCRIPTION
         "
         Indicates if have the callright-in-local .
         false(1),
         true(2)
         "
     ::= { hwEntPbxUserEntry 26 }

   hwEntPbxUserInRightDdd OBJECT-TYPE
     SYNTAX      INTEGER{false(1), true(2)}
     MAX-ACCESS  read-create
     STATUS      current
     DESCRIPTION
         "
         Indicates if have the callright-in-ddd .
         false(1),
         true(2)
         "
     ::= { hwEntPbxUserEntry 27 }

   hwEntPbxUserInRightIdd OBJECT-TYPE
     SYNTAX      INTEGER{false(1), true(2)}
     MAX-ACCESS  read-create
     STATUS      current
     DESCRIPTION
         "
         Indicates if have the callright-in-idd .
         false(1),
         true(2)
         "
     ::= { hwEntPbxUserEntry 28 }

   hwEntPbxUserOutRightInner OBJECT-TYPE
     SYNTAX      INTEGER{false(1), true(2)}
     MAX-ACCESS  read-create
     STATUS      current
     DESCRIPTION
         "
         Indicates if have the callright-out-inner .
         false(1),
         true(2)
         "
     ::= { hwEntPbxUserEntry 29 }

   hwEntPbxUserOutRightLocal OBJECT-TYPE
     SYNTAX      INTEGER{false(1), true(2)}
     MAX-ACCESS  read-create
     STATUS      current
     DESCRIPTION
         "
         Indicates if have the callright-out-local .
         false(1),
         true(2)
         "
     ::= { hwEntPbxUserEntry 30 }

   hwEntPbxUserOutRightDdd OBJECT-TYPE
     SYNTAX      INTEGER{false(1), true(2)}
     MAX-ACCESS  read-create
     STATUS      current
     DESCRIPTION
         "
         Indicates if have the callright-out-ddd .
         false(1),
         true(2)
         "
     ::= { hwEntPbxUserEntry 31 }

   hwEntPbxUserOutRightIdd OBJECT-TYPE
     SYNTAX      INTEGER{false(1), true(2)}
     MAX-ACCESS  read-create
     STATUS      current
     DESCRIPTION
         "
         Indicates if have the callright-out-idd .
         false(1),
         true(2)
         "
     ::= { hwEntPbxUserEntry 32 }

   hwEntPbxUserTelnoPassword OBJECT-TYPE
     SYNTAX      DisplayString(SIZE (1..6))
     MAX-ACCESS  read-create
     STATUS      current
     DESCRIPTION
         "
         Indicates the password for the telno .
         "
     ::= { hwEntPbxUserEntry 33 }

   hwEntPbxUserPriorityValue  OBJECT-TYPE
     SYNTAX      INTEGER{default(1),normal(2),advanced(3),super(4)}
     MAX-ACCESS  read-create
     STATUS      current
     DESCRIPTION
         "
         Indicates the priority of the pbxuser.
         default(1),
         normal(2),
         advanced(3),
         super(4)
         "
     ::= { hwEntPbxUserEntry 34 }


                    
  --==============================================================

 hwEntPbxTrkGrpConfigTable OBJECT-TYPE
     SYNTAX      SEQUENCE OF HwEntPbxTrkGrpConfigEntry
     MAX-ACCESS  not-accessible
     STATUS      current
     DESCRIPTION
       "
       A list of HwEntPbxTrkGrpConfigEntry objects.
       "
     ::= { hwEntVoicePbxMIB 11 }

   hwEntPbxTrkGrpConfigEntry OBJECT-TYPE
     SYNTAX      HwEntPbxTrkGrpConfigEntry
     MAX-ACCESS  not-accessible
     STATUS      current
     DESCRIPTION
       "A list of hwEntPbxTrkGrpConfigEntry objects."
     INDEX    {
               hwEntPbxTrkGrpName
              }
     ::= { hwEntPbxTrkGrpConfigTable 1 }

   HwEntPbxTrkGrpConfigEntry ::=
     SEQUENCE
     {
       hwEntPbxTrkGrpName                           DisplayString,
       hwEntPbxTrkGrpRowStatus                      RowStatus,
       hwEntPbxTrkGrpSignalType                     INTEGER,
       hwEntPbxTrkGrpDesc                           DisplayString,
       hwEntPbxTrkGrpSelectMode                     INTEGER,
       hwEntPbxTrkGrpEnterpriseName                 DisplayString,
       hwEntPbxTrkGrpDnSet                          DisplayString,
       hwEntPbxTrkGrpCountryCode                    DisplayString,
       hwEntPbxTrkGrpAreaCode                       DisplayString,
       hwEntPbxTrkGrpInRight                        INTEGER,
       hwEntPbxTrkGrpOutRight                       INTEGER,
       hwEntPbxTrkGrpPraStandard                    INTEGER,
       hwEntPbxTrkGrpIpGrpRegMode                   INTEGER,
       hwEntPbxTrkGrpSignallingIP                   IpAddress,
       hwEntPbxTrkGrpSignallingPort                 Integer32,
       hwEntPbxTrkGrpMediaIP                        IpAddress,
       hwEntPbxTrkGrpIpGrpPeerAddrMode              INTEGER,
       hwEntPbxTrkGrpPrimaryPeerIP                  IpAddress,
       hwEntPbxTrkGrpPrimaryPeerPort                Integer32,
       hwEntPbxTrkGrpIpGrpPeerSecondaryIP           IpAddress,
       hwEntPbxTrkGrpIpGrpPeerSecondaryPort         Integer32,
       hwEntPbxTrkGrpPrimaryPeerDomain              DisplayString,
       hwEntPbxTrkGrpIpGrpPeerSecondaryDomain       DisplayString,
       hwEntPbxTrkGrpMaxCallNum                     Integer32,
       hwEntPbxTrkGrpRegUri                         DisplayString,
       hwEntPbxTrkGrpHomeDomain                     DisplayString,
       hwEntPbxTrkGrpMgcType                        INTEGER,
       hwEntPbxTrkGrpTransfer                       INTEGER,
       hwEntPbxTrkGrpCSmode                         INTEGER,
       hwEntPbxTrkGrpRegID                          DisplayString,
       hwEntPbxTrkGrpRegPwdType                     INTEGER,
       hwEntPbxTrkGrpRegPwd                         DisplayString,
       hwEntPbxTrkGrpDefaultCallerNum               DisplayString,
       hwEntPbxTrkGrpDynSignallingIPName            DisplayString,
       hwEntPbxTrkGrpDynMediaIPName                 DisplayString,
       hwEntPbxTrkGrpMediaProxy                     INTEGER,
       hwEntPbxTrkGrpMappedSignallingIP             IpAddress,
       hwEntPbxTrkGrpMappedSignallingPort           Integer32,
       hwEntPbxTrkGrpMappedMediaIP                  IpAddress,
       hwEntPbxTrkGrpMappedMediaPortStart           Integer32,
       hwEntPbxTrkGrpMappedMediaProxyPortStart      Integer32,
       hwEntPbxTrkGrpR2ProfileName                  DisplayString,
       hwEntPbxTrkGrpR2IsEarlyMedia                 INTEGER,
       hwEntPbxTrkGrpR2PlayRingback                 INTEGER,
       hwEntPbxTrkGrpAdminStatus                    INTEGER,
       hwEntPbxTrkGrpOutGoingRightInner             INTEGER,
       hwEntPbxTrkGrpOutGoingRightLocal             INTEGER,
       hwEntPbxTrkGrpOutGoingRightDdd               INTEGER,
       hwEntPbxTrkGrpOutGoingRightIdd               INTEGER,
       hwEntPbxTrkGrpCallerNumberType               INTEGER,
       hwEntPbxTrkGrpCalledNumberType               INTEGER
     }

  hwEntPbxTrkGrpName OBJECT-TYPE
     SYNTAX      DisplayString(SIZE (0..32))
     MAX-ACCESS  not-accessible
     STATUS      current
     DESCRIPTION
         "
         Indicates the name of the trunk group.
         "
     ::= { hwEntPbxTrkGrpConfigEntry 1 }

   hwEntPbxTrkGrpRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxTrkGrpConfigEntry 2 }

   hwEntPbxTrkGrpSignalType OBJECT-TYPE
     SYNTAX      INTEGER{dss1Net(1), dss1User(2), fxo(3), sip(4), 
                         qsigNet(5), qsigUser(6), e1r2(7), h323(8)}
     MAX-ACCESS  read-create
     STATUS      current
     DESCRIPTION
         "
         Indicates the signal type of the trunk group.
         "
     ::= { hwEntPbxTrkGrpConfigEntry 3 }

   hwEntPbxTrkGrpDesc OBJECT-TYPE
     SYNTAX      DisplayString(SIZE (0..64))
     MAX-ACCESS  read-create
     STATUS      current
     DESCRIPTION
         "
         Indicates the description of the trunk group,null means clear the value of this parameter.
         "
     ::= { hwEntPbxTrkGrpConfigEntry 4 }

   hwEntPbxTrkGrpSelectMode OBJECT-TYPE
     SYNTAX      INTEGER{loop(1),increase(2),decrease(3),master(4)}
     MAX-ACCESS  read-create
     STATUS      current
     DESCRIPTION
         "
         Indicates the circuit select mode of the trunk group.
         "
     ::= { hwEntPbxTrkGrpConfigEntry 5 }

   hwEntPbxTrkGrpEnterpriseName OBJECT-TYPE
     SYNTAX      DisplayString(SIZE (1..32))
     MAX-ACCESS  read-create
     STATUS      current
     DESCRIPTION
         "
         Indicates the enterprise name of user.
         "
     ::= { hwEntPbxTrkGrpConfigEntry 6 }

   hwEntPbxTrkGrpDnSet OBJECT-TYPE
     SYNTAX      DisplayString(SIZE(1..32))
     MAX-ACCESS  read-create
     STATUS      current
     DESCRIPTION
         "
         Indicates the dnset of the trunk group.
         "
     ::= { hwEntPbxTrkGrpConfigEntry 7 }

   hwEntPbxTrkGrpCountryCode OBJECT-TYPE
     SYNTAX      DisplayString(SIZE (0..4))
     MAX-ACCESS  read-create
     STATUS      current
     DESCRIPTION
         "
         Indicates the country code of the trunk group,null means clear the value of this parameter,only used in the sip trunk group.
         "
     ::= { hwEntPbxTrkGrpConfigEntry 8 }

   hwEntPbxTrkGrpAreaCode OBJECT-TYPE
     SYNTAX      DisplayString(SIZE (0..8))
     MAX-ACCESS  read-create
     STATUS      current
     DESCRIPTION
         "
         Indicates the area code of the trunk group,null means clear the value of this parameter,only used in the sip trunk group.
         "
     ::= { hwEntPbxTrkGrpConfigEntry 9 }

   hwEntPbxTrkGrpInRight OBJECT-TYPE
     SYNTAX      INTEGER{internal(1),local(2),nationalToll(3),
                         internationalToll(4),noRight(5)}
     MAX-ACCESS  read-create
     STATUS      current
     DESCRIPTION
         "
         Indicates the called right of the trunk group.
         internal(1)
         local(2)
         nationalToll(3)
         internationalToll(4)
         noRight(5)
         "
     ::= { hwEntPbxTrkGrpConfigEntry 10 }

   hwEntPbxTrkGrpOutRight OBJECT-TYPE
     SYNTAX      INTEGER{internal(1),local(2),nationalToll(3),
                         internationalToll(4),noRight(5)}
     MAX-ACCESS  read-create
     STATUS      current
     DESCRIPTION
         "
         Indicates the caller right of the trunk group.
         internal(1)
         local(2)
         nationalToll(3)
         internationalToll(4)
         noRight(5)
         "
     ::= { hwEntPbxTrkGrpConfigEntry 11 }

   hwEntPbxTrkGrpPraStandard OBJECT-TYPE
     SYNTAX      INTEGER{q931(1),nfas(2),csc(3),ni1(4)}
     MAX-ACCESS  read-create
     STATUS      current
     DESCRIPTION
         "
         Indicates the pra standard that the trunk group supported.
         q931(1)
         nfas(2)
         csc(3)
         ni1(4)
         default:q931(1)
         "
     ::= { hwEntPbxTrkGrpConfigEntry 12 }

   hwEntPbxTrkGrpIpGrpRegMode OBJECT-TYPE
     SYNTAX      INTEGER{noRegister(1),trunkGroup(2),trunkCircuit(3)}
     MAX-ACCESS  read-create
     STATUS      current
     DESCRIPTION
         "
         Indicates the reg mode of the trunk group,only used in sip trunk group.
         noRegister(1)
      trunkGroup(2)
      trunkCircuit(3)
         "
     ::= { hwEntPbxTrkGrpConfigEntry 13 }

   hwEntPbxTrkGrpSignallingIP OBJECT-TYPE
     SYNTAX      IpAddress
     MAX-ACCESS  read-create
     STATUS      current
     DESCRIPTION
         "
         Indicates the signal IPAddress of the sip trunk group.
         "
     ::= { hwEntPbxTrkGrpConfigEntry 14 }

   hwEntPbxTrkGrpSignallingPort OBJECT-TYPE
     SYNTAX      Integer32(5000..5999)
     MAX-ACCESS  read-create
     STATUS      current
     DESCRIPTION
         "
         Indicates the SigPort of the sip trunk group.
         "
     ::= { hwEntPbxTrkGrpConfigEntry 15 }

   hwEntPbxTrkGrpMediaIP OBJECT-TYPE
     SYNTAX      IpAddress
     MAX-ACCESS  read-create
     STATUS      current
     DESCRIPTION
         "
         Indicates the media IPAddress of the sip trunk group.
         "
     ::= { hwEntPbxTrkGrpConfigEntry 16 }

   hwEntPbxTrkGrpIpGrpPeerAddrMode OBJECT-TYPE
     SYNTAX      INTEGER{static(1),dnsA(2),dnsSrv(3),dnsNaptr(4)}
     MAX-ACCESS  read-create
     STATUS      current
     DESCRIPTION
         "
         Indicates the state of the server.
         static(1)
      dnsA(2)
      dnsSrv(3)
      dnsNaptr(4)
         "
     ::= { hwEntPbxTrkGrpConfigEntry 17 }

   hwEntPbxTrkGrpPrimaryPeerIP OBJECT-TYPE
     SYNTAX      IpAddress
     MAX-ACCESS  read-create
     STATUS      current
     DESCRIPTION
         "
         Indicates the peer master IPAddress of the sip trunk group.
         "
     ::= { hwEntPbxTrkGrpConfigEntry 18 }

    hwEntPbxTrkGrpPrimaryPeerPort OBJECT-TYPE
     SYNTAX      Integer32(1..65535)
     MAX-ACCESS  read-create
     STATUS      current
     DESCRIPTION
         "
         Indicates the peer master sigPort of the sip trunk group.
         "
     ::= { hwEntPbxTrkGrpConfigEntry 19 }

  hwEntPbxTrkGrpIpGrpPeerSecondaryIP OBJECT-TYPE
     SYNTAX      IpAddress
     MAX-ACCESS  read-create
     STATUS      current
     DESCRIPTION
         "
         Indicates the peer second IPAddress of the sip trunk group.
         "
     ::= { hwEntPbxTrkGrpConfigEntry 20 }

   hwEntPbxTrkGrpIpGrpPeerSecondaryPort OBJECT-TYPE
     SYNTAX      Integer32(1..65535)
     MAX-ACCESS  read-create
     STATUS      current
     DESCRIPTION
         "
         Indicates the peer second sigPort of the sip trunk group.
         "
     ::= { hwEntPbxTrkGrpConfigEntry 21 }

   hwEntPbxTrkGrpPrimaryPeerDomain OBJECT-TYPE
     SYNTAX      DisplayString(SIZE (0..32))
     MAX-ACCESS  read-create
     STATUS      current
     DESCRIPTION
         "
         Indicates the peer domain name of the trunk group,null means clear the value of this parameter,only used in the sip trunk group.
         "
     ::= { hwEntPbxTrkGrpConfigEntry 22 }

   hwEntPbxTrkGrpIpGrpPeerSecondaryDomain OBJECT-TYPE
     SYNTAX      DisplayString(SIZE (0..32))
     MAX-ACCESS  read-create
     STATUS      current
     DESCRIPTION
         "
         Indicates the peer second domain name of the trunk group,null means clear the value of this parameter,only used in the sip trunk group.
         "
     ::= { hwEntPbxTrkGrpConfigEntry 23 }

   hwEntPbxTrkGrpMaxCallNum OBJECT-TYPE
     SYNTAX      Integer32(1..65535)
     MAX-ACCESS  read-create
     STATUS      current
     DESCRIPTION
         "
         Indicates the max online call number of the trunk group,only used in sip trunk group.
         default:65535
         "
     ::= { hwEntPbxTrkGrpConfigEntry 24 }

   hwEntPbxTrkGrpRegUri OBJECT-TYPE
     SYNTAX      DisplayString(SIZE (1..32))
     MAX-ACCESS  read-create
     STATUS      current
     DESCRIPTION
         "
         Indicates the register uri of the trunk group,null means clear the value of this parameter,only used in the sip trunk group.
         "
     ::= { hwEntPbxTrkGrpConfigEntry 25 }

  hwEntPbxTrkGrpHomeDomain OBJECT-TYPE
     SYNTAX      DisplayString(SIZE (1..32))
     MAX-ACCESS  read-create
     STATUS      current
     DESCRIPTION
         "
         Indicates the home domain name of the trunk group,null means clear the value of this parameter,only used in the sip trunk group.
         "
     ::= { hwEntPbxTrkGrpConfigEntry 26 }

   hwEntPbxTrkGrpMgcType OBJECT-TYPE
     SYNTAX      INTEGER{mg(1),mgc(2)}
     MAX-ACCESS  read-create
     STATUS      current
     DESCRIPTION
         "
         Indicates adpt type of the trunk group.
         mg(1)
      mgc(2)
         default: mg(1)
         "
     ::= { hwEntPbxTrkGrpConfigEntry 27 }

   hwEntPbxTrkGrpTransfer OBJECT-TYPE
     SYNTAX      INTEGER{tcp(1),udp(2),sctp(3),tls(4)}
     MAX-ACCESS  read-create
     STATUS      current
     DESCRIPTION
         "
         Indicates the TransMode of the trunk group,only used in the sip trunk group.
         tcp(1)
         udp(2)
         sctp(3)
         tls(4)
         default: udp(2)
         "
     ::= { hwEntPbxTrkGrpConfigEntry 28 }

   hwEntPbxTrkGrpCSmode OBJECT-TYPE
     SYNTAX      INTEGER{client(1),server (2),clientserver(3)}
     MAX-ACCESS  read-create
     STATUS      current
     DESCRIPTION
         "
         Indicates the client server mode of the trunk group,only used in the sip trunk group.
         client(1)
         server (2)
         clientServer(3)
         "
     ::= { hwEntPbxTrkGrpConfigEntry 29 }

   hwEntPbxTrkGrpRegID OBJECT-TYPE
     SYNTAX      DisplayString(SIZE (1..32))
     MAX-ACCESS  read-create
     STATUS      current
     DESCRIPTION
         "
         Indicates the register id of the trunk group,null means clear the value of this parameter,only used in the sip trunk group.
         "
     ::= { hwEntPbxTrkGrpConfigEntry 30}

   hwEntPbxTrkGrpRegPwdType OBJECT-TYPE
     SYNTAX      INTEGER{simple(1),cipher(2)}
     MAX-ACCESS  read-create
     STATUS      current
     DESCRIPTION
         "
         Indicates the auth password type of the trunk group.
         simple(1)
         cipher(2)
         "
     ::= { hwEntPbxTrkGrpConfigEntry 31 }

   hwEntPbxTrkGrpRegPwd OBJECT-TYPE
     SYNTAX      DisplayString(SIZE (0..32))
     MAX-ACCESS  read-create
     STATUS      current
     DESCRIPTION
         "
         Indicates the auth password of the trunk group,null means clear the value of this parameter,only used in the sip trunk group.
         "
     ::= { hwEntPbxTrkGrpConfigEntry 32 }

   hwEntPbxTrkGrpDefaultCallerNum OBJECT-TYPE
     SYNTAX      DisplayString(SIZE (0..32))
     MAX-ACCESS  read-create
     STATUS      current
     DESCRIPTION
         "
         Indicates the default-callnum of the trunk group.
         "
     ::= { hwEntPbxTrkGrpConfigEntry 33 }

   hwEntPbxTrkGrpDynSignallingIPName OBJECT-TYPE
     SYNTAX      DisplayString(SIZE (0..64))
     MAX-ACCESS  read-create
     STATUS      current
     DESCRIPTION
         "
         Indicates the local dynamic signal IP name.
         "
     ::= { hwEntPbxTrkGrpConfigEntry 34 }

   hwEntPbxTrkGrpDynMediaIPName OBJECT-TYPE
     SYNTAX      DisplayString(SIZE (0..64))
     MAX-ACCESS  read-create
     STATUS      current
     DESCRIPTION
         "
         Indicates the local dynamic media IP name.
         "
     ::= { hwEntPbxTrkGrpConfigEntry 35 }

   hwEntPbxTrkGrpMediaProxy OBJECT-TYPE
     SYNTAX      INTEGER{disable(1),enable(2),auto(3)}
     MAX-ACCESS  read-create
     STATUS      current
     DESCRIPTION
         "
         Indicates the type of media proxy.
         disable(1)
      enable(2)
      auto(3)
     default: disable(1)
         "
     ::= { hwEntPbxTrkGrpConfigEntry 36 }

    hwEntPbxTrkGrpMappedSignallingIP OBJECT-TYPE
     SYNTAX      IpAddress
     MAX-ACCESS  read-create
     STATUS      current
     DESCRIPTION
         "
         Indicates the mapped signalling IPAddress of the sip trunk group.
         "
     ::= { hwEntPbxTrkGrpConfigEntry 37 }

    hwEntPbxTrkGrpMappedSignallingPort OBJECT-TYPE
     SYNTAX      Integer32(1..65535)
     MAX-ACCESS  read-create
     STATUS      current
     DESCRIPTION
         "
         Indicates the mapped signalling sigPort of the sip trunk group.
         "
     ::= { hwEntPbxTrkGrpConfigEntry 38 }

    hwEntPbxTrkGrpMappedMediaIP OBJECT-TYPE
     SYNTAX      IpAddress
     MAX-ACCESS  read-create
     STATUS      current
     DESCRIPTION
         "
         Indicates the mapped media IPAddress of the sip trunk group.
         "
     ::= { hwEntPbxTrkGrpConfigEntry 39 }

     hwEntPbxTrkGrpMappedMediaPortStart OBJECT-TYPE
     SYNTAX      Integer32(1..65535)
     MAX-ACCESS  read-create
     STATUS      current
     DESCRIPTION
         "
         Indicates the mapped media start port of the sip trunk group.
         "
     ::= { hwEntPbxTrkGrpConfigEntry 40 }

    hwEntPbxTrkGrpMappedMediaProxyPortStart OBJECT-TYPE
     SYNTAX      Integer32(1..65535)
     MAX-ACCESS  read-create
     STATUS      current
     DESCRIPTION
         "
         Indicates the media proxy start port of the sip trunk group.
         "
     ::= { hwEntPbxTrkGrpConfigEntry 41 }

   hwEntPbxTrkGrpR2ProfileName OBJECT-TYPE
     SYNTAX      DisplayString(SIZE (0..64))
     MAX-ACCESS  read-create
     STATUS      current
     DESCRIPTION
         "
         Indicates the profile Index of the r2 trunk group.
         "
     ::= { hwEntPbxTrkGrpConfigEntry 42 }

   hwEntPbxTrkGrpR2IsEarlyMedia OBJECT-TYPE
     SYNTAX      INTEGER{disable(1),enable(2)}
     MAX-ACCESS  read-create
     STATUS      current
     DESCRIPTION
         "
         Indicates if receive  early media of the r2 trunk group.
         disable(1)
         enable(2)
         default: disable(1)
         "
     ::= { hwEntPbxTrkGrpConfigEntry 43 }

   hwEntPbxTrkGrpR2PlayRingback OBJECT-TYPE
     SYNTAX      INTEGER{disable(1),enable(2)}
     MAX-ACCESS  read-create
     STATUS      current
     DESCRIPTION
         "
         Indicates if play ring back of the r2 trunk group.
         disable(1)
         enable(2)
         default: enable(2)
         "
     ::= { hwEntPbxTrkGrpConfigEntry 44 }

   hwEntPbxTrkGrpAdminStatus OBJECT-TYPE
     SYNTAX      INTEGER{reset(1),shutdown(2)}
     MAX-ACCESS  read-write
     STATUS      current
     DESCRIPTION
         "
         Indicates the AdminStatus of the trunk group.
         reset(1)
      shutdown(2)
         "
     ::= { hwEntPbxTrkGrpConfigEntry 45 }
 
   hwEntPbxTrkGrpOutGoingRightInner OBJECT-TYPE
     SYNTAX      INTEGER{false(1),true(2)}
     MAX-ACCESS  read-create
     STATUS      current
     DESCRIPTION
         "
         Indicates if have outgoing right(inner) of the trunk group.
         false(1)
         true(2)
         "
     ::= { hwEntPbxTrkGrpConfigEntry 46 }

   hwEntPbxTrkGrpOutGoingRightLocal OBJECT-TYPE
     SYNTAX      INTEGER{false(1),true(2)}
     MAX-ACCESS  read-create
     STATUS      current
     DESCRIPTION
         "
         Indicates if have outgoing right(local) of the trunk group.
         false(1)
         true(2)
         "
     ::= { hwEntPbxTrkGrpConfigEntry 47 }

   hwEntPbxTrkGrpOutGoingRightDdd OBJECT-TYPE
     SYNTAX      INTEGER{false(1),true(2)}
     MAX-ACCESS  read-create
     STATUS      current
     DESCRIPTION
         "
         Indicates if have outgoing right(DDD) of the trunk group.
         false(1)
         true(2)
         "
     ::= { hwEntPbxTrkGrpConfigEntry 48 }

   hwEntPbxTrkGrpOutGoingRightIdd OBJECT-TYPE
     SYNTAX      INTEGER{false(1),true(2)}
     MAX-ACCESS  read-create
     STATUS      current
     DESCRIPTION
         "
         Indicates if have outgoing right(IDD) of the trunk group.
         false(1)
         true(2)
         "
     ::= { hwEntPbxTrkGrpConfigEntry 49 }
 
   hwEntPbxTrkGrpCallerNumberType OBJECT-TYPE
     SYNTAX      INTEGER{unknown(1),international(2),national(3),networkSpecific(4),subscriber(5),in(6),abbreviated(7),reservedForExtension(8)}
     MAX-ACCESS  read-create
     STATUS      current
     DESCRIPTION
         "
         Indicates the type of callernumber for the trunk group.
         unknown(1),
         international(2),
         national(3),
         networkSpecific(4),
         subscriber(5),
         in(6),
         abbreviated(7),
         reservedForExtension(8)
         "
     ::= { hwEntPbxTrkGrpConfigEntry 50 } 
 
   hwEntPbxTrkGrpCalledNumberType OBJECT-TYPE
     SYNTAX      INTEGER{unknown(1),international(2),national(3),networkSpecific(4),subscriber(5),in(6),abbreviated(7),reservedForExtension(8)}
     MAX-ACCESS  read-create
     STATUS      current
     DESCRIPTION
         "
         Indicates the type of callednumber for the trunk group.
         unknown(1),
         international(2),
         national(3),
         networkSpecific(4),
         subscriber(5),
         in(6),
         abbreviated(7),
         reservedForExtension(8)
         "
     ::= { hwEntPbxTrkGrpConfigEntry 51 }
  --==============================================================

 hwEntPbxTrkGrpRunningTable OBJECT-TYPE
     SYNTAX      SEQUENCE OF HwEntPbxTrkGrpRunningEntry
     MAX-ACCESS  not-accessible
     STATUS      current
     DESCRIPTION
       "
       A list of hwEntPbxTrkGrpRunningEntry objects.
       "
     ::= { hwEntVoicePbxMIB 12 }

   hwEntPbxTrkGrpRunningEntry OBJECT-TYPE
     SYNTAX      HwEntPbxTrkGrpRunningEntry
     MAX-ACCESS  not-accessible
     STATUS      current
     DESCRIPTION
       "A list of hwEntPbxTrkGrpRunningEntry objects."
     INDEX    {
               hwEntPbxTrkGrpRunningTrkGrpName
              }
     ::= { hwEntPbxTrkGrpRunningTable 1 }

   HwEntPbxTrkGrpRunningEntry ::=
     SEQUENCE
     {
       hwEntPbxTrkGrpRunningTrkGrpName                 DisplayString,
       hwEntPbxTrkGrpRunningState                      INTEGER,
       hwEntPbxTrkGrpRunningSipRegState                INTEGER,
       hwEntPbxTrkGrpRunningSignalType                 INTEGER,
       hwEntPbxTrkGrpRunningDesc                       DisplayString,
       hwEntPbxTrkGrpRunningSelectMode                 INTEGER,
       hwEntPbxTrkGrpRunningEnterprise                 DisplayString,
       hwEntPbxTrkGrpRunningDnSet                      DisplayString,
       hwEntPbxTrkGrpRunningCountryCode                DisplayString,
       hwEntPbxTrkGrpRunningAreaCode                   DisplayString,
       hwEntPbxTrkGrpRunningInRight                    INTEGER,
       hwEntPbxTrkGrpRunningOutRight                   INTEGER,
       hwEntPbxTrkGrpRunningPraStandard                INTEGER,
       hwEntPbxTrkGrpRunningIpGrpRegMode               INTEGER,
       hwEntPbxTrkGrpRunningSignallingIP               IpAddress,
       hwEntPbxTrkGrpRunningSignallingPort             Integer32,
       hwEntPbxTrkGrpRunningMediaIP                    IpAddress,
       hwEntPbxTrkGrpRunningIpGrpPeerAddrMode          INTEGER,
       hwEntPbxTrkGrpRunningPrimaryPeerIP              IpAddress,
       hwEntPbxTrkGrpRunningPrimaryPeerPort            Integer32,
       hwEntPbxTrkGrpRunningPeerSecondaryIP            IpAddress,
       hwEntPbxTrkGrpRunningPeerSecondaryPort          Integer32,
       hwEntPbxTrkGrpRunningPrimaryPeerDomain          DisplayString,
       hwEntPbxTrkGrpRunningIpGrpPeerSecondaryDomain   DisplayString,
       hwEntPbxTrkGrpRunningMaxCallNum                 Integer32,
       hwEntPbxTrkGrpRunningTransfer                   INTEGER,
       hwEntPbxTrkGrpRunningRegUri                     DisplayString,
       hwEntPbxTrkGrpRunningHomeDomain                 DisplayString,
       hwEntPbxTrkGrpRunningMgcType                    INTEGER,
       hwEntPbxTrkGrpRunningRegID                      DisplayString,
       hwEntPbxTrkGrpRunningRegPwdType                   INTEGER,
       hwEntPbxTrkGrpRunningRegPwd                     DisplayString,
       hwEntPbxTrkGrpRunningDefaultCallerNum           DisplayString,
       hwEntPbxTrkGrpRunningDynSignallingIPName        DisplayString,
       hwEntPbxTrkGrpRunningDynMediaIPName             DisplayString,
       hwEntPbxTrkGrpRunningCSmode                     INTEGER,
       hwEntPbxTrkGrpRunningMediaProxy                 INTEGER,
       hwEntPbxTrkGrpRunningMappedSignallingIP         IpAddress,
       hwEntPbxTrkGrpRunningMappedSignallingPort       Integer32,
       hwEntPbxTrkGrpRunningMappedMediaIP              IpAddress,
       hwEntPbxTrkGrpRunningMappedMediaPortStart       Integer32,
       hwEntPbxTrkGrpRunningMappedMediaProxyPortStart  Integer32,
       hwEntPbxTrkGrpRunningR2Profile                   DisplayString,
       hwEntPbxTrkGrpRunningR2IsEarlyMedia             INTEGER,
       hwEntPbxTrkGrpRunningR2PlayRingback             INTEGER,
       hwEntPbxTrkGrpRunningBusyNum                    Integer32,
       hwEntPbxTrkGrpRunningIdleNum                    Integer32,
       hwEntPbxTrkGrpRunningFaultNum                   Integer32
     }

   hwEntPbxTrkGrpRunningTrkGrpName OBJECT-TYPE
     SYNTAX      DisplayString(SIZE (0..32))
     MAX-ACCESS  not-accessible
     STATUS      current
     DESCRIPTION
         "
         Indicates the name of the trunk group.
         "
     ::= { hwEntPbxTrkGrpRunningEntry 1 }

   hwEntPbxTrkGrpRunningState OBJECT-TYPE
     SYNTAX      INTEGER{normal(1),wait-ack(2),closed(3),fail(4),unknown(5)}
     MAX-ACCESS  read-only
     STATUS      current
     DESCRIPTION
         "
         Indicates the server state of the trunk group.
         normal(1)
         wait-ack(2)
         closed(3)
         fail(4)
         unknown(5)
         "
     ::= { hwEntPbxTrkGrpRunningEntry 2 }

   hwEntPbxTrkGrpRunningSipRegState OBJECT-TYPE
     SYNTAX      INTEGER{outSservice(1),inSservice(2)}
     MAX-ACCESS  read-only
     STATUS      current
     DESCRIPTION
         "
         Indicates the reg state of the sip trunk group.
         outSservice(1)
         inSservice(2)
         "
     ::= { hwEntPbxTrkGrpRunningEntry 3 }

   hwEntPbxTrkGrpRunningSignalType OBJECT-TYPE
     SYNTAX      INTEGER{dss1Net(1),dss1User(2),fxo(3),sip(4),
                         qsigNet(5),qsigUser(6),e1r2(7),h323(8)}
     MAX-ACCESS  read-only
     STATUS      current
     DESCRIPTION
         "
         Indicates the signal type of the trunk group.
         dss1Net(1)
         dss1User(2)
         fxo(3)
         sip(4)
         qsigNet(5)
         qsigUser(6)
         h323(7)
         "
     ::= { hwEntPbxTrkGrpRunningEntry 4 }

   hwEntPbxTrkGrpRunningDesc OBJECT-TYPE
     SYNTAX      DisplayString(SIZE (0..64))
     MAX-ACCESS  read-only
     STATUS      current
     DESCRIPTION
         "
         Indicates the description of the trunk group,null means clear the value of this parameter.
         "
     ::= { hwEntPbxTrkGrpRunningEntry 5 }

   hwEntPbxTrkGrpRunningSelectMode OBJECT-TYPE
     SYNTAX      INTEGER{loop(1),increae(2),decrease(3),master(4)}
     MAX-ACCESS  read-only
     STATUS      current
     DESCRIPTION
         "
         Indicates the circuit select mode of the trunk group.
         loop(1)
      increase(2)
          decrease(3)
      master(4)
         "
     ::= { hwEntPbxTrkGrpRunningEntry 6 }

   hwEntPbxTrkGrpRunningEnterprise OBJECT-TYPE
     SYNTAX      DisplayString(SIZE (1..32))
     MAX-ACCESS  read-only
     STATUS      current
     DESCRIPTION
         "
         Indicates the enterprise name of user.
         "
     ::= { hwEntPbxTrkGrpRunningEntry 7 }

   hwEntPbxTrkGrpRunningDnSet OBJECT-TYPE
     SYNTAX      DisplayString(SIZE(1..32))
     MAX-ACCESS  read-only
     STATUS      current
     DESCRIPTION
         "
         Indicates the dnset of the trunk group.
         "
     ::= { hwEntPbxTrkGrpRunningEntry 8 }

   hwEntPbxTrkGrpRunningCountryCode OBJECT-TYPE
     SYNTAX      DisplayString(SIZE (1..4))
     MAX-ACCESS  read-only
     STATUS      current
     DESCRIPTION
         "
         Indicates the country code of the trunk group,null means clear the value of this parameter,only used in the sip trunk group.
         "
     ::= { hwEntPbxTrkGrpRunningEntry 9 }

   hwEntPbxTrkGrpRunningAreaCode OBJECT-TYPE
     SYNTAX      DisplayString(SIZE (1..8))
     MAX-ACCESS  read-only
     STATUS      current
     DESCRIPTION
         "
         Indicates the area code of the trunk group,null means clear the value of this parameter,only used in the sip trunk group.
         "
     ::= { hwEntPbxTrkGrpRunningEntry 10 }

   hwEntPbxTrkGrpRunningInRight OBJECT-TYPE
     SYNTAX      INTEGER{internal(1),local(2),nationalToll(3),
                         internationalToll(4),noRight(5)}
     MAX-ACCESS  read-only
     STATUS      current
     DESCRIPTION
         "
         Indicates the called right of the trunk group.
         internal(1)
         local(2)
         nationalToll(3)
         internationalToll(4)
         noRight(5)
         "
     ::= { hwEntPbxTrkGrpRunningEntry 11 }

   hwEntPbxTrkGrpRunningOutRight OBJECT-TYPE
     SYNTAX      INTEGER{internal(1),local(2),nationalToll(3),
                         internationalToll(4),noRight(5)}
     MAX-ACCESS  read-only
     STATUS      current
     DESCRIPTION
         "
         Indicates the caller right of the trunk group.
         internal(1)
         local(2)
         nationalToll(3)
         internationalToll(4)
         noRight(5)
         "
     ::= { hwEntPbxTrkGrpRunningEntry 12 }

   hwEntPbxTrkGrpRunningPraStandard OBJECT-TYPE
     SYNTAX      INTEGER{q931(1),nfas(2),csc(3),ni1(4)}
     MAX-ACCESS  read-only
     STATUS      current
     DESCRIPTION
         "
         Indicates the pra standard that the trunk group supported.
         q931(1)
         nfas(2)
         csc(3)
         ni1(4)
     default: q931(1)
         "
     ::= { hwEntPbxTrkGrpRunningEntry 13 }

   hwEntPbxTrkGrpRunningIpGrpRegMode OBJECT-TYPE
     SYNTAX      INTEGER{noRegister(1),trunkGroup(2),trunkCircuit(3)}
     MAX-ACCESS  read-only
     STATUS      current
     DESCRIPTION
         "
         Indicates the reg mode of the trunk group,only used in sip trunk group.
         noRegister(1)
         trunkGroup(2)
         trunkCircuit(3)
         "
     ::= { hwEntPbxTrkGrpRunningEntry 14 }

   hwEntPbxTrkGrpRunningSignallingIP OBJECT-TYPE
     SYNTAX      IpAddress
     MAX-ACCESS  read-only
     STATUS      current
     DESCRIPTION
         "
         Indicates the signal IPAddress of the sip trunk group.
         "
     ::= { hwEntPbxTrkGrpRunningEntry 15 }

   hwEntPbxTrkGrpRunningSignallingPort OBJECT-TYPE
     SYNTAX      Integer32(5000..5999)
     MAX-ACCESS  read-only
     STATUS      current
     DESCRIPTION
         "
         Indicates the SigPort of the sip trunk group.
         "
     ::= { hwEntPbxTrkGrpRunningEntry 16 }

    hwEntPbxTrkGrpRunningMediaIP OBJECT-TYPE
     SYNTAX      IpAddress
     MAX-ACCESS  read-only
     STATUS      current
     DESCRIPTION
         "
         Indicates the media IPAddress of the sip trunk group.
         "
     ::= { hwEntPbxTrkGrpRunningEntry 17 }

    hwEntPbxTrkGrpRunningIpGrpPeerAddrMode OBJECT-TYPE
     SYNTAX      INTEGER{static(1),dnsA(2),dnsSrv(3),dnsNaptr(4)}
     MAX-ACCESS  read-only
     STATUS      current
     DESCRIPTION
         "
         Indicates the get mode of the peer IPAddress.
         static(1)
         dnsA(2)
         dnsSrv(3)
         dnsNaptr(4)
         "
     ::= { hwEntPbxTrkGrpRunningEntry 18 }

   hwEntPbxTrkGrpRunningPrimaryPeerIP OBJECT-TYPE
     SYNTAX      IpAddress
     MAX-ACCESS  read-only
     STATUS      current
     DESCRIPTION
         "
         Indicates the peer master IPAddress of the sip trunk group.
         "
     ::= { hwEntPbxTrkGrpRunningEntry 19 }

   hwEntPbxTrkGrpRunningPrimaryPeerPort OBJECT-TYPE
     SYNTAX      Integer32(1..65535)
     MAX-ACCESS  read-only
     STATUS      current
     DESCRIPTION
         "
         Indicates the peer master sigPort of the sip trunk group.
         "
     ::= { hwEntPbxTrkGrpRunningEntry 20 }

   hwEntPbxTrkGrpRunningPeerSecondaryIP OBJECT-TYPE
     SYNTAX      IpAddress
     MAX-ACCESS  read-only
     STATUS      current
     DESCRIPTION
         "
         Indicates the peer second IPAddress of the sip trunk group.
         "
     ::= { hwEntPbxTrkGrpRunningEntry 21 }

   hwEntPbxTrkGrpRunningPeerSecondaryPort OBJECT-TYPE
     SYNTAX      Integer32(1..65535)
     MAX-ACCESS  read-only
     STATUS      current
     DESCRIPTION
         "
         Indicates the peer second sigPort of the sip trunk group.
         "
     ::= { hwEntPbxTrkGrpRunningEntry  22 }

   hwEntPbxTrkGrpRunningPrimaryPeerDomain OBJECT-TYPE
     SYNTAX      DisplayString(SIZE (0..32))
     MAX-ACCESS  read-only
     STATUS      current
     DESCRIPTION
         "
         Indicates the peer domain name of the trunk group,null means clear the value of this parameter,only used in the sip trunk group.
         "
     ::= { hwEntPbxTrkGrpRunningEntry 23 }

   hwEntPbxTrkGrpRunningIpGrpPeerSecondaryDomain OBJECT-TYPE
     SYNTAX      DisplayString(SIZE (0..32))
     MAX-ACCESS  read-only
     STATUS      current
     DESCRIPTION
         "
         Indicates the peer second name of the trunk group,null means clear the value of this parameter,only used in the sip trunk group.
         "
     ::= { hwEntPbxTrkGrpRunningEntry 24 }

   hwEntPbxTrkGrpRunningMaxCallNum OBJECT-TYPE
     SYNTAX      Integer32(1..65535)
     MAX-ACCESS  read-only
     STATUS      current
     DESCRIPTION
         "
         Indicates the max online call number of the trunk group,only used in sip trunk group.
         "
     ::= { hwEntPbxTrkGrpRunningEntry 25 }

   hwEntPbxTrkGrpRunningTransfer OBJECT-TYPE
     SYNTAX      INTEGER{tcp(1),udp(2),sctp(3),tls(4)}
     MAX-ACCESS  read-only
     STATUS      current
     DESCRIPTION
         "
         Indicates the TransMode of the trunk group,only used in the sip trunk group.
         tcp(1)
         udp(2)
         sctp(3)
         tls(4)
         default: udp(2)
         "
     ::= { hwEntPbxTrkGrpRunningEntry 26 }

   hwEntPbxTrkGrpRunningRegUri OBJECT-TYPE
     SYNTAX      DisplayString(SIZE (0..32))
     MAX-ACCESS  read-only
     STATUS      current
     DESCRIPTION
         "
         Indicates the register uri of the trunk group,null means clear the value of this parameter,only used in the sip trunk group.
         "
     ::= { hwEntPbxTrkGrpRunningEntry 27 }

   hwEntPbxTrkGrpRunningHomeDomain OBJECT-TYPE
     SYNTAX      DisplayString(SIZE (0..32))
     MAX-ACCESS  read-only
     STATUS      current
     DESCRIPTION
         "
         Indicates the home domain name of the trunk group,null means clear the value of this parameter,only used in the sip trunk group.
         "
     ::= { hwEntPbxTrkGrpRunningEntry 28 }

   hwEntPbxTrkGrpRunningMgcType OBJECT-TYPE
     SYNTAX      INTEGER{mg(1),mgc(2)}
     MAX-ACCESS  read-only
     STATUS      current
     DESCRIPTION
         "
         Indicates adpt type of the trunk group.
         mg(1)
         mgc(2)
     default: mg(1)
         "
     ::= { hwEntPbxTrkGrpRunningEntry 29 }

   hwEntPbxTrkGrpRunningRegID OBJECT-TYPE
     SYNTAX      DisplayString(SIZE (0..32))
     MAX-ACCESS  read-only
     STATUS      current
     DESCRIPTION
         "
         Indicates the register id of the trunk group,null means clear the value of this parameter,only used in the sip trunk group.
         "
     ::= { hwEntPbxTrkGrpRunningEntry 30 }

   hwEntPbxTrkGrpRunningRegPwdType OBJECT-TYPE
     SYNTAX      INTEGER{simple(1),cipher(2)}
     MAX-ACCESS  read-only
     STATUS      current
     DESCRIPTION
         "
         Indicates the auth password type of the trunk group.
         simple(1)
      cipher(2)
         "
     ::= { hwEntPbxTrkGrpRunningEntry 31 }

   hwEntPbxTrkGrpRunningRegPwd OBJECT-TYPE
     SYNTAX      DisplayString(SIZE (0..32))
     MAX-ACCESS  read-only
     STATUS      current
     DESCRIPTION
         "
         Indicates the auth password of the trunk group,null means clear the value of this parameter,only used in the sip trunk group.
         "
     ::= { hwEntPbxTrkGrpRunningEntry 32 }

   hwEntPbxTrkGrpRunningDefaultCallerNum OBJECT-TYPE
     SYNTAX      DisplayString(SIZE (0..32))
     MAX-ACCESS  read-only
     STATUS      current
     DESCRIPTION
         "
         Indicates the default-callnum of the trunk group.
         "
     ::= { hwEntPbxTrkGrpRunningEntry 33 }

   hwEntPbxTrkGrpRunningDynSignallingIPName OBJECT-TYPE
     SYNTAX      DisplayString(SIZE (0..64))
     MAX-ACCESS  read-only
     STATUS      current
     DESCRIPTION
         "
         Indicates the Dyn signal ip name of the trunk group.
         "
     ::= { hwEntPbxTrkGrpRunningEntry 34 }

   hwEntPbxTrkGrpRunningDynMediaIPName OBJECT-TYPE
     SYNTAX      DisplayString(SIZE (0..64))
     MAX-ACCESS  read-only
     STATUS      current
     DESCRIPTION
         "
         Indicates the Dyn media ip name of the trunk group.
         "
     ::= { hwEntPbxTrkGrpRunningEntry 35 }

  hwEntPbxTrkGrpRunningCSmode OBJECT-TYPE
     SYNTAX      INTEGER{client(1),server(2),clientserver(3)}
     MAX-ACCESS  read-only
     STATUS      current
     DESCRIPTION
         "
         Indicates the client server mode of the sip trunk group.
         client(1)
      server (2)
      clientServer(3)
         "
     ::= { hwEntPbxTrkGrpRunningEntry 36 }

   hwEntPbxTrkGrpRunningMediaProxy OBJECT-TYPE
     SYNTAX      INTEGER{disable(1),enable(2),auto(3)}
     MAX-ACCESS  read-only
     STATUS      current
     DESCRIPTION
         "
         Indicates the type of media proxy.
         disable(1)
         enable(2)
         auto(3)
         "
     ::= { hwEntPbxTrkGrpRunningEntry 37 }

    hwEntPbxTrkGrpRunningMappedSignallingIP OBJECT-TYPE
     SYNTAX      IpAddress
     MAX-ACCESS  read-only
     STATUS      current
     DESCRIPTION
         "
         Indicates the mapped signalling IPAddress of the sip trunk group.
         "
     ::= { hwEntPbxTrkGrpRunningEntry 38 }

    hwEntPbxTrkGrpRunningMappedSignallingPort OBJECT-TYPE
     SYNTAX      Integer32(1..65535)
     MAX-ACCESS  read-only
     STATUS      current
     DESCRIPTION
         "
         Indicates the mapped signalling sigPort of the sip trunk group.
         "
     ::= { hwEntPbxTrkGrpRunningEntry 39 }

    hwEntPbxTrkGrpRunningMappedMediaIP OBJECT-TYPE
     SYNTAX      IpAddress
     MAX-ACCESS  read-only
     STATUS      current
     DESCRIPTION
         "
         Indicates the mapped media IPAddress of the sip trunk group.
         "
     ::= { hwEntPbxTrkGrpRunningEntry 40 }

    hwEntPbxTrkGrpRunningMappedMediaPortStart OBJECT-TYPE
     SYNTAX      Integer32(1..65535)
     MAX-ACCESS  read-only
     STATUS      current
     DESCRIPTION
         "
         Indicates the mapped media start port of the sip trunk group.
         "
     ::= { hwEntPbxTrkGrpRunningEntry 41 }

    hwEntPbxTrkGrpRunningMappedMediaProxyPortStart OBJECT-TYPE
     SYNTAX      Integer32(1..65535)
     MAX-ACCESS  read-only
     STATUS      current
     DESCRIPTION
         "
         Indicates the media proxy start port of the sip trunk group.
         "
     ::= { hwEntPbxTrkGrpRunningEntry  42 }

   hwEntPbxTrkGrpRunningR2Profile OBJECT-TYPE
     SYNTAX      DisplayString(SIZE (0..32))
     MAX-ACCESS  read-only
     STATUS      current
     DESCRIPTION
         "
         Indicates the profile Index of the r2 trunk group.
         "
     ::= { hwEntPbxTrkGrpRunningEntry  43 }

   hwEntPbxTrkGrpRunningR2IsEarlyMedia OBJECT-TYPE
     SYNTAX      INTEGER{disable(1),enable(2)}
     MAX-ACCESS  read-only
     STATUS      current
     DESCRIPTION
         "
         Indicates if receive  early media of the r2 trunk group.
         disable(1)
         enable(2)
     default: disable(1)
         "
     ::= { hwEntPbxTrkGrpRunningEntry  44 }

   hwEntPbxTrkGrpRunningR2PlayRingback OBJECT-TYPE
     SYNTAX      INTEGER{disable(1),enable(2)}
     MAX-ACCESS  read-only
     STATUS      current
     DESCRIPTION
         "
         Indicates if play ring back of the r2 trunk group.
         disable(1)
         enable(2)
     default: enable(2)
         "
     ::= { hwEntPbxTrkGrpRunningEntry  45 }

   hwEntPbxTrkGrpRunningBusyNum OBJECT-TYPE
     SYNTAX      Integer32
     MAX-ACCESS  read-only
     STATUS      current
     DESCRIPTION
         "
         Indicates the number of busy trunk in one trunk-group.
         "
     ::= { hwEntPbxTrkGrpRunningEntry  46 }

   hwEntPbxTrkGrpRunningIdleNum OBJECT-TYPE
     SYNTAX      Integer32
     MAX-ACCESS  read-only
     STATUS      current
     DESCRIPTION
         "
         Indicates the number of idle trunk in one trunk-group.
         "
     ::= { hwEntPbxTrkGrpRunningEntry  47 }

   hwEntPbxTrkGrpRunningFaultNum OBJECT-TYPE
     SYNTAX      Integer32
     MAX-ACCESS  read-only
     STATUS      current
     DESCRIPTION
         "
         Indicates the number of fault trunk in one trunk-group.
         "
     ::= { hwEntPbxTrkGrpRunningEntry  48 }
     
  --==============================================================

 hwEntPbxAt0TrkTable OBJECT-TYPE
     SYNTAX      SEQUENCE OF HwEntPbxAt0TrkEntry
     MAX-ACCESS  not-accessible
     STATUS      current
     DESCRIPTION
       "
       A list of hwEntPbxAt0TrkEntry objects.
       "
     ::= { hwEntVoicePbxMIB 13 }

   hwEntPbxAt0TrkEntry OBJECT-TYPE
     SYNTAX      HwEntPbxAt0TrkEntry
     MAX-ACCESS  not-accessible
     STATUS      current
     DESCRIPTION
       "A list of hwEntPbxAt0TrkEntry objects."
     INDEX    {
               hwEntPbxAt0TrkIndex
              }
     ::= { hwEntPbxAt0TrkTable 1 }

   HwEntPbxAt0TrkEntry ::=
     SEQUENCE
     {
       hwEntPbxAt0TrkIndex                  Integer32,
       hwEntPbxAt0TrkRowStatus              RowStatus,
       hwEntPbxAt0TrkPhyStatus              INTEGER,
       hwEntPbxAt0TrkSrvState               INTEGER,
       hwEntPbxAt0TrkGroupName              DisplayString,
       hwEntPbxAt0TrkDialDelay              Integer32,
       hwEntPbxAt0TrkInsertPrefix           DisplayString,
       hwEntPbxAt0TrkInsertDelay            Integer32,
       hwEntPbxAt0ReversePole               INTEGER,
       hwEntPbxAt0TrkDefaultCalledNum       DisplayString,
       hwEntPbxAt0TrkCidTransType           INTEGER,
       hwEntPbxAt0PTPDialMode               INTEGER
     }

   hwEntPbxAt0TrkIndex OBJECT-TYPE
     SYNTAX      Integer32
     MAX-ACCESS  not-accessible
     STATUS      current
     DESCRIPTION
         "
         Indicates the index of the physical trunk,as follow:
                  31                                         0
                  0011001 | xxxxxxxx | xxxxxx | xxxxxxx | 0000
                  port      frame      slot     port      0
                  type

                  The highest 7 bits indicate the type of port, for BRA port, must be 0x19
                  the next 8 bits indicate the frame ID,
                  the next 6 bits indicate the slot ID,
                  the next 7 bits indicate the port ID,
                  the last 4 bits must be 0.

                  The type of port include:
                  AT0  port = 0x1b

         "
     ::= { hwEntPbxAt0TrkEntry 1 }

    hwEntPbxAt0TrkRowStatus OBJECT-TYPE
     SYNTAX      RowStatus
     MAX-ACCESS  read-create
     STATUS      current
     DESCRIPTION
         "
         Indicates the row status.
         "
     ::= { hwEntPbxAt0TrkEntry 2 }

   hwEntPbxAt0TrkPhyStatus OBJECT-TYPE
     SYNTAX      INTEGER{block(1),normal(2)}
     MAX-ACCESS  read-only
     STATUS      current
     DESCRIPTION
         "
         Indicates the config status of the at0 trunk.
         block (1)
      normal(2)
         "
     ::= { hwEntPbxAt0TrkEntry 3 }

   hwEntPbxAt0TrkSrvState OBJECT-TYPE
     SYNTAX      INTEGER{idle(1),busy(2),fault(3),block(4)}
     MAX-ACCESS  read-only
     STATUS      current
     DESCRIPTION
         "
         Indicates the state of AT0 service state.
         idle(1)
         busy(2)
         fault(3)
         block(4)
         "
     ::= { hwEntPbxAt0TrkEntry 4 }

   hwEntPbxAt0TrkGroupName OBJECT-TYPE
     SYNTAX      DisplayString(SIZE(1..32))
     MAX-ACCESS  read-write
     STATUS      current
     DESCRIPTION
         "
         Indicates the at0 trunk group name.
         "
     ::= { hwEntPbxAt0TrkEntry 5 }

   hwEntPbxAt0TrkDialDelay OBJECT-TYPE
     SYNTAX      Integer32(0..20000)
     MAX-ACCESS  read-write
     STATUS      current
     DESCRIPTION
         "
         Indicates the value the time delay after dialling.
         "
     ::= { hwEntPbxAt0TrkEntry 6 }

   hwEntPbxAt0TrkInsertPrefix OBJECT-TYPE
     SYNTAX      DisplayString(SIZE (0..4))
     MAX-ACCESS  read-write
     STATUS      current
     DESCRIPTION
         "
         Indicates the insert prefix.
         "
     ::= { hwEntPbxAt0TrkEntry 7 }

   hwEntPbxAt0TrkInsertDelay OBJECT-TYPE
     SYNTAX      Integer32(0..20000)
     MAX-ACCESS  read-write
     STATUS      current
     DESCRIPTION
         "
         Indicates the value of time delay after inserting a prefix.
         default: 2000
         "
     ::= { hwEntPbxAt0TrkEntry 8 }

   hwEntPbxAt0ReversePole OBJECT-TYPE
     SYNTAX      INTEGER{disable(1),enable(2)}
     MAX-ACCESS  read-write
     STATUS      current
     DESCRIPTION
         "
         Indicates the Peer reverse pole support.
         disable(1)
         enable(2)
     default: enable(2)
         "
     ::= { hwEntPbxAt0TrkEntry 9 }

   hwEntPbxAt0TrkDefaultCalledNum OBJECT-TYPE
     SYNTAX      DisplayString(SIZE (1..32))
     MAX-ACCESS  read-write
     STATUS      current
     DESCRIPTION
         "
         Indicates the default called number.
         "
     ::= { hwEntPbxAt0TrkEntry 10 }

   hwEntPbxAt0TrkCidTransType OBJECT-TYPE
     SYNTAX      INTEGER{bell202(1),v23(2),ntt(3),dtmf(4),r1-5(5),
                         bell202V23Dtmf(6),none(7)}
     MAX-ACCESS  read-write
     STATUS      current
     DESCRIPTION
         "
         Indicates the CID signal transmit type.
         bell202(1)
         v23(2)
         ntt(3)
         dtmf(4)
         r15(5)
         bell202V23Dtmf(6)
         none(7)
         default: bell202(1)
         "
     ::= { hwEntPbxAt0TrkEntry 11 }

   hwEntPbxAt0PTPDialMode  OBJECT-TYPE
     SYNTAX      INTEGER{dtmf(1),pulse(2)}
     MAX-ACCESS  read-write
     STATUS      current
     DESCRIPTION
         "
         Indicates the dial mode.
         dtmf(1)
      pulse (2)
      default: dtmf (1)
         "
     ::= { hwEntPbxAt0TrkEntry 12 }

  --==============================================================

   hwEntPbxSipAt0TrkTable OBJECT-TYPE
     SYNTAX      SEQUENCE OF HwEntPbxSipAt0TrkEntry
     MAX-ACCESS  not-accessible
     STATUS      current
     DESCRIPTION
       "
       A list of hwEntPbxSipAt0TrkEntry objects.
       "
     ::= {  hwEntVoicePbxMIB 14 }

   hwEntPbxSipAt0TrkEntry OBJECT-TYPE
     SYNTAX      HwEntPbxSipAt0TrkEntry
     MAX-ACCESS  not-accessible
     STATUS      current
     DESCRIPTION
       "A list of hwEntPbxSipAt0TrkEntry objects."
     INDEX    {
               hwEntPbxSipAt0TrkGrpName,
               hwEntPbxSipAt0TrkRegister
              }
     ::= { hwEntPbxSipAt0TrkTable 1 }

   HwEntPbxSipAt0TrkEntry ::=
     SEQUENCE
     {
       hwEntPbxSipAt0TrkGrpName                    DisplayString,
       hwEntPbxSipAt0TrkRegister                   DisplayString,
       hwEntPbxSipAt0TrkRowStatus                  RowStatus,
       hwEntPbxSipAt0TrkAdminStatus                INTEGER,
       hwEntPbxSipAt0TrkRegStatus                  INTEGER,
       hwEntPbxSipAt0TrkDefaultCalledNum           DisplayString,
       hwEntPbxSipAt0TrkPwdType                    INTEGER,
       hwEntPbxSipAt0TrkPwd                        DisplayString,
       hwEntPbxSipAt0TrkCallerEnterprise           DisplayString,
       hwEntPbxSipAt0TrkCallerCountryCode          DisplayString,
       hwEntPbxSipAt0TrkCallerAreaCode             DisplayString,
       hwEntPbxSipAt0TrkCallerNum                  DisplayString,
       hwEntPbxSipAt0TrkMaxCallNum                 Integer32
     }

   hwEntPbxSipAt0TrkGrpName OBJECT-TYPE
     SYNTAX      DisplayString(SIZE (0..32))
     MAX-ACCESS  not-accessible
     STATUS      current
     DESCRIPTION
         "
         Indicates the name of the trunk group.
         "
     ::= { hwEntPbxSipAt0TrkEntry 1 }

   hwEntPbxSipAt0TrkRegister OBJECT-TYPE
     SYNTAX      DisplayString(SIZE(1..32))
     MAX-ACCESS  not-accessible
     STATUS      current
     DESCRIPTION
         "
         Indicates the sipat0 group name.
         "
     ::= { hwEntPbxSipAt0TrkEntry 2 }

   hwEntPbxSipAt0TrkRowStatus OBJECT-TYPE
     SYNTAX      RowStatus
     MAX-ACCESS  read-create
     STATUS      current
     DESCRIPTION
         "
         Indicates the row status.
         active(1)
         notInService(2)
         notReady(3)
         createAndGo(4)
         createAndWait(5)
         destroy(6)
         "
     ::= { hwEntPbxSipAt0TrkEntry 3 }

   hwEntPbxSipAt0TrkAdminStatus OBJECT-TYPE
     SYNTAX      INTEGER{startService(1),endService(2)}
     MAX-ACCESS  read-write
     STATUS      current
     DESCRIPTION
         "
         Indicates the status of service.
         startService(1)
      endService(2)
         "
     ::= { hwEntPbxSipAt0TrkEntry 4 }

   hwEntPbxSipAt0TrkRegStatus OBJECT-TYPE
     SYNTAX      INTEGER{outService(1),inService(2)}
     MAX-ACCESS  read-only
     STATUS      current
     DESCRIPTION
         "
         Indicates the status of registration.
         outService(1)
      inService(2)
         "
     ::= { hwEntPbxSipAt0TrkEntry 5 }

   hwEntPbxSipAt0TrkDefaultCalledNum OBJECT-TYPE
     SYNTAX      DisplayString(SIZE (1..32))
     MAX-ACCESS  read-create
     STATUS      current
     DESCRIPTION
         "
         Indicates the default called number.
         "
     ::= { hwEntPbxSipAt0TrkEntry 6 }

   hwEntPbxSipAt0TrkPwdType OBJECT-TYPE
     SYNTAX      INTEGER{simple(1),cipher(2)}
     MAX-ACCESS  read-create
     STATUS      current
     DESCRIPTION
         "
         Indicates the passwords type.
         simple(1)
         cipher(2)
         "
     ::= { hwEntPbxSipAt0TrkEntry 7 }

   hwEntPbxSipAt0TrkPwd OBJECT-TYPE
     SYNTAX      DisplayString(SIZE (0..32))
     MAX-ACCESS  read-create
     STATUS      current
     DESCRIPTION
         "
         Indicates the passwords.
         "
     ::= { hwEntPbxSipAt0TrkEntry 8 }

   hwEntPbxSipAt0TrkCallerEnterprise OBJECT-TYPE
     SYNTAX      DisplayString(SIZE(0..32))
     MAX-ACCESS  read-create
     STATUS      current
     DESCRIPTION
         "
         Indicates the enterprise name of caller.
         "
     ::= { hwEntPbxSipAt0TrkEntry 9 }

   hwEntPbxSipAt0TrkCallerCountryCode OBJECT-TYPE
     SYNTAX      DisplayString(SIZE(0..4))
     MAX-ACCESS  read-create
     STATUS      current
     DESCRIPTION
         "
         Indicates the country code of caller.
         "
     ::= { hwEntPbxSipAt0TrkEntry 10 }

   hwEntPbxSipAt0TrkCallerAreaCode OBJECT-TYPE
     SYNTAX      DisplayString(SIZE(0..8))
     MAX-ACCESS  read-create
     STATUS      current
     DESCRIPTION
         "
         Indicates the area code of caller.
         "
     ::= { hwEntPbxSipAt0TrkEntry 11 }

   hwEntPbxSipAt0TrkCallerNum OBJECT-TYPE
     SYNTAX      DisplayString(SIZE(0..24))
     MAX-ACCESS  read-create
     STATUS      current
     DESCRIPTION
         "
         Indicates the telnum of caller.
         "
     ::= { hwEntPbxSipAt0TrkEntry 12 }

   hwEntPbxSipAt0TrkMaxCallNum OBJECT-TYPE
     SYNTAX      Integer32(1..65535)
     MAX-ACCESS  read-create
     STATUS      current
     DESCRIPTION
         "
         Indicates the maxmum number of the sipat0 trunk.
         "
     ::= { hwEntPbxSipAt0TrkEntry 13 }

  --==============================================================

   hwEntPbxPraTrkTable OBJECT-TYPE
     SYNTAX      SEQUENCE OF HwEntPbxPraTrkEntry
     MAX-ACCESS  not-accessible
     STATUS      current
     DESCRIPTION
       "
       A list of hwEntPbxPraTrkEntry objects.
       "
     ::= { hwEntVoicePbxMIB 26 }

   hwEntPbxPraTrkEntry OBJECT-TYPE
     SYNTAX      HwEntPbxPraTrkEntry
     MAX-ACCESS  not-accessible
     STATUS      current
     DESCRIPTION
       "A list of hwEntPbxPraTrkEntry objects."
     INDEX    {
               hwEntPbxPraTrkIndex
              }
     ::= { hwEntPbxPraTrkTable 1 }

   HwEntPbxPraTrkEntry ::=
     SEQUENCE
     {
        hwEntPbxPraTrkIndex             Integer32,
        hwEntPbxPraTrkRowStatus         RowStatus,
        hwEntPbxPraTrkGroupName         DisplayString,
        hwEntPbxPraTrkAdminStatus       INTEGER,
        hwEntPbxPraTrkChannelNumber     Integer32
     }

   hwEntPbxPraTrkIndex OBJECT-TYPE
     SYNTAX      Integer32
     MAX-ACCESS  not-accessible
     STATUS      current
     DESCRIPTION
     "
     Indicates the index of physical trunk.
     bits 24-31:  slot index
     bits 23-16: subcard index
     bits 15-8: port index
     bits 7-0:  time slot
     "
     ::= { hwEntPbxPraTrkEntry 1 }

   hwEntPbxPraTrkRowStatus OBJECT-TYPE
     SYNTAX      RowStatus
     MAX-ACCESS  read-create
     STATUS      current
     DESCRIPTION
         "
         Indicates the row status.
         active(1)
         notInService(2)
         notReady(3)
         createAndGo(4)
         createAndWait(5)
         destroy(6)
         "
     ::= { hwEntPbxPraTrkEntry 2 }

   hwEntPbxPraTrkGroupName OBJECT-TYPE
     SYNTAX      DisplayString(SIZE(1..32))
     MAX-ACCESS  read-create
     STATUS      current
     DESCRIPTION
         "
         Indicates the pra trunk group name.
         "
     ::= { hwEntPbxPraTrkEntry 3 }

   hwEntPbxPraTrkAdminStatus OBJECT-TYPE
     SYNTAX      INTEGER{block(1),normal(2),reserved(3)}
     MAX-ACCESS  read-create
     STATUS      current
     DESCRIPTION
         "
         Indicates the time slot state of the pra trunk group.
         block(1)
         normal(2)
         reserved(3)
         "
     ::= { hwEntPbxPraTrkEntry 4 }
  
   hwEntPbxPraTrkChannelNumber OBJECT-TYPE
     SYNTAX      Integer32(1..32)
     MAX-ACCESS  read-create
     STATUS      current
     DESCRIPTION
         "
         Indicates the number of channels for the pra trunk group.
         "
     ::= { hwEntPbxPraTrkEntry 5}
  --==============================================================

 hwEntPbxCdrServerTable OBJECT-TYPE
     SYNTAX      SEQUENCE OF HwEntPbxCdrServerEntry
     MAX-ACCESS  not-accessible
     STATUS      current
     DESCRIPTION
       "
       A list of hwEntPbxCdrServerEntry objects.
       "
     ::= { hwEntVoicePbxMIB 25 }

   hwEntPbxCdrServerEntry OBJECT-TYPE
     SYNTAX      HwEntPbxCdrServerEntry
     MAX-ACCESS  not-accessible
     STATUS      current
     DESCRIPTION
       "A list of hwEntPbxCdrServerEntry objects."
     INDEX    {
               hwEntPbxCdrServerProtocolType
              }
     ::= { hwEntPbxCdrServerTable 1 }

   HwEntPbxCdrServerEntry ::=
     SEQUENCE
     {
        hwEntPbxCdrServerProtocolType          INTEGER,
        hwEntPbxCdrServerRowStatus             RowStatus,
        hwEntPbxCdrServerLocalIp               IpAddress,
        hwEntPbxCdrServerLocalPort             Integer32,
        hwEntPbxCdrServerServerIp              IpAddress,
        hwEntPbxCdrServerServerPort            Integer32,
        hwEntPbxCdrServerUserName              DisplayString,
        hwEntPbxCdrServerPasswordType          INTEGER,
        hwEntPbxCdrServerPassword              DisplayString,
        hwEntPbxCdrServerState                 INTEGER,
        hwEntPbxCdrServerIsTextField0          Unsigned32,
        hwEntPbxCdrServerIsTextField1          Unsigned32,
        hwEntPbxCdrServerbillPoolUsed          Integer32,
        hwEntPbxCdrServerbillPoolMax           Integer32,
        hwEntPbxCdrServerbillPoolAlarm         Integer32,
        hwEntPbxCdrServerbillPoolAlarmState    INTEGER,
        hwEntPbxCdrServerbillPoolFullDiscard   INTEGER,
        hwEntPbxCdrServerCallerLimit           INTEGER,
        hwEntPbxCdrServerCallerInteroffice     INTEGER,
        hwEntPbxCdrServerCallerLocal           INTEGER,
        hwEntPbxCdrServerCallerLocaltoll       INTEGER,
        hwEntPbxCdrServerCallerDDD             INTEGER,
        hwEntPbxCdrServerCallerIDD             INTEGER,
        hwEntPbxCdrServerCallerUnknown         INTEGER,
        hwEntPbxCdrServerCalleeLimit           INTEGER,
        hwEntPbxCdrServerCalleeInteroffice     INTEGER,
        hwEntPbxCdrServerCalleeLocal           INTEGER,
        hwEntPbxCdrServerCalleeLocaltoll       INTEGER,
        hwEntPbxCdrServerCalleeDDD             INTEGER,
        hwEntPbxCdrServerCalleeIDD             INTEGER,
        hwEntPbxCdrServerCalleeVU              INTEGER,
        hwEntPbxCdrServerbillFormat            INTEGER

     }

   hwEntPbxCdrServerProtocolType OBJECT-TYPE
     SYNTAX      INTEGER{ftp(1),radius(2),internal(3),diameter(4),sftp(5)}
     MAX-ACCESS  not-accessible
     STATUS      current
     DESCRIPTION
         "
         Indicates the index of CDR server type.
         ftp(1)
         radius(2)
         internal(3)
         diameter(4)
         sftp(5)
         "
     ::= { hwEntPbxCdrServerEntry 1 }

   hwEntPbxCdrServerRowStatus OBJECT-TYPE
     SYNTAX      RowStatus
     MAX-ACCESS  read-create
     STATUS      current
     DESCRIPTION
         "
         Indicates row status of table.
         active(1)
         notInService(2)
         notReady(3)
         createAndGo(4)
         createAndWait(5)
         destroy(6)
         "
     ::= { hwEntPbxCdrServerEntry 2 }

  hwEntPbxCdrServerLocalIp OBJECT-TYPE
     SYNTAX      IpAddress
     MAX-ACCESS  read-create
     STATUS      current
     DESCRIPTION
         "
         Indicates local IP address.
         "
     ::= { hwEntPbxCdrServerEntry 3 }

  hwEntPbxCdrServerLocalPort  OBJECT-TYPE
     SYNTAX      Integer32(1..65535)
     MAX-ACCESS  read-create
     STATUS      current
     DESCRIPTION
         "
         Indicates local UDP port.
         "
     ::= { hwEntPbxCdrServerEntry 4 }

  hwEntPbxCdrServerServerIp OBJECT-TYPE
     SYNTAX      IpAddress
     MAX-ACCESS  read-create
     STATUS      current
     DESCRIPTION
         "
         Indicates the server IP address of CDR server.
         "
     ::= { hwEntPbxCdrServerEntry 5 }

  hwEntPbxCdrServerServerPort OBJECT-TYPE
     SYNTAX      Integer32(1..65535)
     MAX-ACCESS  read-create
     STATUS      current
     DESCRIPTION
         "
         Indicates the server UDP port of CDR server.
         "
     ::= { hwEntPbxCdrServerEntry 6 }

  hwEntPbxCdrServerUserName OBJECT-TYPE
     SYNTAX      DisplayString(SIZE (0..15))
     MAX-ACCESS  read-create
     STATUS      current
     DESCRIPTION
         "
         Indicates the user name of CDR server.
         "
     ::= { hwEntPbxCdrServerEntry 7 }

   hwEntPbxCdrServerPasswordType OBJECT-TYPE
     SYNTAX      INTEGER{simple(1),cipher(2)}
     MAX-ACCESS  read-create
     STATUS      current
     DESCRIPTION
         "
         Indicates the user password type of CDR server.
         simple(1)
         cipher(2)
         "
     ::= { hwEntPbxCdrServerEntry 8 }

   hwEntPbxCdrServerPassword OBJECT-TYPE
     SYNTAX      DisplayString(SIZE (0..15))
     MAX-ACCESS  read-create
     STATUS      current
     DESCRIPTION
         "
         Indicates the user password of CDR server.
         "
     ::= { hwEntPbxCdrServerEntry 9 }

  hwEntPbxCdrServerState OBJECT-TYPE
     SYNTAX      INTEGER{connecting(1),connected(2),transmitting(3),
                         releasing(4),released(5)}
     MAX-ACCESS  read-create
     STATUS      current
     DESCRIPTION
         "
         Indicates the connect state of CDR server.
         connecting(1)
         connected(2)
         transmitting(3)
         releasing(4)
         released(5)
         "
     ::= { hwEntPbxCdrServerEntry 10 }

  hwEntPbxCdrServerIsTextField0 OBJECT-TYPE
     SYNTAX      Unsigned32
     MAX-ACCESS  read-create
     STATUS      current
     DESCRIPTION
         "
         Indicates Text bill field switch.
         "
     ::= { hwEntPbxCdrServerEntry 11 }

  hwEntPbxCdrServerIsTextField1 OBJECT-TYPE
     SYNTAX      Unsigned32
     MAX-ACCESS  read-create
     STATUS      current
     DESCRIPTION
         "
         Indicates Text bill field switch.
         "
     ::= { hwEntPbxCdrServerEntry 12 }

  hwEntPbxCdrServerbillPoolUsed OBJECT-TYPE
     SYNTAX      Integer32(1..10000)
     MAX-ACCESS  read-create
     STATUS      current
     DESCRIPTION
         "
         Indicates billpool usage.
         "
     ::= { hwEntPbxCdrServerEntry 13 }

  hwEntPbxCdrServerbillPoolMax OBJECT-TYPE
     SYNTAX      Integer32(1..10000)
     MAX-ACCESS  read-create
     STATUS      current
     DESCRIPTION
         "
         Indicates billpool size.
         "
     ::= { hwEntPbxCdrServerEntry 14 }

  hwEntPbxCdrServerbillPoolAlarm OBJECT-TYPE
     SYNTAX      Integer32(1..10000)
     MAX-ACCESS  read-create
     STATUS      current
     DESCRIPTION
         "
         Indicates billpool alarm threshold.
         "
     ::= { hwEntPbxCdrServerEntry 15 }

  hwEntPbxCdrServerbillPoolAlarmState OBJECT-TYPE
     SYNTAX      INTEGER{notfull(1),full(2)}
     MAX-ACCESS  read-create
     STATUS      current
     DESCRIPTION
         "
         Indicates billpool alarm state.
         notfull(1)
         full(2)
         "
     ::= { hwEntPbxCdrServerEntry 16 }

  hwEntPbxCdrServerbillPoolFullDiscard OBJECT-TYPE
     SYNTAX      INTEGER{disable(1),enable(2)}
     MAX-ACCESS  read-create
     STATUS      current
     DESCRIPTION
         "
         Indicates is dicard new bill when billpool is full.
         disable(1)
         enable(2)
         "
     ::= { hwEntPbxCdrServerEntry 17 }

  hwEntPbxCdrServerCallerLimit OBJECT-TYPE
     SYNTAX      INTEGER{disable(1),enable(2)}
     MAX-ACCESS  read-create
     STATUS      current
     DESCRIPTION
         "
         Indicates caller limit when billpool is full.
         disable(1)
         enable(2)
         "
     ::= { hwEntPbxCdrServerEntry 18 }

  hwEntPbxCdrServerCallerInteroffice OBJECT-TYPE
     SYNTAX      INTEGER{disable(1),enable(2)}
     MAX-ACCESS  read-create
     STATUS      current
     DESCRIPTION
         "
         Indicates caller interoffice call limit when billpool is full.
         disable(1)
         enable(2)
         "
     ::= { hwEntPbxCdrServerEntry 19 }

  hwEntPbxCdrServerCallerLocal OBJECT-TYPE
     SYNTAX      INTEGER{disable(1),enable(2)}
     MAX-ACCESS  read-create
     STATUS      current
     DESCRIPTION
         "
         Indicates caller local call limit when billpool is full.
         disable(1)
         enable(2)
         "
     ::= { hwEntPbxCdrServerEntry 20 }

  hwEntPbxCdrServerCallerLocaltoll OBJECT-TYPE
     SYNTAX      INTEGER{disable(1),enable(2)}
     MAX-ACCESS  read-create
     STATUS      current
     DESCRIPTION
         "
         Indicates caller localtoll call limit when billpool is full.
         disable(1)
         enable(2)
         "
     ::= { hwEntPbxCdrServerEntry 21 }

  hwEntPbxCdrServerCallerDDD OBJECT-TYPE
     SYNTAX      INTEGER{disable(1),enable(2)}
     MAX-ACCESS  read-create
     STATUS      current
     DESCRIPTION
         "
         Indicates caller DDD call limit when billpool is full.
         disable(1)
         enable(2)
         "
     ::= { hwEntPbxCdrServerEntry 22 }

  hwEntPbxCdrServerCallerIDD OBJECT-TYPE
     SYNTAX      INTEGER{disable(1),enable(2)}
     MAX-ACCESS  read-create
     STATUS      current
     DESCRIPTION
         "
         Indicates caller IDD call limit when billpool is full.
         disable(1)
         enable(2)
         "
     ::= { hwEntPbxCdrServerEntry 23 }

  hwEntPbxCdrServerCallerUnknown OBJECT-TYPE
     SYNTAX      INTEGER{disable(1),enable(2)}
     MAX-ACCESS  read-create
     STATUS      current
     DESCRIPTION
         "
         Indicates caller unknown call limit when billpool is full.
         disable(1)
         enable(2)
         "
     ::= { hwEntPbxCdrServerEntry 24 }

  hwEntPbxCdrServerCalleeLimit OBJECT-TYPE
     SYNTAX      INTEGER{disable(1),enable(2)}
     MAX-ACCESS  read-create
     STATUS      current
     DESCRIPTION
         "
         Indicates callee limit when billpool is full.
         disable(1)
         enable(2)
         "
     ::= { hwEntPbxCdrServerEntry 25 }

  hwEntPbxCdrServerCalleeInteroffice OBJECT-TYPE
     SYNTAX      INTEGER{disable(1),enable(2)}
     MAX-ACCESS  read-create
     STATUS      current
     DESCRIPTION
         "
         Indicates callee interoffice call limit when billpool is full.
         disable(1)
         enable(2)
         "
     ::= { hwEntPbxCdrServerEntry 26 }

  hwEntPbxCdrServerCalleeLocal OBJECT-TYPE
     SYNTAX      INTEGER{disable(1),enable(2)}
     MAX-ACCESS  read-create
     STATUS      current
     DESCRIPTION
         "
         Indicates callee local call limit when billpool is full.
         disable(1)
         enable(2)
         "
     ::= { hwEntPbxCdrServerEntry 27 }

  hwEntPbxCdrServerCalleeLocaltoll OBJECT-TYPE
     SYNTAX      INTEGER{disable(1),enable(2)}
     MAX-ACCESS  read-create
     STATUS      current
     DESCRIPTION
         "
         Indicates callee localtoll call limit when billpool is full.
         disable(1)
         enable(2)
         "
     ::= { hwEntPbxCdrServerEntry 28 }

  hwEntPbxCdrServerCalleeDDD OBJECT-TYPE
     SYNTAX      INTEGER{disable(1),enable(2)}
     MAX-ACCESS  read-create
     STATUS      current
     DESCRIPTION
         "
         Indicates callee DDD call limit when billpool is full.
         disable(1)
         enable(2)
         "
     ::= { hwEntPbxCdrServerEntry 29 }

  hwEntPbxCdrServerCalleeIDD OBJECT-TYPE
     SYNTAX      INTEGER{disable(1),enable(2)}
     MAX-ACCESS  read-create
     STATUS      current
     DESCRIPTION
         "
         Indicates callee IDD call limit when billpool is full.
         disable(1)
         enable(2)
         "
     ::= { hwEntPbxCdrServerEntry 30 }

  hwEntPbxCdrServerCalleeVU OBJECT-TYPE
     SYNTAX      INTEGER{disable(1),enable(2)}
     MAX-ACCESS  read-create
     STATUS      current
     DESCRIPTION
         "
         Indicates callee VU call limit when billpool is full.
         disable(1)
         enable(2)
         "
     ::= { hwEntPbxCdrServerEntry 31 }

  hwEntPbxCdrServerbillFormat OBJECT-TYPE
     SYNTAX      INTEGER{cdr(1),softx(2),text(3),u1900(4)}
     MAX-ACCESS  read-create
     STATUS      current
     DESCRIPTION
         "
         Indicates bill format.
         CDR(1)
         SOFTX(2)
         TEXT(3)
         U1900(4)
         "
     ::= { hwEntPbxCdrServerEntry 32 }


   --==============================================================

   hwEntPbxRouteTable OBJECT-TYPE
     SYNTAX      SEQUENCE OF HwEntPbxRouteEntry
     MAX-ACCESS  not-accessible
     STATUS      current
     DESCRIPTION
       "
       A list of hwEntPbxRouteEntry objects.
       "
     ::= { hwEntVoicePbxMIB 15 }

   hwEntPbxRouteEntry OBJECT-TYPE
     SYNTAX      HwEntPbxRouteEntry
     MAX-ACCESS  not-accessible
     STATUS      current
     DESCRIPTION
       "A list of hwEntPbxRouteEntry objects."
     INDEX    {
               hwEntPbxRouteCallprefixName,
               hwEntPbxRouteCountryCode,
               hwEntPbxRouteAreaCode,
               hwEntPbxRouteCallerNum,
               hwEntPbxRouteFromDate,
               hwEntPbxRouteFromTime,
               hwEntPbxRouteToDate,
               hwEntPbxRouteToTime,
               hwEntPbxRouteRepeatMode,
               hwEntPbxRouteBeginDate,
               hwEntPbxRouteBeginWeekday,
               hwEntPbxRouteBeginTime,
               hwEntPbxRouteEndDate,
               hwEntPbxRouteEndWeekday,
               hwEntPbxRouteEndTime
              }
     ::= { hwEntPbxRouteTable 1 }

   HwEntPbxRouteEntry ::=
     SEQUENCE
     {
       hwEntPbxRouteCallprefixName       DisplayString,
       hwEntPbxRouteCountryCode          DisplayString,
       hwEntPbxRouteAreaCode             DisplayString,
       hwEntPbxRouteCallerNum            DisplayString,
       hwEntPbxRouteFromDate             DisplayString,
       hwEntPbxRouteFromTime             DisplayString,
       hwEntPbxRouteToDate               DisplayString,
       hwEntPbxRouteToTime               DisplayString,
       hwEntPbxRouteRepeatMode           INTEGER,
       hwEntPbxRouteBeginDate            DisplayString,
       hwEntPbxRouteBeginWeekday         INTEGER,
       hwEntPbxRouteBeginTime            DisplayString,
       hwEntPbxRouteEndDate              DisplayString,
       hwEntPbxRouteEndWeekday           INTEGER,
       hwEntPbxRouteEndTime              DisplayString,
       hwEntPbxRouteRowStatus            RowStatus,
       hwEntPbxRouteTrkGrpName1          DisplayString,
       hwEntPbxRouteTrkGrpName2          DisplayString,
       hwEntPbxRouteTrkGrpName3          DisplayString,
       hwEntPbxRouteTrkGrpName4          DisplayString
     }

   hwEntPbxRouteCallprefixName OBJECT-TYPE
     SYNTAX      DisplayString(SIZE (0..32))
     MAX-ACCESS  not-accessible
     STATUS      current
     DESCRIPTION
         "
         Indicates the callprefix name of route.
         "
     ::= { hwEntPbxRouteEntry 1 }

   hwEntPbxRouteCountryCode OBJECT-TYPE
     SYNTAX      DisplayString(SIZE (0..4))
     MAX-ACCESS  not-accessible
     STATUS      current
     DESCRIPTION
         "
         Indicates the country code of route.
         "
     ::= { hwEntPbxRouteEntry 2 }

   hwEntPbxRouteAreaCode OBJECT-TYPE
     SYNTAX      DisplayString(SIZE (0..8))
     MAX-ACCESS  not-accessible
     STATUS      current
     DESCRIPTION
         "
         Indicates the area code of route.
         "
     ::= { hwEntPbxRouteEntry 3 }

   hwEntPbxRouteCallerNum OBJECT-TYPE
     SYNTAX      DisplayString(SIZE (0..24))
     MAX-ACCESS  not-accessible
     STATUS      current
     DESCRIPTION
         "
         Indicates the caller number of route.
         "
     ::= { hwEntPbxRouteEntry 4 }

   hwEntPbxRouteFromDate OBJECT-TYPE
     SYNTAX      DisplayString(SIZE (0..10))
     MAX-ACCESS  not-accessible
     STATUS      current
     DESCRIPTION
         "
         Indicates the begin date of time period.
         format: yyyy-mm-dd
         "
     ::= { hwEntPbxRouteEntry 5 }

  hwEntPbxRouteFromTime OBJECT-TYPE
     SYNTAX      DisplayString(SIZE (0..8))
     MAX-ACCESS  not-accessible
     STATUS      current
     DESCRIPTION
         "
         Indicates the begin time of time period.
         format: hh:mm:ss
         "
     ::= { hwEntPbxRouteEntry 6 }

   hwEntPbxRouteToDate OBJECT-TYPE
     SYNTAX      DisplayString(SIZE (0..10))
     MAX-ACCESS  not-accessible
     STATUS      current
     DESCRIPTION
         "
         Indicates the end date of time period.
         format: yyyy-mm-dd
         "
     ::= { hwEntPbxRouteEntry 7 }

   hwEntPbxRouteToTime OBJECT-TYPE
     SYNTAX      DisplayString(SIZE (0..8))
     MAX-ACCESS  not-accessible
     STATUS      current
     DESCRIPTION
         "
         Indicates the end time of time period.
         format: hh:mm:ss
         "
     ::= { hwEntPbxRouteEntry 8 }

   hwEntPbxRouteRepeatMode OBJECT-TYPE
     SYNTAX      INTEGER{noRepeat(1),yearly(2),monthly(3),weekly(4),daily(5)}
     MAX-ACCESS  not-accessible
     STATUS      current
     DESCRIPTION
         "
         Indicates the repeat mode.
         noRepeat(1);
         yearly(2);
         monthly(3);
         weekly(4);
         daily(5);
         "
     ::= { hwEntPbxRouteEntry 9 }

    hwEntPbxRouteBeginDate OBJECT-TYPE
     SYNTAX      DisplayString(SIZE (0..5))
     MAX-ACCESS  not-accessible
     STATUS      current
     DESCRIPTION
         "
          Indicates the begin date of time repeat.
          format: mm-dd
         "
     ::= { hwEntPbxRouteEntry 10 }

   hwEntPbxRouteBeginWeekday OBJECT-TYPE
     SYNTAX      INTEGER{mon(1),tue(2),wed(3),thu(4),fri(5),sat(6),sun(7),none(8)}
     MAX-ACCESS  not-accessible
     STATUS      current
     DESCRIPTION
         "
         Indicates the begin weekday.
         mon(1);
         tue(2);
         wed(3);
         thu(4);
         fri(5);
         sat(6);
         sun(7);
         none(8);
         "
     ::= { hwEntPbxRouteEntry 11 }

   hwEntPbxRouteBeginTime OBJECT-TYPE
     SYNTAX      DisplayString(SIZE (0..8))
     MAX-ACCESS  not-accessible
     STATUS      current
     DESCRIPTION
         "
         Indicates the begin time of time repeat.
         format: hh:mm:ss
         "
     ::= { hwEntPbxRouteEntry 12 }

   hwEntPbxRouteEndDate OBJECT-TYPE
     SYNTAX      DisplayString(SIZE (0..5))
     MAX-ACCESS  not-accessible
     STATUS      current
     DESCRIPTION
         "
         Indicates the end date of time repeat.
         format: mm-dd
         "
     ::= { hwEntPbxRouteEntry 13 }

   hwEntPbxRouteEndWeekday OBJECT-TYPE
     SYNTAX      INTEGER{mon(1),tue(2),wed(3),thu(4),fri(5),sat(6),sun(7),none(8)}
     MAX-ACCESS  not-accessible
     STATUS      current
     DESCRIPTION
         "
         Indicates the end weekday.
         mon(1);
         tue(2);
         wed(3);
         thu(4);
         fri(5);
         sat(6);
         sun(7);
         none(8);
         "
     ::= { hwEntPbxRouteEntry 14 }

   hwEntPbxRouteEndTime OBJECT-TYPE
     SYNTAX      DisplayString(SIZE (0..8))
     MAX-ACCESS  not-accessible
     STATUS      current
     DESCRIPTION
         "
         Indicates the end time of time repeat.
         format: hh:mm:ss
         "
     ::= { hwEntPbxRouteEntry 15 }

   hwEntPbxRouteRowStatus OBJECT-TYPE
     SYNTAX      RowStatus
     MAX-ACCESS  read-create
     STATUS      current
     DESCRIPTION
         "
         Indicates row status of table.
         "
     ::= { hwEntPbxRouteEntry 16 }

   hwEntPbxRouteTrkGrpName1 OBJECT-TYPE
     SYNTAX      DisplayString(SIZE (0..32))
     MAX-ACCESS  read-create
     STATUS      current
     DESCRIPTION
         "
         Indicates the trunk group name 1.
         "
     ::= { hwEntPbxRouteEntry 17 }

   hwEntPbxRouteTrkGrpName2 OBJECT-TYPE
     SYNTAX      DisplayString(SIZE (0..32))
     MAX-ACCESS  read-create
     STATUS      current
     DESCRIPTION
         "
         Indicates the trunk group name 2.
         "
     ::= { hwEntPbxRouteEntry 18 }

   hwEntPbxRouteTrkGrpName3 OBJECT-TYPE
     SYNTAX      DisplayString(SIZE (0..32))
     MAX-ACCESS  read-create
     STATUS      current
     DESCRIPTION
         "
         Indicates the trunk group name 3.
         "
     ::= { hwEntPbxRouteEntry 19 }

   hwEntPbxRouteTrkGrpName4 OBJECT-TYPE
     SYNTAX      DisplayString(SIZE (0..32))
     MAX-ACCESS  read-create
     STATUS      current
     DESCRIPTION
         "
         Indicates the trunk group name 4.
         "
     ::= { hwEntPbxRouteEntry 20 }

  --==============================================================

   hwEntPbxCallerChgTable OBJECT-TYPE
     SYNTAX      SEQUENCE OF HwEntPbxCallerChgEntry
     MAX-ACCESS  not-accessible
     STATUS      current
     DESCRIPTION
       "
       A list of hwEntPbxCallerChgEntry objects.
       "
     ::= { hwEntVoicePbxMIB 16 }

   hwEntPbxCallerChgEntry OBJECT-TYPE
     SYNTAX      HwEntPbxCallerChgEntry
     MAX-ACCESS  not-accessible
     STATUS      current
     DESCRIPTION
       "A list of hwEntPbxCallerChgEntry objects."
     INDEX    {
               hwEntPbxCallerChgEnterprise,
               hwEntPbxCallerChgDnset,
               hwEntPbxCallerChgCentrex,
               hwEntPbxCallerChgCountryCode,
               hwEntPbxCallerChgAreaCode,
               hwEntPbxCallerChgCallerNum
              }
     ::= { hwEntPbxCallerChgTable 1 }

   HwEntPbxCallerChgEntry ::=
     SEQUENCE
     {
       hwEntPbxCallerChgEnterprise       DisplayString,
       hwEntPbxCallerChgDnset            DisplayString,
       hwEntPbxCallerChgCentrex          DisplayString,
       hwEntPbxCallerChgCountryCode      DisplayString,
       hwEntPbxCallerChgAreaCode         DisplayString,
       hwEntPbxCallerChgCallerNum        DisplayString,
       hwEntPbxCallerChgRowStatus        RowStatus,
       hwEntPbxCallerChgChangeType       INTEGER,
       hwEntPbxCallerChgNewDnSet         DisplayString,
       hwEntPbxCallerChgNewCentrex       DisplayString,
       hwEntPbxCallerChgNewCountryCode   DisplayString,
       hwEntPbxCallerChgNewAreaCode      DisplayString,
       hwEntPbxCallerChgNewEnterprise    DisplayString
     }

   hwEntPbxCallerChgEnterprise OBJECT-TYPE
     SYNTAX      DisplayString(SIZE (1..32))
     MAX-ACCESS  not-accessible
     STATUS      current
     DESCRIPTION
         "
         Indicates the enterprise of caller change.
         "
     ::= { hwEntPbxCallerChgEntry 1 }

   hwEntPbxCallerChgDnset OBJECT-TYPE
     SYNTAX      DisplayString(SIZE (1..32))
     MAX-ACCESS  not-accessible
     STATUS      current
     DESCRIPTION
         "
         Indicates the dn-set of caller change.
         "
     ::= { hwEntPbxCallerChgEntry 2 }

   hwEntPbxCallerChgCentrex OBJECT-TYPE
     SYNTAX      DisplayString(SIZE (1..32))
     MAX-ACCESS  not-accessible
     STATUS      current
     DESCRIPTION
         "
         Indicates the centrex of caller change.
         "
     ::= { hwEntPbxCallerChgEntry 3 }

   hwEntPbxCallerChgCountryCode OBJECT-TYPE
     SYNTAX      DisplayString(SIZE (0..4))
     MAX-ACCESS  not-accessible
     STATUS      current
     DESCRIPTION
         "
         Indicates the country code of caller change.
         "
     ::= { hwEntPbxCallerChgEntry 4 }

  hwEntPbxCallerChgAreaCode OBJECT-TYPE
     SYNTAX      DisplayString(SIZE (0..8))
     MAX-ACCESS  not-accessible
     STATUS      current
     DESCRIPTION
         "
         Indicates the area code of caller change.
         "
     ::= { hwEntPbxCallerChgEntry 5 }

   hwEntPbxCallerChgCallerNum OBJECT-TYPE
     SYNTAX      DisplayString(SIZE (1..24))
     MAX-ACCESS  not-accessible
     STATUS      current
     DESCRIPTION
         "
         Indicates the caller number of caller change.
         "
     ::= { hwEntPbxCallerChgEntry 6 }

   hwEntPbxCallerChgRowStatus OBJECT-TYPE
     SYNTAX      RowStatus
     MAX-ACCESS  read-create
     STATUS      current
     DESCRIPTION
         "
         Indicates row status of table.
         "
     ::= { hwEntPbxCallerChgEntry 7 }

   hwEntPbxCallerChgChangeType OBJECT-TYPE
     SYNTAX      INTEGER{newDnset(1),newCentrex(2),newDnsetCentrex(3),
                         newCountryCode(4),newAreaCode(5),newCountryAreaCode(6),
                         newEnterpriseDnsetCentrex(7)}
     MAX-ACCESS  read-create
     STATUS      current
     DESCRIPTION
         "
         Indicates the change type of caller change.
         newDnset(1);
         newCentrex(2);
         newDnsetCentrex(3);
         newCountryCode(4);
         newAreaCode(5);
         newCountryAreaCode(6);
         newEnterpriseDnsetCentrex(7);
         "
     ::= { hwEntPbxCallerChgEntry 8 }

    hwEntPbxCallerChgNewDnSet OBJECT-TYPE
     SYNTAX      DisplayString(SIZE (0..32))
     MAX-ACCESS  read-create
     STATUS      current
     DESCRIPTION
         "
          Indicates the new dn-set of caller change.
         "
     ::= { hwEntPbxCallerChgEntry 9 }

   hwEntPbxCallerChgNewCentrex OBJECT-TYPE
     SYNTAX      DisplayString(SIZE (0..32))
     MAX-ACCESS  read-create
     STATUS      current
     DESCRIPTION
         "
         Indicates the new centrex of caller change.
         mon(1);
         tue(2);
         wed(3);
         thu(4);
         fri(5);
         sat(6);
         sun(7);
         none(8);
         "
     ::= { hwEntPbxCallerChgEntry 10 }

   hwEntPbxCallerChgNewCountryCode OBJECT-TYPE
     SYNTAX      DisplayString(SIZE (0..4))
     MAX-ACCESS  read-create
     STATUS      current
     DESCRIPTION
         "
         Indicates the new country code of caller change.
         "
     ::= { hwEntPbxCallerChgEntry 11 }

   hwEntPbxCallerChgNewAreaCode OBJECT-TYPE
     SYNTAX      DisplayString(SIZE (1..8))
     MAX-ACCESS  read-create
     STATUS      current
     DESCRIPTION
         "
         Indicates the new area code of caller change.
         "
     ::= { hwEntPbxCallerChgEntry 12 }

   hwEntPbxCallerChgNewEnterprise OBJECT-TYPE
     SYNTAX      DisplayString(SIZE (0..32))
     MAX-ACCESS  read-create
     STATUS      current
     DESCRIPTION
         "
         Indicates the new enterprise name of caller change.
         "
     ::= { hwEntPbxCallerChgEntry 13 }

  --==============================================================

   hwEntPbxBeforeRouteChgTable OBJECT-TYPE
     SYNTAX      SEQUENCE OF HwEntPbxBeforeRouteChgEntry
     MAX-ACCESS  not-accessible
     STATUS      current
     DESCRIPTION
       "
       A list of hwEntPbxBeforeRouteChgEntry objects.
       "
     ::= { hwEntVoicePbxMIB 17 }

   hwEntPbxBeforeRouteChgEntry OBJECT-TYPE
     SYNTAX      HwEntPbxBeforeRouteChgEntry
     MAX-ACCESS  not-accessible
     STATUS      current
     DESCRIPTION
       "A list of hwEntPbxBeforeRouteChgEntry objects."
     INDEX    {
               hwEntPbxBeforeRouteChgName
              }
     ::= { hwEntPbxBeforeRouteChgTable 1 }

   HwEntPbxBeforeRouteChgEntry ::=
     SEQUENCE
     {
       hwEntPbxBeforeRouteChgName             DisplayString,
       hwEntPbxBeforeRouteChgCallprefixName   DisplayString,
       hwEntPbxBeforeRouteChgRowStatus        RowStatus,
       hwEntPbxBeforeRouteChgCountryCode      DisplayString,
       hwEntPbxBeforeRouteChgAreaCode         DisplayString,
       hwEntPbxBeforeRouteChgCallerNum        DisplayString,
       hwEntPbxBeforeRouteChgCentrexNumber    DisplayString,
       hwEntPbxBeforeRouteChgOrigDNChgType    INTEGER,
       hwEntPbxBeforeRouteChgOrigDNChgPos     Integer32,
       hwEntPbxBeforeRouteChgOrigDNChgLen     Integer32,
       hwEntPbxBeforeRouteChgOrigDNNew        DisplayString,
       hwEntPbxBeforeRouteChgTermDNChgType    INTEGER,
       hwEntPbxBeforeRouteChgTermDNChgPos     Integer32,
       hwEntPbxBeforeRouteChgTermDNChgLen     Integer32,
       hwEntPbxBeforeRouteChgTermDNNew        DisplayString,
       hwEntPbxBeforeRouteChgReAnalyse        INTEGER,
       hwEntPbxBeforeRouteChgDualDialToneFlag INTEGER,
       hwEntPbxBeforeRouteChgNewEnterprise    DisplayString,
       hwEntPbxBeforeRouteChgNewDnSet         DisplayString,
       hwEntPbxBeforeRouteChgNewCentrex       DisplayString
     }

   hwEntPbxBeforeRouteChgName OBJECT-TYPE
     SYNTAX      DisplayString(SIZE (1..32))
     MAX-ACCESS  not-accessible
     STATUS      current
     DESCRIPTION
         "
         Indicates the name of before route change.
         "
     ::= { hwEntPbxBeforeRouteChgEntry 1 }

   hwEntPbxBeforeRouteChgRowStatus OBJECT-TYPE
     SYNTAX      RowStatus
     MAX-ACCESS  read-create
     STATUS      current
     DESCRIPTION
         "
         Indicates row status of table.
         "
     ::= { hwEntPbxBeforeRouteChgEntry 2 }

   hwEntPbxBeforeRouteChgCallprefixName OBJECT-TYPE
     SYNTAX      DisplayString(SIZE (0..32))
     MAX-ACCESS  read-create
     STATUS      current
     DESCRIPTION
         "
         Indicates the callprefix name of before route change.
         "
     ::= { hwEntPbxBeforeRouteChgEntry 3 }

   hwEntPbxBeforeRouteChgCountryCode OBJECT-TYPE
     SYNTAX      DisplayString(SIZE (0..4))
     MAX-ACCESS  read-create
     STATUS      current
     DESCRIPTION
         "
         Indicates the country code of before route change.
         "
     ::= { hwEntPbxBeforeRouteChgEntry 4 }

   hwEntPbxBeforeRouteChgAreaCode OBJECT-TYPE
     SYNTAX      DisplayString(SIZE (0..8))
     MAX-ACCESS  read-create
     STATUS      current
     DESCRIPTION
         "
         Indicates the area code of before route change.
         "
     ::= { hwEntPbxBeforeRouteChgEntry 5 }

  hwEntPbxBeforeRouteChgCallerNum OBJECT-TYPE
     SYNTAX      DisplayString(SIZE (0..24))
     MAX-ACCESS  read-create
     STATUS      current
     DESCRIPTION
         "
         Indicates the caller number of before route change.
         "
     ::= { hwEntPbxBeforeRouteChgEntry 6 }

   hwEntPbxBeforeRouteChgCentrexNumber OBJECT-TYPE
     SYNTAX      DisplayString(SIZE (0..8))
     MAX-ACCESS  read-create
     STATUS      current
     DESCRIPTION
         "
         Indicates the centrex number of before route change.
         "
     ::= { hwEntPbxBeforeRouteChgEntry 7 }

   hwEntPbxBeforeRouteChgOrigDNChgType OBJECT-TYPE
     SYNTAX      INTEGER{noChange(1),modify(2),delete(3),insert(4)}
     MAX-ACCESS  read-create
     STATUS      current
     DESCRIPTION
         "
         Indicates the type of original dial number change before route.
         noChange(1);
         modify(2);
         delete(3);
         insert(4);
         "
     ::= { hwEntPbxBeforeRouteChgEntry 8 }

    hwEntPbxBeforeRouteChgOrigDNChgPos OBJECT-TYPE
     SYNTAX      Integer32(1..44)
     MAX-ACCESS  read-create
     STATUS      current
     DESCRIPTION
         "
          Indicates the position of original dial number change before route.
         "
     ::= { hwEntPbxBeforeRouteChgEntry 9 }

   hwEntPbxBeforeRouteChgOrigDNChgLen OBJECT-TYPE
     SYNTAX      Integer32(1..44)
     MAX-ACCESS  read-create
     STATUS      current
     DESCRIPTION
         "
         Indicates the length of original dial number change before route.
         "
     ::= { hwEntPbxBeforeRouteChgEntry 10 }

   hwEntPbxBeforeRouteChgOrigDNNew OBJECT-TYPE
     SYNTAX      DisplayString(SIZE (0..24))
     MAX-ACCESS  read-create
     STATUS      current
     DESCRIPTION
         "
         Indicates the new number of original dial number change before route.
         "
     ::= { hwEntPbxBeforeRouteChgEntry 11 }

   hwEntPbxBeforeRouteChgTermDNChgType OBJECT-TYPE
     SYNTAX      INTEGER{noChange(1),modify(2),delete(3),insert(4)}
     MAX-ACCESS  read-create
     STATUS      current
     DESCRIPTION
         "
         Indicates the type of terminal dial number change before route
         noChange(1);
         modify(2);
         delete(3);
         insert(4);
         default: noChange(1)
         "
     ::= { hwEntPbxBeforeRouteChgEntry 12 }

   hwEntPbxBeforeRouteChgTermDNChgPos OBJECT-TYPE
     SYNTAX      Integer32 (1..44)
     MAX-ACCESS  read-create
     STATUS      current
     DESCRIPTION
         "
         Indicates the position of terminal dial number change before route.
         "
     ::= { hwEntPbxBeforeRouteChgEntry 13 }

   hwEntPbxBeforeRouteChgTermDNChgLen OBJECT-TYPE
     SYNTAX      Integer32(1..44)
     MAX-ACCESS  read-create
     STATUS      current
     DESCRIPTION
         "
         Indicates the length of terminal dial number change before route.
         "
     ::= { hwEntPbxBeforeRouteChgEntry 14 }

   hwEntPbxBeforeRouteChgTermDNNew OBJECT-TYPE
     SYNTAX      DisplayString(SIZE (0..24))
     MAX-ACCESS  read-create
     STATUS      current
     DESCRIPTION
         "
         Indicates the new number of terminal dial number change before route.
         "
     ::= { hwEntPbxBeforeRouteChgEntry 15 }

   hwEntPbxBeforeRouteChgReAnalyse OBJECT-TYPE
     SYNTAX      INTEGER{disable(1),enable(2)}
     MAX-ACCESS  read-create
     STATUS      current
     DESCRIPTION
         "
         Indicates the type of re-analyse.
         1: disable(1)   - no need;
         2: enable(2)   - need;
         "
     ::= { hwEntPbxBeforeRouteChgEntry 16 }

   hwEntPbxBeforeRouteChgDualDialToneFlag OBJECT-TYPE
     SYNTAX      INTEGER{disable(1),enable(2)}
     MAX-ACCESS  read-create
     STATUS      current
     DESCRIPTION
         "
         Indicates the flag of dual dial tone.
         disable(1);
         enable(2);
         "
     ::= { hwEntPbxBeforeRouteChgEntry 17 }

   hwEntPbxBeforeRouteChgNewEnterprise OBJECT-TYPE
     SYNTAX      DisplayString(SIZE (0..32))
     MAX-ACCESS  read-create
     STATUS      current
     DESCRIPTION
         "
         Indicates the new enterprise name of before route change.
         "
     ::= { hwEntPbxBeforeRouteChgEntry 18 }

   hwEntPbxBeforeRouteChgNewDnSet OBJECT-TYPE
     SYNTAX      DisplayString(SIZE (0..32))
     MAX-ACCESS  read-create
     STATUS      current
     DESCRIPTION
         "
         Indicates the new dial number set of before route change.
         "
     ::= { hwEntPbxBeforeRouteChgEntry 19 }

   hwEntPbxBeforeRouteChgNewCentrex OBJECT-TYPE
     SYNTAX      DisplayString(SIZE (0..32))
     MAX-ACCESS  read-create
     STATUS      current
     DESCRIPTION
         "
         Indicates the new centrex of before route change.
         "
     ::= { hwEntPbxBeforeRouteChgEntry 20 }

  --==============================================================

   hwEntPbxAfterRouteChgTable OBJECT-TYPE
     SYNTAX      SEQUENCE OF HwEntPbxAfterRouteChgEntry
     MAX-ACCESS  not-accessible
     STATUS      current
     DESCRIPTION
       "
       A list of hwEntPbxAfterRouteChgEntry objects.
       "
     ::= { hwEntVoicePbxMIB 18 }

   hwEntPbxAfterRouteChgEntry OBJECT-TYPE
     SYNTAX      HwEntPbxAfterRouteChgEntry
     MAX-ACCESS  not-accessible
     STATUS      current
     DESCRIPTION
       "A list of hwEntPbxAfterRouteChgEntry objects."
     INDEX    {
               hwEntPbxAfterRouteChgName
              }
     ::= { hwEntPbxAfterRouteChgTable 1 }

   HwEntPbxAfterRouteChgEntry ::=
     SEQUENCE
     {
       hwEntPbxAfterRouteChgName             DisplayString,
       hwEntPbxAfterRouteChgRowStatus        RowStatus,
       hwEntPbxAfterRouteChgCallprefixName   DisplayString,
       hwEntPbxAfterRouteChgCountryCode      DisplayString,
       hwEntPbxAfterRouteChgAreaCode         DisplayString,
       hwEntPbxAfterRouteChgCallerNum        DisplayString,
       hwEntPbxAfterRouteChgCentrexNumber    DisplayString,
       hwEntPbxAfterRouteChgOrigDNChgType    INTEGER,
       hwEntPbxAfterRouteChgOrigDNChgPos     Integer32,
       hwEntPbxAfterRouteChgOrigDNChgLen     Integer32,
       hwEntPbxAfterRouteChgOrigDNNew        DisplayString,
       hwEntPbxAfterRouteChgTermDNChgType    INTEGER,
       hwEntPbxAfterRouteChgTermDNChgPos     Integer32,
       hwEntPbxAfterRouteChgTermDNChgLen     Integer32,
       hwEntPbxAfterRouteChgTermDNNew        DisplayString,
       hwEntPbxAfterRouteChgTrkGrpName       DisplayString,
       hwEntPbxAfterRouteChgNewEnterprise    DisplayString,
       hwEntPbxAfterRouteChgNewCentrex       DisplayString
     }

   hwEntPbxAfterRouteChgName OBJECT-TYPE
     SYNTAX      DisplayString(SIZE (1..32))
     MAX-ACCESS  not-accessible
     STATUS      current
     DESCRIPTION
         "
         Indicates the name of after route change.
         "
     ::= { hwEntPbxAfterRouteChgEntry 1 }

   hwEntPbxAfterRouteChgRowStatus OBJECT-TYPE
     SYNTAX      RowStatus
     MAX-ACCESS  read-create
     STATUS      current
     DESCRIPTION
         "
         Indicates row status of table.
         "
     ::= { hwEntPbxAfterRouteChgEntry 2 }

   hwEntPbxAfterRouteChgCallprefixName OBJECT-TYPE
     SYNTAX      DisplayString(SIZE (0..32))
     MAX-ACCESS  read-create
     STATUS      current
     DESCRIPTION
         "
         Indicates the area code of after route change.
         "
     ::= { hwEntPbxAfterRouteChgEntry 3 }


   hwEntPbxAfterRouteChgCountryCode OBJECT-TYPE
     SYNTAX      DisplayString(SIZE (0..4))
     MAX-ACCESS  read-create
     STATUS      current
     DESCRIPTION
         "
         Indicates the country code of after route change.
         "
     ::= { hwEntPbxAfterRouteChgEntry 4 }

   hwEntPbxAfterRouteChgAreaCode OBJECT-TYPE
     SYNTAX      DisplayString(SIZE (0..8))
     MAX-ACCESS  read-create
     STATUS      current
     DESCRIPTION
         "
         Indicates the area code of after route change.
         "
     ::= { hwEntPbxAfterRouteChgEntry 5 }

  hwEntPbxAfterRouteChgCallerNum OBJECT-TYPE
     SYNTAX      DisplayString(SIZE (0..24))
     MAX-ACCESS  read-create
     STATUS      current
     DESCRIPTION
         "
         Indicates the caller number of after route change.
         "
     ::= { hwEntPbxAfterRouteChgEntry 6 }


   hwEntPbxAfterRouteChgCentrexNumber OBJECT-TYPE
     SYNTAX      DisplayString(SIZE (0..8))
     MAX-ACCESS  read-create
     STATUS      current
     DESCRIPTION
         "
         Indicates the centrex number of after route change.
         "
     ::= { hwEntPbxAfterRouteChgEntry 7 }

   hwEntPbxAfterRouteChgOrigDNChgType OBJECT-TYPE
     SYNTAX      INTEGER{noChange(1),modify(2),delete(3),insert(4)}
     MAX-ACCESS  read-create
     STATUS      current
     DESCRIPTION
         "
         Indicates the type of original dial number change after route.
         noChange(1);
         modify(2);
         delete(3);
         insert(4);
         "
     ::= { hwEntPbxAfterRouteChgEntry 8 }

    hwEntPbxAfterRouteChgOrigDNChgPos OBJECT-TYPE
     SYNTAX      Integer32(1..44)
     MAX-ACCESS  read-create
     STATUS      current
     DESCRIPTION
         "
          Indicates the position of original dial number change after route.
         "
     ::= { hwEntPbxAfterRouteChgEntry 9 }

   hwEntPbxAfterRouteChgOrigDNChgLen OBJECT-TYPE
     SYNTAX      Integer32(1..44)
     MAX-ACCESS  read-create
     STATUS      current
     DESCRIPTION
         "
         Indicates the length of original dial number change after route.
         "
     ::= { hwEntPbxAfterRouteChgEntry 10 }

   hwEntPbxAfterRouteChgOrigDNNew OBJECT-TYPE
     SYNTAX      DisplayString(SIZE (0..24))
     MAX-ACCESS  read-create
     STATUS      current
     DESCRIPTION
         "
         Indicates the new number of original dial number change after route.
         "
     ::= { hwEntPbxAfterRouteChgEntry 11 }

   hwEntPbxAfterRouteChgTermDNChgType OBJECT-TYPE
     SYNTAX      INTEGER{noChange(1),modify(2),delete(3),insert(4)}
     MAX-ACCESS  read-create
     STATUS      current
     DESCRIPTION
         "
         Indicates the type of terminal dial number change after route
         noChange(1);
         modify(2);
         delete(3);
         insert(4);
         default: noChange(1)
         "
     ::= { hwEntPbxAfterRouteChgEntry 12 }

   hwEntPbxAfterRouteChgTermDNChgPos OBJECT-TYPE
     SYNTAX      Integer32(1..44)
     MAX-ACCESS  read-create
     STATUS      current
     DESCRIPTION
         "
         Indicates the position of terminal dial number change after route.
         "
     ::= { hwEntPbxAfterRouteChgEntry 13 }

   hwEntPbxAfterRouteChgTermDNChgLen OBJECT-TYPE
     SYNTAX      Integer32(1..44)
     MAX-ACCESS  read-create
     STATUS      current
     DESCRIPTION
         "
         Indicates the length of terminal dial number change after route.
         "
     ::= { hwEntPbxAfterRouteChgEntry 14 }

   hwEntPbxAfterRouteChgTermDNNew OBJECT-TYPE
     SYNTAX      DisplayString(SIZE (0..24))
     MAX-ACCESS  read-create
     STATUS      current
     DESCRIPTION
         "
         Indicates the new number of terminal dial number change after route.
         "
     ::= { hwEntPbxAfterRouteChgEntry 15 }

   hwEntPbxAfterRouteChgTrkGrpName OBJECT-TYPE
     SYNTAX      DisplayString(SIZE (0..32))
     MAX-ACCESS  read-create
     STATUS      current
     DESCRIPTION
         "
         Indicates the new trunk group name of after route change.
         "
     ::= { hwEntPbxAfterRouteChgEntry 16 }

   hwEntPbxAfterRouteChgNewEnterprise OBJECT-TYPE
     SYNTAX      DisplayString(SIZE (0..32))
     MAX-ACCESS  read-create
     STATUS      current
     DESCRIPTION
         "
         Indicates the new enterprise name of after route change.
         "
     ::= { hwEntPbxAfterRouteChgEntry 17 }

   hwEntPbxAfterRouteChgNewCentrex OBJECT-TYPE
     SYNTAX      DisplayString(SIZE (0..32))
     MAX-ACCESS  read-create
     STATUS      current
     DESCRIPTION
         "
         Indicates the new centrex of after route change.
         "
     ::= { hwEntPbxAfterRouteChgEntry 18 }

  --==============================================================

 hwEntPbxUsrGrpTable OBJECT-TYPE
     SYNTAX      SEQUENCE OF HwEntPbxUsrGrpEntry
     MAX-ACCESS  not-accessible
     STATUS      current
     DESCRIPTION
       "
       A list of hwEntPbxUsrGrpEntry objects.
       "
     ::= { hwEntVoicePbxMIB 19 }

   hwEntPbxUsrGrpEntry OBJECT-TYPE
     SYNTAX      HwEntPbxUsrGrpEntry
     MAX-ACCESS  not-accessible
     STATUS      current
     DESCRIPTION
       "A list of hwEntPbxUsrGrpEntry objects."
     INDEX    {
               hwEntPbxUsrGrpName
              }
     ::= { hwEntPbxUsrGrpTable 1 }

   HwEntPbxUsrGrpEntry ::=
     SEQUENCE
     {
        hwEntPbxUsrGrpName                      DisplayString,
        hwEntPbxUsrGrpRowStatus                 RowStatus,
        hwEntPbxUserGroupServiceId              INTEGER,
        hwEntPbxUsrGrpEnterpriseName            DisplayString,
        hwEntPbxUsrGrpDnSet                     DisplayString,
        hwEntPbxUserGroupCentrex                DisplayString,
        hwEntPbxUsrGrpCountryCode               DisplayString,
        hwEntPbxUsrGrpAreaCode                  DisplayString,
        hwEntPbxUserGrpAccessCode               DisplayString,
        hwEntPbxUserGrpRegCode                  DisplayString,
        hwEntPbxUserGrpConsoleCode              DisplayString,
        hwEntPbxUsrGrpDstEnterprise             DisplayString,
        hwEntPbxUserGrpDstDnset                 DisplayString,
        hwEntPbxUserGrpDstCentrex               DisplayString,
        hwEntPbxUserGrpMaxQueueNum              Integer32,
        hwEntPbxUserGrpToneId                   Integer32,
        hwEntPbxUsrGrpToneFileName              DisplayString,
        hwEntPbxUserGrpQueue                    INTEGER,
        hwEntPbxUserGrpQueueTime                Integer32,
        hwEntPbxUserGrpRingMode                 INTEGER,
        hwEntPbxUserGrpSelectmode               INTEGER,
        hwEntPbxUserGrpRingTime                 Integer32,
        hwEntPbxUsrGrpIvrNaviMenuName           DisplayString,
        hwEntPbxUsrGrpDirectTransConsole        INTEGER,
        hwEntPbxUsrGrpMenuName                  DisplayString,
        hwEntPbxUsrGrpMenuOprCode               Integer32,
        hwEntPbxUsrGrpCallerNum                 DisplayString,
        hwEntPbxUsrGrpFromDate                  DisplayString,
        hwEntPbxUsrGrpFromTime                  DisplayString,
        hwEntPbxUsrGrpToDate                    DisplayString,
        hwEntPbxUsrGrpToTime                    DisplayString,
        hwEntPbxUsrGrpRepeatMode                INTEGER,
        hwEntPbxUsrGrpBeginDate                 DisplayString,
        hwEntPbxUsrGrpBeginWeekday              INTEGER,
        hwEntPbxUsrGrpBeginTime                 DisplayString,
        hwEntPbxUsrGrpEndDate                   DisplayString,
        hwEntPbxUsrGrpEndWeekday                INTEGER,
        hwEntPbxUsrGrpEndTime                   DisplayString
     }

   hwEntPbxUsrGrpName OBJECT-TYPE
     SYNTAX      DisplayString(SIZE (1..32))
     MAX-ACCESS  not-accessible
     STATUS      current
     DESCRIPTION
         "
         Indicates the name of the user group.
         "
     ::= { hwEntPbxUsrGrpEntry 1 }

   hwEntPbxUsrGrpRowStatus OBJECT-TYPE
     SYNTAX      RowStatus
     MAX-ACCESS  read-create
     STATUS      current
     DESCRIPTION
         "
         RowStatus
         active(1)
         notInService(2)
         notReady(3)
         createAndGo(4)
         createAndWait(5)
         destroy(6)
         "
     ::= { hwEntPbxUsrGrpEntry 2 }

   hwEntPbxUserGroupServiceId OBJECT-TYPE
     SYNTAX      INTEGER{ivr(1),ringParallel(2),ringSerial(3),unical(4),
                         pickup(5),hunt(6),navi(7)}
     MAX-ACCESS  read-create
     STATUS      current
     DESCRIPTION
         "
         Indicates the type of the user group.
         ivr(1)
         ringParallel(2)
         ringSerial(3)
         unicall(4)
         pickup(5)
         hunt(6)
         navi(7)
         "
     ::= { hwEntPbxUsrGrpEntry 3 }

   hwEntPbxUsrGrpEnterpriseName OBJECT-TYPE
     SYNTAX      DisplayString(SIZE (1..32))
     MAX-ACCESS  read-create
     STATUS      current
     DESCRIPTION
         "
         Indicates the enterprise name of user group.
         "
     ::= { hwEntPbxUsrGrpEntry 4 }

   hwEntPbxUsrGrpDnSet OBJECT-TYPE
     SYNTAX      DisplayString(SIZE (1..32))
     MAX-ACCESS  read-create
     STATUS      current
     DESCRIPTION
         "
         Indicates the dnset name of the user group.
         "
     ::= { hwEntPbxUsrGrpEntry 5 }

   hwEntPbxUserGroupCentrex OBJECT-TYPE
      SYNTAX      DisplayString(SIZE (1..32))
      MAX-ACCESS  read-create
      STATUS      current
      DESCRIPTION
          "
          Indicates the centrex name of user group.

          "
      ::= { hwEntPbxUsrGrpEntry 6 }

   hwEntPbxUsrGrpCountryCode OBJECT-TYPE
     SYNTAX      DisplayString(SIZE (0..4))
     MAX-ACCESS  read-create
     STATUS      current
     DESCRIPTION
         "
         Indicates the country code of the user group.
         "
     ::= { hwEntPbxUsrGrpEntry 7 }

   hwEntPbxUsrGrpAreaCode OBJECT-TYPE
     SYNTAX      DisplayString(SIZE (0..8))
     MAX-ACCESS  read-create
     STATUS      current
     DESCRIPTION
         "
         Indicates the area code of the user group.
         "
     ::= { hwEntPbxUsrGrpEntry 8 }

   hwEntPbxUserGrpAccessCode OBJECT-TYPE
     SYNTAX      DisplayString(SIZE (0..24))
     MAX-ACCESS  read-create
     STATUS      current
     DESCRIPTION
         "
         Indicates the access code of the user group.
         "
     ::= { hwEntPbxUsrGrpEntry 9 }

   hwEntPbxUserGrpRegCode OBJECT-TYPE
     SYNTAX      DisplayString(SIZE (0..24))
     MAX-ACCESS  read-create
     STATUS      current
     DESCRIPTION
         "
         Indicates the register code of the user group,only used in the unicall group.
         "
     ::= { hwEntPbxUsrGrpEntry 10 }

   hwEntPbxUserGrpConsoleCode OBJECT-TYPE
     SYNTAX      DisplayString(SIZE (0..24))
     MAX-ACCESS  read-create
     STATUS      current
     DESCRIPTION
         "
         Indicates the Console code of the ivr user group.
         "
     ::= { hwEntPbxUsrGrpEntry 11 }

   hwEntPbxUsrGrpDstEnterprise OBJECT-TYPE
     SYNTAX      DisplayString(SIZE (0..32))
     MAX-ACCESS  read-create
     STATUS      current
     DESCRIPTION
         "
         Indicates the dest enterprise name of user group.
         "
     ::= { hwEntPbxUsrGrpEntry 12 }

   hwEntPbxUserGrpDstDnset OBJECT-TYPE
     SYNTAX      DisplayString(SIZE (0..32))
     MAX-ACCESS  read-create
     STATUS      current
     DESCRIPTION
         "
         Indicates the dest dnset name of the user group.
         "
     ::= { hwEntPbxUsrGrpEntry 13 }

   hwEntPbxUserGrpDstCentrex OBJECT-TYPE
      SYNTAX      DisplayString(SIZE (0..32))
      MAX-ACCESS  read-create
      STATUS      current
      DESCRIPTION
          "
          Indicates the dest centrex name of user group.

          "
      ::= { hwEntPbxUsrGrpEntry 14 }

   hwEntPbxUserGrpMaxQueueNum OBJECT-TYPE
      SYNTAX      Integer32(0..65535)
      MAX-ACCESS  read-create
            STATUS      current
      DESCRIPTION
          "
          Indicates the max queue number of the user group,only used in ivr group.
          "
      ::= { hwEntPbxUsrGrpEntry 15 }

   hwEntPbxUserGrpToneId OBJECT-TYPE
      SYNTAX      Integer32(0..65535)
      MAX-ACCESS  read-create
      STATUS      current
      DESCRIPTION
          "
          Indicates the interaction tone type of ivr user group.
          "
      ::= { hwEntPbxUsrGrpEntry 16}

   hwEntPbxUsrGrpToneFileName OBJECT-TYPE
     SYNTAX      DisplayString(SIZE (0..64))
     MAX-ACCESS  read-create
     STATUS      current
     DESCRIPTION
         "
         Indicates the tone file name of the ivr user group.
         "
     ::= { hwEntPbxUsrGrpEntry 17 }

   hwEntPbxUserGrpQueue OBJECT-TYPE
     SYNTAX      INTEGER{disable(1),enable(2)}
     MAX-ACCESS  read-create
     STATUS      current
     DESCRIPTION
         "
         Indicates queue function of the ivr user group.
         disable(1)
         enable(2)
         default: disable(1)
         "
     ::= { hwEntPbxUsrGrpEntry 18 }

  hwEntPbxUserGrpQueueTime OBJECT-TYPE
     SYNTAX      Integer32(0..3600)
     MAX-ACCESS  read-create
     STATUS      current
     DESCRIPTION
         "
         Indicates queue time of the user group.
         unit: s
         default: 180
         "
     ::= { hwEntPbxUsrGrpEntry 19 }

   hwEntPbxUserGrpRingMode OBJECT-TYPE
     SYNTAX      INTEGER{ringParallel(1),ringSerial(2), ringOne(3)}
     MAX-ACCESS  read-create
     STATUS      current
     DESCRIPTION
         "
         Indicates ring type of the user group.
         ringParallel(1)
         ringSerial(2)
         ringOne(3)
         default: ringParallel(1)
         "
     ::= { hwEntPbxUsrGrpEntry 20 }

   hwEntPbxUserGrpSelectmode OBJECT-TYPE
     SYNTAX      INTEGER{loop(1),increae(2),decrease(3)}
     MAX-ACCESS  read-create
     STATUS      current
     DESCRIPTION
         "
         Indicates the select mode of the user group.
         loop (1)
         increase(2)
         decrease(3)
         default: loop (1)
         "
     ::= { hwEntPbxUsrGrpEntry 21 }

  hwEntPbxUserGrpRingTime OBJECT-TYPE
     SYNTAX      Integer32(1..255)
     MAX-ACCESS  read-create
     STATUS      current
     DESCRIPTION
         "
         Indicates ring time of the user group.
         unit: s
         default: 10
         "
     ::= { hwEntPbxUsrGrpEntry 22 }

  hwEntPbxUsrGrpIvrNaviMenuName OBJECT-TYPE
     SYNTAX      DisplayString(SIZE (1..32))
     MAX-ACCESS  read-create
     STATUS      current
     DESCRIPTION
         "
         Indicates the name of the user group navigation menu, null means clear the value of this parameter.
         "
     ::= { hwEntPbxUsrGrpEntry 23 }

  hwEntPbxUsrGrpDirectTransConsole OBJECT-TYPE
     SYNTAX      INTEGER{disable(1),enable(2)}
     MAX-ACCESS  read-create
     STATUS      current
     DESCRIPTION
         "
         Indicates direct enter function of the ivr user group.
         disable(1)
         enable(2)
         default: disable(1)
         "
     ::= { hwEntPbxUsrGrpEntry 24 }

   hwEntPbxUsrGrpMenuName OBJECT-TYPE
     SYNTAX      DisplayString(SIZE (1..32))
     MAX-ACCESS  read-create
     STATUS      current
     DESCRIPTION
         "
         Indicates the current menu name of the navigation queue user group.
         "
     ::= { hwEntPbxUsrGrpEntry 25 }

   hwEntPbxUsrGrpMenuOprCode OBJECT-TYPE
     SYNTAX      Integer32(0..120)
     MAX-ACCESS  read-create
     STATUS      current
     DESCRIPTION
         "
         Indicates the operation code of the navigation queue user group.
         0 : Dial 0
         1 : Dial 1
         2 : Dial 2
         3 : Dial 3
         4 : Dial 4
         5 : Dial 5
         6 : Dial 6
         7 : Dial 7
         8 : Dial 8
         9 : Dial 9
         10~109: Reserved
         110: Dial *
         111: Dial #
         112: Dial initial number
         113: Dial number ending with #
         114: Timeout and there is no input
         115: Matching fails
         116: Maximum count of errors
         117: Locating the collected information fails
         118: The action fails
         119: Playing voice ends
         120: The calling party cancels the call
         "
     ::= { hwEntPbxUsrGrpEntry 26 }

   hwEntPbxUsrGrpCallerNum OBJECT-TYPE
     SYNTAX      DisplayString(SIZE (1..44))
     MAX-ACCESS  read-create
     STATUS      current
     DESCRIPTION
         "
         Indicates the CallerNum of ivr usser group.
         "
     ::= { hwEntPbxUsrGrpEntry 27 }

   hwEntPbxUsrGrpFromDate OBJECT-TYPE
     SYNTAX      DisplayString(SIZE (0..10))
     MAX-ACCESS  read-create
     STATUS      current
     DESCRIPTION
         "
         Indicates the BeginDate.
         Format: yyy-mm-dd
         "
     ::= { hwEntPbxUsrGrpEntry 28 }

   hwEntPbxUsrGrpFromTime OBJECT-TYPE
     SYNTAX      DisplayString(SIZE (0..8))
     MAX-ACCESS  read-create
     STATUS      current
     DESCRIPTION
         "
         Indicates the BeginTime.
         Format: hh:mm:ss
         "
     ::= { hwEntPbxUsrGrpEntry 29 }

   hwEntPbxUsrGrpToDate OBJECT-TYPE
     SYNTAX      DisplayString(SIZE (0..10))
     MAX-ACCESS  read-create
     STATUS      current
     DESCRIPTION
         "
         Indicates the EndDate.
         Format: yyy-mm-dd
         "
     ::= { hwEntPbxUsrGrpEntry 30 }

   hwEntPbxUsrGrpToTime OBJECT-TYPE
     SYNTAX      DisplayString(SIZE (0..8))
     MAX-ACCESS  read-create
     STATUS      current
     DESCRIPTION
         "
         Indicates the EndTime.
         Format: hh:mm:ss
         "
     ::= { hwEntPbxUsrGrpEntry 31 }

   hwEntPbxUsrGrpRepeatMode OBJECT-TYPE
     SYNTAX      INTEGER{noRepeat(1),yearly(2),monthly(3),weekly(4),daily(5)}
     MAX-ACCESS  read-create
     STATUS      current
     DESCRIPTION
         "
         Indicates the RepeatMode.
         noRepeat(1)
         yearly(2)
         monthly(3)
         weekly(4)
         daily(5)
         "
     ::= { hwEntPbxUsrGrpEntry 32 }

   hwEntPbxUsrGrpBeginDate OBJECT-TYPE
     SYNTAX      DisplayString(SIZE (0..5))
     MAX-ACCESS  read-create
     STATUS      current
     DESCRIPTION
         "
         Indicates the Repeat BeginDate.
         Format: mm-dd
         "
     ::= { hwEntPbxUsrGrpEntry 33 }

   hwEntPbxUsrGrpBeginWeekday OBJECT-TYPE
     SYNTAX      INTEGER{mon(1),tue(2),wed(3),thu(4),fri(5),sat(6),sun(7),none(8)}
     MAX-ACCESS  read-create
     STATUS      current
     DESCRIPTION
         "
         Indicates the Repeat BeginWeekday.
         mon(1)
         tue(2)
         wed(3)
         thu(4)
         fri(5)
         sat(6)
         sun(7)
         none(8)
         "
     ::= { hwEntPbxUsrGrpEntry 34 }

    hwEntPbxUsrGrpBeginTime OBJECT-TYPE
     SYNTAX      DisplayString(SIZE (0..8))
     MAX-ACCESS  read-create
     STATUS      current
     DESCRIPTION
         "
         Indicates the Repeat BeginTime.
         Format: hh:mm:ss
         "
     ::= { hwEntPbxUsrGrpEntry 35 }

   hwEntPbxUsrGrpEndDate OBJECT-TYPE
     SYNTAX      DisplayString(SIZE (0..5))
     MAX-ACCESS  read-create
     STATUS      current
     DESCRIPTION
         "
         Indicates the Repeat EndDate.
         Format: mm-dd
         "
     ::= { hwEntPbxUsrGrpEntry 36 }

   hwEntPbxUsrGrpEndWeekday OBJECT-TYPE
     SYNTAX      INTEGER{mon(1),tue(2),wed(3),thu(4),fri(5),sat(6),sun(7),none(8)}
     MAX-ACCESS  read-create
     STATUS      current
     DESCRIPTION
         "
         Indicates the Repeat EndWeekday.
         mon(1)
         tue(2)
         wed(3)
         thu(4)
         fri(5)
         sat(6)
         sun(7)
         none(8)
         "
     ::= { hwEntPbxUsrGrpEntry 37 }

   hwEntPbxUsrGrpEndTime OBJECT-TYPE
     SYNTAX      DisplayString(SIZE (0..8))
     MAX-ACCESS  read-create
     STATUS      current
     DESCRIPTION
         "
         Indicates the Repeat EndTime.
         Format: hh:mm:ss
         "
     ::= { hwEntPbxUsrGrpEntry 38 }

  --==============================================================

  hwEntPbxGrpMemTable OBJECT-TYPE
     SYNTAX      SEQUENCE OF HwEntPbxGrpMemEntry
     MAX-ACCESS  not-accessible
     STATUS      current
     DESCRIPTION
       "
       A list of HwEntPbxGrpMemEntry objects.
       "
     ::= { hwEntVoicePbxMIB 20 }

  hwEntPbxGrpMemEntry OBJECT-TYPE
     SYNTAX      HwEntPbxGrpMemEntry
     MAX-ACCESS  not-accessible
     STATUS      current
     DESCRIPTION
       "A list of hwEntPbxGrpMemEntry objects."
     INDEX    {
                     hwEntPbxGrpMemUsrGrpName,
                     hwEntPbxGrpMemPbxuser,
                     hwEntPbxGrpMemUnicallTel,
                     hwEntPbxGrpMemFromDate,
                     hwEntPbxGrpMemFromTime,
                     hwEntPbxGrpMemToDate,
                     hwEntPbxGrpMemToTime,
                     hwEntPbxGrpMemRepeatMode,
                     hwEntPbxGrpMemBeginDate,
                     hwEntPbxGrpMemBeginWeekday,
                     hwEntPbxGrpMemBeginTime,
                     hwEntPbxGrpMemEndDate,
                     hwEntPbxGrpMemEndWeekday,
                     hwEntPbxGrpMemEndTime
              }
     ::= { hwEntPbxGrpMemTable 1 }

  HwEntPbxGrpMemEntry ::=
     SEQUENCE
     {
        hwEntPbxGrpMemUsrGrpName            DisplayString,
        hwEntPbxGrpMemPbxuser               DisplayString,
        hwEntPbxGrpMemUnicallTel            DisplayString,
        hwEntPbxGrpMemFromDate              DisplayString,
        hwEntPbxGrpMemFromTime              DisplayString,
        hwEntPbxGrpMemToDate                DisplayString,
        hwEntPbxGrpMemToTime                DisplayString,
        hwEntPbxGrpMemRepeatMode            INTEGER,
        hwEntPbxGrpMemBeginDate             DisplayString,
        hwEntPbxGrpMemBeginWeekday          INTEGER,
        hwEntPbxGrpMemBeginTime             DisplayString,
        hwEntPbxGrpMemEndDate               DisplayString,
        hwEntPbxGrpMemEndWeekday            INTEGER,
        hwEntPbxGrpMemEndTime               DisplayString,
        hwEntPbxGrpMemRowStatus             RowStatus,
        hwEntPbxGrpMemAdminState            INTEGER,
        hwEntPbxGrpMemIndex                 Integer32
    }

   hwEntPbxGrpMemUsrGrpName OBJECT-TYPE
     SYNTAX      DisplayString(SIZE (1..32))
     MAX-ACCESS  not-accessible
     STATUS      current
     DESCRIPTION
         "
         Indicates the name of the user group.
         "
     ::= { hwEntPbxGrpMemEntry 1 }

   hwEntPbxGrpMemPbxuser OBJECT-TYPE
     SYNTAX      DisplayString(SIZE (0..32))
     MAX-ACCESS  not-accessible
     STATUS      current
     DESCRIPTION
         "
         Indicates the user name of group member.
         "
     ::= { hwEntPbxGrpMemEntry 2 }

   hwEntPbxGrpMemUnicallTel OBJECT-TYPE
     SYNTAX      DisplayString(SIZE (0..44))
     MAX-ACCESS  not-accessible
     STATUS      current
     DESCRIPTION
         "
         Indicates the unicall telephone number.
         "
     ::= { hwEntPbxGrpMemEntry 3 }

   hwEntPbxGrpMemFromDate OBJECT-TYPE
     SYNTAX      DisplayString(SIZE (0..10))
     MAX-ACCESS  not-accessible
     STATUS      current
     DESCRIPTION
         "
         Indicates the BeginData of user.
         Format:yyyy-mm-dd
         "
     ::= { hwEntPbxGrpMemEntry 4 }

   hwEntPbxGrpMemFromTime OBJECT-TYPE
     SYNTAX      DisplayString(SIZE (0..8))
     MAX-ACCESS  not-accessible
     STATUS      current
     DESCRIPTION
         "
         Indicates the BeginTime of user.
         "
     ::= { hwEntPbxGrpMemEntry 5 }

   hwEntPbxGrpMemToDate OBJECT-TYPE
     SYNTAX      DisplayString(SIZE (0..10))
     MAX-ACCESS  not-accessible
     STATUS      current
     DESCRIPTION
         "
         Indicates the EndData of user.
         "
     ::= { hwEntPbxGrpMemEntry 6 }

   hwEntPbxGrpMemToTime OBJECT-TYPE
     SYNTAX      DisplayString(SIZE (0..8))
     MAX-ACCESS  not-accessible
     STATUS      current
     DESCRIPTION
         "
         Indicates the EndTime of user.
         "
     ::= { hwEntPbxGrpMemEntry 7 }

   hwEntPbxGrpMemRepeatMode OBJECT-TYPE
     SYNTAX      INTEGER{noRepeat(1),yearly(2),monthly(3),weekly(4),daily(5)}
     MAX-ACCESS  not-accessible
     STATUS      current
     DESCRIPTION
         "
         Indicates the RepeatMode of user.
         noRepeat(1)
         yearly(2)
         monthly(3)
         weekly(4)
         daily(5)
         "
     ::= { hwEntPbxGrpMemEntry 8 }

   hwEntPbxGrpMemBeginDate OBJECT-TYPE
     SYNTAX      DisplayString(SIZE (0..5))
     MAX-ACCESS  not-accessible
     STATUS      current
     DESCRIPTION
         "
         Indicates the Repeat BeginData of user.
         "
     ::= { hwEntPbxGrpMemEntry 9 }

   hwEntPbxGrpMemBeginWeekday OBJECT-TYPE
     SYNTAX      INTEGER{mon(1),tue(2),wed(3),thu(4),fri(5),sat(6),sun(7),none(8)}
     MAX-ACCESS  not-accessible
     STATUS      current
     DESCRIPTION
         "
         Indicates the Repeat BeginWeekday.
         mon(1)
         tue(2)
         wed(3)
         thu(4)
         fri(5)
         sat(6)
         sun(7)
         none(8)
         "
     ::= { hwEntPbxGrpMemEntry 10 }

   hwEntPbxGrpMemBeginTime OBJECT-TYPE
     SYNTAX      DisplayString(SIZE (0..8))
     MAX-ACCESS  not-accessible
     STATUS      current
     DESCRIPTION
         "
         Indicates the Repeat BeginTime of user.
         "
     ::= { hwEntPbxGrpMemEntry 11 }

   hwEntPbxGrpMemEndDate OBJECT-TYPE
     SYNTAX      DisplayString(SIZE (0..5))
     MAX-ACCESS  not-accessible
     STATUS      current
     DESCRIPTION
         "
         Indicates the Repeat EndDate of user.
         "
     ::= { hwEntPbxGrpMemEntry 12 }

   hwEntPbxGrpMemEndWeekday OBJECT-TYPE
     SYNTAX      INTEGER{mon(1),tue(2),wed(3),thu(4),fri(5),sat(6),sun(7),none(8)}
     MAX-ACCESS  not-accessible
     STATUS      current
     DESCRIPTION
         "
         Indicates the Repeat EndWeekday.
         mon(1)
         tue(2)
         wed(3)
         thu(4)
         fri(5)
         sat(6)
         sun(7)
         none(8)
         "
     ::= { hwEntPbxGrpMemEntry 13 }

   hwEntPbxGrpMemEndTime OBJECT-TYPE
     SYNTAX      DisplayString(SIZE (0..8))
     MAX-ACCESS  not-accessible
     STATUS      current
     DESCRIPTION
         "
         Indicates the Repeat EndTime of user.
         "
     ::= { hwEntPbxGrpMemEntry 14 }

   hwEntPbxGrpMemRowStatus OBJECT-TYPE
     SYNTAX      RowStatus
     MAX-ACCESS  read-create
     STATUS      current
     DESCRIPTION
         "
         Indicates row status of table.
         "
     ::= { hwEntPbxGrpMemEntry 15 }

   hwEntPbxGrpMemAdminState OBJECT-TYPE
     SYNTAX      INTEGER{offline(1),online(2)}
     MAX-ACCESS  read-create
     STATUS      current
     DESCRIPTION
         "
         Indicates Service state of user.
         offline(1)
         online(2)
         "
     ::= { hwEntPbxGrpMemEntry 16 }

   hwEntPbxGrpMemIndex OBJECT-TYPE
     SYNTAX      Integer32(0..65535)
     MAX-ACCESS  read-create
     STATUS      current
     DESCRIPTION
         "
         Indicates the group member index.
         "
     ::= { hwEntPbxGrpMemEntry 17 }

  --==============================================================

   hwEntPbxSrvPswTable OBJECT-TYPE
     SYNTAX      SEQUENCE OF HwEntPbxSrvPswEntry
     MAX-ACCESS  not-accessible
     STATUS      current
     DESCRIPTION
       "
       A list of hwEntPbxSrvPswEntry objects.
       "
     ::= { hwEntVoicePbxMIB 21 }

   hwEntPbxSrvPswEntry OBJECT-TYPE
     SYNTAX      HwEntPbxSrvPswEntry
     MAX-ACCESS  not-accessible
     STATUS      current
     DESCRIPTION
       "A list of hwEntPbxSrvPswEntry objects."
     INDEX    {
               hwEntPbxSrvPswUserName,
               hwEntPbxSrvPswServiceType
              }
     ::= { hwEntPbxSrvPswTable 1 }

   HwEntPbxSrvPswEntry ::=
     SEQUENCE
     {
        hwEntPbxSrvPswUserName            DisplayString,
        hwEntPbxSrvPswServiceType         INTEGER,
        hwEntPbxSrvPswPasswordType        INTEGER,
        hwEntPbxSrvPswServicePassword     DisplayString
     }

   hwEntPbxSrvPswUserName OBJECT-TYPE
     SYNTAX      DisplayString(SIZE (1..32))
     MAX-ACCESS  not-accessible
     STATUS      current
     DESCRIPTION
         "
         Indicates the username of the user.
         "
     ::= { hwEntPbxSrvPswEntry 1 }

   hwEntPbxSrvPswServiceType OBJECT-TYPE
     SYNTAX      INTEGER{scccancel(1),cfx(2),dlc(3),pwcb(4),cba(5)}
     MAX-ACCESS  not-accessible
     STATUS      current
     DESCRIPTION
         "
         Indicates the service type of password-service.
         cccancel(1)
         cfx(2)
         dlc(3)
         pwcb(4)
         cba(5)
         "
     ::= { hwEntPbxSrvPswEntry 2 }

   hwEntPbxSrvPswPasswordType OBJECT-TYPE
     SYNTAX      INTEGER{simple(1),cipher(2)}
     MAX-ACCESS  read-create
     STATUS      current
     DESCRIPTION
         "
         Indicates the display type of password.
         simple(1)
         cipher(2)
         "
     ::= { hwEntPbxSrvPswEntry 3 }

   hwEntPbxSrvPswServicePassword OBJECT-TYPE
     SYNTAX      DisplayString(SIZE(0..8))
     MAX-ACCESS  read-create
     STATUS      current
     DESCRIPTION
         "
         Indicates the service password.
         "
     ::= { hwEntPbxSrvPswEntry 4 }

  --==============================================================

   hwEntPbxSrvDlcTable OBJECT-TYPE
     SYNTAX      SEQUENCE OF HwEntPbxSrvDlcEntry
     MAX-ACCESS  not-accessible
     STATUS      current
     DESCRIPTION
       "
       A list of hwEntPbxSrvDlcEntry objects.
       "
     ::= { hwEntVoicePbxMIB 22 }

   hwEntPbxSrvDlcEntry OBJECT-TYPE
     SYNTAX      HwEntPbxSrvDlcEntry
     MAX-ACCESS  not-accessible
     STATUS      current
     DESCRIPTION
       " A list of hwEntPbxSrvDlcEntry objects."
     INDEX    {
               hwEntPbxSrvDlcUserName,
               hwEntPbxSrvDlcNum
               }
     ::= { hwEntPbxSrvDlcTable 1 }

  HwEntPbxSrvDlcEntry ::=
     SEQUENCE
     {
         hwEntPbxSrvDlcUserName            DisplayString,
         hwEntPbxSrvDlcNum                 DisplayString,
         hwEntPbxSrvDlcRowStatus           RowStatus,
         hwEntPbxSrvDlcReserved            Integer32
     }

   hwEntPbxSrvDlcUserName OBJECT-TYPE
     SYNTAX      DisplayString(SIZE (1..32))
     MAX-ACCESS  not-accessible
     STATUS      current
     DESCRIPTION
         "
         Indicates the username of the user.
         "
     ::= { hwEntPbxSrvDlcEntry 1 }


   hwEntPbxSrvDlcNum OBJECT-TYPE
     SYNTAX      DisplayString(SIZE (1..44))
     MAX-ACCESS  not-accessible
     STATUS      current
     DESCRIPTION
         "
         Indicates the Limit CalledNum of register number.
         "
     ::= { hwEntPbxSrvDlcEntry 2 }

   hwEntPbxSrvDlcRowStatus OBJECT-TYPE
     SYNTAX      RowStatus
     MAX-ACCESS  read-create
     STATUS      current
     DESCRIPTION
         "
         Indicates row status of table.
         active(1)
         notInService(2)
         notReady(3)
         createAndGo(4)
         createAndWait(5)
         destroy(6)
         "
     ::= { hwEntPbxSrvDlcEntry 3 }


    hwEntPbxSrvDlcReserved OBJECT-TYPE
     SYNTAX      Integer32
     MAX-ACCESS  read-create
     STATUS      current
     DESCRIPTION
         "
         Reserved
         "
     ::= { hwEntPbxSrvDlcEntry 4 }

  --==============================================================

hwEntPbxCrbtFileTable OBJECT-TYPE
     SYNTAX      SEQUENCE OF HwEntPbxCrbtFileEntry
     MAX-ACCESS  not-accessible
     STATUS      current
     DESCRIPTION
       "
       A list of hwEntPbxCrbtFileEntry objects.
       "
     ::= { hwEntVoicePbxMIB 23 }

   hwEntPbxCrbtFileEntry OBJECT-TYPE
     SYNTAX      HwEntPbxCrbtFileEntry
     MAX-ACCESS  not-accessible
     STATUS      current
     DESCRIPTION
       "A list of hwEntPbxCrbtFileEntry objects."
     INDEX    {
                  hwEntPbxCrbtFileName
              }
     ::= { hwEntPbxCrbtFileTable 1 }

   HwEntPbxCrbtFileEntry ::=
     SEQUENCE
     {
        hwEntPbxCrbtFileName                DisplayString,
        hwEntPbxCrbtFileRowStatus           RowStatus,
        hwEntPbxCrbtFileDesc                DisplayString,
        hwEntPbxCrbtType                    INTEGER,
        hwEntPbxCrbtFileCheckStatus         INTEGER,
        hwEntPbxCrbtFileStorage             INTEGER,
        hwEntPbxCrbtFileEnterpriseName      DisplayString,
        hwEntPbxCrbtFileUserName            DisplayString
     }

   hwEntPbxCrbtFileName OBJECT-TYPE
     SYNTAX      DisplayString(SIZE (1..64))
     MAX-ACCESS  not-accessible
     STATUS      current
     DESCRIPTION
         "
         Indicates the full path and filename of crbt file.
         "
      ::= { hwEntPbxCrbtFileEntry 1 }

   hwEntPbxCrbtFileRowStatus OBJECT-TYPE
     SYNTAX      RowStatus
     MAX-ACCESS  read-create
     STATUS      current
     DESCRIPTION
         "
         Indicates row status of table.
         "
     ::= { hwEntPbxCrbtFileEntry 2 }

   hwEntPbxCrbtFileDesc OBJECT-TYPE
     SYNTAX      DisplayString(SIZE (0..64))
     MAX-ACCESS  read-create
     STATUS      current
     DESCRIPTION
         "
         Indicates the description of crbt file.
         "
     ::= { hwEntPbxCrbtFileEntry 3 }

   hwEntPbxCrbtType OBJECT-TYPE
     SYNTAX      INTEGER{enterpriserCrbt(1),personalCrbt(2)}
     MAX-ACCESS  read-create
     STATUS      current
     DESCRIPTION
         "
         Indicates the type of crbt file.
         enterpriserCrbt(1)
         personalCrbt(2
         "
     ::= { hwEntPbxCrbtFileEntry 4 }

   hwEntPbxCrbtFileCheckStatus OBJECT-TYPE
     SYNTAX      INTEGER{noCheck(1),pass(2),noPass(3)}
     MAX-ACCESS  read-create
     STATUS      current
     DESCRIPTION
         "
         Indicates the check state of crbt file.
         noCheck(1)
         pass(2)
         noPass(3)
         "
     ::= { hwEntPbxCrbtFileEntry 5 }

   hwEntPbxCrbtFileStorage OBJECT-TYPE
     SYNTAX      INTEGER{local(1), mrs(2)}
     MAX-ACCESS  read-create
     STATUS      current
     DESCRIPTION
         "
         Indicates the storage location of crbt file.
         local(1)
         mrs(2)
         default:local(1)
         "
     ::= { hwEntPbxCrbtFileEntry 6 }

   hwEntPbxCrbtFileEnterpriseName OBJECT-TYPE
     SYNTAX      DisplayString(SIZE (0..32))
     MAX-ACCESS  read-create
     STATUS      current
     DESCRIPTION
         "
         Indicates the enterprise of crbt file.
         "
     ::= { hwEntPbxCrbtFileEntry 7 }

   hwEntPbxCrbtFileUserName OBJECT-TYPE
     SYNTAX      DisplayString(SIZE (0..32))
     MAX-ACCESS  read-create
     STATUS      current
     DESCRIPTION
         "
         Indicates the username of crbt file.
         "
     ::= { hwEntPbxCrbtFileEntry 8 }

  --==============================================================

   hwEntPbxSrvCrbtTable OBJECT-TYPE
     SYNTAX      SEQUENCE OF HwEntPbxSrvCrbtEntry
     MAX-ACCESS  not-accessible
     STATUS      current
     DESCRIPTION
       "
       A list of hwEntPbxSrvCrbtEntry objects.
       "
     ::= { hwEntVoicePbxMIB 24 }

   hwEntPbxSrvCrbtEntry OBJECT-TYPE
     SYNTAX      HwEntPbxSrvCrbtEntry
     MAX-ACCESS  not-accessible
     STATUS      current
     DESCRIPTION
       "A list of hwEntPbxSrvCrbtEntry objects."
     INDEX    {
                 hwEntPbxSrvCrbtEnterpriseName,
                 hwEntPbxSrvCrbtUserName,
                 hwEntPbxSrvCrbtTrkGrpName,
                 hwEntPbxSrvCrbtCallerNum,
                 hwEntPbxSrvCrbtFromDate,
                 hwEntPbxSrvCrbtFromTime,
                 hwEntPbxSrvCrbtToDate,
                 hwEntPbxSrvCrbtToTime,
                 hwEntPbxSrvCrbtRepeatMode,
                 hwEntPbxSrvCrbtBeginDate,
                 hwEntPbxSrvCrbtBeginWeekday,
                 hwEntPbxSrvCrbtBeginTime,
                 hwEntPbxSrvCrbtEndDate,
                 hwEntPbxSrvCrbtEndWeekday,
                 hwEntPbxSrvCrbtEndTime
              }
     ::= { hwEntPbxSrvCrbtTable 1 }

   HwEntPbxSrvCrbtEntry ::=
     SEQUENCE
     {
        hwEntPbxSrvCrbtEnterpriseName       DisplayString,
        hwEntPbxSrvCrbtUserName             DisplayString,
        hwEntPbxSrvCrbtTrkGrpName           DisplayString,
        hwEntPbxSrvCrbtCallerNum            DisplayString,
        hwEntPbxSrvCrbtFromDate             DisplayString,
        hwEntPbxSrvCrbtFromTime             DisplayString,
        hwEntPbxSrvCrbtToDate               DisplayString,
        hwEntPbxSrvCrbtToTime               DisplayString,
        hwEntPbxSrvCrbtRepeatMode           INTEGER,
        hwEntPbxSrvCrbtBeginDate            DisplayString,
        hwEntPbxSrvCrbtBeginWeekday         INTEGER,
        hwEntPbxSrvCrbtBeginTime            DisplayString,
        hwEntPbxSrvCrbtEndDate              DisplayString,
        hwEntPbxSrvCrbtEndWeekday           INTEGER,
        hwEntPbxSrvCrbtEndTime              DisplayString,
        hwEntPbxSrvCrbtRowStatus            RowStatus,
        hwEntPbxSrvCrbtFileName             DisplayString
    }

   hwEntPbxSrvCrbtEnterpriseName OBJECT-TYPE
     SYNTAX      DisplayString(SIZE (0..32))
     MAX-ACCESS  not-accessible
     STATUS      current
     DESCRIPTION
         "
         Indicates the enterprise name.
         "
    ::= { hwEntPbxSrvCrbtEntry 1 }

   hwEntPbxSrvCrbtUserName OBJECT-TYPE
     SYNTAX      DisplayString(SIZE (0..32))
     MAX-ACCESS  not-accessible
     STATUS      current
     DESCRIPTION
         "
         Indicates the user name.
         "
     ::= { hwEntPbxSrvCrbtEntry 2 }

   hwEntPbxSrvCrbtTrkGrpName OBJECT-TYPE
     SYNTAX      DisplayString(SIZE(0..32))
     MAX-ACCESS  not-accessible
     STATUS      current
     DESCRIPTION
         "
         Indicates the trunk group name of caller.
         "
     ::= { hwEntPbxSrvCrbtEntry 3 }

   hwEntPbxSrvCrbtCallerNum OBJECT-TYPE
     SYNTAX      DisplayString(SIZE (0..44))
     MAX-ACCESS  not-accessible
     STATUS      current
     DESCRIPTION
         "
         Indicates the caller number.
         "
     ::= { hwEntPbxSrvCrbtEntry 4 }

   hwEntPbxSrvCrbtFromDate OBJECT-TYPE
     SYNTAX      DisplayString(SIZE (0..10))
     MAX-ACCESS  not-accessible
     STATUS      current
     DESCRIPTION
         "
         Indicates the BeginDate.
         Format:yyyy-mm-dd
         "
     ::= { hwEntPbxSrvCrbtEntry 5 }

   hwEntPbxSrvCrbtFromTime OBJECT-TYPE
     SYNTAX      DisplayString(SIZE (0..8))
     MAX-ACCESS  not-accessible
     STATUS      current
     DESCRIPTION
         "
         Indicates the BeginTime.
         "
     ::= { hwEntPbxSrvCrbtEntry 6 }

   hwEntPbxSrvCrbtToDate OBJECT-TYPE
     SYNTAX      DisplayString(SIZE (0..10))
     MAX-ACCESS  not-accessible
     STATUS      current
     DESCRIPTION
         "
         Indicates the EndDate.
         "
     ::= { hwEntPbxSrvCrbtEntry 7 }

   hwEntPbxSrvCrbtToTime OBJECT-TYPE
     SYNTAX      DisplayString(SIZE (0..8))
     MAX-ACCESS  not-accessible
     STATUS      current
     DESCRIPTION
         "
         Indicates the EndTime.
         "
     ::= { hwEntPbxSrvCrbtEntry 8 }

   hwEntPbxSrvCrbtRepeatMode OBJECT-TYPE
     SYNTAX      INTEGER{noRepeat(1),yearly(2),monthly(3),weekly(4),daily(5)}
     MAX-ACCESS  not-accessible
     STATUS      current
     DESCRIPTION
         "
         Indicates the RepeatMode.
         noRepeat(1)
         yearly(2)
         monthly(3)
         weekly(4)
         daily(5)
         "
     ::= { hwEntPbxSrvCrbtEntry 9 }

   hwEntPbxSrvCrbtBeginDate OBJECT-TYPE
     SYNTAX      DisplayString(SIZE (0..5))
     MAX-ACCESS  not-accessible
     STATUS      current
     DESCRIPTION
         "
         Indicates the Repeat BeginDate.
         Format:mm-dd
         "
     ::= { hwEntPbxSrvCrbtEntry 10 }

   hwEntPbxSrvCrbtBeginWeekday OBJECT-TYPE
     SYNTAX      INTEGER{mon(1),tue(2),wed(3),thu(4),fri(5),sat(6),sun(7),none(8)}
     MAX-ACCESS  not-accessible
     STATUS      current
     DESCRIPTION
         "
         Indicates the Repeat BeginWeekday.
         mon(1)
         tue(2)
         wed(3)
         thu(4)
         fri(5)
         sat(6)
         sun(7)
         none(8)
         "
     ::= { hwEntPbxSrvCrbtEntry 11 }

   hwEntPbxSrvCrbtBeginTime OBJECT-TYPE
     SYNTAX      DisplayString(SIZE (0..8))
     MAX-ACCESS  not-accessible
     STATUS      current
     DESCRIPTION
         "
         Indicates the Repeat BeginTime.
         Format: hh:mm:ss
         "
     ::= { hwEntPbxSrvCrbtEntry 12 }

   hwEntPbxSrvCrbtEndDate OBJECT-TYPE
     SYNTAX      DisplayString(SIZE (0..5))
     MAX-ACCESS  not-accessible
     STATUS      current
     DESCRIPTION
         "
         Indicates the Repeat EndDate.
         Format:mm-dd
         "
     ::= { hwEntPbxSrvCrbtEntry 13 }

   hwEntPbxSrvCrbtEndWeekday OBJECT-TYPE
     SYNTAX      INTEGER{mon(1),tue(2),wed(3),thu(4),fri(5),sat(6),sun(7),none(8)}
     MAX-ACCESS  not-accessible
     STATUS      current
     DESCRIPTION
         "
         Indicates the Repeat EndWeekday.
         mon(1)
         tue(2)
         wed(3)
         thu(4)
         fri(5)
         sat(6)
         sun(7)
         none(8)
         "
     ::= { hwEntPbxSrvCrbtEntry 14 }

   hwEntPbxSrvCrbtEndTime OBJECT-TYPE
     SYNTAX      DisplayString(SIZE (0..8))
     MAX-ACCESS  not-accessible
     STATUS      current
     DESCRIPTION
         "
         Indicates the Repeat EndTime.
         "
     ::= { hwEntPbxSrvCrbtEntry 15 }

   hwEntPbxSrvCrbtRowStatus OBJECT-TYPE
     SYNTAX      RowStatus
     MAX-ACCESS  read-create
     STATUS      current
     DESCRIPTION
         "
            Indicates row status of table.
         "
     ::= { hwEntPbxSrvCrbtEntry 16 }

   hwEntPbxSrvCrbtFileName OBJECT-TYPE
     SYNTAX      DisplayString(SIZE (1..64))
     MAX-ACCESS  read-create
     STATUS      current
     DESCRIPTION
         "
         Indicates the full file name.
         "
     ::= { hwEntPbxSrvCrbtEntry 17 }

  --==============================================================

   hwEntPbxUserParaTable OBJECT-TYPE
     SYNTAX      SEQUENCE OF HwEntPbxUserParaEntry
     MAX-ACCESS  not-accessible
     STATUS      current
     DESCRIPTION
       "
       A list of hwEntPbxUserParaTable objects.
       "
     ::= { hwEntVoicePbxMIB 27 }

   hwEntPbxUserParaEntry OBJECT-TYPE
     SYNTAX      HwEntPbxUserParaEntry
     MAX-ACCESS  not-accessible
     STATUS      current
     DESCRIPTION
       "A list of hwEntPbxUserParaTable objects."
     INDEX    {
                 hwEntPbxUserParaName                 
              }
     ::= { hwEntPbxUserParaTable 1 }

   HwEntPbxUserParaEntry ::=
     SEQUENCE
     {
        hwEntPbxUserParaName                    DisplayString,
        hwEntPbxUserPriority                    INTEGER,
        hwEntPbxUserLineType                    INTEGER,
        hwEntPbxUserClipTransmissionSequence    INTEGER,
        hwEntPbxUserClipFormat                  INTEGER,
        hwEntPbxUserDcTime                      Integer32,
        hwEntPbxUserFskTime                     Integer32,
        hwEntPbxUserVqeAgc                      INTEGER,
        hwEntPbxUserVqeAgcLevel                 Integer32,
        hwEntPbxUserVqeSns                      INTEGER,
        hwEntPbxUserVqeSnsLevel                 Integer32,
        hwEntPbxUserDspInputGain                Integer32,
        hwEntPbxUserDspOutputGain               Integer32,
        hwEntPbxUserDetectAnsbarBySingleTone    INTEGER,
        hwEntPbxUserBellAnsFlag                 INTEGER,
        hwEntPbxUserFskMode                     INTEGER,
        hwEntPbxUserTasPattern                  INTEGER,
        hwEntPbxUserSignallingType              INTEGER,
        hwEntPbxUserDesc                        DisplayString,
        hwEntPbxUserAdminStatus                 INTEGER,
        hwEntPbxUserCTPSrvState                 INTEGER,
        hwEntPbxUserCTPAdmState                 INTEGER
    }

   hwEntPbxUserParaName OBJECT-TYPE
     SYNTAX      DisplayString(SIZE (1..32))
     MAX-ACCESS  not-accessible
     STATUS      current
     DESCRIPTION
         "
         Indicates the pbxuser name.
         "
    ::= { hwEntPbxUserParaEntry 1 }

   hwEntPbxUserPriority OBJECT-TYPE
     SYNTAX      INTEGER{cat1(1),cat2(2),cat3(3)}
     MAX-ACCESS  read-write
     STATUS      current
     DESCRIPTION
         "
         Indicates the pbxuser's  priority.
         "
    ::= { hwEntPbxUserParaEntry 2 }

   hwEntPbxUserLineType OBJECT-TYPE
     SYNTAX      INTEGER{del(1),lcpbx(2),ecpbx(3),payphone(4)}
     MAX-ACCESS  read-write
     STATUS      current
     DESCRIPTION
         "
         Indicates the pbxuser's  line type.
         default: del(1)
         "
    ::= { hwEntPbxUserParaEntry 3 }
    
   hwEntPbxUserClipTransmissionSequence OBJECT-TYPE
     SYNTAX      INTEGER{afterRing(1),beforeRing(2)}
     MAX-ACCESS  read-write
     STATUS      current
     DESCRIPTION
         "
         Indicates the pbxuser's  clip transmission sequence.
         default: afterRing(1)
         "
    ::= { hwEntPbxUserParaEntry 4 }
    
   hwEntPbxUserClipFormat OBJECT-TYPE
     SYNTAX      INTEGER{sdmffsk(1),mdmffsk(2),dtmf(3),r1-5(4),etsi(5)}
     MAX-ACCESS  read-write
     STATUS      current
     DESCRIPTION
         "
         Indicates the pbxuser's  clip format.
         default: sdmffsk(1)
         "
    ::= { hwEntPbxUserParaEntry 5 }
    
   hwEntPbxUserDcTime OBJECT-TYPE
     SYNTAX      Integer32(10..100)
     MAX-ACCESS  read-write
     STATUS      current
     DESCRIPTION
         "
         Indicates the pbxuser's  dc time.
         default: 10
         unit:10ms
         "
    ::= { hwEntPbxUserParaEntry 6 }

   hwEntPbxUserFskTime OBJECT-TYPE
     SYNTAX      Integer32(0..100)
     MAX-ACCESS  read-write
     STATUS      current
     DESCRIPTION
         "
         Indicates the pbxuser's  fks time.
         default: 80
         unit:10ms
         "
    ::= { hwEntPbxUserParaEntry 7 }

   hwEntPbxUserVqeAgc OBJECT-TYPE
     SYNTAX      INTEGER{enable(1),disable(2)}
     MAX-ACCESS  read-write
     STATUS      current
     DESCRIPTION
         "
         Indicates the pbxuser's  vqe agc flag.
         default: disable(2)
         "
    ::= { hwEntPbxUserParaEntry 8 }

   hwEntPbxUserVqeAgcLevel OBJECT-TYPE
     SYNTAX      Integer32(0..15)
     MAX-ACCESS  read-write
     STATUS      current
     DESCRIPTION
         "
         Indicates the pbxuser vqe agc level. Correspond to -9~-24dbm0
         default: 13
         "
    ::= { hwEntPbxUserParaEntry 9 }

   hwEntPbxUserVqeSns OBJECT-TYPE
     SYNTAX      INTEGER{enable(1),disable(2)}
     MAX-ACCESS  read-write
     STATUS      current
     DESCRIPTION
         "
         Indicates the pbxuser's  vqe sns flag.
         default: disable(2)
         "
    ::= { hwEntPbxUserParaEntry 10 }

   hwEntPbxUserVqeSnsLevel OBJECT-TYPE
     SYNTAX      Integer32(6..20)
     MAX-ACCESS  read-write
     STATUS      current
     DESCRIPTION
         "
         Indicates the pbxuser's  vqe sns level.
         default: 12
         unit: dB
         "
    ::= { hwEntPbxUserParaEntry 11 }

   hwEntPbxUserDspInputGain OBJECT-TYPE
     SYNTAX      Integer32(0..15)
     MAX-ACCESS  read-write
     STATUS      current
     DESCRIPTION
         "
         Indicates the pbxuser's  dsp input gain.Correspond to -10~5dB
         default: 10
         "
    ::= { hwEntPbxUserParaEntry 12 }
    
   hwEntPbxUserDspOutputGain OBJECT-TYPE
     SYNTAX      Integer32(0..20)
     MAX-ACCESS  read-write
     STATUS      current
     DESCRIPTION
         "
         Indicates the pbxuser's  dsp output gain.Correspond to -10~10dB
         default: 10
         "
    ::= { hwEntPbxUserParaEntry 13 }
    
   hwEntPbxUserDetectAnsbarBySingleTone OBJECT-TYPE
     SYNTAX      INTEGER{enable(1),disable(2)}
     MAX-ACCESS  read-write
     STATUS      current
     DESCRIPTION
         "
         Indicates the pbxuser's  ans bar by single tone.
         default: disable(2)
         "
    ::= { hwEntPbxUserParaEntry 14 }
    
   hwEntPbxUserBellAnsFlag  OBJECT-TYPE
     SYNTAX      INTEGER{enable(1),disable(2)}
     MAX-ACCESS  read-write
     STATUS      current
     DESCRIPTION
         "
         Indicates the pbxuser's  bell ans flag.
         default: disable(2)
         "
    ::= { hwEntPbxUserParaEntry 15 }
    
   hwEntPbxUserFskMode   OBJECT-TYPE
     SYNTAX      INTEGER{bell202(1),ccittV23(2),ntt(3)}
     MAX-ACCESS  read-write
     STATUS      current
     DESCRIPTION
         "
         Indicates the pbxuser's fsk mode.
         default: bell202(1)
         "
    ::= { hwEntPbxUserParaEntry 16 }
    
   hwEntPbxUserTasPattern    OBJECT-TYPE
     SYNTAX      INTEGER{noTas(1),dtAs(2)}
     MAX-ACCESS  read-write
     STATUS      current
     DESCRIPTION
         "
         Indicates the pbxuser's tas pattern.
         default: noTas(1)
         "
    ::= { hwEntPbxUserParaEntry 17 }
    
   hwEntPbxUserSignallingType    OBJECT-TYPE
     SYNTAX      INTEGER{dss1(1),qsig(2)}
     MAX-ACCESS  read-write
     STATUS      current
     DESCRIPTION
         "
         Indicates the pbxuser's signalling type.
         "
    ::= { hwEntPbxUserParaEntry 18 }
    
   hwEntPbxUserDesc    OBJECT-TYPE
     SYNTAX      DisplayString(SIZE(0..64))
     MAX-ACCESS  read-write
     STATUS      current
     DESCRIPTION
         "
         Indicates the pbxuser's description.
         "
    ::= { hwEntPbxUserParaEntry 19 }
    
   hwEntPbxUserAdminStatus    OBJECT-TYPE
     SYNTAX      INTEGER{endService(1), startService(2)}
     MAX-ACCESS  read-write
     STATUS      current
     DESCRIPTION
         "
         Indicates the pbxuser's admin status.
         "
    ::= { hwEntPbxUserParaEntry 20 }
    
    hwEntPbxUserCTPSrvState    OBJECT-TYPE
     SYNTAX      INTEGER{idle(1),busy(2),fault(3),reserved(4),
                         onhook(5),offhook(6),locked(7),ringing(8)}
     MAX-ACCESS  read-only
     STATUS      current
     DESCRIPTION
         "
         Indicates the pbxuser's CTP service state.
         "
    ::= { hwEntPbxUserParaEntry 21 }
    
    hwEntPbxUserCTPAdmState    OBJECT-TYPE
     SYNTAX      INTEGER{lBlock(1),rBlock(2),startSrv(3),graceful(4),vsqmTest(5)}
     MAX-ACCESS  read-only
     STATUS      current
     DESCRIPTION
         "
         Indicates the pbxuser's CTP admin state.
         "
    ::= { hwEntPbxUserParaEntry 22 }
    
   --==============================================================   
 
   hwEntPbxStaticConflictTable OBJECT-TYPE
     SYNTAX      SEQUENCE OF HwEntPbxStaticConflictEntry
     MAX-ACCESS  not-accessible
     STATUS      current
     DESCRIPTION
       "
       A list of hwEntPbxStaticConflictTable objects.
       "
     ::= { hwEntVoicePbxMIB 28 }

   hwEntPbxStaticConflictEntry OBJECT-TYPE
     SYNTAX      HwEntPbxStaticConflictEntry
     MAX-ACCESS  not-accessible
     STATUS      current
     DESCRIPTION
       "A list of hwEntPbxStaticConflictTable objects."
     INDEX    {
                 hwEntPbxStaticConflictSrvIndex                 
              }
     ::= { hwEntPbxStaticConflictTable 1 }
     
   HwEntPbxStaticConflictEntry ::=
     SEQUENCE
     {
        hwEntPbxStaticConflictSrvIndex             Integer32,
        hwEntPbxStaticConflictNewService           BITS  
     }
     
   hwEntPbxStaticConflictSrvIndex    OBJECT-TYPE
     SYNTAX      Integer32(0..255)
     MAX-ACCESS  not-accessible
     STATUS      current
     DESCRIPTION
         "
         Indicates the service index.
         1: CLIP
         2: CLIR
         3: CFU
         4: CFB
         5: CFNR
         6: CFS
         7: CFO
         8: CW
         9: NONE
         10: CALLTRANSFER
         11: CALLHOLD
         12: THREEPARTY
         13: CONF
         14: CALLINSERT
         15: NONE
         16: QUERYDN
         17: DDS
         18: ABBDIAL
         19: WAKECALL
         20: ROMA
         21: PICKUPINGROUP
         22: PICKUPSPECIAL
         23: RINGSERVICE
         24: SCA
         25: RCS
         26: RAC
         27: OVERSTEPCLIR
         28: ICS
         29: REMOTEOFFICE
         30: SCCCANCEL
         31: SCR
         32: PARK
         33: DLC
         34: PWCB
         35: CBA
         36: CRBT
         37: CR
         38: OCM
         39: ICM
         40: CCBS
         41: CCNR
         "
    ::= { hwEntPbxStaticConflictEntry 1 }  
    
   hwEntPbxStaticConflictNewService    OBJECT-TYPE
     SYNTAX      BITS{bit0(0),bit1(1),bit2(2),bit3(3),bit4(4),bit5(5),
                      bit6(6),bit7(7),bit8(8),bit9(9),bit10(10),
                      bit11(11),bit12(12),bit13(13),bit14(14),bit15(15),
                      bit16(16),bit17(17),bit18(18),bit19(19),bit20(20),
                      bit21(21),bit22(22),bit23(23),bit24(24),bit25(25),
                      bit26(26),bit27(27),bit28(28),bit29(29),bit30(30),
                      bit31(31),bit32(32),bit33(33),bit34(34),bit35(35),
                      bit36(36),bit37(37),bit38(38),bit39(39),bit40(40),
                      bit41(41),bit42(42),bit43(43),bit44(44),bit45(45),
                      bit46(46),bit47(47),bit48(48),bit49(49),bit50(50),
                      bit51(51),bit52(52),bit53(53),bit54(54),bit55(55),
                      bit56(56),bit57(57),bit58(58),bit59(59),bit60(60),
                      bit61(61),bit62(62),bit63(63)}
     MAX-ACCESS  read-write
     STATUS      current
     DESCRIPTION
         "
         Indicates the conflict services.
          bit0:  CLIP
          bit1:  CLIR
          bit2:  CFU
          bit3:  CFB
          bit4:  CFNR
          bit5:  CFS
          bit6:  CFO
          bit7:  CW
          bit8:  NONE
          bit9:  CALLTRANSFER
          bit10: CALLHOLD
          bit11: THREEPARTY
          bit12: CONF
          bit13: CALLINSERT
          bit14: NONE
          bit15: QUERYDN
          bit16: DDS
          bit17: ABBDIAL
          bit18: WAKECALL
          bit19: ROMA
          bit20: PICKUPINGROUP
          bit21: PICKUPSPECIAL
          bit22: RINGSERVICE
          bit23: SCA
          bit24: RCS
          bit25: RAC
          bit26: OVERSTEPCLIR
          bit27: ICS
          bit28: REMOTEOFFICE
          bit29: SCCCANCEL
          bit30: SCR
          bit31: PARK
          bit32: DLC
          bit33: PWCB
          bit34: CBA
          bit35: CRBT
          bit36: CR
          bit37: OCM
          bit38: ICM
          bit39: CCBS
          bit40: CCNR
          "
    ::= { hwEntPbxStaticConflictEntry 2 } 
     
   --==============================================================   
 
   hwEntPbxDynamicConflictTable OBJECT-TYPE
     SYNTAX      SEQUENCE OF HwEntPbxDynamicConflictEntry
     MAX-ACCESS  not-accessible
     STATUS      current
     DESCRIPTION
       "
       A list of hwEntPbxDynamicConflictTable objects.
       "
     ::= { hwEntVoicePbxMIB 29 }

   hwEntPbxDynamicConflictEntry OBJECT-TYPE
     SYNTAX      HwEntPbxDynamicConflictEntry
     MAX-ACCESS  not-accessible
     STATUS      current
     DESCRIPTION
       "A list of hwEntPbxDynamicConflictTable objects."
     INDEX    {
                 hwEntPbxDynamicConflictSrvIndex                 
              }
     ::= { hwEntPbxDynamicConflictTable 1 }
     
   HwEntPbxDynamicConflictEntry ::=
     SEQUENCE
     {
        hwEntPbxDynamicConflictSrvIndex             Integer32,
        hwEntPbxDynamicConflictNewService           BITS  
     }
     
   hwEntPbxDynamicConflictSrvIndex    OBJECT-TYPE
     SYNTAX      Integer32(0..255)
     MAX-ACCESS  not-accessible
     STATUS      current
     DESCRIPTION
         "
         Indicates the service index.
         1: CLIP
         2: CLIR
         3: CFU
         4: CFB
         5: CFNR
         6: CFS
         7: CFO
         8: CW
         9: NONE
         10: CALLTRANSFER
         11: CALLHOLD
         12: THREEPARTY
         13: CONF
         14: CALLINSERT
         15: NONE
         16: QUERYDN
         17: DDS
         18: ABBDIAL
         19: WAKECALL
         20: ROMA
         21: PICKUPINGROUP
         22: PICKUPSPECIAL
         23: RINGSERVICE
         24: SCA
         25: RCS
         26: RAC
         27: OVERSTEPCLIR
         28: ICS
         29: REMOTEOFFICE
         30: SCCCANCEL
         31: SCR
         32: PARK
         33: DLC
         34: PWCB
         35: CBA
         36: CRBT
         37: CR
         38: OCM
         39: ICM
         40: CCBS
         41: CCNR

         "
    ::= { hwEntPbxDynamicConflictEntry 1 }  
    
   hwEntPbxDynamicConflictNewService    OBJECT-TYPE
     SYNTAX      BITS{bit0(0),bit1(1),bit2(2),bit3(3),bit4(4),bit5(5),
                      bit6(6),bit7(7),bit8(8),bit9(9),bit10(10),
                      bit11(11),bit12(12),bit13(13),bit14(14),bit15(15),
                      bit16(16),bit17(17),bit18(18),bit19(19),bit20(20),
                      bit21(21),bit22(22),bit23(23),bit24(24),bit25(25),
                      bit26(26),bit27(27),bit28(28),bit29(29),bit30(30),
                      bit31(31),bit32(32),bit33(33),bit34(34),bit35(35),
                      bit36(36),bit37(37),bit38(38),bit39(39),bit40(40),
                      bit41(41),bit42(42),bit43(43),bit44(44),bit45(45),
                      bit46(46),bit47(47),bit48(48),bit49(49),bit50(50),
                      bit51(51),bit52(52),bit53(53),bit54(54),bit55(55),
                      bit56(56),bit57(57),bit58(58),bit59(59),bit60(60),
                      bit61(61),bit62(62),bit63(63)}
     MAX-ACCESS  read-write
     STATUS      current
     DESCRIPTION
         "
         Indicates the conflict services.
          bit0:  CLIP
          bit1:  CLIR
          bit2:  CFU
          bit3:  CFB
          bit4:  CFNR
          bit5:  CFS
          bit6:  CFO
          bit7:  CW
          bit8:  NONE
          bit9:  CALLTRANSFER
          bit10: CALLHOLD
          bit11: THREEPARTY
          bit12: CONF
          bit13: CALLINSERT
          bit14: NONE
          bit15: QUERYDN
          bit16: DDS
          bit17: ABBDIAL
          bit18: WAKECALL
          bit19: ROMA
          bit20: PICKUPINGROUP
          bit21: PICKUPSPECIAL
          bit22: RINGSERVICE
          bit23: SCA
          bit24: RCS
          bit25: RAC
          bit26: OVERSTEPCLIR
          bit27: ICS
          bit28: REMOTEOFFICE
          bit29: SCCCANCEL
          bit30: SCR
          bit31: PARK
          bit32: DLC
          bit33: PWCB
          bit34: CBA
          bit35: CRBT
          bit36: CR
          bit37: OCM
          bit38: ICM
          bit39: CCBS
          bit40: CCNR
         "
    ::= { hwEntPbxDynamicConflictEntry 2 } 
    
   --==============================================================   
 
   hwEntPbxSrvCfxTable OBJECT-TYPE
     SYNTAX      SEQUENCE OF HwEntPbxSrvCfxEntry
     MAX-ACCESS  not-accessible
     STATUS      current
     DESCRIPTION
       "
       A list of hwEntPbxSrvCfxTable objects.
       "
     ::= { hwEntVoicePbxMIB 30 }

   hwEntPbxSrvCfxEntry OBJECT-TYPE
     SYNTAX      HwEntPbxSrvCfxEntry
     MAX-ACCESS  not-accessible
     STATUS      current
     DESCRIPTION
       "A list of hwEntPbxSrvCfxTable objects."
     INDEX    {
                 hwEntPbxSrvCfxUserName,
                 hwEntPbxSrvCfxType               
              }
     ::= { hwEntPbxSrvCfxTable 1 }
     
   HwEntPbxSrvCfxEntry ::=
     SEQUENCE
     {
        hwEntPbxSrvCfxUserName             DisplayString,
        hwEntPbxSrvCfxType                 INTEGER,
        hwEntPbxSrvCfxRowStatus            RowStatus,
        hwEntPbxSrvCfxNumber               DisplayString,
        hwEntPbxSrvCfnrTime                Integer32
     }  
    
   hwEntPbxSrvCfxUserName OBJECT-TYPE
     SYNTAX      DisplayString(SIZE (1..32))
     MAX-ACCESS  not-accessible
     STATUS      current
     DESCRIPTION
         "
         Indicates the pbxuser name.
         "
    ::= { hwEntPbxSrvCfxEntry 1 }
    
   hwEntPbxSrvCfxType OBJECT-TYPE
     SYNTAX      INTEGER{cfu(1), cfb(2), cfnr(3), cfo(4)}
     MAX-ACCESS  not-accessible
     STATUS      current
     DESCRIPTION
         "
         Indicates the call forward type.
         "
    ::= { hwEntPbxSrvCfxEntry 2 }
    
   hwEntPbxSrvCfxRowStatus OBJECT-TYPE
     SYNTAX      RowStatus
     MAX-ACCESS  read-create
     STATUS      current
     DESCRIPTION
         "
         Indicates row status of table.
         "
     ::= { hwEntPbxSrvCfxEntry 3 }

   hwEntPbxSrvCfxNumber  OBJECT-TYPE
     SYNTAX      DisplayString(SIZE (1..44))
     MAX-ACCESS  read-create
     STATUS      current
     DESCRIPTION
         "
         Indicates the call forward telephone number.
         "
    ::= { hwEntPbxSrvCfxEntry 4 }
    
   hwEntPbxSrvCfnrTime  OBJECT-TYPE
     SYNTAX      Integer32(1..255)
     MAX-ACCESS  read-create
     STATUS      current
     DESCRIPTION
         "
         Indicates the CFNR time.
         "
    ::= { hwEntPbxSrvCfxEntry 5 }
  
   --==============================================================     

   hwEntPbxSrvRacTable OBJECT-TYPE
     SYNTAX      SEQUENCE OF HwEntPbxSrvRacEntry
     MAX-ACCESS  not-accessible
     STATUS      current
     DESCRIPTION
       "
       A list of hwEntPbxSrvRacTable objects.
       "
     ::= { hwEntVoicePbxMIB 31 }

   hwEntPbxSrvRacEntry OBJECT-TYPE
     SYNTAX      HwEntPbxSrvRacEntry
     MAX-ACCESS  not-accessible
     STATUS      current
     DESCRIPTION
       "A list of hwEntPbxSrvRacTable objects."
     INDEX    {
                 hwEntPbxSrvRacUserName          
              }
     ::= { hwEntPbxSrvRacTable 1 }
     
   HwEntPbxSrvRacEntry ::=
     SEQUENCE
     {
        hwEntPbxSrvRacUserName             DisplayString,
        hwEntPbxSrvRacRowStatus            RowStatus,
        hwEntPbxSrvRacToneId               Integer32
     }  
    
   hwEntPbxSrvRacUserName OBJECT-TYPE
     SYNTAX      DisplayString(SIZE (1..32))
     MAX-ACCESS  not-accessible
     STATUS      current
     DESCRIPTION
         "
         Indicates the pbxuser name.
         "
    ::= { hwEntPbxSrvRacEntry 1 }
    
   hwEntPbxSrvRacRowStatus OBJECT-TYPE
     SYNTAX      RowStatus
     MAX-ACCESS  read-create
     STATUS      current
     DESCRIPTION
         "
         Indicates row status of table.
         "
     ::= { hwEntPbxSrvRacEntry 2 }
    
   hwEntPbxSrvRacToneId OBJECT-TYPE
     SYNTAX      Integer32(1..1000)
     MAX-ACCESS  read-create
     STATUS      current
     DESCRIPTION
         "
         Indicates the tone type.
         "
    ::= { hwEntPbxSrvRacEntry 3 }    
     
   --==============================================================     

   hwEntPbxSrvScaTable OBJECT-TYPE
     SYNTAX      SEQUENCE OF HwEntPbxSrvScaEntry
     MAX-ACCESS  not-accessible
     STATUS      current
     DESCRIPTION
       "
       A list of hwEntPbxSrvScaTable objects.
       "
     ::= { hwEntVoicePbxMIB 32 }

   hwEntPbxSrvScaEntry OBJECT-TYPE
     SYNTAX      HwEntPbxSrvScaEntry
     MAX-ACCESS  not-accessible
     STATUS      current
     DESCRIPTION
       "A list of hwEntPbxSrvScaTable objects."
     INDEX    {
                 hwEntPbxSrvScaUserName,
                 hwEntPbxSrvScaJudgeGrp          
              }
     ::= { hwEntPbxSrvScaTable 1 }
     
   HwEntPbxSrvScaEntry ::=
     SEQUENCE
     {
        hwEntPbxSrvScaUserName             DisplayString,
        hwEntPbxSrvScaJudgeGrp             Integer32,
        hwEntPbxSrvScaRowStatus            RowStatus,
        hwEntPbxSrvScaCallerNum            DisplayString,
        hwEntPbxSrvScaFromDate             DisplayString,
        hwEntPbxSrvScaFromTime             DisplayString,
        hwEntPbxSrvScaToDate               DisplayString,
        hwEntPbxSrvScaToTime               DisplayString,
        hwEntPbxSrvScaRepeatMode           INTEGER,
        hwEntPbxSrvScaBeginDate            DisplayString,
        hwEntPbxSrvScaBeginWeekday         INTEGER,
        hwEntPbxSrvScaBeginTime            DisplayString,
        hwEntPbxSrvScaEndWeekday           INTEGER,
        hwEntPbxSrvScaEndDate              DisplayString,
        hwEntPbxSrvScaEndTime              DisplayString,
        hwEntPbxSrvScaJudgeGroupActive     INTEGER
     }  
    
   hwEntPbxSrvScaUserName OBJECT-TYPE
     SYNTAX      DisplayString(SIZE (1..32))
     MAX-ACCESS  not-accessible
     STATUS      current
     DESCRIPTION
         "
         Indicates the pbxuser name.
         "
    ::= { hwEntPbxSrvScaEntry 1 }
    
   hwEntPbxSrvScaJudgeGrp OBJECT-TYPE
     SYNTAX      Integer32(0..99)
     MAX-ACCESS  not-accessible
     STATUS      current
     DESCRIPTION
         "
         Indicates the pbxuser name.
         "
    ::= { hwEntPbxSrvScaEntry 2 }
    
   hwEntPbxSrvScaRowStatus OBJECT-TYPE
     SYNTAX      RowStatus
     MAX-ACCESS  read-create
     STATUS      current
     DESCRIPTION
         "
         Indicates row status of table.
         "
     ::= { hwEntPbxSrvScaEntry 3 }
     
   hwEntPbxSrvScaCallerNum OBJECT-TYPE
     SYNTAX      DisplayString(SIZE (0..44))
     MAX-ACCESS  read-create
     STATUS      current
     DESCRIPTION
         "
         Indicates caller number of scr service.
         "
     ::= { hwEntPbxSrvScaEntry 4 }
     
   hwEntPbxSrvScaFromDate OBJECT-TYPE
     SYNTAX      DisplayString(SIZE (0..10))
     MAX-ACCESS  read-create
     STATUS      current
     DESCRIPTION
         "
         Indicates the BeginDate.
         Format: yyy-mm-dd
         "
     ::= { hwEntPbxSrvScaEntry 5 }

   hwEntPbxSrvScaFromTime OBJECT-TYPE
     SYNTAX      DisplayString(SIZE (0..8))
     MAX-ACCESS  read-create
     STATUS      current
     DESCRIPTION
         "
         Indicates the BeginTime.
         Format: hh:mm:ss
         "
     ::= { hwEntPbxSrvScaEntry 6 }

   hwEntPbxSrvScaToDate OBJECT-TYPE
     SYNTAX      DisplayString(SIZE (0..10))
     MAX-ACCESS  read-create
     STATUS      current
     DESCRIPTION
         "
         Indicates the EndDate.
         Format: yyy-mm-dd
         "
     ::= { hwEntPbxSrvScaEntry 7 }

   hwEntPbxSrvScaToTime OBJECT-TYPE
     SYNTAX      DisplayString(SIZE (0..8))
     MAX-ACCESS  read-create
     STATUS      current
     DESCRIPTION
         "
         Indicates the EndTime.
         Format: hh:mm:ss
         "
     ::= { hwEntPbxSrvScaEntry 8 }

   hwEntPbxSrvScaRepeatMode OBJECT-TYPE
     SYNTAX      INTEGER{noRepeat(1),yearly(2),monthly(3),weekly(4),daily(5)}
     MAX-ACCESS  read-create
     STATUS      current
     DESCRIPTION
         "
         Indicates the RepeatMode.
         noRepeat(1)
         yearly(2)
         monthly(3)
         weekly(4)
         daily(5)
         "
     ::= { hwEntPbxSrvScaEntry 9 }

   hwEntPbxSrvScaBeginDate OBJECT-TYPE
     SYNTAX      DisplayString(SIZE (0..5))
     MAX-ACCESS  read-create
     STATUS      current
     DESCRIPTION
         "
         Indicates the Repeat BeginDate.
         Format: mm-dd
         "
     ::= { hwEntPbxSrvScaEntry 10 }

   hwEntPbxSrvScaBeginWeekday OBJECT-TYPE
     SYNTAX      INTEGER{mon(1),tue(2),wed(3),thu(4),fri(5),sat(6),sun(7),none(8)}
     MAX-ACCESS  read-create
     STATUS      current
     DESCRIPTION
         "
         Indicates the Repeat BeginWeekday.
         mon(1)
         tue(2)
         wed(3)
         thu(4)
         fri(5)
         sat(6)
         sun(7)
         none(8)
         "
     ::= { hwEntPbxSrvScaEntry 11 }

    hwEntPbxSrvScaBeginTime OBJECT-TYPE
     SYNTAX      DisplayString(SIZE (0..8))
     MAX-ACCESS  read-create
     STATUS      current
     DESCRIPTION
         "
         Indicates the Repeat BeginTime.
         Format: hh:mm:ss
         "
     ::= { hwEntPbxSrvScaEntry 12 }

   hwEntPbxSrvScaEndDate OBJECT-TYPE
     SYNTAX      DisplayString(SIZE (0..5))
     MAX-ACCESS  read-create
     STATUS      current
     DESCRIPTION
         "
         Indicates the Repeat EndDate.
         Format: mm-dd
         "
     ::= { hwEntPbxSrvScaEntry 13 }

   hwEntPbxSrvScaEndWeekday OBJECT-TYPE
     SYNTAX      INTEGER{mon(1),tue(2),wed(3),thu(4),fri(5),sat(6),sun(7),none(8)}
     MAX-ACCESS  read-create
     STATUS      current
     DESCRIPTION
         "
         Indicates the Repeat EndWeekday.
         mon(1)
         tue(2)
         wed(3)
         thu(4)
         fri(5)
         sat(6)
         sun(7)
         none(8)
         "
     ::= { hwEntPbxSrvScaEntry 14 }

   hwEntPbxSrvScaEndTime OBJECT-TYPE
     SYNTAX      DisplayString(SIZE (0..8))
     MAX-ACCESS  read-create
     STATUS      current
     DESCRIPTION
         "
         Indicates the Repeat EndTime.
         Format: hh:mm:ss
         "
     ::= { hwEntPbxSrvScaEntry 15 }

   hwEntPbxSrvScaJudgeGroupActive  OBJECT-TYPE
     SYNTAX      INTEGER{enable(1),disable(2)}
     MAX-ACCESS  read-create
     STATUS      current
     DESCRIPTION
         "
         Indicates jugde group active state.
         enable(1)
         disable(2)
          
         default: disable(2)
         "
     ::= { hwEntPbxSrvScaEntry 16 }
     
   --==============================================================     

   hwEntPbxSrvDndTable OBJECT-TYPE
     SYNTAX      SEQUENCE OF HwEntPbxSrvDndEntry
     MAX-ACCESS  not-accessible
     STATUS      current
     DESCRIPTION
       "
       A list of hwEntPbxSrvDndTable objects.
       "
     ::= { hwEntVoicePbxMIB 33 }

   hwEntPbxSrvDndEntry OBJECT-TYPE
     SYNTAX      HwEntPbxSrvDndEntry
     MAX-ACCESS  not-accessible
     STATUS      current
     DESCRIPTION
       "A list of hwEntPbxSrvDndTable objects."
     INDEX    {
                 hwEntPbxSrvDndUserName          
              }
     ::= { hwEntPbxSrvDndTable 1 }
     
   HwEntPbxSrvDndEntry ::=
     SEQUENCE
     {
        hwEntPbxSrvDndUserName             DisplayString,
        hwEntPbxSrvDndRowStatus            RowStatus,
        hwEntPbxSrvDndToneId               Integer32
     }  
    
   hwEntPbxSrvDndUserName OBJECT-TYPE
     SYNTAX      DisplayString(SIZE (1..32))
     MAX-ACCESS  not-accessible
     STATUS      current
     DESCRIPTION
         "
         Indicates the pbxuser name.
         "
    ::= { hwEntPbxSrvDndEntry 1 }
    
   hwEntPbxSrvDndRowStatus OBJECT-TYPE
     SYNTAX      RowStatus
     MAX-ACCESS  read-create
     STATUS      current
     DESCRIPTION
         "
         Indicates row status of table.
         "
     ::= { hwEntPbxSrvDndEntry 2 }
    
   hwEntPbxSrvDndToneId OBJECT-TYPE
     SYNTAX      Integer32(1..1000)
     MAX-ACCESS  read-create
     STATUS      current
     DESCRIPTION
         "
         Indicates the tone type.
         "
    ::= { hwEntPbxSrvDndEntry 3 }     
     
   --==============================================================     

   hwEntPbxSrvWakeTable OBJECT-TYPE
     SYNTAX      SEQUENCE OF HwEntPbxSrvWakeEntry
     MAX-ACCESS  not-accessible
     STATUS      current
     DESCRIPTION
       "
       A list of hwEntPbxSrvWakeTable objects.
       "
     ::= { hwEntVoicePbxMIB 34 }

   hwEntPbxSrvWakeEntry OBJECT-TYPE
     SYNTAX      HwEntPbxSrvWakeEntry
     MAX-ACCESS  not-accessible
     STATUS      current
     DESCRIPTION
       "A list of hwEntPbxSrvWakeTable objects."
     INDEX    {
                 hwEntPbxSrvWakeUserName          
              }
     ::= { hwEntPbxSrvWakeTable 1 }
     
   HwEntPbxSrvWakeEntry ::=
     SEQUENCE
     {
        hwEntPbxSrvWakeUserName             DisplayString,
        hwEntPbxSrvWakeRowStatus            RowStatus,
        hwEntPbxSrvWakeTime                 DisplayString,
        hwEntPbxSrvWakeDays                 Integer32,
        hwEntPbxSrvWakeBeginDate            DisplayString,
        hwEntPbxSrvWakeToneId               Integer32
     }  
    
   hwEntPbxSrvWakeUserName OBJECT-TYPE
     SYNTAX      DisplayString(SIZE (1..32))
     MAX-ACCESS  not-accessible
     STATUS      current
     DESCRIPTION
         "
         Indicates the pbxuser name.
         "
    ::= { hwEntPbxSrvWakeEntry 1 }
    
   hwEntPbxSrvWakeRowStatus OBJECT-TYPE
     SYNTAX      RowStatus
     MAX-ACCESS  read-create
     STATUS      current
     DESCRIPTION
         "
         Indicates row status of table.
         "
     ::= { hwEntPbxSrvWakeEntry 2 }
    
   hwEntPbxSrvWakeTime OBJECT-TYPE
     SYNTAX      DisplayString(SIZE (1..8))
     MAX-ACCESS  read-create
     STATUS      current
     DESCRIPTION
         "
         Indicates the wake time.
         "
    ::= { hwEntPbxSrvWakeEntry 3 }
 
   hwEntPbxSrvWakeDays OBJECT-TYPE
     SYNTAX      Integer32(0..99)
     MAX-ACCESS  read-create
     STATUS      current
     DESCRIPTION
         "
         Indicates the wake days.
         "
    ::= { hwEntPbxSrvWakeEntry 4 }
    
      hwEntPbxSrvWakeBeginDate OBJECT-TYPE
     SYNTAX      DisplayString(SIZE (0..10))
     MAX-ACCESS  read-create
     STATUS      current
     DESCRIPTION
         "
         Indicates the begin date.
         "
    ::= { hwEntPbxSrvWakeEntry 5 }
    
   hwEntPbxSrvWakeToneId OBJECT-TYPE
     SYNTAX      Integer32(1..1000)
     MAX-ACCESS  read-create
     STATUS      current
     DESCRIPTION
         "
         Indicates the tone id.
         "
    ::= { hwEntPbxSrvWakeEntry 6 }
    
   --==============================================================     

   hwEntPbxSrvAbbTable OBJECT-TYPE
     SYNTAX      SEQUENCE OF HwEntPbxSrvAbbEntry
     MAX-ACCESS  not-accessible
     STATUS      current
     DESCRIPTION
       "
       A list of hwEntPbxSrvAbbTable objects.
       "
     ::= { hwEntVoicePbxMIB 35 }

   hwEntPbxSrvAbbEntry OBJECT-TYPE
     SYNTAX      HwEntPbxSrvAbbEntry
     MAX-ACCESS  not-accessible
     STATUS      current
     DESCRIPTION
       "A list of hwEntPbxSrvAbbTable objects."
     INDEX    {
                 hwEntPbxSrvAbbUserName,
                 hwEntPbxSrvAbbCodeNum
              }
     ::= { hwEntPbxSrvAbbTable 1 }
     
   HwEntPbxSrvAbbEntry ::=
     SEQUENCE
     {
        hwEntPbxSrvAbbUserName             DisplayString,
        hwEntPbxSrvAbbCodeNum              DisplayString,
        hwEntPbxSrvAbbRowStatus            RowStatus,
        hwEntPbxSrvAbbCalledNum            DisplayString
     }  
    
   hwEntPbxSrvAbbUserName OBJECT-TYPE
     SYNTAX      DisplayString(SIZE (1..32))
     MAX-ACCESS  not-accessible
     STATUS      current
     DESCRIPTION
         "
         Indicates the pbxuser name.
         "
    ::= { hwEntPbxSrvAbbEntry 1 }
        
   hwEntPbxSrvAbbCodeNum OBJECT-TYPE
     SYNTAX      DisplayString(SIZE (2))
     MAX-ACCESS  not-accessible
     STATUS      current
     DESCRIPTION
         "
         Indicates the abb code number.
         "
    ::= { hwEntPbxSrvAbbEntry 2 }
    
   hwEntPbxSrvAbbRowStatus OBJECT-TYPE
     SYNTAX      RowStatus
     MAX-ACCESS  read-create
     STATUS      current
     DESCRIPTION
         "
         Indicates row status of table.
         "
     ::= { hwEntPbxSrvAbbEntry 3 }
 
   hwEntPbxSrvAbbCalledNum OBJECT-TYPE
     SYNTAX      DisplayString(SIZE (1..24))
     MAX-ACCESS  read-create
     STATUS      current
     DESCRIPTION
         "
         Indicates the called number.
         "
    ::= { hwEntPbxSrvAbbEntry 4 }
    
   --==============================================================     

   hwEntPbxSrvRcsTable OBJECT-TYPE
     SYNTAX      SEQUENCE OF HwEntPbxSrvRcsEntry
     MAX-ACCESS  not-accessible
     STATUS      current
     DESCRIPTION
       "
       A list of hwEntPbxSrvRcsTable objects.
       "
     ::= { hwEntVoicePbxMIB 36 }

   hwEntPbxSrvRcsEntry OBJECT-TYPE
     SYNTAX      HwEntPbxSrvRcsEntry
     MAX-ACCESS  not-accessible
     STATUS      current
     DESCRIPTION
       "A list of hwEntPbxSrvRcsTable objects."
     INDEX    {
                 hwEntPbxSrvRcsUserName,
                 hwEntPbxSrvRcsJudgeGrp          
              }
     ::= { hwEntPbxSrvRcsTable 1 }
     
   HwEntPbxSrvRcsEntry ::=
     SEQUENCE
     {
        hwEntPbxSrvRcsUserName             DisplayString,
        hwEntPbxSrvRcsJudgeGrp             Integer32,
        hwEntPbxSrvRcsRowStatus            RowStatus,
        hwEntPbxSrvRcsCallerNum            DisplayString,
        hwEntPbxSrvRcsFromDate             DisplayString,
        hwEntPbxSrvRcsFromTime             DisplayString,
        hwEntPbxSrvRcsToDate               DisplayString,
        hwEntPbxSrvRcsToTime               DisplayString,
        hwEntPbxSrvRcsRepeatMode           INTEGER,
        hwEntPbxSrvRcsBeginDate            DisplayString,
        hwEntPbxSrvRcsBeginWeekday         INTEGER,
        hwEntPbxSrvRcsBeginTime            DisplayString,
        hwEntPbxSrvRcsEndWeekday           INTEGER,
        hwEntPbxSrvRcsEndDate              DisplayString,
        hwEntPbxSrvRcsEndTime              DisplayString,
        hwEntPbxSrvRcsJudgeGroupActive     INTEGER
     }  
    
   hwEntPbxSrvRcsUserName OBJECT-TYPE
     SYNTAX      DisplayString(SIZE (1..32))
     MAX-ACCESS  not-accessible
     STATUS      current
     DESCRIPTION
         "
         Indicates the pbxuser name.
         "
    ::= { hwEntPbxSrvRcsEntry 1 }
    
   hwEntPbxSrvRcsJudgeGrp OBJECT-TYPE
     SYNTAX      Integer32(0..99)
     MAX-ACCESS  not-accessible
     STATUS      current
     DESCRIPTION
         "
         Indicates the pbxuser name.
         "
    ::= { hwEntPbxSrvRcsEntry 2 }
    
   hwEntPbxSrvRcsRowStatus OBJECT-TYPE
     SYNTAX      RowStatus
     MAX-ACCESS  read-create
     STATUS      current
     DESCRIPTION
         "
         Indicates row status of table.
         "
     ::= { hwEntPbxSrvRcsEntry 3 }
     
   hwEntPbxSrvRcsCallerNum OBJECT-TYPE
     SYNTAX      DisplayString(SIZE (0..44))
     MAX-ACCESS  read-create
     STATUS      current
     DESCRIPTION
         "
         Indicates caller number of scr service.
         "
     ::= { hwEntPbxSrvRcsEntry 4 }
     
   hwEntPbxSrvRcsFromDate OBJECT-TYPE
     SYNTAX      DisplayString(SIZE (0..10))
     MAX-ACCESS  read-create
     STATUS      current
     DESCRIPTION
         "
         Indicates the BeginDate.
         Format: yyy-mm-dd
         "
     ::= { hwEntPbxSrvRcsEntry 5 }

   hwEntPbxSrvRcsFromTime OBJECT-TYPE
     SYNTAX      DisplayString(SIZE (0..8))
     MAX-ACCESS  read-create
     STATUS      current
     DESCRIPTION
         "
         Indicates the BeginTime.
         Format: hh:mm:ss
         "
     ::= { hwEntPbxSrvRcsEntry 6 }

   hwEntPbxSrvRcsToDate OBJECT-TYPE
     SYNTAX      DisplayString(SIZE (0..10))
     MAX-ACCESS  read-create
     STATUS      current
     DESCRIPTION
         "
         Indicates the EndDate.
         Format: yyy-mm-dd
         "
     ::= { hwEntPbxSrvRcsEntry 7 }

   hwEntPbxSrvRcsToTime OBJECT-TYPE
     SYNTAX      DisplayString(SIZE (0..8))
     MAX-ACCESS  read-create
     STATUS      current
     DESCRIPTION
         "
         Indicates the EndTime.
         Format: hh:mm:ss
         "
     ::= { hwEntPbxSrvRcsEntry 8 }

   hwEntPbxSrvRcsRepeatMode OBJECT-TYPE
     SYNTAX      INTEGER{noRepeat(1),yearly(2),monthly(3),weekly(4),daily(5)}
     MAX-ACCESS  read-create
     STATUS      current
     DESCRIPTION
         "
         Indicates the RepeatMode.
         noRepeat(1)
         yearly(2)
         monthly(3)
         weekly(4)
         daily(5)
         "
     ::= { hwEntPbxSrvRcsEntry 9 }

   hwEntPbxSrvRcsBeginDate OBJECT-TYPE
     SYNTAX      DisplayString(SIZE (0..5))
     MAX-ACCESS  read-create
     STATUS      current
     DESCRIPTION
         "
         Indicates the Repeat BeginDate.
         Format: mm-dd
         "
     ::= { hwEntPbxSrvRcsEntry 10 }

   hwEntPbxSrvRcsBeginWeekday OBJECT-TYPE
     SYNTAX      INTEGER{mon(1),tue(2),wed(3),thu(4),fri(5),sat(6),sun(7),none(8)}
     MAX-ACCESS  read-create
     STATUS      current
     DESCRIPTION
         "
         Indicates the Repeat BeginWeekday.
         mon(1)
         tue(2)
         wed(3)
         thu(4)
         fri(5)
         sat(6)
         sun(7)
         none(8)
         "
     ::= { hwEntPbxSrvRcsEntry 11 }

    hwEntPbxSrvRcsBeginTime OBJECT-TYPE
     SYNTAX      DisplayString(SIZE (0..8))
     MAX-ACCESS  read-create
     STATUS      current
     DESCRIPTION
         "
         Indicates the Repeat BeginTime.
         Format: hh:mm:ss
         "
     ::= { hwEntPbxSrvRcsEntry 12 }

   hwEntPbxSrvRcsEndDate OBJECT-TYPE
     SYNTAX      DisplayString(SIZE (0..5))
     MAX-ACCESS  read-create
     STATUS      current
     DESCRIPTION
         "
         Indicates the Repeat EndDate.
         Format: mm-dd
         "
     ::= { hwEntPbxSrvRcsEntry 13 }

   hwEntPbxSrvRcsEndWeekday OBJECT-TYPE
     SYNTAX      INTEGER{mon(1),tue(2),wed(3),thu(4),fri(5),sat(6),sun(7),none(8)}
     MAX-ACCESS  read-create
     STATUS      current
     DESCRIPTION
         "
         Indicates the Repeat EndWeekday.
         mon(1)
         tue(2)
         wed(3)
         thu(4)
         fri(5)
         sat(6)
         sun(7)
         none(8)
         "
     ::= { hwEntPbxSrvRcsEntry 14 }

   hwEntPbxSrvRcsEndTime OBJECT-TYPE
     SYNTAX      DisplayString(SIZE (0..8))
     MAX-ACCESS  read-create
     STATUS      current
     DESCRIPTION
         "
         Indicates the Repeat EndTime.
         Format: hh:mm:ss
         "
     ::= { hwEntPbxSrvRcsEntry 15 }

   hwEntPbxSrvRcsJudgeGroupActive  OBJECT-TYPE
     SYNTAX      INTEGER{enable(1),disable(2)}
     MAX-ACCESS  read-create
     STATUS      current
     DESCRIPTION
         "
         Indicates jugde group active state.
         enable(1)
         disable(2)
         
         default: disable(2)
         "
     ::= { hwEntPbxSrvRcsEntry 16 }
         
   --==============================================================     

   hwEntPbxSrvScrTable OBJECT-TYPE
     SYNTAX      SEQUENCE OF HwEntPbxSrvScrEntry
     MAX-ACCESS  not-accessible
     STATUS      current
     DESCRIPTION
       "
       A list of hwEntPbxSrvScrTable objects.
       "
     ::= { hwEntVoicePbxMIB 37 }

   hwEntPbxSrvScrEntry OBJECT-TYPE
     SYNTAX      HwEntPbxSrvScrEntry
     MAX-ACCESS  not-accessible
     STATUS      current
     DESCRIPTION
       "A list of hwEntPbxSrvScrTable objects."
     INDEX    {
                 hwEntPbxSrvScrUserName        
              }
     ::= { hwEntPbxSrvScrTable 1 }
     
   HwEntPbxSrvScrEntry ::=
     SEQUENCE
     {
        hwEntPbxSrvScrUserName                 DisplayString,
        hwEntPbxSrvScrRowStatus                RowStatus,
        hwEntPbxSrvScrCentrex                  DisplayString,
        hwEntPbxSrvScrCountryCode              DisplayString,
        hwEntPbxSrvScrAreaCode                 DisplayString,
        hwEntPbxSrvScrTelno                    DisplayString        
     }  
    
   hwEntPbxSrvScrUserName OBJECT-TYPE
     SYNTAX      DisplayString(SIZE (1..32))
     MAX-ACCESS  not-accessible
     STATUS      current
     DESCRIPTION
         "
         Indicates the pbx user name.
         "
    ::= { hwEntPbxSrvScrEntry 1 }
       
   hwEntPbxSrvScrRowStatus OBJECT-TYPE
     SYNTAX      RowStatus
     MAX-ACCESS  read-create
     STATUS      current
     DESCRIPTION
         "
         Indicates row status of table.
         "
     ::= { hwEntPbxSrvScrEntry 2 }
     
   hwEntPbxSrvScrCentrex OBJECT-TYPE
     SYNTAX      DisplayString(SIZE (0..32))
     MAX-ACCESS  read-create
     STATUS      current
     DESCRIPTION
         "
         Indicates the centrex of secretory.
         "
     ::= { hwEntPbxSrvScrEntry 3 }
     
   hwEntPbxSrvScrCountryCode OBJECT-TYPE
     SYNTAX      DisplayString(SIZE (0..4))
     MAX-ACCESS  read-create
     STATUS      current
     DESCRIPTION
         "
         Indicates the country code of secretory.
         "
     ::= { hwEntPbxSrvScrEntry 4 }

   hwEntPbxSrvScrAreaCode OBJECT-TYPE
     SYNTAX      DisplayString(SIZE (0..8))
     MAX-ACCESS  read-create
     STATUS      current
     DESCRIPTION
         "
         Indicates the area code of secretory.
         "
     ::= { hwEntPbxSrvScrEntry 5 }

   hwEntPbxSrvScrTelno OBJECT-TYPE
     SYNTAX      DisplayString(SIZE (1..24))
     MAX-ACCESS  read-create
     STATUS      current
     DESCRIPTION
         "
         Indicates the telephon number of secretory.
         "
     ::= { hwEntPbxSrvScrEntry 6 }
     
   --==============================================================     

   hwEntPbxSrvRmtTable OBJECT-TYPE
     SYNTAX      SEQUENCE OF HwEntPbxSrvRmtEntry
     MAX-ACCESS  not-accessible
     STATUS      current
     DESCRIPTION
       "
       A list of hwEntPbxSrvRmtTable objects.
       "
     ::= { hwEntVoicePbxMIB 38 }

   hwEntPbxSrvRmtEntry OBJECT-TYPE
     SYNTAX      HwEntPbxSrvRmtEntry
     MAX-ACCESS  not-accessible
     STATUS      current
     DESCRIPTION
       "A list of hwEntPbxSrvRmtTable objects."
     INDEX    {
                 hwEntPbxSrvRmtUserName        
              }
     ::= { hwEntPbxSrvRmtTable 1 }
     
   HwEntPbxSrvRmtEntry ::=
     SEQUENCE
     {
        hwEntPbxSrvRmtUserName                 DisplayString,
        hwEntPbxSrvRmtRowStatus                RowStatus,
        hwEntPbxSrvRmtCentrex                  DisplayString,
        hwEntPbxSrvRmtCountryCode              DisplayString,
        hwEntPbxSrvRmtAreaCode                 DisplayString,
        hwEntPbxSrvRmtTelno                    DisplayString        
     }  
    
   hwEntPbxSrvRmtUserName OBJECT-TYPE
     SYNTAX      DisplayString(SIZE (1..32))
     MAX-ACCESS  not-accessible
     STATUS      current
     DESCRIPTION
         "
         Indicates the pbx user name.
         "
    ::= { hwEntPbxSrvRmtEntry 1 }
       
   hwEntPbxSrvRmtRowStatus OBJECT-TYPE
     SYNTAX      RowStatus
     MAX-ACCESS  read-create
     STATUS      current
     DESCRIPTION
         "
         Indicates row status of table.
         "
     ::= { hwEntPbxSrvRmtEntry 2 }
     
   hwEntPbxSrvRmtCentrex OBJECT-TYPE
     SYNTAX      DisplayString(SIZE (0..32))
     MAX-ACCESS  read-create
     STATUS      current
     DESCRIPTION
         "
         Indicates the centrex of remote office.
         "
     ::= { hwEntPbxSrvRmtEntry 3 }
     
   hwEntPbxSrvRmtCountryCode OBJECT-TYPE
     SYNTAX      DisplayString(SIZE (0..4))
     MAX-ACCESS  read-create
     STATUS      current
     DESCRIPTION
         "
         Indicates the country code of remote office.
         "
     ::= { hwEntPbxSrvRmtEntry 4 }

   hwEntPbxSrvRmtAreaCode OBJECT-TYPE
     SYNTAX      DisplayString(SIZE (0..8))
     MAX-ACCESS  read-create
     STATUS      current
     DESCRIPTION
         "
         Indicates the area code of remote office.
         "
     ::= { hwEntPbxSrvRmtEntry 5 }

   hwEntPbxSrvRmtTelno OBJECT-TYPE
     SYNTAX      DisplayString(SIZE (1..24))
     MAX-ACCESS  read-create
     STATUS      current
     DESCRIPTION
         "
         Indicates the telephone number of remote office.
         "
     ::= { hwEntPbxSrvRmtEntry 6 }

   --==============================================================     

   hwEntPbxSrvCbaTable OBJECT-TYPE
     SYNTAX      SEQUENCE OF HwEntPbxSrvCbaEntry
     MAX-ACCESS  not-accessible
     STATUS      current
     DESCRIPTION
       "
       A list of hwEntPbxSrvCbaTable objects.
       "
     ::= { hwEntVoicePbxMIB 39 }

   hwEntPbxSrvCbaEntry OBJECT-TYPE
     SYNTAX      HwEntPbxSrvCbaEntry
     MAX-ACCESS  not-accessible
     STATUS      current
     DESCRIPTION
       "A list of hwEntPbxSrvCbaTable objects."
     INDEX    {
                 hwEntPbxSrvCbaUserName        
              }
     ::= { hwEntPbxSrvCbaTable 1 }
     
   HwEntPbxSrvCbaEntry ::=
     SEQUENCE
     {
        hwEntPbxSrvCbaUserName                 DisplayString,
        hwEntPbxSrvCbaRowStatus                RowStatus,
        hwEntPbxSrvCbaType                     INTEGER 
     }  
    
   hwEntPbxSrvCbaUserName OBJECT-TYPE
     SYNTAX      DisplayString(SIZE (1..32))
     MAX-ACCESS  not-accessible
     STATUS      current
     DESCRIPTION
         "
         Indicates the pbx user name.
         "
    ::= { hwEntPbxSrvCbaEntry 1 }
       
   hwEntPbxSrvCbaRowStatus OBJECT-TYPE
     SYNTAX      RowStatus
     MAX-ACCESS  read-create
     STATUS      current
     DESCRIPTION
         "
         Indicates row status of table.
         "
     ::= { hwEntPbxSrvCbaEntry 2 }
     
   hwEntPbxSrvCbaType OBJECT-TYPE
     SYNTAX      INTEGER{all(1), iddCdd(2), idd(3)} 
     MAX-ACCESS  read-create
     STATUS      current
     DESCRIPTION
         "
         Indicates the cba type.
         "
     ::= { hwEntPbxSrvCbaEntry 3 }   
     
   --==============================================================     

   hwEntPbxSrvCallInterceptTable OBJECT-TYPE
     SYNTAX      SEQUENCE OF HwEntPbxSrvCallInterceptEntry
     MAX-ACCESS  not-accessible
     STATUS      current
     DESCRIPTION
       "
       A list of hwEntPbxSrvCallInterceptTable objects.
       "
     ::= { hwEntVoicePbxMIB 40 }

   hwEntPbxSrvCallInterceptEntry OBJECT-TYPE
     SYNTAX      HwEntPbxSrvCallInterceptEntry
     MAX-ACCESS  not-accessible
     STATUS      current
     DESCRIPTION
       "A list of hwEntPbxSrvCallInterceptTable objects."
     INDEX    {
                 hwEntPbxSrvCallInterceptName        
              }
     ::= { hwEntPbxSrvCallInterceptTable 1 }
     
   HwEntPbxSrvCallInterceptEntry ::=
     SEQUENCE
     {
        hwEntPbxSrvCallInterceptName                 DisplayString,
        hwEntPbxSrvCallInterceptRowStatus            RowStatus,
        hwEntPbxSrvCallInterceptEnterprise           DisplayString,
        hwEntPbxSrvCallInterceptDnset                DisplayString,
        hwEntPbxSrvCallInterceptCentrex              DisplayString,
        hwEntPbxSrvCallInterceptCallStatus           INTEGER,
        hwEntPbxSrvCallInterceptCallPrefix           DisplayString,
        hwEntPbxSrvCallInterceptToneId               Integer32
     }  
    
   hwEntPbxSrvCallInterceptName OBJECT-TYPE
     SYNTAX      DisplayString(SIZE (1..32))
     MAX-ACCESS  not-accessible
     STATUS      current
     DESCRIPTION
         "
         Indicates the CallIntercept name.
         "
    ::= { hwEntPbxSrvCallInterceptEntry 1 }
       
   hwEntPbxSrvCallInterceptRowStatus OBJECT-TYPE
     SYNTAX      RowStatus
     MAX-ACCESS  read-create
     STATUS      current
     DESCRIPTION
         "
         Indicates row status of table.
         "
     ::= { hwEntPbxSrvCallInterceptEntry 2 }
     
   hwEntPbxSrvCallInterceptEnterprise OBJECT-TYPE
     SYNTAX      DisplayString(SIZE (1..32))
     MAX-ACCESS  read-create
     STATUS      current
     DESCRIPTION
         "
         Indicates enterprise of callIntercept service.
         "
     ::= { hwEntPbxSrvCallInterceptEntry 3 }
     
   hwEntPbxSrvCallInterceptDnset OBJECT-TYPE
     SYNTAX      DisplayString(SIZE (1..32))
     MAX-ACCESS  read-create
     STATUS      current
     DESCRIPTION
         "
         Indicates dnset of CallIntercept service.
         "
     ::= { hwEntPbxSrvCallInterceptEntry 4 }

   hwEntPbxSrvCallInterceptCentrex OBJECT-TYPE
     SYNTAX      DisplayString(SIZE (1..32))
     MAX-ACCESS  read-create
     STATUS      current
     DESCRIPTION
         "
         Indicates centrex of callIntercept service.
         "
     ::= { hwEntPbxSrvCallInterceptEntry 5 }

   hwEntPbxSrvCallInterceptCallStatus OBJECT-TYPE
     SYNTAX      INTEGER{busy(1), noAnswer(2), offline(3), 
                         dnError(4), noRight(5), unreachable(6)}
     MAX-ACCESS  read-create
     STATUS      current
     DESCRIPTION
         "
         Indicates the call status of callIntercept service.
         "
     ::= { hwEntPbxSrvCallInterceptEntry 6 }

   hwEntPbxSrvCallInterceptCallPrefix OBJECT-TYPE
     SYNTAX      DisplayString(SIZE (0..32))
     MAX-ACCESS  read-create
     STATUS      current
     DESCRIPTION
         "
         Indicates the callPrefix of callIntercept service.
         "
     ::= { hwEntPbxSrvCallInterceptEntry 7 }
     
   hwEntPbxSrvCallInterceptToneId OBJECT-TYPE
     SYNTAX      Integer32(1..1000)
     MAX-ACCESS  read-create
     STATUS      current
     DESCRIPTION
         "
         Indicates the tone id  of callIntercept service.
         "
     ::= { hwEntPbxSrvCallInterceptEntry 8 }
     
     
   --==============================================================     

   hwEntPbxSrvAlertRingTable OBJECT-TYPE
     SYNTAX      SEQUENCE OF HwEntPbxSrvAlertRingEntry
     MAX-ACCESS  not-accessible
     STATUS      current
     DESCRIPTION
       "
       A list of hwEntPbxSrvAlertRingTable objects.
       "
     ::= { hwEntVoicePbxMIB 41 }

   hwEntPbxSrvAlertRingEntry OBJECT-TYPE
     SYNTAX      HwEntPbxSrvAlertRingEntry
     MAX-ACCESS  not-accessible
     STATUS      current
     DESCRIPTION
       "A list of hwEntPbxSrvAlertRingTable objects."
     INDEX    {
                 hwEntPbxSrvAlertRingName        
              }
     ::= { hwEntPbxSrvAlertRingTable 1 }
     
   HwEntPbxSrvAlertRingEntry ::=
     SEQUENCE
     {
        hwEntPbxSrvAlertRingName                 DisplayString,
        hwEntPbxSrvAlertRingRowStatus            RowStatus,
        hwEntPbxSrvAlertRingEnterprise           DisplayString,
        hwEntPbxSrvAlertRingCentrex              DisplayString,
        hwEntPbxSrvAlertRingCentrexRingId        Integer32,
        hwEntPbxSrvAlertRingOutLocalRingId       Integer32,
        hwEntPbxSrvAlertRingOutDDDRingId         Integer32,
        hwEntPbxSrvAlertRingOutIDDRingId         Integer32
        
     }  
    
   hwEntPbxSrvAlertRingName OBJECT-TYPE
     SYNTAX      DisplayString(SIZE (1..32))
     MAX-ACCESS  not-accessible
     STATUS      current
     DESCRIPTION
         "
         Indicates the alert ring name.
         "
    ::= { hwEntPbxSrvAlertRingEntry 1 }
       
   hwEntPbxSrvAlertRingRowStatus OBJECT-TYPE
     SYNTAX      RowStatus
     MAX-ACCESS  read-create
     STATUS      current
     DESCRIPTION
         "
         Indicates row status of table.
         "
     ::= { hwEntPbxSrvAlertRingEntry 2 }
     
   hwEntPbxSrvAlertRingEnterprise OBJECT-TYPE
     SYNTAX      DisplayString(SIZE (1..32))
     MAX-ACCESS  read-create
     STATUS      current
     DESCRIPTION
         "
         Indicates the enterprise of alert ring service.
         "
     ::= { hwEntPbxSrvAlertRingEntry 3 }
     
   hwEntPbxSrvAlertRingCentrex OBJECT-TYPE
     SYNTAX      DisplayString(SIZE (1..32))
     MAX-ACCESS  read-create
     STATUS      current
     DESCRIPTION
         "
         Indicates the centrex of alert ring service.
         "
     ::= { hwEntPbxSrvAlertRingEntry 4 }

   hwEntPbxSrvAlertRingCentrexRingId OBJECT-TYPE
     SYNTAX      Integer32(0..15)
     MAX-ACCESS  read-create
     STATUS      current
     DESCRIPTION
         "
         Indicates the centrex ring id.
         "
     ::= { hwEntPbxSrvAlertRingEntry 5 }

   hwEntPbxSrvAlertRingOutLocalRingId OBJECT-TYPE
     SYNTAX      Integer32(0..15)
     MAX-ACCESS  read-create
     STATUS      current
     DESCRIPTION
         "
         Indicates the out local ring id.
         "
     ::= { hwEntPbxSrvAlertRingEntry 6 }
     
   hwEntPbxSrvAlertRingOutDDDRingId OBJECT-TYPE
     SYNTAX      Integer32(0..15)
     MAX-ACCESS  read-create
     STATUS      current
     DESCRIPTION
         "
         Indicates the out ddd ring id.
         "
     ::= { hwEntPbxSrvAlertRingEntry 7 }
     
   hwEntPbxSrvAlertRingOutIDDRingId OBJECT-TYPE
     SYNTAX      Integer32(0..15)
     MAX-ACCESS  read-create
     STATUS      current
     DESCRIPTION
         "
         Indicates the out idd ring id.
         "
     ::= { hwEntPbxSrvAlertRingEntry 8 }
     
   --==============================================================   

   hwEntPbxE1r2TrkTable OBJECT-TYPE
     SYNTAX      SEQUENCE OF HwEntPbxE1r2TrkEntry
     MAX-ACCESS  not-accessible
     STATUS      current
     DESCRIPTION
       "
       A list of hwEntPbxE1r2TrkEntry objects.
       "
     ::= { hwEntVoicePbxMIB 42 }

   hwEntPbxE1r2TrkEntry OBJECT-TYPE
     SYNTAX      HwEntPbxE1r2TrkEntry
     MAX-ACCESS  not-accessible
     STATUS      current
     DESCRIPTION
       "A list of hwEntPbxE1r2TrkEntry objects."
       INDEX   {
                   hwEntPbxE1r2TrkIndex
               }
     ::= { hwEntPbxE1r2TrkTable 1 }

   HwEntPbxE1r2TrkEntry ::=
     SEQUENCE
     {
        hwEntPbxE1r2TrkIndex             Integer32,
        hwEntPbxE1r2TrkRowStatus         RowStatus,
        hwEntPbxE1r2TrkGrpName           DisplayString,
        hwEntPbxE1r2TrkCfgStatus         INTEGER,
        hwEntPbxE1r2TrkAdminStatus         INTEGER
     }

   hwEntPbxE1r2TrkIndex OBJECT-TYPE
     SYNTAX      Integer32
     MAX-ACCESS  not-accessible
     STATUS      current
     DESCRIPTION
         "
         Indicates the index of physical trunk.
         bits 24-31:  slot index
         bits 23-16: subcard index
         bits 15-8: port index
         bits 7-0:  time slot
         "
     ::= { hwEntPbxE1r2TrkEntry 1 }

   hwEntPbxE1r2TrkRowStatus OBJECT-TYPE
     SYNTAX      RowStatus
     MAX-ACCESS  read-create
     STATUS      current
     DESCRIPTION
         "
         Indicates the row status.
         active(1)
         notInService(2)
         notReady(3)
         createAndGo(4)
         createAndWait(5)
         destroy(6)
         "
     ::= { hwEntPbxE1r2TrkEntry 2 }

   hwEntPbxE1r2TrkGrpName OBJECT-TYPE
     SYNTAX      DisplayString(SIZE(1..32))
     MAX-ACCESS  read-create
     STATUS      current
     DESCRIPTION
         "
         Indicates the pra trunk group name.
         "
     ::= { hwEntPbxE1r2TrkEntry 3 }

   hwEntPbxE1r2TrkCfgStatus OBJECT-TYPE
     SYNTAX      INTEGER{block(1),normal(2),reserved(3)}
     MAX-ACCESS  read-create
     STATUS      current
     DESCRIPTION
         "
         Indicates the time slot config state of the e1r2 trunk group.
         block(1)
          normal(2)
          reserved(3)
         "
     ::= { hwEntPbxE1r2TrkEntry 4 }
     
   hwEntPbxE1r2TrkAdminStatus OBJECT-TYPE
     SYNTAX      INTEGER{normal(1),lBlock(2),rBlock(3),lrBlock(4),reserved(5)}
     MAX-ACCESS  read-only
     STATUS      current
     DESCRIPTION
         "
         Indicates the time slot admin state of the e1r2 trunk group.
         normal(1)
         lBlock(2)
         rBlock(3)
         lrBlock(4)
         reserved(5)
         "
     ::= { hwEntPbxE1r2TrkEntry 5 }
    
   --==============================================================     

   hwEntPbxSystemParaTable OBJECT-TYPE
     SYNTAX      SEQUENCE OF HwEntPbxSystemParaEntry
     MAX-ACCESS  not-accessible
     STATUS      current
     DESCRIPTION
       "
       A list of hwEntPbxSystemParaTable objects.
       "
     ::= { hwEntVoicePbxMIB 43 }

   hwEntPbxSystemParaEntry OBJECT-TYPE
     SYNTAX      HwEntPbxSystemParaEntry
     MAX-ACCESS  not-accessible
     STATUS      current
     DESCRIPTION
       "A list of hwEntPbxSystemParaTable objects."
     INDEX    {
                 hwEntPbxSystemParaIndex        
              }
     ::= { hwEntPbxSystemParaTable 1 }
     
   HwEntPbxSystemParaEntry ::=
     SEQUENCE
     {
        hwEntPbxSystemParaIndex                 Integer32,
        hwEntPbxSystemParaValue                 Integer32
     }  
    
   hwEntPbxSystemParaIndex OBJECT-TYPE
     SYNTAX      Integer32(0..255)
     MAX-ACCESS  not-accessible
     STATUS      current
     DESCRIPTION
         "
         Indicates the pbx system parameter index.
         "
    ::= { hwEntPbxSystemParaEntry 1 }
       
   hwEntPbxSystemParaValue OBJECT-TYPE
     SYNTAX      Integer32
     MAX-ACCESS  read-write
     STATUS      current
     DESCRIPTION
         "
         Indicates the pbx system parameter value.
         "
     ::= { hwEntPbxSystemParaEntry 2 }
    
   --==============================================================     

   hwEntPbxIsdnCauseMapTable OBJECT-TYPE
     SYNTAX      SEQUENCE OF HwEntPbxIsdnCauseMapEntry
     MAX-ACCESS  not-accessible
     STATUS      current
     DESCRIPTION
       "
       A list of hwEntPbxIsdnCauseMapTable objects.
       "
     ::= { hwEntVoicePbxMIB 44 }

   hwEntPbxIsdnCauseMapEntry OBJECT-TYPE
     SYNTAX      HwEntPbxIsdnCauseMapEntry
     MAX-ACCESS  not-accessible
     STATUS      current
     DESCRIPTION
       "A list of hwEntPbxIsdnCauseMapTable objects."
     INDEX    {
                 hwEntPbxIsdnCauseMapIsdnCause        
              }
     ::= { hwEntPbxIsdnCauseMapTable 1 }
     
   HwEntPbxIsdnCauseMapEntry ::=
     SEQUENCE
     {
        hwEntPbxIsdnCauseMapIsdnCause             Integer32,
        hwEntPbxIsdnCauseMapRowStatus             RowStatus,
        hwEntPbxIsdnCauseMapSipResponse           Integer32
     }  
    
   hwEntPbxIsdnCauseMapIsdnCause OBJECT-TYPE
     SYNTAX      Integer32(1..127)
     MAX-ACCESS  not-accessible
     STATUS      current
     DESCRIPTION
         "
         Indicates the ISDN cause.
         "
    ::= { hwEntPbxIsdnCauseMapEntry 1 }
       
   hwEntPbxIsdnCauseMapRowStatus OBJECT-TYPE
     SYNTAX      RowStatus
     MAX-ACCESS  read-create
     STATUS      current
     DESCRIPTION
         "
         Indicates row status of table.
         "
     ::= { hwEntPbxIsdnCauseMapEntry 2 }
       
       
   hwEntPbxIsdnCauseMapSipResponse OBJECT-TYPE
     SYNTAX      Integer32(100..699)
     MAX-ACCESS  read-create
     STATUS      current
     DESCRIPTION
         "
         Indicates the sip response.
         "
     ::= { hwEntPbxIsdnCauseMapEntry 3 }
     
   --==============================================================     

   hwEntPbxSipCauseMapTable OBJECT-TYPE
     SYNTAX      SEQUENCE OF HwEntPbxSipCauseMapEntry
     MAX-ACCESS  not-accessible
     STATUS      current
     DESCRIPTION
       "
       A list of hwEntPbxSipCauseMapTable objects.
       "
     ::= { hwEntVoicePbxMIB 45 }

   hwEntPbxSipCauseMapEntry OBJECT-TYPE
     SYNTAX      HwEntPbxSipCauseMapEntry
     MAX-ACCESS  not-accessible
     STATUS      current
     DESCRIPTION
       "A list of hwEntPbxSipCauseMapTable objects."
     INDEX    {
                 hwEntPbxSipCauseMapSipResponse        
              }
     ::= { hwEntPbxSipCauseMapTable 1 }
     
   HwEntPbxSipCauseMapEntry ::=
     SEQUENCE
     {
        hwEntPbxSipCauseMapSipResponse               Integer32,
        hwEntPbxSipCauseMapRowStatus                 RowStatus,
        hwEntPbxSipCauseMapIsdnCause                 Integer32
     }  
    
   hwEntPbxSipCauseMapSipResponse OBJECT-TYPE
     SYNTAX      Integer32(100..699)
     MAX-ACCESS  not-accessible
     STATUS      current
     DESCRIPTION
         "
         Indicates the sip response.
         "
    ::= { hwEntPbxSipCauseMapEntry 1 }
       
   hwEntPbxSipCauseMapRowStatus OBJECT-TYPE
     SYNTAX      RowStatus
     MAX-ACCESS  read-create
     STATUS      current
     DESCRIPTION
         "
         Indicates row status of table.
         "
     ::= { hwEntPbxSipCauseMapEntry 2 }
       
       
   hwEntPbxSipCauseMapIsdnCause OBJECT-TYPE
     SYNTAX      Integer32(1..127)
     MAX-ACCESS  read-create
     STATUS      current
     DESCRIPTION
         "
         Indicates the ISDN cause.
         "
     ::= { hwEntPbxSipCauseMapEntry 3 }
    
   --==============================================================     

   hwEntPbxTrkGrpCodecPriConfigTable OBJECT-TYPE
     SYNTAX      SEQUENCE OF HwEntPbxTrkGrpCodecPriConfigEntry
     MAX-ACCESS  not-accessible
     STATUS      current
     DESCRIPTION
         "
         A list of hwEntPbxTrkGrpCodecPriConfigTable objects.
         "
     ::= { hwEntVoicePbxMIB 46 }

   hwEntPbxTrkGrpCodecPriConfigEntry OBJECT-TYPE
     SYNTAX      HwEntPbxTrkGrpCodecPriConfigEntry
     MAX-ACCESS  not-accessible
     STATUS      current
     DESCRIPTION
       "A list of hwEntPbxTrkGrpCodecPriConfigTable objects."
     INDEX    {
                 hwEntPbxTrkGrpCodecPriTrkGrpName,
                 hwEntPbxTrkGrpCodecPriIndex        
              }
     ::= { hwEntPbxTrkGrpCodecPriConfigTable 1 }
     
   HwEntPbxTrkGrpCodecPriConfigEntry ::=
     SEQUENCE
     {
        hwEntPbxTrkGrpCodecPriTrkGrpName                DisplayString,
        hwEntPbxTrkGrpCodecPriIndex                     Integer32,
        hwEntPbxTrkGrpCodecPriCodec                     Integer32,
        hwEntPbxTrkGrpCodecPriPt                        Integer32
     }  
    
   hwEntPbxTrkGrpCodecPriTrkGrpName OBJECT-TYPE
     SYNTAX      DisplayString(SIZE (1..32))
     MAX-ACCESS  not-accessible
     STATUS      current
     DESCRIPTION
         "
         Indicates the trunk group name.
         "
    ::= { hwEntPbxTrkGrpCodecPriConfigEntry 1 }
       
   hwEntPbxTrkGrpCodecPriIndex OBJECT-TYPE
     SYNTAX      Integer32(0..7)
     MAX-ACCESS  not-accessible
     STATUS      current
     DESCRIPTION
         "
         Indicates the code priority index.
         "
     ::= { hwEntPbxTrkGrpCodecPriConfigEntry 2 }
       
       
   hwEntPbxTrkGrpCodecPriCodec OBJECT-TYPE
     SYNTAX      Integer32(0..255)
     MAX-ACCESS  read-write
     STATUS      current
     DESCRIPTION
         "
         Indicates the codec.
         "
     ::= { hwEntPbxTrkGrpCodecPriConfigEntry 3 }
       
   hwEntPbxTrkGrpCodecPriPt OBJECT-TYPE
     SYNTAX      Integer32(0..255)
     MAX-ACCESS  read-write
     STATUS      current
     DESCRIPTION
         "
         Indicates the packetization time.
         "
     ::= { hwEntPbxTrkGrpCodecPriConfigEntry 4 }
     
   --==============================================================     

   hwEntPbxTrkGrpCodecPriRunningTable OBJECT-TYPE
     SYNTAX      SEQUENCE OF HwEntPbxTrkGrpCodecPriRunningEntry
     MAX-ACCESS  not-accessible
     STATUS      current
     DESCRIPTION
       "
       A list of hwEntPbxTrkGrpCodecPriRunningTable objects.
       "
     ::= { hwEntVoicePbxMIB 47 }

   hwEntPbxTrkGrpCodecPriRunningEntry OBJECT-TYPE
     SYNTAX      HwEntPbxTrkGrpCodecPriRunningEntry
     MAX-ACCESS  not-accessible
     STATUS      current
     DESCRIPTION
       "A list of hwEntPbxTrkGrpCodecPriRunningTable objects."
     INDEX    {
                 hwEntPbxTrkGrpCodecPriRunningTrkGrpName,
                 hwEntPbxTrkGrpCodecPriRunningIndex        
              }
     ::= { hwEntPbxTrkGrpCodecPriRunningTable 1 }
     
   HwEntPbxTrkGrpCodecPriRunningEntry ::=
     SEQUENCE
     {
        hwEntPbxTrkGrpCodecPriRunningTrkGrpName                DisplayString,
        hwEntPbxTrkGrpCodecPriRunningIndex                     Integer32,
        hwEntPbxTrkGrpCodecPriRunningCodec                     Integer32,
        hwEntPbxTrkGrpCodecPriRunningPt                        Integer32
     }  
    
   hwEntPbxTrkGrpCodecPriRunningTrkGrpName OBJECT-TYPE
     SYNTAX      DisplayString(SIZE (1..32))
     MAX-ACCESS  not-accessible
     STATUS      current
     DESCRIPTION
         "
         Indicates the trunk group name.
         "
    ::= { hwEntPbxTrkGrpCodecPriRunningEntry 1 }
       
   hwEntPbxTrkGrpCodecPriRunningIndex OBJECT-TYPE
     SYNTAX      Integer32(0..7)
     MAX-ACCESS  not-accessible
     STATUS      current
     DESCRIPTION
         "
         Indicates the code priority index.
         "
     ::= { hwEntPbxTrkGrpCodecPriRunningEntry 2 }
       
       
   hwEntPbxTrkGrpCodecPriRunningCodec OBJECT-TYPE
     SYNTAX      Integer32(0..255)
     MAX-ACCESS  read-only
     STATUS      current
     DESCRIPTION
         "
         Indicates the codec.
         "
     ::= { hwEntPbxTrkGrpCodecPriRunningEntry 3 }
       
   hwEntPbxTrkGrpCodecPriRunningPt OBJECT-TYPE
     SYNTAX      Integer32(0..255)
     MAX-ACCESS  read-only
     STATUS      current
     DESCRIPTION
         "
         Indicates the packetization time.
         "
     ::= { hwEntPbxTrkGrpCodecPriRunningEntry 4 }
     

   --==============================================================     

   hwEntPbxSIPServerCodecPriConfigTable OBJECT-TYPE
     SYNTAX      SEQUENCE OF HwEntPbxSIPServerCodecPriConfigEntry
     MAX-ACCESS  not-accessible
     STATUS      current
     DESCRIPTION
       "
       A list of hwEntPbxSIPServerCodecPriConfigTable objects.
       "
     ::= { hwEntVoicePbxMIB 48 }

   hwEntPbxSIPServerCodecPriConfigEntry OBJECT-TYPE
     SYNTAX      HwEntPbxSIPServerCodecPriConfigEntry
     MAX-ACCESS  not-accessible
     STATUS      current
     DESCRIPTION
       "A list of hwEntPbxSIPServerCodecPriConfigTable objects."
     INDEX    {
                 hwEntPbxSIPServerCodecPriSIPServerId,
                 hwEntPbxSIPServerCodecPriIndex        
              }
     ::= { hwEntPbxSIPServerCodecPriConfigTable 1 }
     
   HwEntPbxSIPServerCodecPriConfigEntry ::=
     SEQUENCE
     {
        hwEntPbxSIPServerCodecPriSIPServerId               Integer32,
        hwEntPbxSIPServerCodecPriIndex                     Integer32,
        hwEntPbxSIPServerCodecPriCodec                     Integer32,
        hwEntPbxSIPServerCodecPriPt                        Integer32
     }  
    
   hwEntPbxSIPServerCodecPriSIPServerId OBJECT-TYPE
     SYNTAX      Integer32(0..65535)
     MAX-ACCESS  not-accessible
     STATUS      current
     DESCRIPTION
         "
         Indicates the sip server id.
         "
    ::= { hwEntPbxSIPServerCodecPriConfigEntry 1 }
       
   hwEntPbxSIPServerCodecPriIndex OBJECT-TYPE
     SYNTAX      Integer32(0..7)
     MAX-ACCESS  not-accessible
     STATUS      current
     DESCRIPTION
         "
         Indicates the code priority index.
         "
     ::= { hwEntPbxSIPServerCodecPriConfigEntry 2 }
       
       
   hwEntPbxSIPServerCodecPriCodec OBJECT-TYPE
     SYNTAX      Integer32(0..255)
     MAX-ACCESS  read-write
     STATUS      current
     DESCRIPTION
         "
         Indicates the codec.
         "
     ::= { hwEntPbxSIPServerCodecPriConfigEntry 3 }
       
   hwEntPbxSIPServerCodecPriPt OBJECT-TYPE
     SYNTAX      Integer32(0..255)
     MAX-ACCESS  read-write
     STATUS      current
     DESCRIPTION
         "
         Indicates the packetization time.
         "
     ::= { hwEntPbxSIPServerCodecPriConfigEntry 4 }
     
   --==============================================================     

   hwEntPbxSIPServerCodecPriRunningTable OBJECT-TYPE
     SYNTAX      SEQUENCE OF HwEntPbxSIPServerCodecPriRunningEntry
     MAX-ACCESS  not-accessible
     STATUS      current
     DESCRIPTION
         "
         A list of hwEntPbxSIPServerCodecPriRunningTable objects.
         "
     ::= { hwEntVoicePbxMIB 49 }

   hwEntPbxSIPServerCodecPriRunningEntry OBJECT-TYPE
     SYNTAX      HwEntPbxSIPServerCodecPriRunningEntry
     MAX-ACCESS  not-accessible
     STATUS      current
     DESCRIPTION
       "A list of hwEntPbxSIPServerCodecPriRunningTable objects."
     INDEX    {
                 hwEntPbxSIPServerCodecPriRunningSIPServerId,
                 hwEntPbxSIPServerCodecPriRunningIndex        
              }
     ::= { hwEntPbxSIPServerCodecPriRunningTable 1 }
     
   HwEntPbxSIPServerCodecPriRunningEntry ::=
     SEQUENCE
     {
        hwEntPbxSIPServerCodecPriRunningSIPServerId               Integer32,
        hwEntPbxSIPServerCodecPriRunningIndex                     Integer32,
        hwEntPbxSIPServerCodecPriRunningCodec                     Integer32,
        hwEntPbxSIPServerCodecPriRunningPt                        Integer32
     }  
    
   hwEntPbxSIPServerCodecPriRunningSIPServerId OBJECT-TYPE
     SYNTAX      Integer32(0..65535)
     MAX-ACCESS  not-accessible
     STATUS      current
     DESCRIPTION
         "
         Indicates the sip server id.
         "
    ::= { hwEntPbxSIPServerCodecPriRunningEntry 1 }
       
   hwEntPbxSIPServerCodecPriRunningIndex OBJECT-TYPE
     SYNTAX      Integer32(0..7)
     MAX-ACCESS  not-accessible
     STATUS      current
     DESCRIPTION
         "
         Indicates the code priority index.
         "
     ::= { hwEntPbxSIPServerCodecPriRunningEntry 2 }
       
       
   hwEntPbxSIPServerCodecPriRunningCodec OBJECT-TYPE
     SYNTAX      Integer32(0..255)
     MAX-ACCESS  read-only
     STATUS      current
     DESCRIPTION
         "
         Indicates the codec.
         "
     ::= { hwEntPbxSIPServerCodecPriRunningEntry 3 }
       
   hwEntPbxSIPServerCodecPriRunningPt OBJECT-TYPE
     SYNTAX      Integer32(0..255)
     MAX-ACCESS  read-only
     STATUS      current
     DESCRIPTION
         "
         Indicates the packetization time.
         "
     ::= { hwEntPbxSIPServerCodecPriRunningEntry 4 }     
     
   --==============================================================     

   hwEntPbxTrkGrpSoftParaConfigTable OBJECT-TYPE
     SYNTAX      SEQUENCE OF HwEntPbxTrkGrpSoftParaConfigEntry
     MAX-ACCESS  not-accessible
     STATUS      current
     DESCRIPTION
       "
       A list of hwEntPbxTrkGrpSoftParaConfigTable objects.
       "
     ::= { hwEntVoicePbxMIB 50 }

   hwEntPbxTrkGrpSoftParaConfigEntry OBJECT-TYPE
     SYNTAX      HwEntPbxTrkGrpSoftParaConfigEntry
     MAX-ACCESS  not-accessible
     STATUS      current
     DESCRIPTION
       "A list of hwEntPbxTrkGrpSoftParaConfigTable objects."
     INDEX    {
                 hwEntPbxTrkGrpSoftParaTrkGrpName,
                 hwEntPbxTrkGrpSoftParaIndex        
              }
     ::= { hwEntPbxTrkGrpSoftParaConfigTable 1 }
     
   HwEntPbxTrkGrpSoftParaConfigEntry ::=
     SEQUENCE
     {
        hwEntPbxTrkGrpSoftParaTrkGrpName                DisplayString,
        hwEntPbxTrkGrpSoftParaIndex                     Integer32,
        hwEntPbxTrkGrpSoftParaValue                     Integer32
     }  
    
   hwEntPbxTrkGrpSoftParaTrkGrpName OBJECT-TYPE
     SYNTAX      DisplayString(SIZE (1..32))
     MAX-ACCESS  not-accessible
     STATUS      current
     DESCRIPTION
         "
         Indicates the trunk group name.
         "
    ::= { hwEntPbxTrkGrpSoftParaConfigEntry 1 }
       
   hwEntPbxTrkGrpSoftParaIndex OBJECT-TYPE
     SYNTAX      Integer32(0..255)
     MAX-ACCESS  not-accessible
     STATUS      current
     DESCRIPTION
         "
         Indicates the soft parameter index.
         "
     ::= { hwEntPbxTrkGrpSoftParaConfigEntry 2 }
       
       
   hwEntPbxTrkGrpSoftParaValue OBJECT-TYPE
     SYNTAX      Integer32
     MAX-ACCESS  read-write
     STATUS      current
     DESCRIPTION
         "
         Indicates the soft parameter value.
         "
     ::= { hwEntPbxTrkGrpSoftParaConfigEntry 3 }

   --==============================================================     

   hwEntPbxTrkGrpSoftParaRunningTable OBJECT-TYPE
     SYNTAX      SEQUENCE OF HwEntPbxTrkGrpSoftParaRunningEntry
     MAX-ACCESS  not-accessible
     STATUS      current
     DESCRIPTION
       "
       A list of hwEntPbxTrkGrpSoftParaRunningTable objects.
       "
     ::= { hwEntVoicePbxMIB 51 }

   hwEntPbxTrkGrpSoftParaRunningEntry OBJECT-TYPE
     SYNTAX      HwEntPbxTrkGrpSoftParaRunningEntry
     MAX-ACCESS  not-accessible
     STATUS      current
     DESCRIPTION
       "A list of hwEntPbxTrkGrpSoftParaRunningTable objects."
     INDEX    {
                 hwEntPbxTrkGrpSoftParaRunningTrkGrpName,
                 hwEntPbxTrkGrpSoftParaRunningIndex        
              }
     ::= { hwEntPbxTrkGrpSoftParaRunningTable 1 }
     
   HwEntPbxTrkGrpSoftParaRunningEntry ::=
     SEQUENCE
     {
        hwEntPbxTrkGrpSoftParaRunningTrkGrpName                DisplayString,
        hwEntPbxTrkGrpSoftParaRunningIndex                     Integer32,
        hwEntPbxTrkGrpSoftParaRunningValue                     Integer32
     }  
    
   hwEntPbxTrkGrpSoftParaRunningTrkGrpName OBJECT-TYPE
     SYNTAX      DisplayString(SIZE (1..32))
     MAX-ACCESS  not-accessible
     STATUS      current
     DESCRIPTION
         "
         Indicates the trunk group name.
         "
    ::= { hwEntPbxTrkGrpSoftParaRunningEntry 1 }
       
   hwEntPbxTrkGrpSoftParaRunningIndex OBJECT-TYPE
     SYNTAX      Integer32(0..255)
     MAX-ACCESS  not-accessible
     STATUS      current
     DESCRIPTION
         "
         Indicates the soft parameter index.
         "
     ::= { hwEntPbxTrkGrpSoftParaRunningEntry 2 }
       
       
   hwEntPbxTrkGrpSoftParaRunningValue OBJECT-TYPE
     SYNTAX      Integer32
     MAX-ACCESS  read-only
     STATUS      current
     DESCRIPTION
         "
         Indicates the soft parameter value.
         "
     ::= { hwEntPbxTrkGrpSoftParaRunningEntry 3 }

   --==============================================================     

   hwEntPbxSIPServerSoftParaConfigTable OBJECT-TYPE
     SYNTAX      SEQUENCE OF HwEntPbxSIPServerSoftParaConfigEntry
     MAX-ACCESS  not-accessible
     STATUS      current
     DESCRIPTION
       "
       A list of hwEntPbxSIPServerSoftParaConfigTable objects.
       "
     ::= { hwEntVoicePbxMIB 52 }

   hwEntPbxSIPServerSoftParaConfigEntry OBJECT-TYPE
     SYNTAX      HwEntPbxSIPServerSoftParaConfigEntry
     MAX-ACCESS  not-accessible
     STATUS      current
     DESCRIPTION
       "A list of hwEntPbxSIPServerSoftParaConfigTable objects."
     INDEX    {
                 hwEntPbxSIPServerSoftParaSIPServerId,
                 hwEntPbxSIPServerSoftParaIndex        
              }
     ::= { hwEntPbxSIPServerSoftParaConfigTable 1 }
     
   HwEntPbxSIPServerSoftParaConfigEntry ::=
     SEQUENCE
     {
        hwEntPbxSIPServerSoftParaSIPServerId               Integer32,
        hwEntPbxSIPServerSoftParaIndex                     Integer32,
        hwEntPbxSIPServerSoftParaValue                     Integer32
     }  
    
   hwEntPbxSIPServerSoftParaSIPServerId OBJECT-TYPE
     SYNTAX      Integer32(0..65535)
     MAX-ACCESS  not-accessible
     STATUS      current
     DESCRIPTION
         "
         Indicates the sip server id.
         "
    ::= { hwEntPbxSIPServerSoftParaConfigEntry 1 }
       
   hwEntPbxSIPServerSoftParaIndex OBJECT-TYPE
     SYNTAX      Integer32(0..255)
     MAX-ACCESS  not-accessible
     STATUS      current
     DESCRIPTION
         "
         Indicates the soft parameter index.
         "
     ::= { hwEntPbxSIPServerSoftParaConfigEntry 2 }
       
       
   hwEntPbxSIPServerSoftParaValue OBJECT-TYPE
     SYNTAX      Integer32
     MAX-ACCESS  read-write
     STATUS      current
     DESCRIPTION
         "
         Indicates the soft parameter value.
         "
     ::= { hwEntPbxSIPServerSoftParaConfigEntry 3 }
     
   --==============================================================     

   hwEntPbxSIPServerSoftParaRunningTable OBJECT-TYPE
     SYNTAX      SEQUENCE OF HwEntPbxSIPServerSoftParaRunningEntry
     MAX-ACCESS  not-accessible
     STATUS      current
     DESCRIPTION
       "
       A list of hwEntPbxSIPServerSoftParaRunningTable objects.
       "
     ::= { hwEntVoicePbxMIB 53 }

   hwEntPbxSIPServerSoftParaRunningEntry OBJECT-TYPE
     SYNTAX      HwEntPbxSIPServerSoftParaRunningEntry
     MAX-ACCESS  not-accessible
     STATUS      current
     DESCRIPTION
       "A list of hwEntPbxSIPServerSoftParaRunningTable objects."
     INDEX    {
                 hwEntPbxSIPServerSoftParaRunningSIPServerId,
                 hwEntPbxSIPServerSoftParaRunningIndex        
              }
     ::= { hwEntPbxSIPServerSoftParaRunningTable 1 }
     
   HwEntPbxSIPServerSoftParaRunningEntry ::=
     SEQUENCE
     {
        hwEntPbxSIPServerSoftParaRunningSIPServerId               Integer32,
        hwEntPbxSIPServerSoftParaRunningIndex                     Integer32,
        hwEntPbxSIPServerSoftParaRunningValue                     Integer32
     }  
    
   hwEntPbxSIPServerSoftParaRunningSIPServerId OBJECT-TYPE
     SYNTAX      Integer32(0..65535)
     MAX-ACCESS  not-accessible
     STATUS      current
     DESCRIPTION
         "
         Indicates the sip server id.
         "
    ::= { hwEntPbxSIPServerSoftParaRunningEntry 1 }
       
   hwEntPbxSIPServerSoftParaRunningIndex OBJECT-TYPE
     SYNTAX      Integer32(0..255)
     MAX-ACCESS  not-accessible
     STATUS      current
     DESCRIPTION
         "
         Indicates the soft parameter index.
         "
     ::= { hwEntPbxSIPServerSoftParaRunningEntry 2 }
       
       
   hwEntPbxSIPServerSoftParaRunningValue OBJECT-TYPE
     SYNTAX      Integer32
     MAX-ACCESS  read-only
     STATUS      current
     DESCRIPTION
         "
         Indicates the soft parameter value.
         "
     ::= { hwEntPbxSIPServerSoftParaRunningEntry 3 }

 --==

    hwEntPbxConfHallConfigTable OBJECT-TYPE
     SYNTAX      SEQUENCE OF HwEntPbxConfHallConfigEntry
     MAX-ACCESS  not-accessible
     STATUS      current
     DESCRIPTION
         "
         This table is used to config the conference hall.
         "
     ::= { hwEntVoicePbxMIB 54 }
 
   hwEntPbxConfHallConfigEntry OBJECT-TYPE
     SYNTAX      HwEntPbxConfHallConfigEntry
     MAX-ACCESS  not-accessible
     STATUS      current
     DESCRIPTION
         "
         This table is used to config the conference hall.
         "
     INDEX    {  
                hwEntPbxConfHallName
              }
     ::= { hwEntPbxConfHallConfigTable 1 }
 
   HwEntPbxConfHallConfigEntry ::=
     SEQUENCE
     {
       hwEntPbxConfHallName                         DisplayString,
       hwEntPbxConfHallRowStatus                    RowStatus,
       hwEntPbxConfHallEnterpriseName               DisplayString,
       hwEntPbxConfAccessCodeDnSet                  DisplayString,
       hwEntPbxConfAccessCodeCountryCode            DisplayString,
       hwEntPbxConfAccessCodeAreaCode               DisplayString,
       hwEntPbxConfAccessCodeTelNo                  DisplayString,
       hwEntPbxConfAccessCodeCentrexName            DisplayString,
       hwEntPbxConfAccessCodeCentrexTelno           DisplayString,
       hwEntPbxConfHallMaxAllowRegTotal             Integer32,
       hwEntPbxConfHallMaxOnlineRoomTotal           Integer32,
       hwEntPbxConfHallMaxOnlineAttendeeTotal       Integer32,
       hwEntPbxConfHallCurRegistedNum               Integer32,
       hwEntPbxConfHallCurOnlineRoomNum             Integer32,
       hwEntPbxConfHallCurOnlineAttendeeNum         Integer32,
       hwEntPbxConfPortalNaviMenuName               DisplayString,
       hwEntPbxInviteeJoinConfNaviMenuName          DisplayString,    
       hwEntPbxConRemindBeforefExpiryNaviMenuName   DisplayString,  
       hwEntPbxLeaveConfNaviMenuName                DisplayString,
       hwEntPbxConfOperNaviMenuName                 DisplayString
     }
     
   hwEntPbxConfHallName OBJECT-TYPE
     SYNTAX      DisplayString(SIZE (1..32))
     MAX-ACCESS  not-accessible
     STATUS      current
     DESCRIPTION
         "
         Indicates the conference hall name.
         "
     ::= { hwEntPbxConfHallConfigEntry 1 }

   hwEntPbxConfHallRowStatus OBJECT-TYPE
     SYNTAX      RowStatus
     MAX-ACCESS  read-create
     STATUS      current
     DESCRIPTION
         "
         RowStatus
         active(1)
         notInService(2)
         notReady(3)
         createAndGo(4)
         createAndWait(5)
         destroy(6)
         "
     ::= { hwEntPbxConfHallConfigEntry 2 }
     
   hwEntPbxConfHallEnterpriseName OBJECT-TYPE
     SYNTAX      DisplayString(SIZE (1..32))
     MAX-ACCESS  read-create
     STATUS      current
     DESCRIPTION
         "
         Indicates the enterprise of conference hall.
         "
     ::= { hwEntPbxConfHallConfigEntry 3 }
     
   hwEntPbxConfAccessCodeDnSet OBJECT-TYPE
     SYNTAX      DisplayString(SIZE (1..32))
     MAX-ACCESS  read-create
     STATUS      current
     DESCRIPTION
         "
         Indicates the dnset of conference hall.
         "
     ::= { hwEntPbxConfHallConfigEntry 4 }
     
   hwEntPbxConfAccessCodeCountryCode OBJECT-TYPE
     SYNTAX      DisplayString(SIZE (1..4))
     MAX-ACCESS  read-create
     STATUS      current
     DESCRIPTION
         "
         Indicates the country code of conference hall access code.
         "
     ::= { hwEntPbxConfHallConfigEntry 5 }
     
   hwEntPbxConfAccessCodeAreaCode OBJECT-TYPE
     SYNTAX      DisplayString(SIZE (1..8))
     MAX-ACCESS  read-create
     STATUS      current
     DESCRIPTION
         "
         Indicates the area code of conference hall access code.
         "
     ::= { hwEntPbxConfHallConfigEntry 6 }
     
   hwEntPbxConfAccessCodeTelNo OBJECT-TYPE
     SYNTAX      DisplayString(SIZE (1..24))
     MAX-ACCESS  read-create
     STATUS      current
     DESCRIPTION
         "
         Indicates the telephone number of conference hall access code.
         "
     ::= { hwEntPbxConfHallConfigEntry 7 }
     
   hwEntPbxConfAccessCodeCentrexName OBJECT-TYPE
     SYNTAX      DisplayString(SIZE (1..32))
     MAX-ACCESS  read-create
     STATUS      current
     DESCRIPTION
         "
         Indicates the centrex name of conference hall access code.
         "
     ::= { hwEntPbxConfHallConfigEntry 8 } 
     
   hwEntPbxConfAccessCodeCentrexTelno OBJECT-TYPE
     SYNTAX      DisplayString(SIZE (1..8))
     MAX-ACCESS  read-create
     STATUS      current
     DESCRIPTION
         "
         Indicates the centrex number of conference hall access code.
         "
     ::= { hwEntPbxConfHallConfigEntry 9 } 
     
   hwEntPbxConfHallMaxAllowRegTotal OBJECT-TYPE
     SYNTAX      Integer32
     MAX-ACCESS  read-write
     STATUS      current
     DESCRIPTION
         "
         Indicates the max reg conference number of conference hall.
         "
     ::= { hwEntPbxConfHallConfigEntry 10 }
     
   hwEntPbxConfHallMaxOnlineRoomTotal OBJECT-TYPE
     SYNTAX      Integer32
     MAX-ACCESS  read-write
     STATUS      current
     DESCRIPTION
         "
         Indicates the max online room number of conference hall.
         "
     ::= { hwEntPbxConfHallConfigEntry 11 }

   hwEntPbxConfHallMaxOnlineAttendeeTotal OBJECT-TYPE
     SYNTAX      Integer32
     MAX-ACCESS  read-write
     STATUS      current
     DESCRIPTION
         "
         Indicates the max online attendee number of conference hall.
         "
     ::= { hwEntPbxConfHallConfigEntry 12 }

   hwEntPbxConfHallCurRegistedNum OBJECT-TYPE
     SYNTAX      Integer32
     MAX-ACCESS  read-only
     STATUS      current
     DESCRIPTION
         "
         Indicates the current registed conference number of conference hall.
         "
     ::= { hwEntPbxConfHallConfigEntry 13 }

   hwEntPbxConfHallCurOnlineRoomNum OBJECT-TYPE
     SYNTAX      Integer32
     MAX-ACCESS  read-only
     STATUS      current
     DESCRIPTION
         "
         Indicates the online room number of conference hall.
         "
     ::= { hwEntPbxConfHallConfigEntry 14 }
     
   hwEntPbxConfHallCurOnlineAttendeeNum OBJECT-TYPE
     SYNTAX      Integer32
     MAX-ACCESS  read-only
     STATUS      current
     DESCRIPTION
         "
         Indicates the current online attendee number of conference hall.
         "
     ::= { hwEntPbxConfHallConfigEntry 15 }
     
   hwEntPbxConfPortalNaviMenuName OBJECT-TYPE
     SYNTAX      DisplayString(SIZE (1..32))
     MAX-ACCESS  read-create
     STATUS      current
     DESCRIPTION
         "
         Indicates the conference portal navi menu name.
         "
     ::= { hwEntPbxConfHallConfigEntry 16 } 
     
   hwEntPbxInviteeJoinConfNaviMenuName OBJECT-TYPE
     SYNTAX      DisplayString(SIZE (1..32))
     MAX-ACCESS  read-create
     STATUS      current
     DESCRIPTION
         "
         Indicates the join conference navi menu name.
         "
     ::= { hwEntPbxConfHallConfigEntry 17 } 
     
   hwEntPbxConRemindBeforefExpiryNaviMenuName OBJECT-TYPE
     SYNTAX      DisplayString(SIZE (1..32))
     MAX-ACCESS  read-create
     STATUS      current
     DESCRIPTION
         "
         Indicates the remind navi menu name beforef expiry.
         "
     ::= { hwEntPbxConfHallConfigEntry 18 }
     
   hwEntPbxLeaveConfNaviMenuName OBJECT-TYPE
     SYNTAX      DisplayString(SIZE (1..32))
     MAX-ACCESS  read-create
     STATUS      current
     DESCRIPTION
         "
         Indicates the leave conference navi menu name.
         "
     ::= { hwEntPbxConfHallConfigEntry 19 }  
     
   hwEntPbxConfOperNaviMenuName OBJECT-TYPE
     SYNTAX      DisplayString(SIZE (1..32))
     MAX-ACCESS  read-create
     STATUS      current
     DESCRIPTION
         "
         Indicates the conference operate navi menu name.
         "
     ::= { hwEntPbxConfHallConfigEntry 20 }  
     
     --==
     
   hwEntPbxConfRegConfigTable OBJECT-TYPE
     SYNTAX      SEQUENCE OF HwEntPbxConfRegConfigEntry
     MAX-ACCESS  not-accessible
     STATUS      current
     DESCRIPTION
         "
         This table is used to register conference.
         "
     ::= { hwEntVoicePbxMIB 55 }
 
   hwEntPbxConfRegConfigEntry OBJECT-TYPE
     SYNTAX      HwEntPbxConfRegConfigEntry
     MAX-ACCESS  not-accessible
     STATUS      current
     DESCRIPTION
         "
         This table is used to register conference.
         "
     INDEX    {  
                hwEntPbxConfRegId
              }
     ::= { hwEntPbxConfRegConfigTable 1 }
     
   HwEntPbxConfRegConfigEntry ::=
     SEQUENCE
     {
       hwEntPbxConfRegId                            Integer32,
       hwEntPbxConfRegRowStatus                     RowStatus,
       hwEntPbxConfRegHallName                      DisplayString,
       hwEntPbxConfBeginDate                        DisplayString,
       hwEntPbxConfBeginTime                        DisplayString,
       hwEntPbxConfIsInstant                        INTEGER,
       hwEntPbxConfDuration                         Integer32,
       hwEntPbxConfAttendeeNum                      Integer32,
       hwEntPbxConfGuestPassword                    DisplayString,
       hwEntPbxConfChaimanPassword                  DisplayString,
       hwEntPbxConfRegName                          DisplayString,
       hwEntPbxConfDesc                             DisplayString,
       hwEntPbxConfLanguageType                     INTEGER,
       hwEntPbxConfEntryToneType                    INTEGER,
       hwEntPbxConfExitToneType                     INTEGER
     }   
     
   hwEntPbxConfRegId OBJECT-TYPE
     SYNTAX      Integer32
     MAX-ACCESS  not-accessible
     STATUS      current
     DESCRIPTION
         "
         Indicates the register id.
         "
     ::= { hwEntPbxConfRegConfigEntry 1}  
     
   hwEntPbxConfRegRowStatus OBJECT-TYPE
     SYNTAX      RowStatus
     MAX-ACCESS  read-create
     STATUS      current
     DESCRIPTION
         "
         RowStatus
         active(1)
         notInService(2)
         notReady(3)
         createAndGo(4)
         createAndWait(5)
         destroy(6)
         "
     ::= { hwEntPbxConfRegConfigEntry 2 }  
     
   hwEntPbxConfRegHallName OBJECT-TYPE
     SYNTAX      DisplayString(SIZE (1..32))
     MAX-ACCESS  read-create
     STATUS      current
     DESCRIPTION
         "
         Indicates the confer hall name.
         "
     ::= { hwEntPbxConfRegConfigEntry 3}  
          
   hwEntPbxConfBeginDate OBJECT-TYPE
     SYNTAX      DisplayString(SIZE (0..10))
     MAX-ACCESS  read-create
     STATUS      current
     DESCRIPTION
         "
         Indicates the begin data of conference.
         format: YYYY-MM-DD
         "
     ::= { hwEntPbxConfRegConfigEntry 4 }  
     
   hwEntPbxConfBeginTime OBJECT-TYPE
     SYNTAX      DisplayString(SIZE (0..10))
     MAX-ACCESS  read-create
     STATUS      current
     DESCRIPTION
         "
         Indicates the begin time of conference.
         format: HH:MM:SS 
         "
     ::= { hwEntPbxConfRegConfigEntry 5 } 
     
   hwEntPbxConfIsInstant  OBJECT-TYPE
     SYNTAX      INTEGER {no(1), yes(2)}
     MAX-ACCESS  read-create
     STATUS      current
     DESCRIPTION
         "
         Indicates the whether the conference is instant conference.
         "
     ::= { hwEntPbxConfRegConfigEntry 6 } 
     
   hwEntPbxConfDuration  OBJECT-TYPE
     SYNTAX      Integer32
     MAX-ACCESS  read-create
     STATUS      current
     DESCRIPTION
         "
         Indicates the conference duration.
         "
     ::= { hwEntPbxConfRegConfigEntry 7 } 
     
   hwEntPbxConfAttendeeNum   OBJECT-TYPE
     SYNTAX      Integer32 (3..32)
     MAX-ACCESS  read-create
     STATUS      current
     DESCRIPTION
         "
         Indicates the conference attendee number.
         "
     ::= { hwEntPbxConfRegConfigEntry 8 } 
     
   hwEntPbxConfGuestPassword  OBJECT-TYPE
     SYNTAX      DisplayString(SIZE (0..6))
     MAX-ACCESS  read-create
     STATUS      current
     DESCRIPTION
         "
         Indicates the guest's password.
         "
     ::= { hwEntPbxConfRegConfigEntry 9 }  
     
   hwEntPbxConfChaimanPassword  OBJECT-TYPE
     SYNTAX      DisplayString(SIZE (0..6))
     MAX-ACCESS  read-create
     STATUS      current
     DESCRIPTION
         "
         Indicates the chaiman's password.
         "
     ::= { hwEntPbxConfRegConfigEntry 10 }  
     
   hwEntPbxConfRegName OBJECT-TYPE
     SYNTAX      DisplayString(SIZE (0..32))
     MAX-ACCESS  read-create
     STATUS      current
     DESCRIPTION
         "
         Indicates the conference registrant name.
         "
     ::= { hwEntPbxConfRegConfigEntry 11 }  
     
   hwEntPbxConfDesc OBJECT-TYPE
     SYNTAX      DisplayString(SIZE (0..32))
     MAX-ACCESS  read-create
     STATUS      current
     DESCRIPTION
         "
         Indicates the conference description.
         "
     ::= { hwEntPbxConfRegConfigEntry 12 }  
     
   hwEntPbxConfLanguageType OBJECT-TYPE
     SYNTAX      INTEGER {native(1), international(2)}
     MAX-ACCESS  read-create
     STATUS      current
     DESCRIPTION
         "
         Indicates the conference language type.
         "
     ::= { hwEntPbxConfRegConfigEntry 13 }
     
   hwEntPbxConfEntryToneType OBJECT-TYPE
     SYNTAX      INTEGER {mute(1), entryTone(2)}
     MAX-ACCESS  read-create
     STATUS      current
     DESCRIPTION
         "
         Indicates the conference entry tone.
         default: entryTone(2)
         "
     ::= { hwEntPbxConfRegConfigEntry 14 }
            
   hwEntPbxConfExitToneType OBJECT-TYPE
     SYNTAX      INTEGER {mute(1), exitTone(2)}
     MAX-ACCESS  read-create
     STATUS      current
     DESCRIPTION
         "
         Indicates the conference exit tone.
         default: exitTone(2)
         "
     ::= { hwEntPbxConfRegConfigEntry 15 }

   --==
     
   hwEntPbxConfOperTable OBJECT-TYPE
     SYNTAX      SEQUENCE OF HwEntPbxConfOperEntry
     MAX-ACCESS  not-accessible
     STATUS      current
     DESCRIPTION
         "
         This table is used to operate the conference.
         "
     ::= { hwEntVoicePbxMIB 56 }
 
   hwEntPbxConfOperEntry OBJECT-TYPE
     SYNTAX      HwEntPbxConfOperEntry
     MAX-ACCESS  not-accessible
     STATUS      current
     DESCRIPTION
         "
         This table is used to operate the conference.
         "
     INDEX    {  
                hwEntPbxConfOperId
              }
     ::= { hwEntPbxConfOperTable 1 }
     
   HwEntPbxConfOperEntry ::=
     SEQUENCE
     {
       hwEntPbxConfOperId                           Integer32,
       hwEntPbxConfOperType                         INTEGER,
       hwEntPbxConfDelayLen                         Integer32,
       hwEntPbxConfStatus                           INTEGER
     }        
     
   hwEntPbxConfOperId OBJECT-TYPE
     SYNTAX      Integer32
     MAX-ACCESS  not-accessible
     STATUS      current
     DESCRIPTION
         "
         Indicates the conference id.
         "
     ::= { hwEntPbxConfOperEntry 1 }
     
   hwEntPbxConfOperType OBJECT-TYPE
     SYNTAX      INTEGER {cancel(1), close(2), lock(3), unlock(4), 
                          delay(5), mute(6), cancelMute(7)}
     MAX-ACCESS  read-create
     STATUS      current
     DESCRIPTION
         "
         Indicates the conference operate type.
         "
     ::= { hwEntPbxConfOperEntry 2 }     
     
   hwEntPbxConfDelayLen OBJECT-TYPE
     SYNTAX      Integer32
     MAX-ACCESS  read-create
     STATUS      current
     DESCRIPTION
         "
         Indicates the conference delay time.
         unit: min
         "
     ::= { hwEntPbxConfOperEntry 3 }  
     
   hwEntPbxConfStatus OBJECT-TYPE
     SYNTAX      INTEGER {beforeStart(1), processing(2), delay(3), lock(4), 
                          mute(5), close(6), forceClose(7)}
     MAX-ACCESS  read-only
     STATUS      current
     DESCRIPTION
         "
         Indicates the conference status.
         "
     ::= { hwEntPbxConfOperEntry 4 }  
     
   --==
     
   hwEntPbxConfAttendeeOperTable OBJECT-TYPE
     SYNTAX      SEQUENCE OF HwEntPbxConfAttendeeOperEntry
     MAX-ACCESS  not-accessible
     STATUS      current
     DESCRIPTION
         "
         This table is used to operate the conference by attendee.
         "
     ::= { hwEntVoicePbxMIB 57 }
 
   hwEntPbxConfAttendeeOperEntry OBJECT-TYPE
     SYNTAX      HwEntPbxConfAttendeeOperEntry
     MAX-ACCESS  not-accessible
     STATUS      current
     DESCRIPTION
         "
         This table is used to operate the conference by attendee.
         "
     INDEX    {  
                hwEntPbxConfAttendeeOperId
              }
     ::= { hwEntPbxConfAttendeeOperTable 1 }
     
   HwEntPbxConfAttendeeOperEntry ::=
     SEQUENCE
     {
       hwEntPbxConfAttendeeOperId                   Integer32,
       hwEntPbxConfAttendeeTelNo                    DisplayString,
       hwEntPbxConfAttendeeType                     INTEGER,
       hwEntPbxConfAttendeeOperType                 INTEGER,
       hwEntPbxConfAttendeeStatus                   INTEGER
     }      
   
   hwEntPbxConfAttendeeOperId OBJECT-TYPE
     SYNTAX      Integer32
     MAX-ACCESS  not-accessible
     STATUS      current
     DESCRIPTION
         "
         Indicates the conference id.
         "
     ::= { hwEntPbxConfAttendeeOperEntry 1 }
     
   hwEntPbxConfAttendeeTelNo OBJECT-TYPE
     SYNTAX      DisplayString(SIZE (1..44))
     MAX-ACCESS  read-create
     STATUS      current
     DESCRIPTION
         "
         Indicates the attendee telephone number.
         "
     ::= { hwEntPbxConfAttendeeOperEntry 2 }     
     
   hwEntPbxConfAttendeeType OBJECT-TYPE
     SYNTAX      INTEGER {attendee(1), chairman(2)}
     MAX-ACCESS  read-create
     STATUS      current
     DESCRIPTION
         "
         Indicates the attendee type.
         default: attendee(1)
         "
     ::= { hwEntPbxConfAttendeeOperEntry 3 }  
     
   hwEntPbxConfAttendeeOperType OBJECT-TYPE
     SYNTAX      INTEGER {invite(1), cancelInvite(2), setChairman(3), mute(4), 
                          cancelMute(5), close(6), forceClose(7)}
     MAX-ACCESS  read-create
     STATUS      current
     DESCRIPTION
         "
         Indicates the attendee operate type.
         "
     ::= { hwEntPbxConfAttendeeOperEntry 4 }   
     
   hwEntPbxConfAttendeeStatus OBJECT-TYPE
     SYNTAX      INTEGER {call(1), busy(2), ring(3), noAnswer(4)}
     MAX-ACCESS  read-create
     STATUS      current
     DESCRIPTION
         "
         Indicates the attendee status.
         "
     ::= { hwEntPbxConfAttendeeOperEntry 5 }    

  --==============================================================
     
   hwEntPbxSignalTraceConfigTable OBJECT-TYPE
     SYNTAX      SEQUENCE OF HwEntPbxSignalTraceConfigEntry
     MAX-ACCESS  not-accessible
     STATUS      current
     DESCRIPTION
       "
       Indicates the trace configuration table of signal.
       "
     ::= { hwEntVoicePbxMIB 58 }     
     
   hwEntPbxSignalTraceConfigEntry OBJECT-TYPE
     SYNTAX      HwEntPbxSignalTraceConfigEntry
     MAX-ACCESS  not-accessible
     STATUS      current
     DESCRIPTION
       ""
     INDEX    {  
               hwEntPbxSignalTraceTaskNo
              }
     ::= { hwEntPbxSignalTraceConfigTable 1 }
 
   HwEntPbxSignalTraceConfigEntry ::=
     SEQUENCE
     {
       hwEntPbxSignalTraceTaskNo             Integer32,       
       hwEntPbxSignalTraceRowStatus          RowStatus,
       hwEntPbxSignalTraceTaskID             Unsigned32,
       hwEntPbxSignalTraceTarget             INTEGER,
       hwEntPbxSignalTraceSipIp              IpAddress,
       hwEntPbxSignalTraceTrkIndex           Integer32,
       hwEntPbxSignalTraceStartTS            Integer32,
       hwEntPbxSignalTraceEndTS              Integer32,   
       hwEntPbxSignalTraceDn                 DisplayString,
       hwEntPbxSignalTraceEntName            DisplayString,
       hwEntPbxSignalTraceFilter             Integer32,
       hwEntPbxSignalTraceSequence           Unsigned32,    
       hwEntPbxSignalTraceServerIp           IpAddress, 
       hwEntPbxSignalTraceServerPort         Integer32,   
       hwEntPbxSignalTraceServerUserName     DisplayString,
       hwEntPbxSignalTraceServerPassword     DisplayString
     }

   hwEntPbxSignalTraceTaskNo OBJECT-TYPE
     SYNTAX Integer32
     MAX-ACCESS not-accessible
     STATUS current
     DESCRIPTION
         "Indicates the task number of signal trace."
     ::= { hwEntPbxSignalTraceConfigEntry 1 } 

   hwEntPbxSignalTraceRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxSignalTraceConfigEntry 2 }
                   
   hwEntPbxSignalTraceTaskID OBJECT-TYPE
     SYNTAX      Unsigned32
     MAX-ACCESS  read-create
     STATUS      current
     DESCRIPTION
         "Indicates the task ID of signal trace."
     ::= { hwEntPbxSignalTraceConfigEntry 3 }
     
   hwEntPbxSignalTraceTarget OBJECT-TYPE
     SYNTAX      INTEGER{sip(1), pra(2), r2(3), user(4), bra(5)}
     MAX-ACCESS  read-create
     STATUS      current
     DESCRIPTION
         "
         Indicates the target of signal trace.
         Options:
         sip(1) -Sip protocol
         pra(2) -Pra protocol
         r2(3)  -R2 protocol
         user(4) -User trace
         bra(5) -Bra protocol
         Default: sip(1)
         "
     ::= { hwEntPbxSignalTraceConfigEntry 4 }     

   hwEntPbxSignalTraceSipIp OBJECT-TYPE
     SYNTAX IpAddress
     MAX-ACCESS read-create
     STATUS current
     DESCRIPTION
         "Indicates the ip address of peer sip point."
     ::= { hwEntPbxSignalTraceConfigEntry 5 }

   hwEntPbxSignalTraceTrkIndex OBJECT-TYPE
     SYNTAX Integer32
     MAX-ACCESS read-create
     STATUS current
     DESCRIPTION
         "
         Indicates the index of physical trunk.
 	 bits 24-31:  slot index
 	 bits 23-16: subcard index
 	 bits 15-8: port index
 	 bits 7-0:  time slot
         "
     ::= { hwEntPbxSignalTraceConfigEntry 6 }

   hwEntPbxSignalTraceStartTS OBJECT-TYPE
     SYNTAX Integer32(0..65535)
     MAX-ACCESS read-create
     STATUS current
     DESCRIPTION
         "Indicates the start ts of r2 signal trace."
     ::= { hwEntPbxSignalTraceConfigEntry 7 }
     
   hwEntPbxSignalTraceEndTS OBJECT-TYPE
     SYNTAX Integer32(0..65535)
     MAX-ACCESS read-create
     STATUS current
     DESCRIPTION
         "Indicates the end ts of r2 signal trace."
     ::= { hwEntPbxSignalTraceConfigEntry 8 }     

   hwEntPbxSignalTraceDn OBJECT-TYPE
     SYNTAX DisplayString(SIZE (1..16))
     MAX-ACCESS read-create
     STATUS current
     DESCRIPTION
         "Indicates the user number of signal trace."
     ::= { hwEntPbxSignalTraceConfigEntry 9 } 

   hwEntPbxSignalTraceEntName OBJECT-TYPE
     SYNTAX DisplayString(SIZE (1..32))
     MAX-ACCESS read-create
     STATUS current
     DESCRIPTION
         "Indicates the enterprise name of signal trace."
     ::= { hwEntPbxSignalTraceConfigEntry 10 } 
      
   hwEntPbxSignalTraceFilter OBJECT-TYPE
     SYNTAX Integer32(0..65535)
     MAX-ACCESS read-create
     STATUS current
     DESCRIPTION
         "Indicates the filter of signal trace."
     ::= { hwEntPbxSignalTraceConfigEntry 11 } 
                        
   hwEntPbxSignalTraceSequence OBJECT-TYPE
     SYNTAX Unsigned32
     MAX-ACCESS read-create
     STATUS current
     DESCRIPTION
         "Indicates the sequence of signal trace."
     ::= { hwEntPbxSignalTraceConfigEntry 12 }  

   hwEntPbxSignalTraceServerIp OBJECT-TYPE
     SYNTAX IpAddress
     MAX-ACCESS read-create
     STATUS current
     DESCRIPTION
         "Indicates the ip address of the server which receive the signal message."
     ::= { hwEntPbxSignalTraceConfigEntry 13 }

   hwEntPbxSignalTraceServerPort OBJECT-TYPE
     SYNTAX Integer32
     MAX-ACCESS read-create
     STATUS current
     DESCRIPTION
         "Indicates the port id of the server which receive the signal message."
     ::= { hwEntPbxSignalTraceConfigEntry 14 } 

   hwEntPbxSignalTraceServerUserName OBJECT-TYPE
     SYNTAX DisplayString(SIZE (1..32))
     MAX-ACCESS read-create
     STATUS current
     DESCRIPTION
         "Indicates the username of the server which receive the signal message."
     ::= { hwEntPbxSignalTraceConfigEntry 15 }
 
    hwEntPbxSignalTraceServerPassword OBJECT-TYPE
     SYNTAX DisplayString(SIZE (1..32))
     MAX-ACCESS read-create
     STATUS current
     DESCRIPTION
         "Indicates the password of the server which receive the signal message."
     ::= { hwEntPbxSignalTraceConfigEntry 16 }
                                   
  --==============================================================
       
   hwEntPbxMeasureConfigTable OBJECT-TYPE
     SYNTAX      SEQUENCE OF HwEntPbxMeasureConfigEntry
     MAX-ACCESS  not-accessible
     STATUS      current
     DESCRIPTION
       "
       Indicates the configuration table of measurement.
       "
     ::= { hwEntVoicePbxMIB 59 }
   
   hwEntPbxMeasureConfigEntry OBJECT-TYPE
     SYNTAX      HwEntPbxMeasureConfigEntry
     MAX-ACCESS  not-accessible
     STATUS      current
     DESCRIPTION
       ""
     INDEX    {  
               hwEntPbxMeasureUnitID
              }
     ::= { hwEntPbxMeasureConfigTable 1 }
 
   HwEntPbxMeasureConfigEntry ::=
     SEQUENCE
     {
       hwEntPbxMeasureUnitID                       Integer32,
       hwEntPbxMeasureRowStatus                    RowStatus,
       hwEntPbxMeasureTaskID                       Unsigned32,       
       hwEntPbxMeasureName                         DisplayString,
       hwEntPbxMeasureGlobal                       BITS,
       hwEntPbxMeasureIncoming                     BITS,
       hwEntPbxMeasureOutgoing                     BITS,
       hwEntPbxMeasureStartDateTime                OCTET STRING,
       hwEntPbxMeasureEndDateTime                  OCTET STRING,
       hwEntPbxMeasureInterval                     Integer32,       
       hwEntPbxMeasureServerIp                     IpAddress,
       hwEntPbxMeasureServerPort                   Integer32,
       hwEntPbxMeasureServerUserName               DisplayString,
       hwEntPbxMeasureServerPassword               DisplayString
     }

  hwEntPbxMeasureUnitID OBJECT-TYPE
     SYNTAX      Integer32
     MAX-ACCESS  not-accessible
     STATUS      current
     DESCRIPTION
         "Indicates the unit ID of measurement."
     ::= { hwEntPbxMeasureConfigEntry 1 } 
              
   hwEntPbxMeasureRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxMeasureConfigEntry 2 }

  hwEntPbxMeasureTaskID OBJECT-TYPE
     SYNTAX      Unsigned32
     MAX-ACCESS  read-create
     STATUS      current
     DESCRIPTION
         "Indicates the task ID of measurement."
     ::= { hwEntPbxMeasureConfigEntry 3 }  
          
  hwEntPbxMeasureName OBJECT-TYPE
     SYNTAX DisplayString(SIZE (1..23))
     MAX-ACCESS read-create
     STATUS current
     DESCRIPTION
         "Indicates the name of measurement."
     ::= { hwEntPbxMeasureConfigEntry 4 }

  hwEntPbxMeasureGlobal OBJECT-TYPE
     SYNTAX      BITS{bit0(0),bit1(1),bit2(2),bit3(3),bit4(4),bit5(5),
                      bit6(6),bit7(7),bit8(8),bit9(9),bit10(10),
                      bit11(11),bit12(12),bit13(13)}
     MAX-ACCESS  read-create
     STATUS      current
     DESCRIPTION
         "
         Indicates the global value.
         bit0:hm01
         bit1:hm02
         bit2:hm03
         bit3:hm04
         bit4:hm05
         bit5:hm06
         bit6:hm07
         bit7:hm08
         bit8:hm09
         bit9:hm10
         bit10:hm11
         bit11:hm12
         bit12:hm13
         bit13:all
         "
     ::= { hwEntPbxMeasureConfigEntry 5 }

  hwEntPbxMeasureIncoming OBJECT-TYPE
     SYNTAX      BITS{bit0(0),bit1(1),bit2(2),bit3(3),bit4(4),bit5(5),
                      bit6(6),bit7(7),bit8(8),bit9(9),bit10(10),
                      bit11(11),bit12(12),bit13(13)}
     MAX-ACCESS  read-create
     STATUS      current
     DESCRIPTION
         "
         Indicates the incoming value.
         bit0:no used
         bit1:no used
         bit2:no used
         bit3:hm14
         bit4:hm15
         bit5:hm16
         bit6:hm17
         bit7:no used
         bit8:no used
         bit9:no used
         bit10:no used
         bit11:no used
         bit12:no used
         bit13:all
         "
     ::= { hwEntPbxMeasureConfigEntry 6 }

  hwEntPbxMeasureOutgoing OBJECT-TYPE
     SYNTAX      BITS{bit0(0),bit1(1),bit2(2),bit3(3),bit4(4),bit5(5),
                      bit6(6),bit7(7),bit8(8),bit9(9),bit10(10),
                      bit11(11),bit12(12),bit13(13)}
     MAX-ACCESS  read-create
     STATUS      current
     DESCRIPTION
         "
         Indicates the outgoing value.
         bit0:no used
         bit1:no used
         bit2:no used
         bit3:no used
         bit4:no used
         bit5:no used
         bit6:no used
         bit7:hm18   
         bit8:hm19
         bit9:hm20
         bit10:hm21
         bit11:no used
         bit12:no used
         bit13:all
         "
     ::= { hwEntPbxMeasureConfigEntry 7 }

  hwEntPbxMeasureStartDateTime OBJECT-TYPE
     SYNTAX OCTET STRING(SIZE (1..20))
     MAX-ACCESS read-create
     STATUS current
     DESCRIPTION
         "Indicates start datetime of measurement."
     ::= { hwEntPbxMeasureConfigEntry 8 }

  hwEntPbxMeasureEndDateTime OBJECT-TYPE
     SYNTAX OCTET STRING(SIZE (1..20))
     MAX-ACCESS read-create
     STATUS current
     DESCRIPTION
         "Indicates end datetime of measurement."
     ::= { hwEntPbxMeasureConfigEntry 9 }

  hwEntPbxMeasureInterval OBJECT-TYPE
     SYNTAX      Integer32
     MAX-ACCESS  read-create
     STATUS      current
     DESCRIPTION
         "Indicates the interval of measurement."
     ::= { hwEntPbxMeasureConfigEntry 10 } 
     
   hwEntPbxMeasureServerIp OBJECT-TYPE
     SYNTAX IpAddress
     MAX-ACCESS read-create
     STATUS current
     DESCRIPTION
         "Indicates the ip address of the server which receive the measure message."
     ::= { hwEntPbxMeasureConfigEntry 11 }

   hwEntPbxMeasureServerPort OBJECT-TYPE
     SYNTAX Integer32
     MAX-ACCESS read-create
     STATUS current
     DESCRIPTION
         "Indicates the port id of the server which receive the measure message."
     ::= { hwEntPbxMeasureConfigEntry 12 }   

   hwEntPbxMeasureServerUserName OBJECT-TYPE
     SYNTAX DisplayString(SIZE (1..32))
     MAX-ACCESS read-create
     STATUS current
     DESCRIPTION
         "Indicates the username of the server which receive the measure message."
     ::= { hwEntPbxMeasureConfigEntry 13 }
     
   hwEntPbxMeasureServerPassword OBJECT-TYPE
     SYNTAX DisplayString(SIZE (1..32))
     MAX-ACCESS read-create
     STATUS current
     DESCRIPTION
         "Indicates the password of the server which receive the measure message."
     ::= { hwEntPbxMeasureConfigEntry 14 }
         
  --============================================================== 

   hwEntPbxUserStateTraceTable OBJECT IDENTIFIER  ::= { hwEntVoicePbxMIB 60 } 

   hwEntPbxUserStateTraceTotal OBJECT-TYPE
     SYNTAX      Integer32
     MAX-ACCESS  read-only
     STATUS      current
     DESCRIPTION
         "Indicates the number of total user."
     ::= { hwEntPbxUserStateTraceTable 1 }

   hwEntPbxUserStateTraceIdle OBJECT-TYPE
     SYNTAX      Integer32
     MAX-ACCESS  read-only
     STATUS      current
     DESCRIPTION
         "Indicates the number of idle user."
     ::= { hwEntPbxUserStateTraceTable 2 }

   hwEntPbxUserStateTraceBusy OBJECT-TYPE
     SYNTAX      Integer32
     MAX-ACCESS  read-only
     STATUS      current
     DESCRIPTION
         "Indicates the number of busy user."
     ::= { hwEntPbxUserStateTraceTable 3 }

   hwEntPbxUserStateTraceFault OBJECT-TYPE
     SYNTAX      Integer32
     MAX-ACCESS  read-only
     STATUS      current
     DESCRIPTION
         "Indicates the number of fault user."
     ::= { hwEntPbxUserStateTraceTable 4 }

  hwEntPbxUserStateTraceTime OBJECT-TYPE
     SYNTAX OCTET STRING(SIZE (1..20))
     MAX-ACCESS read-only
     STATUS current
     DESCRIPTION
         "Indicates the datetime of the system."
     ::= { hwEntPbxUserStateTraceTable 5 }

  --============================================================== 

   hwEntPbxConferenceAttributeTable OBJECT IDENTIFIER  ::= { hwEntVoicePbxMIB 61 } 

   hwEntPbxConferenceAttributeConfIDLenth OBJECT-TYPE
     SYNTAX      INTEGER{two(1), eight(2)}
     MAX-ACCESS  read-write
     STATUS      current
     DESCRIPTION
         "Indicates the length for generated conference id.
          two(1)
          eight(2)
         "
     ::= { hwEntPbxConferenceAttributeTable 1 }

   hwEntPbxConferenceAttributeReconvokeTimes OBJECT-TYPE
     SYNTAX      Integer32(0..16)
     MAX-ACCESS  read-write
     STATUS      current
     DESCRIPTION
         "Indicates the default reconvoke times of reserved conference."
     ::= { hwEntPbxConferenceAttributeTable 2 }

   hwEntPbxConferenceAttributeConvokeTelno OBJECT-TYPE
     SYNTAX      DisplayString(SIZE (1..32))
     MAX-ACCESS  read-write
     STATUS      current
     DESCRIPTION
         "Indicates the default convoker telno of reserved conference."
     ::= { hwEntPbxConferenceAttributeTable 3 }

   hwEntPbxConferenceAttributeCallRight OBJECT-TYPE
     SYNTAX      BITS{bit0(0),bit1(1),bit2(2),bit3(3),bit4(4),bit5(5),
                      bit6(6),bit7(7)}
     MAX-ACCESS  read-write
     STATUS      current
     DESCRIPTION
         "Indicates the callrights of all conference.
          bit(0):out-ddd
          bit(1):out-idd
          bit(2):out-inter
          bit(3):out-local
          bit(4):reserved
          bit(5):reserved
          bit(6):reserved
          bit(7):reserved
         "
     ::= { hwEntPbxConferenceAttributeTable 4 }
   --==============================================================                                            
  hwEntPbxCallPrefixCallrouteTable OBJECT-TYPE
     SYNTAX      SEQUENCE OF HwEntPbxCallPrefixCallrouteEntry
     MAX-ACCESS  not-accessible
     STATUS      current
     DESCRIPTION
       "
       A list of HwEntPbxPbxCallRouteConfigEntry objects.
       "
     ::= { hwEntVoicePbxMIB 62 }

   hwEntPbxCallPrefixCallrouteEntry OBJECT-TYPE
     SYNTAX      HwEntPbxCallPrefixCallrouteEntry
     MAX-ACCESS  not-accessible
     STATUS      current
     DESCRIPTION
       ""
     INDEX    {
               hwEntPbxCallPrefixCallrouteCallprefixName,
               hwEntPbxCallPrefixCallrouteCallrouteName
              }
     ::= { hwEntPbxCallPrefixCallrouteTable 1 }

   HwEntPbxCallPrefixCallrouteEntry ::=
     SEQUENCE
     {
       hwEntPbxCallPrefixCallrouteCallprefixName    DisplayString,
       hwEntPbxCallPrefixCallrouteCallrouteName     DisplayString,
       hwEntPbxCallPrefixCallrouteRowStatus         RowStatus,
       hwEntPbxCallPrefixCallrouteIndexNo           Integer32
     }

   hwEntPbxCallPrefixCallrouteCallprefixName OBJECT-TYPE
     SYNTAX      DisplayString(SIZE (1..32))
     MAX-ACCESS  not-accessible
     STATUS      current
     DESCRIPTION
         "
         Indicates the name of the callprefix.
         "
     ::= { hwEntPbxCallPrefixCallrouteEntry 1 }
 
   hwEntPbxCallPrefixCallrouteCallrouteName OBJECT-TYPE
     SYNTAX      DisplayString(SIZE (1..32))
     MAX-ACCESS  not-accessible
     STATUS      current
     DESCRIPTION
         "
         Indicates the corresponding callroute name bind to the callprefix.
         "
     ::= { hwEntPbxCallPrefixCallrouteEntry 2 }  

   hwEntPbxCallPrefixCallrouteRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxCallPrefixCallrouteEntry 3 }   
 
   hwEntPbxCallPrefixCallrouteIndexNo OBJECT-TYPE
     SYNTAX      Integer32
     MAX-ACCESS  read-create
     STATUS      current
     DESCRIPTION
         "
         Indicates the corresponding callroute sequence no for the callprefix.
         "
     ::= { hwEntPbxCallPrefixCallrouteEntry 4 }
                                                                                                                                                                                                                                         
  --==============================================================

   hwEntPbxNewCallerChgTable OBJECT-TYPE
     SYNTAX      SEQUENCE OF HwEntPbxNewCallerChgEntry
     MAX-ACCESS  not-accessible
     STATUS      current
     DESCRIPTION
       "
       A list of hwEntPbxNewCallerChgEntry objects.
       "
     ::= { hwEntVoicePbxMIB 63 }

   hwEntPbxNewCallerChgEntry OBJECT-TYPE
     SYNTAX      HwEntPbxNewCallerChgEntry
     MAX-ACCESS  not-accessible
     STATUS      current
     DESCRIPTION
       ""
     INDEX    {
               hwEntPbxNewCallerChgName
              }
     ::= { hwEntPbxNewCallerChgTable 1 }

   HwEntPbxNewCallerChgEntry ::=
     SEQUENCE
     {
       hwEntPbxNewCallerChgName              DisplayString,
       hwEntPbxNewCallerChgRowStatus         RowStatus,
       hwEntPbxNewCallerChgCallerPrefix      DisplayString,
       hwEntPbxNewCallerChgEnterprise        DisplayString,
       hwEntPbxNewCallerChgDnset             DisplayString,
       hwEntPbxNewCallerChgCallSourceName    DisplayString,
       hwEntPbxNewCallerChgOrigDNChgType     INTEGER,
       hwEntPbxNewCallerChgOrigDNChgPos      Integer32,
       hwEntPbxNewCallerChgOrigDNChgLen      Integer32,
       hwEntPbxNewCallerChgOrigDNNew         DisplayString,
       hwEntPbxNewCallerChgTermDNChgType     INTEGER,
       hwEntPbxNewCallerChgTermDNChgPos      Integer32,
       hwEntPbxNewCallerChgTermDNChgLen      Integer32,
       hwEntPbxNewCallerChgTermDNNew         DisplayString
     }

   hwEntPbxNewCallerChgName OBJECT-TYPE
     SYNTAX      DisplayString(SIZE (1..32))
     MAX-ACCESS  not-accessible
     STATUS      current
     DESCRIPTION
         "
         Indicates the name of caller change.
         "
     ::= { hwEntPbxNewCallerChgEntry 1 }

   hwEntPbxNewCallerChgRowStatus OBJECT-TYPE
     SYNTAX      RowStatus
     MAX-ACCESS  read-create
     STATUS      current
     DESCRIPTION
         "
         Indicates row status of table.
         "
     ::= { hwEntPbxNewCallerChgEntry 2 }
     
   hwEntPbxNewCallerChgCallerPrefix OBJECT-TYPE
     SYNTAX      DisplayString(SIZE (1..24))
     MAX-ACCESS  read-create
     STATUS      current
     DESCRIPTION
         "
         Indicates the caller prefix of caller change.
         "
     ::= { hwEntPbxNewCallerChgEntry 3 }
          
   hwEntPbxNewCallerChgEnterprise OBJECT-TYPE
     SYNTAX      DisplayString(SIZE (1..32))
     MAX-ACCESS  read-create
     STATUS      current
     DESCRIPTION
         "
         Indicates the enterprise of caller change.
         "
     ::= { hwEntPbxNewCallerChgEntry 4 }

   hwEntPbxNewCallerChgDnset OBJECT-TYPE
     SYNTAX      DisplayString(SIZE (1..32))
     MAX-ACCESS  read-create
     STATUS      current
     DESCRIPTION
         "
         Indicates the dn-set of caller change.
         "
     ::= { hwEntPbxNewCallerChgEntry 5 }

   hwEntPbxNewCallerChgCallSourceName OBJECT-TYPE
     SYNTAX      DisplayString(SIZE (1..32))
     MAX-ACCESS  read-create
     STATUS      current
     DESCRIPTION
         "
         Indicates the call source name of caller change.
         "
     ::= { hwEntPbxNewCallerChgEntry 6 }   

   hwEntPbxNewCallerChgOrigDNChgType OBJECT-TYPE
     SYNTAX      INTEGER{noChange(1),modify(2),delete(3),insert(4)}
     MAX-ACCESS  read-create
     STATUS      current
     DESCRIPTION
         "
         Indicates the change type of original dial number
         noChange(1);
         modify(2);
         delete(3);
         insert(4);         
         "
     ::= { hwEntPbxNewCallerChgEntry 7 }

   hwEntPbxNewCallerChgOrigDNChgPos OBJECT-TYPE
     SYNTAX      Integer32(1..32)
     MAX-ACCESS  read-create
     STATUS      current
     DESCRIPTION
         "
         Indicates the position of original dial number change.
         "
     ::= { hwEntPbxNewCallerChgEntry 8 }

   hwEntPbxNewCallerChgOrigDNChgLen OBJECT-TYPE
     SYNTAX      Integer32(1..32)
     MAX-ACCESS  read-create
     STATUS      current
     DESCRIPTION
         "
         Indicates the length of original dial number change.
         "
     ::= { hwEntPbxNewCallerChgEntry 9 }

   hwEntPbxNewCallerChgOrigDNNew OBJECT-TYPE
     SYNTAX      DisplayString(SIZE (1..24))
     MAX-ACCESS  read-create
     STATUS      current
     DESCRIPTION
         "
         Indicates the new number of original dial number change after route.
         "
     ::= { hwEntPbxNewCallerChgEntry 10 }
               
   hwEntPbxNewCallerChgTermDNChgType OBJECT-TYPE
     SYNTAX      INTEGER{noChange(1),modify(2),delete(3),insert(4)}
     MAX-ACCESS  read-create
     STATUS      current
     DESCRIPTION
         "
         Indicates the change type of terminal dial number
         noChange(1);
         modify(2);
         delete(3);
         insert(4);         
         "
     ::= { hwEntPbxNewCallerChgEntry 11 }

   hwEntPbxNewCallerChgTermDNChgPos OBJECT-TYPE
     SYNTAX      Integer32(1..32)
     MAX-ACCESS  read-create
     STATUS      current
     DESCRIPTION
         "
         Indicates the position of terminal dial number change.
         "
     ::= { hwEntPbxNewCallerChgEntry 12 }

   hwEntPbxNewCallerChgTermDNChgLen OBJECT-TYPE
     SYNTAX      Integer32(1..32)
     MAX-ACCESS  read-create
     STATUS      current
     DESCRIPTION
         "
         Indicates the length of terminal dial number change.
         "
     ::= { hwEntPbxNewCallerChgEntry 13 }

   hwEntPbxNewCallerChgTermDNNew OBJECT-TYPE
     SYNTAX      DisplayString(SIZE (1..24))
     MAX-ACCESS  read-create
     STATUS      current
     DESCRIPTION
         "
         Indicates the new number of terminal dial number change after route.
         "
     ::= { hwEntPbxNewCallerChgEntry 14 }
     
  --==============================================================                                            
  hwEntPbxCallRouteConfigTable OBJECT-TYPE
     SYNTAX      SEQUENCE OF HwEntPbxCallRouteConfigEntry
     MAX-ACCESS  not-accessible
     STATUS      current
     DESCRIPTION
       "
       A list of HwEntPbxPbxCallRouteConfigEntry objects.
       "
     ::= { hwEntVoicePbxMIB 64 }

   hwEntPbxCallRouteConfigEntry OBJECT-TYPE
     SYNTAX      HwEntPbxCallRouteConfigEntry
     MAX-ACCESS  not-accessible
     STATUS      current
     DESCRIPTION
       ""
     INDEX    {
               hwEntPbxCallRouteName
              }
     ::= { hwEntPbxCallRouteConfigTable 1 }

   HwEntPbxCallRouteConfigEntry ::=
     SEQUENCE
     {
       hwEntPbxCallRouteName                        DisplayString,
       hwEntPbxCallRouteRowStatus                   RowStatus,
       hwEntPbxCallRouteSelectType                  INTEGER,
       hwEntPbxCallRouteRerouteDealName             DisplayString
     }

  hwEntPbxCallRouteName OBJECT-TYPE
     SYNTAX      DisplayString(SIZE (1..32))
     MAX-ACCESS  not-accessible
     STATUS      current
     DESCRIPTION
         "
         Indicates the name of the call route.
         "
     ::= { hwEntPbxCallRouteConfigEntry 1 }

  hwEntPbxCallRouteRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxCallRouteConfigEntry 2 }   
 
   hwEntPbxCallRouteSelectType OBJECT-TYPE
     SYNTAX      INTEGER{chargebase(1),loadshare(2),perloadshare(3),
                         userpriorlevel(4),loadbalance(5),callertelnobase(6),none(7)}
     MAX-ACCESS  read-create
     STATUS      current
     DESCRIPTION
         "
         SelectType:
         chargebase(1)
         loadshare(2)
         perloadshare(3)
         userpriorlevel(4)
         loadbalance(5)
         callertimebase(6)
         none(7)
         default: none(7)
         "
     ::= { hwEntPbxCallRouteConfigEntry 3 }  
  
   hwEntPbxCallRouteRerouteDealName OBJECT-TYPE
     SYNTAX      DisplayString(SIZE (0..32))
     MAX-ACCESS  read-create
     STATUS      current
     DESCRIPTION
         "
         Indicates the name of the RerouteDeal name.
         "
     ::= { hwEntPbxCallRouteConfigEntry 4 } 
   --==============================================================

  hwEntPbxRerouteDealConfigTable OBJECT-TYPE
     SYNTAX      SEQUENCE OF HwEntPbxRerouteDealConfigEntry
     MAX-ACCESS  not-accessible
     STATUS      current
     DESCRIPTION
       "
       A list of HwEntPbxPbxRerouteDealConfigEntry objects.
       "
     ::= { hwEntVoicePbxMIB 65 }

   hwEntPbxRerouteDealConfigEntry OBJECT-TYPE
     SYNTAX      HwEntPbxRerouteDealConfigEntry
     MAX-ACCESS  not-accessible
     STATUS      current
     DESCRIPTION
       ""
     INDEX    {
               hwEntPbxRerouteDealName
              }
     ::= { hwEntPbxRerouteDealConfigTable 1 }

   HwEntPbxRerouteDealConfigEntry ::=
     SEQUENCE
     {
       hwEntPbxRerouteDealName                        DisplayString,
       hwEntPbxRerouteDealRowStatus                   RowStatus,
       hwEntPbxRerouteDealCallRoutename               DisplayString,
       hwEntPbxRerouteDealReCallRouteName             DisplayString,
       hwEntPbxRerouteDealFailedType                  INTEGER
     }

  hwEntPbxRerouteDealName OBJECT-TYPE
     SYNTAX      DisplayString(SIZE (1..32))
     MAX-ACCESS  not-accessible
     STATUS      current
     DESCRIPTION
         "
         Indicates the name of the reroute deal.
         "
     ::= { hwEntPbxRerouteDealConfigEntry 1 }

   hwEntPbxRerouteDealRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxRerouteDealConfigEntry 2 }   

   hwEntPbxRerouteDealCallRoutename OBJECT-TYPE
     SYNTAX      DisplayString(SIZE (0..32))
     MAX-ACCESS  read-create
     STATUS      current
     DESCRIPTION
         "
         Indicates the name of the callroute that will do the rerouted.
         "
     ::= { hwEntPbxRerouteDealConfigEntry 3 } 

   hwEntPbxRerouteDealReCallRouteName OBJECT-TYPE
     SYNTAX      DisplayString(SIZE (0..32))
     MAX-ACCESS  read-create
     STATUS      current
     DESCRIPTION
         "
         Indicates the name of the callroute that will be do the reroute work.
         "
     ::= { hwEntPbxRerouteDealConfigEntry 4 } 

   hwEntPbxRerouteDealFailedType OBJECT-TYPE
     SYNTAX      INTEGER{route-failed(1),call-failed(2)}
     MAX-ACCESS  read-create
     STATUS      current
     DESCRIPTION
         "
         Indicates the failed type for the reroutedeal.
         route-failed(1),
         call-failed(2),
         default:route-failed(1)
         "
     ::= { hwEntPbxRerouteDealConfigEntry 5 } 
   --==============================================================     

   hwEntPbxTimeTempletTable OBJECT-TYPE
     SYNTAX      SEQUENCE OF HwEntPbxTimeTempletEntry
     MAX-ACCESS  not-accessible
     STATUS      current
     DESCRIPTION
       "
       A list of hwEntPbxTimeTempletTable objects.
       "
     ::= { hwEntVoicePbxMIB 66 }

   hwEntPbxTimeTempletEntry OBJECT-TYPE
     SYNTAX      HwEntPbxTimeTempletEntry
     MAX-ACCESS  not-accessible
     STATUS      current
     DESCRIPTION
       ""
     INDEX    {
                 hwEntPbxTimeTempletName        
              }
     ::= { hwEntPbxTimeTempletTable 1 }
     
   HwEntPbxTimeTempletEntry ::=
     SEQUENCE
     {
        hwEntPbxTimeTempletName                  DisplayString,
        hwEntPbxTimeTempletRowStatus             RowStatus,
        hwEntPbxTimeTempletFromDate              DisplayString,
        hwEntPbxTimeTempletFromTime              DisplayString,
        hwEntPbxTimeTempletToDate                DisplayString,
        hwEntPbxTimeTempletToTime                DisplayString,
        hwEntPbxTimeTempletRepeatMode            INTEGER,
        hwEntPbxTimeTempletBeginDate             DisplayString,
        hwEntPbxTimeTempletBeginWeekday          INTEGER,
        hwEntPbxTimeTempletBeginTime             DisplayString,
        hwEntPbxTimeTempletEndDate               DisplayString,
        hwEntPbxTimeTempletEndWeekday            INTEGER,
        hwEntPbxTimeTempletEndTime               DisplayString
     }  
    
   hwEntPbxTimeTempletName OBJECT-TYPE
     SYNTAX      DisplayString(SIZE (1..32))
     MAX-ACCESS  not-accessible
     STATUS      current
     DESCRIPTION
         "
         Indicates the pbx timetemplet name.
         "
    ::= { hwEntPbxTimeTempletEntry 1 }

   hwEntPbxTimeTempletRowStatus	OBJECT-TYPE
     SYNTAX      RowStatus
     MAX-ACCESS  read-create 
     STATUS      current
     DESCRIPTION
         "
         RowStatus:
         active(1)
         notInService(2)
         notReady(3)
         createAndGo(4)
         createAndWait(5)
         destroy(6)
         "
     ::= { hwEntPbxTimeTempletEntry 2 }   
       
   hwEntPbxTimeTempletFromDate OBJECT-TYPE
     SYNTAX      DisplayString(SIZE (0..10))
     MAX-ACCESS  read-create
     STATUS      current
     DESCRIPTION
         "
         Indicates the begin date of time period.
         format: yyyy-mm-dd
         "
     ::= { hwEntPbxTimeTempletEntry 3 }

  hwEntPbxTimeTempletFromTime OBJECT-TYPE
     SYNTAX      DisplayString(SIZE (0..8))
     MAX-ACCESS  read-create
     STATUS      current
     DESCRIPTION
         "
         Indicates the begin time of time period.
         format: hh:mm:ss
         "
     ::= { hwEntPbxTimeTempletEntry 4 }

   hwEntPbxTimeTempletToDate OBJECT-TYPE
     SYNTAX      DisplayString(SIZE (0..10))
     MAX-ACCESS  read-create
     STATUS      current
     DESCRIPTION
         "
         Indicates the end date of time period.
         format: yyyy-mm-dd
         "
     ::= { hwEntPbxTimeTempletEntry 5 }

   hwEntPbxTimeTempletToTime OBJECT-TYPE
     SYNTAX      DisplayString(SIZE (0..8))
     MAX-ACCESS  read-create
     STATUS      current
     DESCRIPTION
         "
         Indicates the end time of time period.
         format: hh:mm:ss
         "
     ::= { hwEntPbxTimeTempletEntry 6 }

   hwEntPbxTimeTempletRepeatMode OBJECT-TYPE
     SYNTAX      INTEGER{noRepeat(1),yearly(2),monthly(3),weekly(4),daily(5)}
     MAX-ACCESS  read-create
     STATUS      current
     DESCRIPTION
         "
         Indicates the repeat mode.
         noRepeat(1);
         yearly(2);
         monthly(3);
         weekly(4);
         daily(5);
         "
     ::= { hwEntPbxTimeTempletEntry 7 }

    hwEntPbxTimeTempletBeginDate OBJECT-TYPE
     SYNTAX      DisplayString(SIZE (0..5))
     MAX-ACCESS  read-create
     STATUS      current
     DESCRIPTION
         "
          Indicates the begin date of time repeat.
          format: mm-dd
         "
     ::= { hwEntPbxTimeTempletEntry 8 }

   hwEntPbxTimeTempletBeginWeekday OBJECT-TYPE
     SYNTAX      INTEGER{mon(1),tue(2),wed(3),thu(4),fri(5),sat(6),sun(7),none(8)}
     MAX-ACCESS  read-create
     STATUS      current
     DESCRIPTION
         "
         Indicates the begin weekday.
         mon(1);
         tue(2);
         wed(3);
         thu(4);
         fri(5);
         sat(6);
         sun(7);
         none(8);
         "
     ::= { hwEntPbxTimeTempletEntry 9 }

   hwEntPbxTimeTempletBeginTime OBJECT-TYPE
     SYNTAX      DisplayString(SIZE (0..8))
     MAX-ACCESS  read-create
     STATUS      current
     DESCRIPTION
         "
         Indicates the begin time of time repeat.
         format: hh:mm:ss
         "
     ::= { hwEntPbxTimeTempletEntry 10 }

   hwEntPbxTimeTempletEndDate OBJECT-TYPE
     SYNTAX      DisplayString(SIZE (0..5))
     MAX-ACCESS  read-create
     STATUS      current
     DESCRIPTION
         "
         Indicates the end date of time repeat.
         format: mm-dd
         "
     ::= { hwEntPbxTimeTempletEntry 11 }

   hwEntPbxTimeTempletEndWeekday OBJECT-TYPE
     SYNTAX      INTEGER{mon(1),tue(2),wed(3),thu(4),fri(5),sat(6),sun(7),none(8)}
     MAX-ACCESS  read-create
     STATUS      current
     DESCRIPTION
         "
         Indicates the end weekday.
         mon(1);
         tue(2);
         wed(3);
         thu(4);
         fri(5);
         sat(6);
         sun(7);
         none(8);
         "
     ::= { hwEntPbxTimeTempletEntry 12 }

   hwEntPbxTimeTempletEndTime OBJECT-TYPE
     SYNTAX      DisplayString(SIZE (0..8))
     MAX-ACCESS  read-create
     STATUS      current
     DESCRIPTION
         "
         Indicates the end time of time repeat.
         format: hh:mm:ss
         "
     ::= { hwEntPbxTimeTempletEntry 13 }

  --==============================================================

   hwEntPbxCallSourceTable OBJECT-TYPE
     SYNTAX      SEQUENCE OF HwEntPbxCallSourceEntry
     MAX-ACCESS  not-accessible
     STATUS      current
     DESCRIPTION
       "
       A list of hwEntPbxCallSourceEntry objects.
       "
     ::= { hwEntVoicePbxMIB 67 }

   hwEntPbxCallSourceEntry OBJECT-TYPE
     SYNTAX      HwEntPbxCallSourceEntry
     MAX-ACCESS  not-accessible
     STATUS      current
     DESCRIPTION
       ""
     INDEX    {
               hwEntPbxCallSourceName
              }
     ::= { hwEntPbxCallSourceTable 1 }

   HwEntPbxCallSourceEntry ::=
     SEQUENCE
     {
       hwEntPbxCallSourceName                DisplayString,
       hwEntPbxCallSourceRowStatus           RowStatus,
       hwEntPbxCallSourceReserved            Integer32
     }

   hwEntPbxCallSourceName OBJECT-TYPE
     SYNTAX      DisplayString(SIZE (1..32))
     MAX-ACCESS  not-accessible
     STATUS      current
     DESCRIPTION
         "
         Indicates the name of call source.
         "
     ::= { hwEntPbxCallSourceEntry 1 }

   hwEntPbxCallSourceRowStatus OBJECT-TYPE
     SYNTAX      RowStatus
     MAX-ACCESS  read-create
     STATUS      current
     DESCRIPTION
         "
         Indicates row status of table.
         "
     ::= { hwEntPbxCallSourceEntry 2 }
     
   hwEntPbxCallSourceReserved OBJECT-TYPE
     SYNTAX      Integer32
     MAX-ACCESS  read-create
     STATUS      current
     DESCRIPTION
         "
         Reserved.
         "
     ::= { hwEntPbxCallSourceEntry 3 }
     
   --==============================================================

  hwEntPbxRouteAnalysisTable OBJECT-TYPE
     SYNTAX      SEQUENCE OF HwEntPbxRouteAnalysisEntry
     MAX-ACCESS  not-accessible
     STATUS      current
     DESCRIPTION
       "
       A list of hwEntPbxRouteAnalysisTable objects.
       "
     ::= { hwEntVoicePbxMIB 68 }

   hwEntPbxRouteAnalysisEntry OBJECT-TYPE
     SYNTAX      HwEntPbxRouteAnalysisEntry
     MAX-ACCESS  not-accessible
     STATUS      current
     DESCRIPTION
       ""
     INDEX    {
               hwEntPbxRouteAnalysisName
              }
     ::= { hwEntPbxRouteAnalysisTable 1 }

   HwEntPbxRouteAnalysisEntry ::=
     SEQUENCE
     {
       hwEntPbxRouteAnalysisName                      DisplayString,
       hwEntPbxRouteAnalysisRowStatus                 RowStatus,
       hwEntPbxRouteAnalysisCallsourceName            DisplayString,
       hwEntPbxRouteAnalysisCallRoutename             DisplayString,
       hwEntPbxRouteAnalysisTrunkGroupName            DisplayString
     }
	 
   hwEntPbxRouteAnalysisName OBJECT-TYPE
     SYNTAX      DisplayString(SIZE (1..32))
     MAX-ACCESS  not-accessible
     STATUS      current
     DESCRIPTION
         "
         Indicates the pbx Routeanalysis name.
         "
    ::= { hwEntPbxRouteAnalysisEntry 1 }
	
   hwEntPbxRouteAnalysisRowStatus OBJECT-TYPE
	 SYNTAX      RowStatus
     MAX-ACCESS  read-create 
     STATUS      current
     DESCRIPTION
         "
         RowStatus:
         active(1)
         notInService(2)
         notReady(3)
         createAndGo(4)
         createAndWait(5)
         destroy(6)
         "
     ::= { hwEntPbxRouteAnalysisEntry 2 }    
 
   hwEntPbxRouteAnalysisCallsourceName OBJECT-TYPE
     SYNTAX      DisplayString(SIZE (0..32))
     MAX-ACCESS  read-create
     STATUS      current
     DESCRIPTION
         "
         Indicates the callsource for the routeanalysis.
         "
     ::= { hwEntPbxRouteAnalysisEntry 3 } 
   
   hwEntPbxRouteAnalysisCallRoutename OBJECT-TYPE
     SYNTAX      DisplayString(SIZE (0..32))
     MAX-ACCESS  read-create
     STATUS      current
     DESCRIPTION
         "
         Indicates the callroute for the routeanalysis.
         "
     ::= { hwEntPbxRouteAnalysisEntry 4 } 
 
   hwEntPbxRouteAnalysisTrunkGroupName OBJECT-TYPE
     SYNTAX      DisplayString(SIZE (0..32))
     MAX-ACCESS  read-create
     STATUS      current
     DESCRIPTION
         "
         Indicates the trunkgroup for the routeanalysis.
         "
     ::= { hwEntPbxRouteAnalysisEntry 5 }	 
 
   --==============================================================                                            
  hwEntPbxTrkGrpCallRouteConfigTable OBJECT-TYPE
     SYNTAX      SEQUENCE OF HwEntPbxTrkGrpCallRouteConfigEntry
     MAX-ACCESS  not-accessible
     STATUS      current
     DESCRIPTION
       "
       A list of hwEntPbxTrkGrpCallRouteConfigTable objects.
       "
     ::= { hwEntVoicePbxMIB 69 }

  hwEntPbxTrkGrpCallRouteConfigEntry OBJECT-TYPE
     SYNTAX      HwEntPbxTrkGrpCallRouteConfigEntry
     MAX-ACCESS  not-accessible
     STATUS      current
     DESCRIPTION
       ""
     INDEX    {
               hwEntPbxTrkGrpCallRouteTrkgrpName,
               hwEntPbxTrkGrpCallRouteCallrouteName
              }
     ::= { hwEntPbxTrkGrpCallRouteConfigTable 1 }

  HwEntPbxTrkGrpCallRouteConfigEntry ::=
     SEQUENCE
     {
       hwEntPbxTrkGrpCallRouteTrkgrpName            DisplayString,
       hwEntPbxTrkGrpCallRouteCallrouteName         DisplayString,
       hwEntPbxTrkGrpCallRouteRowStatus             RowStatus,
       hwEntPbxTrkGrpCallRouteTimeTempletName       DisplayString,
       hwEntPbxTrkGrpCallRouteCharge                Integer32,
       hwEntPbxTrkGrpCallRoutePercent               Integer32,
       hwEntPbxTrkGrpCallRouteUserPriorLevel        INTEGER,
       hwEntPbxTrkGrpCallRouteCallerNumber          DisplayString,
       hwEntPbxTrkGrpCallRouteSelectLevel           Integer32
     }

  hwEntPbxTrkGrpCallRouteTrkgrpName OBJECT-TYPE
     SYNTAX      DisplayString(SIZE (1..32))
     MAX-ACCESS  not-accessible
     STATUS      current
     DESCRIPTION
         "
         Indicates the name of the trunkgroup related by the callroute.
         "
     ::= { hwEntPbxTrkGrpCallRouteConfigEntry 1 }

  hwEntPbxTrkGrpCallRouteCallrouteName OBJECT-TYPE
     SYNTAX      DisplayString(SIZE (1..32))
     MAX-ACCESS  not-accessible
     STATUS      current
     DESCRIPTION
         "
         Indicates the name of callroute related by the trunkgroup.
         "
     ::= { hwEntPbxTrkGrpCallRouteConfigEntry 2 } 
 
  hwEntPbxTrkGrpCallRouteRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxTrkGrpCallRouteConfigEntry 3 }   

  hwEntPbxTrkGrpCallRouteTimeTempletName OBJECT-TYPE
     SYNTAX      DisplayString(SIZE (1..32))
     MAX-ACCESS  read-create
     STATUS      current
     DESCRIPTION
         "
         Indicates the detail timetemplet name used by the trunkgroup related by the callroute whose selecttype is timebase.
         "
     ::= { hwEntPbxTrkGrpCallRouteConfigEntry 4 }   
 
  hwEntPbxTrkGrpCallRouteCharge OBJECT-TYPE
     SYNTAX      Integer32(0..65534)
     MAX-ACCESS  read-create
     STATUS      current
     DESCRIPTION
         "
         Indicates the charge value of the callroute for the trunkgroup related by the callroute whose selecttype is charge.
         "
     ::= { hwEntPbxTrkGrpCallRouteConfigEntry 5 }

  hwEntPbxTrkGrpCallRoutePercent OBJECT-TYPE
     SYNTAX      Integer32(0..100)
     MAX-ACCESS  read-create
     STATUS      current
     DESCRIPTION
         "
         Indicates the percent value of the callroute for the trunk group related by the callroute whose selecttype is percent.
         "
     ::= { hwEntPbxTrkGrpCallRouteConfigEntry 6 }

  hwEntPbxTrkGrpCallRouteUserPriorLevel OBJECT-TYPE
     SYNTAX      INTEGER{default(1),normal(2),advanced(3),super(4)}
     MAX-ACCESS  read-create
     STATUS      current
     DESCRIPTION
         "
         Indicates UserPriorLevel of the callroute for the trunk group related by the callroute whose selecttype is userpriorlevel.
         default(1)
         normal(2)
         advanced(3)
         super(4)
         "
     ::= { hwEntPbxTrkGrpCallRouteConfigEntry 7 }

  hwEntPbxTrkGrpCallRouteCallerNumber OBJECT-TYPE
     SYNTAX      DisplayString(SIZE (1..32))
     MAX-ACCESS  read-create
     STATUS      current
     DESCRIPTION
         "
         Indicates the callernumber by the trunkgroup related by the callroute whose selecttype is caller-telno-based.
         "
     ::= { hwEntPbxTrkGrpCallRouteConfigEntry 8 }  

  hwEntPbxTrkGrpCallRouteSelectLevel OBJECT-TYPE
     SYNTAX      Integer32(0..254)
     MAX-ACCESS  read-create
     STATUS      current
     DESCRIPTION
         "
         Indicates the select-level for the trunkgroup-callroute relationn in which callroute selecttype is caller-telno-based.
         "
     ::= { hwEntPbxTrkGrpCallRouteConfigEntry 9 }  
   --==============================================================           
  hwEntPbxConfConfigTable OBJECT-TYPE
     SYNTAX      SEQUENCE OF HwEntPbxConfConfigEntry
     MAX-ACCESS  not-accessible
     STATUS      current
     DESCRIPTION
       "
       A list of hwEntPbxConfConfigEntry objects.
       "
     ::= { hwEntVoicePbxMIB 70 }

  hwEntPbxConfConfigEntry OBJECT-TYPE
     SYNTAX      HwEntPbxConfConfigEntry
     MAX-ACCESS  not-accessible
     STATUS      current
     DESCRIPTION
       ""
     INDEX    {
               hwEntPbxConfName               
              }
     ::= { hwEntPbxConfConfigTable 1 }

  HwEntPbxConfConfigEntry ::=
     SEQUENCE
     {
       hwEntPbxConfName                          DisplayString,
       hwEntPbxConfRowStatus                     RowStatus,
       hwEntPbxConfDescription                   DisplayString,
       hwEntPbxConfId                            Unsigned32,
       hwEntPbxConfEnterpriseName                DisplayString,
       hwEntPbxConfDnsetName                     DisplayString,
       hwEntPbxConfRegNum                        Integer32,
       hwEntPbxConfAttendeePwd                   DisplayString,
       hwEntPbxConfChairmanPwd                   DisplayString,
       hwEntPbxConfStartDate                     DisplayString,
       hwEntPbxConfStartTime                     DisplayString,
       hwEntPbxConfEndDate                       DisplayString,
       hwEntPbxConfEndTime                       DisplayString,
       hwEntPbxConfEnterPrompt                   INTEGER,
       hwEntPbxConfLeavePrompt                   INTEGER,
       hwEntPbxConfChairman                      DisplayString,
       hwEntPbxConfType                          INTEGER,
       hwEntPbxConfState                         INTEGER 
     }

  hwEntPbxConfName OBJECT-TYPE
     SYNTAX      DisplayString(SIZE (1..32))
     MAX-ACCESS  not-accessible
     STATUS      current
     DESCRIPTION
         "
         Indicates the name of the conference.
         "
     ::= { hwEntPbxConfConfigEntry 1 }      

  hwEntPbxConfRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxConfConfigEntry 2 }  
     
  hwEntPbxConfDescription OBJECT-TYPE
     SYNTAX      DisplayString(SIZE (1..128))
     MAX-ACCESS  read-create
     STATUS      current
     DESCRIPTION
         "
         Indicates the description of the conference.
         "
     ::= { hwEntPbxConfConfigEntry 3 }   
 
  hwEntPbxConfId OBJECT-TYPE
     SYNTAX      Unsigned32
     MAX-ACCESS  read-create
     STATUS      current
     DESCRIPTION
         "
         Indicates the conference ID of conference.
         "
     ::= { hwEntPbxConfConfigEntry 4 }     
     
  hwEntPbxConfEnterpriseName OBJECT-TYPE
     SYNTAX      DisplayString(SIZE (1..32))
     MAX-ACCESS  read-create
     STATUS      current
     DESCRIPTION
         "
         Indicates the enterprise name of the conference.
         "
     ::= { hwEntPbxConfConfigEntry 5 }    
     
  hwEntPbxConfDnsetName OBJECT-TYPE
     SYNTAX      DisplayString(SIZE (1..32))
     MAX-ACCESS  read-create
     STATUS      current
     DESCRIPTION
         "
         Indicates the dial plan name of the conference.
         "
     ::= { hwEntPbxConfConfigEntry 6 }    

  hwEntPbxConfRegNum OBJECT-TYPE
     SYNTAX      Integer32
     MAX-ACCESS  read-create
     STATUS      current
     DESCRIPTION
         "
         Indicates the max reg seat number of conference.
         "
     ::= { hwEntPbxConfConfigEntry 7 }     
     
  hwEntPbxConfAttendeePwd OBJECT-TYPE
     SYNTAX      DisplayString(SIZE (1..16))
     MAX-ACCESS  read-create
     STATUS      current
     DESCRIPTION
         "
         Indicates the attendee's password of the conference.
         "
     ::= { hwEntPbxConfConfigEntry 8 }    
     
  hwEntPbxConfChairmanPwd OBJECT-TYPE
     SYNTAX      DisplayString(SIZE (1..16))
     MAX-ACCESS  read-create
     STATUS      current
     DESCRIPTION
         "
         Indicates the chairman's password of the conference.
         "
     ::= { hwEntPbxConfConfigEntry 9 }    
     
  hwEntPbxConfStartDate OBJECT-TYPE
     SYNTAX      DisplayString(SIZE (1..10))
     MAX-ACCESS  read-create
     STATUS      current
     DESCRIPTION
         "
         Indicates the start date of the conference.
         "
     ::= { hwEntPbxConfConfigEntry 10 }    

  hwEntPbxConfStartTime OBJECT-TYPE
     SYNTAX      DisplayString(SIZE (1..10))
     MAX-ACCESS  read-create
     STATUS      current
     DESCRIPTION
         "
         Indicates the start time of the conference.
         "
     ::= { hwEntPbxConfConfigEntry 11 }    
     
  hwEntPbxConfEndDate OBJECT-TYPE
     SYNTAX      DisplayString(SIZE (1..10))
     MAX-ACCESS  read-create
     STATUS      current
     DESCRIPTION
         "
         Indicates the end date of the conference.
         "
     ::= { hwEntPbxConfConfigEntry 12 }    

  hwEntPbxConfEndTime OBJECT-TYPE
     SYNTAX      DisplayString(SIZE (1..10))
     MAX-ACCESS  read-create
     STATUS      current
     DESCRIPTION
         "
         Indicates the end time of the conference.
         "
     ::= { hwEntPbxConfConfigEntry 13 }      
     
  hwEntPbxConfEnterPrompt OBJECT-TYPE
     SYNTAX      INTEGER{beep(1),beepandname(2)}
     MAX-ACCESS  read-create
     STATUS      current
     DESCRIPTION
         "
         Indicates the prompt to enter the conference.
         beep(1)
         beepandname(2)
         "
     ::= { hwEntPbxConfConfigEntry 14 }         
     
  hwEntPbxConfLeavePrompt OBJECT-TYPE
     SYNTAX      INTEGER{beep(1),beepandname(2)}
     MAX-ACCESS  read-create
     STATUS      current
     DESCRIPTION
         "
         Indicates the prompt to leave the conference.
         beep(1)
         beepandname(2)
         "
     ::= { hwEntPbxConfConfigEntry 15 }         
     
  hwEntPbxConfChairman OBJECT-TYPE
     SYNTAX      DisplayString(SIZE (1..32))
     MAX-ACCESS  read-create
     STATUS      current
     DESCRIPTION
         "
         Indicates telephone number of chairman.
         "
     ::= { hwEntPbxConfConfigEntry 16 }
     
  hwEntPbxConfType OBJECT-TYPE
     SYNTAX      INTEGER{booked(1),immediate(2)}
     MAX-ACCESS  read-create
     STATUS      current
     DESCRIPTION
         "
         Indicates the type of conference.
         booked(1)       --booked conference
         immediate(2)    --immediate conference(voice included)
         "
     ::= { hwEntPbxConfConfigEntry 17 }         
     
  hwEntPbxConfState OBJECT-TYPE
     SYNTAX      INTEGER{idle(1),start(2),calling(3),busy(4)}
     MAX-ACCESS  read-only
     STATUS      current
     DESCRIPTION
         "
         Indicates the state of conference.
         idle(1)    --conference is not started or all attendees have leaved
         start(2)   --conference is started
         calling(3)  --conference is calling other attendees(there is only one attendee present)
         busy(4)    --conference is running normal(there is at least two attendees present now)
         "
     ::= { hwEntPbxConfConfigEntry 18 }


   --==============================================================           
  hwEntPbxConferenceAttendeeCfgTable OBJECT-TYPE
     SYNTAX      SEQUENCE OF HwEntPbxConferenceAttendeeCfgEntry
     MAX-ACCESS  not-accessible
     STATUS      current
     DESCRIPTION
       "
       A list of hwEntPbxConferenceAttendeeCfgEntry objects.
       "
     ::= { hwEntVoicePbxMIB 71 }

  hwEntPbxConferenceAttendeeCfgEntry OBJECT-TYPE
     SYNTAX      HwEntPbxConferenceAttendeeCfgEntry
     MAX-ACCESS  not-accessible
     STATUS      current
     DESCRIPTION
       ""
     INDEX    {
               hwEntPbxConferenceAttendeeConfName,
               hwEntPbxConferenceAttendeeTelNo   
              }
     ::= { hwEntPbxConferenceAttendeeCfgTable 1 }

  HwEntPbxConferenceAttendeeCfgEntry ::=
     SEQUENCE
     {       
       hwEntPbxConferenceAttendeeConfName              DisplayString,
       hwEntPbxConferenceAttendeeTelNo                 DisplayString,
       hwEntPbxConferenceAttendeeRowStatus             RowStatus,
       hwEntPbxConferenceAttendeeUserName              DisplayString,
       hwEntPbxConferenceAttendeeMode                  INTEGER,
       hwEntPbxConferenceAttendeeConfState             INTEGER
     }

  hwEntPbxConferenceAttendeeConfName OBJECT-TYPE
     SYNTAX      DisplayString(SIZE (1..32))
     MAX-ACCESS  not-accessible
     STATUS      current
     DESCRIPTION
         "
         Indicates the conference-name the attendee bond to.
         "
     ::= { hwEntPbxConferenceAttendeeCfgEntry 1 }      

  hwEntPbxConferenceAttendeeTelNo OBJECT-TYPE
     SYNTAX      DisplayString(SIZE (1..32))
     MAX-ACCESS  not-accessible
     STATUS      current
     DESCRIPTION
         "
         Indicates the telephone number of the conference attendee.
         "
     ::= { hwEntPbxConferenceAttendeeCfgEntry 2 }   
 
  hwEntPbxConferenceAttendeeRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxConferenceAttendeeCfgEntry 3 }  



  hwEntPbxConferenceAttendeeUserName OBJECT-TYPE
     SYNTAX      DisplayString(SIZE (0..32))
     MAX-ACCESS  read-create
     STATUS      current
     DESCRIPTION
         "
         Indicates the username of the conference attendee.
         "
     ::= { hwEntPbxConferenceAttendeeCfgEntry 4 }

  hwEntPbxConferenceAttendeeMode OBJECT-TYPE
     SYNTAX      INTEGER{listentalk(1),listenonly(2),talkonly(3),chairman(4),
                         insert(5),isolate(6),kick(7)}
     MAX-ACCESS  read-create
     STATUS      current
     DESCRIPTION
         "
         Indicates the mode of attendee.
         listentalk(1)
         listenonly(2)
         talkonly(3)
         chairman(4)
         insert(5)
         isolate(6)
         kick(7)
         "
     ::= { hwEntPbxConferenceAttendeeCfgEntry 5 }     

  hwEntPbxConferenceAttendeeConfState OBJECT-TYPE
     SYNTAX      INTEGER{leave(1),enter(2),invite(3)}
     MAX-ACCESS  read-create
     STATUS      current
     DESCRIPTION
         "
         Indicates the conference state of attendee.
         leave(1)   --the attendee has leaved the conference
         enter(2)   --the attendee has entered the conference
         invite(3)  --inviting the attendee
         "
     ::= { hwEntPbxConferenceAttendeeCfgEntry 6 }     


   --==============================================================           
  hwEntPbxAlarmParaTable OBJECT IDENTIFIER  ::= { hwEntVoicePbxMIB 72 }

  hwEntPbxAlarmShelf OBJECT-TYPE
        SYNTAX Integer32
        MAX-ACCESS accessible-for-notify
        STATUS current
        DESCRIPTION
            "Indicates the shelf no."
        ::= { hwEntPbxAlarmParaTable 1 }

  hwEntPbxAlarmSlot OBJECT-TYPE
        SYNTAX Integer32
        MAX-ACCESS accessible-for-notify
        STATUS current
        DESCRIPTION
            "Indicates the slot no"
        ::= { hwEntPbxAlarmParaTable 2 }
        
  hwEntPbxAlarmUpgradeFailInfo OBJECT-TYPE
        SYNTAX OCTET STRING(SIZE (1..1024))
        MAX-ACCESS accessible-for-notify
        STATUS current
        DESCRIPTION
            "Indicates the failed information of upgrade"
        ::= { hwEntPbxAlarmParaTable 3 }        

  hwEntPbxAlarmPort OBJECT-TYPE
        SYNTAX Integer32
        MAX-ACCESS accessible-for-notify
        STATUS current
        DESCRIPTION
            "Indicates the port no"
        ::= { hwEntPbxAlarmParaTable 4 }

  hwEntPbxAlarmTsn OBJECT-TYPE
        SYNTAX Integer32
        MAX-ACCESS accessible-for-notify
        STATUS current
        DESCRIPTION
            "Indicates the tsn number"
        ::= { hwEntPbxAlarmParaTable 5 }

  hwEntPbxAlarmInterfaceName OBJECT-TYPE
        SYNTAX DisplayString
        MAX-ACCESS accessible-for-notify
        STATUS current
        DESCRIPTION
            "Indicates the interface name"
        ::= { hwEntPbxAlarmParaTable 6 }                                
   --==============================================================           
  hwEntPbxTraps OBJECT IDENTIFIER ::= { hwEntVoicePbxMIB 73 }

  hwEntPbxBillpoolOverflow NOTIFICATION-TYPE
        OBJECTS {hwEntPbxAlarmShelf, hwEntPbxAlarmSlot}
        STATUS current
        DESCRIPTION 
                "bill pool is overflow."
        ::= { hwEntPbxTraps 1 }

  hwEntPbxBillpoolOverflowRestore NOTIFICATION-TYPE
        OBJECTS {hwEntPbxAlarmShelf, hwEntPbxAlarmSlot}
        STATUS current
        DESCRIPTION 
                "bill pool is not overflow."
        ::= { hwEntPbxTraps 2 }

  hwEntPbxBillpoolFull NOTIFICATION-TYPE
        OBJECTS {hwEntPbxAlarmShelf, hwEntPbxAlarmSlot}
        STATUS current
        DESCRIPTION 
                "bill pool is full."
        ::= { hwEntPbxTraps 3 }

  hwEntPbxBillpoolFullRestore NOTIFICATION-TYPE
        OBJECTS {hwEntPbxAlarmShelf, hwEntPbxAlarmSlot}
        STATUS current
        DESCRIPTION 
                "bill pool is not full."
        ::= { hwEntPbxTraps 4 }

  hwEntPbxBillCommInterrupt NOTIFICATION-TYPE
        OBJECTS {hwEntPbxAlarmShelf, hwEntPbxAlarmSlot}
        STATUS current
        DESCRIPTION 
                "Commutinction with bill server interrupt."
        ::= { hwEntPbxTraps 5 }

  hwEntPbxBillCommRestore NOTIFICATION-TYPE
        OBJECTS {hwEntPbxAlarmShelf, hwEntPbxAlarmSlot}
        STATUS current
        DESCRIPTION 
                "Commutinction with bill server restore."
        ::= { hwEntPbxTraps 6 }

  hwEntPbxUpgradeFailTrap NOTIFICATION-TYPE
        OBJECTS {hwEntPbxAlarmUpgradeFailInfo}
        STATUS current
        DESCRIPTION 
                "Config upgrade is failed."
        ::= { hwEntPbxTraps 7 }

  hwEntPbxE1FaultTrap NOTIFICATION-TYPE
        OBJECTS { hwEntPbxAlarmSlot, hwEntPbxAlarmPort }
        STATUS current
        DESCRIPTION 
                "E1 is fault."
        ::= { hwEntPbxTraps 8 }

  hwEntPbxE1ResumeTrap NOTIFICATION-TYPE
        OBJECTS { hwEntPbxAlarmSlot, hwEntPbxAlarmPort }
        STATUS current
        DESCRIPTION 
                "E1 is Resumed."
        ::= { hwEntPbxTraps 9 }
  
  hwEntPbxBillSendFailTrap NOTIFICATION-TYPE
        OBJECTS {hwEntPbxAlarmShelf, hwEntPbxAlarmSlot}
        STATUS current
        DESCRIPTION 
                "Send bill failed."
        ::= { hwEntPbxTraps 10 }
        
  hwEntPbxBillCreateFailTrap NOTIFICATION-TYPE
        OBJECTS {hwEntPbxAlarmShelf, hwEntPbxAlarmSlot}
        STATUS current
        DESCRIPTION 
                "Create bill failed."
        ::= { hwEntPbxTraps 11 }
        
  hwEntPbxDspResourceNotEnoughTrap NOTIFICATION-TYPE
        STATUS current
        DESCRIPTION 
                "DSP resource is not enough."
        ::= { hwEntPbxTraps 12 } 
        
  hwEntPbxAt0CircuitFaultTrap NOTIFICATION-TYPE
        OBJECTS {hwEntPbxAlarmSlot, hwEntPbxAlarmPort, hwEntPbxAlarmTsn}
        STATUS current
        DESCRIPTION 
                "AT0 circuit fault."
        ::= { hwEntPbxTraps 13 }            
 
  hwEntPbxAt0CircuitRestoreTrap NOTIFICATION-TYPE
        OBJECTS {hwEntPbxAlarmSlot, hwEntPbxAlarmPort, hwEntPbxAlarmTsn}
        STATUS current
        DESCRIPTION 
                "AT0 circuit restore."
        ::= { hwEntPbxTraps 14 }     

  hwEntPbxUserNumberLockTrap NOTIFICATION-TYPE
        OBJECTS {hwEntPbxUserName}
        STATUS current
        DESCRIPTION 
                "Lock user number."
        ::= { hwEntPbxTraps 15 }   

  hwEntPbxUserNumberUnLockTrap NOTIFICATION-TYPE
        OBJECTS {hwEntPbxUserName}
        STATUS current
        DESCRIPTION 
                "Unlock user number."
        ::= { hwEntPbxTraps 16 }   

  hwEntPbxPriLinkFaultTrap NOTIFICATION-TYPE
        OBJECTS {hwEntPbxAlarmSlot, hwEntPbxAlarmPort, hwEntPbxAlarmTsn}
        STATUS current
        DESCRIPTION 
                "PRI link fault."
        ::= { hwEntPbxTraps 17 }  

  hwEntPbxPriLinkRestoreTrap NOTIFICATION-TYPE
        OBJECTS {hwEntPbxAlarmSlot, hwEntPbxAlarmPort, hwEntPbxAlarmTsn}
        STATUS current
        DESCRIPTION 
                "PRI link restore."
        ::= { hwEntPbxTraps 18 }                                             
   --==============================================================           
  hwEntPbxVoiceFileTable OBJECT-TYPE
     SYNTAX      SEQUENCE OF HwEntPbxVoiceFileEntry
     MAX-ACCESS  not-accessible
     STATUS      current
     DESCRIPTION
       "
       A list of hwEntPbxVoiceFileEntry objects.
       "
     ::= { hwEntVoicePbxMIB 74 }

  hwEntPbxVoiceFileEntry OBJECT-TYPE
     SYNTAX      HwEntPbxVoiceFileEntry
     MAX-ACCESS  not-accessible
     STATUS      current
     DESCRIPTION
       ""
     INDEX    {
               hwEntPbxVoiceFileName   
              }
     ::= { hwEntPbxVoiceFileTable 1 }

  HwEntPbxVoiceFileEntry ::=
     SEQUENCE
     {
       hwEntPbxVoiceFileName                           DisplayString,
       hwEntPbxVoiceFileRowStatus                      RowStatus,
       hwEntPbxVoiceFileType                           INTEGER
     }

  hwEntPbxVoiceFileName OBJECT-TYPE
     SYNTAX      DisplayString(SIZE (1..64))
     MAX-ACCESS  not-accessible
     STATUS      current
     DESCRIPTION
         "
         Indicates the index of the voice-file.
         "
     ::= { hwEntPbxVoiceFileEntry 1 }      
  
  hwEntPbxVoiceFileRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxVoiceFileEntry 2 }  
     
  hwEntPbxVoiceFileType OBJECT-TYPE
     SYNTAX      INTEGER{welcome-voice(1),menu-voice(2)}
     MAX-ACCESS  read-create
     STATUS      current
     DESCRIPTION
         "
         Indicates the type of the voice-file
         welcome-voice(1)
         menu-voice(2)
         "
     ::= { hwEntPbxVoiceFileEntry 3 }   


   --==============================================================           
  hwEntPbxIvrTimeIndexTable OBJECT-TYPE
     SYNTAX      SEQUENCE OF HwEntPbxIvrTimeIndexEntry
     MAX-ACCESS  not-accessible
     STATUS      current
     DESCRIPTION
       "
       A list of hwEntPbxIvrTimeIndexEntry objects.
       "
     ::= { hwEntVoicePbxMIB 75 }

  hwEntPbxIvrTimeIndexEntry OBJECT-TYPE
     SYNTAX      HwEntPbxIvrTimeIndexEntry
     MAX-ACCESS  not-accessible
     STATUS      current
     DESCRIPTION
       ""
     INDEX    {
               hwEntPbxIvrTimeIndexNo   
              }
     ::= { hwEntPbxIvrTimeIndexTable 1 }

  HwEntPbxIvrTimeIndexEntry ::=
     SEQUENCE
     {
       hwEntPbxIvrTimeIndexNo                          Unsigned32,
       hwEntPbxIvrTimeIndexRowStatus                   RowStatus,
       hwEntPbxIvrTimeIndexStartYear                   Integer32,
       hwEntPbxIvrTimeIndexStartMonth                  Integer32,
       hwEntPbxIvrTimeIndexStartDay                    Integer32,
       hwEntPbxIvrTimeIndexStartWeekday                INTEGER,
       hwEntPbxIvrTimeIndexStartHour                   Integer32,
       hwEntPbxIvrTimeIndexStartMinute                 Integer32,
       hwEntPbxIvrTimeIndexStartSecond                 Integer32, 
       hwEntPbxIvrTimeIndexEndYear                     Integer32,
       hwEntPbxIvrTimeIndexEndMonth                    Integer32,
       hwEntPbxIvrTimeIndexEndDay                      Integer32,
       hwEntPbxIvrTimeIndexEndWeekday                  INTEGER,
       hwEntPbxIvrTimeIndexEndHour                     Integer32,
       hwEntPbxIvrTimeIndexEndMinute                   Integer32,
       hwEntPbxIvrTimeIndexEndSecond                   Integer32,
       hwEntPbxIvrTimeIndexIsHoliday                   INTEGER 
     }  
    
   hwEntPbxIvrTimeIndexNo OBJECT-TYPE
     SYNTAX      Unsigned32
     MAX-ACCESS  not-accessible
     STATUS      current
     DESCRIPTION
         "
         Indicates the ivr time-index.
         "
     ::= { hwEntPbxIvrTimeIndexEntry 1 }

   hwEntPbxIvrTimeIndexRowStatus OBJECT-TYPE
     SYNTAX      RowStatus
     MAX-ACCESS  read-create 
     STATUS      current
     DESCRIPTION
         "
         RowStatus:
         active(1)
         notInService(2)
         notReady(3)
         createAndGo(4)
         createAndWait(5)
         destroy(6)
         "
     ::= { hwEntPbxIvrTimeIndexEntry 2 }   
       
   hwEntPbxIvrTimeIndexStartYear OBJECT-TYPE
     SYNTAX      Integer32(1970..2100)
     MAX-ACCESS  read-create
     STATUS      current
     DESCRIPTION
         "
         Indicates the Start-Year of ivr-time.
         "
     ::= { hwEntPbxIvrTimeIndexEntry 3 }

   hwEntPbxIvrTimeIndexStartMonth OBJECT-TYPE
     SYNTAX      Integer32(1..12)
     MAX-ACCESS  read-create
     STATUS      current
     DESCRIPTION
         "
         Indicates the Start-Month of ivr-time.
         "
     ::= { hwEntPbxIvrTimeIndexEntry 4 }

   hwEntPbxIvrTimeIndexStartDay OBJECT-TYPE
     SYNTAX      Integer32(1..31)
     MAX-ACCESS  read-create
     STATUS      current
     DESCRIPTION
         "
         Indicates the Start-Day of ivr-time.
         "
     ::= { hwEntPbxIvrTimeIndexEntry 5 }

   hwEntPbxIvrTimeIndexStartWeekday OBJECT-TYPE
     SYNTAX      INTEGER{mon(1),tue(2),wed(3),thu(4),fri(5),sat(6),sun(7),none(8)}
     MAX-ACCESS  read-create
     STATUS      current
     DESCRIPTION
         "
         Indicates the Start-WeekDay of ivr-time.
         mon(1);
         tue(2);
         wed(3);
         thu(4);
         fri(5);
         sat(6);
         sun(7);
         none(8);
         "
     ::= { hwEntPbxIvrTimeIndexEntry 6 }
 
   hwEntPbxIvrTimeIndexStartHour OBJECT-TYPE
     SYNTAX      Integer32(0..23)
     MAX-ACCESS  read-create
     STATUS      current
     DESCRIPTION
         "
         Indicates the Start-Hour of ivr-time.
         "
     ::= { hwEntPbxIvrTimeIndexEntry 7 }

   hwEntPbxIvrTimeIndexStartMinute OBJECT-TYPE
     SYNTAX      Integer32(0..59)
     MAX-ACCESS  read-create
     STATUS      current
     DESCRIPTION
         "
         Indicates the Start-Minute of ivr-time.
         "
     ::= { hwEntPbxIvrTimeIndexEntry 8 }
 
   hwEntPbxIvrTimeIndexStartSecond OBJECT-TYPE
     SYNTAX      Integer32(0..59)
     MAX-ACCESS  read-create
     STATUS      current
     DESCRIPTION
         "
         Indicates the Start-Second of ivr-time.
         "
     ::= { hwEntPbxIvrTimeIndexEntry 9 }

   hwEntPbxIvrTimeIndexEndYear OBJECT-TYPE
     SYNTAX      Integer32(1970..2100)
     MAX-ACCESS  read-create
     STATUS      current
     DESCRIPTION
         "
         Indicates the End-Year of ivr-time.
         "
     ::= { hwEntPbxIvrTimeIndexEntry 10 }

   hwEntPbxIvrTimeIndexEndMonth OBJECT-TYPE
     SYNTAX      Integer32(1..12)
     MAX-ACCESS  read-create
     STATUS      current
     DESCRIPTION
         "
         Indicates the end Month of ivr-time.
         "
     ::= { hwEntPbxIvrTimeIndexEntry 11 }

   hwEntPbxIvrTimeIndexEndDay OBJECT-TYPE
     SYNTAX      Integer32(1..31)
     MAX-ACCESS  read-create
     STATUS      current
     DESCRIPTION
         "
         Indicates the End-Day of ivr-time.
         "
     ::= { hwEntPbxIvrTimeIndexEntry 12 }

   hwEntPbxIvrTimeIndexEndWeekday OBJECT-TYPE
     SYNTAX      INTEGER{mon(1),tue(2),wed(3),thu(4),fri(5),sat(6),sun(7),none(8)}
     MAX-ACCESS  read-create
     STATUS      current
     DESCRIPTION
         "
         Indicates the End-WeekDay of ivr-time.
         mon(1);
         tue(2);
         wed(3);
         thu(4);
         fri(5);
         sat(6);
         sun(7);
         none(8);
         "
     ::= { hwEntPbxIvrTimeIndexEntry 13 }
 
   hwEntPbxIvrTimeIndexEndHour OBJECT-TYPE
     SYNTAX      Integer32(0..23)
     MAX-ACCESS  read-create
     STATUS      current
     DESCRIPTION
         "
         Indicates the End-Hour of ivr-time.
         "
     ::= { hwEntPbxIvrTimeIndexEntry 14 }

   hwEntPbxIvrTimeIndexEndMinute OBJECT-TYPE
     SYNTAX      Integer32(0..59)
     MAX-ACCESS  read-create
     STATUS      current
     DESCRIPTION
         "
         Indicates the End-Minute of ivr-time.
         "
     ::= { hwEntPbxIvrTimeIndexEntry 15 }
 
   hwEntPbxIvrTimeIndexEndSecond OBJECT-TYPE
     SYNTAX      Integer32(0..59)
     MAX-ACCESS  read-create
     STATUS      current
     DESCRIPTION
         "
         Indicates the End-Second of ivr-time.
         "
     ::= { hwEntPbxIvrTimeIndexEntry 16 }

   hwEntPbxIvrTimeIndexIsHoliday OBJECT-TYPE
     SYNTAX      INTEGER{false(1),true(2)}  
     MAX-ACCESS  read-create
     STATUS      current
     DESCRIPTION
         "
         Indicates if ivr-time is Holiday.
         false(1);
          true(2);
         "
     ::= { hwEntPbxIvrTimeIndexEntry 17 } 

   --==============================================================           
  hwEntPbxIvrTable OBJECT-TYPE
     SYNTAX      SEQUENCE OF HwEntPbxIvrEntry
     MAX-ACCESS  not-accessible
     STATUS      current
     DESCRIPTION
       "
       A list of hwEntPbxIvrEntry objects.
       "
     ::= { hwEntVoicePbxMIB 76 }

  hwEntPbxIvrEntry OBJECT-TYPE
     SYNTAX      HwEntPbxIvrEntry
     MAX-ACCESS  not-accessible
     STATUS      current
     DESCRIPTION
       ""
     INDEX    {
               hwEntPbxIvrVu   
              }
     ::= { hwEntPbxIvrTable 1 }

  HwEntPbxIvrEntry ::=
     SEQUENCE
     {
       hwEntPbxIvrVu                                     DisplayString,
       hwEntPbxIvrVuRowStatus                            RowStatus, 
       hwEntPbxIvrFileName                               DisplayString,
       hwEntPbxIvrNumberLength                           Integer32,
       hwEntPbxIvrScriptType                             INTEGER,
       hwEntPbxIvrConfigString                           OCTET STRING,
       hwEntPbxIvrConfigStringLength                     Integer32
     }

  hwEntPbxIvrVu OBJECT-TYPE
     SYNTAX      DisplayString(SIZE (1..32))
     MAX-ACCESS  not-accessible
     STATUS      current
     DESCRIPTION
         "
         Indicates the name of ivr-config.
         "
     ::= { hwEntPbxIvrEntry 1 }      
  
  hwEntPbxIvrVuRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxIvrEntry 2 }  

   hwEntPbxIvrFileName OBJECT-TYPE
     SYNTAX      DisplayString(SIZE (1..32))
     MAX-ACCESS  read-create
     STATUS      current
     DESCRIPTION
         "
         Indicates the File-name of ivr-config.
         "
     ::= { hwEntPbxIvrEntry 3 }   
     
  hwEntPbxIvrNumberLength OBJECT-TYPE
     SYNTAX      Integer32
     MAX-ACCESS  read-create
     STATUS      current
     DESCRIPTION
         "
         Indicates the numberLength of ivr-config.
         "
     ::= { hwEntPbxIvrEntry 4 }   

  hwEntPbxIvrScriptType OBJECT-TYPE
     SYNTAX      INTEGER{graphic-config(1),upload-file(2)}
     MAX-ACCESS  read-create
     STATUS      current
     DESCRIPTION
         "
         Indicates the script type of ivr-config.
         graphic-config(1);
         upload-file(2);
         "
     ::= { hwEntPbxIvrEntry 5 } 

  hwEntPbxIvrConfigString OBJECT-TYPE
     SYNTAX      OCTET STRING(SIZE (1..32768))
     MAX-ACCESS  read-create
     STATUS      current
     DESCRIPTION
         "
         Indicates the config string of ivr-config.
         "
     ::= { hwEntPbxIvrEntry 6 } 

  hwEntPbxIvrConfigStringLength OBJECT-TYPE
     SYNTAX      Integer32
     MAX-ACCESS  read-create
     STATUS      current
     DESCRIPTION
         "
         Indicates the config string length of ivr-config.
         "
     ::= { hwEntPbxIvrEntry 7 }   
 
   --==============================================================           
  hwEntPbxIvrFileTable OBJECT-TYPE
     SYNTAX      SEQUENCE OF HwEntPbxIvrFileEntry
     MAX-ACCESS  not-accessible
     STATUS      current
     DESCRIPTION
       "
       A list of hwEntPbxIvrFileEntry objects.
       "
     ::= { hwEntVoicePbxMIB 77 }

  hwEntPbxIvrFileEntry OBJECT-TYPE
     SYNTAX      HwEntPbxIvrFileEntry
     MAX-ACCESS  not-accessible
     STATUS      current
     DESCRIPTION
       ""
     INDEX    {
               hwEntPbxIvrFileIvrVu   
              }
     ::= { hwEntPbxIvrFileTable 1 }

  HwEntPbxIvrFileEntry ::=
     SEQUENCE
     {
       hwEntPbxIvrFileIvrVu                              DisplayString,
       hwEntPbxIvrFileRowStatus                          RowStatus,
       hwEntPbxIvrFilePath                               DisplayString
     }

  hwEntPbxIvrFileIvrVu OBJECT-TYPE
     SYNTAX      DisplayString(SIZE (1..32))
     MAX-ACCESS  not-accessible
     STATUS      current
     DESCRIPTION
         "
         Indicates the name of ivr-config.
         "
     ::= { hwEntPbxIvrFileEntry 1 }      
  
  hwEntPbxIvrFileRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxIvrFileEntry 2 }  
     
  hwEntPbxIvrFilePath OBJECT-TYPE
     SYNTAX      DisplayString(SIZE (1..64))
     MAX-ACCESS  read-create
     STATUS      current
     DESCRIPTION
         "
         Indicates the ivr file-path of the ivrfile.
         "
     ::= { hwEntPbxIvrFileEntry 3 }   
   --==============================================================           
  hwEntPbxNumberMapTable OBJECT-TYPE
     SYNTAX      SEQUENCE OF HwEntPbxNumberMapEntry
     MAX-ACCESS  not-accessible
     STATUS      current
     DESCRIPTION
       "
       A list of hwEntPbxNumberMapEntry objects.
       "
     ::= { hwEntVoicePbxMIB 78 }

  hwEntPbxNumberMapEntry OBJECT-TYPE
     SYNTAX      HwEntPbxNumberMapEntry
     MAX-ACCESS  not-accessible
     STATUS      current
     DESCRIPTION
       ""
     INDEX    {
               hwEntPbxNumberMapName   
              }
     ::= { hwEntPbxNumberMapTable 1 }

  HwEntPbxNumberMapEntry ::=
     SEQUENCE
     {
       hwEntPbxNumberMapName                           DisplayString,
       hwEntPbxNumberMapRowStatus                      RowStatus,
       hwEntPbxNumberMapEnterpriseName                 DisplayString,
       hwEntPbxNumberMapExternNumber                   DisplayString,
       hwEntPbxNumberMapInnerNumber                    DisplayString
     }

  hwEntPbxNumberMapName OBJECT-TYPE
     SYNTAX      DisplayString(SIZE (1..32))
     MAX-ACCESS  not-accessible
     STATUS      current
     DESCRIPTION
         "
         Indicates the name of the nubmermap
         "
     ::= { hwEntPbxNumberMapEntry 1 } 
 
  hwEntPbxNumberMapRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxNumberMapEntry 2 }  
 
   hwEntPbxNumberMapEnterpriseName OBJECT-TYPE
     SYNTAX      DisplayString(SIZE (1..32))
     MAX-ACCESS  read-create
     STATUS      current
     DESCRIPTION
         "
         Indicates the enterprise of the nubmermap record.
         "
     ::= { hwEntPbxNumberMapEntry 3 } 
  
  hwEntPbxNumberMapExternNumber OBJECT-TYPE
     SYNTAX      DisplayString(SIZE (1..32))
     MAX-ACCESS  read-create
     STATUS      current
     DESCRIPTION
         "
         Indicates the extern number of the nubmermap
         "
     ::= { hwEntPbxNumberMapEntry 4 }   
  hwEntPbxNumberMapInnerNumber OBJECT-TYPE
     SYNTAX      DisplayString(SIZE (1..32))
     MAX-ACCESS  read-create
     STATUS      current
     DESCRIPTION
         "
         Indicates the inner number of the numbermap.
         "
     ::= { hwEntPbxNumberMapEntry 5 }   

   --==============================================================           
  hwEntPbxSrvVoiceMailCfxTable OBJECT-TYPE
     SYNTAX      SEQUENCE OF HwEntPbxSrvVoiceMailCfxEntry
     MAX-ACCESS  not-accessible
     STATUS      current
     DESCRIPTION
       "
       A list of hwEntPbxSrvVoiceMailCfxEntry objects.
       "
     ::= { hwEntVoicePbxMIB 79 }

  hwEntPbxSrvVoiceMailCfxEntry OBJECT-TYPE
     SYNTAX      HwEntPbxSrvVoiceMailCfxEntry
     MAX-ACCESS  not-accessible
     STATUS      current
     DESCRIPTION
       ""
     INDEX    {
               hwEntPbxSrvVoiceMailCfxUserName,
               hwEntPbxSrvVoiceMailCfxType
              }
     ::= { hwEntPbxSrvVoiceMailCfxTable 1 }

  HwEntPbxSrvVoiceMailCfxEntry ::=
     SEQUENCE
     {
       hwEntPbxSrvVoiceMailCfxUserName                   DisplayString,
       hwEntPbxSrvVoiceMailCfxType                       INTEGER,
       hwEntPbxSrvVoiceMailCfxRowStatus                  RowStatus,
       hwEntPbxSrvVoiceMailCfxUmsNo                      Unsigned32,
       hwEntPbxSrvVoiceMailCfxActive                     INTEGER,
       hwEntPbxSrvVoiceMailCfxCfnrTime                   Integer32
     }

  hwEntPbxSrvVoiceMailCfxUserName OBJECT-TYPE
     SYNTAX      DisplayString(SIZE (1..32))
     MAX-ACCESS  not-accessible
     STATUS      current
     DESCRIPTION
         "
         Indicates pbxusername of the vms service.
         "
     ::= { hwEntPbxSrvVoiceMailCfxEntry 1 } 
    
  hwEntPbxSrvVoiceMailCfxType OBJECT-TYPE
     SYNTAX      INTEGER{vcfu(1),vcfb(2),vcfnr(3),vcfo(4),vcfc(5)}
     MAX-ACCESS  not-accessible
     STATUS      current
     DESCRIPTION
         "
         Indicates vms Cfx-type of the vms service.
         vcfu(1),
         vcfb(2),
         vcfnr(3),
         vcfo(4),
         vcfc(5);
         "
     ::= { hwEntPbxSrvVoiceMailCfxEntry 2 } 
 
  hwEntPbxSrvVoiceMailCfxRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxSrvVoiceMailCfxEntry 3 }  
     
  hwEntPbxSrvVoiceMailCfxUmsNo OBJECT-TYPE
     SYNTAX      Unsigned32
     MAX-ACCESS  read-create
     STATUS      current
     DESCRIPTION
         "
         Indicates umsNo for the certain vms-cfx service.
         "
     ::= { hwEntPbxSrvVoiceMailCfxEntry 4 } 

  hwEntPbxSrvVoiceMailCfxActive OBJECT-TYPE
     SYNTAX      INTEGER{false(1),true(2)}
     MAX-ACCESS  read-create
     STATUS      current
     DESCRIPTION
         "
         Indicates whether active the certain vms-cfx service.
         "
     ::= { hwEntPbxSrvVoiceMailCfxEntry 5 } 

  hwEntPbxSrvVoiceMailCfxCfnrTime OBJECT-TYPE
     SYNTAX      Integer32(5..55)
     MAX-ACCESS  read-create
     STATUS      current
     DESCRIPTION
         "
         Indicates the non-response time config for certain vms-cfnr service.
         "
     ::= { hwEntPbxSrvVoiceMailCfxEntry 6 } 
   --==============================================================           
  hwEntPbxUmsCfgTable OBJECT-TYPE
     SYNTAX      SEQUENCE OF HwEntPbxUmsCfgEntry
     MAX-ACCESS  not-accessible
     STATUS      current
     DESCRIPTION
       "
       A list of hwEntPbxUmsCfgEntry objects.
       "
     ::= { hwEntVoicePbxMIB 80 }

  hwEntPbxUmsCfgEntry OBJECT-TYPE
     SYNTAX      HwEntPbxUmsCfgEntry
     MAX-ACCESS  not-accessible
     STATUS      current
     DESCRIPTION
       ""
     INDEX    {
               hwEntPbxUmsCfgUmsNo
              }
     ::= { hwEntPbxUmsCfgTable 1 }

  HwEntPbxUmsCfgEntry ::=
     SEQUENCE
     {    
       hwEntPbxUmsCfgUmsNo                      Unsigned32,
       hwEntPbxUmsCfgRowStatus                  RowStatus,
       hwEntPbxUmsCfgCallprefix                 DisplayString
     }

  hwEntPbxUmsCfgUmsNo OBJECT-TYPE
     SYNTAX      Unsigned32
     MAX-ACCESS  not-accessible
     STATUS      current
     DESCRIPTION
         "
         Indicates ums No.
         "
     ::= { hwEntPbxUmsCfgEntry 1 } 
    
  hwEntPbxUmsCfgRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxUmsCfgEntry 2 }  
     
  hwEntPbxUmsCfgCallprefix OBJECT-TYPE
     SYNTAX      DisplayString(SIZE (1..32))
     MAX-ACCESS  read-create
     STATUS      current
     DESCRIPTION
         "
         Indicates callprefix related to the configed ums.
         "
     ::= { hwEntPbxUmsCfgEntry 3 } 
  --=============================================================

  hwEntPbxVmsFilePathTable OBJECT IDENTIFIER  ::= { hwEntVoicePbxMIB 81 }

  hwEntPbxVmsFilePath  OBJECT-TYPE
        SYNTAX DisplayString(SIZE (1..32))
        MAX-ACCESS read-write
        STATUS current
        DESCRIPTION
              "
              Indicates the VMS file path.
              "
    ::= { hwEntPbxVmsFilePathTable 1 }
   --==============================================================           
  hwEntPbxUnicallCfgTable OBJECT-TYPE
     SYNTAX      SEQUENCE OF HwEntPbxUnicallCfgEntry
     MAX-ACCESS  not-accessible
     STATUS      current
     DESCRIPTION
       "
       A list of hwEntPbxUnicallCfgEntry objects.
       "
     ::= { hwEntVoicePbxMIB 82 }

  hwEntPbxUnicallCfgEntry OBJECT-TYPE
     SYNTAX      HwEntPbxUnicallCfgEntry
     MAX-ACCESS  not-accessible
     STATUS      current
     DESCRIPTION
       ""
     INDEX    {
               hwEntPbxUnicallCfgPbxUserName
              }
     ::= { hwEntPbxUnicallCfgTable 1 }

  HwEntPbxUnicallCfgEntry ::=
     SEQUENCE
     {    
       hwEntPbxUnicallCfgPbxUserName                DisplayString,
       hwEntPbxUnicallCfgRowStatus                  RowStatus,
       hwEntPbxUnicallCfgBusySelectMode             INTEGER,
       hwEntPbxUnicallCfgRingMode                   INTEGER,
       hwEntPbxUnicallCfgPriorityMode               INTEGER,
       hwEntPbxUnicallCfgSelectInterval             Integer32
     }

  hwEntPbxUnicallCfgPbxUserName OBJECT-TYPE
     SYNTAX      DisplayString(SIZE (1..32))
     MAX-ACCESS  not-accessible
     STATUS      current
     DESCRIPTION
         "
         Indicates Unicall Pbxuser name.
         "
     ::= { hwEntPbxUnicallCfgEntry 1 } 
    
  hwEntPbxUnicallCfgRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxUnicallCfgEntry 2 }  
     
  hwEntPbxUnicallCfgBusySelectMode OBJECT-TYPE
     SYNTAX      INTEGER{null(1),all(2),active(3),inactive(4)}
     MAX-ACCESS  read-create
     STATUS      current
     DESCRIPTION
         "
         Indicates Unicall BusySelect mode.
         null(1)
         all(2)
         active(3)
         inactive(4)
         "
     ::= { hwEntPbxUnicallCfgEntry 3 } 

  hwEntPbxUnicallCfgRingMode OBJECT-TYPE
     SYNTAX      INTEGER{alert(1),append(2)}
     MAX-ACCESS  read-create
     STATUS      current
     DESCRIPTION
         "
         Indicates Unicall Ring mode.
         alert(1)
         append(2)
         "
     ::= { hwEntPbxUnicallCfgEntry 4 } 

  hwEntPbxUnicallCfgPriorityMode OBJECT-TYPE
     SYNTAX      INTEGER{dynamic(1),static(2)}
     MAX-ACCESS  read-create
     STATUS      current
     DESCRIPTION
         "
         Indicates Unicall Priority mode.
         dynamic(1)
         static(2)
         "
     ::= { hwEntPbxUnicallCfgEntry 5 } 

   hwEntPbxUnicallCfgSelectInterval OBJECT-TYPE
     SYNTAX      Integer32(5..30)
     MAX-ACCESS  read-create
     STATUS      current
     DESCRIPTION
         "
         Indicates Unicall Select interval(second).
         "
     ::= { hwEntPbxUnicallCfgEntry 6 } 

 --==============================================================           
  hwEntPbxUnicallBindMemberCfgTable OBJECT-TYPE
     SYNTAX      SEQUENCE OF HwEntPbxUnicallBindMemberCfgEntry
     MAX-ACCESS  not-accessible
     STATUS      current
     DESCRIPTION
       "
       A list of hwEntPbxUnicallBindMemberCfgEntry objects.
       "
     ::= { hwEntVoicePbxMIB 83 }

  hwEntPbxUnicallBindMemberCfgEntry OBJECT-TYPE
     SYNTAX      HwEntPbxUnicallBindMemberCfgEntry
     MAX-ACCESS  not-accessible
     STATUS      current
     DESCRIPTION
       ""
     INDEX    {
               hwEntPbxUnicallBindMemberCfgPbxUserName,
               hwEntPbxUnicallBindMemberCfgBindNumber,
               hwEntPbxUnicallBindMemberCfgBindType
              }
     ::= { hwEntPbxUnicallBindMemberCfgTable 1 }

  HwEntPbxUnicallBindMemberCfgEntry ::=
     SEQUENCE
     {    
       hwEntPbxUnicallBindMemberCfgPbxUserName                DisplayString,
       hwEntPbxUnicallBindMemberCfgBindNumber                 DisplayString,
       hwEntPbxUnicallBindMemberCfgBindType                   INTEGER,
       hwEntPbxUnicallBindMemberCfgRowStatus                  RowStatus,
       hwEntPbxUnicallBindMemberCfgPriority                   Integer32,
       hwEntPbxUnicallBindMemberCfgTimeRangeName              DisplayString
     }

  hwEntPbxUnicallBindMemberCfgPbxUserName OBJECT-TYPE
     SYNTAX      DisplayString(SIZE (1..32))
     MAX-ACCESS  not-accessible
     STATUS      current
     DESCRIPTION
         "
         Indicates Unicall Pbxuser name.
         "
     ::= { hwEntPbxUnicallBindMemberCfgEntry 1 } 

  hwEntPbxUnicallBindMemberCfgBindNumber OBJECT-TYPE
     SYNTAX      DisplayString(SIZE (1..32))
     MAX-ACCESS  not-accessible
     STATUS      current
     DESCRIPTION
         "
         Indicates Unicall bind number or ID.
         "
     ::= { hwEntPbxUnicallBindMemberCfgEntry 2 }   
 
  hwEntPbxUnicallBindMemberCfgBindType OBJECT-TYPE
     SYNTAX      INTEGER{internal-no(1),external-no(2),term-id(3)}
     MAX-ACCESS  not-accessible
     STATUS      current
     DESCRIPTION
         "
         Indicates Unicall Bind type.
 internal-no(1),
 external-no(2),
         term-id(3);
         "
     ::= { hwEntPbxUnicallBindMemberCfgEntry 3 } 

  hwEntPbxUnicallBindMemberCfgRowStatus OBJECT-TYPE
     SYNTAX      RowStatus
     MAX-ACCESS  read-create
     STATUS      current
     DESCRIPTION
         "
         RowStatus:
         active(1)
         notInService(2)
         notReady(3)
         createAndGo(4)
         createAndWait(5)
         destroy(6)
         "
     ::= { hwEntPbxUnicallBindMemberCfgEntry 4 }  
     
  hwEntPbxUnicallBindMemberCfgPriority OBJECT-TYPE
     SYNTAX      Integer32(0..3)
     MAX-ACCESS  read-create
     STATUS      current
     DESCRIPTION
         "
         Indicates Unicall Priority for certain bind number.
         "
     ::= { hwEntPbxUnicallBindMemberCfgEntry 5 } 
 
  hwEntPbxUnicallBindMemberCfgTimeRangeName OBJECT-TYPE
     SYNTAX      DisplayString(SIZE (1..32))
     MAX-ACCESS  read-create
     STATUS      current
     DESCRIPTION
         "
         Indicates Unicall TimeRange name for certain bind number.
         "
     ::= { hwEntPbxUnicallBindMemberCfgEntry 6 }  
  
 hwEntPbxSelfServiceHttpServerTable OBJECT-TYPE
     SYNTAX      SEQUENCE OF HwEntPbxSelfServiceHttpServerEntry
     MAX-ACCESS  not-accessible
     STATUS      current
     DESCRIPTION
       "
       A list of hwEntPbxSelfServiceHttpServerEntry objects.
       "
     ::= { hwEntVoicePbxMIB 84 }

   hwEntPbxSelfServiceHttpServerEntry OBJECT-TYPE
     SYNTAX      HwEntPbxSelfServiceHttpServerEntry
     MAX-ACCESS  not-accessible
     STATUS      current
     DESCRIPTION
       ""
     INDEX    {
               hwEntPbxSelfServiceHttpServerIndex
              }
     ::= { hwEntPbxSelfServiceHttpServerTable 1 }

   HwEntPbxSelfServiceHttpServerEntry ::=
     SEQUENCE
     {
        hwEntPbxSelfServiceHttpServerIndex           Integer32,
        hwEntPbxSelfServiceHttpServerRowStatus       RowStatus,
        hwEntPbxSelfServiceHttpServerPort            Integer32,
        hwEntPbxSelfServiceHttpSecureServerPort      Integer32,
        hwEntPbxSelfServiceHttpServerStatus          INTEGER,
        hwEntPbxSelfServiceHttpSecureServerStatus    INTEGER
     }

   hwEntPbxSelfServiceHttpServerIndex OBJECT-TYPE
     SYNTAX      Integer32
     MAX-ACCESS  not-accessible
     STATUS      current
     DESCRIPTION
         "
         Indicates the index of self service http server.
         index must be 0 now.
         "
     ::= { hwEntPbxSelfServiceHttpServerEntry 1 }
  
   hwEntPbxSelfServiceHttpServerRowStatus OBJECT-TYPE
     SYNTAX      RowStatus
     MAX-ACCESS  read-create
     STATUS      current
     DESCRIPTION
         "
         Indicates row status of table.
         active(1)
         notInService(2)
         notReady(3)
         createAndGo(4)
         createAndWait(5)
         destroy(6)
         "
     ::= { hwEntPbxSelfServiceHttpServerEntry 2 }

  hwEntPbxSelfServiceHttpServerPort OBJECT-TYPE
     SYNTAX      Integer32(1025..51200)
     MAX-ACCESS  read-create
     STATUS      current
     DESCRIPTION
         "
         Indicates self service http server port.
         "
     ::= { hwEntPbxSelfServiceHttpServerEntry 3 }

  hwEntPbxSelfServiceHttpSecureServerPort  OBJECT-TYPE
     SYNTAX      Integer32(1025..51200)
     MAX-ACCESS  read-create
     STATUS      current
     DESCRIPTION
         "
         Indicates self service http secure-server port.
         "
     ::= { hwEntPbxSelfServiceHttpServerEntry 4 }
     
  hwEntPbxSelfServiceHttpServerStatus  OBJECT-TYPE
     SYNTAX      INTEGER{disable(1),enable(2)}
     MAX-ACCESS  read-create
     STATUS      current
     DESCRIPTION
         "
         Indicates self service http server status.
         "
     ::= { hwEntPbxSelfServiceHttpServerEntry 5 }    
     
  hwEntPbxSelfServiceHttpSecureServerStatus  OBJECT-TYPE
     SYNTAX      INTEGER{disable(1),enable(2)}
     MAX-ACCESS  read-create
     STATUS      current
     DESCRIPTION
         "
         Indicates self service http secure-server status.
         "
     ::= { hwEntPbxSelfServiceHttpServerEntry 6 }          
   
    --  ============== conformance information ==============
        hwEntVoicePbxConformance OBJECT IDENTIFIER ::= { hwEntVoicePbxMIB 100 }


        hwEntVoicePbxCompliances OBJECT IDENTIFIER ::= { hwEntVoicePbxConformance 1 }
        hwEntVoicePbxCompliance  MODULE-COMPLIANCE
               STATUS      current
               DESCRIPTION
                   "The compliance statement for systems supporting the this module."

               MODULE      -- this module
               MANDATORY-GROUPS    {hwEntPbxEnterpriseGroup, hwEntPbxDnsetGroup, hwEntPbxCentrexGroup, hwEntPbxCountryCodeGroup, 
               			hwEntPbxAreaCodeGroup, hwEntPbxDefaultCodeGroup, hwEntPbxCallprefixGroup, hwEntPbxSIPServerConfigGroup, 
               			hwEntPbxSIPServerRunningGroup, hwEntPbxUserGroup, hwEntPbxTrkGrpConfigGroup, hwEntPbxTrkGrpRunningGroup, 
               			hwEntPbxAt0TrkGroup, hwEntPbxSipAt0TrkGroup, hwEntPbxPraTrkGroup, hwEntPbxCdrServerGroup, hwEntPbxRouteGroup, 
               			hwEntPbxCallerChgGroup, hwEntPbxBeforeRouteChgGroup, hwEntPbxAfterRouteChgGroup, hwEntPbxUsrGrpGroup, 
               			hwEntPbxGrpMemGroup, hwEntPbxSrvPswGroup, hwEntPbxSrvDlcGroup, hwEntPbxCrbtFileGroup, hwEntPbxSrvCrbtGroup, 
               			hwEntPbxUserParaGroup, hwEntPbxStaticConflictGroup, hwEntPbxDynamicConflictGroup, hwEntPbxSrvCfxGroup, 
               			hwEntPbxSrvRacGroup, hwEntPbxSrvScaGroup, hwEntPbxSrvDndGroup, hwEntPbxSrvWakeGroup, hwEntPbxSrvAbbGroup, 
               			hwEntPbxSrvRcsGroup, hwEntPbxSrvScrGroup, hwEntPbxSrvRmtGroup, hwEntPbxSrvCbaGroup, hwEntPbxSrvCallInterceptGroup, 
               			hwEntPbxSrvAlertRingGroup, hwEntPbxE1r2TrkGroup, hwEntPbxSystemParaGroup, hwEntPbxIsdnCauseMapGroup, 
               			hwEntPbxSipCauseMapGroup, hwEntPbxTrkGrpCodecPriConfigGroup, hwEntPbxTrkGrpCodecPriRunningGroup, 
               			hwEntPbxSIPServerCodecPriConfigGroup, hwEntPbxSIPServerCodecPriRunningGroup, hwEntPbxTrkGrpSoftParaConfigGroup, 
               			hwEntPbxTrkGrpSoftParaRunningGroup, hwEntPbxSIPServerSoftParaConfigGroup, hwEntPbxSIPServerSoftParaRunningGroup, 
               			hwEntPbxConfHallConfigGroup, hwEntPbxConfRegConfigGroup, hwEntPbxConfOperGroup, hwEntPbxConfAttendeeOperGroup,
               			hwEntPbxSignalTraceConfigGroup,hwEntPbxMeasureConfigGroup,hwEntPbxUserStateTraceGroup,
               			hwEntPbxConferenceAttributeGroup,hwEntPbxCallPrefixCallrouteGroup,hwEntPbxNewCallerChgGroup,
               			hwEntPbxCallRouteConfigGroup,hwEntPbxRerouteDealConfigGroup,
               			hwEntPbxTimeTempletGroup,hwEntPbxCallSourceGroup,hwEntPbxRouteAnalysisGroup,hwEntPbxTrkGrpCallRouteConfigGroup,
               			hwEntPbxConfConfigGroup,hwEntPbxConferenceAttendeeCfgGroup,hwEntPbxAlarmParaGroup,
               			hwEntPbxTrapsGroup,hwEntPbxVoiceFileGroup,hwEntPbxIvrTimeIndexGroup,
               			hwEntPbxIvrGroup,hwEntPbxIvrFileGroup,hwEntPbxNumberMapGroup,
               			hwEntPbxSrvVoiceMailCfxGroup,hwEntPbxUmsCfgGroup,hwEntPbxVmsFilePathGroup,
               			hwEntPbxUnicallCfgGroup,hwEntPbxUnicallBindMemberCfgGroup,hwEntPbxSelfServiceHttpServerGroup } 
                                               
              ::= { hwEntVoicePbxCompliances 1 }  
              
          
        --  ============== groups ==============  
        hwEntVoicePbxGroups OBJECT IDENTIFIER ::= { hwEntVoicePbxConformance 2 } 
        
        hwEntPbxEnterpriseGroup OBJECT-GROUP
            OBJECTS {
	       hwEntPbxEnterpriseName,
	       hwEntPbxEnterpriseRowStatus,
	       hwEntPbxEnterpriseDesc,
	       hwEntPbxEnterpriseCentrexNum,
	       hwEntPbxEnterpriseDnsetNum,
	       hwEntPbxEnterpriseSvrRightCrbt
                
             }       
            STATUS current
            DESCRIPTION 
                "The hwEntPbxEnterprise group."
            ::= { hwEntVoicePbxGroups 1 }


        hwEntPbxDnsetGroup OBJECT-GROUP
            OBJECTS {
	       hwEntPbxDnsetEnterpriseName,
	       hwEntPbxDnsetName,
	       hwEntPbxDnsetRowStatus,
	       hwEntPbxDnsetDesc        
	     }                  
            STATUS current
            DESCRIPTION 
                "The hwEntPbxDnsetGroup group."
            ::= { hwEntVoicePbxGroups 2 }
            
        hwEntPbxCentrexGroup OBJECT-GROUP
            OBJECTS {
	      	hwEntPbxCentrexEnterpriseName,
       		hwEntPbxCentrexName,
	       	hwEntPbxCentrexRowStatus,
	       	hwEntPbxCentrexDesc
	       	       
	     }            
            STATUS current
            DESCRIPTION 
                "The hwEntPbxCentrexGroup group."
            ::= { hwEntVoicePbxGroups 3 }
            
        hwEntPbxCountryCodeGroup OBJECT-GROUP
            OBJECTS { 
               hwEntPbxCountryCode,
	       hwEntPbxCountryCodeRowStatus,
	       hwEntPbxCountryName,
	       hwEntPbxInternationalPrefix,
	       hwEntPbxNationalPrefix 
                              
                    }            
            STATUS current
            DESCRIPTION 
                "The hwEntPbxCountryCodeGroup group."
            ::= { hwEntVoicePbxGroups 4 }
            
        hwEntPbxAreaCodeGroup OBJECT-GROUP
            OBJECTS { 
                hwEntPbxAreaCodeCountryCode,
	       hwEntPbxAreaCode,
	       hwEntPbxAreaCodeRowStatus,
	       hwEntPbxAreaName             
                }
            STATUS current
            DESCRIPTION 
                "The hwEntPbxAreaCodeGroup Group."
            ::= { hwEntVoicePbxGroups 5 }
  
	hwEntPbxDefaultCodeGroup OBJECT-GROUP
            OBJECTS { 
                hwEntDefaultCountryCode,
		hwEntDefaultAreaCode            
                }
            STATUS current
            DESCRIPTION 
                "The hwEntPbxDefaultCode Group."
            ::= { hwEntVoicePbxGroups 6 }
           
        hwEntPbxCallprefixGroup OBJECT-GROUP
           OBJECTS {
	      hwEntPbxCallprefixName,
	       hwEntPbxCallprefixRowStatus,
	       hwEntPbxCallprefixPrefix,
	       hwEntPbxCallprefixEnterprise,
	       hwEntPbxCallprefixDnset,
	       hwEntPbxCallprefixCentrex,
	       hwEntPbxCallprefixcallCategory,
	       hwEntPbxCallprefixCallAttribute,
	       hwEntPbxCallprefixMaxLen,
	       hwEntPbxCallprefixMinLen,
	       hwEntPbxCallprefixDstLocation,
	       hwEntPbxCallprefixRingDelay,
	       hwEntPbxCallprefixLongCaller,
	       hwEntPbxCallprefixCallerMap,
	       hwEntPbxCallprefixCalledMap,
	       hwEntPbxCallprefixCallRoute,
	       hwEntPbxCallprefixVuServiceName,
	       hwEntPbxCallprefixVuLoopCount,
	       hwEntPbxCallprefixVuOutGoingRightDdd,
	       hwEntPbxCallprefixVuOutGoingRightIdd,
	       hwEntPbxCallprefixVuOutGoingRightInter,
	       hwEntPbxCallprefixVuOutGoingRightLocal,
	       hwEntPbxCallprefixPwdCallLimit
	     }
            STATUS current
            DESCRIPTION 
                "The hwEntPbxCallprefixGroup group."
            ::= { hwEntVoicePbxGroups 7 }             
                    
        hwEntPbxSIPServerConfigGroup OBJECT-GROUP
            OBJECTS { 
               hwEntPbxSIPServerIndex,
	       hwEntPbxSIPServerRowStatus,
	       hwEntPbxSIPServerSignallingIP,
	       hwEntPbxSIPServerSignallingPort,
	       hwEntPbxSIPServerMediaIP,
	       hwEntPbxSIPServerRegUri,
	       hwEntPbxSIPServerHomeDomain,
	       hwEntPbxSipServerSignallingDomain,
	       hwEntPbxSipServerDdnsClientName,
	       hwEntPbxSipServerDynSignallingIPName,
	       hwEntPbxSipServerDynMediaIPName,
	       hwEntPbxSIPServerTransfer,
	       hwEntPbxSIPServerCSmode,
	       hwEntPbxSIPServerSignallingProxy,
	       hwEntPbxSIPServerMediaProxy,
	       hwEntPbxSIPServerMappedSignallingIP,
	       hwEntPbxSIPServerMappedSignallingPort,
	       hwEntPbxSIPServerMappedMediaIP,
	       hwEntPbxSIPServerMappedMediaPortStart,
	       hwEntPbxSIPServerMappedMediaProxyPortStart,
	       hwEntPbxSIPServerAdminStatus
                    }            
            STATUS current
            DESCRIPTION 
                "The hwEntPbxSIPServerConfigGroup group."
            ::= { hwEntVoicePbxGroups 8 }            
 
        hwEntPbxSIPServerRunningGroup OBJECT-GROUP
            OBJECTS { 
	       hwEntPbxSIPServerRunningSIPServerIndex,
	       hwEntPbxSIPServerRunningSignallingIP,
	       hwEntPbxSIPServerRunningSignallingPort,
	       hwEntPbxSIPServerRunningMediaIP,
	       hwEntPbxSIPServerRunningRegUri,
	       hwEntPbxSIPServerRunningHomeDomain,
	       hwEntPbxSIPServerRunningSignalDomain,
	       hwEntPbxSIPServerRunningDdnsClientName,
	       hwEntPbxSIPServerRunningDynSignallingIPName,
	       hwEntPbxSIPServerRunningDynMediaIPName,
	       hwEntPbxSIPServerRunningTransfer,
	       hwEntPbxSIPServerRunningCSmode,
	       hwEntPbxSIPServerRunningSignallingProxy,
	       hwEntPbxSIPServerRunningMediaProxy,
	       hwEntPbxSIPServerRunningMappedSignallingIP,
	       hwEntPbxSIPServerRunningMappedSignallingPort,
	       hwEntPbxSIPServerRunningMappedMediaIP,
	       hwEntPbxSIPServerRunningMappedMediaPortStart,
	       hwEntPbxSIPServerRunningMappedMediaProxyPortStart,
	       hwEntPbxSIPServerRunningState
	     }       
            STATUS current
            DESCRIPTION 
                "The hwEntPbxSIPServerRunningGroup group."
            ::= { hwEntVoicePbxGroups 9 } 

	hwEntPbxUserGroup OBJECT-GROUP
            OBJECTS { 
	       hwEntPbxUserName,
	       hwEntPbxUserRowStatus,
	       hwEntPbxUserType,
	       hwEntPbxUserPrivateId,
	       hwEntPbxUserEnterprise,
	       hwEntPbxUserCountryCode,
	       hwEntPbxUserAreaCode,
	       hwEntPbxUserTelno,
	       hwEntPbxUserKind,
	       hwEntPbxUserStatus,
	       hwEntPbxUserCentrex,
	       hwEntPbxUserCentrexNumber,
	       hwEntPbxUserDnSet,
	       hwEntPbxUserInRight,
	       hwEntPbxUserOutRight,
	       hwEntPbxUserNewServiceRight,
	       hwEntPbxUserNewServiceActive,
	       hwEntPbxUserMsnIndex,
	       hwEntPbxUserPasswordType,
	       hwEntPbxUserPassword,
	       hwEntPbxUserRegState,
	       hwEntPbxUserSrvState,
	       hwEntPbxUserLongDn,
	       hwEntPbxUserPwd,
	       hwEntPbxUserInRightInner,
	       hwEntPbxUserInRightLocal,
	       hwEntPbxUserInRightDdd,
	       hwEntPbxUserInRightIdd,
	       hwEntPbxUserOutRightInner,
	       hwEntPbxUserOutRightLocal,
	       hwEntPbxUserOutRightDdd,
	       hwEntPbxUserOutRightIdd,
	       hwEntPbxUserTelnoPassword,
	       hwEntPbxUserPriorityValue  
	     }       
            STATUS current
            DESCRIPTION 
                "The hwEntPbxUserGroup group."
            ::= { hwEntVoicePbxGroups 10 } 

	hwEntPbxTrkGrpConfigGroup OBJECT-GROUP
            OBJECTS { 
	       hwEntPbxTrkGrpName ,
	       hwEntPbxTrkGrpRowStatus,
	       hwEntPbxTrkGrpSignalType,
	       hwEntPbxTrkGrpDesc,
	       hwEntPbxTrkGrpSelectMode,
	       hwEntPbxTrkGrpEnterpriseName,
	       hwEntPbxTrkGrpDnSet,
	       hwEntPbxTrkGrpCountryCode,
	       hwEntPbxTrkGrpAreaCode,
	       hwEntPbxTrkGrpInRight,
	       hwEntPbxTrkGrpOutRight,
	       hwEntPbxTrkGrpPraStandard,
	       hwEntPbxTrkGrpIpGrpRegMode,
	       hwEntPbxTrkGrpSignallingIP,
	       hwEntPbxTrkGrpSignallingPort,
	       hwEntPbxTrkGrpMediaIP,
	       hwEntPbxTrkGrpIpGrpPeerAddrMode,
	       hwEntPbxTrkGrpPrimaryPeerIP,
	       hwEntPbxTrkGrpPrimaryPeerPort,
	       hwEntPbxTrkGrpIpGrpPeerSecondaryIP,
	       hwEntPbxTrkGrpIpGrpPeerSecondaryPort,
	       hwEntPbxTrkGrpPrimaryPeerDomain,
	       hwEntPbxTrkGrpIpGrpPeerSecondaryDomain,
	       hwEntPbxTrkGrpMaxCallNum,
	       hwEntPbxTrkGrpRegUri,
	       hwEntPbxTrkGrpHomeDomain,
	       hwEntPbxTrkGrpMgcType,
	       hwEntPbxTrkGrpTransfer,
	       hwEntPbxTrkGrpCSmode,
	       hwEntPbxTrkGrpRegID,
	       hwEntPbxTrkGrpRegPwdType,
	       hwEntPbxTrkGrpRegPwd,
	       hwEntPbxTrkGrpDefaultCallerNum,
	       hwEntPbxTrkGrpDynSignallingIPName,
	       hwEntPbxTrkGrpDynMediaIPName,
	       hwEntPbxTrkGrpMediaProxy,
	       hwEntPbxTrkGrpMappedSignallingIP,
	       hwEntPbxTrkGrpMappedSignallingPort,
	       hwEntPbxTrkGrpMappedMediaIP,
	       hwEntPbxTrkGrpMappedMediaPortStart,
	       hwEntPbxTrkGrpMappedMediaProxyPortStart,
	       hwEntPbxTrkGrpR2ProfileName,
	       hwEntPbxTrkGrpR2IsEarlyMedia,
	       hwEntPbxTrkGrpR2PlayRingback,
	       hwEntPbxTrkGrpAdminStatus,
	       hwEntPbxTrkGrpOutGoingRightInner,
               hwEntPbxTrkGrpOutGoingRightLocal,
               hwEntPbxTrkGrpOutGoingRightDdd,
               hwEntPbxTrkGrpOutGoingRightIdd,
               hwEntPbxTrkGrpCallerNumberType,
               hwEntPbxTrkGrpCalledNumberType 
	     }       
            STATUS current
            DESCRIPTION 
                "The hwEntPbxTrkGrpConfigGroup group."
            ::= { hwEntVoicePbxGroups 11 } 
            
	hwEntPbxTrkGrpRunningGroup OBJECT-GROUP
            OBJECTS { 
	       hwEntPbxTrkGrpRunningTrkGrpName,
	       hwEntPbxTrkGrpRunningState,
	       hwEntPbxTrkGrpRunningSipRegState,
	       hwEntPbxTrkGrpRunningSignalType,
	       hwEntPbxTrkGrpRunningDesc,
	       hwEntPbxTrkGrpRunningSelectMode,
	       hwEntPbxTrkGrpRunningEnterprise,
	       hwEntPbxTrkGrpRunningDnSet,
	       hwEntPbxTrkGrpRunningCountryCode,
	       hwEntPbxTrkGrpRunningAreaCode,
	       hwEntPbxTrkGrpRunningInRight,
	       hwEntPbxTrkGrpRunningOutRight,
	       hwEntPbxTrkGrpRunningPraStandard,
	       hwEntPbxTrkGrpRunningIpGrpRegMode,
	       hwEntPbxTrkGrpRunningSignallingIP,
	       hwEntPbxTrkGrpRunningSignallingPort,
	       hwEntPbxTrkGrpRunningMediaIP,
	       hwEntPbxTrkGrpRunningIpGrpPeerAddrMode,
	       hwEntPbxTrkGrpRunningPrimaryPeerIP,
	       hwEntPbxTrkGrpRunningPrimaryPeerPort,
	       hwEntPbxTrkGrpRunningPeerSecondaryIP,
	       hwEntPbxTrkGrpRunningPeerSecondaryPort,
	       hwEntPbxTrkGrpRunningPrimaryPeerDomain,
	       hwEntPbxTrkGrpRunningIpGrpPeerSecondaryDomain,
	       hwEntPbxTrkGrpRunningMaxCallNum,
	       hwEntPbxTrkGrpRunningTransfer,
	       hwEntPbxTrkGrpRunningRegUri,
	       hwEntPbxTrkGrpRunningHomeDomain,
	       hwEntPbxTrkGrpRunningMgcType,
	       hwEntPbxTrkGrpRunningRegID,
	       hwEntPbxTrkGrpRunningRegPwdType,
	       hwEntPbxTrkGrpRunningRegPwd,
	       hwEntPbxTrkGrpRunningDefaultCallerNum,
	       hwEntPbxTrkGrpRunningDynSignallingIPName,
	       hwEntPbxTrkGrpRunningDynMediaIPName,
	       hwEntPbxTrkGrpRunningCSmode,
	       hwEntPbxTrkGrpRunningMediaProxy,
	       hwEntPbxTrkGrpRunningMappedSignallingIP,
	       hwEntPbxTrkGrpRunningMappedSignallingPort,
	       hwEntPbxTrkGrpRunningMappedMediaIP,
	       hwEntPbxTrkGrpRunningMappedMediaPortStart,
	       hwEntPbxTrkGrpRunningMappedMediaProxyPortStart,
	       hwEntPbxTrkGrpRunningR2Profile,
	       hwEntPbxTrkGrpRunningR2IsEarlyMedia,
	       hwEntPbxTrkGrpRunningR2PlayRingback 
	     }       
            STATUS current
            DESCRIPTION 
                "The hwEntPbxTrkGrpRunningGroup group."
            ::= { hwEntVoicePbxGroups 12 }
            
	hwEntPbxAt0TrkGroup OBJECT-GROUP
            OBJECTS { 
	       hwEntPbxAt0TrkIndex,
	       hwEntPbxAt0TrkRowStatus,
	       hwEntPbxAt0TrkPhyStatus,
	       hwEntPbxAt0TrkSrvState,
	       hwEntPbxAt0TrkGroupName,
	       hwEntPbxAt0TrkDialDelay,
	       hwEntPbxAt0TrkInsertPrefix,
	       hwEntPbxAt0TrkInsertDelay,
	       hwEntPbxAt0ReversePole,
	       hwEntPbxAt0TrkDefaultCalledNum,
	       hwEntPbxAt0TrkCidTransType,
	       hwEntPbxAt0PTPDialMode     
	     }       
            STATUS current
            DESCRIPTION 
                "The hwEntPbxAt0TrkGroup group."
            ::= { hwEntVoicePbxGroups 13 }
            
	hwEntPbxSipAt0TrkGroup OBJECT-GROUP
            OBJECTS { 
	       hwEntPbxSipAt0TrkGrpName,
	       hwEntPbxSipAt0TrkRegister,
	       hwEntPbxSipAt0TrkRowStatus,
	       hwEntPbxSipAt0TrkAdminStatus,
	       hwEntPbxSipAt0TrkRegStatus,
	       hwEntPbxSipAt0TrkDefaultCalledNum,
	       hwEntPbxSipAt0TrkPwdType,
	       hwEntPbxSipAt0TrkPwd,
	       hwEntPbxSipAt0TrkCallerEnterprise,
	       hwEntPbxSipAt0TrkCallerCountryCode,
	       hwEntPbxSipAt0TrkCallerAreaCode,
	       hwEntPbxSipAt0TrkCallerNum  
	     }       
            STATUS current
            DESCRIPTION 
                "The hwEntPbxSipAt0TrkGroup group."
            ::= { hwEntVoicePbxGroups 14 }
            
 	hwEntPbxPraTrkGroup OBJECT-GROUP
            OBJECTS { 
	       hwEntPbxPraTrkIndex,
	        hwEntPbxPraTrkRowStatus,
	        hwEntPbxPraTrkGroupName,
	        hwEntPbxPraTrkAdminStatus
	     }       
            STATUS current
            DESCRIPTION 
                "The hwEntPbxPraTrkGroupp group."
            ::= { hwEntVoicePbxGroups 15 }
            
	hwEntPbxCdrServerGroup OBJECT-GROUP
            OBJECTS { 
	       hwEntPbxCdrServerProtocolType,
	        hwEntPbxCdrServerRowStatus,
	        hwEntPbxCdrServerLocalIp,
	        hwEntPbxCdrServerLocalPort,
	        hwEntPbxCdrServerServerIp,
	        hwEntPbxCdrServerServerPort,
	        hwEntPbxCdrServerUserName,
	        hwEntPbxCdrServerPasswordType,
	        hwEntPbxCdrServerPassword,
	        hwEntPbxCdrServerState,
	        hwEntPbxCdrServerIsTextField0,
	        hwEntPbxCdrServerIsTextField1,
	        hwEntPbxCdrServerbillPoolUsed,
	        hwEntPbxCdrServerbillPoolMax,
	        hwEntPbxCdrServerbillPoolAlarm,
	        hwEntPbxCdrServerbillPoolAlarmState,
	        hwEntPbxCdrServerbillPoolFullDiscard,
	        hwEntPbxCdrServerCallerLimit,
	        hwEntPbxCdrServerCallerInteroffice,
	        hwEntPbxCdrServerCallerLocal,
	        hwEntPbxCdrServerCallerLocaltoll,
	        hwEntPbxCdrServerCallerDDD,
	        hwEntPbxCdrServerCallerIDD,
	        hwEntPbxCdrServerCallerUnknown,
	        hwEntPbxCdrServerCalleeLimit,
	        hwEntPbxCdrServerCalleeInteroffice,
	        hwEntPbxCdrServerCalleeLocal,
	        hwEntPbxCdrServerCalleeLocaltoll,
	        hwEntPbxCdrServerCalleeDDD,
	        hwEntPbxCdrServerCalleeIDD,
	        hwEntPbxCdrServerCalleeVU,
	        hwEntPbxCdrServerbillFormat
	     }       
            STATUS current
            DESCRIPTION 
                "The hwEntPbxCdrServerGroup group."
            ::= { hwEntVoicePbxGroups 16 }
            
 	hwEntPbxRouteGroup OBJECT-GROUP
            OBJECTS { 
	       hwEntPbxRouteCallprefixName,
	       hwEntPbxRouteCountryCode,
	       hwEntPbxRouteAreaCode,
	       hwEntPbxRouteCallerNum,
	       hwEntPbxRouteFromDate,
	       hwEntPbxRouteFromTime,
	       hwEntPbxRouteToDate,
	       hwEntPbxRouteToTime,
	       hwEntPbxRouteRepeatMode,
	       hwEntPbxRouteBeginDate,
	       hwEntPbxRouteBeginWeekday,
	       hwEntPbxRouteBeginTime,
	       hwEntPbxRouteEndDate,
	       hwEntPbxRouteEndWeekday,
	       hwEntPbxRouteEndTime,
	       hwEntPbxRouteRowStatus,
	       hwEntPbxRouteTrkGrpName1,
	       hwEntPbxRouteTrkGrpName2,
	       hwEntPbxRouteTrkGrpName3,
	       hwEntPbxRouteTrkGrpName4  
	     }       
            STATUS current
            DESCRIPTION 
                "The hwEntPbxRouteGroup group."
            ::= { hwEntVoicePbxGroups 17 }
            
 	hwEntPbxCallerChgGroup OBJECT-GROUP
            OBJECTS { 
	       hwEntPbxCallerChgEnterprise,
	       hwEntPbxCallerChgDnset,
	       hwEntPbxCallerChgCentrex,
	       hwEntPbxCallerChgCountryCode,
	       hwEntPbxCallerChgAreaCode,
	       hwEntPbxCallerChgCallerNum,
	       hwEntPbxCallerChgRowStatus,
	       hwEntPbxCallerChgChangeType,
	       hwEntPbxCallerChgNewDnSet,
	       hwEntPbxCallerChgNewCentrex,
	       hwEntPbxCallerChgNewCountryCode,
	       hwEntPbxCallerChgNewAreaCode,
	       hwEntPbxCallerChgNewEnterprise
	     }       
            STATUS current
            DESCRIPTION 
                "The hwEntPbxCallerChgGroup group."
            ::= { hwEntVoicePbxGroups 18 }
            
	hwEntPbxBeforeRouteChgGroup OBJECT-GROUP
            OBJECTS { 
	       hwEntPbxBeforeRouteChgName,
	       hwEntPbxBeforeRouteChgCallprefixName,
	       hwEntPbxBeforeRouteChgRowStatus,
	       hwEntPbxBeforeRouteChgCountryCode,
	       hwEntPbxBeforeRouteChgAreaCode,
	       hwEntPbxBeforeRouteChgCallerNum,
	       hwEntPbxBeforeRouteChgCentrexNumber,
	       hwEntPbxBeforeRouteChgOrigDNChgType,
	       hwEntPbxBeforeRouteChgOrigDNChgPos,
	       hwEntPbxBeforeRouteChgOrigDNChgLen,
	       hwEntPbxBeforeRouteChgOrigDNNew,
	       hwEntPbxBeforeRouteChgTermDNChgType,
	       hwEntPbxBeforeRouteChgTermDNChgPos,
	       hwEntPbxBeforeRouteChgTermDNChgLen,
	       hwEntPbxBeforeRouteChgTermDNNew,
	       hwEntPbxBeforeRouteChgReAnalyse,
	       hwEntPbxBeforeRouteChgDualDialToneFlag,
	       hwEntPbxBeforeRouteChgNewEnterprise,
	       hwEntPbxBeforeRouteChgNewDnSet,
	       hwEntPbxBeforeRouteChgNewCentrex  
	     }       
            STATUS current
            DESCRIPTION 
                "The hwEntPbxBeforeRouteChgGroup group."
            ::= { hwEntVoicePbxGroups 19 }
            
	hwEntPbxAfterRouteChgGroup OBJECT-GROUP
            OBJECTS { 
	       hwEntPbxAfterRouteChgName,
	       hwEntPbxAfterRouteChgRowStatus,
	       hwEntPbxAfterRouteChgCallprefixName,
	       hwEntPbxAfterRouteChgCountryCode,
	       hwEntPbxAfterRouteChgAreaCode,
	       hwEntPbxAfterRouteChgCallerNum,
	       hwEntPbxAfterRouteChgCentrexNumber,
	       hwEntPbxAfterRouteChgOrigDNChgType,
	       hwEntPbxAfterRouteChgOrigDNChgPos,
	       hwEntPbxAfterRouteChgOrigDNChgLen,
	       hwEntPbxAfterRouteChgOrigDNNew,
	       hwEntPbxAfterRouteChgTermDNChgType,
	       hwEntPbxAfterRouteChgTermDNChgPos,
	       hwEntPbxAfterRouteChgTermDNChgLen,
	       hwEntPbxAfterRouteChgTermDNNew,
	       hwEntPbxAfterRouteChgTrkGrpName,
	       hwEntPbxAfterRouteChgNewEnterprise,
	       hwEntPbxAfterRouteChgNewCentrex  
	     }       
            STATUS current
            DESCRIPTION 
                "The hwEntPbxAfterRouteChgGroup group."
            ::= { hwEntVoicePbxGroups 20 }
            
	hwEntPbxUsrGrpGroup OBJECT-GROUP
            OBJECTS { 
	       hwEntPbxUsrGrpName,
	        hwEntPbxUsrGrpRowStatus,
	        hwEntPbxUserGroupServiceId,
	        hwEntPbxUsrGrpEnterpriseName,
	        hwEntPbxUsrGrpDnSet,
	        hwEntPbxUserGroupCentrex,
	        hwEntPbxUsrGrpCountryCode,
	        hwEntPbxUsrGrpAreaCode,
	        hwEntPbxUserGrpAccessCode,
	        hwEntPbxUserGrpRegCode,
	        hwEntPbxUserGrpConsoleCode,
	        hwEntPbxUsrGrpDstEnterprise,
	        hwEntPbxUserGrpDstDnset,
	        hwEntPbxUserGrpDstCentrex,
	        hwEntPbxUserGrpMaxQueueNum,
	        hwEntPbxUserGrpToneId,
	        hwEntPbxUsrGrpToneFileName,
	        hwEntPbxUserGrpQueue,
	        hwEntPbxUserGrpQueueTime,
	        hwEntPbxUserGrpRingMode,
	        hwEntPbxUserGrpSelectmode,
	        hwEntPbxUserGrpRingTime,
	        hwEntPbxUsrGrpIvrNaviMenuName,
	        hwEntPbxUsrGrpDirectTransConsole,
	        hwEntPbxUsrGrpMenuName,
	        hwEntPbxUsrGrpMenuOprCode,
	        hwEntPbxUsrGrpCallerNum,
	        hwEntPbxUsrGrpFromDate,
	        hwEntPbxUsrGrpFromTime,
	        hwEntPbxUsrGrpToDate,
	        hwEntPbxUsrGrpToTime,
	        hwEntPbxUsrGrpRepeatMode,
	        hwEntPbxUsrGrpBeginDate,
	        hwEntPbxUsrGrpBeginWeekday,
	        hwEntPbxUsrGrpBeginTime,
	        hwEntPbxUsrGrpEndDate,
	        hwEntPbxUsrGrpEndWeekday,
	        hwEntPbxUsrGrpEndTime
	     }       
            STATUS current
            DESCRIPTION 
                "The hwEntPbxUsrGrpGroup group."
            ::= { hwEntVoicePbxGroups 21 }
            
 	hwEntPbxGrpMemGroup OBJECT-GROUP
            OBJECTS { 
	        hwEntPbxGrpMemUsrGrpName,
	        hwEntPbxGrpMemPbxuser,
	        hwEntPbxGrpMemUnicallTel,
	        hwEntPbxGrpMemFromDate,
	        hwEntPbxGrpMemFromTime,
	        hwEntPbxGrpMemToDate,
	        hwEntPbxGrpMemToTime,
	        hwEntPbxGrpMemRepeatMode,
	        hwEntPbxGrpMemBeginDate,
	        hwEntPbxGrpMemBeginWeekday,
	        hwEntPbxGrpMemBeginTime,
	        hwEntPbxGrpMemEndDate,
	        hwEntPbxGrpMemEndWeekday,
	        hwEntPbxGrpMemEndTime,
	        hwEntPbxGrpMemRowStatus,
	        hwEntPbxGrpMemAdminState,
	        hwEntPbxGrpMemIndex
	     }       
            STATUS current
            DESCRIPTION 
                "The hwEntPbxGrpMemGroup group."
            ::= { hwEntVoicePbxGroups 22 }
            
 	hwEntPbxSrvPswGroup OBJECT-GROUP
            OBJECTS { 
	       hwEntPbxSrvPswUserName,
	        hwEntPbxSrvPswServiceType,
	        hwEntPbxSrvPswPasswordType,
	        hwEntPbxSrvPswServicePassword 
	     }       
            STATUS current
            DESCRIPTION 
                "The hwEntPbxSrvPswGroup group."
            ::= { hwEntVoicePbxGroups 23 }                          
            
       hwEntPbxSrvDlcGroup OBJECT-GROUP
	     OBJECTS { 
	         hwEntPbxSrvDlcUserName,
	         hwEntPbxSrvDlcNum,
	         hwEntPbxSrvDlcRowStatus,
	         hwEntPbxSrvDlcReserved
	     }
	     STATUS current
             DESCRIPTION 
            "The hwEntPbxSrvDlcGroup group."
            ::= { hwEntVoicePbxGroups 24 }  
            
	   hwEntPbxCrbtFileGroup OBJECT-GROUP
	     OBJECTS { 
	        hwEntPbxCrbtFileName,
	        hwEntPbxCrbtFileRowStatus,
	        hwEntPbxCrbtFileDesc,
	        hwEntPbxCrbtType,
	        hwEntPbxCrbtFileCheckStatus,
	        hwEntPbxCrbtFileStorage,
	        hwEntPbxCrbtFileEnterpriseName,
	        hwEntPbxCrbtFileUserName         
	     }
	    STATUS current
            DESCRIPTION 
            "The hwEntPbxCrbtFileGroup group."
            ::= { hwEntVoicePbxGroups 25 }
            
            
	   hwEntPbxSrvCrbtGroup OBJECT-GROUP
	     OBJECTS { 
	        hwEntPbxSrvCrbtEnterpriseName,
	        hwEntPbxSrvCrbtUserName,
	        hwEntPbxSrvCrbtTrkGrpName,
	        hwEntPbxSrvCrbtCallerNum,
	        hwEntPbxSrvCrbtFromDate,
	        hwEntPbxSrvCrbtFromTime,
	        hwEntPbxSrvCrbtToDate,
	        hwEntPbxSrvCrbtToTime,
	        hwEntPbxSrvCrbtRepeatMode,
	        hwEntPbxSrvCrbtBeginDate,
	        hwEntPbxSrvCrbtBeginWeekday,
	        hwEntPbxSrvCrbtBeginTime,
	        hwEntPbxSrvCrbtEndDate,
	        hwEntPbxSrvCrbtEndWeekday,
	        hwEntPbxSrvCrbtEndTime,
	        hwEntPbxSrvCrbtRowStatus,
	        hwEntPbxSrvCrbtFileName          
	    }
	    STATUS current
            DESCRIPTION 
		"The hwEntPbxSrvCrbtGroup group."
            ::= { hwEntVoicePbxGroups 26 }
            
            
	   hwEntPbxUserParaGroup OBJECT-GROUP
	     OBJECTS { 
	        hwEntPbxUserParaName,
	        hwEntPbxUserPriority,
	        hwEntPbxUserLineType,
	        hwEntPbxUserClipTransmissionSequence,
	        hwEntPbxUserClipFormat,
	        hwEntPbxUserDcTime,
	        hwEntPbxUserFskTime,
	        hwEntPbxUserVqeAgc,
	        hwEntPbxUserVqeAgcLevel,
	        hwEntPbxUserVqeSns,
	        hwEntPbxUserVqeSnsLevel,
	        hwEntPbxUserDspInputGain,
	        hwEntPbxUserDspOutputGain,
	        hwEntPbxUserDetectAnsbarBySingleTone,
	        hwEntPbxUserBellAnsFlag,
	        hwEntPbxUserFskMode,
	        hwEntPbxUserTasPattern,
	        hwEntPbxUserSignallingType,
	        hwEntPbxUserDesc,
	        hwEntPbxUserAdminStatus,
	        hwEntPbxUserCTPSrvState,
	        hwEntPbxUserCTPAdmState           
	    }
	    STATUS current
            DESCRIPTION 	
	     "The hwEntPbxUserParaGroup group."
            ::= { hwEntVoicePbxGroups 27 }
            
            
	   hwEntPbxStaticConflictGroup OBJECT-GROUP
	     OBJECTS { 
	        hwEntPbxStaticConflictSrvIndex,
	        hwEntPbxStaticConflictNewService 
	     }
	    STATUS current
            DESCRIPTION 	     
	    "The hwEntPbxStaticConflictGroup group."
            ::= { hwEntVoicePbxGroups 28 }
            
            
	   hwEntPbxDynamicConflictGroup OBJECT-GROUP
	     OBJECTS { 
	        hwEntPbxDynamicConflictSrvIndex,
	        hwEntPbxDynamicConflictNewService 
	     }
	    STATUS current
            DESCRIPTION 
            "The hwEntPbxDynamicConflictGroup group."
            ::= { hwEntVoicePbxGroups 29 }
            
            	     
	   hwEntPbxSrvCfxGroup OBJECT-GROUP
	     OBJECTS { 
	        hwEntPbxSrvCfxUserName,
	        hwEntPbxSrvCfxType,
	        hwEntPbxSrvCfxRowStatus,
	        hwEntPbxSrvCfxNumber,
	        hwEntPbxSrvCfnrTime
	     }        
	    STATUS current
            DESCRIPTION 
            "The hwEntPbxSrvCfxGroup group."
            ::= { hwEntVoicePbxGroups 30 }
            
            	    
	   hwEntPbxSrvRacGroup OBJECT-GROUP
	     OBJECTS { 
	        hwEntPbxSrvRacUserName,
	        hwEntPbxSrvRacRowStatus,
	        hwEntPbxSrvRacToneId
	     }        
	    STATUS current
            DESCRIPTION 
            "The hwEntPbxSrvRacGroup group."
            ::= { hwEntVoicePbxGroups 31 }
            
            	    
	   hwEntPbxSrvScaGroup OBJECT-GROUP
	     OBJECTS { 
	        hwEntPbxSrvScaUserName,
	        hwEntPbxSrvScaJudgeGrp,
	        hwEntPbxSrvScaRowStatus,
	        hwEntPbxSrvScaCallerNum,
	        hwEntPbxSrvScaFromDate,
	        hwEntPbxSrvScaFromTime,
	        hwEntPbxSrvScaToDate,
	        hwEntPbxSrvScaToTime,
	        hwEntPbxSrvScaRepeatMode,
	        hwEntPbxSrvScaBeginDate,
	        hwEntPbxSrvScaBeginWeekday,
	        hwEntPbxSrvScaBeginTime,
	        hwEntPbxSrvScaEndWeekday,
	        hwEntPbxSrvScaEndDate,
	        hwEntPbxSrvScaEndTime,
	        hwEntPbxSrvScaJudgeGroupActive
	     }        
	    STATUS current
            DESCRIPTION 
            "The hwEntPbxSrvScaGroup group."
            ::= { hwEntVoicePbxGroups 32 }
            
            	    
	   hwEntPbxSrvDndGroup OBJECT-GROUP
	     OBJECTS { 
	        hwEntPbxSrvDndUserName,
	        hwEntPbxSrvDndRowStatus,
	        hwEntPbxSrvDndToneId
	     }        
	    STATUS current
            DESCRIPTION 
            "The hwEntPbxSrvDndGroup group."
            ::= { hwEntVoicePbxGroups 33 }
            	    
	   
	   hwEntPbxSrvWakeGroup OBJECT-GROUP
	     OBJECTS { 
	        hwEntPbxSrvWakeUserName,
	        hwEntPbxSrvWakeRowStatus,
	        hwEntPbxSrvWakeTime,
	        hwEntPbxSrvWakeDays,
	        hwEntPbxSrvWakeBeginDate,
	        hwEntPbxSrvWakeToneId
	     }        
	    STATUS current
            DESCRIPTION 
            "The hwEntPbxSrvWakeGroup group."
            ::= { hwEntVoicePbxGroups 34 }
            
            	    
	   hwEntPbxSrvAbbGroup OBJECT-GROUP
	     OBJECTS { 
	        hwEntPbxSrvAbbUserName,
	        hwEntPbxSrvAbbCodeNum,
	        hwEntPbxSrvAbbRowStatus,
	        hwEntPbxSrvAbbCalledNum         
	     }        
	    STATUS current
            DESCRIPTION 
            "The hwEntPbxSrvAbbGroup group."
            ::= { hwEntVoicePbxGroups 35 }
            
            	     
	   hwEntPbxSrvRcsGroup OBJECT-GROUP
	     OBJECTS { 
	        hwEntPbxSrvRcsUserName,
	        hwEntPbxSrvRcsJudgeGrp,
	        hwEntPbxSrvRcsRowStatus,
	        hwEntPbxSrvRcsCallerNum,
	        hwEntPbxSrvRcsFromDate,
	        hwEntPbxSrvRcsFromTime,
	        hwEntPbxSrvRcsToDate,
	        hwEntPbxSrvRcsToTime,
	        hwEntPbxSrvRcsRepeatMode,
	        hwEntPbxSrvRcsBeginDate,
	        hwEntPbxSrvRcsBeginWeekday,
	        hwEntPbxSrvRcsBeginTime,
	        hwEntPbxSrvRcsEndWeekday,
	        hwEntPbxSrvRcsEndDate,
	        hwEntPbxSrvRcsEndTime,
	        hwEntPbxSrvRcsJudgeGroupActive
	     }        
	    STATUS current
            DESCRIPTION 
            "The hwEntPbxSrvRcsGroup group."
            ::= { hwEntVoicePbxGroups 36 }
            
            	     
	   hwEntPbxSrvScrGroup OBJECT-GROUP
	     OBJECTS { 
	        hwEntPbxSrvScrUserName,
	        hwEntPbxSrvScrRowStatus,
	        hwEntPbxSrvScrCentrex,
	        hwEntPbxSrvScrCountryCode,
	        hwEntPbxSrvScrAreaCode,
	        hwEntPbxSrvScrTelno                         
	     }        
	    STATUS current
            DESCRIPTION 
            "The hwEntPbxSrvScrGroup group."
            ::= { hwEntVoicePbxGroups 37 }
            
            	     
	   hwEntPbxSrvRmtGroup OBJECT-GROUP
	     OBJECTS { 
	        hwEntPbxSrvRmtUserName,
	        hwEntPbxSrvRmtRowStatus,
	        hwEntPbxSrvRmtCentrex,
	        hwEntPbxSrvRmtCountryCode,
	        hwEntPbxSrvRmtAreaCode,
	        hwEntPbxSrvRmtTelno                         
	     }        
	    STATUS current
            DESCRIPTION 
            "The hwEntPbxSrvRmtGroup group."
            ::= { hwEntVoicePbxGroups 38 }
            
            	  
	   hwEntPbxSrvCbaGroup OBJECT-GROUP
	     OBJECTS { 
	        hwEntPbxSrvCbaUserName,
	        hwEntPbxSrvCbaRowStatus,
	        hwEntPbxSrvCbaType 
	     }        
	    STATUS current
            DESCRIPTION 
            "The hwEntPbxSrvCbaGroup group."
            ::= { hwEntVoicePbxGroups 39 }
            
            	     
	   hwEntPbxSrvCallInterceptGroup OBJECT-GROUP
	     OBJECTS { 
	        hwEntPbxSrvCallInterceptName,
	        hwEntPbxSrvCallInterceptRowStatus,
	        hwEntPbxSrvCallInterceptEnterprise,
	        hwEntPbxSrvCallInterceptDnset,
	        hwEntPbxSrvCallInterceptCentrex,
	        hwEntPbxSrvCallInterceptCallStatus,
	        hwEntPbxSrvCallInterceptCallPrefix,
	        hwEntPbxSrvCallInterceptToneId
	     }        
	    STATUS current
            DESCRIPTION 
            "The hwEntPbxSrvCallInterceptGroup group."
            ::= { hwEntVoicePbxGroups 40 }
            
            	     
	   hwEntPbxSrvAlertRingGroup OBJECT-GROUP
	     OBJECTS { 
	        hwEntPbxSrvAlertRingName,
	        hwEntPbxSrvAlertRingRowStatus,
	        hwEntPbxSrvAlertRingEnterprise,
	        hwEntPbxSrvAlertRingCentrex,
	        hwEntPbxSrvAlertRingCentrexRingId,
	        hwEntPbxSrvAlertRingOutLocalRingId,
	        hwEntPbxSrvAlertRingOutDDDRingId,
	        hwEntPbxSrvAlertRingOutIDDRingId
	        
	     }        
	    STATUS current
            DESCRIPTION 
            "The hwEntPbxSrvAlertRingGroup group."
            ::= { hwEntVoicePbxGroups 41 }
            
            	 
	   hwEntPbxE1r2TrkGroup OBJECT-GROUP
	     OBJECTS { 
	        hwEntPbxE1r2TrkIndex,
	        hwEntPbxE1r2TrkRowStatus,
	        hwEntPbxE1r2TrkGrpName,
	        hwEntPbxE1r2TrkCfgStatus,
	        hwEntPbxE1r2TrkAdminStatus   
	     }
	    STATUS current
            DESCRIPTION 
            "The hwEntPbxE1r2TrkGroup group."
            ::= { hwEntVoicePbxGroups 42 }
            
            	    
	   hwEntPbxSystemParaGroup OBJECT-GROUP
	     OBJECTS { 
	        hwEntPbxSystemParaIndex,
	        hwEntPbxSystemParaValue
	     }        
	    STATUS current
            DESCRIPTION 
            "The hwEntPbxSystemParaGroup group."
            ::= { hwEntVoicePbxGroups 43 }
            	    
	     
	   hwEntPbxIsdnCauseMapGroup OBJECT-GROUP
	     OBJECTS { 
	        hwEntPbxIsdnCauseMapIsdnCause,
	        hwEntPbxIsdnCauseMapRowStatus,
	        hwEntPbxIsdnCauseMapSipResponse
	     }        
	    STATUS current
            DESCRIPTION 	    
	    "The hwEntPbxIsdnCauseMapGroup group."
            ::= { hwEntVoicePbxGroups 44 }
            
             
	   hwEntPbxSipCauseMapGroup OBJECT-GROUP
	     OBJECTS { 
	        hwEntPbxSipCauseMapSipResponse,
	        hwEntPbxSipCauseMapRowStatus,
	        hwEntPbxSipCauseMapIsdnCause
	     }        
	    STATUS current
            DESCRIPTION 
            "The hwEntPbxSipCauseMapGroup group."
            ::= { hwEntVoicePbxGroups 45 }
            
            	    
	   hwEntPbxTrkGrpCodecPriConfigGroup OBJECT-GROUP
	     OBJECTS { 
	        hwEntPbxTrkGrpCodecPriTrkGrpName,
	        hwEntPbxTrkGrpCodecPriIndex,
	        hwEntPbxTrkGrpCodecPriCodec,
	        hwEntPbxTrkGrpCodecPriPt   
	     }        
	    STATUS current
            DESCRIPTION 
            "The hwEntPbxTrkGrpCodecPriConfigGroup group."
            ::= { hwEntVoicePbxGroups 46 }
            	    
	     
	   hwEntPbxTrkGrpCodecPriRunningGroup OBJECT-GROUP
	     OBJECTS { 
	        hwEntPbxTrkGrpCodecPriRunningTrkGrpName,
	        hwEntPbxTrkGrpCodecPriRunningIndex,
	        hwEntPbxTrkGrpCodecPriRunningCodec,
	        hwEntPbxTrkGrpCodecPriRunningPt   
	     }        
	    STATUS current
            DESCRIPTION 
            "The hwEntPbxTrkGrpCodecPriRunningGroup group."
            ::= { hwEntVoicePbxGroups 47 }
            	    
	     
	   hwEntPbxSIPServerCodecPriConfigGroup OBJECT-GROUP
	     OBJECTS { 
	        hwEntPbxSIPServerCodecPriSIPServerId,
	        hwEntPbxSIPServerCodecPriIndex,
	        hwEntPbxSIPServerCodecPriCodec,
	        hwEntPbxSIPServerCodecPriPt   
	     }        
	    STATUS current
            DESCRIPTION 
            "The hwEntPbxSIPServerCodecPriConfigGroup group."
            ::= { hwEntVoicePbxGroups 48 }
            	    
	     
	   hwEntPbxSIPServerCodecPriRunningGroup OBJECT-GROUP
	     OBJECTS { 
	        hwEntPbxSIPServerCodecPriRunningSIPServerId,
	        hwEntPbxSIPServerCodecPriRunningIndex,
	        hwEntPbxSIPServerCodecPriRunningCodec,
	        hwEntPbxSIPServerCodecPriRunningPt   
	     }        
	    STATUS current
            DESCRIPTION 
            "The hwEntPbxSIPServerCodecPriRunningGroup group."
            ::= { hwEntVoicePbxGroups 49 }
            	    
	    
	   hwEntPbxTrkGrpSoftParaConfigGroup OBJECT-GROUP
	     OBJECTS { 
	        hwEntPbxTrkGrpSoftParaTrkGrpName,
	        hwEntPbxTrkGrpSoftParaIndex,
	        hwEntPbxTrkGrpSoftParaValue
	     }        
	    STATUS current
            DESCRIPTION 
            "The hwEntPbxTrkGrpSoftParaConfigGroup group."
            ::= { hwEntVoicePbxGroups 50 }
            	    
	     
	   hwEntPbxTrkGrpSoftParaRunningGroup OBJECT-GROUP
	     OBJECTS { 
	        hwEntPbxTrkGrpSoftParaRunningTrkGrpName,
	        hwEntPbxTrkGrpSoftParaRunningIndex,
	        hwEntPbxTrkGrpSoftParaRunningValue
	     }        
	    STATUS current
            DESCRIPTION 
            "The hwEntPbxTrkGrpSoftParaRunningGroup group."
            ::= { hwEntVoicePbxGroups 51 }
            	    
	    
	   hwEntPbxSIPServerSoftParaConfigGroup OBJECT-GROUP
	     OBJECTS { 
	        hwEntPbxSIPServerSoftParaSIPServerId,
	        hwEntPbxSIPServerSoftParaIndex,
	        hwEntPbxSIPServerSoftParaValue
	     }        
	    STATUS current
            DESCRIPTION 
            "The hwEntPbxSIPServerSoftParaConfigGroup group."
            ::= { hwEntVoicePbxGroups 52 }
            	    
	     
	   hwEntPbxSIPServerSoftParaRunningGroup OBJECT-GROUP
	     OBJECTS { 
	        hwEntPbxSIPServerSoftParaRunningSIPServerId,
	        hwEntPbxSIPServerSoftParaRunningIndex,
	        hwEntPbxSIPServerSoftParaRunningValue
	     }        
	    STATUS current
            DESCRIPTION 
            "The hwEntPbxSIPServerSoftParaRunning group."
            ::= { hwEntVoicePbxGroups 53 }


	   hwEntPbxConfHallConfigGroup OBJECT-GROUP
	     OBJECTS {
	       hwEntPbxConfHallName,
	       hwEntPbxConfHallRowStatus,
	       hwEntPbxConfHallEnterpriseName,
	       hwEntPbxConfAccessCodeDnSet,
	       hwEntPbxConfAccessCodeCountryCode,
	       hwEntPbxConfAccessCodeAreaCode,
	       hwEntPbxConfAccessCodeTelNo,
	       hwEntPbxConfAccessCodeCentrexName,
	       hwEntPbxConfAccessCodeCentrexTelno,
	       hwEntPbxConfHallMaxAllowRegTotal,
	       hwEntPbxConfHallMaxOnlineRoomTotal,
	       hwEntPbxConfHallMaxOnlineAttendeeTotal,
	       hwEntPbxConfHallCurRegistedNum,
	       hwEntPbxConfHallCurOnlineRoomNum,
	       hwEntPbxConfHallCurOnlineAttendeeNum,
	       hwEntPbxConfPortalNaviMenuName,
	       hwEntPbxInviteeJoinConfNaviMenuName,    
	       hwEntPbxConRemindBeforefExpiryNaviMenuName,  
	       hwEntPbxLeaveConfNaviMenuName,
	       hwEntPbxConfOperNaviMenuName
	     }
	    STATUS current
            DESCRIPTION 
            "The hwEntPbxConfHallConfigGroup group."
            ::= { hwEntVoicePbxGroups 54 }
            	     
	    
	   hwEntPbxConfRegConfigGroup OBJECT-GROUP
	     OBJECTS { 
	       hwEntPbxConfRegId,
	       hwEntPbxConfRegRowStatus,
	       hwEntPbxConfRegHallName,
	       hwEntPbxConfBeginDate,
	       hwEntPbxConfBeginTime,
	       hwEntPbxConfIsInstant,
	       hwEntPbxConfDuration,
	       hwEntPbxConfAttendeeNum,
	       hwEntPbxConfGuestPassword,
	       hwEntPbxConfChaimanPassword,
	       hwEntPbxConfRegName,
	       hwEntPbxConfDesc,
	       hwEntPbxConfLanguageType,
	       hwEntPbxConfEntryToneType,
	       hwEntPbxConfExitToneType      
	     }         
	    STATUS current
            DESCRIPTION 
            "The hwEntPbxConfRegConfigGroup group."
            ::= { hwEntVoicePbxGroups 55 }


	hwEntPbxConfOperGroup OBJECT-GROUP
	     OBJECTS { 
	       hwEntPbxConfOperId,
	       hwEntPbxConfOperType,
	       hwEntPbxConfDelayLen,
	       hwEntPbxConfStatus
	     }              
	    STATUS current
            DESCRIPTION 
            "The hwEntPbxConfOperGroup group."
            ::= { hwEntVoicePbxGroups 56 }
            
            	     
	   hwEntPbxConfAttendeeOperGroup OBJECT-GROUP
	     OBJECTS { 
	       hwEntPbxConfAttendeeOperId,
	       hwEntPbxConfAttendeeTelNo,
	       hwEntPbxConfAttendeeType,
	       hwEntPbxConfAttendeeOperType,
	       hwEntPbxConfAttendeeStatus
	     }            
	    STATUS current
            DESCRIPTION 
		"The hwEntPbxConfAttendeeOperGroup group."
            ::= { hwEntVoicePbxGroups 57 }     

           hwEntPbxSignalTraceConfigGroup OBJECT-GROUP
	     OBJECTS
	     {
	       hwEntPbxSignalTraceTaskNo,       
	       hwEntPbxSignalTraceRowStatus,
	       hwEntPbxSignalTraceTaskID,
	       hwEntPbxSignalTraceTarget,
	       hwEntPbxSignalTraceSipIp,
	       hwEntPbxSignalTraceTrkIndex,
	       hwEntPbxSignalTraceStartTS,
	       hwEntPbxSignalTraceEndTS,   
	       hwEntPbxSignalTraceDn,
	       hwEntPbxSignalTraceEntName,
	       hwEntPbxSignalTraceFilter,  
	       hwEntPbxSignalTraceServerIp, 
	       hwEntPbxSignalTraceServerPort,   
	       hwEntPbxSignalTraceServerUserName,
	       hwEntPbxSignalTraceServerPassword     
	     }
	     STATUS current
             DESCRIPTION 
		"The hwEntPbxSignalTraceConfigGroup group."
             ::= { hwEntVoicePbxGroups 58 }
             
                 
	   hwEntPbxMeasureConfigGroup OBJECT-GROUP
	     OBJECTS
	     {
	       hwEntPbxMeasureUnitID,
	       hwEntPbxMeasureRowStatus,
	       hwEntPbxMeasureTaskID,       
	       hwEntPbxMeasureName,
	       hwEntPbxMeasureGlobal,
	       hwEntPbxMeasureIncoming,
	       hwEntPbxMeasureOutgoing,
	       hwEntPbxMeasureStartDateTime,
	       hwEntPbxMeasureEndDateTime,
	       hwEntPbxMeasureInterval,       
	       hwEntPbxMeasureServerIp,
	       hwEntPbxMeasureServerPort,
	       hwEntPbxMeasureServerUserName,
	       hwEntPbxMeasureServerPassword               
	     }
	     STATUS current
             DESCRIPTION 
		"The hwEntPbxMeasureConfigGroup group."
             ::=  { hwEntVoicePbxGroups 59 }
     
     	   hwEntPbxUserStateTraceGroup  OBJECT-GROUP
	     OBJECTS
	     { 
	       hwEntPbxUserStateTraceTotal,
	       hwEntPbxUserStateTraceIdle,
	       hwEntPbxUserStateTraceBusy,
	       hwEntPbxUserStateTraceFault,
	       hwEntPbxUserStateTraceTime
	     }
	     STATUS current
             DESCRIPTION 
		"The hwEntPbxUserStateTraceGroup group."
             ::=  { hwEntVoicePbxGroups 60 }

	   hwEntPbxConferenceAttributeGroup   OBJECT-GROUP
	     OBJECTS
	     { 
	       hwEntPbxConferenceAttributeConfIDLenth,
	       hwEntPbxConferenceAttributeReconvokeTimes,
	       hwEntPbxConferenceAttributeConvokeTelno,
	       hwEntPbxConferenceAttributeCallRight
	     }
	     STATUS current
             DESCRIPTION 
		"The hwEntPbxConferenceAttributeGroup group."
             ::=  { hwEntVoicePbxGroups 61 }
  


   	   hwEntPbxCallPrefixCallrouteGroup OBJECT-GROUP
	     OBJECTS
             {
	       hwEntPbxCallPrefixCallrouteCallprefixName,
	       hwEntPbxCallPrefixCallrouteCallrouteName,
	       hwEntPbxCallPrefixCallrouteRowStatus,
	       hwEntPbxCallPrefixCallrouteIndexNo
   	     }
	     STATUS current
             DESCRIPTION 
		"The hwEntPbxCallPrefixCallrouteGroup group."
             ::=  { hwEntVoicePbxGroups 62 }
             

           hwEntPbxNewCallerChgGroup OBJECT-GROUP
	     OBJECTS
             {
	       hwEntPbxNewCallerChgName,
	       hwEntPbxNewCallerChgRowStatus,
	       hwEntPbxNewCallerChgCallerPrefix,
	       hwEntPbxNewCallerChgEnterprise,
	       hwEntPbxNewCallerChgDnset,
	       hwEntPbxNewCallerChgCallSourceName,
	       hwEntPbxNewCallerChgOrigDNChgType,
	       hwEntPbxNewCallerChgOrigDNChgPos,
	       hwEntPbxNewCallerChgOrigDNChgLen,
	       hwEntPbxNewCallerChgOrigDNNew,
	       hwEntPbxNewCallerChgTermDNChgType,
	       hwEntPbxNewCallerChgTermDNChgPos,
	       hwEntPbxNewCallerChgTermDNChgLen,
	       hwEntPbxNewCallerChgTermDNNew
   	     }
	     STATUS current
             DESCRIPTION 
		"The hwEntPbxNewCallerChgGroup group."
             ::=  { hwEntVoicePbxGroups 63 }                  
 
           hwEntPbxCallRouteConfigGroup OBJECT-GROUP
	     OBJECTS
             {
	       hwEntPbxCallRouteName,
	       hwEntPbxCallRouteRowStatus,
	       hwEntPbxCallRouteSelectType,
	       hwEntPbxCallRouteRerouteDealName             
   	     }
 	     STATUS current
             DESCRIPTION 
		"The hwEntPbxCallRouteConfigGroup group."
             ::=  { hwEntVoicePbxGroups 64 }                    
     
  	   hwEntPbxRerouteDealConfigGroup OBJECT-GROUP
	     OBJECTS
             {
	       hwEntPbxRerouteDealName,
	       hwEntPbxRerouteDealRowStatus,
	       hwEntPbxRerouteDealCallRoutename,
	       hwEntPbxRerouteDealReCallRouteName,
	       hwEntPbxRerouteDealFailedType              
   	     }
	     STATUS current
             DESCRIPTION 
		"The hwEntPbxRerouteDealConfigGroup group."
             ::=  { hwEntVoicePbxGroups 65 }

           hwEntPbxTimeTempletGroup OBJECT-GROUP
	     OBJECTS
             {
	       hwEntPbxTimeTempletName,
	       hwEntPbxTimeTempletRowStatus,
	       hwEntPbxTimeTempletFromDate,
	       hwEntPbxTimeTempletFromTime,
	       hwEntPbxTimeTempletToDate,
	       hwEntPbxTimeTempletToTime,
	       hwEntPbxTimeTempletRepeatMode,
	       hwEntPbxTimeTempletBeginDate,
	       hwEntPbxTimeTempletBeginWeekday,
	       hwEntPbxTimeTempletBeginTime,
	       hwEntPbxTimeTempletEndDate,
	       hwEntPbxTimeTempletEndWeekday,
	       hwEntPbxTimeTempletEndTime               
   	     }  
	     STATUS current
             DESCRIPTION 
		"The hwEntPbxTimeTempletGroup group."
             ::=  { hwEntVoicePbxGroups 66 }
 
      
  	   hwEntPbxCallSourceGroup OBJECT-GROUP
	     OBJECTS
             {
  	   hwEntPbxCallSourceName,
  	   hwEntPbxCallSourceRowStatus,
  	   hwEntPbxCallSourceReserved
   	     }
             STATUS current
             DESCRIPTION 
		"The hwEntPbxCallSourceGroup group."
             ::=  { hwEntVoicePbxGroups 67 }

           hwEntPbxRouteAnalysisGroup OBJECT-GROUP
	     OBJECTS
             {
  	   hwEntPbxRouteAnalysisName,
  	   hwEntPbxRouteAnalysisRowStatus,
  	   hwEntPbxRouteAnalysisCallsourceName,
  	   hwEntPbxRouteAnalysisCallRoutename,
  	   hwEntPbxRouteAnalysisTrunkGroupName            
   	     }
             STATUS current
             DESCRIPTION 
		"The hwEntPbxRouteAnalysisGroup group."
             ::=  { hwEntVoicePbxGroups 68 }	 
	 
	 
	   hwEntPbxTrkGrpCallRouteConfigGroup OBJECT-GROUP
	     OBJECTS
             {
  	   hwEntPbxTrkGrpCallRouteTrkgrpName,
  	   hwEntPbxTrkGrpCallRouteCallrouteName,
  	   hwEntPbxTrkGrpCallRouteRowStatus,
  	   hwEntPbxTrkGrpCallRouteTimeTempletName,
  	   hwEntPbxTrkGrpCallRouteCharge,
  	   hwEntPbxTrkGrpCallRoutePercent,
  	   hwEntPbxTrkGrpCallRouteUserPriorLevel,
  	   hwEntPbxTrkGrpCallRouteCallerNumber,
  	   hwEntPbxTrkGrpCallRouteSelectLevel
   	     }
	     STATUS current
             DESCRIPTION 
		"The hwEntPbxTrkGrpCallRouteConfigGroup group."
             ::=  { hwEntVoicePbxGroups 69 }
     
     
 	   hwEntPbxConfConfigGroup OBJECT-GROUP
	     OBJECTS
             {
  	   hwEntPbxConfName,
  	   hwEntPbxConfRowStatus,
  	   hwEntPbxConfDescription,
  	   hwEntPbxConfId,
  	   hwEntPbxConfEnterpriseName,
  	   hwEntPbxConfDnsetName,
  	   hwEntPbxConfRegNum,
  	   hwEntPbxConfAttendeePwd,
  	   hwEntPbxConfChairmanPwd,
  	   hwEntPbxConfStartDate,
  	   hwEntPbxConfStartTime,
  	   hwEntPbxConfEndDate,
  	   hwEntPbxConfEndTime,
  	   hwEntPbxConfEnterPrompt,
  	   hwEntPbxConfLeavePrompt,
  	   hwEntPbxConfChairman,
  	   hwEntPbxConfType,
  	   hwEntPbxConfState
   	     }
	     STATUS current
             DESCRIPTION 
		"The hwEntPbxConfConfigGroup group."
             ::=  { hwEntVoicePbxGroups 70 }
     
  	   hwEntPbxConferenceAttendeeCfgGroup OBJECT-GROUP
	     OBJECTS
             {       
  	   hwEntPbxConferenceAttendeeConfName,
  	   hwEntPbxConferenceAttendeeTelNo,
  	   hwEntPbxConferenceAttendeeRowStatus,
  	   hwEntPbxConferenceAttendeeUserName,
  	   hwEntPbxConferenceAttendeeMode,
  	   hwEntPbxConferenceAttendeeConfState         
   	     }
             STATUS current
             DESCRIPTION 
		"The hwEntPbxConferenceAttendeeCfgGroup group."
             ::=  { hwEntVoicePbxGroups 71 }


           hwEntPbxAlarmParaGroup OBJECT-GROUP
	     OBJECTS
             {      
	       hwEntPbxAlarmShelf,
	       hwEntPbxAlarmSlot,
	       hwEntPbxAlarmUpgradeFailInfo,
	       hwEntPbxAlarmPort,
	       hwEntPbxAlarmTsn,
	       hwEntPbxAlarmInterfaceName
 	     }
             STATUS current
             DESCRIPTION 
		"The hwEntPbxAlarmParaGroup group."
            ::=  { hwEntVoicePbxGroups 72 }
  
           hwEntPbxTrapsGroup OBJECT-GROUP
	     OBJECTS
             {     
  	   hwEntPbxBillpoolOverflow,
  	   hwEntPbxBillpoolOverflowRestore,
  	   hwEntPbxBillpoolFull,
  	   hwEntPbxBillpoolFullRestore,
  	   hwEntPbxBillCommInterrupt,
  	   hwEntPbxBillCommRestore,
  	   hwEntPbxUpgradeFailTrap,
  	   hwEntPbxE1FaultTrap,
  	   hwEntPbxE1ResumeTrap,
  	   hwEntPbxBillSendFailTrap,
  	   hwEntPbxBillCreateFailTrap,
  	   hwEntPbxDspResourceNotEnoughTrap,
  	   hwEntPbxAt0CircuitFaultTrap,
  	   hwEntPbxAt0CircuitRestoreTrap,
  	   hwEntPbxUserNumberLockTrap,
  	   hwEntPbxUserNumberUnLockTrap,
  	   hwEntPbxPriLinkFaultTrap,
  	   hwEntPbxPriLinkRestoreTrap 
             }
             STATUS current
             DESCRIPTION 
		"The hwEntPbxTrapsGroup group."
             ::=  { hwEntVoicePbxGroups 73 } 
  
  
  
    	   hwEntPbxVoiceFileGroup OBJECT-GROUP
	     OBJECTS
             {
  	   	   hwEntPbxVoiceFileName,
  	   	   hwEntPbxVoiceFileRowStatus,
  	   	   hwEntPbxVoiceFileType                       
   	     }
             STATUS current
             DESCRIPTION 
		"The hwEntPbxVoiceFileGroup group."
             ::=  { hwEntVoicePbxGroups 74 }

           hwEntPbxIvrTimeIndexGroup OBJECT-GROUP
	     OBJECTS
             {
  	   	   hwEntPbxIvrTimeIndexNo,
  	   	   hwEntPbxIvrTimeIndexRowStatus,
  	   	   hwEntPbxIvrTimeIndexStartYear,
  	   	   hwEntPbxIvrTimeIndexStartMonth,
  	   	   hwEntPbxIvrTimeIndexStartDay,
  	   	   hwEntPbxIvrTimeIndexStartWeekday,
  	   	   hwEntPbxIvrTimeIndexStartHour,
  	   	   hwEntPbxIvrTimeIndexStartMinute,
  	   	   hwEntPbxIvrTimeIndexStartSecond, 
  	   	   hwEntPbxIvrTimeIndexEndYear,
  	   	   hwEntPbxIvrTimeIndexEndMonth,
  	   	   hwEntPbxIvrTimeIndexEndDay,
  	   	   hwEntPbxIvrTimeIndexEndWeekday,
  	   	   hwEntPbxIvrTimeIndexEndHour,
  	   	   hwEntPbxIvrTimeIndexEndMinute,
  	   	   hwEntPbxIvrTimeIndexEndSecond,
  	   	   hwEntPbxIvrTimeIndexIsHoliday
   	     }  
             STATUS current
             DESCRIPTION 
		"The hwEntPbxIvrTimeIndexGroup group."
             ::=  { hwEntVoicePbxGroups 75 }    
     
 	   hwEntPbxIvrGroup OBJECT-GROUP
	     OBJECTS
             {
  	   	   hwEntPbxIvrVu,
  	   	   hwEntPbxIvrVuRowStatus, 
  	   	   hwEntPbxIvrFileName,
  	   	   hwEntPbxIvrNumberLength,
  	   	   hwEntPbxIvrScriptType,
  	   	   hwEntPbxIvrConfigString,
  	   	   hwEntPbxIvrConfigStringLength
   	     }
	     STATUS current
             DESCRIPTION 
		"The hwEntPbxIvrGroup group."
             ::=  { hwEntVoicePbxGroups 76 }    
     
 	   hwEntPbxIvrFileGroup OBJECT-GROUP
	     OBJECTS
             {
  	   	   hwEntPbxIvrFileIvrVu,
  	   	   hwEntPbxIvrFileRowStatus,
  	   	   hwEntPbxIvrFilePath
   	     }
	     STATUS current
             DESCRIPTION 
		"The hwEntPbxIvrFileGroup group."
             ::=  { hwEntVoicePbxGroups 77 }    
     
  	   hwEntPbxNumberMapGroup OBJECT-GROUP
	     OBJECTS
             {
  	   	   hwEntPbxNumberMapName,
  	   	   hwEntPbxNumberMapRowStatus,
  	   	   hwEntPbxNumberMapEnterpriseName,
  	   	   hwEntPbxNumberMapExternNumber,
  	   	   hwEntPbxNumberMapInnerNumber                    
   	     }
             STATUS current
             DESCRIPTION 
		"The hwEntPbxNumberMapGroup group."
             ::=  { hwEntVoicePbxGroups 78 }    

  	   hwEntPbxSrvVoiceMailCfxGroup OBJECT-GROUP
	     OBJECTS
             {
  	   	   hwEntPbxSrvVoiceMailCfxUserName,
  	   	   hwEntPbxSrvVoiceMailCfxType,
  	   	   hwEntPbxSrvVoiceMailCfxRowStatus,
  	   	   hwEntPbxSrvVoiceMailCfxUmsNo,
  	   	   hwEntPbxSrvVoiceMailCfxActive,
  	   	   hwEntPbxSrvVoiceMailCfxCfnrTime 
   	     }
	     STATUS current
             DESCRIPTION 
		"The hwEntPbxSrvVoiceMailCfxGroup group."
            ::=  { hwEntVoicePbxGroups 79 }    
     
  	   hwEntPbxUmsCfgGroup OBJECT-GROUP
	     OBJECTS
             {   
  	   	   hwEntPbxUmsCfgUmsNo,
  	   	   hwEntPbxUmsCfgRowStatus,
  	   	   hwEntPbxUmsCfgCallprefix                 
   	     }
             STATUS current
             DESCRIPTION 
		"The hwEntPbxUmsCfgGroup group."
             ::=  { hwEntVoicePbxGroups 80 }    

  	   hwEntPbxVmsFilePathGroup    OBJECT-GROUP
             OBJECTS
             {   
  	        hwEntPbxVmsFilePath 
	     }
             STATUS current
             DESCRIPTION 
		"The hwEntPbxVmsFilePathGroup group."
             ::=  { hwEntVoicePbxGroups 81 }   
  
  
  
   	   hwEntPbxUnicallCfgGroup OBJECT-GROUP
	     OBJECTS
             {   
  	   	   hwEntPbxUnicallCfgPbxUserName,
  	   	   hwEntPbxUnicallCfgRowStatus,
  	   	   hwEntPbxUnicallCfgBusySelectMode,
  	   	   hwEntPbxUnicallCfgRingMode,
  	   	   hwEntPbxUnicallCfgPriorityMode,
  	   	   hwEntPbxUnicallCfgSelectInterval
   	     }
             STATUS current
             DESCRIPTION 
		"The hwEntPbxUnicallCfgGroup group."
             ::=  { hwEntVoicePbxGroups 82 }     
     
  	   hwEntPbxUnicallBindMemberCfgGroup OBJECT-GROUP
	     OBJECTS
             {   
  	   	   hwEntPbxUnicallBindMemberCfgPbxUserName,
  	   	   hwEntPbxUnicallBindMemberCfgBindNumber,
  	   	   hwEntPbxUnicallBindMemberCfgBindType,
  	   	   hwEntPbxUnicallBindMemberCfgRowStatus,
  	   	   hwEntPbxUnicallBindMemberCfgPriority,
  	   	   hwEntPbxUnicallBindMemberCfgTimeRangeName              
   	     }
             STATUS current
             DESCRIPTION 
		"The hwEntPbxUnicallBindMemberCfgGroup group."
             ::=  { hwEntVoicePbxGroups 83 }

   	   hwEntPbxSelfServiceHttpServerGroup OBJECT-GROUP
	 	     OBJECTS
             {
   	   	   hwEntPbxSelfServiceHttpServerIndex,
   	   	   hwEntPbxSelfServiceHttpServerRowStatus,
   	   	   hwEntPbxSelfServiceHttpServerPort,
   	   	   hwEntPbxSelfServiceHttpSecureServerPort,
   	   	   hwEntPbxSelfServiceHttpServerStatus,
   	   	   hwEntPbxSelfServiceHttpSecureServerStatus
   	     }
             STATUS current
             DESCRIPTION 
		"The hwEntPbxSelfServiceHttpServerGroup group."
             ::=  { hwEntVoicePbxGroups 84 }            
            
                               
        --  ============== conformance information define end ==============   

END
