HUAWEI-VDSL-QAM-MIB DEFINITIONS ::= BEGIN

    IMPORTS

    MODULE-IDENTITY, 
    OBJECT-TYPE,
    Counter64,
    Gauge32, Integer32, Counter32,
    NOTIFICATION-TYPE				FROM SNMPv2-SMI
    huaweiMgmt						FROM HUAWEI-MIB	
    TEXTUAL-CONVENTION,
    RowStatus,
    TruthValue                      FROM SNMPv2-TC
    HCPerfCurrentCount,
    HCPerfIntervalCount             FROM HC-PerfHist-TC-MIB
    MODULE-COMPLIANCE, 
    OBJECT-GROUP,
    NOTIFICATION-GROUP              FROM SNMPv2-CONF
    ifIndex                         FROM IF-MIB
    SnmpAdminString                 FROM SNMP-FRAMEWORK-MIB;

    hwVdslQam MODULE-IDENTITY
       LAST-UPDATED "200111010000Z" -- November 1, 2001
       ORGANIZATION "ADSLMIB Working Group"
       CONTACT-INFO "WG-email:  XDSLMIB@LISTSERV.ECIRALEIGH.COM 
                  Subscribe: LISTSERV@LISTSERV.ECIRALEIGH.COM 
                             In Body: subscribe/signoff XDSLMIB 
                             Archive: index XDSLMIB/get <archivename> 

                  Chair:     Mike Sneed
                             ECI Telecom
                  Postal:    1017 Main Campus Drive
                             Raleigh NC 27606 USA
                  Email:     Mike.Sneed@go.ecitele.com
                  Phone:     +1 919 513 1435
                  Editor:    Bob Ray
                             Verilink Corporation
                  Postal:    950 Explorer Blvd
                             Huntsville, AL 35806 USA
                  Email:     bray@verilink.com
                  Phone:     +1 256 327 2380
                 "

    DESCRIPTION
        "The MIB module defining objects for the management of a pair of
        VDSL modems at each end of the VDSL line.  Each such line has
        an entry in an ifTable which may include multiple modem lines.
        An agent may reside at either end of the VDSL line however the
        MIB is designed to require no management communication between
        them beyond that inherent in the low-level VDSL line protocol.
        The agent may monitor and control this protocol for its needs.

        VDSL lines may support optional Fast or Interleaved channels.
        If these are supported, additional entries corresponding to the
        supported channels must be created in the ifTable. Thus a VDSL
        line that supports both channels will have three entries in the
        ifTable, one for each physical, fast, and interleaved, whose
        ifType values are equal to vdsl(97), fast(125), and
        interleaved(124), respectively. The ifStackTable is used to
        represent the relationship between the entries.
 
        Naming Conventions:
            Vtuc -- (VTUC) modem at near (Central) end of line
            Vtur -- (VTUR) modem at Remote end of line
            Vtu  -- One of either Vtuc or Vtur
            Curr -- Current
            Prev -- Previous
            Atn  -- Attenuation
            ES   -- Errored Second.
            LCS  -- Line Code Specific
            Lof  -- Loss of Frame
            Lol  -- Loss of Link
            Los  -- Loss of Signal
            Lpr  -- Loss of Power
            xxxs -- interval of Seconds in which xxx occurs
                    (e.g., xxx=Lof, Los, Lpr)
            Max  -- Maximum
            Mgn  -- Margin
            Min  -- Minimum
            Psd  -- Power Spectral Density
            Snr  -- Signal to Noise Ratio
            Tx   -- Transmit
            Blks -- Blocks, a data unit, see vdslVtuXChanCrcBlockLength
            "        


    REVISION "200111010000Z" -- November 1, 2001
    DESCRIPTION "Initial draft."

    ::= { huaweiMgmt 28 }

    vdslLineMib    OBJECT IDENTIFIER ::= { hwVdslQam 1 }
    vdslMibObjects OBJECT IDENTIFIER ::= { vdslLineMib 1 }

    --
    -- textual conventions used in this MIB
    --

    VdslLineCodingType ::= TEXTUAL-CONVENTION
        STATUS       current
        DESCRIPTION
            "This data type is used as the syntax for the VDSL
             Line Code."
        SYNTAX  INTEGER 
            {
            other(1), -- none of the following
            mcm(2),   -- Multiple Carrier Modulation 
            scm(3)    -- Single Carrier Modulation
            }

    VdslLineEntity ::= TEXTUAL-CONVENTION
        STATUS       current
        DESCRIPTION
            "Identifies a modem as being either Vtuc or Vtur.  A
            VDSL line consists of two modems, a Vtuc and a Vtur."
        SYNTAX  INTEGER 
            {
            vtuc(1), -- central site modem
            vtur(2)  -- remote site modem
            }

    --
    -- objects
    --

    vdslLineTable OBJECT-TYPE
        SYNTAX       SEQUENCE OF VdslLineEntry
        MAX-ACCESS   not-accessible
        STATUS       current
        DESCRIPTION
            "This table includes common attributes describing
            both ends of the line.  It is required for all VDSL
            physical interfaces.  VDSL physical interfaces are
            those ifEntries where ifType is equal to vdsl(97)."
        ::= { vdslMibObjects 1 }

    vdslLineEntry OBJECT-TYPE
        SYNTAX       VdslLineEntry
        MAX-ACCESS   not-accessible
        STATUS       current
        DESCRIPTION  "An entry in the vdslLineTable."
        INDEX        { ifIndex }
        ::= { vdslLineTable 1 }

    VdslLineEntry ::=
        SEQUENCE 
            {
            vdslLineCoding                         VdslLineCodingType,
            vdslLineType                           INTEGER,
            vdslLineConfProfile                    SnmpAdminString,
            vdslLineAlarmConfProfile               SnmpAdminString
            }

    vdslLineCoding OBJECT-TYPE
        SYNTAX       VdslLineCodingType
        MAX-ACCESS   read-only
        STATUS       current
        DESCRIPTION
            "Specifies the VDSL coding type used on this line."
        REFERENCE    "T1E1.4/2000-009R3"    -- Part 1, common spec
        ::= { vdslLineEntry 1 }

    vdslLineType OBJECT-TYPE
        SYNTAX       INTEGER 
            {
            noChannel(1),         -- no channels exist
            fastOnly(2),          -- fast channel only
            slowOnly(3),          -- slow channel only
            either(4),            -- either fast or slow channel exist
            both(5)               -- both fast and slow channels exist
            }
        MAX-ACCESS   read-only
        STATUS       current
        DESCRIPTION
            "Defines the type of VDSL physical line
            entity that exists, by defining whether and how
            the line is channelized.  If the line is channelized,
            the value will be other than noChannel(1).  This
            object defines which channel type(s) are supported.

            In the case that the line is channelized, the manager
            can use the ifStackTable to determine the ifIndex for
            the associated channel(s)."
        REFERENCE    "T1E1.4/2000-009R3"    -- Part 1, common spec
        ::= { vdslLineEntry 2 }

    vdslLineConfProfile OBJECT-TYPE
        SYNTAX       SnmpAdminString (SIZE (1..32))
        MAX-ACCESS   read-write
        STATUS       current
        DESCRIPTION
            "The value of this object identifies the row
            in the VDSL Line Configuration Profile Table,
            ( vdslLineConfProfileTable ), which applies for this
            VDSL line, and channels if applicable."
        ::= { vdslLineEntry 3 }

    vdslLineAlarmConfProfile OBJECT-TYPE
        SYNTAX       SnmpAdminString (SIZE (1..32))
        MAX-ACCESS   read-write
        STATUS       current
        DESCRIPTION
            "The value of this object identifies the row in the VDSL
            Line Alarm Configuration Profile Table, 
            ( vdslLineAlarmConfProfileTable ), which applies to this
            VDSL line, and channels if applicable."
        ::= { vdslLineEntry 4 }

    vdslPhysTable OBJECT-TYPE
        SYNTAX       SEQUENCE OF VdslPhysEntry
        MAX-ACCESS   not-accessible
        STATUS       current
        DESCRIPTION
            "This table provides one row for each Vtu.  Each row 
            contains the Physical Layer Parameters table for that 
            Vtu.  VDSL physical interfaces are those ifEntries where 
            ifType is equal to vdsl(97)."
        ::= { vdslMibObjects 2 }

    vdslPhysEntry OBJECT-TYPE
        SYNTAX       VdslPhysEntry
        MAX-ACCESS   not-accessible
        STATUS       current
        DESCRIPTION  "An entry in the vdslPhysTable."
        INDEX        { ifIndex, vdslPhysSide }
        ::= { vdslPhysTable 1 }

    VdslPhysEntry ::=
        SEQUENCE 
            {
            vdslPhysSide                           VdslLineEntity,
            vdslInvSerialNumber                    SnmpAdminString,
            vdslInvVendorID                        SnmpAdminString,
            vdslInvVersionNumber                   SnmpAdminString,
            vdslCurrSnrMgn                         INTEGER,
            vdslCurrAtn                            Gauge32,
            vdslCurrStatus                         BITS,
            vdslCurrOutputPwr                      INTEGER,
            vdslCurrAttainableRate                 Gauge32,
            hwVdslActualRate					   Integer32,
            hwVdslCurrSnr						   Integer32,
            hwVdslMse							   Integer32,
            hwVdslChipHrdVer					   Integer32,
            hwVdslChipSftVer                       Integer32,
            hwVdslChipPatchVer					   Integer32		   	
            }

    vdslPhysSide OBJECT-TYPE
        SYNTAX       VdslLineEntity
        MAX-ACCESS   read-only
        STATUS       current
        DESCRIPTION
            "Identifies whether the modem is the Vtuc or Vtur."
        ::= { vdslPhysEntry 1 }

    vdslInvSerialNumber OBJECT-TYPE
        SYNTAX       SnmpAdminString(SIZE (0..32))
        MAX-ACCESS   read-only
        STATUS       current
        DESCRIPTION
            "The vendor specific string that identifies the
            vendor equipment."
        REFERENCE    "T1E1.4/2000-009R3"    -- Part 1, common spec
        ::= { vdslPhysEntry 2 }

    vdslInvVendorID OBJECT-TYPE
        SYNTAX       SnmpAdminString (SIZE (0..16))
        MAX-ACCESS   read-only
        STATUS       current
        DESCRIPTION
            "The vendor ID code is a copy of the binary vendor 
            identification field defined by the PHY[10] and 
            expressed as readable characters."
        REFERENCE    "T1E1.4/2000-009R3"    -- Part 1, common spec
        ::= { vdslPhysEntry 3 }

    vdslInvVersionNumber OBJECT-TYPE
        SYNTAX       SnmpAdminString (SIZE (0..16))
        MAX-ACCESS   read-only
        STATUS       current
        DESCRIPTION
            "The vendor specific version number sent by this Vtu
            as part of the initialization messages.  It is a copy
            of the binary version number field defined by the
            PHY[10] and expressed as readable characters."
        REFERENCE    "T1E1.4/2000-009R3"    -- Part 1, common spec
        ::= { vdslPhysEntry 4 }

    vdslCurrSnrMgn OBJECT-TYPE
        SYNTAX       INTEGER(-640..640)
        UNITS        "tenth dB"
        MAX-ACCESS   read-only
        STATUS       current
        DESCRIPTION
            "Noise Margin as seen by this Vtu with respect to its
            received signal in tenth dB."
        REFERENCE    "T1E1.4/2000-009R3"    -- Part 1, common spec
         ::= { vdslPhysEntry 5 }

    vdslCurrAtn OBJECT-TYPE
        SYNTAX       Gauge32(0..630)
        UNITS        "tenth dB"
        MAX-ACCESS   read-only
        STATUS       current
        DESCRIPTION
            "Measured difference in the total power transmitted by 
            the peer Vtu and the total power received by this Vtu."
        REFERENCE    "T1E1.4/2000-009R3"    -- Part 1, common spec
         ::= { vdslPhysEntry 6 }     

--   
    hwVdslActualRate OBJECT-TYPE
			SYNTAX Integer32
			UNITS "bps"
			MAX-ACCESS read-only
			STATUS current
			DESCRIPTION
				"
				The actual rate of this Vtu.
				"
			::= { vdslPhysEntry 65536 }
		
	hwVdslCurrSnr OBJECT-TYPE
			SYNTAX Integer32
			UNITS "tenth dB"
			MAX-ACCESS read-only
			STATUS current
			DESCRIPTION
				"
				Current Signal to Noise Ratio.
				"
			::= { vdslPhysEntry 65537 }
		
	hwVdslMse OBJECT-TYPE
			SYNTAX Integer32
			UNITS "tenth dB"
			MAX-ACCESS read-only
			STATUS current
			DESCRIPTION
				"
				Minimum Square Error.
				"
			::= { vdslPhysEntry 65538 }
		
	hwVdslChipHrdVer OBJECT-TYPE
			SYNTAX Integer32
			MAX-ACCESS read-only
			STATUS current
			DESCRIPTION
				"
				VDSL chip hardware version
				"
			::= { vdslPhysEntry 65539 }
		
	hwVdslChipSftVer OBJECT-TYPE
			SYNTAX Integer32
			MAX-ACCESS read-only
			STATUS current
			DESCRIPTION
				"
				VDSL chip software version
				"
			::= { vdslPhysEntry 65540 }
		
	hwVdslChipPatchVer OBJECT-TYPE
			SYNTAX Integer32
			MAX-ACCESS read-only
			STATUS current
			DESCRIPTION
				"
				VDSL chip patch version
				"
			::= { vdslPhysEntry 65541 }
--end 

    vdslCurrStatus OBJECT-TYPE
        SYNTAX       BITS 
            {
            noDefect(0),
            lossOfFraming(1),
            lossOfSignal(2),
            lossOfPower(3),
            lossOfSignalQuality(4),
            lossOfLink(5),
            dataInitFailure(6),
            configInitFailure(7),
            protocolInitFailure(8),
            noPeerVtuPresent(9)
            }
        MAX-ACCESS  read-only
        STATUS      current
        DESCRIPTION
            "Indicates current state of the Vtu line.  This is a
            bit-map of possible conditions.  The various bit
            positions are:

            0   noDefect             There no defects on the line

            1   lossOfFraming        Vtu failure due to not receiving 
                                     valid frame.

            2   lossOfSignal         Vtu failure due to not receiving 
                                     signal.

            3   lossOfPower          Vtu failure due to loss of power.

            4   lossOfSignalQuality  Loss of Signal Quality is declared
                                     when the Noise Margin falls below 
                                     the Minimum Noise Margin, or the 
                                     bit-error-rate exceeds 10^-7.

            5   lossOfLink           Vtu failure due to inability to 
                                     link with peer Vtu.

            6   dataInitFailure      Vtu failure during initialization 
                                     due to bit errors corrupting
                                     startup exchange data.

            7   configInitFailure    Vtu failure during initialization 
                                     due to peer Vtu not able to support
                                     requested configuration.

            8   protocolInitFailure  Vtu failure during initialization 
                                     due to incompatible protocol used 
                                     by the peer Vtu.

            9   noPeerVtuPresent     Vtu failure during initialization 
                                     due to no activation sequence 
                                     detected from peer Vtu.

            This is intended to supplement ifOperStatus."
        REFERENCE    "T1E1.4/2000-009R3"    -- Part 1, common spec
         ::= { vdslPhysEntry 7 }

    vdslCurrOutputPwr OBJECT-TYPE
        SYNTAX       INTEGER (-310..310)
        UNITS        "tenth dBm"
        MAX-ACCESS   read-only
        STATUS       current
        DESCRIPTION
            "Measured total output power transmitted by this ATU.
            This is the measurement that was reported during
            the last activation sequence."
        REFERENCE    "T1E1.4/2000-009R3"    -- Part 1, common spec
        ::= { vdslPhysEntry 8 }

    vdslCurrAttainableRate OBJECT-TYPE
        SYNTAX       Gauge32
        UNITS        "bps"
        MAX-ACCESS   read-only
        STATUS       current
        DESCRIPTION
            "Indicates the maximum currently attainable data rate
            by the Vtu.  This value will be equal or greater than
            the current line rate."
        REFERENCE    "T1E1.4/2000-009R3"    -- Part 1, common spec
        ::= { vdslPhysEntry 9 }

    vdslChanTable OBJECT-TYPE
        SYNTAX       SEQUENCE OF VdslChanEntry
        MAX-ACCESS   not-accessible
        STATUS       current
        DESCRIPTION
            "This table provides one row for each Vtu channel.
            VDSL channel interfaces are those ifEntries where 
            ifType is equal to interleave(124) or fast(125)."
        ::= { vdslMibObjects 3 }

    vdslChanEntry OBJECT-TYPE
        SYNTAX       VdslChanEntry
        MAX-ACCESS   not-accessible
        STATUS       current
        DESCRIPTION  
            "An entry in the vdslChanTable."
        INDEX        { ifIndex, vdslPhysSide }
        ::= { vdslChanTable 1 }

    VdslChanEntry ::=
        SEQUENCE 
            {
            vdslChanInterleaveDelay                Gauge32,
            vdslChanCrcBlockLength                 Gauge32
            }

    vdslChanInterleaveDelay OBJECT-TYPE
        SYNTAX       Gauge32
        UNITS        "milli-seconds"
        MAX-ACCESS   read-only
        STATUS       current
        DESCRIPTION
            "Interleave Delay for this channel.

            Interleave delay applies only to the interleave 
            (slow) channel and defines the mapping (relative 
            spacing) between subsequent input bytes at the 
            interleaver input and their placement in the bit 
            stream at the interleaver output.  Larger numbers 
            provide greater separation between consecutive 
            input bytes in the output bit stream allowing for 
            improved impulse noise immunity at the expense of 
            payload latency.

            In the case where the ifType is fast(125), use
            noSuchObject."
        REFERENCE    "T1E1.4/2000-009R3"    -- Part 1, common spec
        ::= { vdslChanEntry 1 }

    vdslChanCrcBlockLength OBJECT-TYPE
        SYNTAX       Gauge32
        UNITS        "byte"
        MAX-ACCESS   read-only
        STATUS       current
        DESCRIPTION
            "Indicates the length of the channel data-block
            on which the CRC operates."
        REFERENCE    "T1E1.4/2000-009R3"    -- Part 1, common spec
        ::= { vdslChanEntry 2 }

    vdslPerfDataTable       OBJECT-TYPE
        SYNTAX       SEQUENCE OF VdslPerfDataEntry
        MAX-ACCESS   not-accessible
        STATUS       current
        DESCRIPTION
            "This table provides one row for each VDSL physical
            interface.  VDSL physical interfaces are those ifEntries
            where ifType is equal to vdsl(97)."
         ::= { vdslMibObjects 4 }

    vdslPerfDataEntry       OBJECT-TYPE
        SYNTAX        VdslPerfDataEntry
        MAX-ACCESS    not-accessible
        STATUS        current
        DESCRIPTION     
            "An entry in the vdslPerfDataTable."
        INDEX         { ifIndex, vdslPhysSide }
        ::= { vdslPerfDataTable 1 }

    VdslPerfDataEntry ::=
        SEQUENCE 
            {
            vdslPerfValidIntervals                 INTEGER,
            vdslPerfInvalidIntervals               INTEGER,
            vdslPerfLofs                           Counter64,
            vdslPerfLoss                           Counter64,
            vdslPerfLprs                           Counter64,
            vdslPerfESs                            Counter64,
            vdslPerfInits                          Counter64,
            vdslPerfCurr15MinTimeElapsed           INTEGER,
            vdslPerfCurr15MinLofs                  HCPerfCurrentCount,
            vdslPerfCurr15MinLoss                  HCPerfCurrentCount,
            vdslPerfCurr15MinLprs                  HCPerfCurrentCount,
            vdslPerfCurr15MinESs                   HCPerfCurrentCount,
            vdslPerfCurr15MinInits                 HCPerfCurrentCount
            }

    vdslPerfValidIntervals OBJECT-TYPE
        SYNTAX       INTEGER(0..96)
        MAX-ACCESS   read-only
        STATUS       current
        DESCRIPTION
            "Valid Intervals per xxxValidInterval definition
            found in HC-PerfHist-TC-MIB."
        ::= { vdslPerfDataEntry 1 }

    vdslPerfInvalidIntervals OBJECT-TYPE
        SYNTAX       INTEGER(0..96)
        MAX-ACCESS   read-only
        STATUS       current
        DESCRIPTION
            "Invalid Intervals per xxxInvalidInterval definition
            found in HC-PerfHist-TC-MIB."
        ::= { vdslPerfDataEntry 2 }

    vdslPerfLofs OBJECT-TYPE
        SYNTAX       Counter64
        UNITS        "seconds"
        MAX-ACCESS   read-only
        STATUS       current
        DESCRIPTION
            "Count of seconds since the unit was last reset that there 
            was Loss of Framing."
        REFERENCE    "T1E1.4/2000-009R3"    -- Part 1, common spec
        ::= { vdslPerfDataEntry 3 }

    vdslPerfLoss OBJECT-TYPE
        SYNTAX       Counter64
        UNITS        "seconds"
        MAX-ACCESS   read-only
        STATUS       current
        DESCRIPTION
            "Count of seconds since the unit was last reset that there 
            was Loss of Signal."
        REFERENCE    "T1E1.4/2000-009R3"    -- Part 1, common spec
        ::= { vdslPerfDataEntry 4 }

    vdslPerfLprs OBJECT-TYPE
        SYNTAX       Counter64
        UNITS        "seconds"
        MAX-ACCESS   read-only
        STATUS       current
        DESCRIPTION
            "Count of seconds since the unit was last reset that there 
            was Loss of Power."
        REFERENCE    "T1E1.4/2000-009R3"    -- Part 1, common spec
        ::= { vdslPerfDataEntry 5 }

    vdslPerfESs OBJECT-TYPE
        SYNTAX       Counter64
        UNITS        "seconds"
        MAX-ACCESS   read-only
        STATUS       current
        DESCRIPTION
            "Count of Errored Seconds since the unit was last reset.
            An Errored Second is a one-second interval containing one 
            or more crc anomalies, or one or more los defects."
        REFERENCE    "T1E1.4/2000-009R3"    -- Part 1, common spec
        ::= { vdslPerfDataEntry 6 }

    vdslPerfInits OBJECT-TYPE
        SYNTAX       Counter64
        MAX-ACCESS   read-only
        STATUS       current
        DESCRIPTION
            "Count of the line initialization attempts since the unit
            was last reset.  This count includes both successful and 
            failed attempts."

        REFERENCE    "T1E1.4/2000-009R3"    -- Part 1, common spec
        ::= { vdslPerfDataEntry 7 }

    vdslPerfCurr15MinTimeElapsed OBJECT-TYPE
        SYNTAX       INTEGER(0..899)
        UNITS        "seconds"
        MAX-ACCESS   read-only
        STATUS       current
        DESCRIPTION
            "Total elapsed seconds in this interval."
        REFERENCE    "T1E1.4/2000-009R3"    -- Part 1, common spec
        ::= { vdslPerfDataEntry 8 }

    vdslPerfCurr15MinLofs OBJECT-TYPE
        SYNTAX       HCPerfCurrentCount
        UNITS        "seconds"
        MAX-ACCESS   read-only
        STATUS       current
        DESCRIPTION
            "Count of seconds during this interval that there 
            was Loss of Framing."
        REFERENCE    "T1E1.4/2000-009R3"    -- Part 1, common spec
        ::= { vdslPerfDataEntry 9 }

    vdslPerfCurr15MinLoss OBJECT-TYPE
        SYNTAX       HCPerfCurrentCount
        UNITS        "seconds"
        MAX-ACCESS   read-only
        STATUS       current
        DESCRIPTION
            "Count of seconds during this interval that there 
            was Loss of Signal."
        REFERENCE    "T1E1.4/2000-009R3"    -- Part 1, common spec
        ::= { vdslPerfDataEntry 10 }

    vdslPerfCurr15MinLprs OBJECT-TYPE
        SYNTAX       HCPerfCurrentCount
        UNITS        "seconds"
        MAX-ACCESS   read-only
        STATUS       current
        DESCRIPTION
            "Count of seconds during this interval that there 
            was Loss of Power."
        REFERENCE    "T1E1.4/2000-009R3"    -- Part 1, common spec
        ::= { vdslPerfDataEntry 11 }

    vdslPerfCurr15MinESs OBJECT-TYPE
        SYNTAX       HCPerfCurrentCount
        UNITS        "seconds"
        MAX-ACCESS   read-only
        STATUS       current
        DESCRIPTION
            "Count of Errored Seconds during this interval.  An Errored 
            Second is a one-second interval containing one or more crc 
            anomalies, or one or more los defects."
        REFERENCE    "T1E1.4/2000-009R3"    -- Part 1, common spec
        ::= { vdslPerfDataEntry 12 }

    vdslPerfCurr15MinInits OBJECT-TYPE
        SYNTAX       HCPerfCurrentCount
        MAX-ACCESS   read-only
        STATUS       current
        DESCRIPTION
            "Count of the line initialization attempts during this
            interval.  This count includes both successful and 
            failed attempts."
        REFERENCE    "T1E1.4/2000-009R3"    -- Part 1, common spec
        ::= { vdslPerfDataEntry 13 }

    vdslPerfIntervalTable       OBJECT-TYPE
        SYNTAX       SEQUENCE OF VdslPerfIntervalEntry
        MAX-ACCESS   not-accessible
        STATUS       current
        DESCRIPTION
            "This table provides one row for each Vtu performance 
            data collection interval.  VDSL physical interfaces are
            those ifEntries where ifType is equal to vdsl(97)."
         ::= { vdslMibObjects 5 }

    vdslPerfIntervalEntry       OBJECT-TYPE
        SYNTAX        VdslPerfIntervalEntry
        MAX-ACCESS    not-accessible
        STATUS        current
        DESCRIPTION     
            "An entry in the vdslPerfIntervalTable."
        INDEX         { ifIndex, vdslPhysSide, vdslIntervalNumber }
        ::= { vdslPerfIntervalTable 1 }

    VdslPerfIntervalEntry ::=
        SEQUENCE 
            {
            vdslIntervalNumber                     INTEGER,
            vdslIntervalLofs                       HCPerfIntervalCount,
            vdslIntervalLoss                       HCPerfIntervalCount,
            vdslIntervalLprs                       HCPerfIntervalCount,
            vdslIntervalESs                        HCPerfIntervalCount,
            vdslIntervalInits                      HCPerfIntervalCount
            }

    vdslIntervalNumber OBJECT-TYPE
        SYNTAX       INTEGER(1..96)
        MAX-ACCESS   not-accessible
        STATUS       current
        DESCRIPTION
            "Performance Data Interval number 1 is the the most 
            recent previous interval; interval 96 is 24 hours ago.
            Intervals 2..96 are optional."
        ::= { vdslPerfIntervalEntry 1 }

    vdslIntervalLofs OBJECT-TYPE
        SYNTAX       HCPerfIntervalCount
        UNITS        "seconds"
        MAX-ACCESS   read-only
        STATUS       current
        DESCRIPTION
            "Count of seconds in the interval when there was Loss
            of Framing."
        REFERENCE    "T1E1.4/2000-009R3"    -- Part 1, common spec
        ::= { vdslPerfIntervalEntry 2 }

    vdslIntervalLoss OBJECT-TYPE
        SYNTAX       HCPerfIntervalCount
        UNITS        "seconds"
        MAX-ACCESS   read-only
        STATUS       current
        DESCRIPTION
            "Count of seconds in the interval when there was Loss
            of Signal."
        REFERENCE    "T1E1.4/2000-009R3"    -- Part 1, common spec
        ::= { vdslPerfIntervalEntry 3 }

    vdslIntervalLprs OBJECT-TYPE
        SYNTAX       HCPerfIntervalCount
        UNITS        "seconds"
        MAX-ACCESS   read-only
        STATUS       current
        DESCRIPTION
            "Count of seconds in the interval when there was Loss
            of Power."
        REFERENCE    "T1E1.4/2000-009R3"    -- Part 1, common spec
        ::= { vdslPerfIntervalEntry 4 }

    vdslIntervalESs OBJECT-TYPE
        SYNTAX       HCPerfIntervalCount
        UNITS        "seconds"
        MAX-ACCESS   read-only
        STATUS       current
        DESCRIPTION
            "Count of Errored Seconds in the interval.  An Errored 
            Second is a one-second interval containing one or more crc 
            anomalies, or one or more los defects."
        REFERENCE    "T1E1.4/2000-009R3"    -- Part 1, common spec
        ::= { vdslPerfIntervalEntry 5 }

    vdslIntervalInits OBJECT-TYPE
        SYNTAX       HCPerfIntervalCount
        MAX-ACCESS   read-only
        STATUS       current
        DESCRIPTION
            "Count of the line initialization attempts during this
            interval.  This count includes both successful and 
            failed attempts."
        REFERENCE    "T1E1.4/2000-009R3"    -- Part 1, common spec
        ::= { vdslPerfIntervalEntry 6 }

    vdslChanPerfDataTable       OBJECT-TYPE
        SYNTAX       SEQUENCE OF VdslChanPerfDataEntry
        MAX-ACCESS   not-accessible
        STATUS       current
        DESCRIPTION
            "This table provides one row for each Vtu channel.
            VDSL channel interfaces are those ifEntries where 
            ifType is equal to interleave(124) or fast(125)."
         ::= { vdslMibObjects 6 }

    vdslChanPerfDataEntry OBJECT-TYPE
        SYNTAX        VdslChanPerfDataEntry
        MAX-ACCESS    not-accessible
        STATUS        current
        DESCRIPTION     
            "An entry in the vdslChanPerfDataTable."
        INDEX         { ifIndex, vdslPhysSide }
        ::= { vdslChanPerfDataTable 1 }

    VdslChanPerfDataEntry ::=
        SEQUENCE 
            {
            vdslChanPerfValidIntervals             INTEGER,
            vdslChanPerfInvalidIntervals           INTEGER,
            vdslChanCorrectedOctets                Counter64,
            vdslChanUncorrectBlks                  Counter64,
            vdslChanPerfCurr15MinTimeElapsed       INTEGER,
            vdslChanPerfCurr15MinCorrectedOctets   HCPerfCurrentCount,
            vdslChanPerfCurr15MinUncorrectBlks     HCPerfCurrentCount
            }

    vdslChanPerfValidIntervals OBJECT-TYPE
        SYNTAX        INTEGER(0..96)
        MAX-ACCESS    read-only
        STATUS        current
        DESCRIPTION     
            "Valid Intervals per xxxValidInterval definition
            found in HC-PerfHist-TC-MIB."
        ::= { vdslChanPerfDataEntry 1 }

    vdslChanPerfInvalidIntervals OBJECT-TYPE
        SYNTAX        INTEGER(0..96)
        MAX-ACCESS    read-only
        STATUS        current
        DESCRIPTION     
            "Invalid Intervals per xxxInvalidInterval definition
            found in HC-PerfHist-TC-MIB."
        ::= { vdslChanPerfDataEntry 2 }

    vdslChanCorrectedOctets OBJECT-TYPE
        SYNTAX        Counter64
        MAX-ACCESS    read-only
        STATUS        current
        DESCRIPTION   
            "Count of corrected octets since the unit was last reset."
        REFERENCE    "T1E1.4/2000-009R3"    -- Part 1, common spec
        ::= { vdslChanPerfDataEntry 3 }

    vdslChanUncorrectBlks OBJECT-TYPE
        SYNTAX        Counter64
        MAX-ACCESS    read-only
        STATUS        current
        DESCRIPTION     
            "Count of uncorrected blocks since the unit was last reset."
        REFERENCE    "T1E1.4/2000-009R3"    -- Part 1, common spec
        ::= { vdslChanPerfDataEntry 4 }

    vdslChanPerfCurr15MinTimeElapsed OBJECT-TYPE
        SYNTAX        INTEGER(0..899)
        UNITS         "seconds"
        MAX-ACCESS    read-only
        STATUS        current
        DESCRIPTION     
            "Total elapsed seconds in this interval."
        ::= { vdslChanPerfDataEntry 5 }

    vdslChanPerfCurr15MinCorrectedOctets OBJECT-TYPE
        SYNTAX        HCPerfCurrentCount
        MAX-ACCESS    read-only
        STATUS        current
        DESCRIPTION     
            "Count of corrected octets in this interval."
        REFERENCE    "T1E1.4/2000-009R3"    -- Part 1, common spec
        ::= { vdslChanPerfDataEntry 6 }

    vdslChanPerfCurr15MinUncorrectBlks OBJECT-TYPE
        SYNTAX        HCPerfCurrentCount
        MAX-ACCESS    read-only
        STATUS        current
        DESCRIPTION     
            "Count of uncorrected blocks in this interval."
        REFERENCE    "T1E1.4/2000-009R3"    -- Part 1, common spec
        ::= { vdslChanPerfDataEntry 7 }

    vdslChanIntervalTable       OBJECT-TYPE
        SYNTAX       SEQUENCE OF VdslChanIntervalEntry
        MAX-ACCESS   not-accessible
        STATUS       current
        DESCRIPTION
            "This table provides one row for each Vtu channel data 
            collection interval.  VDSL channel interfaces are those 
            ifEntries where ifType is equal to interleave(124) or 
            fast(125)."
         ::= { vdslMibObjects 7 }

    vdslChanIntervalEntry OBJECT-TYPE
        SYNTAX        VdslChanIntervalEntry
        MAX-ACCESS    not-accessible
        STATUS        current
        DESCRIPTION     
            "An entry in the vdslChanIntervalTable."
        INDEX         { ifIndex, vdslPhysSide, vdslChanIntervalNumber }
        ::= { vdslChanIntervalTable 1 }

    VdslChanIntervalEntry ::=
        SEQUENCE 
            {
            vdslChanIntervalNumber                 INTEGER,
            vdslChanIntervalCorrectedOctets        HCPerfIntervalCount,
            vdslChanIntervalUncorrectBlks          HCPerfIntervalCount
            }

    vdslChanIntervalNumber OBJECT-TYPE
        SYNTAX        INTEGER(1..96)
        MAX-ACCESS    not-accessible
        STATUS        current
        DESCRIPTION
            "Performance Data Interval number 1 is the the most 
            recent previous interval; interval 96 is 24 hours ago.
            Intervals 2..96 are optional."
        ::= { vdslChanIntervalEntry 1 }

    vdslChanIntervalCorrectedOctets OBJECT-TYPE
        SYNTAX        HCPerfIntervalCount
        MAX-ACCESS    read-only
        STATUS        current
        DESCRIPTION     
            "Count of corrected octets in this interval."
        REFERENCE    "T1E1.4/2000-009R3"    -- Part 1, common spec
        ::= { vdslChanIntervalEntry 2 }

    vdslChanIntervalUncorrectBlks OBJECT-TYPE
        SYNTAX        HCPerfIntervalCount
        MAX-ACCESS    read-only
        STATUS        current
        DESCRIPTION     
            "Count of uncorrected blocks in this interval."

        REFERENCE    "T1E1.4/2000-009R3"    -- Part 1, common spec
        ::= { vdslChanIntervalEntry 3 }

    vdslLineConfProfileTable OBJECT-TYPE
        SYNTAX         SEQUENCE OF VdslLineConfProfileEntry
        MAX-ACCESS     not-accessible
        STATUS         current
        DESCRIPTION
            "This table contains information on the VDSL line
            configuration.  One entry in this table reflects a
            profile defined by a manager which can be used to
            configure the VDSL line."
        ::= { vdslMibObjects 8 }

    vdslLineConfProfileEntry OBJECT-TYPE
        SYNTAX         VdslLineConfProfileEntry
        MAX-ACCESS     not-accessible
        STATUS         current
        DESCRIPTION
            "Each entry consists of a list of parameters that
            represents the configuration of a VDSL modem.  A 
            default profile will always exist.  This profile's 
            name will be set to `DEFVAL' and its parameters will 
            be set to vendor specific values, unless otherwise 
            specified in this document."
        INDEX { IMPLIED vdslLineConfProfileName,
                        vdslPhysSide }
        ::= { vdslLineConfProfileTable 1 }

    VdslLineConfProfileEntry ::=
        SEQUENCE 
            {
            vdslLineConfProfileName                SnmpAdminString,
            vdslLineConfTargetSnrMgn               INTEGER,
            vdslLineConfTxSpeed                    INTEGER,
            vdslLineConfRxSpeed                    INTEGER,
            vdslLineConfProfileRowStatus           RowStatus,
            hwVdslLineConfAutoTrain				   INTEGER
            }

    vdslLineConfProfileName OBJECT-TYPE
        SYNTAX       SnmpAdminString (SIZE (1..32))
        MAX-ACCESS   read-create
        STATUS       current
        DESCRIPTION
            "This object is used by the line configuration table
            in order to identify a row in that table.  The system 
            will always provide a default profile whose name is 
            `DEFVAL'."
        ::= { vdslLineConfProfileEntry 1 }

    vdslLineConfTargetSnrMgn OBJECT-TYPE
        SYNTAX       INTEGER (0..310)
        UNITS        "tenth dB"
        MAX-ACCESS   read-create
        STATUS       current
        DESCRIPTION
            "Configured Target Signal/Noise Margin.  This is the 
            Noise Margin the modem must achieve with a BER of 10-7 
            or better to successfully complete initialization."
        REFERENCE    "T1E1.4/2000-009R3"    -- Part 1, common spec
        ::= { vdslLineConfProfileEntry 2 }

    vdslLineConfTxSpeed OBJECT-TYPE
        SYNTAX       INTEGER 
        UNITS        "bits per second"
        MAX-ACCESS   read-create
        STATUS       current
        DESCRIPTION
            "Transmit speed for this modem.  The corresponding modem
            on the other end of the VDSL line will have an equal
            vdslLineConfRxSpeed value."
        REFERENCE    "T1E1.4/2000-009R3"    -- Part 1, common spec
        ::= { vdslLineConfProfileEntry 3 }

    vdslLineConfRxSpeed OBJECT-TYPE
        SYNTAX       INTEGER 
        UNITS        "bits per second"
        MAX-ACCESS   read-create
        STATUS       current
        DESCRIPTION
            "Receive speed for this modem.  The corresponding modem
            on the other end of the VDSL line will have an equal
            vdslLineConfTxSpeed value."
        REFERENCE    "T1E1.4/2000-009R3"    -- Part 1, common spec
        ::= { vdslLineConfProfileEntry 4 }

    vdslLineConfProfileRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineConfProfileEntry 5 }
        
	hwVdslLineConfAutoTrain OBJECT-TYPE
		SYNTAX INTEGER
		{
			enabled(1),
			disabled(2)
		}
		MAX-ACCESS read-write
		STATUS current
		DESCRIPTION
			"
			This object specifies if the modem is allowed to train automatically.
			"
		DEFVAL { 1 }
		::= { vdslLineConfProfileEntry 65536 }


    -- 
    -- Multiple carrier modulation (MCM) configuration profile tables
    --

    vdslLineMCMConfProfileTable OBJECT-TYPE
        SYNTAX       SEQUENCE OF VdslLineMCMConfProfileEntry
        MAX-ACCESS   not-accessible
        STATUS       current
        DESCRIPTION
            "This table contains information on the VDSL line
            configuration.  One entry in this table reflects a
            profile defined by a manager which can be used to
            configure the VDSL line.

            This table MUST be implemented for multiple carrier VDSL
            lines.  This table MUST NOT be implemented for Single 
            carrier VDSL lines."
        ::= { vdslMibObjects 9 }

    vdslLineMCMConfProfileEntry OBJECT-TYPE
        SYNTAX       VdslLineMCMConfProfileEntry
        MAX-ACCESS   not-accessible
        STATUS       current
        DESCRIPTION
            "Each entry consists of a list of parameters that
            represents the configuration of a multiple carrier
            modulation VDSL modem.  A default profile will always 
            exist.  This profile's name will be set to `DEFVAL' 
            and its parameters will be set to vendor specific values,
            unless otherwise specified in this document."
        INDEX { IMPLIED vdslLineConfProfileName,
                        vdslPhysSide }
        ::= { vdslLineMCMConfProfileTable 1 }

    VdslLineMCMConfProfileEntry ::=
        SEQUENCE
            {
            vdslMCMConfProfileTxWindowLength       INTEGER,
            vdslMCMConfProfileRowStatus            RowStatus
            } 

    vdslMCMConfProfileTxWindowLength OBJECT-TYPE
        SYNTAX       INTEGER(1..255)
        UNITS        "samples"
        MAX-ACCESS   read-create
        STATUS       current
        DESCRIPTION
            "Specifies the length of the transmit window, counted
            in samples at the sampling rate corresponding to the 
            negotiated value of N."
        REFERENCE    "T1E1.4/2000-013R4"    -- Part 3, MCM
        ::= { vdslLineMCMConfProfileEntry 1 }

    vdslMCMConfProfileRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineMCMConfProfileEntry 2 }

    vdslLineMCMConfProfileTxBandTable OBJECT-TYPE
        SYNTAX       SEQUENCE OF VdslLineMCMConfProfileTxBandEntry
        MAX-ACCESS   not-accessible
        STATUS       current
        DESCRIPTION
            "This table contains transmit band descriptor configuration
            information for a VDSL line.  Each entry in this table 
            reflects the configuration for one of possibly many bands
            with a multiple carrier modulation (MCM) VDSL line.
            These entries are defined by a manager and can be used to
            configure the VDSL line.

            This table MUST be implemented for multiple carrier 
            modulation (MCM) VDSL lines.  This table MUST NOT be 
            implemented for single carrier modulation VDSL lines."
        ::= { vdslMibObjects 10 }

    vdslLineMCMConfProfileTxBandEntry OBJECT-TYPE
        SYNTAX       VdslLineMCMConfProfileTxBandEntry
        MAX-ACCESS   not-accessible
        STATUS       current
        DESCRIPTION
            "Each entry consists of a transmit band descriptor, which
            defines the start and stop bands and the power spectral
            density (PSD) for that band.  

            A default profile will always exist.  This profile's name 
            will be set to `DEFVAL' and its parameters will be set to 
            vendor specific values, unless otherwise specified in this 
            document."
        INDEX { IMPLIED vdslLineConfProfileName, 
                        vdslPhysSide,
                        vdslMCMConfProfileTxBandNumber }
        ::= { vdslLineMCMConfProfileTxBandTable 1 }

    VdslLineMCMConfProfileTxBandEntry ::=
        SEQUENCE
            {
            vdslMCMConfProfileTxBandNumber           INTEGER,
            vdslMCMConfProfileTxBandStart            INTEGER,
            vdslMCMConfProfileTxBandStop             INTEGER,
            vdslMCMConfProfileTxBandRowStatus        RowStatus
            } 

    vdslMCMConfProfileTxBandNumber OBJECT-TYPE
        SYNTAX       INTEGER
        MAX-ACCESS   read-create
        STATUS       current
        DESCRIPTION
            "The index for this band descriptor entry."
        ::= { vdslLineMCMConfProfileTxBandEntry 1 }

    vdslMCMConfProfileTxBandStart OBJECT-TYPE
        SYNTAX       INTEGER
        MAX-ACCESS   read-create
        STATUS       current
        DESCRIPTION
            "Start tone index for this band."
        REFERENCE    "T1E1.4/2000-013R4"    -- Part 3, MCM
        ::= { vdslLineMCMConfProfileTxBandEntry 2 }

    vdslMCMConfProfileTxBandStop OBJECT-TYPE
        SYNTAX       INTEGER
        MAX-ACCESS   read-create
        STATUS       current
        DESCRIPTION
            "Stop tone index for this band."
        REFERENCE    "T1E1.4/2000-013R4"    -- Part 3, MCM
        ::= { vdslLineMCMConfProfileTxBandEntry 3 }

    vdslMCMConfProfileTxBandRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineMCMConfProfileTxBandEntry 4 }

    vdslLineMCMConfProfileRxBandTable OBJECT-TYPE
        SYNTAX       SEQUENCE OF VdslLineMCMConfProfileRxBandEntry
        MAX-ACCESS   not-accessible
        STATUS       current
        DESCRIPTION
            "This table contains receive band descriptor configuration
            information for a VDSL line.  Each entry in this table 
            reflects the configuration for one of possibly many bands
            with a multiple carrier modulation (MCM) VDSL line.
            These entries are defined by a manager and can be used to
            configure the VDSL line.

            This table MUST be implemented for multiple carrier 
            modulation (MCM) VDSL lines.  This table MUST NOT be 
            implemented for single carrier modulation VDSL lines."
        ::= { vdslMibObjects 11 }

    vdslLineMCMConfProfileRxBandEntry OBJECT-TYPE
        SYNTAX       VdslLineMCMConfProfileRxBandEntry
        MAX-ACCESS   not-accessible
        STATUS       current
        DESCRIPTION
            "Each entry consists of a transmit band descriptor, which
            defines the start and stop bands and the power spectral
            density (PSD) for that band.  

            A default profile will always exist.  This profile's name 
            will be set to `DEFVAL' and its parameters will be set to 
            vendor specific values, unless otherwise specified in this 
            document."
        INDEX { IMPLIED vdslLineConfProfileName, 
                        vdslPhysSide,
                        vdslMCMConfProfileRxBandNumber }
        ::= { vdslLineMCMConfProfileRxBandTable 1 }

    VdslLineMCMConfProfileRxBandEntry ::=
        SEQUENCE
            {
            vdslMCMConfProfileRxBandNumber           INTEGER,
            vdslMCMConfProfileRxBandStart            INTEGER,
            vdslMCMConfProfileRxBandStop             INTEGER,
            vdslMCMConfProfileRxBandRowStatus        RowStatus
            } 

    vdslMCMConfProfileRxBandNumber OBJECT-TYPE
        SYNTAX       INTEGER
        MAX-ACCESS   read-create
        STATUS       current
        DESCRIPTION
            "The index for this band descriptor entry."
        ::= { vdslLineMCMConfProfileRxBandEntry 1 }

    vdslMCMConfProfileRxBandStart OBJECT-TYPE
        SYNTAX       INTEGER
        MAX-ACCESS   read-create
        STATUS       current
        DESCRIPTION
            "Start tone index for this band."
        REFERENCE    "T1E1.4/2000-013R4"    -- Part 3, MCM
        ::= { vdslLineMCMConfProfileRxBandEntry 2 }

    vdslMCMConfProfileRxBandStop OBJECT-TYPE
        SYNTAX       INTEGER
        MAX-ACCESS   read-create
        STATUS       current
        DESCRIPTION
            "Stop tone index for this band."
        REFERENCE    "T1E1.4/2000-013R4"    -- Part 3, MCM
        ::= { vdslLineMCMConfProfileRxBandEntry 3 }

    vdslMCMConfProfileRxBandRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineMCMConfProfileRxBandEntry 4 }

    vdslLineMCMConfProfileTxPSDTable OBJECT-TYPE
        SYNTAX       SEQUENCE OF VdslLineMCMConfProfileTxPSDEntry
        MAX-ACCESS   not-accessible
        STATUS       current
        DESCRIPTION
            "This table contains transmit PSD mask descriptor 
            configuration information for a VDSL line.  Each entry in 
            this table reflects the configuration for one tone within
            a multiple carrier modulation (MCM) VDSL line.  These 
            entries are defined by a manager and can be used to 
            configure the VDSL line.

            This table MUST be implemented for multiple carrier 
            modulation (MCM) VDSL lines.  This table MUST NOT be 
            implemented for single carrier modulation VDSL lines."
        ::= { vdslMibObjects 12 }

    vdslLineMCMConfProfileTxPSDEntry OBJECT-TYPE
        SYNTAX       VdslLineMCMConfProfileTxPSDEntry
        MAX-ACCESS   not-accessible
        STATUS       current
        DESCRIPTION
            "Each entry consists of a transmit PSD mask descriptor, 
            which defines the power spectral density (PSD) for a tone.

            A default profile will always exist.  This profile's name 
            will be set to `DEFVAL' and its parameters will be set to 
            vendor specific values, unless otherwise specified in this 
            document."
        INDEX { IMPLIED vdslLineConfProfileName, 
                        vdslPhysSide,
                        vdslMCMConfProfileTxPSDNumber }
        ::= { vdslLineMCMConfProfileTxPSDTable 1 }

    VdslLineMCMConfProfileTxPSDEntry ::=
        SEQUENCE
            {
            vdslMCMConfProfileTxPSDNumber            INTEGER,
            vdslMCMConfProfileTxPSDTone              INTEGER,
            vdslMCMConfProfileTxPSDPSD               INTEGER,
            vdslMCMConfProfileTxPSDRowStatus         RowStatus
            } 

    vdslMCMConfProfileTxPSDNumber OBJECT-TYPE
        SYNTAX       INTEGER
        MAX-ACCESS   read-create
        STATUS       current
        DESCRIPTION
            "The index for this mask descriptor entry."
        ::= { vdslLineMCMConfProfileTxPSDEntry 1 }

    vdslMCMConfProfileTxPSDTone OBJECT-TYPE
        SYNTAX       INTEGER
        MAX-ACCESS   read-create
        STATUS       current
        DESCRIPTION
            "The tone index for which the PSD is being specified."
        REFERENCE    "T1E1.4/2000-013R4"    -- Part 3, MCM
        ::= { vdslLineMCMConfProfileTxPSDEntry 2 }

    vdslMCMConfProfileTxPSDPSD OBJECT-TYPE
        SYNTAX       INTEGER
        UNITS        "0.5dB"
        MAX-ACCESS   read-create
        STATUS       current
        DESCRIPTION
            "Power Spectral Density level in steps of 0.5dB with
            an offset of -140dbm/Hz."
        REFERENCE    "T1E1.4/2000-013R4"    -- Part 3, MCM
        ::= { vdslLineMCMConfProfileTxPSDEntry 3 }

    vdslMCMConfProfileTxPSDRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineMCMConfProfileTxPSDEntry 4 }

    vdslLineMCMConfProfileMaxTxPSDTable OBJECT-TYPE
        SYNTAX       SEQUENCE OF VdslLineMCMConfProfileMaxTxPSDEntry
        MAX-ACCESS   not-accessible
        STATUS       current
        DESCRIPTION
            "This table contains transmit maximum PSD mask descriptor 
            configuration information for a VDSL line.  Each entry in 
            this table reflects the configuration for one tone within
            a multiple carrier modulation (MCM) VDSL modem.  These 
            entries are defined by a manager and can be used to 
            configure the VDSL line.

            This table MUST be implemented for multiple carrier 
            modulation (MCM) VDSL lines.  This table MUST NOT be 
            implemented for single carrier modulation VDSL lines."
        ::= { vdslMibObjects 13 }

    vdslLineMCMConfProfileMaxTxPSDEntry OBJECT-TYPE
        SYNTAX       VdslLineMCMConfProfileMaxTxPSDEntry
        MAX-ACCESS   not-accessible
        STATUS       current
        DESCRIPTION
            "Each entry consists of a transmit PSD mask descriptor, 
            which defines the maximum power spectral density (PSD) 
            for a tone.

            A default profile will always exist.  This profile's name 
            will be set to `DEFVAL' and its parameters will be set to 
            vendor specific values, unless otherwise specified in this 
            document."
        INDEX { IMPLIED vdslLineConfProfileName, 
                        vdslPhysSide,
                        vdslMCMConfProfileMaxTxPSDNumber }
        ::= { vdslLineMCMConfProfileMaxTxPSDTable 1 }

    VdslLineMCMConfProfileMaxTxPSDEntry ::=
        SEQUENCE
            {
            vdslMCMConfProfileMaxTxPSDNumber            INTEGER,
            vdslMCMConfProfileMaxTxPSDTone              INTEGER,
            vdslMCMConfProfileMaxTxPSDPSD               INTEGER,
            vdslMCMConfProfileMaxTxPSDRowStatus         RowStatus
            } 

    vdslMCMConfProfileMaxTxPSDNumber OBJECT-TYPE
        SYNTAX       INTEGER
        MAX-ACCESS   read-create
        STATUS       current
        DESCRIPTION
            "The index for this band descriptor entry."
        ::= { vdslLineMCMConfProfileMaxTxPSDEntry 1 }

    vdslMCMConfProfileMaxTxPSDTone OBJECT-TYPE
        SYNTAX       INTEGER
        MAX-ACCESS   read-create
        STATUS       current
        DESCRIPTION
            "The tone index for which the PSD is being specified."
        REFERENCE    "T1E1.4/2000-013R4"    -- Part 3, MCM
        ::= { vdslLineMCMConfProfileMaxTxPSDEntry 2 }

    vdslMCMConfProfileMaxTxPSDPSD OBJECT-TYPE
        SYNTAX       INTEGER
        UNITS        "0.5dB"
        MAX-ACCESS   read-create
        STATUS       current
        DESCRIPTION
            "Power Spectral Density level in steps of 0.5dB with
            an offset of -140dbm/Hz."
        REFERENCE    "T1E1.4/2000-013R4"    -- Part 3, MCM
        ::= { vdslLineMCMConfProfileMaxTxPSDEntry 3 }

    vdslMCMConfProfileMaxTxPSDRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineMCMConfProfileMaxTxPSDEntry 4 }

    vdslLineMCMConfProfileMaxRxPSDTable OBJECT-TYPE
        SYNTAX       SEQUENCE OF VdslLineMCMConfProfileMaxRxPSDEntry
        MAX-ACCESS   not-accessible
        STATUS       current
        DESCRIPTION
            "This table contains maximum receive PSD mask descriptor 
            configuration information for a VDSL line.  Each entry in 
            this table reflects the configuration for one tone within
            a multiple carrier modulation (MCM) VDSL modem.  These 
            entries are defined by a manager and can be used to 
            configure the VDSL line.

            This table MUST be implemented for multiple carrier 
            modulation (MCM) VDSL lines.  This table MUST NOT be 
            implemented for single carrier modulation VDSL lines."
        ::= { vdslMibObjects 14 }

    vdslLineMCMConfProfileMaxRxPSDEntry OBJECT-TYPE
        SYNTAX       VdslLineMCMConfProfileMaxRxPSDEntry
        MAX-ACCESS   not-accessible
        STATUS       current
        DESCRIPTION
            "Each entry consists of a transmit PSD mask descriptor, 
            which defines the power spectral density (PSD) for a
            tone.

            A default profile will always exist.  This profile's name 
            will be set to `DEFVAL' and its parameters will be set to 
            vendor specific values, unless otherwise specified in this 
            document."
        INDEX { IMPLIED vdslLineConfProfileName, 
                        vdslPhysSide,
                        vdslMCMConfProfileMaxRxPSDNumber }
        ::= { vdslLineMCMConfProfileMaxRxPSDTable 1 }

    VdslLineMCMConfProfileMaxRxPSDEntry ::=
        SEQUENCE
            {
            vdslMCMConfProfileMaxRxPSDNumber            INTEGER,
            vdslMCMConfProfileMaxRxPSDTone              INTEGER,
            vdslMCMConfProfileMaxRxPSDPSD               INTEGER,
            vdslMCMConfProfileMaxRxPSDRowStatus         RowStatus
            } 

    vdslMCMConfProfileMaxRxPSDNumber OBJECT-TYPE
        SYNTAX       INTEGER
        MAX-ACCESS   read-create
        STATUS       current
        DESCRIPTION
            "The index for this band descriptor entry."
        ::= { vdslLineMCMConfProfileMaxRxPSDEntry 1 }

    vdslMCMConfProfileMaxRxPSDTone OBJECT-TYPE
        SYNTAX       INTEGER
        MAX-ACCESS   read-create
        STATUS       current
        DESCRIPTION
            "The tone index for which the PSD is being specified."
        REFERENCE    "T1E1.4/2000-013R4"    -- Part 3, MCM
        ::= { vdslLineMCMConfProfileMaxRxPSDEntry 2 }

    vdslMCMConfProfileMaxRxPSDPSD OBJECT-TYPE
        SYNTAX       INTEGER
        UNITS        "0.5dB"
        MAX-ACCESS   read-create
        STATUS       current
        DESCRIPTION
            "Power Spectral Density level in steps of 0.5dB with
            an offset of -140dbm/Hz."
        REFERENCE    "T1E1.4/2000-013R4"    -- Part 3, MCM
        ::= { vdslLineMCMConfProfileMaxRxPSDEntry 3 }

    vdslMCMConfProfileMaxRxPSDRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineMCMConfProfileMaxRxPSDEntry 4 }

    -- 
    -- Single carrier modulation (SCM) configuration profile table
    --

    vdslLineSCMConfProfileTable OBJECT-TYPE
        SYNTAX       SEQUENCE OF VdslLineSCMConfProfileEntry
        MAX-ACCESS   not-accessible
        STATUS       current
        DESCRIPTION
            "This table contains information on the VDSL line
            configuration.  One entry in this table reflects a
            profile defined by a manager which can be used to
            configure the VDSL line.

            This table MUST be implemented for single carrier 
            modulation (SCM) VDSL lines.  This table MUST NOT be 
            implemented for multiple carrier modulation (MCM) VDSL 
            lines."
        ::= { vdslMibObjects 15 }

    vdslLineSCMConfProfileEntry OBJECT-TYPE
        SYNTAX       VdslLineSCMConfProfileEntry
        MAX-ACCESS   not-accessible
        STATUS       current
        DESCRIPTION
            "Each entry consists of a list of parameters that
            represents the configuration of a single carrier
            modulation VDSL modem.  A default profile will always 
            exist.  This profile's name will be set to `DEFVAL' 
            and its parameters will be set to vendor specific values,
            unless otherwise specified in this document."
        INDEX { IMPLIED vdslLineConfProfileName,
                        vdslPhysSide }
        ::= { vdslLineSCMConfProfileTable 1 }

    VdslLineSCMConfProfileEntry ::=
        SEQUENCE
            {
            vdslSCMConfProfileInterleaveDepth      INTEGER,
            vdslSCMConfProfileFastCodewordSize     INTEGER,
            vdslSCMConfProfileTransmitPSDMask      BITS,
            vdslSCMConfProfileTransmitPSDLevel     INTEGER,
            vdslSCMConfProfileSymbolRateProfile    INTEGER,
            vdslSCMConfProfileConstellationSize    INTEGER,
            vdslSCMConfProfileCenterFrequency      INTEGER,
            vdslSCMConfProfileRowStatus            RowStatus
            } 

    vdslSCMConfProfileInterleaveDepth OBJECT-TYPE
        SYNTAX       INTEGER
        UNITS        "octets"
        MAX-ACCESS   read-create
        STATUS       current
        DESCRIPTION
            "Specifies the interleaving depth."
        REFERENCE    "T1E1.4/2000-011R3"    -- Part 2, SCM
        ::= { vdslLineSCMConfProfileEntry 1 }

    vdslSCMConfProfileFastCodewordSize OBJECT-TYPE
        SYNTAX       INTEGER(0..180)
        UNITS        "octets"
        MAX-ACCESS   read-create
        STATUS       current
        DESCRIPTION
            "Specifies the length in octets of the fast codeword.
            A value of 0 indicates that the single latency transport 
            class is to be utilized."
        REFERENCE    "T1E1.4/2000-011R3"    -- Part 2, SCM
        ::= { vdslLineSCMConfProfileEntry 2 }

    vdslSCMConfProfileTransmitPSDMask OBJECT-TYPE
        SYNTAX       BITS
            {
            vendorNotch1(0),     -- vendor specific notch
            vendorNotch2(1),     -- vendor specific notch
            amateurBand30m(2),   -- amateur radio band notch
            amateurBand40m(3),   -- amateur radio band notch
            amateurBand80m(4),   -- amateur radio band notch
            amateurBand160m(5)   -- amateur radio band notch 
            }
        MAX-ACCESS   read-create
        STATUS       current
        DESCRIPTION
            "The transmit power spectral density mask code."
        REFERENCE    "T1E1.4/2000-011R3"    -- Part 2, SCM
        ::= { vdslLineSCMConfProfileEntry 3 }

    vdslSCMConfProfileTransmitPSDLevel OBJECT-TYPE
        SYNTAX       INTEGER
        UNITS        "dBm/Hz"
        MAX-ACCESS   read-create
        STATUS       current
        DESCRIPTION
            "The transmit power spectral density for the VDSL modem."
        REFERENCE    "T1E1.4/2000-011R3"    -- Part 2, SCM
        ::= { vdslLineSCMConfProfileEntry 4 }

    vdslSCMConfProfileSymbolRateProfile OBJECT-TYPE
        SYNTAX       INTEGER
        UNITS        "kbaud"
        MAX-ACCESS   read-create
        STATUS       current
        DESCRIPTION
            "The symbol rate profile calculated as S = SR/BSR, where
            SR is the required symbol rate in kbaud, BSR  = 67.5."
        REFERENCE    "T1E1.4/2000-011R3"    -- Part 2, SCM
        ::= { vdslLineSCMConfProfileEntry 5 }

    vdslSCMConfProfileConstellationSize OBJECT-TYPE
        SYNTAX       INTEGER(0..15)
        UNITS        "log2"
        MAX-ACCESS   read-create
        STATUS       current
        DESCRIPTION
            "Specifies the constellation size."

        REFERENCE    "T1E1.4/2000-011R3"    -- Part 2, SCM
        ::= { vdslLineSCMConfProfileEntry 6 }

    vdslSCMConfProfileCenterFrequency OBJECT-TYPE
        SYNTAX       INTEGER(0..511)
        UNITS        "kHz"
        MAX-ACCESS   read-create
        STATUS       current
        DESCRIPTION
            "Specifies the center frequency profile K."
        REFERENCE    "T1E1.4/2000-011R3"    -- Part 2, SCM
        ::= { vdslLineSCMConfProfileEntry 7 }

    vdslSCMConfProfileRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineSCMConfProfileEntry 8 }

    --
    -- Alarm configuration profile table
    -- 

    vdslLineAlarmConfProfileTable OBJECT-TYPE
        SYNTAX       SEQUENCE OF VdslLineAlarmConfProfileEntry
        MAX-ACCESS   not-accessible
        STATUS       current
        DESCRIPTION
            "This table contains information on the VDSL line alarm
            configuration.  One entry in this table reflects a profile
            defined by a manager which can be used to configure the 
            VDSL line alarm thresholds."
        ::= { vdslMibObjects 16 }

    vdslLineAlarmConfProfileEntry OBJECT-TYPE
        SYNTAX       VdslLineAlarmConfProfileEntry 
        MAX-ACCESS   not-accessible
        STATUS       current
        DESCRIPTION
            "Each entry consists of a list of parameters that
            represents the configuration of a VDSL line alarm
            profile.  A default profile will always exist.  This 
            profile's name will be set to `DEFVAL' and its 
            parameters will be set to vendor specific values,
            unless otherwise specified in this document."
        INDEX { IMPLIED vdslLineAlarmConfProfileName,
                        vdslPhysSide }
        ::= { vdslLineAlarmConfProfileTable 1 }

    VdslLineAlarmConfProfileEntry ::=
        SEQUENCE 
            {
            vdslLineAlarmConfProfileName         SnmpAdminString,
            vdslThresh15MinLofs                  INTEGER,
            vdslThresh15MinLoss                  INTEGER,
            vdslThresh15MinLprs                  INTEGER,
            vdslThresh15MinESs                   INTEGER,
            vdslInitFailureNotificationEnable    TruthValue,
            vdslLineAlarmConfProfileRowStatus    RowStatus
            }

    vdslLineAlarmConfProfileName OBJECT-TYPE
        SYNTAX       SnmpAdminString (SIZE (1..32))
        MAX-ACCESS   read-create
        STATUS       current
        DESCRIPTION
            "This object is used by the line alarm configuration table
            in order to identify a row in that table.  The system will
            always provide a default profile whose name is `DEFVAL'."
        ::= { vdslLineAlarmConfProfileEntry 1 }

    vdslThresh15MinLofs OBJECT-TYPE
        SYNTAX       INTEGER(0..899)
        UNITS        "seconds"
        MAX-ACCESS   read-create
        STATUS       current
        DESCRIPTION
            "This object configures the threshold for the number of
             loss of frame seconds (lofs) within any given 15-minute
             performance data collection interval.  If the value of 
             loss of frame seconds in a particular 15-minute collection 
             interval reaches/exceeds this value, a 
             vdslPerfLofsThreshNotification notification will be 
             generated.  No more than one notification will be sent 
             per interval."
        ::= { vdslLineAlarmConfProfileEntry 2 }

    vdslThresh15MinLoss OBJECT-TYPE
        SYNTAX       INTEGER(0..899)
        UNITS        "seconds"
        MAX-ACCESS   read-create
        STATUS       current
        DESCRIPTION
            "This object configures the threshold for the number of
             loss of signal seconds (loss) within any given 15-minute
             performance data collection interval.  If the value of 
             loss of frame seconds in a particular 15-minute collection 
             interval reaches/exceeds this value, a 
             vdslPerfLossThreshNotification notification will be 
             generated.  One notification will be sent per interval
             per endpoint."
        ::= { vdslLineAlarmConfProfileEntry 3 }

    vdslThresh15MinLprs OBJECT-TYPE
        SYNTAX       INTEGER(0..899)
        UNITS        "seconds"
        MAX-ACCESS   read-create
        STATUS       current
        DESCRIPTION
            "This object configures the threshold for the number of
             loss of power seconds (lprs) within any given 15-minute
             performance data collection interval.  If the value of 
             loss of frame seconds in a particular 15-minute collection 
             interval reaches/exceeds this value, a 
             vdslPerfLprsThreshNotification notification will be 
             generated.  No more than one notification will be sent 
             per interval."
        ::= { vdslLineAlarmConfProfileEntry 4 }

    vdslThresh15MinESs OBJECT-TYPE
        SYNTAX       INTEGER(0..899)
        UNITS        "seconds"
        MAX-ACCESS   read-create
        STATUS       current
        DESCRIPTION
            "This object configures the threshold for the number of
             errored seconds (lofs) within any given 15-minute
             performance data collection interval.  If the value of 
             loss of frame seconds in a particular 15-minute collection 
             interval reaches/exceeds this value, a 
             vdslPerfESsThreshNotification notification will be 
             generated.  No more than one notification will be sent 
             per interval."
        ::= { vdslLineAlarmConfProfileEntry 5 }

    vdslInitFailureNotificationEnable OBJECT-TYPE
        SYNTAX       TruthValue
        MAX-ACCESS   read-create
        STATUS       current
        DESCRIPTION
            "This object specifies if a vdslInitFailureNotification 
            notification will be generated if an initialization
            failure occurs."
        ::= { vdslLineAlarmConfProfileEntry 6 }

    vdslLineAlarmConfProfileRowStatus OBJECT-TYPE
        SYNTAX       RowStatus
        MAX-ACCESS   read-create
        STATUS       current
        DESCRIPTION
            "This object is used to create a new row or modify or
            delete an existing row in this table.

            A profile activated by setting this object to `active'.  
            When `active' is set, the system will validate the profile.

            Before a profile can be deleted or taken out of
            service, (by setting this object to `destroy' or
            `outOfService') it must be first unreferenced
            from all associated lines."
        ::= { vdslLineAlarmConfProfileEntry 7 }
      
		hwVdslEtherStatsTable OBJECT-TYPE
			SYNTAX SEQUENCE OF HwVdslEtherStatsEntry
			MAX-ACCESS not-accessible
			STATUS current
			DESCRIPTION
				"
				This table provides one row for each Vtu. Each row 
				contains the ehternet statistic Parameters table for
				that Vtu.This table is Ether state for VDSL table.
				"
			::= { vdslMibObjects 65536 }
		
		hwVdslEtherStatsEntry OBJECT-TYPE
			SYNTAX HwVdslEtherStatsEntry
			MAX-ACCESS not-accessible
			STATUS current
			DESCRIPTION
				"
				An entry in the hwVdslEtherStatsTable.
				This table defines and collects the statistical data of Ether.
				"
			INDEX { ifIndex, vdslPhysSide }
			::= { hwVdslEtherStatsTable 1 }
		
		HwVdslEtherStatsEntry ::=
			SEQUENCE { 
				hwVdslEtherStatsAlignmentErrors
					Counter32,
				hwVdslEtherStatsSingleCollisionFrames
					Counter32,
				hwVdslEtherStatsMultipleCollisionFrames
					Counter32,
				hwVdslEtherStatsDeferredTransmissions
					Counter32,
				hwVdslEtherStatsLateCollisionFrames
					Counter32,
				hwVdslEtherStatsExcessiveCollisionFrames
					Counter32,
				hwVdslEtherStatsReceiveErrors
					Counter32,
				hwVdslEtherStatsCarrierErrors
					Counter32,
				hwVdslEtherStatsTooLongErrors
					Counter32,
				hwVdslEtherStatsSequenceErrors
					Counter32,
				hwVdslEtherStatsTransmitOctets
					Counter32,
				hwVdslEtherStatsReceiveOctets
					Counter32,
				hwVdslEtherStatsReceiveBroadcastFrames
					Counter32,
				hwVdslEtherStatsReceivePauseFrames
					Counter32,
				hwVdslEtherStatsTransmitPauseFrames
					Counter32,
				hwVdslEtherStatsTransmitFrames
					Counter32,
				hwVdslEtherStatsReceiveFrames
					Counter32
			 }

		hwVdslEtherStatsAlignmentErrors OBJECT-TYPE
			SYNTAX Counter32
			MAX-ACCESS read-only
			STATUS current
			DESCRIPTION
				"
				The total number of frames received with alignment errors (an odd
				number of nibbles).
				"
			::= { hwVdslEtherStatsEntry 1 }
		
		hwVdslEtherStatsSingleCollisionFrames OBJECT-TYPE
			SYNTAX Counter32
			MAX-ACCESS read-only
			STATUS current
			DESCRIPTION
				"
				A count of successfully transmitted frames for which transmission 
				was inhibited by exactly one collision.
				"
			::= { hwVdslEtherStatsEntry 2 }
		
		hwVdslEtherStatsMultipleCollisionFrames OBJECT-TYPE
			SYNTAX Counter32
			MAX-ACCESS read-only
			STATUS current
			DESCRIPTION
				"
				A count of successfully transmitted frames for which transmission
				was inhibited by more than one collision.
				"
			::= { hwVdslEtherStatsEntry 3 }
		
		hwVdslEtherStatsDeferredTransmissions OBJECT-TYPE
			SYNTAX Counter32
			MAX-ACCESS read-only
			STATUS current
			DESCRIPTION
				"
				A count of frames for which the first transmission
				attempt was delayed because the Ethernet media was
				busy.
				"
			::= { hwVdslEtherStatsEntry 4 }
		
		hwVdslEtherStatsLateCollisionFrames OBJECT-TYPE
			SYNTAX Counter32
			MAX-ACCESS read-only
			STATUS current
			DESCRIPTION
				"
				The total number of times that a collision was detected
				on a particular interface later than 512 bit-times into
				the transmission of a packet.
				"
			::= { hwVdslEtherStatsEntry 5 }
		
		hwVdslEtherStatsExcessiveCollisionFrames OBJECT-TYPE
			SYNTAX Counter32
			MAX-ACCESS read-only
			STATUS current
			DESCRIPTION
				"
				A count of frames for which transmission failed due to 
				excessive collisions.
				"
			::= { hwVdslEtherStatsEntry 6 }
		
		hwVdslEtherStatsReceiveErrors OBJECT-TYPE
			SYNTAX Counter32
			MAX-ACCESS read-only
			STATUS current
			DESCRIPTION
				"
				The total number of frames received with less than 64 bytes.
				"
			::= { hwVdslEtherStatsEntry 7 }
		
		hwVdslEtherStatsCarrierErrors OBJECT-TYPE
			SYNTAX Counter32
			MAX-ACCESS read-only
			STATUS current
			DESCRIPTION
				"The total number of times that the carrier sense condition was
				lost or never asserted when attempting to transmit a frame on 
				a particular interface.
				"
			::= { hwVdslEtherStatsEntry 8 }
		
		hwVdslEtherStatsTooLongErrors OBJECT-TYPE
			SYNTAX Counter32
			MAX-ACCESS read-only
			STATUS current
			DESCRIPTION
				"
				The total number of frames received with more than maximum length.
				"
			::= { hwVdslEtherStatsEntry 9 }
		
		hwVdslEtherStatsSequenceErrors OBJECT-TYPE
			SYNTAX Counter32
			MAX-ACCESS read-only
			STATUS current
			DESCRIPTION
				"
				The total number of frames received that had a bad Frame Check
				Sequence (FCS).
				"
			::= { hwVdslEtherStatsEntry 10 }
		
		hwVdslEtherStatsTransmitOctets OBJECT-TYPE
			SYNTAX Counter32
			MAX-ACCESS read-only
			STATUS current
			DESCRIPTION
				"
				A count of data and padding octets of frames that are successfully
				transmitted.
				"
			::= { hwVdslEtherStatsEntry 11 }
		
		hwVdslEtherStatsReceiveOctets OBJECT-TYPE
			SYNTAX Counter32
			MAX-ACCESS read-only
			STATUS current
			DESCRIPTION
				"
				A count of data and padding octets of frames that are successfully
				received.
				"
			::= { hwVdslEtherStatsEntry 12 }
		
		hwVdslEtherStatsReceiveBroadcastFrames OBJECT-TYPE
			SYNTAX Counter32
			MAX-ACCESS read-only
			STATUS current
			DESCRIPTION
				"
				A count of frames that are successfully received and are directed
				to the broadcast group address.
				"
			::= { hwVdslEtherStatsEntry 13 }
		
		hwVdslEtherStatsReceivePauseFrames OBJECT-TYPE
			SYNTAX Counter32
			MAX-ACCESS read-only
			STATUS current
			DESCRIPTION
				"
				The total number of PAUSE packets received.
				"
			::= { hwVdslEtherStatsEntry 14 }
		
		hwVdslEtherStatsTransmitPauseFrames OBJECT-TYPE
			SYNTAX Counter32
			MAX-ACCESS read-only
			STATUS current
			DESCRIPTION
				"
				The total number of PAUSE packets transmitted.
				"
			::= { hwVdslEtherStatsEntry 15 }
		
		hwVdslEtherStatsTransmitFrames OBJECT-TYPE
			SYNTAX Counter32
			MAX-ACCESS read-only
			STATUS current
			DESCRIPTION
				"
				The total number of valid data frames that have been transferred
				over the transmit channel.
				"
			::= { hwVdslEtherStatsEntry 16 }
		
		hwVdslEtherStatsReceiveFrames OBJECT-TYPE
			SYNTAX Counter32
			MAX-ACCESS read-only
			STATUS current
			DESCRIPTION
				"
				The total number of valid data frames that have been transferred
				over the receive channel.
				"
			::= { hwVdslEtherStatsEntry 17 }
			
			
    -- Notification definitions

    vdslNotifications OBJECT IDENTIFIER ::= { vdslLineMib 0 }

    vdslPerfLofsThreshNotification NOTIFICATION-TYPE
        OBJECTS      { 
                     vdslPerfCurr15MinLofs,
                     vdslThresh15MinLofs 
                     }
        STATUS       current
        DESCRIPTION
            "Loss of Framing 15-minute interval threshold reached."
        ::= { vdslNotifications 1 }

    vdslPerfLossThreshNotification NOTIFICATION-TYPE
        OBJECTS       { 
                      vdslPerfCurr15MinLoss,
                      vdslThresh15MinLoss 
                      }
        STATUS        current
        DESCRIPTION
            "Loss of Signal 15-minute interval threshold reached."
        ::= { vdslNotifications 2 }

    vdslPerfLprsThreshNotification NOTIFICATION-TYPE
        OBJECTS       {
                      vdslPerfCurr15MinLprs,
                      vdslThresh15MinLprs 
                      }
        STATUS        current
        DESCRIPTION
            "Loss of Power 15-minute interval threshold reached."
        ::= { vdslNotifications 3 }

    vdslPerfESsThreshNotification NOTIFICATION-TYPE
        OBJECTS       { 
                      vdslPerfCurr15MinESs,
                      vdslThresh15MinESs 
                      }
        STATUS        current
        DESCRIPTION
            "Errored Second 15-minute interval threshold reached."
        ::= { vdslNotifications 4 }

    vdslInitFailureNotification NOTIFICATION-TYPE
        OBJECTS       {
                      vdslCurrStatus 
                      }
        STATUS        current
        DESCRIPTION
            "Vtu initialization failed.  See vdslCurrStatus for 
            potential reasons."
        ::= { vdslNotifications 5 }

    -- conformance information

    vdslConformance OBJECT IDENTIFIER ::= { vdslLineMib 3 }
    vdslGroups OBJECT IDENTIFIER ::= { vdslConformance 1 }
    vdslCompliances OBJECT IDENTIFIER ::= { vdslConformance 2 }

    vdslLineMibCompliance MODULE-COMPLIANCE
        STATUS  current
        DESCRIPTION
            "The compliance statement for SNMP entities which 
            manage VDSL interfaces."

        MODULE  -- this module
        MANDATORY-GROUPS
            {
            vdslGroup
            }

        GROUP       vdslMCMGroup
        DESCRIPTION
            "This group is mandatory for VDSL Lines which
            utilize multiple carrier modulation. 

            This group should not be implemented for VDSL lines
            which utilize single carrier modulation."

        GROUP       vdslSCMGroup
        DESCRIPTION
            "This group is mandatory for VDSL lines which
            utilize single carrier modulation.

            This group should not be implemented for VDSL lines
            which utilize multiple carrier modulation"
        ::= { vdslCompliances 1 }

    -- units of conformance

        vdslGroup OBJECT-GROUP
            OBJECTS 
                {
                vdslLineCoding,
                vdslLineType,
                vdslLineConfProfile,
                vdslLineAlarmConfProfile,
                vdslPhysSide,
                vdslInvSerialNumber,
                vdslInvVendorID,
                vdslInvVersionNumber,
                vdslCurrSnrMgn,
                vdslCurrAtn,
                vdslCurrStatus,
                vdslCurrOutputPwr,
                vdslCurrAttainableRate,
                vdslChanInterleaveDelay,
                vdslChanCrcBlockLength,
                vdslPerfValidIntervals,
                vdslPerfInvalidIntervals,
                vdslPerfLofs,
                vdslPerfLoss,
                vdslPerfLprs,
                vdslPerfESs,
                vdslPerfInits,
                vdslPerfCurr15MinTimeElapsed,
                vdslPerfCurr15MinLofs,
                vdslPerfCurr15MinLoss,
                vdslPerfCurr15MinLprs,
                vdslPerfCurr15MinESs,
                vdslPerfCurr15MinInits,
                vdslIntervalLofs,
                vdslIntervalLoss,
                vdslIntervalLprs,
                vdslIntervalESs,
                vdslIntervalInits,
                vdslChanPerfValidIntervals,
                vdslChanPerfInvalidIntervals,
                vdslChanCorrectedOctets,
                vdslChanUncorrectBlks,
                vdslChanPerfCurr15MinTimeElapsed,
                vdslChanPerfCurr15MinCorrectedOctets,
                vdslChanPerfCurr15MinUncorrectBlks,
                vdslChanIntervalCorrectedOctets,
                vdslChanIntervalUncorrectBlks,
                vdslLineConfProfileName,
                vdslLineConfTargetSnrMgn,
                vdslLineConfTxSpeed,
                vdslLineConfRxSpeed,
                vdslLineConfProfileRowStatus,
                vdslLineAlarmConfProfileName,
                vdslThresh15MinLofs,
                vdslThresh15MinLoss,
                vdslThresh15MinLprs,
                vdslThresh15MinESs,
                vdslInitFailureNotificationEnable,
                vdslLineAlarmConfProfileRowStatus
                }
            STATUS     current
            DESCRIPTION
                "A collection of objects providing information about
                 a VDSL Line."
            ::= { vdslGroups 1 }

        vdslMCMGroup OBJECT-GROUP
             OBJECTS 
                {
                vdslMCMConfProfileTxWindowLength,
                vdslMCMConfProfileRowStatus,
                vdslMCMConfProfileTxBandNumber,
                vdslMCMConfProfileTxBandStart,
                vdslMCMConfProfileTxBandStop,
                vdslMCMConfProfileTxBandRowStatus,
                vdslMCMConfProfileRxBandNumber,
                vdslMCMConfProfileRxBandStart,
                vdslMCMConfProfileRxBandStop,
                vdslMCMConfProfileRxBandRowStatus,
                vdslMCMConfProfileTxPSDNumber,
                vdslMCMConfProfileTxPSDTone,
                vdslMCMConfProfileTxPSDPSD,
                vdslMCMConfProfileTxPSDRowStatus,
                vdslMCMConfProfileMaxTxPSDNumber,
                vdslMCMConfProfileMaxTxPSDTone,
                vdslMCMConfProfileMaxTxPSDPSD,
                vdslMCMConfProfileMaxTxPSDRowStatus,
                vdslMCMConfProfileMaxRxPSDNumber,
                vdslMCMConfProfileMaxRxPSDTone,
                vdslMCMConfProfileMaxRxPSDPSD,
                vdslMCMConfProfileMaxRxPSDRowStatus
                }
             STATUS     current
             DESCRIPTION
                 "A collection of objects providing configuration
                 information for a VDSL line based upon multiple carrier 
                 modulation modem."
         ::= { vdslGroups 2 }

        vdslSCMGroup    OBJECT-GROUP
            OBJECTS 
                {
                vdslSCMConfProfileInterleaveDepth,
                vdslSCMConfProfileFastCodewordSize,
                vdslSCMConfProfileTransmitPSDMask,
                vdslSCMConfProfileTransmitPSDLevel,
                vdslSCMConfProfileSymbolRateProfile,
                vdslSCMConfProfileConstellationSize,
                vdslSCMConfProfileCenterFrequency,
                vdslSCMConfProfileRowStatus
                }
            STATUS      current
            DESCRIPTION
                 "A collection of objects providing configuration
                 information for a VDSL line based upon single carrier 
                 modulation modem."
        ::= { vdslGroups 3 }

        vdslNotificationGroup    NOTIFICATION-GROUP
            NOTIFICATIONS
                {
                vdslPerfLofsThreshNotification,
                vdslPerfLossThreshNotification,
                vdslPerfLprsThreshNotification,
                vdslPerfESsThreshNotification,
                vdslInitFailureNotification
                }
            STATUS      current
            DESCRIPTION
                 "This group supports notifications of significant 
                 conditions associated with VDSL Lines."
        ::= { vdslGroups 4 }    
        			

    END

-- 
--    Copyright (C) The Internet Society (2001).  All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF 
--    MERCHANTABILITY OR FITNESS FOR A PARTICULAR PURPOSE.
