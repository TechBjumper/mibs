-- *****************************************************************
-- BYTESPHERE-EVENTLOG-MIB.my:  ByteSphere EVENTLOG message MIB file
--
-- October 2007, Nicholas W. Saparoff
--
-- Copyright (c) 2007 by BYTESPHERE TECHNOLOGIES LLC
-- All rights reserved.
-- 
-- *****************************************************************
--

-- This MIB provides a way to generate system level message from
-- BYTESPHERE MonitorEngine Servers.

-- All EVENTLOG messages have the following attributes:
--      timestamp (optional), originator name (where the message came
--      from), subject name (what the message is about), 
--	severity, message name, message text
--

BYTESPHERE-EVENTLOG-MIB DEFINITIONS ::= BEGIN

IMPORTS
        MODULE-IDENTITY,
        NOTIFICATION-TYPE,
        OBJECT-TYPE,
        Integer32,
        Counter32
                FROM SNMPv2-SMI
        TEXTUAL-CONVENTION,
        DisplayString,
        TimeStamp,
        TruthValue
                FROM SNMPv2-TC
        MODULE-COMPLIANCE,
        OBJECT-GROUP,
        NOTIFICATION-GROUP
                FROM SNMPv2-CONF
        bytesphereMgmt
        	FROM BYTESPHERE-SMI
		SyslogSeverity FROM SYSLOG-TC-MIB;


bytesphereEventLogMib MODULE-IDENTITY
        LAST-UPDATED        "200710050000Z"
        ORGANIZATION        "ByteSphere Technologies LLC"
        CONTACT-INFO
                "       ByteSphere Technologies LLC
                Postal: 955 Mass Ave #141
                        Cambridge, MA  02139
                        USA

                E-mail: bscustsupt@bytesphere.com"
                
        DESCRIPTION
                "The MIB module to describe the system
                 messages generated by BYTESPHERE applications."
        REVISION        "200710050000Z"
        DESCRIPTION
                "Initial version of this MIB module."
        ::= { bytesphereMgmt 1 }

bytesphereEventLogMibObjects OBJECT IDENTIFIER ::= { bytesphereEventLogMib 1 }

-- Subgroups

eventLogInfo          OBJECT IDENTIFIER ::= { bytesphereEventLogMibObjects 1 }
eventLogMessages      OBJECT IDENTIFIER ::= { bytesphereEventLogMibObjects 2 }

-- Textual Conventions

EventSeverity ::= TEXTUAL-CONVENTION
       STATUS  current
       DESCRIPTION
               "The severity of a ByteSphere message.

		 'none':     : may also be interpreted as a clear
                 'info'	     : informational messages 
                 'warning'   : warning conditions
                 'minor'     : minor event occurred
                 'major'     : error conditions
                 'critical'  : critical conditions"

       SYNTAX  INTEGER {    
       			    none(0),
       			    info(1),
                            warning(2),
                            minor(3),
                            major(4),
                            critical(5)
                       	}


eventLogMibNotificationsSent OBJECT-TYPE
        SYNTAX     Counter32
        UNITS      "notifications"
        MAX-ACCESS read-only
        STATUS     current
        DESCRIPTION
                "The number of event notifications that
                 have been sent. This number may include notifications
                 that were prevented from being transmitted due to
                 reasons such as resource limitations and/or
                 non-connectivity.  If one is receiving notifications,
                 one can periodically poll this object to determine if
                 any notifications were missed.  If so, a poll of the
                 eventLogTable might be appropriate."
        ::= { eventLogInfo 1 }

eventLogMibNotificationsEnabled OBJECT-TYPE
        SYNTAX     TruthValue
        MAX-ACCESS read-write
        STATUS     current
        DESCRIPTION
                "Indicates whether event log notifications
                 will or will not be sent when an event message is
                 generated by the device.  Disabling notifications
                 does not prevent event messages from being added
                 to the eventLogTable."
        DEFVAL { false }
        ::= { eventLogInfo 2 }

eventLogMibMinSeverity OBJECT-TYPE
        SYNTAX     SyslogSeverity
        MAX-ACCESS read-write
        STATUS     current
        DESCRIPTION
                "Indicates which event severity levels will be
                 processed.  Any event message with a severity value
                 lesser than this value will be ignored by the agent."
        DEFVAL { warning }
        ::= { eventLogInfo 3 }

        
-- eventLogMessages

eventLogTableMaxLength OBJECT-TYPE
        SYNTAX     Integer32 (0..10000)
        UNITS      "entries"
        MAX-ACCESS read-write
        STATUS     current
        DESCRIPTION
                "The upper limit on the number of entries that the
                 eventLogTable may contain.  A value of 0 will
                 prevent any events from being retained. When this
                 table is full, the oldest entry will be deleted and
                 a new one will be created."
        DEFVAL  { 100 }
        ::= { eventLogMessages 1 }

eventLogTableEventsFlushed OBJECT-TYPE
        SYNTAX     Counter32
        UNITS      "messages"
        MAX-ACCESS read-only
        STATUS     current
        DESCRIPTION
                "The number of entries that have been removed from
                 the eventLogTable in order to make room for new
                 entries. This object can be utilized to determine
                 whether your polling frequency on the event table
                 is fast enough and/or the size of your event table
                 is large enough such that you are not missing
                 messages."
        ::= { eventLogMessages 2 }
        
eventLogTable OBJECT-TYPE
        SYNTAX     SEQUENCE OF EventLogEntry
        MAX-ACCESS not-accessible
        STATUS     current
        DESCRIPTION
                "A table of EVENTLOG messages generated by this device.
                 All 'interesting' EVENTLOG messages (i.e. severity >=
                 eventLogMibMinSeverity ) are entered into this table."
        ::= { eventLogMessages 3 }

eventLogEntry OBJECT-TYPE
        SYNTAX     EventLogEntry
        MAX-ACCESS not-accessible
        STATUS     current
        DESCRIPTION
                "A EVENTLOG message that was previously generated by this
                 device. Each entry is indexed by a message index."
        INDEX   { eventLogIndex }
        ::= { eventLogTable 1 }

EventLogEntry ::=
    SEQUENCE {
        eventLogIndex       Integer32,
        eventLogOrigin      DisplayString,
        eventLogOriginID    Integer32,
        eventLogObject      DisplayString,
        eventLogObjectID    DisplayString,
        eventLogObjectType  DisplayString,
        eventLogObjectClass DisplayString,
        eventLogSeverity    EventSeverity,
        eventLogEventName   DisplayString,
        eventLogEventText   DisplayString,
        eventLogTimestamp   TimeStamp
    }

eventLogIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { eventLogEntry 1 }

eventLogOrigin OBJECT-TYPE
        SYNTAX     DisplayString (SIZE (1..20))
        MAX-ACCESS read-only
        STATUS     current
        DESCRIPTION
                "Name of the engine that generated this message.
                 For example: 'hostname (ipaddress)'."
        ::= { eventLogEntry 2 }

eventLogOriginID OBJECT-TYPE
        SYNTAX     Integer32 (1..2147483647)
        MAX-ACCESS read-only
        STATUS     current
        DESCRIPTION
                "Internal ID of the facility that generated this message.
                 For example: '1'."
        ::= { eventLogEntry 3 }
        
eventLogObject OBJECT-TYPE
        SYNTAX     DisplayString (SIZE (1..255))
        MAX-ACCESS read-only
        STATUS     current
        DESCRIPTION
                "Name of the subject this message is about.
                 For example: 'sysname-port-ethernet-1'."
        ::= { eventLogEntry 4 }

eventLogObjectID OBJECT-TYPE
        SYNTAX     DisplayString (SIZE (1..255))
        MAX-ACCESS read-only
        STATUS     current
        DESCRIPTION
                "Internal name of the object this message is about.
                 For example: '1022'."
        ::= { eventLogEntry 5 }

eventLogObjectType OBJECT-TYPE
        SYNTAX     DisplayString (SIZE (1..255))
        MAX-ACCESS read-only
        STATUS     current
        DESCRIPTION
                "Type of object this message is about.
                 For example: 'snmp-mib2-if'."
        ::= { eventLogEntry 6 }

eventLogObjectClass OBJECT-TYPE
        SYNTAX     DisplayString (SIZE (1..255))
        MAX-ACCESS read-only
        STATUS     current
        DESCRIPTION
                "Class of the object this message is about.
                 For example: 'MonitorType'."
        ::= { eventLogEntry 7 }

eventLogSeverity OBJECT-TYPE
        SYNTAX     EventSeverity
        MAX-ACCESS read-only
        STATUS     current
        DESCRIPTION
                "The severity of the message."
        ::= { eventLogEntry 8 }

eventLogEventName OBJECT-TYPE
        SYNTAX     DisplayString (SIZE (1..30))
        MAX-ACCESS read-only
        STATUS     current
        DESCRIPTION
                "A textual identification for the message type.
                 A facility name in conjunction with a message name
                 uniquely identifies a message type."
        ::= { eventLogEntry 9 }

eventLogEventText OBJECT-TYPE
        SYNTAX     DisplayString (SIZE (1..2056))
        MAX-ACCESS read-only
        STATUS     current
        DESCRIPTION
                "The text of the message."
        ::= { eventLogEntry 10 }

eventLogTimestamp OBJECT-TYPE
        SYNTAX     TimeStamp
        MAX-ACCESS read-only
        STATUS     current
        DESCRIPTION
                "The value of sysUpTime when this message was
                 generated."
        ::= { eventLogEntry 11 }

-- notifications

bytesphereEventLogMibNotificationPrefix    OBJECT IDENTIFIER ::= { bytesphereEventLogMib 2 }
bytesphereEventLogMibNotifications         OBJECT IDENTIFIER ::= { bytesphereEventLogMibNotificationPrefix 0 }

eventGenerated NOTIFICATION-TYPE
        OBJECTS { eventLogOrigin,
        	  eventLogOriginID,
        	  eventLogObject,
        	  eventLogObjectID,
		  eventLogObjectType,
		  eventLogObjectClass,
                  eventLogSeverity,
                  eventLogEventName,
                  eventLogEventText,
                  eventLogTimestamp
        }
        STATUS     current
        DESCRIPTION
                "When a EVENTLOG message is generated by the device a
                 eventGenerated notification is sent.  The
                 sending of these notifications can be enabled/disabled
                 via the eventLogMibNotificationsEnabled object."
        ::= { bytesphereEventLogMibNotifications 1 }



END
