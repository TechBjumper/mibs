ACC-IPFILTER DEFINITIONS ::= BEGIN

    IMPORTS
	 OBJECT-TYPE, IpAddress, Counter, TimeTicks FROM RFC1155-SMI
         accTrapLogSeqNum FROM ACC-SYSTEM
	accBRG, DisplayString, RowStatus, IfIndex, SmdsAddress
             FROM ACC-MIB;

-- IP Filter Group
      accIpFilter   OBJECT IDENTIFIER  ::= { accBRG 18 }
        accIpSrcRouting  OBJECT-TYPE   
                        SYNTAX  INTEGER {
                           on(1),  --
                           off(2)  -- Discard source-routed IP packets
                        }
                        ACCESS read-write
                        STATUS  mandatory
                        DESCRIPTION
                         " Source Routing mode"
                        ::= { accIpFilter 1 }
-- This filter table is being deprecated in favor of the one that follows.
-- The new table represents extended IP filtering capability added in 
-- version 7.3.8 of the router application.
        accIpFiltTable  OBJECT-TYPE
                        SYNTAX SEQUENCE OF AccIpFiltEntry
                        ACCESS not-accessible
                        STATUS deprecated
                        DESCRIPTION
                         " List of IP filters
                           Entries added/deleted by management action.
                           Setting any object to NULL deletes the entry"
                        ::= { accIpFilter 2 }
          accIpFiltEntry  OBJECT-TYPE
                        SYNTAX AccIpFiltEntry
                        ACCESS not-accessible
                        STATUS deprecated
                        DESCRIPTION
                         " Specific IP filter"
                        INDEX { accIpFiltDAddr,
                                accIpFiltDNetMask,
                                accIpFiltSAddr,
                                accIpFiltSNetMask,
                                accIpFiltParm,
                                accIpFiltDisp }
                        ::= { accIpFiltTable 1 }
                AccIpFiltEntry ::= SEQUENCE {
                        accIpFiltDAddr          IpAddress,
                        accIpFiltDNetMask       IpAddress,
                        accIpFiltSAddr          IpAddress,
                        accIpFiltSNetMask       IpAddress,
                        accIpFiltParm           OCTET STRING,
                        accIpFiltDisp           INTEGER
                        }
            accIpFiltDAddr  OBJECT-TYPE  
                        SYNTAX  IpAddress
                        ACCESS  read-write
                        STATUS  deprecated
                        DESCRIPTION
                         " Destination Address "
                        ::= { accIpFiltEntry 1 }
            accIpFiltDNetMask  OBJECT-TYPE  
                        SYNTAX  IpAddress
                        ACCESS  read-write
                        STATUS  deprecated
                        DESCRIPTION
                         " Destination Network Mask"
                        ::= { accIpFiltEntry 2 }
            accIpFiltSAddr  OBJECT-TYPE  
                        SYNTAX  IpAddress
                        ACCESS  read-write
                        STATUS  deprecated
                        DESCRIPTION
                         " Source Address "
                        ::= { accIpFiltEntry 3 }
            accIpFiltSNetMask  OBJECT-TYPE  
                        SYNTAX  IpAddress
                        ACCESS  read-write
                        STATUS  deprecated
                        DESCRIPTION
                         " Source Network Mask "
                        ::= { accIpFiltEntry 4 }
            accIpFiltParm  OBJECT-TYPE  
                        SYNTAX  OCTET STRING
                        ACCESS  read-write
                        STATUS  deprecated
                        DESCRIPTION
                         " Filter parameters;
                             Byte 0 is Operation 1
                                [0,1,2] = [None, !,=]
                            Bytes 1,2 is Protocol
                            Byte 3 is Operation 2
                                [0           = none
                                [1,2,3,4]    = both [!, <, >, =]
                                [5,6,7,8]    = destination [!, <, >, =]
                                [9,10,11,12] = source [!, <, >, =]
                             Bytes 4,5 is UDP/TCP port number"
                        ::= { accIpFiltEntry 5 }
            accIpFiltDisp  OBJECT-TYPE  
                        SYNTAX  INTEGER {
                                 normalPriority(0),
                                 discard(1),
                                 lowPriority(2),
                                 highPriority(3)
                                }
                        ACCESS  read-write
                        STATUS  deprecated
                        DESCRIPTION
                         " Disposition of  packets meeting the
                           filter criteria.  Packets not discarded
                           will be output with the selected relative
                           transmission priority.
                        "
                        ::= { accIpFiltEntry 6 }
-- MIB For The Existing IP SMDS Address Table
            accIpSmdsAtTable OBJECT-TYPE
                        SYNTAX SEQUENCE OF AccIpSmdsAtEntry
                        ACCESS not-accessible
                        STATUS mandatory
                        DESCRIPTION
                            "The IP/SMDS address translation table.
                            Contains the IP address, Local SNI, IP
                            multicast address (E.164 format), and
                            ARP multicast address (E.164 format)."
                        ::= { accIpFilter 3 }
            accIpSmdsAtEntry OBJECT-TYPE
                        SYNTAX AccIpSmdsAtEntry
                        ACCESS not-accessible
                        STATUS mandatory
                        DESCRIPTION
                            "An IP/SMDS address translation table entry.
                            Each entry contains an IP address and 
                            necessary SMDS translation parameters."
                        INDEX { accIpSmdsAtIpAddr }
                        ::= { accIpSmdsAtTable 1 }
            AccIpSmdsAtEntry ::= SEQUENCE {
                        accIpSmdsAtIpAddr       IpAddress,
                        accIpSmdsAtSmdsAddr     SmdsAddress, 
                        accIpSmdsAtIpMcast      SmdsAddress,
                        accIpSmdsAtArpMcast     SmdsAddress
                        }
            accIpSmdsAtIpAddr OBJECT-TYPE
                        SYNTAX IpAddress
                        ACCESS read-only
                        STATUS mandatory
                        DESCRIPTION
                            "The IP address associated with the Local SNI,
                            IP Multicast and ARP Multicast SMDS addresses."
                        ::= { accIpSmdsAtEntry 1 }
            accIpSmdsAtSmdsAddr OBJECT-TYPE
                        SYNTAX SmdsAddress
                        ACCESS read-write
                        STATUS mandatory
                        DESCRIPTION
                            "The local SNI SMDS address in E.164 address
                            format (e.g., 0xC18005551212FFFF)"
                        ::= { accIpSmdsAtEntry 2 }
            accIpSmdsAtIpMcast OBJECT-TYPE
                        SYNTAX SmdsAddress
                        ACCESS read-write
                        STATUS mandatory
                        DESCRIPTION
                            "The IP Multicast SMDS Group address in
                            E.164 address format (e.g.,0xE18005551111FFFF)"
                        ::= { accIpSmdsAtEntry 3 }
            accIpSmdsAtArpMcast OBJECT-TYPE
                        SYNTAX SmdsAddress
                        ACCESS read-only
                        STATUS mandatory
                        DESCRIPTION
                            "The ARP Multicast SMDS Group address in
                            E.164 address format (e.g.,0xE18005551111FFFF)"
                        ::= { accIpSmdsAtEntry 4 }
           accIpSubDirBcast     OBJECT-TYPE   
                         SYNTAX  INTEGER {
                                 bcast(1),
                                 nobcast(2)
                                 }
                       ACCESS  read-write
                       STATUS  mandatory
                       DESCRIPTION
                  "Packets with an all-ones host portion of the
                   destination IP address are called Subnet Directed
                   Broadcast (or Limited Broadcast) packets.  This
                   object selects if these packets are to be broadcast
                   onto the destination subnet."
                       ::= { accIpFilter  4 }
-- This table is only used for the display of current filters. 
-- The table that follows this one is used for editing the filter database.
-- These changes added with version 7.3.8 of the router application.
        accIpIfFiltDispTable    OBJECT-TYPE
                        SYNTAX SEQUENCE OF AccIpIfFiltDispEntry
                        ACCESS not-accessible
                        STATUS mandatory
                        DESCRIPTION
                         " List of revised IP filters which add support for
                           filtering by source or destination interface."
                        ::= { accIpFilter 5 }
          accIpIfFiltDispEntry  OBJECT-TYPE
                        SYNTAX AccIpIfFiltDispEntry
                        ACCESS not-accessible
                        STATUS mandatory
                        DESCRIPTION
                         " An entry in the revised IP filter table."
                        INDEX { accIpIfFiltDispIfIndex,
                                accIpIfFiltDispPktDir,
                                accIpIfFiltDispSeqNum
                                }
                        ::= { accIpIfFiltDispTable 1 }
                AccIpIfFiltDispEntry ::= SEQUENCE {
                        accIpIfFiltDispIfIndex          INTEGER,
                        accIpIfFiltDispPktDir           INTEGER,
                        accIpIfFiltDispSeqNum           INTEGER,
                        accIpIfFiltDispDAddr            IpAddress,
                        accIpIfFiltDispDNetMask         IpAddress,
                        accIpIfFiltDispSAddr            IpAddress,
                        accIpIfFiltDispSNetMask         IpAddress,
                        accIpIfFiltDispOp1              INTEGER,
                        accIpIfFiltDispProtocol         INTEGER,
                        accIpIfFiltDispOp2              INTEGER,
                        accIpIfFiltDispUDPTCPPort       INTEGER,
                        accIpIfFiltDispDispos           INTEGER,
                        accIpIfFiltDispMatches          Counter,
                        accIpIfFiltDispLastMatchTime    TimeTicks,
                        accIpIfFiltDispMatchPkt OCTET STRING
                        }
            accIpIfFiltDispIfIndex  OBJECT-TYPE  
                        SYNTAX  INTEGER
                        ACCESS  read-only
                        STATUS  mandatory
                        DESCRIPTION
                         " Interface index to which this filter applies, or
                           zero for global filters.
                           This integer identifies the row of the system wide 
                           interfaces table associated with the particular 
                           interface."
                        ::= { accIpIfFiltDispEntry 1 }
            accIpIfFiltDispPktDir  OBJECT-TYPE   
                        SYNTAX  INTEGER {
                                input(1),
                                output(2),
                                global(3)
                                }
                        ACCESS  read-only
                        STATUS  mandatory
                        DESCRIPTION
                         "Stream direction to which filter is applied.
                          Input and Output require an interface to
                          be specified. Global indicates all interfaces
                          and both directions. Input and Global filters are 
                          applied prior to Output filters.
                          NOTE: a packet originating in the router may not
                          pass through the filter logic."
                        ::= { accIpIfFiltDispEntry 2 }
            accIpIfFiltDispSeqNum  OBJECT-TYPE   
                        SYNTAX  INTEGER
                        ACCESS  read-only
                        STATUS  mandatory
                        DESCRIPTION
                          " An internally generated sequence number used to
                            allow the Filter display table to be retruned in
                            the order the filters are applied (most specific
                            to least specific) without violating SNMP ordering
                            rules. Sequence numbers for all filters may change
                            with a single addition or modification of a filter.
                            Sequence numbers, once assigned, are not assigned
                            again. This number has no intrinsic meaning." 
                        ::= { accIpIfFiltDispEntry 3 }
            accIpIfFiltDispDAddr  OBJECT-TYPE    
                        SYNTAX  IpAddress
                        ACCESS  read-only
                        STATUS  mandatory
                        DESCRIPTION
                         " Destination Address "
                        ::= { accIpIfFiltDispEntry 4 }
            accIpIfFiltDispDNetMask  OBJECT-TYPE  
                        SYNTAX  IpAddress
                        ACCESS  read-only
                        STATUS  mandatory
                        DESCRIPTION
                         " Destination Network Mask"
                        ::= { accIpIfFiltDispEntry 5 }
            accIpIfFiltDispSAddr  OBJECT-TYPE    
                        SYNTAX  IpAddress
                        ACCESS  read-only
                        STATUS  mandatory
                        DESCRIPTION
                         " Source Address "
                        ::= { accIpIfFiltDispEntry 6 }
            accIpIfFiltDispSNetMask  OBJECT-TYPE  
                        SYNTAX  IpAddress
                        ACCESS  read-only
                        STATUS  mandatory
                        DESCRIPTION
                         " Source Network Mask "
                        ::= { accIpIfFiltDispEntry 7 }
            accIpIfFiltDispOp1  OBJECT-TYPE     
                        SYNTAX  INTEGER {
                                none(1),
                                not-equal(2),
                                equal(3)
                                }
                        ACCESS  read-only
                        STATUS  mandatory
                        DESCRIPTION
                         " Logical operation to be performed on the next
                           object/parameter (protocol). If 'none', the 
                           filter will match any protocol."
                        ::= { accIpIfFiltDispEntry 8 }
            accIpIfFiltDispProtocol  OBJECT-TYPE        
                        SYNTAX  INTEGER (0..255)
                        ACCESS  read-only
                        STATUS  mandatory
                        DESCRIPTION
                         " Ip protocol on which to filter."
                        REFERENCE
                         " Assigned numbers document."
                        ::= { accIpIfFiltDispEntry 9 }
            accIpIfFiltDispOp2  OBJECT-TYPE     
                        SYNTAX  INTEGER {
                                none(1),
                                not-equal(2),
                                less-than(3),
                                greater-than(4),
                                equal(5),
                                src-not-equal(6),
                                src-less-than(7),
                                src-greater-than(8),
                                src-equal(9),
                                dst-not-equal(10),
                                dst-less-than(11),
                                dst-greater-than(12),
                                dst-equal(13)
                                }
                        ACCESS  read-only
                        STATUS  mandatory
                        DESCRIPTION
                         " Logical operation to be performed on the next
                           object/parameter (port)."
                        ::= { accIpIfFiltDispEntry 10 }
            accIpIfFiltDispUDPTCPPort  OBJECT-TYPE      
                        SYNTAX  INTEGER (1..65535)
                        ACCESS  read-only
                        STATUS  mandatory
                        DESCRIPTION
                         " The UDP or TCP port number to which the previous
                           logical operation is to apply."
                        ::= { accIpIfFiltDispEntry 11 }
	    accIpIfFiltDispDispos  OBJECT-TYPE	
			SYNTAX	INTEGER {
				 discard(1),
				 log(2),
				 lowPriority(3),
				 normalPriority(4),
				 highPriority(5)
				}
			ACCESS	read-only
			STATUS	mandatory
			DESCRIPTION
			 " Disposition of packets meeting the
                           filter criteria. Packets not discarded
                           will be output with the selected relative
                           transmission priority. The log option causes a
                           rate selected trap to be generated."
                        ::= { accIpIfFiltDispEntry 12 }
            accIpIfFiltDispMatches  OBJECT-TYPE
                        SYNTAX  Counter
                        ACCESS  read-only
                        STATUS  mandatory
                        DESCRIPTION
                         "The number of times this filter criteria has been
                          applied."
                        ::= { accIpIfFiltDispEntry 13 }
            accIpIfFiltDispLastMatchTime  OBJECT-TYPE
                        SYNTAX  TimeTicks
                        ACCESS  read-only
                        STATUS  mandatory
                        DESCRIPTION
                         " The value of sysUpTime the last time this filter
                           was applied."
                        ::= { accIpIfFiltDispEntry 14 }
            accIpIfFiltDispMatchPkt  OBJECT-TYPE
                        SYNTAX  OCTET STRING -- (SIZE (64))
                        ACCESS  read-only
                        STATUS  mandatory
                        DESCRIPTION
                         " This object is used exclusivley for returning
                           information in a trap about the last packet that was 
                           filtered. A query of this object will return an
                           octet string of length zero."
                        ::= { accIpIfFiltDispEntry 15 }
-- This table is only used for editing the filter database.
        accIpIfFiltEditTable    OBJECT-TYPE
                        SYNTAX SEQUENCE OF AccIpIfFiltEditEntry
                        ACCESS not-accessible
                        STATUS mandatory
                        DESCRIPTION
                         " A transient table which is used to create/delete
                           /modify an entry in the IP filter database."
                        ::= { accIpFilter 6 }
          accIpIfFiltEditEntry  OBJECT-TYPE
                        SYNTAX AccIpIfFiltEditEntry
                        ACCESS not-accessible
                        STATUS mandatory
                        DESCRIPTION
                         " An entry in the revised IP filter table."
                        INDEX { accIpIfFiltEditIndex }
                        ::= { accIpIfFiltEditTable 1 }
                AccIpIfFiltEditEntry ::= SEQUENCE {
                        accIpIfFiltEditIndex            INTEGER,
                        accIpIfFiltEditAction           INTEGER,
                        accIpIfFiltEditIfIndex          INTEGER,
                        accIpIfFiltEditPktDir           INTEGER,
                        accIpIfFiltEditDAddr            IpAddress,
                        accIpIfFiltEditDNetMask         IpAddress,
                        accIpIfFiltEditSAddr            IpAddress,
                        accIpIfFiltEditSNetMask         IpAddress,
                        accIpIfFiltEditOp1              INTEGER,
                        accIpIfFiltEditProtocol         INTEGER,
                        accIpIfFiltEditOp2              INTEGER,
                        accIpIfFiltEditUDPTCPPort       INTEGER,
                        accIpIfFiltEditDispos           INTEGER
                        }
            accIpIfFiltEditIndex  OBJECT-TYPE    
                        SYNTAX  INTEGER
                        ACCESS  read-only
                        STATUS  mandatory
                        DESCRIPTION
                         "An arbitrary number assigned to the record that
                          is currently being edited."
                        ::= { accIpIfFiltEditEntry 1 }
            accIpIfFiltEditAction  OBJECT-TYPE   
                        SYNTAX  INTEGER {
                                add(1),
                                delete(2)
                                }
                        ACCESS  read-write
                        STATUS  mandatory
                        DESCRIPTION
                         " The action to be performed with this record. In the
                          future the field 'pending' may be added."
                        ::= { accIpIfFiltEditEntry 2 }
            accIpIfFiltEditIfIndex  OBJECT-TYPE  
                        SYNTAX  INTEGER
                        ACCESS  read-write
                        STATUS  mandatory
                        DESCRIPTION
                         " Interface index to which this filter applies, or
                           zero for global filters.
                           This integer identifies the row of the system wide 
                           interfaces table associated with the particular 
                           interface."
                        ::= { accIpIfFiltEditEntry 3 }
            accIpIfFiltEditPktDir  OBJECT-TYPE   
                        SYNTAX  INTEGER {
                                input(1),
                                output(2),
                                global(3)
                                }
                        ACCESS  read-write
                        STATUS  mandatory
                        DESCRIPTION
                         "Stream direction to which filter is applied.
                          Input and Output require an interface to
                          be specified. Global indicates all interfaces
                          and both directions. Input and Global filters are
                          applied prior to Output filters.
                          NOTE: a packet originating in the router may not
                          pass through the filter logic."
                        ::= { accIpIfFiltEditEntry 4 }
            accIpIfFiltEditDAddr  OBJECT-TYPE    
                        SYNTAX  IpAddress
                        ACCESS  read-write
                        STATUS  mandatory
                        DESCRIPTION
                         " Destination Address "
                        ::= { accIpIfFiltEditEntry 5 }
            accIpIfFiltEditDNetMask  OBJECT-TYPE  
                        SYNTAX  IpAddress
                        ACCESS  read-write
                        STATUS  mandatory
                        DESCRIPTION
                         " Destination Network Mask"
                        ::= { accIpIfFiltEditEntry 6 }
            accIpIfFiltEditSAddr  OBJECT-TYPE    
                        SYNTAX  IpAddress
                        ACCESS  read-write
                        STATUS  mandatory
                        DESCRIPTION
                         " Source Address "
                        ::= { accIpIfFiltEditEntry 7 }
            accIpIfFiltEditSNetMask  OBJECT-TYPE  
                        SYNTAX  IpAddress
                        ACCESS  read-write
                        STATUS  mandatory
                        DESCRIPTION
                         " Source Network Mask "
                        ::= { accIpIfFiltEditEntry 8 }
            accIpIfFiltEditOp1  OBJECT-TYPE     
                        SYNTAX  INTEGER {
                                none(1),
                                equal(2),
                                not-equal(3)
                                }
                        ACCESS  read-write
                        STATUS  mandatory
                        DESCRIPTION
                         " Logical operation to be performed on the next
                           object/parameter (protocol). If 'none', the 
                           filter will match any protocol."
                        ::= { accIpIfFiltEditEntry 9 }
            accIpIfFiltEditProtocol  OBJECT-TYPE        
                        SYNTAX  INTEGER (0..255)
                        ACCESS  read-write
                        STATUS  mandatory
                        DESCRIPTION
                         " Ip protocol on which to filter."
                        REFERENCE
                         " Assigned numbers document."
                        ::= { accIpIfFiltEditEntry 10 }
            accIpIfFiltEditOp2  OBJECT-TYPE     
                        SYNTAX  INTEGER {
                                none(1),
                                equal(2),
                                not-equal(3),
                                less-than(4),
                                greater-than(5),
                                dst-equal(6),
                                dst-not-equal(7),
                                dst-less-than(8),
                                dst-greater-than(9),
                                src-equal(10),
                                src-not-equal(11),
                                src-less-than(12),
                                src-greater-than(13)
                                }
                        ACCESS  read-write
                        STATUS  mandatory
                        DESCRIPTION
                         " Logical operation to be performed on the next
                           object/parameter (port)."
                        ::= { accIpIfFiltEditEntry 11 }
            accIpIfFiltEditUDPTCPPort  OBJECT-TYPE      
                        SYNTAX  INTEGER (1..65535)
                        ACCESS  read-write
                        STATUS  mandatory
                        DESCRIPTION
                         " The UDP or TCP port number to which the previous
                           logical operation is to apply."
                        ::= { accIpIfFiltEditEntry 12 }
            accIpIfFiltEditDispos  OBJECT-TYPE  
                        SYNTAX  INTEGER {
                                 discard(1),
                                 log(2),
                                 normalPriority(3),
                                 lowPriority(4),
                                 highPriority(5)
                                }
                        ACCESS  read-write
                        STATUS  mandatory
                        DESCRIPTION
                         " Disposition of packets meeting the
                           filter criteria. Packets not discarded
                           will be output with the selected relative
                           transmission priority. The log option causes a
                           rate sensitive trap to be generated."
                        ::= { accIpIfFiltEditEntry 13 }
      -- The MIB branches (accIpIfFiltDispTable and accIpIfFiltEditTable) containing
      -- the existing port-specific IP filters will be deprecated.  A new branch
      -- containing the objects for defining and managing port-independent named IP
      -- filters is added:
      accIpNamedFiltTable       OBJECT-TYPE
        SYNTAX          SEQUENCE OF AccIpNamedFiltEntry
        ACCESS          not-accessible
        STATUS          mandatory
        DESCRIPTION
        "Table of port-independent named IP filters"
      ::= { accIpFilter 7 }
      accIpNamedFiltEntry       OBJECT-TYPE
        SYNTAX          AccIpNamedFiltEntry
        ACCESS          not-accessible
        STATUS          mandatory
        DESCRIPTION
        "Entry for a single named port-independent named IP filter"
--        INDEX { INTEGER }
      ::= { accIpNamedFiltTable 1 }
      AccIpNamedFiltEntry ::= SEQUENCE {
                accIpNamedFiltName              OCTET STRING,
                accIpNamedFiltAction            INTEGER,
                accIpNamedFiltPktDir            INTEGER,
                accIpNamedFiltDAddr             IpAddress,
                accIpNamedFiltDNetMask          IpAddress,
                accIpNamedFiltSAddr             IpAddress,
                accIpNamedFiltSNetMask          IpAddress,
                accIpNamedFiltOp1               INTEGER,
                accIpNamedFiltProtocol          INTEGER,
                accIpNamedFiltOp2               INTEGER,
                accIpNamedFiltUDPTCPPort        INTEGER,
                accIpNamedFiltDisp              INTEGER,
                accIpNamedFiltMatches           Counter,
                accIpNamedFiltLastMatch         TimeTicks,
                accIpNamedFiltApplId            INTEGER,
                accIpNamedFiltSAIndex           OCTET STRING
                }
      accIpNamedFiltName        OBJECT-TYPE
        SYNTAX          OCTET STRING
        ACCESS          read-write
        STATUS          mandatory
        DESCRIPTION
        "The name of the filter entry."
      ::= { accIpNamedFiltEntry 1 }
      accIpNamedFiltAction      OBJECT-TYPE
        SYNTAX          INTEGER {
                        add(1),
                        delete (2)
                        }
        ACCESS          read-write
        STATUS          mandatory
        DESCRIPTION
        "Action to perform on filter entry: ADD or DELETE"
      ::= { accIpNamedFiltEntry 2 }
      accIpNamedFiltPktDir      OBJECT-TYPE
        SYNTAX          INTEGER {
                        input (1),
                        output (2)
                        }
        ACCESS          read-write
        STATUS          mandatory
        DESCRIPTION
        "Direction filter is to be applied in.  Filters which 
        are applied globally ignore this parameter"
      ::=  { accIpNamedFiltEntry 3 }
      accIpNamedFiltDAddr       OBJECT-TYPE
        SYNTAX          IpAddress
        ACCESS          read-write
        STATUS          mandatory
        DESCRIPTION
        "Destination address to apply in filter"
      ::= { accIpNamedFiltEntry 4 }
      accIpNamedFiltDNetMask    OBJECT-TYPE
        SYNTAX          IpAddress
        ACCESS          read-write
        STATUS          mandatory
        DESCRIPTION
        "Desintation network mask to apply in filter"
      ::= { accIpNamedFiltEntry 5 }
      accIpNamedFiltSAddr       OBJECT-TYPE
        SYNTAX          IpAddress
        ACCESS          read-write
        STATUS          mandatory
        DESCRIPTION
        "Source address to apply in filter"
      ::= { accIpNamedFiltEntry 6 }
      accIpNamedFiltSNetMask    OBJECT-TYPE
        SYNTAX          IpAddress
        ACCESS          read-write
        STATUS          mandatory
        DESCRIPTION
        "Source network mask to apply in filter"
      ::= { accIpNamedFiltEntry 7 }
      accIpNamedFiltOp1		OBJECT-TYPE
      	SYNTAX		INTEGER {
      			none (1),
      			not-equal (2),
      			equal (3)
      			}
      	ACCESS		read-write
      	STATUS		mandatory
      	DESCRIPTION
      	"First operator to apply in filter"
      ::= { accIpNamedFiltEntry 8 }
      accIpNamedFiltProtocol    OBJECT-TYPE
        SYNTAX          INTEGER (0..255)
        ACCESS          read-write
        STATUS          mandatory
        DESCRIPTION
        "Protocol to apply in filter"
      ::= { accIpNamedFiltEntry 9 }
      accIpNamedFiltOp2		OBJECT-TYPE
      	SYNTAX		INTEGER {
      			none (1),
      			not-equal (2),
      			less-than (3),
      			greater-than (4),
      			equal (5),
      			src-not-equal (6),
      			src-less-than (7),
      			src-greater-than (8),
      			src-equal (9),
      			dst-not-equal (10),
      			dst-less-than (11),
      			dst-greater-than (12),
			dst-equal(13)
      			}
      	ACCESS		read-write
      	STATUS		mandatory
      	DESCRIPTION
      	"The secondary operator to apply"
      ::= { accIpNamedFiltEntry 10 }
      accIpNamedFiltUDPTCPPort  OBJECT-TYPE
        SYNTAX          INTEGER (1..65535)
        ACCESS          read-write
        STATUS          mandatory
        DESCRIPTION
        "UDP/TCP port number to apply in filter"
      ::= { accIpNamedFiltEntry 11 }
      accIpNamedFiltDisp                OBJECT-TYPE
        SYNTAX          INTEGER {
                        discard (1),
                        log (2),
                        normalPriority (3),
                        lowPriority (4),
                        highPriority (5)
                        }
        ACCESS          read-write
        STATUS          mandatory
              DESCRIPTION ""
      ::= { accIpNamedFiltEntry 12 }
      accIpNamedFiltMatches     OBJECT-TYPE
        SYNTAX          Counter
        ACCESS          read-only
        STATUS          mandatory
        DESCRIPTION
        "Count of times this filter has been matched"
      ::= { accIpNamedFiltEntry 13 }
      accIpNamedFiltLastMatch   OBJECT-TYPE
        SYNTAX          TimeTicks
        ACCESS          read-only
        STATUS          mandatory
        DESCRIPTION
        "Time/Date that filter was last matched"
      ::= { accIpNamedFiltEntry 14 }
      accIpNamedFiltApplId   OBJECT-TYPE
        SYNTAX          INTEGER
        ACCESS          read-only
        STATUS          mandatory
        DESCRIPTION
        "User defined identification number associated with an application. 
        (i.e, telnet, ftp)"
      ::= { accIpNamedFiltEntry 15 }
      accIpNamedFiltSAIndex             OBJECT-TYPE
        SYNTAX          OCTET STRING
        ACCESS          read-write
        STATUS          mandatory
        DESCRIPTION     "Points to a Security Association used for one
                                 communication flow"
      ::= { accIpNamedFiltEntry 16 }
-- The IP filter application table
   accIpFiltApplTable        OBJECT-TYPE
                SYNTAX  SEQUENCE OF AccIpFiltApplEntry
                ACCESS  not-accessible
                STATUS  mandatory
                DESCRIPTION
                   "Table showing the list of IP filters that will
                    be applied on a given interface, shown in the 
                    order that they will be applied. This is essentially
                    an expansion of the filter profile to filter entries
                    on a per interface basis."
                ::= { accIpFilter 8 }
   AccIpFiltApplEntry ::= SEQUENCE {
                accIpFiltApplIfIndex    INTEGER,
                accIpFiltApplPktDir     INTEGER,
                accIpFiltApplSeqNum     INTEGER,
                accIpFiltApplName       DisplayString,
                accIpFiltApplMatches    Counter,
                accIpFiltApplLastMatch  TimeTicks
                }
    accIpFiltApplEntry      OBJECT-TYPE
                SYNTAX  AccIpFiltApplEntry
                ACCESS  not-accessible
                STATUS  mandatory
                DESCRIPTION
                  " A single entry in the filter application table."
                INDEX { accIpFiltApplIfIndex,
                        accIpFiltApplPktDir,
                        accIpFiltApplSeqNum }
                ::= { accIpFiltApplTable 1 }
    accIpFiltApplIfIndex  OBJECT-TYPE    
                SYNTAX  INTEGER
                ACCESS  read-only
                STATUS  mandatory
                DESCRIPTION
                 " Interface index to which this filter applies, or
                   zero for global filters.
                   This integer identifies the row of the system wide 
                   interfaces table associated with the particular 
                   interface."
                ::= { accIpFiltApplEntry 1 }
    accIpFiltApplPktDir  OBJECT-TYPE     
                SYNTAX  INTEGER {
                        input(1),
                        output(2),
                        global(3)
                        }
                ACCESS  read-only
                STATUS  mandatory
                DESCRIPTION
                 "Stream direction to which filter is applied.
                  Input and Output require an interface to
                  be specified. Global indicates all interfaces
                  and both directions. Input and Global filters are 
                  applied prior to Output filters.
                  NOTE: a packet originating in the router may not
                  pass through the filter logic."
                ::= { accIpFiltApplEntry 2 }
    accIpFiltApplSeqNum  OBJECT-TYPE     
                SYNTAX  INTEGER
                ACCESS  read-only
                STATUS  mandatory
                DESCRIPTION
                " An internally generated sequence number used to
                  allow the Filter display table to be returned in
                  the order the filters are applied (most specific
                  to least specific) without violating SNMP ordering
                  rules. Sequence numbers for all filters may change
                  with a single addition or modification of a filter.
                  Sequence numbers, once assigned, are not assigned
                  again. This number has no intrinsic meaning." 
                ::= { accIpFiltApplEntry 3 }
    accIpFiltApplName        OBJECT-TYPE
        SYNTAX          DisplayString
        ACCESS          read-only
        STATUS          mandatory
        DESCRIPTION
        "The name of the filter entry."
      ::= { accIpFiltApplEntry 4 }
      accIpFiltApplMatches     OBJECT-TYPE
        SYNTAX          Counter
        ACCESS          read-only
        STATUS          mandatory
        DESCRIPTION
        "Count of times this filter has been matched"
      ::= { accIpFiltApplEntry 5 }
      accIpFiltApplLastMatch   OBJECT-TYPE
        SYNTAX          TimeTicks
        ACCESS          read-only
        STATUS          mandatory
        DESCRIPTION
        "Time/Date that filter was last matched"
      ::= { accIpFiltApplEntry 6 }

END
