-- file automatically created


TELDAT-TRAP-TLNT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tlntTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TLNT event subsystem."
    REVISION "201401200930Z"
    DESCRIPTION "Initial implementation"
        ::= { telEventTraps 171 }


tlntEventsGroup	OBJECT IDENTIFIER	::= { tlntTrapsMIB 1 }

tlntNotifications	OBJECT IDENTIFIER	::= { tlntTrapsMIB 2 }
tlntNotificationsPrefix	OBJECT IDENTIFIER	::= { tlntNotifications 0 }

tlntEventObjects1 OBJECT-IDENTITY
    STATUS current
    DESCRIPTION
        "Event TLNT.1
        Generic event to display any information."
    ::= { tlntEventsGroup 1 }

tlnt1-generic-info OBJECT-TYPE
    SYNTAX DisplayString
    MAX-ACCESS accessible-for-notify
    STATUS current
    DESCRIPTION
        "Parameter 'generic-info' in event TLNT.1"
    ::= { tlntEventObjects1 1 }

tlntEventObjects2 OBJECT-IDENTITY
    STATUS current
    DESCRIPTION
        "Event TLNT.2
        Generic event to display any information."
    ::= { tlntEventsGroup 2 }

tlnt2-generic-info OBJECT-TYPE
    SYNTAX DisplayString
    MAX-ACCESS accessible-for-notify
    STATUS current
    DESCRIPTION
        "Parameter 'generic-info' in event TLNT.2"
    ::= { tlntEventObjects2 1 }

tlntEventObjects3 OBJECT-IDENTITY
    STATUS current
    DESCRIPTION
        "Event TLNT.3
        No memory available to execute an operation."
    ::= { tlntEventsGroup 3 }

tlnt3-memory-info OBJECT-TYPE
    SYNTAX DisplayString
    MAX-ACCESS accessible-for-notify
    STATUS current
    DESCRIPTION
        "Parameter 'memory-info' in event TLNT.3"
    ::= { tlntEventObjects3 1 }

tlntEventObjects4 OBJECT-IDENTITY
    STATUS current
    DESCRIPTION
        "Event TLNT.4
        Timer for an operation has timed out."
    ::= { tlntEventsGroup 4 }

tlnt4-timer-info OBJECT-TYPE
    SYNTAX DisplayString
    MAX-ACCESS accessible-for-notify
    STATUS current
    DESCRIPTION
        "Parameter 'timer-info' in event TLNT.4"
    ::= { tlntEventObjects4 1 }

tlntEventObjects5 OBJECT-IDENTITY
    STATUS current
    DESCRIPTION
        "Event TLNT.5
        An error has ocurred while executing a RTOS operation."
    ::= { tlntEventsGroup 5 }

tlnt5-error-info OBJECT-TYPE
    SYNTAX DisplayString
    MAX-ACCESS accessible-for-notify
    STATUS current
    DESCRIPTION
        "Parameter 'error-info' in event TLNT.5"
    ::= { tlntEventObjects5 1 }

tlntEventObjects6 OBJECT-IDENTITY
    STATUS current
    DESCRIPTION
        "Event TLNT.6
        An error has ocurred while executing a SOCKED operation."
    ::= { tlntEventsGroup 6 }

tlnt6-error-info OBJECT-TYPE
    SYNTAX DisplayString
    MAX-ACCESS accessible-for-notify
    STATUS current
    DESCRIPTION
        "Parameter 'error-info' in event TLNT.6"
    ::= { tlntEventObjects6 1 }

tlntEventObjects7 OBJECT-IDENTITY
    STATUS current
    DESCRIPTION
        "Event TLNT.7
        An error has ocurred while executing a pseudoterminal operation."
    ::= { tlntEventsGroup 7 }

tlnt7-error-info OBJECT-TYPE
    SYNTAX DisplayString
    MAX-ACCESS accessible-for-notify
    STATUS current
    DESCRIPTION
        "Parameter 'error-info' in event TLNT.7"
    ::= { tlntEventObjects7 1 }

tlntEventObjects8 OBJECT-IDENTITY
    STATUS current
    DESCRIPTION
        "Event TLNT.8
        Telnet negotiation."
    ::= { tlntEventsGroup 8 }

tlnt8-generic-info OBJECT-TYPE
    SYNTAX DisplayString
    MAX-ACCESS accessible-for-notify
    STATUS current
    DESCRIPTION
        "Parameter 'generic-info' in event TLNT.8"
    ::= { tlntEventObjects8 1 }

tlntEventObjects9 OBJECT-IDENTITY
    STATUS current
    DESCRIPTION
        "Event TLNT.9
        A client Telnet session has been open or closed"
    ::= { tlntEventsGroup 9 }

tlnt9-operation OBJECT-TYPE
    SYNTAX DisplayString
    MAX-ACCESS accessible-for-notify
    STATUS current
    DESCRIPTION
        "Parameter 'operation' in event TLNT.9"
    ::= { tlntEventObjects9 1 }

tlnt9-session-id OBJECT-TYPE
    SYNTAX Integer32
    MAX-ACCESS accessible-for-notify
    STATUS current
    DESCRIPTION
        "Parameter 'session-id' in event TLNT.9"
    ::= { tlntEventObjects9 2 }

tlnt9-local-address OBJECT-TYPE
    SYNTAX IpAddress
    MAX-ACCESS accessible-for-notify
    STATUS current
    DESCRIPTION
        "Parameter 'local-address' in event TLNT.9"
    ::= { tlntEventObjects9 3 }

tlnt9-remote-address OBJECT-TYPE
    SYNTAX IpAddress
    MAX-ACCESS accessible-for-notify
    STATUS current
    DESCRIPTION
        "Parameter 'remote-address' in event TLNT.9"
    ::= { tlntEventObjects9 4 }


tlntNotification1 NOTIFICATION-TYPE
    OBJECTS { 
              tlnt1-generic-info 
            }
    STATUS current
    DESCRIPTION
        "Notification of Event TLNT.1

        Message: '$1'

        Parameters list:
              $1: tlnt1-generic-info

        Generic event to display any information."
    ::= { tlntNotificationsPrefix 1 }

tlntNotification2 NOTIFICATION-TYPE
    OBJECTS { 
              tlnt2-generic-info 
            }
    STATUS current
    DESCRIPTION
        "Notification of Event TLNT.2

        Message: '$1'

        Parameters list:
              $1: tlnt2-generic-info

        Generic event to display any information."
    ::= { tlntNotificationsPrefix 2 }

tlntNotification3 NOTIFICATION-TYPE
    OBJECTS { 
              tlnt3-memory-info 
            }
    STATUS current
    DESCRIPTION
        "Notification of Event TLNT.3

        Message: 'No memory available: $1'

        Parameters list:
              $1: tlnt3-memory-info

        No memory available to execute an operation."
    ::= { tlntNotificationsPrefix 3 }

tlntNotification4 NOTIFICATION-TYPE
    OBJECTS { 
              tlnt4-timer-info 
            }
    STATUS current
    DESCRIPTION
        "Notification of Event TLNT.4

        Message: 'Timeout: $1'

        Parameters list:
              $1: tlnt4-timer-info

        Timer for an operation has timed out."
    ::= { tlntNotificationsPrefix 4 }

tlntNotification5 NOTIFICATION-TYPE
    OBJECTS { 
              tlnt5-error-info 
            }
    STATUS current
    DESCRIPTION
        "Notification of Event TLNT.5

        Message: 'RTOS error: $1'

        Parameters list:
              $1: tlnt5-error-info

        An error has ocurred while executing a RTOS operation."
    ::= { tlntNotificationsPrefix 5 }

tlntNotification6 NOTIFICATION-TYPE
    OBJECTS { 
              tlnt6-error-info 
            }
    STATUS current
    DESCRIPTION
        "Notification of Event TLNT.6

        Message: 'SOCKET error: $1'

        Parameters list:
              $1: tlnt6-error-info

        An error has ocurred while executing a SOCKED operation."
    ::= { tlntNotificationsPrefix 6 }

tlntNotification7 NOTIFICATION-TYPE
    OBJECTS { 
              tlnt7-error-info 
            }
    STATUS current
    DESCRIPTION
        "Notification of Event TLNT.7

        Message: 'Pseudoterminal error: $1'

        Parameters list:
              $1: tlnt7-error-info

        An error has ocurred while executing a pseudoterminal operation."
    ::= { tlntNotificationsPrefix 7 }

tlntNotification8 NOTIFICATION-TYPE
    OBJECTS { 
              tlnt8-generic-info 
            }
    STATUS current
    DESCRIPTION
        "Notification of Event TLNT.8

        Message: '$1'

        Parameters list:
              $1: tlnt8-generic-info

        Telnet negotiation."
    ::= { tlntNotificationsPrefix 8 }

tlntNotification9 NOTIFICATION-TYPE
    OBJECTS { 
              tlnt9-operation, 
              tlnt9-session-id,
              tlnt9-local-address,
              tlnt9-remote-address 
            }
    STATUS current
    DESCRIPTION
        "Notification of Event TLNT.9

        Message: '$1 client session $2 local-ip $3 remote-ip $4'

        Parameters list:
              $1: tlnt9-operation
              $2: tlnt9-session-id
              $3: tlnt9-local-address
              $4: tlnt9-remote-address

        A client Telnet session has been open or closed"
    ::= { tlntNotificationsPrefix 9 }


END
