-- This file is corresponding to Release 6.1.2.100 from 2001/09/26 00:00:00
-- (C)opyright 1991-1999 BinTec Communications AG, All Rights Reserved
-- $RCSfile: mibdns,v $ 
-- $Revision: 1.8 $ 

BIANCA-BRICK-DNS-MIB DEFINITIONS ::= BEGIN
 
        IMPORTS
		DisplayString FROM SNMPv2-TC
            IpAddress, Counter
                FROM RFC1155-SMI
 
            OBJECT-TYPE
                FROM RFC-1212;

    org         OBJECT IDENTIFIER ::= { iso 3 }
    dod         OBJECT IDENTIFIER ::= { org 6 }
    internet    OBJECT IDENTIFIER ::= { dod 1 }
    private     OBJECT IDENTIFIER ::= { internet 4 }
    enterprises OBJECT IDENTIFIER ::= { private 1 }
    bintec      OBJECT IDENTIFIER ::= { enterprises 272 }
    bibo        OBJECT IDENTIFIER ::= { bintec 4 }
    biboip      OBJECT IDENTIFIER
        ::= { bibo 5 }

-- DNS MIB

        ipDns OBJECT IDENTIFIER  ::= { biboip 20 }
            -- Subtree containing tables and settings for DNS handling

        ipDnsDhcpAssign OBJECT-TYPE
            SYNTAX  INTEGER { 
                        none (1), -- Donut send any nameserver -addresses
                        self (2), -- Send own address as the only nameserver
                        global(3)  -- Send ns-addresses from global admin table
                      }
            ACCESS  read-write
            STATUS  mandatory
            DESCRIPTION
                "This variable determines the assignment policy, when a BinTec 
                 router acts as a DHCP-server and is asked for nameserver 
                 addresses.
		  Possible values:
                        none  (1), -- Donut send any nameserver -addresses
                        self  (2), -- Send own address as the only nameserver
                        global(3)  -- Send ns-addresses from global admin table."
            ::= { ipDns 1 }

        ipDnsIpcpAssign OBJECT-TYPE
            SYNTAX  INTEGER { 
                        none  (1), -- Donut send any nameserver addresses
                        self  (2), -- Send own address as the only nameserver
                        global(3)  -- Send ns-addresses from global admin table
                      }
            ACCESS  read-write
            STATUS  mandatory
            DESCRIPTION
                "This variable determines the assignment policy, when a BinTec 
                 router is asked for nameservers during IPCP negotiation.
		  Possible values:
                        none  (1), -- Donut send any nameserver addresses
                        self  (2), -- Send own address as the only nameserver
                        global(3)  -- Send ns-addresses from global admin table."
            ::= { ipDns 2 }

        ipDnsUsePosCache OBJECT-TYPE
            SYNTAX  INTEGER { no(1), yes(2) }
            ACCESS  read-write
            STATUS  mandatory
            DESCRIPTION
                "Decides, whether positive caching is performed or not."
            ::= { ipDns 3 }

        ipDnsUseNegCache OBJECT-TYPE
            SYNTAX  INTEGER { no(1), yes(2) }
            ACCESS  read-write
            STATUS  mandatory
            DESCRIPTION
                "Decides, whether negative caching is performed or not."
            ::= { ipDns 4 }

        ipDnsMaxCacheSize OBJECT-TYPE
            SYNTAX  INTEGER 
            ACCESS  read-write
            STATUS  mandatory
            DESCRIPTION
                "Defines the maximum number of entries in the DNS table.
                 If this limit is reached, the dynamic entries are discarded 
                 according to the lru order, if a new entry is to be added."
            ::= { ipDns 5 }

        ipDnsPositiveTtl OBJECT-TYPE
            SYNTAX  INTEGER 
            ACCESS  read-write
            STATUS  mandatory
            DESCRIPTION
                "The time to live used for a positive cache entry, if the 
                 responding nameserver does not tell it explicitly
		 (i.e. TTL=0)."
            ::= { ipDns 6 }

        ipDnsNegativeTtl OBJECT-TYPE
            SYNTAX  INTEGER 
            ACCESS  read-write
            STATUS  mandatory
            DESCRIPTION
                "The time to live used for negative cache entries."
            ::= { ipDns 7 }

        ipDnsDefaultIfIndex OBJECT-TYPE
            SYNTAX  INTEGER 
            ACCESS  read-write
            STATUS  mandatory
            DESCRIPTION
                "The index of the interface (from the pppTable) whose 
                 nameserver should be requested by default, if nothing else 
                 works. -1 defines no default interface for DNS forwarding."
            ::= { ipDns 8 }

	ipDnsNumReceives OBJECT-TYPE
            SYNTAX  INTEGER 
            ACCESS  read-only
            STATUS  mandatory
            DESCRIPTION
                "The number of packets received."
            ::= { ipDns 9 }

	ipDnsNumInvalids OBJECT-TYPE
            SYNTAX  INTEGER 
            ACCESS  read-only
            STATUS  mandatory
            DESCRIPTION
                "The number of invalid packets received."
            ::= { ipDns 10 }

	ipDnsNumRequests OBJECT-TYPE
            SYNTAX  INTEGER 
            ACCESS  read-only
            STATUS  mandatory
            DESCRIPTION
                "The number of questions received. If a packet is received, this
		 variable is incremented by the number of question records
		 contained in the packet."
            ::= { ipDns 11 }

	ipDnsNumCacheHits OBJECT-TYPE
            SYNTAX  INTEGER 
            ACCESS  read-only
            STATUS  mandatory
            DESCRIPTION
                "The number of times a question could be answered 
		 immediately due to a cache entry."
            ::= { ipDns 12 }

	ipDnsNumForwards OBJECT-TYPE
            SYNTAX  INTEGER 
            ACCESS  read-only
            STATUS  mandatory
            DESCRIPTION
                "The number of questions forwarded to other name servers."
            ::= { ipDns 13 }

	ipDnsNumOks OBJECT-TYPE
            SYNTAX  INTEGER 
            ACCESS  read-only
            STATUS  mandatory
            DESCRIPTION
                "The number of requests answered successfully."
            ::= { ipDns 14 }

	ipDnsNumFails OBJECT-TYPE
            SYNTAX  INTEGER 
            ACCESS  read-only
            STATUS  mandatory
            DESCRIPTION
                "The number of requests answered with a SERVFAIL packet."
            ::= { ipDns 15 }

        ipDnsDynamicGlobals OBJECT-TYPE
            SYNTAX  INTEGER { 
                        yes (1),  -- Overwrite global name servers each time a 
				  -- name server has been negotiated successfully 
				  -- via IPCP
                        no   (2)  -- Never overwrite global name servers.
                      }
            ACCESS  read-write
            STATUS  mandatory
            DESCRIPTION
                "This object determines, if the global name servers in table admin 
		 are being overwritten each time a name server has been negotiated
		 successfully via IPCP or not
		 Possible values:
                        yes (1),  -- Overwrite global name servers each time a 
				  -- name server has been negotiated successfully 
				  -- via IPCP
                        no   (2)  -- Never overwrite global name servers."
            ::= { ipDns 17 }



        ipDnsTable OBJECT-TYPE
            SYNTAX SEQUENCE OF IpDnsEntry
            ACCESS not-accessible
            STATUS mandatory
            DESCRIPTION
                "Contains both static and temporary entries of DNS records "
            ::= { ipDns 16 }

        ipDnsEntry OBJECT-TYPE
            SYNTAX IpDnsEntry
            ACCESS not-accessible
            STATUS mandatory
            DESCRIPTION
                "Contains either DNS routing-information or DNS-caching-
                 information, depending on the values of the ip-address and 
                 interface-index fields"
            INDEX { ipDnsEntName }
        ::= { ipDnsTable 1 }

        IpDnsEntry ::=
            SEQUENCE {
                ipDnsEntName     DisplayString, 
                ipDnsEntIpaddr   IpAddress,
                ipDnsEntIfIndex  INTEGER,
                ipDnsEntResponse INTEGER,
                ipDnsEntStatic   INTEGER,
                ipDnsEntTtl      INTEGER,
                ipDnsEntLru      INTEGER,
                ipDnsEntHash     INTEGER,
		ipDnsEntRefCount INTEGER
            }

        ipDnsEntName OBJECT-TYPE
            SYNTAX DisplayString
            ACCESS read-write
            STATUS mandatory
            DESCRIPTION
                "DNS-name"
        ::= { ipDnsEntry 1 }

        ipDnsEntIpaddr OBJECT-TYPE
            SYNTAX IpAddress
            ACCESS read-write
            STATUS mandatory
            DESCRIPTION
                "The ip-address, 0.0.0.0 for a not resolved or wildcard entry"
        ::= { ipDnsEntry 2 }

        ipDnsEntIfIndex OBJECT-TYPE
            SYNTAX INTEGER
            ACCESS read-write
            STATUS mandatory
            DESCRIPTION
                "The index of the interface (from the pppTable) whose nameserver
                 should be requested for this entry. If this field contains a 
                 negative value, the static nameservers are queried."
        ::= { ipDnsEntry 3 }

        ipDnsEntResponse OBJECT-TYPE
            SYNTAX INTEGER { ignore(1), negative(2), positive(3) }
            ACCESS read-write
            STATUS mandatory
            DESCRIPTION
                "Response for queries matching this entry"
        ::= { ipDnsEntry 4 }

        ipDnsEntStatic OBJECT-TYPE
            SYNTAX INTEGER { no(1), yes(2), delete(3) }
            ACCESS read-write
            STATUS mandatory
            DESCRIPTION
                "Determines, whether the entry is static (yes), dynamic(no) 
                 (ttl is decremented) or marked for discard (delete)"
        ::= { ipDnsEntry 5 }

        ipDnsEntTtl OBJECT-TYPE
            SYNTAX  INTEGER 
            ACCESS read-write
            STATUS mandatory
            DESCRIPTION
                "The remaining time-to-live of the entry in seconds. 
                 This Field is only used, if the type of the entry is dynamic."
        ::= { ipDnsEntry 6 }

        ipDnsEntLru OBJECT-TYPE
            SYNTAX INTEGER 
            ACCESS read-write
            STATUS mandatory
            DESCRIPTION
                "This Field is only used, if the type of the entry is dynamic.
                 It is an internal value determining the order, in whch dynamic 
                 entries are discarded in case of a full dns table 
                 (last-recently-used). Internally, it represents the number 
                 of seconds elapsed since 01.01.1970."
        ::= { ipDnsEntry 7 }

        ipDnsEntHash OBJECT-TYPE
            SYNTAX INTEGER 
            ACCESS read-only
            STATUS mandatory
            DESCRIPTION
                "The hash value for the name field. This value is
                 re-compted at boot time and may change due to
                 changing hash algorithms."
        ::= { ipDnsEntry 8 }

        ipDnsEntRefCount OBJECT-TYPE
            SYNTAX INTEGER 
            ACCESS read-write
            STATUS mandatory
            DESCRIPTION
                "Counts the number of times the entry has been referenced. 
		 For immediate entries it resembles the number of times
		 a question could be answered due to this entry, for entries
		 pointing to another nameserver, the number of times, the
		 associated interface has been tried to pull up."
        ::= { ipDnsEntry 9 }





END
