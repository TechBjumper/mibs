ZTE-AN-INTERFACE-BRG-PERF-MIB DEFINITIONS ::= BEGIN

    IMPORTS 
        MODULE-IDENTITY, OBJECT-TYPE, NOTIFICATION-TYPE,
        Integer32, Gauge32, Counter64                   FROM SNMPv2-SMI
        RowStatus, DisplayString, TruthValue,
        TEXTUAL-CONVENTION, DateAndTime                 FROM SNMPv2-TC
        MODULE-COMPLIANCE, OBJECT-GROUP                 FROM SNMPv2-CONF
        ifIndex                                         FROM IF-MIB
        zxAnInterface                                   FROM ZTE-AN-SMI
        HCPerfCurrentCount                              FROM HC-PerfHist-TC-MIB
        zxAnSubIfIndex                                  FROM ZTE-AN-IF-MIB;
        
      zxAnInterfaceBrgPerfMib MODULE-IDENTITY
        LAST-UPDATED    "201109132000Z"
        ORGANIZATION    "ZTE Corporation"
        CONTACT-INFO    "Zhang Weiping   ZTE Corporation
                         Mail: zhang.weiping@zte.com.cn
                         Tel : 021-68896470"
        DESCRIPTION     
            "The MIB module for the Performance Management of ZTE Access
             Node interface."
    
        REVISION        "201109132000Z"
        DESCRIPTION
            "Modify this mib according to standard."
                
        REVISION        "201109101600Z"
        DESCRIPTION
            "Modify the description."
                                     
        REVISION        "201107021400Z"
        DESCRIPTION
            "Initial version of this MIB module."
        ::= {zxAnInterface 33}

--------------------------------------------------------------------------------
-- Following management objects are defined.
-- 1. zxAnBrgIfCurr15MinPerfTable
-- 2. zxAnBrgIfCurr1DayPerfTable
-- 3. zxAnBrgIfHis15MinPerfTable
-- 4. zxAnBrgIfHis1DayPerfTable
-- 5. zxAnBrgIfAlmProfileConfTable
-- 6. zxAnBrgIfAlmProfileApplyTable
-- 7. zxAnBrgIfAlmProfileTable
-- 8. zxAnBrgIfCurrMinPerfTable
-- 9. zxAnBrgIfHisMinPerfTable

-- Following conformance information is defined.
--31. zxAnBrgIfPerfConformance
--------------------------------------------------------------------------------    
    zxAnBrgIfPerfObjects          OBJECT IDENTIFIER ::= { zxAnInterfaceBrgPerfMib 2 }            
      
--------------------------------------------------------------------------------
-- 1. zxAnBrgIfCurr15MinPerfTable
--------------------------------------------------------------------------------

    zxAnBrgIfCurr15MinPerfTable    OBJECT-TYPE
        SYNTAX      SEQUENCE OF ZxAnBrgIfCurr15MinPerfEntry
        MAX-ACCESS  not-accessible
        STATUS      current
        DESCRIPTION 
             "The 15 minutes interval performance data table of the bridge interfaces."             
        ::= { zxAnBrgIfPerfObjects 2 }

    zxAnBrgIfCurr15MinPerfEntry    OBJECT-TYPE
        SYNTAX      ZxAnBrgIfCurr15MinPerfEntry
        MAX-ACCESS  not-accessible
        STATUS      current
        DESCRIPTION 
            "The 15 minutes interval performance data entry of the bridge interfaces."
        INDEX   { ifIndex,zxAnSubIfIndex}
        ::= { zxAnBrgIfCurr15MinPerfTable 1 }

    ZxAnBrgIfCurr15MinPerfEntry ::= SEQUENCE {
        zxAnBrgIfC15MTimeElapsed            Gauge32,
        zxAnBrgIfC15MInOctets               Counter64,
        zxAnBrgIfC15MInUcastPkts            Counter64,
        zxAnBrgIfC15MInMcastPkts            Counter64,
        zxAnBrgIfC15MInBcastPkts            Counter64,
        zxAnBrgIfC15MOutOctets              Counter64,
        zxAnBrgIfC15MOutUcastPkts           Counter64,
        zxAnBrgIfC15MOutMcastPkts           Counter64,
        zxAnBrgIfC15MOutBcastPkts           Counter64,
        zxAnBrgIfC15MInErroredPktRate       Gauge32,
        zxAnBrgIfC15MInBwUsingRatio         Integer32,
        zxAnBrgIfC15MOutBwUsingRatio        Integer32,  
        zxAnBrgIfC15MReset                  INTEGER
        }
      
    zxAnBrgIfC15MTimeElapsed OBJECT-TYPE 
        SYNTAX      Gauge32(0..899)
        UNITS       "seconds"
        MAX-ACCESS  read-only
        STATUS      current
        DESCRIPTION     
            "Number of seconds that have elapsed since the beginning of the 
             current 15 minutes interval."
        ::= { zxAnBrgIfCurr15MinPerfEntry 1 }         
        
    zxAnBrgIfC15MInOctets    OBJECT-TYPE 
        SYNTAX      Counter64
        MAX-ACCESS  read-only
        STATUS      current
        DESCRIPTION     
            "The total number of octets received on the interface,
            including framing characters in current 15 minutes interval."
        ::= { zxAnBrgIfCurr15MinPerfEntry 2 }

    zxAnBrgIfC15MInUcastPkts    OBJECT-TYPE 
        SYNTAX      Counter64
        MAX-ACCESS  read-only
        STATUS      current
        DESCRIPTION     
           "The number of packets, delivered by this sub-layer to a
            higher (sub-)layer, which were not addressed to a multicast
            or broadcast address at this sub-layer and in current 15 
            minutes interval."
        ::= { zxAnBrgIfCurr15MinPerfEntry 3 }

    zxAnBrgIfC15MInMcastPkts    OBJECT-TYPE 
        SYNTAX      Counter64
        MAX-ACCESS  read-only
        STATUS      current
        DESCRIPTION     
            "The number of packets, delivered by this sub-layer to a
            higher (sub-)layer, which were addressed to a multicast
            address at this sub-layer and in current 15 minutes interval. 
            For a MAC layer protocol, this includes both Group and 
            Functional addresses."
        ::= { zxAnBrgIfCurr15MinPerfEntry 4 }

    zxAnBrgIfC15MInBcastPkts    OBJECT-TYPE 
        SYNTAX      Counter64
        MAX-ACCESS  read-only
        STATUS      current
        DESCRIPTION     
            "The number of packets, delivered by this sub-layer to a
            higher (sub-)layer, which were addressed to a broadcast
            address at this sub-layer and in current 15 minutes interval."
        ::= { zxAnBrgIfCurr15MinPerfEntry 5 }

    zxAnBrgIfC15MOutOctets    OBJECT-TYPE 
        SYNTAX      Counter64
        MAX-ACCESS  read-only
        STATUS      current
        DESCRIPTION     
            "The total number of octets transmitted out of the interface, 
            including framing characters in curent 15 minutes interval."
        ::= { zxAnBrgIfCurr15MinPerfEntry 6 }

    zxAnBrgIfC15MOutUcastPkts    OBJECT-TYPE 
        SYNTAX      Counter64
        MAX-ACCESS  read-only
        STATUS      current
        DESCRIPTION     
            "The total number of packets that higher-level protocols
            requested be transmitted, and which were not addressed to a
            multicast or broadcast address at this sub-layer, including
            those that were discarded or not sent in current 15 minutes interval."
        ::= { zxAnBrgIfCurr15MinPerfEntry 7 }
        
    zxAnBrgIfC15MOutMcastPkts    OBJECT-TYPE 
        SYNTAX      Counter64
        MAX-ACCESS  read-only
        STATUS      current
        DESCRIPTION     
            "The total number of packets that higher-level protocols
            requested be transmitted, and which were addressed to a
            multicast address at this sub-layer, including those that
            were discarded or not sent and in current 15 minutes interval.
            For a MAC layer protocol, this includes both Group and 
            Functional addresses."
        ::= { zxAnBrgIfCurr15MinPerfEntry 8 }

    zxAnBrgIfC15MOutBcastPkts    OBJECT-TYPE 
        SYNTAX      Counter64
        MAX-ACCESS  read-only
        STATUS      current
        DESCRIPTION     
            "The total number of packets that higher-level protocols
            requested be transmitted, and which were addressed to a
            broadcast address at this sub-layer, including those that
            were discarded or not sent in 15 current minutes interval."
        ::= { zxAnBrgIfCurr15MinPerfEntry 9 }
      
    zxAnBrgIfC15MInErroredPktRate    OBJECT-TYPE 
        SYNTAX      Gauge32
        UNITS       "pps"
        MAX-ACCESS  read-only
        STATUS      current
        DESCRIPTION     
            "The received errored packet rate in current 15 minutes."
        ::= { zxAnBrgIfCurr15MinPerfEntry 50 }
               
    zxAnBrgIfC15MInBwUsingRatio    OBJECT-TYPE 
        SYNTAX      Integer32(0..100)
        UNITS       "percents"
        MAX-ACCESS  read-only
        STATUS      current
        DESCRIPTION     
            "An estimate of the interface's current received bandwidth using 
            ratio in current 15 minutes."
        ::= { zxAnBrgIfCurr15MinPerfEntry 52 }
        
    zxAnBrgIfC15MOutBwUsingRatio    OBJECT-TYPE 
        SYNTAX      Integer32(0..100)
        UNITS       "percents"
        MAX-ACCESS  read-only
        STATUS      current
        DESCRIPTION     
            "An estimate of the interface's current transmitted bandwidth using
            ratio in current 15 minutes."
        ::= { zxAnBrgIfCurr15MinPerfEntry 53 }
                 
    zxAnBrgIfC15MReset OBJECT-TYPE 
        SYNTAX      INTEGER
            {
                perfReset(1)
            }
        MAX-ACCESS  read-write
        STATUS      current
        DESCRIPTION     
            "Clear all the current 15 minutes performance variables.
             When get this variable, always return 1."
        ::= { zxAnBrgIfCurr15MinPerfEntry 100 }     
            
--------------------------------------------------------------------------------
-- 2. zxAnBrgIfCurr1DayPerfTable
--------------------------------------------------------------------------------

    zxAnBrgIfCurr1DayPerfTable    OBJECT-TYPE
        SYNTAX      SEQUENCE OF ZxAnBrgIfCurr1DayPerfEntry
        MAX-ACCESS  not-accessible
        STATUS      current
        DESCRIPTION 
             "The 1 day interval performance data table of the bridge interfaces."             
        ::= { zxAnBrgIfPerfObjects 3 }

    zxAnBrgIfCurr1DayPerfEntry    OBJECT-TYPE
        SYNTAX      ZxAnBrgIfCurr1DayPerfEntry
        MAX-ACCESS  not-accessible
        STATUS      current
        DESCRIPTION 
            "The 1 day interval performance data entry of the bridge interfaces."
        INDEX   { ifIndex,zxAnSubIfIndex}
        ::= { zxAnBrgIfCurr1DayPerfTable 1 }

    ZxAnBrgIfCurr1DayPerfEntry ::= SEQUENCE {
        zxAnBrgIfC1DTimeElapsed            Gauge32,
        zxAnBrgIfC1DInOctets               Counter64,
        zxAnBrgIfC1DInUcastPkts            Counter64,
        zxAnBrgIfC1DInMcastPkts            Counter64,
        zxAnBrgIfC1DInBcastPkts            Counter64,
        zxAnBrgIfC1DOutOctets              Counter64,
        zxAnBrgIfC1DOutUcastPkts           Counter64,
        zxAnBrgIfC1DOutMcastPkts           Counter64,
        zxAnBrgIfC1DOutBcastPkts           Counter64,
        zxAnBrgIfC1DInErroredPktRate       Gauge32,
        zxAnBrgIfC1DInBwUsingRatio         Integer32,
        zxAnBrgIfC1DOutBwUsingRatio        Integer32,
        zxAnBrgIfC1DReset                  INTEGER
        }
      
    zxAnBrgIfC1DTimeElapsed OBJECT-TYPE 
        SYNTAX      Gauge32(0..86399)
        UNITS       "seconds"
        MAX-ACCESS  read-only
        STATUS      current
        DESCRIPTION     
            "Number of seconds that have elapsed since the beginning of the 
             current 1 day interval."
        ::= { zxAnBrgIfCurr1DayPerfEntry 1 } 
    
    zxAnBrgIfC1DInOctets    OBJECT-TYPE 
        SYNTAX      Counter64
        MAX-ACCESS  read-only
        STATUS      current
        DESCRIPTION     
            "The total number of octets received on the interface,
            including framing characters in current one day interval."
        ::= { zxAnBrgIfCurr1DayPerfEntry 2 }

    zxAnBrgIfC1DInUcastPkts    OBJECT-TYPE 
        SYNTAX      Counter64
        MAX-ACCESS  read-only
        STATUS      current
        DESCRIPTION     
            "The total number of octets received on the interface,
            including framing characters in current one day interval."
        ::= { zxAnBrgIfCurr1DayPerfEntry 3 }

    zxAnBrgIfC1DInMcastPkts    OBJECT-TYPE 
        SYNTAX      Counter64
        MAX-ACCESS  read-only
        STATUS      current
        DESCRIPTION     
            "The number of packets, delivered by this sub-layer to a
            higher (sub-)layer, which were addressed to a multicast
            address at this sub-layer and in current one day interval.
            For a MAC layer protocol, this includes both Group and 
            Functional addresses."
        ::= { zxAnBrgIfCurr1DayPerfEntry 4 }

    zxAnBrgIfC1DInBcastPkts    OBJECT-TYPE 
        SYNTAX      Counter64
        MAX-ACCESS  read-only
        STATUS      current
        DESCRIPTION     
            "The number of packets, delivered by this sub-layer to a
            higher (sub-)layer, which were addressed to a broadcast
            address at this sub-layer and in current one day interval."
        ::= { zxAnBrgIfCurr1DayPerfEntry 5 }

    zxAnBrgIfC1DOutOctets    OBJECT-TYPE 
        SYNTAX      Counter64
        MAX-ACCESS  read-only
        STATUS      current
        DESCRIPTION     
            "The total number of octets transmitted out of the interface, 
            including framing characters in curent one day interval."
        ::= { zxAnBrgIfCurr1DayPerfEntry 6 }

    zxAnBrgIfC1DOutUcastPkts    OBJECT-TYPE 
        SYNTAX      Counter64
        MAX-ACCESS  read-only
        STATUS      current
        DESCRIPTION     
            "The total number of packets that higher-level protocols
            requested be transmitted, and which were not addressed to a
            multicast or broadcast address at this sub-layer, including
            those that were discarded or not sent in current one day interval."
        ::= { zxAnBrgIfCurr1DayPerfEntry 7 }
        
    zxAnBrgIfC1DOutMcastPkts    OBJECT-TYPE 
        SYNTAX      Counter64
        MAX-ACCESS  read-only
        STATUS      current
        DESCRIPTION     
            "The total number of packets that higher-level protocols
            requested be transmitted, and which were addressed to a
            multicast address at this sub-layer, including those that
            were discarded or not sent and in current one day interval. 
            For a MAC layer protocol, this includes both Group and 
            Functional addresses."
        ::= { zxAnBrgIfCurr1DayPerfEntry 8 }

    zxAnBrgIfC1DOutBcastPkts    OBJECT-TYPE 
        SYNTAX      Counter64
        MAX-ACCESS  read-only
        STATUS      current
        DESCRIPTION     
            "The total number of packets that higher-level protocols
            requested be transmitted, and which were addressed to a
            broadcast address at this sub-layer, including those that
            were discarded or not sent in current one day interval."
        ::= { zxAnBrgIfCurr1DayPerfEntry 9 }

    zxAnBrgIfC1DInErroredPktRate    OBJECT-TYPE 
        SYNTAX      Gauge32
        UNITS       "pps"
        MAX-ACCESS  read-only
        STATUS      current
        DESCRIPTION     
            "The received errored packet rate in current one day."
        ::= { zxAnBrgIfCurr1DayPerfEntry 50 }
                
    zxAnBrgIfC1DInBwUsingRatio    OBJECT-TYPE 
        SYNTAX      Integer32(0..100)
        UNITS       "percents"
        MAX-ACCESS  read-only
        STATUS      current
        DESCRIPTION  
            "An estimate of the interface's received bandwidth using ratio 
            in current one day."  
        ::= { zxAnBrgIfCurr1DayPerfEntry 52 }
                
    zxAnBrgIfC1DOutBwUsingRatio    OBJECT-TYPE 
        SYNTAX      Integer32(0..100)
        UNITS       "percents"
        MAX-ACCESS  read-only
        STATUS      current
        DESCRIPTION   
            "An estimate of the interface's transmitted bandwidth using ratio 
            in current one day."  
        ::= { zxAnBrgIfCurr1DayPerfEntry 53 }
               
    zxAnBrgIfC1DReset OBJECT-TYPE 
        SYNTAX      INTEGER
            {
                perfReset(1)
            }
        MAX-ACCESS  read-write
        STATUS      current
        DESCRIPTION     
            "Clear all the current 1 day performance variables.
             When get this variable, always return 1."
        ::= { zxAnBrgIfCurr1DayPerfEntry 100 }  
        
--------------------------------------------------------------------------------
-- 3. zxAnBrgIfHis15MinPerfTable
--------------------------------------------------------------------------------

    zxAnBrgIfHis15MinPerfTable    OBJECT-TYPE
        SYNTAX      SEQUENCE OF ZxAnBrgIfHis15MinPerfEntry
        MAX-ACCESS  not-accessible
        STATUS      current
        DESCRIPTION 
             "The 15 minutes interval history performance data table of the bridge interfaces."             
        ::= { zxAnBrgIfPerfObjects 4 }

    zxAnBrgIfHis15MinPerfEntry    OBJECT-TYPE
        SYNTAX      ZxAnBrgIfHis15MinPerfEntry
        MAX-ACCESS  not-accessible
        STATUS      current
        DESCRIPTION 
            "The 15 minutes interval performance data entry of the bridge interfaces."
        INDEX   { ifIndex,zxAnSubIfIndex,zxAnBrgIfH15MIntervalNo }
        ::= { zxAnBrgIfHis15MinPerfTable 1 }

    ZxAnBrgIfHis15MinPerfEntry ::= SEQUENCE {
        zxAnBrgIfH15MIntervalNo             Integer32,
        zxAnBrgIfH15MIntervalValidData      TruthValue,
        zxAnBrgIfH15MDateTime               DateAndTime,
        zxAnBrgIfH15MInOctets               Counter64,
        zxAnBrgIfH15MInUcastPkts            Counter64,
        zxAnBrgIfH15MInMcastPkts            Counter64,
        zxAnBrgIfH15MInBcastPkts            Counter64,
        zxAnBrgIfH15MOutOctets              Counter64,
        zxAnBrgIfH15MOutUcastPkts           Counter64,
        zxAnBrgIfH15MOutMcastPkts           Counter64,
        zxAnBrgIfH15MOutBcastPkts           Counter64,
        zxAnBrgIfH15MInErroredPktRate       Gauge32,
        zxAnBrgIfH15MInBwUsingRatio         Integer32,
        zxAnBrgIfH15MOutBwUsingRatio        Integer32        
        }
      
    zxAnBrgIfH15MIntervalNo    OBJECT-TYPE 
        SYNTAX      Integer32(1..96)
        MAX-ACCESS  not-accessible
        STATUS      current
        DESCRIPTION     
             "Performance data interval number 1 is the the most recent 
              previous interval; interval 96 is 24 hours ago.  
              Intervals 2..96 are optional."       
        ::= { zxAnBrgIfHis15MinPerfEntry 1 }        
        
    zxAnBrgIfH15MIntervalValidData    OBJECT-TYPE 
        SYNTAX      TruthValue
        MAX-ACCESS  read-only
        STATUS      current
        DESCRIPTION     
             "Performance data valid flag. 
              true(1) means valid.  
              false(2) means invalidm and the performace data is useless."       
        ::= { zxAnBrgIfHis15MinPerfEntry 2 }        

    zxAnBrgIfH15MDateTime    OBJECT-TYPE   
        SYNTAX      DateAndTime
        MAX-ACCESS  read-only
        STATUS      current
        DESCRIPTION     
             "The 15 minutes interval performance data generation time."       
        ::= { zxAnBrgIfHis15MinPerfEntry 3 }            
        
    zxAnBrgIfH15MInOctets    OBJECT-TYPE 
        SYNTAX      Counter64
        MAX-ACCESS  read-only
        STATUS      current
        DESCRIPTION     
            "The total number of octets received on the interface,
            including framing characters in current 15 historical interval."
        ::= { zxAnBrgIfHis15MinPerfEntry 4 }

    zxAnBrgIfH15MInUcastPkts    OBJECT-TYPE 
        SYNTAX      Counter64
        MAX-ACCESS  read-only
        STATUS      current
        DESCRIPTION     
           "The number of packets, delivered by this sub-layer to a
            higher (sub-)layer, which were not addressed to a multicast
            or broadcast address at this sub-layer and in historical 15 
            minutes interval."
        ::= { zxAnBrgIfHis15MinPerfEntry 5 }

    zxAnBrgIfH15MInMcastPkts    OBJECT-TYPE 
        SYNTAX      Counter64
        MAX-ACCESS  read-only
        STATUS      current
        DESCRIPTION     
            "The number of packets, delivered by this sub-layer to a
            higher (sub-)layer, which were addressed to a multicast
            address at this sub-layer and in historical 15 minutes 
            interval.For a MAC layer protocol, this includes both 
            Group and Functional addresses."
        ::= { zxAnBrgIfHis15MinPerfEntry 6 }

    zxAnBrgIfH15MInBcastPkts    OBJECT-TYPE 
        SYNTAX      Counter64
        MAX-ACCESS  read-only
        STATUS      current
        DESCRIPTION     
            "The number of packets, delivered by this sub-layer to a
            higher (sub-)layer, which were addressed to a broadcast
            address at this sub-layer and in historical 15 minutes interval."
        ::= { zxAnBrgIfHis15MinPerfEntry 7 }

    zxAnBrgIfH15MOutOctets    OBJECT-TYPE 
        SYNTAX      Counter64
        MAX-ACCESS  read-only
        STATUS      current
        DESCRIPTION     
            "The total number of octets transmitted out of the interface, 
            including framing characters in historical 15 minutes interval."
        ::= { zxAnBrgIfHis15MinPerfEntry 8 }

    zxAnBrgIfH15MOutUcastPkts    OBJECT-TYPE 
        SYNTAX      Counter64
        MAX-ACCESS  read-only
        STATUS      current
        DESCRIPTION     
            "The total number of packets that higher-level protocols
            requested be transmitted, and which were not addressed to a
            multicast or broadcast address at this sub-layer, including
            those that were discarded or not sent in historical 15 minutes
             interval."
        ::= { zxAnBrgIfHis15MinPerfEntry 9 }
        
    zxAnBrgIfH15MOutMcastPkts    OBJECT-TYPE 
        SYNTAX      Counter64
        MAX-ACCESS  read-only
        STATUS      current
        DESCRIPTION     
            "The total number of packets that higher-level protocols
            requested be transmitted, and which were addressed to a
            multicast address at this sub-layer, including those that
            were discarded or not sent and in historical 15 minutes 
            interval.For a MAC layer protocol, this includes both Group
            and Functional addresses."
        ::= { zxAnBrgIfHis15MinPerfEntry 10 }

    zxAnBrgIfH15MOutBcastPkts    OBJECT-TYPE 
        SYNTAX      Counter64
        MAX-ACCESS  read-only
        STATUS      current
        DESCRIPTION     
            "The total number of packets that higher-level protocols
            requested be transmitted, and which were addressed to a
            broadcast address at this sub-layer, including those that
            were discarded or not sent in 15 historical minutes interval."
        ::= { zxAnBrgIfHis15MinPerfEntry 11 }

    zxAnBrgIfH15MInErroredPktRate    OBJECT-TYPE 
        SYNTAX      Gauge32
        UNITS       "pps"
        MAX-ACCESS  read-only
        STATUS      current
        DESCRIPTION     
            "The received errored packet rate in historical 15 minutes."
        ::= { zxAnBrgIfHis15MinPerfEntry 50 }
        
    zxAnBrgIfH15MInBwUsingRatio    OBJECT-TYPE 
        SYNTAX      Integer32(0..100)
        UNITS       "percents"
        MAX-ACCESS  read-only
        STATUS      current
        DESCRIPTION     
            "An estimate of the interface's received bandwidth using ratio 
            in historical 15 minutes."
        ::= { zxAnBrgIfHis15MinPerfEntry 52 }
        
    zxAnBrgIfH15MOutBwUsingRatio    OBJECT-TYPE 
        SYNTAX      Integer32(0..100)
        UNITS       "percents"
        MAX-ACCESS  read-only
        STATUS      current
        DESCRIPTION     
            "An estimate of the interface's transmitted bandwidth using ratio 
            in historical 15 minutes."
        ::= { zxAnBrgIfHis15MinPerfEntry 53 }   
                        
--------------------------------------------------------------------------------
-- 4. zxAnBrgIfHis1DayPerfTable
--------------------------------------------------------------------------------

    zxAnBrgIfHis1DayPerfTable    OBJECT-TYPE
        SYNTAX      SEQUENCE OF ZxAnBrgIfHis1DayPerfEntry
        MAX-ACCESS  not-accessible
        STATUS      current
        DESCRIPTION 
             "The 1 day interval history performance data table of the bridge interfaces."             
        ::= { zxAnBrgIfPerfObjects 5 }

    zxAnBrgIfHis1DayPerfEntry    OBJECT-TYPE
        SYNTAX      ZxAnBrgIfHis1DayPerfEntry
        MAX-ACCESS  not-accessible
        STATUS      current
        DESCRIPTION 
            "The 1 day interval performance data entry of the bridge interfaces."
        INDEX   { ifIndex,zxAnSubIfIndex, zxAnBrgIfH1DIntervalNo }
        ::= { zxAnBrgIfHis1DayPerfTable 1 }

    ZxAnBrgIfHis1DayPerfEntry ::= SEQUENCE {
        zxAnBrgIfH1DIntervalNo             Integer32,
        zxAnBrgIfH1DIntervalValidData      TruthValue,
        zxAnBrgIfH1DDateTime               DateAndTime,
        zxAnBrgIfH1DInOctets               Counter64,
        zxAnBrgIfH1DInUcastPkts            Counter64,
        zxAnBrgIfH1DInMcastPkts            Counter64,
        zxAnBrgIfH1DInBcastPkts            Counter64,
        zxAnBrgIfH1DOutOctets              Counter64,
        zxAnBrgIfH1DOutUcastPkts           Counter64,
        zxAnBrgIfH1DOutMcastPkts           Counter64,
        zxAnBrgIfH1DOutBcastPkts           Counter64,
        zxAnBrgIfH1DInErroredPktRate       Gauge32,
        zxAnBrgIfH1DInBwUsingRatio         Integer32,
        zxAnBrgIfH1DOutBwUsingRatio        Integer32
        }
      
    zxAnBrgIfH1DIntervalNo  OBJECT-TYPE 
        SYNTAX      Integer32(1..7)
        MAX-ACCESS  not-accessible
        STATUS      current
        DESCRIPTION     
             "Performance data interval number 1 is the the most recent 
              previous interval; interval 7 is 1 week ago.  
              Intervals 2..7 are optional."       
        ::= { zxAnBrgIfHis1DayPerfEntry 1 }        
        
    zxAnBrgIfH1DIntervalValidData    OBJECT-TYPE 
        SYNTAX      TruthValue
        MAX-ACCESS  read-only
        STATUS      current
        DESCRIPTION     
             "Performance data valid flag. 
              true(1) means valid.  
              false(2) means invalidm and the performace data is useless."       
        ::= { zxAnBrgIfHis1DayPerfEntry 2 }        

    zxAnBrgIfH1DDateTime    OBJECT-TYPE   
        SYNTAX      DateAndTime
        MAX-ACCESS  read-only
        STATUS      current
        DESCRIPTION     
             "The 1 day interval performance data generation time."       
        ::= { zxAnBrgIfHis1DayPerfEntry 3 }
    
    zxAnBrgIfH1DInOctets    OBJECT-TYPE 
        SYNTAX      Counter64
        MAX-ACCESS  read-only
        STATUS      current
        DESCRIPTION     
            "The total number of octets received on the interface,
            including framing characters in historical one day interval."
        ::= { zxAnBrgIfHis1DayPerfEntry 4 }

    zxAnBrgIfH1DInUcastPkts    OBJECT-TYPE 
        SYNTAX      Counter64
        MAX-ACCESS  read-only
        STATUS      current
        DESCRIPTION     
            "The total number of octets received on the interface,
            including framing characters in historical one day interval."
        ::= { zxAnBrgIfHis1DayPerfEntry 5 }

    zxAnBrgIfH1DInMcastPkts    OBJECT-TYPE 
        SYNTAX      Counter64
        MAX-ACCESS  read-only
        STATUS      current
        DESCRIPTION     
            "The number of packets, delivered by this sub-layer to a
            higher (sub-)layer, which were addressed to a multicast
            address at this sub-layer and in historical one day interval.
            For a MAC layer protocol, this includes both Group and 
            Functional addresses."
        ::= { zxAnBrgIfHis1DayPerfEntry 6 }

    zxAnBrgIfH1DInBcastPkts    OBJECT-TYPE 
        SYNTAX      Counter64
        MAX-ACCESS  read-only
        STATUS      current
        DESCRIPTION     
            "The number of packets, delivered by this sub-layer to a
            higher (sub-)layer, which were addressed to a broadcast
            address at this sub-layer and in historical one day interval."
        ::= { zxAnBrgIfHis1DayPerfEntry 7 }

    zxAnBrgIfH1DOutOctets    OBJECT-TYPE 
        SYNTAX      Counter64
        MAX-ACCESS  read-only
        STATUS      current
        DESCRIPTION     
            "The total number of octets transmitted out of the interface, 
            including framing characters in historical one day interval."
        ::= { zxAnBrgIfHis1DayPerfEntry 8 }

    zxAnBrgIfH1DOutUcastPkts    OBJECT-TYPE 
        SYNTAX      Counter64
        MAX-ACCESS  read-only
        STATUS      current
        DESCRIPTION     
            "The total number of packets that higher-level protocols
            requested be transmitted, and which were not addressed to a
            multicast or broadcast address at this sub-layer, including
            those that were discarded or not sent in historical one day
            interval."
        ::= { zxAnBrgIfHis1DayPerfEntry 9 }
        
    zxAnBrgIfH1DOutMcastPkts    OBJECT-TYPE 
        SYNTAX      Counter64
        MAX-ACCESS  read-only
        STATUS      current
        DESCRIPTION     
            "The total number of packets that higher-level protocols
            requested be transmitted, and which were addressed to a
            multicast address at this sub-layer, including those that
            were discarded or not sent and in historical one day interval. 
            For a MAC layer protocol, this includes both Group and 
            Functional addresses."
        ::= { zxAnBrgIfHis1DayPerfEntry 10 }

    zxAnBrgIfH1DOutBcastPkts    OBJECT-TYPE 
        SYNTAX      Counter64
        MAX-ACCESS  read-only
        STATUS      current
        DESCRIPTION     
            "The total number of packets that higher-level protocols
            requested be transmitted, and which were addressed to a
            broadcast address at this sub-layer, including those that
            were discarded or not sent in historical one day interval."
        ::= { zxAnBrgIfHis1DayPerfEntry 11 }

    zxAnBrgIfH1DInErroredPktRate    OBJECT-TYPE 
        SYNTAX      Gauge32
        UNITS       "pps"
        MAX-ACCESS  read-only
        STATUS      current
        DESCRIPTION     
            "The received errored packet rate in historical one day."
        ::= { zxAnBrgIfHis1DayPerfEntry 50 }
                
    zxAnBrgIfH1DInBwUsingRatio    OBJECT-TYPE 
        SYNTAX      Integer32(0..100)
        UNITS       "percents"
        MAX-ACCESS  read-only
        STATUS      current
        DESCRIPTION     
            "An estimate of the interface's received bandwidth using ratio 
            in historical one day."
        ::= { zxAnBrgIfHis1DayPerfEntry 52 }
                
    zxAnBrgIfH1DOutBwUsingRatio    OBJECT-TYPE 
        SYNTAX      Integer32(0..100)
        UNITS       "percents"
        MAX-ACCESS  read-only
        STATUS      current
        DESCRIPTION     
            "An estimate of the interface's transmitted bandwidth using ratio 
            in historical one day."
        ::= { zxAnBrgIfHis1DayPerfEntry 53 }  
                                
--------------------------------------------------------------------------------
-- 5. zxAnBrgIfAlmProfileConfTable
--------------------------------------------------------------------------------

    zxAnBrgIfAlmProfileConfTable   OBJECT-TYPE
        SYNTAX      SEQUENCE OF ZxAnBrgIfAlmProfileConfEntry
        MAX-ACCESS  not-accessible
        STATUS      current
        DESCRIPTION 
             "The performance alarm threshold profile table of the bridge interfaces."             
        ::= { zxAnBrgIfPerfObjects 6 }

    zxAnBrgIfAlmProfileConfEntry   OBJECT-TYPE
        SYNTAX      ZxAnBrgIfAlmProfileConfEntry
        MAX-ACCESS  not-accessible
        STATUS      current
        DESCRIPTION 
            "The performance alarm threshold profile table of the bridge interfaces.These
              variables in the profile configuration is optional,if not configured,
              it means the correspongding alarm is not reported, but the alarm and
               clear alarm threshold configuration is needed to bind. "
        INDEX   { zxAnBrgIfAlmProfileName, zxAnBrgIfPerfVariable }
        ::= { zxAnBrgIfAlmProfileConfTable 1 }

    ZxAnBrgIfAlmProfileConfEntry ::= SEQUENCE {
        zxAnBrgIfAlmProfileName        DisplayString,  
        zxAnBrgIfPerfVariable          OBJECT IDENTIFIER,
        zxAnBrgIfRiseAlmThresh         HCPerfCurrentCount,
        zxAnBrgIfClrRiseAlmThresh      HCPerfCurrentCount,        
        zxAnBrgIfRiseWarnThresh        HCPerfCurrentCount,  
        zxAnBrgIfClrRiseWarnThresh     HCPerfCurrentCount,        
        zxAnBrgIfFallWarnThresh        HCPerfCurrentCount, 
        zxAnBrgIfClrFallWarnThresh     HCPerfCurrentCount, 
        zxAnBrgIfFallAlmThresh         HCPerfCurrentCount,
        zxAnBrgIfClrFallAlmThresh      HCPerfCurrentCount,
        zxAnBrgIfThreshUsed            BITS,
        zxAnBrgIfAlmProfileConfRowStatus   RowStatus
        }

    zxAnBrgIfAlmProfileName  OBJECT-TYPE 
        SYNTAX      DisplayString (SIZE (1..32))
        MAX-ACCESS  not-accessible
        STATUS      current
        DESCRIPTION     
            "The profile name."
        ::= { zxAnBrgIfAlmProfileConfEntry 1 }
        
    zxAnBrgIfPerfVariable  OBJECT-TYPE 
        SYNTAX      OBJECT IDENTIFIER
        MAX-ACCESS  not-accessible
        STATUS      current
        DESCRIPTION     
            "The object identifier of performance variables."
        ::= { zxAnBrgIfAlmProfileConfEntry 2 }
        
    zxAnBrgIfRiseAlmThresh  OBJECT-TYPE 
        SYNTAX      HCPerfCurrentCount
        MAX-ACCESS  read-create
        STATUS      current
        DESCRIPTION     
            "The threshold for rising alarm."
        ::= { zxAnBrgIfAlmProfileConfEntry 3 }

    zxAnBrgIfClrRiseAlmThresh  OBJECT-TYPE 
        SYNTAX      HCPerfCurrentCount
        MAX-ACCESS  read-create
        STATUS      current
        DESCRIPTION     
            "The threshold for rising alarm restore."
        ::= { zxAnBrgIfAlmProfileConfEntry 4 }

    zxAnBrgIfRiseWarnThresh  OBJECT-TYPE 
        SYNTAX      HCPerfCurrentCount
        MAX-ACCESS  read-create
        STATUS      current
        DESCRIPTION     
            "The threshold for rising warning."
        ::= { zxAnBrgIfAlmProfileConfEntry 5 }

    zxAnBrgIfClrRiseWarnThresh  OBJECT-TYPE 
        SYNTAX      HCPerfCurrentCount
        MAX-ACCESS  read-create
        STATUS      current
        DESCRIPTION     
            "The threshold for rising warning restore."
        ::= { zxAnBrgIfAlmProfileConfEntry 6 }
        
    zxAnBrgIfFallWarnThresh  OBJECT-TYPE 
        SYNTAX      HCPerfCurrentCount
        MAX-ACCESS  read-create
        STATUS      current
        DESCRIPTION     
            "The threshold for falling warning."
        ::= { zxAnBrgIfAlmProfileConfEntry 7 }

    zxAnBrgIfClrFallWarnThresh  OBJECT-TYPE 
        SYNTAX      HCPerfCurrentCount
        MAX-ACCESS  read-create
        STATUS      current
        DESCRIPTION     
            "The threshold for falling warning restore."
        ::= { zxAnBrgIfAlmProfileConfEntry 8 }        
        
    zxAnBrgIfFallAlmThresh  OBJECT-TYPE 
        SYNTAX      HCPerfCurrentCount
        MAX-ACCESS  read-create
        STATUS      current
        DESCRIPTION     
            "The threshold for falling alarm."
        ::= { zxAnBrgIfAlmProfileConfEntry 9 }

    zxAnBrgIfClrFallAlmThresh  OBJECT-TYPE 
        SYNTAX      HCPerfCurrentCount
        MAX-ACCESS  read-create
        STATUS      current
        DESCRIPTION     
            "The threshold for falling alarm restore."
        ::= { zxAnBrgIfAlmProfileConfEntry 10 }   
                    
    zxAnBrgIfThreshUsed  OBJECT-TYPE 
         SYNTAX           BITS 
           {
               riseAlmThresh(0),
               riseAlmClrThresh(1),
               riseWarnThresh(2),
               riseWarnClrThresh(3),
               fallWarnThresh(4),
               fallWarnClrThresh(5),
               fallAlmThresh(6),
               fallAlmClrThresh(7)
           }             
        MAX-ACCESS  read-create
        STATUS      current
        DESCRIPTION     
            "The threshold used flag."
        ::= { zxAnBrgIfAlmProfileConfEntry 11 }   
        
    zxAnBrgIfAlmProfileConfRowStatus  OBJECT-TYPE
        SYNTAX      RowStatus
        MAX-ACCESS  read-create
        STATUS      current
        DESCRIPTION     
            "The status of this conceptual row.

             To create a row in this table, a manager must
             set this object to createAndGo(4).
             
             To delete a row in this table, a manager must
             set this object to destroy(6). "
        ::= { zxAnBrgIfAlmProfileConfEntry 50 }
        
--------------------------------------------------------------------------------
-- 6. zxAnBrgIfAlmProfileApplyTable
--------------------------------------------------------------------------------

    zxAnBrgIfAlmProfileApplyTable   OBJECT-TYPE
        SYNTAX      SEQUENCE OF ZxAnBrgIfAlmProfileApplyEntry
        MAX-ACCESS  not-accessible
        STATUS      current
        DESCRIPTION 
             "The performance alarm threshold profile configuration table of 
              the bridge interfaces."             
        ::= { zxAnBrgIfPerfObjects 7 }

    zxAnBrgIfAlmProfileApplyEntry   OBJECT-TYPE
        SYNTAX      ZxAnBrgIfAlmProfileApplyEntry
        MAX-ACCESS  not-accessible
        STATUS      current
        DESCRIPTION 
            "The performance alarm threshold profile configuration entry of 
             the bridge interfaces."
        INDEX   { ifIndex,zxAnSubIfIndex }
        ::= { zxAnBrgIfAlmProfileApplyTable 1 }

    ZxAnBrgIfAlmProfileApplyEntry ::= SEQUENCE {
        zxAnBrgIfAlmPrf                DisplayString,
        zxAnBrgIfAlmPrfApplyRowStatus      RowStatus
        }
        
    zxAnBrgIfAlmPrf  OBJECT-TYPE 
        SYNTAX      DisplayString (SIZE (1..32))
        MAX-ACCESS  read-create
        STATUS      current
        DESCRIPTION     
            "The performance alarm threshold profile."
        ::= { zxAnBrgIfAlmProfileApplyEntry 1 }
               
     zxAnBrgIfAlmPrfApplyRowStatus  OBJECT-TYPE 
        SYNTAX      RowStatus
        MAX-ACCESS  read-create
        STATUS      current
        DESCRIPTION     
            "The status of this conceptual row.

             To create a row in this table, a manager must
             set this object to createAndGo(4).
            
             To delete a row in this table, a manager must
             set this object to destroy(6). "
        ::= { zxAnBrgIfAlmProfileApplyEntry 50 }   
                        
--------------------------------------------------------------------------------
-- 7. zxAnBrgIfAlmProfileTable
--------------------------------------------------------------------------------

    zxAnBrgIfAlmProfileTable   OBJECT-TYPE
        SYNTAX      SEQUENCE OF ZxAnBrgIfAlmProfileEntry
        MAX-ACCESS  not-accessible
        STATUS      current
        DESCRIPTION 
             "The performance alarm threshold profile table of the bridge interfaces.
             It can be used to delete all of the performance alarm threshold profiles
             which has the same name configured in 'zxAnBrgIfAlmProfileConfTable'."
        ::= { zxAnBrgIfPerfObjects 8 }

    zxAnBrgIfAlmProfileEntry   OBJECT-TYPE
        SYNTAX      ZxAnBrgIfAlmProfileEntry
        MAX-ACCESS  not-accessible
        STATUS      current
        DESCRIPTION 
            "The performance alarm threshold profile entry of the bridge interfaces."
        INDEX   { zxAnBrgIfAlmProfileName}
        ::= { zxAnBrgIfAlmProfileTable 1 }

    ZxAnBrgIfAlmProfileEntry ::= SEQUENCE {
        zxAnBrgIfAlmProfileRowStatus   RowStatus
        }       
              
    zxAnBrgIfAlmProfileRowStatus  OBJECT-TYPE
        SYNTAX      RowStatus
        MAX-ACCESS  read-create
        STATUS      current
        DESCRIPTION     
            "The status of this conceptual row.

             To create a profile in this table, a manager must
             set this object to createAndGo(4).
             
             To delete a profile in this table, a manager must
             set this object to destroy(6). "
        ::= { zxAnBrgIfAlmProfileEntry 50 }

-------------------------------------------------------------------------------
-- 8. zxAnBrgIfCurrMinPerfTable
--------------------------------------------------------------------------------

    zxAnBrgIfCurrMinPerfTable    OBJECT-TYPE
        SYNTAX      SEQUENCE OF ZxAnBrgIfCurrMinPerfEntry
        MAX-ACCESS  not-accessible
        STATUS      current
        DESCRIPTION
            "The minutes interval performance data table of the
             bridge interfaces."
        ::= { zxAnBrgIfPerfObjects 9 }

    zxAnBrgIfCurrMinPerfEntry    OBJECT-TYPE
        SYNTAX      ZxAnBrgIfCurrMinPerfEntry
        MAX-ACCESS  not-accessible
        STATUS      current
        DESCRIPTION
            "The minutes interval performance data entry of the
             bridge interfaces."
        INDEX   { ifIndex, zxAnSubIfIndex }
        ::= { zxAnBrgIfCurrMinPerfTable 1 }

    ZxAnBrgIfCurrMinPerfEntry ::= SEQUENCE {
        zxAnBrgIfCMinTimeElapsed            Gauge32,
        zxAnBrgIfCMinInOctets               Counter64,
        zxAnBrgIfCMinInUcastPkts            Counter64,
        zxAnBrgIfCMinInMcastPkts            Counter64,
        zxAnBrgIfCMinInBcastPkts            Counter64,
        zxAnBrgIfCMinOutOctets              Counter64,
        zxAnBrgIfCMinOutUcastPkts           Counter64,
        zxAnBrgIfCMinOutMcastPkts           Counter64,
        zxAnBrgIfCMinOutBcastPkts           Counter64,
        zxAnBrgIfCMinInErroredPktRate       Gauge32,
        zxAnBrgIfCMinInBwUsingRatio         Integer32,
        zxAnBrgIfCMinOutBwUsingRatio        Integer32,
        zxAnBrgIfCMinReset                  INTEGER
        }

    zxAnBrgIfCMinTimeElapsed OBJECT-TYPE
        SYNTAX      Gauge32
        UNITS       "Seconds"
        MAX-ACCESS  read-only
        STATUS      current
        DESCRIPTION
            "Number of seconds that have elapsed since the beginning of the
             current minutes interval."
        ::= { zxAnBrgIfCurrMinPerfEntry 1 }
        
    zxAnBrgIfCMinInOctets    OBJECT-TYPE
        SYNTAX      Counter64
        MAX-ACCESS  read-only
        STATUS      current
        DESCRIPTION
            "The total number of octets received on the interface,
             including framing characters in current minutes interval."
        ::= { zxAnBrgIfCurrMinPerfEntry 2 }

    zxAnBrgIfCMinInUcastPkts    OBJECT-TYPE
        SYNTAX      Counter64
        MAX-ACCESS  read-only
        STATUS      current
        DESCRIPTION
            "The number of packets, delivered by this sub-layer to a
             higher (sub-)layer, which were not addressed to a multicast
             or broadcast address at this sub-layer and in current
             minutes interval."
        ::= { zxAnBrgIfCurrMinPerfEntry 3 }

    zxAnBrgIfCMinInMcastPkts    OBJECT-TYPE 
        SYNTAX      Counter64
        MAX-ACCESS  read-only
        STATUS      current
        DESCRIPTION
            "The number of packets, delivered by this sub-layer to a
             higher (sub-)layer, which were addressed to a multicast
             address at this sub-layer and in current minutes interval.
             For a MAC layer protocol, this includes both Group and
             Functional addresses."
        ::= { zxAnBrgIfCurrMinPerfEntry 4 }

    zxAnBrgIfCMinInBcastPkts    OBJECT-TYPE 
        SYNTAX      Counter64
        MAX-ACCESS  read-only
        STATUS      current
        DESCRIPTION
            "The number of packets, delivered by this sub-layer to a
             higher (sub-)layer, which were addressed to a broadcast
             address at this sub-layer and in current minutes interval."
        ::= { zxAnBrgIfCurrMinPerfEntry 5 }

    zxAnBrgIfCMinOutOctets    OBJECT-TYPE
        SYNTAX      Counter64
        MAX-ACCESS  read-only
        STATUS      current
        DESCRIPTION
            "The total number of octets transmitted out of the interface,
             including framing characters in curent minutes interval."
        ::= { zxAnBrgIfCurrMinPerfEntry 6 }

    zxAnBrgIfCMinOutUcastPkts    OBJECT-TYPE 
        SYNTAX      Counter64
        MAX-ACCESS  read-only
        STATUS      current
        DESCRIPTION
            "The total number of packets that higher-level protocols
             requested be transmitted, and which were not addressed to a
             multicast or broadcast address at this sub-layer, including
             those that were discarded or not sent in current minutes interval."
        ::= { zxAnBrgIfCurrMinPerfEntry 7 }

    zxAnBrgIfCMinOutMcastPkts    OBJECT-TYPE
        SYNTAX      Counter64
        MAX-ACCESS  read-only
        STATUS      current
        DESCRIPTION
            "The total number of packets that higher-level protocols
             requested be transmitted, and which were addressed to a
             multicast address at this sub-layer, including those that
             were discarded or not sent and in current minutes interval.
             For a MAC layer protocol, this includes both Group and
             Functional addresses."
        ::= { zxAnBrgIfCurrMinPerfEntry 8 }

    zxAnBrgIfCMinOutBcastPkts    OBJECT-TYPE
        SYNTAX      Counter64
        MAX-ACCESS  read-only
        STATUS      current
        DESCRIPTION
            "The total number of packets that higher-level protocols
             requested be transmitted, and which were addressed to a
             broadcast address at this sub-layer, including those that
             were discarded or not sent in current minutes interval."
        ::= { zxAnBrgIfCurrMinPerfEntry 9 }

    zxAnBrgIfCMinInErroredPktRate    OBJECT-TYPE
        SYNTAX      Gauge32
        UNITS       "pps"
        MAX-ACCESS  read-only
        STATUS      current
        DESCRIPTION
            "The received errored packet rate in current minutes."
        ::= { zxAnBrgIfCurrMinPerfEntry 50 }

    zxAnBrgIfCMinInBwUsingRatio    OBJECT-TYPE
        SYNTAX      Integer32(0..100)
        UNITS       "percent"
        MAX-ACCESS  read-only
        STATUS      current
        DESCRIPTION
            "An estimate of the interface's current received bandwidth using
             ratio in current minutes."
        ::= { zxAnBrgIfCurrMinPerfEntry 52 }

    zxAnBrgIfCMinOutBwUsingRatio    OBJECT-TYPE
        SYNTAX      Integer32(0..100)
        UNITS       "percent"
        MAX-ACCESS  read-only
        STATUS      current
        DESCRIPTION
            "An estimate of the interface's current transmitted bandwidth using
             ratio in current minutes."
        ::= { zxAnBrgIfCurrMinPerfEntry 53 }

    zxAnBrgIfCMinReset OBJECT-TYPE
        SYNTAX      INTEGER
            {
                perfReset(1)
            }
        MAX-ACCESS  read-write
        STATUS      current
        DESCRIPTION
            "Clear all the current minutes performance variables.
             When get this variable, always return 1."
        ::= { zxAnBrgIfCurrMinPerfEntry 100 }

--------------------------------------------------------------------------------
-- 9. zxAnBrgIfHisMinPerfTable
--------------------------------------------------------------------------------

    zxAnBrgIfHisMinPerfTable    OBJECT-TYPE
        SYNTAX      SEQUENCE OF ZxAnBrgIfHisMinPerfEntry
        MAX-ACCESS  not-accessible
        STATUS      current
        DESCRIPTION 
            "The minutes interval history performance data table of the
             bridge interfaces."
        ::= { zxAnBrgIfPerfObjects 10 }

    zxAnBrgIfHisMinPerfEntry    OBJECT-TYPE
        SYNTAX      ZxAnBrgIfHisMinPerfEntry
        MAX-ACCESS  not-accessible
        STATUS      current
        DESCRIPTION
            "The minutes interval history performance data entry of the
             bridge interfaces."
        INDEX   { ifIndex, zxAnSubIfIndex, zxAnBrgIfHMinIntervalNo }
        ::= { zxAnBrgIfHisMinPerfTable 1 }

    ZxAnBrgIfHisMinPerfEntry ::= SEQUENCE {
        zxAnBrgIfHMinIntervalNo             Integer32,
        zxAnBrgIfHMinIntervalValidData      TruthValue,
        zxAnBrgIfHMinDateTime               DateAndTime,
        zxAnBrgIfHMinInOctets               Counter64,
        zxAnBrgIfHMinInUcastPkts            Counter64,
        zxAnBrgIfHMinInMcastPkts            Counter64,
        zxAnBrgIfHMinInBcastPkts            Counter64,
        zxAnBrgIfHMinOutOctets              Counter64,
        zxAnBrgIfHMinOutUcastPkts           Counter64,
        zxAnBrgIfHMinOutMcastPkts           Counter64,
        zxAnBrgIfHMinOutBcastPkts           Counter64,
        zxAnBrgIfHMinInErroredPktRate       Gauge32,
        zxAnBrgIfHMinInBwUsingRatio         Integer32,
        zxAnBrgIfHMinOutBwUsingRatio        Integer32
        }

    zxAnBrgIfHMinIntervalNo    OBJECT-TYPE
        SYNTAX      Integer32
        MAX-ACCESS  not-accessible
        STATUS      current
        DESCRIPTION
             "Performance data interval number."
        ::= { zxAnBrgIfHisMinPerfEntry 1 }

    zxAnBrgIfHMinIntervalValidData    OBJECT-TYPE
        SYNTAX      TruthValue
        MAX-ACCESS  read-only
        STATUS      current
        DESCRIPTION
             "Performance data valid flag.
              true(1) means valid.
              false(2) means invalidm and the performace data is useless."
        ::= { zxAnBrgIfHisMinPerfEntry 2 }

    zxAnBrgIfHMinDateTime    OBJECT-TYPE
        SYNTAX      DateAndTime
        MAX-ACCESS  read-only
        STATUS      current
        DESCRIPTION
             "The minutes interval performance data generation time."
        ::= { zxAnBrgIfHisMinPerfEntry 3 }

    zxAnBrgIfHMinInOctets    OBJECT-TYPE
        SYNTAX      Counter64
        MAX-ACCESS  read-only
        STATUS      current
        DESCRIPTION
            "The total number of octets received on the interface,
             including framing characters in current historical interval."
        ::= { zxAnBrgIfHisMinPerfEntry 4 }

    zxAnBrgIfHMinInUcastPkts    OBJECT-TYPE
        SYNTAX      Counter64
        MAX-ACCESS  read-only
        STATUS      current
        DESCRIPTION
           "The number of packets, delivered by this sub-layer to a
            higher (sub-)layer, which were not addressed to a multicast
            or broadcast address at this sub-layer and in historical
            minutes interval."
        ::= { zxAnBrgIfHisMinPerfEntry 5 }

    zxAnBrgIfHMinInMcastPkts    OBJECT-TYPE
        SYNTAX      Counter64
        MAX-ACCESS  read-only
        STATUS      current
        DESCRIPTION
            "The number of packets, delivered by this sub-layer to a
             higher (sub-)layer, which were addressed to a multicast
             address at this sub-layer and in historical minutes
             interval.For a MAC layer protocol, this includes both
             Group and Functional addresses."
        ::= { zxAnBrgIfHisMinPerfEntry 6 }

    zxAnBrgIfHMinInBcastPkts    OBJECT-TYPE
        SYNTAX      Counter64
        MAX-ACCESS  read-only
        STATUS      current
        DESCRIPTION
            "The number of packets, delivered by this sub-layer to a
             higher (sub-)layer, which were addressed to a broadcast
             address at this sub-layer and in historical minutes interval."
        ::= { zxAnBrgIfHisMinPerfEntry 7 }

    zxAnBrgIfHMinOutOctets    OBJECT-TYPE
        SYNTAX      Counter64
        MAX-ACCESS  read-only
        STATUS      current
        DESCRIPTION
            "The total number of octets transmitted out of the interface,
             including framing characters in historical minutes interval."
        ::= { zxAnBrgIfHisMinPerfEntry 8 }

    zxAnBrgIfHMinOutUcastPkts    OBJECT-TYPE
        SYNTAX      Counter64
        MAX-ACCESS  read-only
        STATUS      current
        DESCRIPTION
            "The total number of packets that higher-level protocols
             requested be transmitted, and which were not addressed to a
             multicast or broadcast address at this sub-layer, including
             those that were discarded or not sent in historical minutes
             interval."
        ::= { zxAnBrgIfHisMinPerfEntry 9 }

    zxAnBrgIfHMinOutMcastPkts    OBJECT-TYPE
        SYNTAX      Counter64
        MAX-ACCESS  read-only
        STATUS      current
        DESCRIPTION
            "The total number of packets that higher-level protocols
             requested be transmitted, and which were addressed to a
             multicast address at this sub-layer, including those that
             were discarded or not sent and in historical minutes 
             interval.For a MAC layer protocol, this includes both Group
             and Functional addresses."
        ::= { zxAnBrgIfHisMinPerfEntry 10 }

    zxAnBrgIfHMinOutBcastPkts    OBJECT-TYPE
        SYNTAX      Counter64
        MAX-ACCESS  read-only
        STATUS      current
        DESCRIPTION
            "The total number of packets that higher-level protocols
             requested be transmitted, and which were addressed to a
             broadcast address at this sub-layer, including those that
             were discarded or not sent in historical minutes interval."
        ::= { zxAnBrgIfHisMinPerfEntry 11 }

    zxAnBrgIfHMinInErroredPktRate    OBJECT-TYPE
        SYNTAX      Gauge32
        UNITS       "pps"
        MAX-ACCESS  read-only
        STATUS      current
        DESCRIPTION
            "The received errored packet rate in historical minutes."
        ::= { zxAnBrgIfHisMinPerfEntry 50 }

    zxAnBrgIfHMinInBwUsingRatio    OBJECT-TYPE
        SYNTAX      Integer32(0..100)
        UNITS       "percent"
        MAX-ACCESS  read-only
        STATUS      current
        DESCRIPTION
            "An estimate of the interface's received bandwidth using ratio
             in historical minutes."
        ::= { zxAnBrgIfHisMinPerfEntry 52 }

    zxAnBrgIfHMinOutBwUsingRatio    OBJECT-TYPE
        SYNTAX      Integer32(0..100)
        UNITS       "percent"
        MAX-ACCESS  read-only
        STATUS      current
        DESCRIPTION
            "An estimate of the interface's transmitted bandwidth using ratio
             in historical minutes."
        ::= { zxAnBrgIfHisMinPerfEntry 53 }

--------------------------------------------------------------------------------
--31 zxAnBrgIfPerfConformance
--------------------------------------------------------------------------------

    zxAnBrgIfPerfConformance      OBJECT IDENTIFIER ::= { zxAnInterfaceBrgPerfMib 4 }     

    zxAnBrgIfPerfCompliances      OBJECT IDENTIFIER ::= { zxAnBrgIfPerfConformance 1 }
    zxAnBrgIfPerfGroups           OBJECT IDENTIFIER ::= { zxAnBrgIfPerfConformance 2 }  
    
    zxAnBrgIfPerfCompliance MODULE-COMPLIANCE
        STATUS      current
        DESCRIPTION 
            "The compliance statement for entities which implement the
             ZTE-AN-INTERFACE-BRG-PERF-MIB."
    
        MODULE       -- this module
            MANDATORY-GROUPS { 
                   zxAnBrgIfPerfCurr15MinGroup,
                   zxAnBrgIfPerfCurr1DayGroup,
                   zxAnBrgIfPerfHis15MinGroup,
                   zxAnBrgIfPerfHis1DayGroup,
                   zxAnBrgIfPerfAlmProfileGroup,
                   zxAnBrgIfPerfCurrMinGroup,
                   zxAnBrgIfPerfHisMinGroup
                   }
        ::= { zxAnBrgIfPerfCompliances 1 }
    
-- Units of compliance
         
    zxAnBrgIfPerfCurr15MinGroup OBJECT-GROUP
        OBJECTS {
            zxAnBrgIfC15MTimeElapsed,
            zxAnBrgIfC15MInOctets,
            zxAnBrgIfC15MInUcastPkts,
            zxAnBrgIfC15MInMcastPkts,
            zxAnBrgIfC15MInBcastPkts,
            zxAnBrgIfC15MOutOctets,
            zxAnBrgIfC15MOutUcastPkts,
            zxAnBrgIfC15MOutMcastPkts,
            zxAnBrgIfC15MOutBcastPkts,
            zxAnBrgIfC15MReset 
        }
        STATUS  current
        DESCRIPTION 
            "A collection of objects providing for 15 minutes interval 
             performance data of interfaces."
        ::= { zxAnBrgIfPerfGroups 1 }
        
    zxAnBrgIfPerfCurr1DayGroup OBJECT-GROUP
        OBJECTS {
            zxAnBrgIfC1DTimeElapsed,
            zxAnBrgIfC1DInOctets,
            zxAnBrgIfC1DInUcastPkts,
            zxAnBrgIfC1DInMcastPkts,
            zxAnBrgIfC1DInBcastPkts,
            zxAnBrgIfC1DOutOctets,
            zxAnBrgIfC1DOutUcastPkts,
            zxAnBrgIfC1DOutMcastPkts,
            zxAnBrgIfC1DOutBcastPkts,
            zxAnBrgIfC1DReset  
        }
        STATUS  current
        DESCRIPTION 
            "A collection of objects providing 1 day interval performance data 
             of interfaces."
        ::= { zxAnBrgIfPerfGroups 2 }                

    zxAnBrgIfPerfHis15MinGroup OBJECT-GROUP
        OBJECTS {
            zxAnBrgIfH15MIntervalValidData,
            zxAnBrgIfH15MDateTime,
            zxAnBrgIfH15MInOctets,
            zxAnBrgIfH15MInUcastPkts,
            zxAnBrgIfH15MInMcastPkts,
            zxAnBrgIfH15MInBcastPkts,
            zxAnBrgIfH15MOutOctets,
            zxAnBrgIfH15MOutUcastPkts,
            zxAnBrgIfH15MOutMcastPkts,
            zxAnBrgIfH15MOutBcastPkts
        }
        STATUS  current
        DESCRIPTION 
            "A collection of objects providing for 15 minutes interval 
             performance data of interfaces."
        ::= { zxAnBrgIfPerfGroups 3 }
        
    zxAnBrgIfPerfHis1DayGroup OBJECT-GROUP
        OBJECTS {
            zxAnBrgIfH1DIntervalValidData,
            zxAnBrgIfH1DDateTime,
            zxAnBrgIfH1DInOctets,
            zxAnBrgIfH1DInUcastPkts,
            zxAnBrgIfH1DInMcastPkts,
            zxAnBrgIfH1DInBcastPkts,
            zxAnBrgIfH1DOutOctets,
            zxAnBrgIfH1DOutUcastPkts,
            zxAnBrgIfH1DOutMcastPkts,
            zxAnBrgIfH1DOutBcastPkts
        }
        STATUS  current
        DESCRIPTION 
            "A collection of objects providing 1 day interval performance data 
             of interfaces."
        ::= { zxAnBrgIfPerfGroups 4 }   
        
    zxAnBrgIfPerfAlmProfileGroup OBJECT-GROUP
        OBJECTS {
            zxAnBrgIfRiseAlmThresh,
            zxAnBrgIfClrRiseAlmThresh,        
            zxAnBrgIfRiseWarnThresh,  
            zxAnBrgIfClrRiseWarnThresh,        
            zxAnBrgIfFallWarnThresh, 
            zxAnBrgIfClrFallWarnThresh, 
            zxAnBrgIfFallAlmThresh,
            zxAnBrgIfClrFallAlmThresh,
            zxAnBrgIfAlmProfileConfRowStatus
        }
        STATUS  current
        DESCRIPTION 
            "A collection of objects providing for performance alarm threshold 
             profile of interfaces."
        ::= { zxAnBrgIfPerfGroups 5 }   
        
    zxAnBrgIfAlmProfileApplyGroup OBJECT-GROUP
        OBJECTS {
            zxAnBrgIfAlmPrf,
            zxAnBrgIfAlmPrfApplyRowStatus
        }
        STATUS  current
        DESCRIPTION 
            "A collection of objects providing for performance alarm threshold 
             profile apply control configuration information."            
        ::= { zxAnBrgIfPerfGroups 6 }   
 
    zxAnBrgIfAlmProfileGroup OBJECT-GROUP
        OBJECTS {
            zxAnBrgIfAlmProfileRowStatus
        }
        STATUS  current
        DESCRIPTION 
            "A collection of objects providing for performance alarm threshold 
             profile  configuration information."            
        ::= { zxAnBrgIfPerfGroups 7 }
    
  zxAnBrgIfPerfCurrMinGroup OBJECT-GROUP
        OBJECTS {
            zxAnBrgIfCMinTimeElapsed,
            zxAnBrgIfCMinInOctets,
            zxAnBrgIfCMinInUcastPkts,
            zxAnBrgIfCMinInMcastPkts,
            zxAnBrgIfCMinInBcastPkts,
            zxAnBrgIfCMinOutOctets,
            zxAnBrgIfCMinOutUcastPkts,
            zxAnBrgIfCMinOutMcastPkts,
            zxAnBrgIfCMinOutBcastPkts,
            zxAnBrgIfCMinReset 
        }
        STATUS  current
        DESCRIPTION 
            "A collection of objects providing for minutes interval 
             performance data of interfaces."
        ::= { zxAnBrgIfPerfGroups 8 }

  zxAnBrgIfPerfHisMinGroup OBJECT-GROUP
        OBJECTS {
            zxAnBrgIfHMinIntervalValidData,
            zxAnBrgIfHMinDateTime,
            zxAnBrgIfHMinInOctets,
            zxAnBrgIfHMinInUcastPkts,
            zxAnBrgIfHMinInMcastPkts,
            zxAnBrgIfHMinInBcastPkts,
            zxAnBrgIfHMinOutOctets,
            zxAnBrgIfHMinOutUcastPkts,
            zxAnBrgIfHMinOutMcastPkts,
            zxAnBrgIfHMinOutBcastPkts
        }
        STATUS  current
        DESCRIPTION 
            "A collection of objects providing for minutes interval 
             performance data of interfaces."
        ::= { zxAnBrgIfPerfGroups 9 }
END
