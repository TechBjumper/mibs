-- Teldat, S.A.

                -- Parque Tecnolgico de Madrid

                -- 28760, Tres Cantos (Madrid)

                -- Tlf: +34-918076565

                -- Fax: +34-918076521

                -- e-mail: id@teldat.com


                -- MIB privada de Teldat

                -- MIB de configuracin de GW IEC104/101.


    -- Historial:
    --      07/02/14  M.A. Pastor      XH 3523. Errors with HP Openview 9.20
    -- 1.3  11-01-13    E. Amorena      XH 2610. MIBs compilation.
    -- 1.2  03/01/13  F. Hernandez     XH 2610. Compilation error
    -- 1.1  21/12/11  Benjamin G.      Soporte de varias direcc. IP por C.C.
    -- 1.0  15/04/11  Benjamin G.      Implementacin inicial

    --------------------------------------------------------------------------

TELDAT-CFG-PROTOCOL-GW104-MIB DEFINITIONS ::= BEGIN

-- Tipos importados

    IMPORTS
        IpAddress
            FROM RFC1155-SMI

        OBJECT-TYPE
            FROM RFC-1212

        DisplayString
            FROM RFC1213-MIB

        telProdNpConfProtocol
            FROM TELDAT-SW-STRUCTURE-MIB;


    -- telProdNpConfProtGW104 group

    telProdNpConfProtGW104          OBJECT IDENTIFIER ::= { telProdNpConfProtocol 14 }


--  = = = = = = = = = = = = = = = = = = = = = = = = = = = = = = = = = = = = = =
--  GW104 global configuration variables
--  = = = = = = = = = = = = = = = = = = = = = = = = = = = = = = = = = = = = = =

  -- Grupo telProdNpGW104Global

    telProdNpGW104Global OBJECT IDENTIFIER ::= { telProdNpConfProtGW104 1 }

    telProdNpGW104GloEnable OBJECT-TYPE
        SYNTAX  INTEGER {
            disabled(0),
            enabled(1)
            }
        ACCESS  read-write
        STATUS  mandatory
        DESCRIPTION
            "Enables Gateway IEC-104/101 operation."
        ::={ telProdNpGW104Global 1 }

    telProdNpGW104Glo101-On OBJECT-TYPE
        SYNTAX  INTEGER {
            disabled(0),
            enabled(1)
            }
        ACCESS  read-write
        STATUS  mandatory
        DESCRIPTION
            "Enables IEC-101 operation regardless IEC-104 agents status."
        ::={ telProdNpGW104Global 2 }

    telProdNpGW104Glo104-On OBJECT-TYPE
        SYNTAX  INTEGER {
            disabled(0),
            enabled(1)
            }
        ACCESS  read-write
        STATUS  mandatory
        DESCRIPTION
            "Enables IEC-104 agents operation regardless IEC-101
             interfaces status."
        ::={ telProdNpGW104Global 3 }

    telProdNpGW104GloASDUComAddr OBJECT-TYPE
        SYNTAX  INTEGER (1..65534)
        ACCESS  read-write
        STATUS  mandatory
        DESCRIPTION
            "Set ASDU Common Address field value."
        ::={ telProdNpGW104Global 4 }

    telProdNpGW104GloASDUComAddrSz OBJECT-TYPE
        SYNTAX  INTEGER (1..2)
        ACCESS  read-write
        STATUS  mandatory
        DESCRIPTION
            "Set ASDU Common Address field size."
        ::={ telProdNpGW104Global 5 }

    telProdNpGW104GloCauseTransfSz OBJECT-TYPE
        SYNTAX  INTEGER (1..2)
        ACCESS  read-write
        STATUS  mandatory
        DESCRIPTION
            "Set Cause of Transfer field size."
        ::={ telProdNpGW104Global 6 }

    telProdNpGW104GloInfoObjAddrSz OBJECT-TYPE
        SYNTAX  INTEGER (1..3)
        ACCESS  read-write
        STATUS  mandatory
        DESCRIPTION
            "Set Information Object Address field size."
        ::={ telProdNpGW104Global 7 }

    telProdNpGW104GloIoa10000 OBJECT-TYPE
        SYNTAX  INTEGER {
            disabled(0),
            enabled(1)
            }
        ACCESS  read-write
        STATUS  mandatory
        DESCRIPTION
            "Enable use of IOA 10000."
        ::={ telProdNpGW104Global 8 }

    telProdNpGW104GloIoa10007 OBJECT-TYPE
        SYNTAX  INTEGER {
            disabled(0),
            enabled(1)
            }
        ACCESS  read-write
        STATUS  mandatory
        DESCRIPTION
            "Enable use of IOA 10007."
        ::={ telProdNpGW104Global 9 }

    telProdNpGW104GloOrigFilter OBJECT-TYPE
        SYNTAX  INTEGER {
            disabled(0),
            enabled(1)
            }
        ACCESS  read-write
        STATUS  mandatory
        DESCRIPTION
            "Enable originator address filter for messages received from
             Control Center ."
        ::={ telProdNpGW104Global 10 }


--  = = = = = = = = = = = = = = = = = = = = = = = = = = = = = = = = = = = = = =
--  GW104 agents configuration global variables
--  = = = = = = = = = = = = = = = = = = = = = = = = = = = = = = = = = = = = = =

  -- Grupo telProdNpGW104Agent



    telProdNpGW104AgentTable OBJECT-TYPE
        SYNTAX  SEQUENCE OF TelProdNpGW104AgentEntry
        ACCESS  not-accessible
        STATUS  mandatory
        DESCRIPTION
            "Agents list. The table index is the Agent position."
        ::= { telProdNpConfProtGW104 2 }

   telProdNpGW104AgentEntry OBJECT-TYPE
        SYNTAX  TelProdNpGW104AgentEntry
        ACCESS  not-accessible
        STATUS  mandatory
        DESCRIPTION
            "Each entry consists in an IEC-104 Agent.  Each entry contains the
             corresponding IEC-104 agent configuration."
        INDEX   { telProdNpGW104AgentIndex }
        ::={ telProdNpGW104AgentTable 1 }

    TelProdNpGW104AgentEntry ::=
        SEQUENCE{
            telProdNpGW104AgentIndex        INTEGER,
            telProdNpGW104AgentStatus       INTEGER,
            telProdNpGW104AgentName         DisplayString,
            telProdNpGW104AgentAlarmBuf     INTEGER,
            telProdNpGW104AgentK            INTEGER,
            telProdNpGW104AgentLocTcpPort   INTEGER,
            telProdNpGW104AgentT0           INTEGER,
            telProdNpGW104AgentT1           INTEGER,
            telProdNpGW104AgentT2           INTEGER,
            telProdNpGW104AgentT3           INTEGER,
            telProdNpGW104AgentW            INTEGER,
            telProdNpGW104AgentVrf          DisplayString
        }

    telProdNpGW104AgentIndex OBJECT-TYPE
        SYNTAX  INTEGER
        ACCESS  read-only
        STATUS  mandatory
        DESCRIPTION
            "IEC-104 agent position in the table."
        ::={ telProdNpGW104AgentEntry 1 }

    telProdNpGW104AgentStatus OBJECT-TYPE
        SYNTAX  INTEGER{
            valid(1),
            add(2),
            delete(3)
            }
        ACCESS  read-write
        STATUS  mandatory
        DESCRIPTION
            "Table control variable.
            Set to 1 does nothing.
            Set to 2 adds a new row (IEC-104 Agent) in the table with default
            values and returns 2. If it already exists, then it returns error.
            It must be added immediately after the last index.
            Set to 3 deletes all table fields corresponding to that Agent,
            and returns 3.
            Get returns 1 if the control exists."
        ::={ telProdNpGW104AgentEntry 2 }

    telProdNpGW104AgentName OBJECT-TYPE
        SYNTAX  DisplayString(SIZE(1..20))
        ACCESS  read-write
        STATUS  mandatory
        DESCRIPTION
            "IEC-104 agent name. Agents names must be different, can not be
             repeated. If name already exists, then it returns error."
        ::={ telProdNpGW104AgentEntry 3 }

    telProdNpGW104AgentAlarmBuf OBJECT-TYPE
        SYNTAX  INTEGER(1..64)
        ACCESS  read-write
        STATUS  mandatory
        DESCRIPTION
            "Alarm buffer queue length."
        ::={ telProdNpGW104AgentEntry 4 }

    telProdNpGW104AgentK OBJECT-TYPE
        SYNTAX  INTEGER(1..33767)
        ACCESS  read-write
        STATUS  mandatory
        DESCRIPTION
            "Max. number of IEC-104 send messages without confirmation."
        ::={ telProdNpGW104AgentEntry 5 }

    telProdNpGW104AgentLocTcpPort OBJECT-TYPE
        SYNTAX  INTEGER(1..65535)
        ACCESS  read-write
        STATUS  mandatory
        DESCRIPTION
            "Local TCP port for IEC-104 agent listen."
        ::={ telProdNpGW104AgentEntry 6 }

    telProdNpGW104AgentT0 OBJECT-TYPE
        SYNTAX  INTEGER(1..255)
        ACCESS  read-write
        STATUS  mandatory
        DESCRIPTION
            "T0 defined by IEC-104, establish connection timeout.
             Value indicates in seconds."
        ::={ telProdNpGW104AgentEntry 7 }

    telProdNpGW104AgentT1 OBJECT-TYPE
        SYNTAX  INTEGER(1..255)
        ACCESS  read-write
        STATUS  mandatory
        DESCRIPTION
            "T1 defined by IEC-104, SEND or TEST APDU type timeout.
             Value indicates in seconds."
        ::={ telProdNpGW104AgentEntry 8 }

    telProdNpGW104AgentT2 OBJECT-TYPE
        SYNTAX  INTEGER(1..255)
        ACCESS  read-write
        STATUS  mandatory
        DESCRIPTION
            "T2 defined by IEC-104, data message confirmation timeout.
             Value indicates in seconds."
        ::={ telProdNpGW104AgentEntry 9 }

    telProdNpGW104AgentT3 OBJECT-TYPE
        SYNTAX  INTEGER(1..255)
        ACCESS  read-write
        STATUS  mandatory
        DESCRIPTION
            "T3 defined by IEC-104, sending S message timeout on long inactivity
             periods. Value indicates in seconds."
        ::={ telProdNpGW104AgentEntry 10 }

    telProdNpGW104AgentW OBJECT-TYPE
        SYNTAX  INTEGER(1..33767)
        ACCESS  read-write
        STATUS  mandatory
        DESCRIPTION
            "Max. number of IEC-104 received messages  confirmed."
        ::={ telProdNpGW104AgentEntry 11 }

    telProdNpGW104AgentVrf OBJECT-TYPE
        SYNTAX  DisplayString(SIZE(1..32))
        ACCESS  read-write
        STATUS  mandatory
        DESCRIPTION
            "VRF name. If VRF is configured on router, can be asociate in
            agent. Return error if VRF name don't exist."
        ::={ telProdNpGW104AgentEntry 12 }


--  = = = = = = = = = = = = = = = = = = = = = = = = = = = = = = = = = = = = = =
--  GW104 agents configuration Control Center IP variables
--  = = = = = = = = = = = = = = = = = = = = = = = = = = = = = = = = = = = = = =

  -- Grupo telProdNpGW104AgentCcIp



    telProdNpGW104AgentCcIpTable OBJECT-TYPE
        SYNTAX  SEQUENCE OF TelProdNpGW104AgentCcIpEntry
        ACCESS  not-accessible
        STATUS  mandatory
        DESCRIPTION
            "Agents list. The table index is the Agent position."
        ::= { telProdNpConfProtGW104 3 }

   telProdNpGW104AgentCcIpEntry OBJECT-TYPE
        SYNTAX  TelProdNpGW104AgentCcIpEntry
        ACCESS  not-accessible
        STATUS  mandatory
        DESCRIPTION
            " Each entry contains a Control Center IP address for an IEC-104
              Agent. First index indicates IEC-104 Agent this value must correspond
              with same in Agent global parameters table. The second table index
              indicates the order number of that Control Center IP address inside
              that Agent."
        INDEX   { telProdNpGW104AgentCcIpAgIndex, telProdNpGW104AgentCcIpIndex }
        ::={ telProdNpGW104AgentCcIpTable 1 }

    TelProdNpGW104AgentCcIpEntry ::=
        SEQUENCE{
            telProdNpGW104AgentCcIpAgIndex  INTEGER,
            telProdNpGW104AgentCcIpIndex    INTEGER,
            telProdNpGW104AgentCcIpStatus   INTEGER,
            telProdNpGW104AgentCcIpAddr     IpAddress
        }

    telProdNpGW104AgentCcIpAgIndex OBJECT-TYPE
        SYNTAX  INTEGER
        ACCESS  read-only
        STATUS  mandatory
        DESCRIPTION
            "IEC-104 agent position index, must be the same that agents table."
        ::={ telProdNpGW104AgentCcIpEntry 1 }

    telProdNpGW104AgentCcIpIndex OBJECT-TYPE
        SYNTAX  INTEGER
        ACCESS  read-only
        STATUS  mandatory
        DESCRIPTION
            "Control Center IP address position in the table."
        ::={ telProdNpGW104AgentCcIpEntry 2 }

    telProdNpGW104AgentCcIpStatus OBJECT-TYPE
        SYNTAX  INTEGER{
            valid(1),
            delete(2)
            }
        ACCESS  read-write
        STATUS  mandatory
        DESCRIPTION
            "Table control variable.
             Set to 1 does nothing.
             Set to 2 deletes corresponding Control Center IP address to that Agent.
             Get returns 1 if the control exists.
             It returns ERROR if agent don't exist, index don't was greated."
        ::={ telProdNpGW104AgentCcIpEntry 3 }

    telProdNpGW104AgentCcIpAddr OBJECT-TYPE
        SYNTAX  IpAddress
        ACCESS  read-write
        STATUS  mandatory
        DESCRIPTION
            "Control Center IP address for IEC-104 agents filter. Adding a new IP
            address, that don't exist in the table, create a new row in the table."
        ::={ telProdNpGW104AgentCcIpEntry 4 }


END
