-- =================================================================
-- Copyright (C) 2003 by  HUAWEI TECHNOLOGIES. All rights reserved.
--
-- Description:HUAWEI-BRAS-SRVCFGINTERFACE-MIB
-- Reference:
-- Version: V1.0
-- History:
--       
-- =================================================================

        HUAWEI-BRAS-SRVCFGINTERFACE-MIB DEFINITIONS ::= BEGIN
 
                IMPORTS
                        hwBRASMib                     
                                FROM HUAWEI-MIB
                        InterfaceIndex                  
                                FROM IF-MIB                     
                        IpAddress, Integer32, OBJECT-TYPE                       
                                FROM SNMPv2-SMI                 
                        RowStatus, MacAddress, TruthValue, DisplayString                        
                                FROM SNMPv2-TC
                        EnabledStatus
                                FROM P-BRIDGE-MIB;
        
                hwBRASSrvcfgInterface MODULE-IDENTITY 
                        LAST-UPDATED "200403041608Z"
                        ORGANIZATION 
                                "
                                Huawei Technologies Co., Ltd.
                                "
                CONTACT-INFO 
                        "
                        NanJing Institute,Huawei Technologies Co.,Ltd.
                        HuiHong Mansion,No.91 BaiXia Rd.
                        NanJing, P.R. of China
                        Zipcode:210001
                         
                        Http://www.huawei.com                                       
                        E-mail:support@huawei.com 
                        "
            
                DESCRIPTION 
                        "The MIB contains objects of module SRVCFG INTERFACE."
                ::= { hwBRASMib 1 }
        
                hwSrvcfgInterfaceMibObjects OBJECT IDENTIFIER ::= { hwBRASSrvcfgInterface 1 }
                
                hwBRASIfCfgTable OBJECT-TYPE
                        SYNTAX SEQUENCE OF HwBRASIfCfgEntry
                        MAX-ACCESS not-accessible
                        STATUS current
                        DESCRIPTION
                                "
                                
                                "
                        ::= { hwSrvcfgInterfaceMibObjects 1 }
                
                hwBRASIfCfgEntry OBJECT-TYPE
                        SYNTAX HwBRASIfCfgEntry
                        MAX-ACCESS not-accessible
                        STATUS current
                        DESCRIPTION
                                "
                                Description.
                                "
                        INDEX { hwBRASIfCfgIfIndex }
                        ::= { hwBRASIfCfgTable 1 }

                HwBRASIfCfgEntry ::=
                        SEQUENCE { 
                            hwBRASIfCfgIfIndex
                                    InterfaceIndex,
                            hwBRASIfCfgAccessType
                                    INTEGER,
                            hwBRASIfCfgBRASIfName
                                    DisplayString,
                            hwBRASIfCfgPreAuthDomain
                                    DisplayString,
                            hwBRASIfCfgAuthDomain
                                    DisplayString,
                            hwBRASIfCfgForceAuthDomain
                                    INTEGER,
                            hwBRASIfCfgAcctCpyRdSvr
                                    DisplayString,
                            hwBRASIfCfgAuthMethod
                                    INTEGER,
                            hwBRASIfCfgNasPortType
                                    INTEGER,
                            hwBRASIfCfgLeaseName
                                    DisplayString,
                            hwBRASIfCfgLeasePwd
                                    DisplayString,
                            hwBRASIfCfgArpInterval
                                    INTEGER,
                            hwBRASIfCfgArpFailTimes  
                                    INTEGER,
                            hwBRASIfCfgArpProxy
                                    TruthValue,
                            hwBRASIfCfgRoamIsp
                                    TruthValue,                                    
                            hwBRASIfCfgDhcpBroadCast
                                    TruthValue,
                            hwBRASIfCfgHostCar
                                    INTEGER,
                            hwBRASIfCfgRowStatus
                                    RowStatus,
                            hwBRASIfCfgEapTrigger
                                    TruthValue,
                            hwBRASIfCfgWlanSwitch
                                    INTEGER,
                            hwBRASIfCfgWlanAuthorization
                                    TruthValue,
                            hwBRASIfCfgDhcpShortLease
                                    INTEGER,
                            hwBRASIfCfgRoamDomain
                                    DisplayString,
                            hwBRASIfVsiName
                                    DisplayString,
                            hwBRASIfCfgOption82
                                    TruthValue,
                            hwBRASIfVpnInstance
                                    DisplayString,
                            hwBRASIfCopyMulticasePerUser
                                    TruthValue,
                            hwBRASIfCfgNDProxy
                                    TruthValue,
                            hwBRASIfCfgVBasMAC
                                    MacAddress,
                            hwBRASIfCfgVBasAuthMode
                                    INTEGER,
                            hwBRASIfCfgPermitDomain1
                                    DisplayString,
                            hwBRASIfCfgPermitDomain2
                                    DisplayString,
                            hwBRASIfCfgPermitDomain3
                                    DisplayString,
                            hwBRASIfCfgPermitDomain4
                                    DisplayString,                            
                            hwBRASIfCfgAccessDelayType
                                INTEGER,
                            hwBRASIfCfgTermlessDelayTime
                                INTEGER,
                            hwBRASIfCfgOddMacDelayTime
                                INTEGER,
                            hwBRASIfCfgEvenMacDelayTime
                                INTEGER,
                            hwBRASIfCfgAccessNodeIdentify
                                DisplayString,
                            hwBRASIfCfgAniDelayTime
                                INTEGER,
                            hwBRASIfCfgRemoteBackupProfile
                                    DisplayString   
                        }

                hwBRASIfCfgIfIndex OBJECT-TYPE
                    SYNTAX InterfaceIndex
                    MAX-ACCESS read-only
                    STATUS current
                    DESCRIPTION
                        "
                        
                        "
                    ::= { hwBRASIfCfgEntry 1 }

                hwBRASIfCfgAccessType OBJECT-TYPE
                    SYNTAX INTEGER
                        {
                        interface(0),
                        l2subscriber(1),
                        l2leasedline(2),
                        l3leasedline(3),
                        l3subscriber(6)
                        }
                    MAX-ACCESS read-write
                    STATUS current
                    DESCRIPTION
                        "
                        
                        "
                    ::= { hwBRASIfCfgEntry 2 }

                hwBRASIfCfgBRASIfName OBJECT-TYPE
                    SYNTAX DisplayString(SIZE(1..32))
                    MAX-ACCESS read-write
                    STATUS current
                    DESCRIPTION
                        "
                        
                        "
                    ::= { hwBRASIfCfgEntry 3 }

                hwBRASIfCfgPreAuthDomain OBJECT-TYPE
                    SYNTAX DisplayString (SIZE(1..64))
                    MAX-ACCESS read-write
                    STATUS current
                    DESCRIPTION
                        "
                        "
                    ::= { hwBRASIfCfgEntry 4 }

                hwBRASIfCfgAuthDomain OBJECT-TYPE
                    SYNTAX DisplayString (SIZE(1..64))
                    MAX-ACCESS read-write
                    STATUS current
                    DESCRIPTION
                        "
                        "
                    ::= { hwBRASIfCfgEntry 5 }

                hwBRASIfCfgForceAuthDomain OBJECT-TYPE
                    SYNTAX INTEGER
                    {
                none(0),
                force(1),
                replace(2)
                }
                    MAX-ACCESS read-write
                    STATUS current
                    DESCRIPTION
                        "
                        "
                    DEFVAL {0}
                    ::= { hwBRASIfCfgEntry 6}
                    
                hwBRASIfCfgAcctCpyRdSvr OBJECT-TYPE
                    SYNTAX DisplayString (SIZE(1..32))
                    MAX-ACCESS read-write
                    STATUS current
                    DESCRIPTION
                        "
                        "
                    ::= { hwBRASIfCfgEntry 7 }

                hwBRASIfCfgAuthMethod OBJECT-TYPE
                    SYNTAX INTEGER(1..16)
                    MAX-ACCESS read-write
                    STATUS current
                    DESCRIPTION
                        "
                        "
                    DEFVAL {1}
                    ::= { hwBRASIfCfgEntry 8}
                        
                hwBRASIfCfgNasPortType OBJECT-TYPE
                    SYNTAX INTEGER(0..20)
                    MAX-ACCESS read-write
                    STATUS current
                    DESCRIPTION
                        "
                        "
                    ::= { hwBRASIfCfgEntry 9 }

                hwBRASIfCfgLeaseName OBJECT-TYPE
                    SYNTAX DisplayString (SIZE(1..129))
                    MAX-ACCESS read-write
                    STATUS current
                    DESCRIPTION
                        "
                        "
                    ::= { hwBRASIfCfgEntry 10 }

                hwBRASIfCfgLeasePwd OBJECT-TYPE
                    SYNTAX DisplayString (SIZE(1..128))
                    MAX-ACCESS read-write
                    STATUS current
                    DESCRIPTION
                        "
                        "
                    ::= { hwBRASIfCfgEntry 11 }

                hwBRASIfCfgArpInterval OBJECT-TYPE
                    SYNTAX INTEGER(0..121)
                    MAX-ACCESS read-write
                    STATUS current
                    DESCRIPTION
                        "
                        "
                    DEFVAL { 30 }
                    ::= { hwBRASIfCfgEntry 12 }

                hwBRASIfCfgArpFailTimes OBJECT-TYPE
                    SYNTAX INTEGER(2..11)
                    MAX-ACCESS read-write
                    STATUS current
                    DESCRIPTION
                        "
                        "
                    DEFVAL { 5 }
                    ::= { hwBRASIfCfgEntry 13 }

                hwBRASIfCfgArpProxy OBJECT-TYPE
                    SYNTAX TruthValue
                    MAX-ACCESS read-write
                    STATUS current
                    DESCRIPTION
                        "
                        "
                    DEFVAL { false }
                    ::= { hwBRASIfCfgEntry 14 }

                hwBRASIfCfgRoamIsp OBJECT-TYPE
                    SYNTAX TruthValue
                    MAX-ACCESS read-write
                    STATUS current
                    DESCRIPTION
                        "
                        "
                    DEFVAL { false }
                    ::= { hwBRASIfCfgEntry 15 }

                hwBRASIfCfgDhcpBroadCast OBJECT-TYPE
                    SYNTAX TruthValue
                    MAX-ACCESS read-write
                    STATUS current
                    DESCRIPTION
                        "
                        "
                    DEFVAL { false }
                    ::= { hwBRASIfCfgEntry 16 }

                hwBRASIfCfgHostCar OBJECT-TYPE
                    SYNTAX INTEGER(0..16)
                    MAX-ACCESS read-write
                    STATUS current
                    DESCRIPTION
                        "
                        "
                    DEFVAL { 0 }
                    ::= { hwBRASIfCfgEntry 17 }
                    
                hwBRASIfCfgRowStatus OBJECT-TYPE
                    SYNTAX RowStatus
                    MAX-ACCESS read-write
                    STATUS current
                    DESCRIPTION
                        "
                        "
                    ::= { hwBRASIfCfgEntry 18 }
                    
                hwBRASIfCfgEapTrigger OBJECT-TYPE
                    SYNTAX TruthValue
                    MAX-ACCESS read-write
                    STATUS current
                    DESCRIPTION
                        "
                        "
                    DEFVAL { false }
                    ::= { hwBRASIfCfgEntry 19 }
                    
                hwBRASIfCfgWlanSwitch OBJECT-TYPE
                    SYNTAX INTEGER(0..1)
                    MAX-ACCESS read-write
                    STATUS current
                    DESCRIPTION
                        "
                        "
                    DEFVAL { 0 }
                    ::= { hwBRASIfCfgEntry 20 }
                    
                hwBRASIfCfgWlanAuthorization OBJECT-TYPE
                    SYNTAX TruthValue
                    MAX-ACCESS read-write
                    STATUS current
                    DESCRIPTION
                        "
                        "
                    DEFVAL { false }
                    ::= { hwBRASIfCfgEntry 21 }
                    
                hwBRASIfCfgDhcpShortLease OBJECT-TYPE
                    SYNTAX INTEGER(9..240)
                    MAX-ACCESS read-write
                    STATUS current
                    DESCRIPTION
                        "
                        "
                    DEFVAL { 9 }
                    ::= { hwBRASIfCfgEntry 22 }
                
                hwBRASIfCfgRoamDomain OBJECT-TYPE
                    SYNTAX DisplayString (SIZE(1..64))
                    MAX-ACCESS read-write
                    STATUS current
                    DESCRIPTION
                        "
                        "
                    ::= { hwBRASIfCfgEntry 23 }
                    
                hwBRASIfVsiName OBJECT-TYPE
                    SYNTAX DisplayString (SIZE(1..20))
                    MAX-ACCESS read-write
                    STATUS current
                    DESCRIPTION
                        "
                        VSI Name
                        "
                    ::= { hwBRASIfCfgEntry 24 }
                    
                hwBRASIfCfgOption82 OBJECT-TYPE
                    SYNTAX TruthValue
                    MAX-ACCESS read-write
                    STATUS current
                    DESCRIPTION
                        "
                        option82 switch
                        "
                    DEFVAL { false }
                    ::= { hwBRASIfCfgEntry 25 }
                    
                hwBRASIfVpnInstance OBJECT-TYPE
                    SYNTAX DisplayString (SIZE(1..31))
                    MAX-ACCESS read-write
                    STATUS current
                    DESCRIPTION
                        "
                        vpn-instance name
                        "
                    ::= { hwBRASIfCfgEntry 26 }                    
                    
                hwBRASIfCopyMulticasePerUser OBJECT-TYPE
                    SYNTAX TruthValue
                    MAX-ACCESS read-write
                    STATUS current
                    DESCRIPTION
                        "
                        "
                    DEFVAL { false }
                    ::= { hwBRASIfCfgEntry 27 }

                hwBRASIfCfgNDProxy OBJECT-TYPE
                    SYNTAX TruthValue
                    MAX-ACCESS read-write
                    STATUS current
                    DESCRIPTION
                        "
                        "
                    DEFVAL { false }
                    ::= { hwBRASIfCfgEntry 28 }
                    
                hwBRASIfCfgVBasMAC OBJECT-TYPE
                    SYNTAX MacAddress
                    MAX-ACCESS read-write
                    STATUS current
                    DESCRIPTION
                        "
                        "
                    ::= { hwBRASIfCfgEntry 29 }
                    
                hwBRASIfCfgVBasAuthMode OBJECT-TYPE
                    SYNTAX INTEGER
                        {
                        ignore(0),
                        reject(1)
                        }
                    MAX-ACCESS read-write
                    STATUS current
                    DESCRIPTION
                        "
                        "
                    DEFVAL { 1 }
                    ::= { hwBRASIfCfgEntry 30 }
                    
                hwBRASIfCfgPermitDomain1 OBJECT-TYPE
                    SYNTAX DisplayString (SIZE(1..64))
                    MAX-ACCESS read-write
                    STATUS current
                    DESCRIPTION
                        "
                        "
                    ::= { hwBRASIfCfgEntry 31 }
                    
                hwBRASIfCfgPermitDomain2 OBJECT-TYPE
                    SYNTAX DisplayString (SIZE(1..64))
                    MAX-ACCESS read-write
                    STATUS current
                    DESCRIPTION
                        "
                        "
                    ::= { hwBRASIfCfgEntry 32 }
                
                hwBRASIfCfgPermitDomain3 OBJECT-TYPE
                    SYNTAX DisplayString (SIZE(1..64))
                    MAX-ACCESS read-write
                    STATUS current
                    DESCRIPTION
                        "
                        "
                    ::= { hwBRASIfCfgEntry 33 }    
                     
                hwBRASIfCfgPermitDomain4 OBJECT-TYPE
                    SYNTAX DisplayString (SIZE(1..64))
                    MAX-ACCESS read-write
                    STATUS current
                    DESCRIPTION
                        "
                        "
                    ::= { hwBRASIfCfgEntry 34 }     
                    
                    
                hwBRASIfCfgAccessDelayType OBJECT-TYPE
                    SYNTAX INTEGER
                        {   
                        none(0),
                        termless(1),   
                        according-ani(2),
                        according-mac(3)
                        }
                    MAX-ACCESS read-write
                    STATUS current
                    DESCRIPTION
                        "
                        "                    
                    ::= { hwBRASIfCfgEntry 35 }
                    
                hwBRASIfCfgTermlessDelayTime OBJECT-TYPE
                    SYNTAX INTEGER(0..255)
                    MAX-ACCESS read-write
                    STATUS current
                    DESCRIPTION
                        "
                        "
                    DEFVAL { 0 }
                    ::= { hwBRASIfCfgEntry 36 }     
                    
                hwBRASIfCfgOddMacDelayTime OBJECT-TYPE
                    SYNTAX INTEGER(0..255)
                    MAX-ACCESS read-write
                    STATUS current
                    DESCRIPTION
                        "
                        "
                    DEFVAL { 0 }
                    ::= { hwBRASIfCfgEntry 37 }  
                    
                hwBRASIfCfgEvenMacDelayTime OBJECT-TYPE
                    SYNTAX INTEGER(0..255)
                    MAX-ACCESS read-write
                    STATUS current
                    DESCRIPTION
                        "
                        "
                    DEFVAL { 0 }
                    ::= { hwBRASIfCfgEntry 38 }
                    
                hwBRASIfCfgAccessNodeIdentify OBJECT-TYPE
                    SYNTAX DisplayString (SIZE(1..32))
                    MAX-ACCESS read-write
                    STATUS current
                    DESCRIPTION
                        "
                        "
                    ::= { hwBRASIfCfgEntry 39 }
                    
                hwBRASIfCfgAniDelayTime OBJECT-TYPE
                    SYNTAX INTEGER(0..255)
                    MAX-ACCESS read-write
                    STATUS current
                    DESCRIPTION
                        "
                        "
                    DEFVAL { 0 }
                    ::= { hwBRASIfCfgEntry 40 }
                     
               hwBRASIfCfgRemoteBackupProfile OBJECT-TYPE
                    SYNTAX DisplayString (SIZE(1..32))
                    MAX-ACCESS read-write
                    STATUS current
                    DESCRIPTION
                        "
                        "
                    ::= { hwBRASIfCfgEntry 42 }              

                hwBRASIfVlanTable OBJECT-TYPE
                        SYNTAX SEQUENCE OF HwBRASIfVlanEntry
                        MAX-ACCESS not-accessible
                        STATUS current
                        DESCRIPTION
                                "
                                "
                        ::= { hwSrvcfgInterfaceMibObjects 2 }
                
                hwBRASIfVlanEntry OBJECT-TYPE
                        SYNTAX HwBRASIfVlanEntry
                        MAX-ACCESS not-accessible
                        STATUS current
                        DESCRIPTION
                                "
                                Description.
                                "
                        INDEX { hwBRASIfVlanIfIndex, hwBRASIfVlanVlanId,hwBRASIfQinQVlanID}
                        ::= { hwBRASIfVlanTable 1 }

                HwBRASIfVlanEntry ::=
                        SEQUENCE { 
                            hwBRASIfVlanIfIndex
                                    InterfaceIndex,
                            hwBRASIfVlanVlanId
                                    INTEGER,
                            hwBRASIfVlanVlanNumber
                                    INTEGER,
                            hwBRASIfVlanAccessLimit
                                    INTEGER,
                            hwBRASIfVlanAccessNumber 
                                    INTEGER,
                            hwBRASIfVlanBlock 
                                    TruthValue,
                            hwBRASIfVlanDevAccessNumber 
                                    INTEGER,
                            hwBRASIfVlanSchedulerVcName
                                    DisplayString,
                            hwBRASIfVlanSchedulerVcGroupName
                                    DisplayString,
                            hwBRASIfVlanSchedulerVpGroupName
                                    DisplayString,
                            hwBRASIfQinQVlanID
                                    INTEGER
                        }

                hwBRASIfVlanIfIndex OBJECT-TYPE
                    SYNTAX InterfaceIndex
                    MAX-ACCESS read-only
                    STATUS current
                    DESCRIPTION
                        "
                        "
                    ::= { hwBRASIfVlanEntry 1 }

                hwBRASIfVlanVlanId OBJECT-TYPE
                    SYNTAX INTEGER(0..4094)
                    MAX-ACCESS read-only
                    STATUS current
                    DESCRIPTION
                        "
                        "
                    ::= { hwBRASIfVlanEntry 2 }

                hwBRASIfVlanVlanNumber OBJECT-TYPE
                    SYNTAX INTEGER(0..4094)
                    MAX-ACCESS read-write
                    STATUS current
                    DESCRIPTION
                        "
                        "
                    ::= { hwBRASIfVlanEntry 3 }

                hwBRASIfVlanAccessLimit OBJECT-TYPE
                    SYNTAX INTEGER(0..49153)
                    MAX-ACCESS read-write
                    STATUS current
                    DESCRIPTION
                        "
                        "
                    DEFVAL { 49152 }
                    ::= { hwBRASIfVlanEntry 4 }
                    
                hwBRASIfVlanAccessNumber OBJECT-TYPE
                    SYNTAX INTEGER(0..49152)
                    MAX-ACCESS read-only
                    STATUS current
                    DESCRIPTION
                        "
                        "
                    DEFVAL { 49152 }
                    ::= { hwBRASIfVlanEntry 5 }                    
                    
                hwBRASIfVlanBlock OBJECT-TYPE
                    SYNTAX TruthValue
                    MAX-ACCESS read-write
                    STATUS current
                    DESCRIPTION
                        "
                        "
                    DEFVAL { false }
                    ::= { hwBRASIfVlanEntry 6 }
                    
        hwBRASIfVlanDevAccessNumber OBJECT-TYPE
                    SYNTAX INTEGER(0..4096)
                    MAX-ACCESS read-only
                    STATUS current
                    DESCRIPTION
                        "
                        "
                    ::= { hwBRASIfVlanEntry 7 }
                    
                hwBRASIfVlanSchedulerVcName OBJECT-TYPE
                    SYNTAX DisplayString (SIZE(0..32))
                    MAX-ACCESS read-write
                    STATUS current
                    DESCRIPTION
                        "
                        scheduler vc name
                        "
                    ::= { hwBRASIfVlanEntry 8 }
                    
                hwBRASIfVlanSchedulerVcGroupName OBJECT-TYPE
                    SYNTAX DisplayString (SIZE(0..32))
                    MAX-ACCESS read-write
                    STATUS current
                    DESCRIPTION
                        "
                        scheduler vc-group name
                        "
                    ::= { hwBRASIfVlanEntry 9 }
                    
                hwBRASIfVlanSchedulerVpGroupName OBJECT-TYPE
                    SYNTAX DisplayString (SIZE(0..32))
                    MAX-ACCESS read-write
                    STATUS current
                    DESCRIPTION
                        "
                        scheduler vp-group name
                        "
                    ::= { hwBRASIfVlanEntry 10 }

                hwBRASIfQinQVlanID OBJECT-TYPE
                    SYNTAX INTEGER(0..4094)
                    MAX-ACCESS read-only
                    STATUS current
                    DESCRIPTION
                        "
                        QinQ VLAN
                        "
                    ::= { hwBRASIfVlanEntry 11 }
                            
           hwBRASIfPvcTable OBJECT-TYPE
                        SYNTAX SEQUENCE OF HwBRASIfPvcEntry
                        MAX-ACCESS not-accessible
                        STATUS current
                        DESCRIPTION
                                "
                                "
                        ::= { hwSrvcfgInterfaceMibObjects 3 }
                
                hwBRASIfPvcEntry OBJECT-TYPE
                        SYNTAX HwBRASIfPvcEntry
                        MAX-ACCESS not-accessible
                        STATUS current
                        DESCRIPTION
                                "
                                Description.
                                "
                        INDEX { hwBRASIfPvcIfIndex, hwBRASIfPvcVpi, hwBRASIfPvcVci }
                        ::= { hwBRASIfPvcTable 1 }

                HwBRASIfPvcEntry ::=
                        SEQUENCE { 
                            hwBRASIfPvcIfIndex
                                    InterfaceIndex,
                            hwBRASIfPvcVpi
                                    INTEGER,
                            hwBRASIfPvcVci
                                    INTEGER,                                    
                            hwBRASIfPvcPvcNumber
                                    INTEGER,
                            hwBRASIfPvcAccessLimit
                                    INTEGER,
                            hwBRASIfPvcAccessNumber 
                                    INTEGER,
                            hwBRASIfPvcBlock 
                                    TruthValue,
                            hwBRASIfPvcDevAccessNumber 
                                    INTEGER,
                            hwBRASIfPvcSchedulerVcGroupName
                                    DisplayString,
                            hwBRASIfPvcSchedulerVpGroupName
                                    DisplayString
                        }

               hwBRASIfPvcIfIndex OBJECT-TYPE
                    SYNTAX InterfaceIndex
                    MAX-ACCESS read-only
                    STATUS current
                    DESCRIPTION
                        "
                        "
                    ::= { hwBRASIfPvcEntry 1 }
                    
               hwBRASIfPvcVpi OBJECT-TYPE
                    SYNTAX INTEGER(0..255)
                    MAX-ACCESS read-only
                    STATUS current
                    DESCRIPTION
                        "
                        "
                    ::= { hwBRASIfPvcEntry 2 }

                hwBRASIfPvcVci OBJECT-TYPE
                    SYNTAX INTEGER(0..65534)
                    MAX-ACCESS read-only
                    STATUS current
                    DESCRIPTION
                        "
                        "
                    ::= { hwBRASIfPvcEntry 3 }
                    
                hwBRASIfPvcPvcNumber OBJECT-TYPE
                    SYNTAX INTEGER(0..4094)
                    MAX-ACCESS read-write
                    STATUS current
                    DESCRIPTION
                        "
                        "
                    ::= { hwBRASIfPvcEntry 4 }

                hwBRASIfPvcAccessLimit OBJECT-TYPE
                    SYNTAX INTEGER(0..49153)
                    MAX-ACCESS read-write
                    STATUS current
                    DESCRIPTION
                        "
                        "
                    DEFVAL { 49152 }
                    ::= { hwBRASIfPvcEntry 5 }
                    
                hwBRASIfPvcAccessNumber OBJECT-TYPE
                    SYNTAX INTEGER(0..49152)
                    MAX-ACCESS read-only
                    STATUS current
                    DESCRIPTION
                        "
                        "
                    DEFVAL { 49152 }
                    ::= { hwBRASIfPvcEntry 6 }                    
                    
                hwBRASIfPvcBlock OBJECT-TYPE
                    SYNTAX TruthValue
                    MAX-ACCESS read-write
                    STATUS current
                    DESCRIPTION
                        "
                        "
                    DEFVAL { false }
                    ::= { hwBRASIfPvcEntry 7 }
                    
                hwBRASIfPvcDevAccessNumber OBJECT-TYPE
                    SYNTAX INTEGER(0..4096)
                    MAX-ACCESS read-only
                    STATUS current
                    DESCRIPTION
                        "
                        "
                    ::= { hwBRASIfPvcEntry 8 }
                    
                hwBRASIfPvcSchedulerVcGroupName OBJECT-TYPE
                    SYNTAX DisplayString (SIZE(1..31))
                    MAX-ACCESS read-write
                    STATUS current
                    DESCRIPTION
                        "
                        scheduler vc-group name
                        "
                    ::= { hwBRASIfPvcEntry 9 }
                    
                hwBRASIfPvcSchedulerVpGroupName OBJECT-TYPE
                    SYNTAX DisplayString (SIZE(1..31))
                    MAX-ACCESS read-write
                    STATUS current
                    DESCRIPTION
                        "
                        scheduler vp-group name
                        "
                    ::= { hwBRASIfPvcEntry 10 }
                             
           hwSTPRelayTable OBJECT-TYPE
                        SYNTAX SEQUENCE OF HwSTPRelayEntry
                        MAX-ACCESS not-accessible
                        STATUS current
                        DESCRIPTION
                                "
                                "
                        ::= { hwSrvcfgInterfaceMibObjects 4 }
                
                hwSTPRelayEntry OBJECT-TYPE
                        SYNTAX HwSTPRelayEntry
                        MAX-ACCESS not-accessible
                        STATUS current
                        DESCRIPTION
                               "
                               Description.
                               "
                        INDEX { hwSTPRelayIndex }
                        ::= { hwSTPRelayTable 1 }
                
                HwSTPRelayEntry ::=
                        SEQUENCE { 
                                hwSTPRelayIndex
                                        INTEGER,
                                hwSTPRelayInIfIndex
                                        InterfaceIndex,                                        
                                hwSTPRelayOutIfIndex
                                        InterfaceIndex,
                                hwSTPRelayRowStatus
                                        RowStatus,
                                hwSTPRelayInIfName
                                        DisplayString,
                                hwSTPRelayOutIfName
                                        DisplayString,
                            hwSTPRelayInMac
                                    MacAddress,
                            hwSTPRelayOutMac
                                    MacAddress
                         }

                hwSTPRelayIndex OBJECT-TYPE
                        SYNTAX INTEGER(0..127)
                        MAX-ACCESS read-only
                        STATUS current
                        DESCRIPTION
                                "
                                "
                        ::= { hwSTPRelayEntry 1 }
                        
                hwSTPRelayInIfIndex OBJECT-TYPE
                    SYNTAX InterfaceIndex
                    MAX-ACCESS read-create
                    STATUS current
                    DESCRIPTION
                        "
                        "
                    ::= { hwSTPRelayEntry 2 }
                    
                hwSTPRelayOutIfIndex OBJECT-TYPE
                        SYNTAX InterfaceIndex
                        MAX-ACCESS read-create
                        STATUS current
                        DESCRIPTION
                                "
                                "
                        ::= { hwSTPRelayEntry 3 }

                hwSTPRelayRowStatus OBJECT-TYPE
                        SYNTAX RowStatus
                        MAX-ACCESS read-create
                        STATUS current
                        DESCRIPTION
                                "
                                "
                        ::= { hwSTPRelayEntry 4 }
                        
                hwSTPRelayInIfName OBJECT-TYPE
                        SYNTAX DisplayString (SIZE (1..47))
                        MAX-ACCESS read-create
                        STATUS current
                        DESCRIPTION
                                "
                                "
                        ::= { hwSTPRelayEntry 5 }
                        
                hwSTPRelayOutIfName OBJECT-TYPE
                        SYNTAX DisplayString (SIZE (1..47))
                        MAX-ACCESS read-create
                        STATUS current
                        DESCRIPTION
                                "
                                "
                        ::= { hwSTPRelayEntry 6 }
                        
                hwSTPRelayInMac OBJECT-TYPE
                    SYNTAX MacAddress
                    MAX-ACCESS read-create
                    STATUS current
                    DESCRIPTION
                        "
                        stp-relay-line mac-address of in side
                        "
                    ::= { hwSTPRelayEntry 7 }
                    
                hwSTPRelayOutMac OBJECT-TYPE
                    SYNTAX MacAddress
                    MAX-ACCESS read-create
                    STATUS current
                    DESCRIPTION
                        "
                        stp-relay-line mac-address of in side
                        "
                    ::= { hwSTPRelayEntry 8 }  
          
                  
            hwPortAccessLimitTable OBJECT-TYPE
                        SYNTAX SEQUENCE OF HwPortAccessLimitEntry
                        MAX-ACCESS not-accessible
                        STATUS current
                        DESCRIPTION
                        "
                        "
                        ::= { hwSrvcfgInterfaceMibObjects 5 }
                
                hwPortAccessLimitEntry OBJECT-TYPE
                        SYNTAX HwPortAccessLimitEntry
                        MAX-ACCESS not-accessible
                        STATUS current
                        DESCRIPTION
                        "
                        Description.
                        "
                        INDEX { hwPortAccessLimitIfIndex }
                        ::= { hwPortAccessLimitTable 1 }
                
                HwPortAccessLimitEntry ::=
                        SEQUENCE { 
                                hwPortAccessLimitIfIndex
                                        InterfaceIndex,
                                hwPortAccessLimitLimit
                                        INTEGER,
                                hwPortAccessLimitNumber
                                        INTEGER,
                                hwPortAccessLimitDevNumber
                                        INTEGER                                       
                        }
                
                hwPortAccessLimitIfIndex OBJECT-TYPE
                        SYNTAX InterfaceIndex
                        MAX-ACCESS read-only
                        STATUS current
                        DESCRIPTION
                                "
                                "
                        ::= { hwPortAccessLimitEntry 1 }
                
                hwPortAccessLimitLimit OBJECT-TYPE
                        SYNTAX INTEGER (0..49153)
                        MAX-ACCESS read-write
                        STATUS current
                        DESCRIPTION
                                "
                                "
                        ::= { hwPortAccessLimitEntry 2 }
                        
                hwPortAccessLimitNumber OBJECT-TYPE
                        SYNTAX INTEGER (0..49152)
                        MAX-ACCESS read-only
                        STATUS current
                        DESCRIPTION
                                "
                                "
                        ::= { hwPortAccessLimitEntry 3 }         
                        
                hwPortAccessLimitDevNumber OBJECT-TYPE
                        SYNTAX INTEGER (0..4096)
                        MAX-ACCESS read-only
                        STATUS current
                        DESCRIPTION
                                "
                                "
                        ::= { hwPortAccessLimitEntry 4 }
                        
            hwL3SubscriberIspTable OBJECT-TYPE
                        SYNTAX SEQUENCE OF HwL3SubscriberIspEntry
                        MAX-ACCESS not-accessible
                        STATUS current
                        DESCRIPTION
                                "
                                "
                        ::= { hwSrvcfgInterfaceMibObjects 6 }
                
                hwL3SubscriberIspEntry OBJECT-TYPE
                        SYNTAX HwL3SubscriberIspEntry
                        MAX-ACCESS not-accessible
                        STATUS current
                        DESCRIPTION
                               "
                               Description.
                               "
                        INDEX { hwL3SubscriberIspStartIp,hwL3SubscriberIspVpnId  }
                        ::= { hwL3SubscriberIspTable 1 }
                
                HwL3SubscriberIspEntry ::=
                        SEQUENCE { 
                                hwL3SubscriberIspStartIp
                                        IpAddress,
                                hwL3SubscriberIspVpnId
                                        DisplayString,
                                hwL3SubscriberIspEndIp
                                        IpAddress,
                                hwL3SubscriberIspDomainName
                                        DisplayString,
                                hwL3SubscriberIspRowStatus
                                        RowStatus
                         }

                hwL3SubscriberIspStartIp OBJECT-TYPE
                        SYNTAX IpAddress
                        MAX-ACCESS read-only
                        STATUS current
                        DESCRIPTION
                                "
                                "
                        ::= { hwL3SubscriberIspEntry 1 }

                hwL3SubscriberIspVpnId OBJECT-TYPE
                        SYNTAX DisplayString (SIZE (1..19))
                        MAX-ACCESS read-only
                        STATUS current
                        DESCRIPTION
                                "
                                "
                        ::= { hwL3SubscriberIspEntry 2 }

                hwL3SubscriberIspEndIp OBJECT-TYPE
                        SYNTAX IpAddress
                        MAX-ACCESS read-create
                        STATUS current
                        DESCRIPTION
                                "
                                "
                        ::= { hwL3SubscriberIspEntry 3 }

                hwL3SubscriberIspDomainName OBJECT-TYPE
                        SYNTAX DisplayString (SIZE (1..64))
                        MAX-ACCESS read-create
                        STATUS current
                        DESCRIPTION
                                "
                                "
                        ::= { hwL3SubscriberIspEntry 4 }

                hwL3SubscriberIspRowStatus OBJECT-TYPE
                        SYNTAX RowStatus
                        MAX-ACCESS read-create
                        STATUS current
                        DESCRIPTION
                                "
                                "
                        ::= { hwL3SubscriberIspEntry 5 }
                                               
     srvcfgScalar        OBJECT IDENTIFIER  ::= { hwSrvcfgInterfaceMibObjects 8 }   
  
   --
   --      The SrvCfg Scalar configuration
   --
   --      This group of objects describe the global configuration of SrvCfg.
   
   
   hwDhcpOption60DomainInclude     OBJECT-TYPE
           SYNTAX          TruthValue
           MAX-ACCESS      read-write
           STATUS          current
           DESCRIPTION
              "
              "
           ::= { srvcfgScalar 1 }
           
  hwDhcpOption60PartialMatch     OBJECT-TYPE
           SYNTAX          TruthValue
           MAX-ACCESS      read-write
           STATUS          current
           DESCRIPTION
              "
              "
           ::= { srvcfgScalar 2 }
           
     hwConnTimeOutTable        OBJECT IDENTIFIER  ::= { hwSrvcfgInterfaceMibObjects 9 }
  
  hwConnTimeOutTcp OBJECT-TYPE
           SYNTAX       INTEGER (1..255)
           MAX-ACCESS      read-write
           STATUS        current
           DESCRIPTION
              "
              "
           DEFVAL { 5 }
           ::= { hwConnTimeOutTable 1 }
           
  hwConnTimeOutUdp OBJECT-TYPE
           SYNTAX        INTEGER (1..255)
           MAX-ACCESS      read-write
           STATUS          current
           DESCRIPTION
              "
              "
           DEFVAL { 3 }
           ::= { hwConnTimeOutTable 2 }
           
           hwBRASIfVlanNumTable OBJECT-TYPE
                        SYNTAX SEQUENCE OF HwBRASIfVlanNumEntry
                        MAX-ACCESS not-accessible
                        STATUS current
                        DESCRIPTION
                                "
                                "
                        ::= { hwSrvcfgInterfaceMibObjects 10 }
                
                hwBRASIfVlanNumEntry OBJECT-TYPE
                        SYNTAX HwBRASIfVlanNumEntry
                        MAX-ACCESS not-accessible
                        STATUS current
                        DESCRIPTION
                                "
                                Description.
                                "
                        INDEX { hwBRASIfSlot }
                        ::= { hwBRASIfVlanNumTable 1 }

                HwBRASIfVlanNumEntry ::=
                        SEQUENCE { 
                            hwBRASIfSlot
                                    INTEGER,
                            hwBRASSlotVlanNum
                                    INTEGER,
                            hwBRASSLotStaticVlanNum
                                    INTEGER                           
                        }
        
                hwBRASIfSlot OBJECT-TYPE
                    SYNTAX INTEGER(0..16)
                    MAX-ACCESS read-only
                    STATUS current
                    DESCRIPTION
                        "
                        "
                    ::= { hwBRASIfVlanNumEntry 1 }
                    
                hwBRASSlotVlanNum OBJECT-TYPE
                    SYNTAX INTEGER(0..65536)
                    MAX-ACCESS read-only
                    STATUS current
                    DESCRIPTION
                        "
                        "
                    ::= { hwBRASIfVlanNumEntry 2 }
                    
                hwBRASSLotStaticVlanNum OBJECT-TYPE
                    SYNTAX INTEGER(0..16384)
                    MAX-ACCESS read-only
                    STATUS current
                    DESCRIPTION
                        "
                        "
                    ::= { hwBRASIfVlanNumEntry 3 } 

                hwServiceIfCfgTable OBJECT-TYPE
                        SYNTAX SEQUENCE OF HwServiceIfCfgEntry
                        MAX-ACCESS not-accessible
                        STATUS current
                        DESCRIPTION
                                "
                                "
                        ::= { hwSrvcfgInterfaceMibObjects 11 }
                
                hwServiceIfCfgEntry OBJECT-TYPE
                        SYNTAX HwServiceIfCfgEntry
                        MAX-ACCESS not-accessible
                        STATUS current
                        DESCRIPTION
                                "
                                An entry of hwServiceIfCfgTable.
                                "
                        INDEX { hwServiceIfCfgIfIndex }
                        ::= { hwServiceIfCfgTable 1 }

                HwServiceIfCfgEntry ::=
                        SEQUENCE { 
                            hwServiceIfCfgIfIndex
                                    InterfaceIndex,
                            hwServiceIfCfgIdentificationMode
                                    INTEGER,
                            hwServiceIfCfgDomain
                                    DisplayString,
                            hwServiceIfCfgUserName
                                    DisplayString,
                            hwServiceIfCfgPassword
                                    DisplayString,
                            hwServiceIfCfgDetectNum
                                    Integer32,
                            hwServiceIfCfgDetectInterval
                                    Integer32,
                            hwServiceIfCfgOption82
                                    TruthValue,
                            hwServiceIfCfgAccessLimit
                                    Integer32,
                            hwServiceIfCfgOption60
                                    TruthValue,
                            hwServiceIfCfgIpTriggerEnable
                                    EnabledStatus,
                            hwServiceIfCfgArpTriggerEnable
                                    EnabledStatus,
                            hwServiceIfCfgIfBlock  
                                    TruthValue,
                            hwServiceIfCfgQosProfile
                                    DisplayString,
                            hwServiceIfCfgBindingUserPasswordMode
                                    INTEGER,                                    
                            hwServiceIfCfgBindingUserNameFormat
                                    Integer32,
                            hwServiceIfCfgBindingUserPassword
                                    DisplayString,
                            hwServiceIfCfgRowStatus
                                    RowStatus
                        }

                hwServiceIfCfgIfIndex OBJECT-TYPE
                    SYNTAX InterfaceIndex
                    MAX-ACCESS not-accessible
                    STATUS current
                    DESCRIPTION
                        "
                        "
                    ::= { hwServiceIfCfgEntry 1 }

                  hwServiceIfCfgIdentificationMode OBJECT-TYPE
                    SYNTAX INTEGER
                            {
                            host(1),
                            location(2),
                            ceVlan(3)
                            }
                    MAX-ACCESS read-create
                    STATUS current
                    DESCRIPTION
                        "
                        
                       "
                    ::= { hwServiceIfCfgEntry 2 }

                  hwServiceIfCfgDomain OBJECT-TYPE
                    SYNTAX DisplayString (SIZE(1..20))
                    MAX-ACCESS read-create
                    STATUS current
                    DESCRIPTION
                        "
                        
                       "
                    ::= { hwServiceIfCfgEntry 3 }
                  
                  hwServiceIfCfgUserName OBJECT-TYPE
                    SYNTAX DisplayString (SIZE(1..31))
                    MAX-ACCESS read-create
                    STATUS current
                    DESCRIPTION
                        "
                        
                       "
                    ::= { hwServiceIfCfgEntry 4 }
               
                    hwServiceIfCfgPassword OBJECT-TYPE
                    SYNTAX DisplayString (SIZE(1..31))
                    MAX-ACCESS read-create
                    STATUS current
                    DESCRIPTION
                        "
                        
                       "
                    ::= { hwServiceIfCfgEntry 5 }

                    hwServiceIfCfgDetectNum OBJECT-TYPE
                    SYNTAX Integer32(2..10)
                    MAX-ACCESS read-create
                    STATUS current
                    DESCRIPTION
                        "
                        
                       "
                    ::= { hwServiceIfCfgEntry 6 }

                    hwServiceIfCfgDetectInterval OBJECT-TYPE
                    SYNTAX Integer32(0..120)
                    MAX-ACCESS read-create
                    STATUS current
                    DESCRIPTION
                        "
                        
                       "
                    ::= { hwServiceIfCfgEntry 7 }

                    hwServiceIfCfgOption82 OBJECT-TYPE
                    SYNTAX TruthValue
                    MAX-ACCESS read-create
                    STATUS current
                    DESCRIPTION
                        "
                        
                       "
                    ::= { hwServiceIfCfgEntry 8 }

                    hwServiceIfCfgAccessLimit OBJECT-TYPE
                    SYNTAX Integer32(0..16384)
                    MAX-ACCESS read-create
                    STATUS current
                    DESCRIPTION
                        "
                        
                      "
                    ::= { hwServiceIfCfgEntry 9 }

                    hwServiceIfCfgOption60 OBJECT-TYPE
                    SYNTAX TruthValue
                    MAX-ACCESS read-create
                    STATUS current
                    DESCRIPTION
                        "
                        
                      "
                    ::= { hwServiceIfCfgEntry 10 }  
                       
                    hwServiceIfCfgIpTriggerEnable OBJECT-TYPE
                    SYNTAX EnabledStatus
                    MAX-ACCESS read-create
                    STATUS current
                    DESCRIPTION
                        "
                        
                        "      
                    DEFVAL {disabled}
                    ::= { hwServiceIfCfgEntry 11 }     
                    
                    hwServiceIfCfgArpTriggerEnable OBJECT-TYPE
                    SYNTAX EnabledStatus
                    MAX-ACCESS read-create
                    STATUS current
                    DESCRIPTION
                        "
                        
                        "   
                    DEFVAL {disabled}
                    ::= { hwServiceIfCfgEntry 12 }
                  
                    hwServiceIfCfgIfBlock   OBJECT-TYPE
                    SYNTAX TruthValue
                    MAX-ACCESS read-create
                    STATUS current
                    DESCRIPTION
                        "
                       
                        "
                    ::= { hwServiceIfCfgEntry 13 }   
                    
                    hwServiceIfCfgQosProfile   OBJECT-TYPE
                    SYNTAX DisplayString (SIZE(1..31))
                    MAX-ACCESS read-create
                    STATUS current
                    DESCRIPTION
                        "
                        
                        "
                    ::= { hwServiceIfCfgEntry 14 }

                    hwServiceIfCfgBindingUserPasswordMode   OBJECT-TYPE
                    SYNTAX INTEGER
                    {
                     simple(1),
                     cipher(2)
                    }                         
                    MAX-ACCESS read-create
                    STATUS current
                    DESCRIPTION
                        "
                        
                        "
                    ::= { hwServiceIfCfgEntry 15 }  
                    
                    hwServiceIfCfgBindingUserNameFormat   OBJECT-TYPE
                    SYNTAX Integer32(1..7)                         
                    MAX-ACCESS read-create
                    STATUS current
                    DESCRIPTION
                        "
                        
                        "
                    ::= { hwServiceIfCfgEntry 16 }
 
                    hwServiceIfCfgBindingUserPassword   OBJECT-TYPE
                    SYNTAX DisplayString (SIZE(1..16))                         
                    MAX-ACCESS read-create
                    STATUS current
                    DESCRIPTION
                        "
                        
                        "
                    ::= { hwServiceIfCfgEntry 17 }
                    
                   hwServiceIfCfgRowStatus OBJECT-TYPE
                    SYNTAX RowStatus
                    MAX-ACCESS read-create
                    STATUS current
                    DESCRIPTION
                        "  
                        "
                    ::= { hwServiceIfCfgEntry 18 }
    --  ============== conformance information ==============
        hwSrvcfgInterfaceConformance OBJECT IDENTIFIER ::= { hwBRASSrvcfgInterface 2 }
        
        
        hwSrvcfgInterfaceCompliances OBJECT IDENTIFIER ::= { hwSrvcfgInterfaceConformance 1 }
        hwSrvcfgInterfaceCompliance MODULE-COMPLIANCE
               STATUS      current
               DESCRIPTION
                   "
                   The compliance statement for systems supporting 
                the this module.
                "

               MODULE      -- this module
               MANDATORY-GROUPS    {hwBRASIfCfgGroup, hwBRASIfVlanGroup, hwBRASIfPvcGroup,
                            hwSTPRelayServerGroup, hwPortAccessLimitGroup, hwL3SubscriberIspGroup,
                            hwConnTimeOutGroup, hwSrvcfgScalarGroup, hwBRASIfVlanNumGroup,
                            hwServiceIfCfgGroup }  
                                               
              ::= { hwSrvcfgInterfaceCompliances 1 }  
     --  ============== groups ==============  
        hwSrvcfgInterfaceGroups OBJECT IDENTIFIER ::= { hwSrvcfgInterfaceConformance 2 } 
        
        hwBRASIfCfgGroup OBJECT-GROUP
            OBJECTS {
                            hwBRASIfCfgAccessType,
                            hwBRASIfCfgBRASIfName,
                            hwBRASIfCfgPreAuthDomain,
                            hwBRASIfCfgAuthDomain,
                            hwBRASIfCfgForceAuthDomain,
                            hwBRASIfCfgAcctCpyRdSvr,
                            hwBRASIfCfgAuthMethod,
                            hwBRASIfCfgNasPortType,
                            hwBRASIfCfgLeaseName,
                            hwBRASIfCfgLeasePwd,
                            hwBRASIfCfgArpInterval,
                            hwBRASIfCfgArpFailTimes,
                            hwBRASIfCfgArpProxy,
                            hwBRASIfCfgRoamIsp,                                    
                            hwBRASIfCfgDhcpBroadCast,
                            hwBRASIfCfgHostCar,
                            hwBRASIfCfgRowStatus,
                            hwBRASIfCfgEapTrigger,
                            hwBRASIfCfgWlanSwitch,
                            hwBRASIfCfgWlanAuthorization,
                            hwBRASIfCfgDhcpShortLease,
                            hwBRASIfCfgRoamDomain,
                            hwBRASIfVsiName,
                            hwBRASIfCfgOption82,
                            hwBRASIfVpnInstance,
                            hwBRASIfCopyMulticasePerUser,
                            hwBRASIfCfgNDProxy,
                            hwBRASIfCfgVBasMAC,
                            hwBRASIfCfgVBasAuthMode,
                            hwBRASIfCfgPermitDomain1,
                            hwBRASIfCfgPermitDomain2,
                            hwBRASIfCfgPermitDomain3,
                            hwBRASIfCfgPermitDomain4,                        
                            hwBRASIfCfgAccessDelayType,
                            hwBRASIfCfgTermlessDelayTime,
                            hwBRASIfCfgOddMacDelayTime,
                            hwBRASIfCfgEvenMacDelayTime,
                            hwBRASIfCfgAccessNodeIdentify,
                            hwBRASIfCfgAniDelayTime,
                            hwBRASIfCfgRemoteBackupProfile
                 }       
            STATUS current
            DESCRIPTION 
                "
                "
            ::= { hwSrvcfgInterfaceGroups 1 }


        hwBRASIfVlanGroup OBJECT-GROUP
            OBJECTS {    
                            hwBRASIfVlanVlanNumber,
                            hwBRASIfVlanAccessLimit,
                            hwBRASIfVlanAccessNumber,
                            hwBRASIfVlanBlock,
                            hwBRASIfVlanDevAccessNumber,
                            hwBRASIfVlanSchedulerVcName,
                            hwBRASIfVlanSchedulerVcGroupName,
                            hwBRASIfVlanSchedulerVpGroupName    
                           }          
            STATUS current
            DESCRIPTION 
                "
                "
            ::= { hwSrvcfgInterfaceGroups 2 }
            
        hwBRASIfPvcGroup OBJECT-GROUP
            OBJECTS {                                
                            hwBRASIfPvcPvcNumber,
                            hwBRASIfPvcAccessLimit,
                            hwBRASIfPvcAccessNumber,
                            hwBRASIfPvcBlock,
                            hwBRASIfPvcDevAccessNumber,
                            hwBRASIfPvcSchedulerVcGroupName,
                            hwBRASIfPvcSchedulerVpGroupName
                    }            
            STATUS current
            DESCRIPTION 
                "
                "
            ::= { hwSrvcfgInterfaceGroups 3 }
            
        hwSTPRelayServerGroup OBJECT-GROUP
            OBJECTS {
                                hwSTPRelayInIfIndex,                                        
                                hwSTPRelayOutIfIndex,
                                hwSTPRelayRowStatus,
                                hwSTPRelayInIfName,
                                hwSTPRelayOutIfName,
                            hwSTPRelayInMac,
                            hwSTPRelayOutMac
                    }            
            STATUS current
            DESCRIPTION 
                "
                "
            ::= { hwSrvcfgInterfaceGroups 4 }
            
        hwPortAccessLimitGroup OBJECT-GROUP
            OBJECTS {
                                hwPortAccessLimitLimit,
                                hwPortAccessLimitNumber,
                                hwPortAccessLimitDevNumber
                }
            STATUS current
            DESCRIPTION 
                "
                "
            ::= { hwSrvcfgInterfaceGroups 5 }
            
        hwL3SubscriberIspGroup OBJECT-GROUP
                OBJECTS {
                                hwL3SubscriberIspEndIp,
                                hwL3SubscriberIspDomainName,
                                hwL3SubscriberIspRowStatus
                }
            STATUS current
            DESCRIPTION 
                "
                "
            ::= { hwSrvcfgInterfaceGroups 6 }             
                    
        hwConnTimeOutGroup OBJECT-GROUP
            OBJECTS { 
                hwConnTimeOutTcp,
                hwConnTimeOutUdp
                    }            
            STATUS current
            DESCRIPTION 
                "
                "
            ::= { hwSrvcfgInterfaceGroups 7 }
            
        hwSrvcfgScalarGroup OBJECT-GROUP
            OBJECTS { 
                hwDhcpOption60DomainInclude,
                hwDhcpOption60PartialMatch
                    }            
            STATUS current
            DESCRIPTION 
                "
                "
            ::= { hwSrvcfgInterfaceGroups 8 }
        
        hwBRASIfVlanNumGroup OBJECT-GROUP
            OBJECTS {
                            hwBRASSlotVlanNum,
                            hwBRASSLotStaticVlanNum 
                    }            
            STATUS current
            DESCRIPTION 
                "
                "
            ::= { hwSrvcfgInterfaceGroups 9 }
            
        hwServiceIfCfgGroup OBJECT-GROUP
            OBJECTS {
                            hwServiceIfCfgIdentificationMode,
                            hwServiceIfCfgDomain,
                            hwServiceIfCfgUserName,
                            hwServiceIfCfgPassword,
                            hwServiceIfCfgDetectNum,
                            hwServiceIfCfgDetectInterval,
                            hwServiceIfCfgOption82,
                            hwServiceIfCfgAccessLimit,
                            hwServiceIfCfgOption60,
                            hwServiceIfCfgIpTriggerEnable,
                            hwServiceIfCfgArpTriggerEnable,
                            hwServiceIfCfgIfBlock,
                            hwServiceIfCfgQosProfile,
                            hwServiceIfCfgBindingUserPasswordMode,                                    
                            hwServiceIfCfgBindingUserNameFormat,
                            hwServiceIfCfgBindingUserPassword,
                            hwServiceIfCfgRowStatus
                    }            
            STATUS current
            DESCRIPTION 
                "
                "
            ::= { hwSrvcfgInterfaceGroups 10 }            
             
                    
        --  ============== conformance information define end ==============                    

                                                    
        END
