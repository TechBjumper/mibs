--========================================================
--
-- MIB      : Common Routing  Avaya Inc.
--
-- Version  : 2.6.4           13 Feb. 2001
--
--========================================================
--
-- Copyright 1997, 1998, 1999, 2000, 2001  Avaya Inc.  
-- All Rights Reserved.  
--
-- Reproduction of this document is authorized on condition 
-- that the foregoing copyright notice is included.
--
-- This Avaya SNMP Management Information Base Specification
-- (Specification) embodies Avaya confidential and
-- Proprietary intellectual property.  Avaya retains all
-- Title and ownership in the Specification, including any revisions
--
-- It is Avaya's intent to encourage the widespread use of this
-- Specification in connection with the management of Avaya products.
-- Avaya grants vendors, end-users, and other interested parties
-- a non-exclusive license to use this Specification in connection
-- with the management of Avaya products.
--
-- This Specification is supplied "as is," and Avaya makes
-- no warranty, either express or implied, as to the use,
-- operation, condition, or performance of the Specification.
--
--========================================================
--
-- RCS
--
-- Version 2.6.4
-- 13 Feb. 2001
-- 1. drStaticCidr is directly under croute.
-- 2. Some fields in drStaticCidrEntry removed - Shili Ben-Dori 
-- Version 2.6.3
-- 28 Jan. 2001
-- 1. Added Static routes table, for FWLB routes and more - itaiz
-- 2. Copyright changed from Lucent/Lannet to Avaya
--
-- Version 2.6.2
-- 31 Oct. 2000
-- 1. routeGroupRouteMode modified to include routeAndWebSwitch(21) Value. - Itai Z.
--
-- Version 2.6.1
-- 04 July 2000
-- 1. Change the order of ipEZ2RcontrolBoostedRoutersTimeout &
--     ipEZ2RcontrolHostsTimeout and ipEZ2RcontrolAutoLearnMode in ipEZ2R control table - Shili B.
--
-- Version 2.6.0
-- 16 May 2000
-- 1. Add 2 mib items ipEZ2RcontrolBoostedRoutersTimeout &
--     ipEZ2RcontrolHostsTimeout to ipEZ2R control table - Shili B.
--
-- Version 2.5.0
-- 5 Apr. 2000
-- 1. Remove the ipPolicyMgmt subtree under ipRoute - Same subtree  in policy mib. - Niv H.
-- 2. Add new item ipInterfaceIcmpRedirects to ipInterface table - Eyal A.
-- 3. Add new item drIpInterfaceIcmpRedirects to drIpInterface table - Eyal A.
--
-- Version 2.4.0
-- 11 Jan. 2000
-- 1. Add new item ipInterfaceNetbiosRebroadcast to the ipInterface table. - Yigal N.
-- 2. Add new sub-tree to enable distribution of layer2 and ip interface tables - Eyal A.
--
-- Version 2.3.0
-- 03 Nov. 1999
-- 1. Add new item ipVRRPAdminStatus as a global switch for VRRP - Yigal N.
-- 2. Add new item ipInterfaceName to the ipInterface table. - Yigal N.
--
-- Version 2.2.1
-- 06 Sep. 1998
-- 1. Change the access of routeGroupRouteMode item to read-write - Yigal N.
--
-- Version 2.2.0
-- 06 Sep. 1998
-- 1. Add new item ipPolicyControlActiveEZ2routeList to ipPolicyControl table - Yigal N.
-- 2. Remove do-not-route enum from ipPolicyList table - Yigal N.
--
-- Version 2.1.0
-- 01 Sep. 1998
-- 1. Add new table routeGroupTable for router module management. - Yigal N.
-- 2. Change access of ipPolicyListType to read-write. - Yigal N.
-- 3. Add new item ipPolicyListChecksum to ipPolicyList table - Yigal N.
-- 4. Add new item ipPolicyControlChecksum to ipPolicyControl table - Yigal N.
--
-- Version 2.0.0
-- 17 Aug. 1998
-- 1. Add 3 new tables ipPolicyXX for policy management. - Yigal N.
-- 2. Add 2 new table to control the EZ2route mode - Yigal N.
-- 3. Add new enumeration (sna & ipx) to vlBridgeProtocol - Yigal N.
--
-- Version 1.9.2
-- 11 Mar. 1998
-- 1. Add new enumeration to layer2GlobalsBridgeEnable for redundancy support. - Yigal N.
--
-- Version 1.9.1
-- 1. Add new item relayVlRelayAddr to relay table. - Yigal N.
--
-- Version 1.9.0
-- 14 Dec. 1998
-- 1. Change names of ipxCircRIPState & ipxCircSAPState to ipxCircRIPStatus &.
--     ipxCircSAPStatus respectively. - Yigal N.
-- 2. Add new items ipxCircRipState & ipxCircSapState to the interface table. -Yigal N.
-- 3. Add ipxDestAgingTime mib to ipxDest table & ipxServAgingTime mib to ipxServ table - Yigal N.
--
-- Version 1.8.0
-- 23 Nov. 1998
-- 1. Delete decLAT from the enumeration of the vlBridgeProtocol, and change the order - Yigal N.
-- 2. Add IP Multicast table to support IP Multicast. - Yigal N.
--
-- Version 1.7.0
-- 19 Nov. 1998
-- 1. Add 2 new mibs items, ripInterfaceSendMode & ripInterfaceVersion
--     for RIP, to support RIP-2  - Yigal N.
-- 2. Change the mib name of ripInterfacePoisonReverse  to ripInterfaceSplitHorizon
--     and it's enumeration. - Yigal N.
-- 3. Change the Index order of vlBridge table vlBridgeProtocol befor vlBridgeGroupIndex -Yigal N.
--
-- Version 1.6.0
-- 15 Feb. 1998
-- 1. Replace standard name NetNumber to NetNum due to browser load problem - Yigal N.
--
-- Version 1.5.0
-- 18 Jan. 1998
-- 1. Add ipxSapFilterGlobals sub-tree to ipxRoute sub-tree - Yigal N.
-- 2. Change ACCESS of ipxSapFilterCircIndex from RO to RW - Yigal N.
--
-- Version 1.4.0
-- 11 Jan. 1998
-- 1. Add new mib ripInterfaceState to ripInterfaceTable. - Yigal N.
--
-- Version 1.3.0
-- 15 Dec. 1997
-- 1. Add mibs to support ARP Server feature. IpInterfaceARPServerStatus to ip interface table
--     and global parameter ipShortcutARPServerStatus. - Yigal N. (Eyal A.)
-- 
-- Version 1.2.0
-- 07 Dec. 1997
-- 1. Replace definition of NetNumber from INTEGER(1.. 4294967295) to INTEGER -
--     Yigal N. (Eyal A.).
-- 2. Delete ipxSapFilterServiceNetMask mib item from ipxSap table and change the
--     numbering of the other mibs in the table - Yigal N. (Eyal A.)
-- 3. Add mibs to support IP Redundancy. IpInterfaceMainRouterAddr to ip interface table
--     and 3 global parameters: ipRedundancyStatus, ipRedundancyTimeout and
--     ipRedundancyPollingInterval. - Yigal N. (Eyal A.)
-- 4. Change the suffix name of ipGlobalsBOOTPRelayStatus from Enable to Status, and add
--     more enumeration to the list backup and active Backup - Yigal N. (Eyal A.)
--
-- Version 1.1.0
-- 23 Nov. 1997
-- 1. Change the ACCESS of ipAccessControlSrcAddr, ipAccessControlSrcMask,
--     ipAccessControlDstAddr, ipAccessControlDstMask and ipxAccessControlSrcAddr,
--     ipxAccessControlDstAddr mib items from read-only to read-write.
-- 2. Add SAP filter table for IPX.
--
-- Version 1.0.4
-- 10 Nov. 1997
-- 1. Add IP Access Control Table & IPX Access Control Table.
--
-- Version 1.0.3
-- 29 Sep. 1997
-- 1. Move mib item BridgeEnable from ipRoute group to layer2 group.
-- 2. Change bcast address from enum to values 0 or 1.
-- 3. Change SYNTAX of ipxServType from OCTET-STRING to INTEGER.
-- 4. Change SYNTAX of ipxServName from OCTET-STRING to DisplayString.
-- 5. Change SYNTAX of ipxServSocket from OCTET-STRING to INTEGER.
--
-- Version 1.0.2
-- 23 Sep. 1997
-- 1. Add Row Status to Relay Table. This item used for deleting entry.
--
-- Version 1.0.1
-- 23 Sep. 1997
-- 1. Change order of the ipRoute sub-tree
-- 2. Move Relay from layer2 to ipRoute sub-tree..
--
-- Version 1.0.0
-- 18 Sep. 1997
-- 1. Initial version.
--========================================================

CROUTE-MIB DEFINITIONS ::= BEGIN

IMPORTS
	IpAddress
    FROM RFC1155-SMI
	OBJECT-TYPE
    FROM RFC-1212
	PhysAddress,
	DisplayString
    FROM RFC1213-MIB
	lannet
    FROM GEN-MIB
    OwnerString
    FROM RMON-MIB;

RowStatus ::= INTEGER {
	active(1),
	notInService(2),
	notReady(3),
	createAndGo(4),
	createAndWait(5),
	destroy(6)
	}

NetNum ::= INTEGER

-- Common Routing
-- Implementation of this group is mandatory for all devices containing the

croute	OBJECT IDENTIFIER ::= { lannet 31} 

-- IP Routing Group.

ipRoute OBJECT IDENTIFIER  ::= { croute 1 } 

-- IP Global Parameters Group.
ipGlobals OBJECT IDENTIFIER  ::= { ipRoute 1 }

ipGlobalsBOOTPRelayStatus OBJECT-TYPE
	SYNTAX INTEGER {
		enable(1),
		disable(2),
		backup(3),
		activeBackup(4)
		}
	ACCESS  read-write
	STATUS  mandatory
	DESCRIPTION
	" Whenever to activate the BOOTP Relay protocol on the device.
	enable  -	set by the user,
		means activate the BOOTP Relay protocol over the defined VLANs.
	disable -	set by the user,
		means don't active the BOOTP Relay protocol.
	backup - set by the user,
		means the BOOTP Relay protocol is in stand-by. It will enter to activeBackup mode
		after IP REDUNDANCY mechanism will enter to active mode.
	activeBackup -  set by the device (status),
		means the backup BOOTP Relay is working (after time-out of IP REDUNDANCY)."
	DEFVAL  { disable }
	::=   { ipGlobals 1 }

ipGlobalsICMPErrMsgEnable OBJECT-TYPE
	SYNTAX INTEGER {
		enable(1),
		disable(2)
		}
	ACCESS  read-write
	STATUS  mandatory
	DESCRIPTION
	" Whenever to send ICMP messages such as Destination Unreachable, etc. "
	DEFVAL  { enable }
	::=   { ipGlobals 2 }

ipGlobalsARPInactiveTimeout OBJECT-TYPE
	SYNTAX INTEGER
	ACCESS  read-write
	STATUS  mandatory
	DESCRIPTION
	"Time-out required to remove inactive ARP entries. The value is in seconds.
	The default value is 4 hours "
	DEFVAL  { 14400 }
	::=   { ipGlobals 3 }

-- The IP interfaces Table
-- This table contains all the parameters to configure the IP interfaces

ipInterfaceTable OBJECT-TYPE
	SYNTAX  SEQUENCE OF IpInterfaceEntry
	ACCESS  not-accessible
	STATUS  mandatory
	DESCRIPTION
	"This table is an extention of MIB II IpAddrTable, and is used to
	add/delete entries to/from that table. In addition it contains private objects."
	::= { ipRoute 2 }

ipInterfaceEntry OBJECT-TYPE
	SYNTAX  IpInterfaceEntry
	ACCESS  not-accessible
	STATUS  mandatory
	DESCRIPTION
	"The information concerning one of this entity's IP interfaces.
	An IP interface is a logical connection to a certain IP net/subnet."
	INDEX   { ipInterfaceAddr }
	::= { ipInterfaceTable 1 }

IpInterfaceEntry ::=
	SEQUENCE {
		ipInterfaceAddr			IpAddress,
		ipInterfaceNetMask		IpAddress,
		ipInterfaceLowerIfAlias		DisplayString,
		ipInterfaceType			INTEGER,
		ipInterfaceForwardIpBroadcast	INTEGER,
		ipInterfaceBroadcastAddr		INTEGER,
		ipInterfaceProxyArp		INTEGER,
		ipInterfaceStatus			RowStatus,
		ipInterfaceMainRouterAddr	IpAddress,
		ipInterfaceARPServerStatus	INTEGER,
		ipInterfaceName			DisplayString,
		ipInterfaceNetbiosRebroadcast	INTEGER,
		ipInterfaceIcmpRedirects		INTEGER
		}

ipInterfaceAddr OBJECT-TYPE
	SYNTAX  IpAddress
	ACCESS  read-only
	STATUS  mandatory
	DESCRIPTION
	"The IP address to which this entry's addressing information pertains."
	::= { ipInterfaceEntry 1 }

ipInterfaceNetMask OBJECT-TYPE
	SYNTAX  IpAddress
	ACCESS  read-write
	STATUS  mandatory
	DESCRIPTION
	"The subnet mask associated with the IP address of this entry.
	The value of the mask is an IP address with all the network bits
	set to 1 and all the hosts bits set to 0."
	::= { ipInterfaceEntry 2 }

ipInterfaceLowerIfAlias OBJECT-TYPE
	SYNTAX  DisplayString	(SIZE(0..16))
	ACCESS  read-write
	STATUS  mandatory
	DESCRIPTION
	"This object is an 'alias' name for the lower-layer interface on top
	of which this IP interface is defined. The alias is specified 
	by the network manager, and provides a non-volatile 'handle'
	for the lower-layer interface.
	The semantics of the object are similar to the semantics of
	the ifAlias object, defined by the Interfaces MIB. At the time 
	when this Madge MIB object was defined, the latest release
	of the Interfaces MIB was draft-ietf-ifmib-mib-05.txt. The
	purpose is to support all methods (static or dynamic) for creation 
	of interfaces and to allow creation of IP table entries without the need 
	of the layer 2 interface to be present on the device at the time of the
	creation. It is assumed that some implementation dependent mechanisms
	allow the IP application to be informed about the creation of new lower
	layer interfaces."
	::= { ipInterfaceEntry 3 }

ipInterfaceType OBJECT-TYPE
	SYNTAX  INTEGER {
		broadcast (1),
		nBMA (2),
		ptp (3)
		}
	ACCESS  read-write
	STATUS  mandatory
	DESCRIPTION
	"The logical type of the interface. The default depends on the physical type.
	For example Ethernet and Token-Ring LANs are of type broadcast"
	DEFVAL  { broadcast }
	::= { ipInterfaceEntry 4 }

ipInterfaceForwardIpBroadcast OBJECT-TYPE
	SYNTAX INTEGER {
		enable(1),
		disable(2)
		}
	ACCESS  read-write
	STATUS  mandatory
	DESCRIPTION
	" Whether the router forwards IP directed broadcasts that are to be
	transmitted as link-layer broadcast to an attached net or subnet. "
	DEFVAL  { enable }
	::=   { ipInterfaceEntry 5 }

ipInterfaceBroadcastAddr OBJECT-TYPE
	SYNTAX INTEGER
	ACCESS  read-write
	STATUS  mandatory
	DESCRIPTION
	"The value of the least-significant bit in the IP broadcast address used
	for sending datagrams on the (logical) interface associated with the IP
	address of this entry.
	For example, when the Internet standard all-ones broadcast address is
	used, the value will be 1. This value applies to both the subnet and
	network broadcasts addresses used by the entity on this (logical) interface."
	DEFVAL  { 1 }
	::=   { ipInterfaceEntry 6 }

ipInterfaceProxyArp OBJECT-TYPE
	SYNTAX INTEGER {
		enable(1),
		disable(2)
		}
	ACCESS  read-write
	STATUS  mandatory
	DESCRIPTION
	" When proxy ARP is enabled, the router responds to ARP 
	requests received on one link-layer interface for an IP-address 
	that is reachable via another link-layer interface. 
	The response provides the router's own MAC address. "
	DEFVAL  { disable }
	::=   { ipInterfaceEntry 7 }

ipInterfaceStatus OBJECT-TYPE
	SYNTAX RowStatus
	ACCESS  read-write
	STATUS  mandatory
	DESCRIPTION
	" For adding and deleting IP interfaces. Deleting this row means 
	deleting the corresponding entry in IpAddrTable (MIB II). Deleting an 
	IP interface also causes deletion of all static routes defined on this IP 
	interface, as well as protocol interfaces (e.g. RIP and OSPF) defined on 
	this IP interface."
	::= { ipInterfaceEntry 8 }

ipInterfaceMainRouterAddr OBJECT-TYPE
	SYNTAX  IpAddress
	ACCESS  read-write
	STATUS  mandatory
	DESCRIPTION
	"The IP address of the main router backed up on this interface."
	::= { ipInterfaceEntry 9 }

ipInterfaceARPServerStatus OBJECT-TYPE
	SYNTAX INTEGER {
		enable(1),
		disable(2)
		}
	ACCESS  read-write
	STATUS  mandatory
	DESCRIPTION
	"Whenever to activate the ARP Server mechanism on this interface.
	enable  -	set by the user,
		means activate the ARP Server mechanism over this IP interface.
	disable -	set by the user,
		means don't active the ARP Server mechanism over this IP interface."
	DEFVAL  { disable }
	::=   { ipInterfaceEntry 10 }

ipInterfaceName OBJECT-TYPE
	SYNTAX  DisplayString	(SIZE(0..32))
	ACCESS  read-write
	STATUS  mandatory
	DESCRIPTION
	"The name of this interface for compatibility with cli."
	::= { ipInterfaceEntry 11 }

ipInterfaceNetbiosRebroadcast OBJECT-TYPE
	SYNTAX INTEGER {
		inbound(1),
		outbound(2),
		both(3),
		disable(4)
		}
	ACCESS  read-write
	STATUS  mandatory        
	DESCRIPTION
	"inbound - netbios received from the interface are rebarodcasted,
	 outbound - netbios are rebraodcasted to this interface,
	 both - netbios are rebroadacsted both from and to this interface,
	disable - netbios is not rebraodcasted neither from nor to this interface.
	Currently only both and disable are supported"
	DEFVAL  { disable }
	::= { ipInterfaceEntry 12 }

ipInterfaceIcmpRedirects OBJECT-TYPE
	SYNTAX INTEGER {
		enable(1),
		disable(2)
		}
	ACCESS  read-write
	STATUS  mandatory        
	DESCRIPTION
	"enable - enable the sending of redirect messages if the router is forced to 
	                re-send a packet through the same interface on which it was received.
	disable - disable the sending of redirect messages on this interface."
	DEFVAL  { enable }
	::= { ipInterfaceEntry 13 }
 

-- RIP Global Parameters Group.
ripGlobals OBJECT IDENTIFIER  ::= { ipRoute 3 }

ripGlobalsRIPEnable OBJECT-TYPE
	SYNTAX INTEGER {
		enable(1),
		disable(2)
		}
	ACCESS  read-write
	STATUS  mandatory
	DESCRIPTION
	" Whenever to activate the RIP protocol on the device.
	disable means don't activate RIP over all the IP interfaces
	enable means that the status of each interface is relevant "
	DEFVAL  { enable }
	::=   { ripGlobals 1 }

ripGlobalsLeakOSPFIntoRIP OBJECT-TYPE
	SYNTAX INTEGER {
		enable(1),
		disable(2)
		}
	ACCESS  read-write
	STATUS  mandatory
	DESCRIPTION
	"Whenever to leak (redistribute) routes learned from OSPF protocol into
	the domain of the RIP protocol."
	DEFVAL  { disable }
	::=   { ripGlobals 2 }

ripGlobalsLeakStaticIntoRIP OBJECT-TYPE
	SYNTAX INTEGER {
		enable(1),
		disable(2)
		}
	ACCESS  read-write
	STATUS  mandatory
	DESCRIPTION
	"Whenever to leak (redistribute) routes learned from Static Route into
	the domain of the RIP protocol."
	DEFVAL  { enable }
	::=   { ripGlobals 3 }

-- The RIP interfaces Table
-- This table contains extention parameters to configure the RIP interfaces

ripInterfaceTable OBJECT-TYPE
	SYNTAX  SEQUENCE OF RipInterfaceEntry
	ACCESS  not-accessible
	STATUS  mandatory
	DESCRIPTION
	"This table is an extention of rip2IfConfTable, and is used to add/delete
	objects entries to/from that table."
	::= { ipRoute 4 }

ripInterfaceEntry OBJECT-TYPE
	SYNTAX  RipInterfaceEntry
	ACCESS  not-accessible
	STATUS  mandatory
	DESCRIPTION
	"The information concerning one of this entity's IP interfaces.
	An IP interface is a logical connection to a certain IP net/subnet."
	INDEX   { ripInterfaceAddr }
	::= { ripInterfaceTable 1 }

RipInterfaceEntry ::=
	SEQUENCE {
		ripInterfaceAddr			IpAddress,
		ripInterfaceMetric		INTEGER,
		ripInterfaceSplitHorizon		INTEGER,
		ripInterfaceAcceptDefaultRoute	INTEGER,
		ripInterfaceSendDefaultRoute	INTEGER,
		ripInterfaceState			INTEGER,
		ripInterfaceSendMode		INTEGER,
		ripInterfaceVersion		INTEGER
		}

ripInterfaceAddr OBJECT-TYPE
	SYNTAX  IpAddress
	ACCESS  read-only
	STATUS  mandatory
	DESCRIPTION
	"The IP address to which this entry's addressing information pertains."
	::= { ripInterfaceEntry 1 }

ripInterfaceMetric OBJECT-TYPE
	SYNTAX INTEGER ( 0..15 )
	ACCESS  read-write
	STATUS  mandatory
	DESCRIPTION
	" This variable indicates the number of hops that is to be assign
	to that interface. "
	DEFVAL  { 1 }
	::=   { ripInterfaceEntry 2 }

ripInterfaceSplitHorizon OBJECT-TYPE
	SYNTAX INTEGER {
		poisonReverse(1),
		splitHorizon(2),
		none(3)
		}
	ACCESS  read-write
	STATUS  mandatory
	DESCRIPTION
	" Whether to activate Poison Reverse algorithm, 
	Split Horizon or none of them, on this interface "
	DEFVAL  { splitHorizon }
	::=   { ripInterfaceEntry 3 }

ripInterfaceAcceptDefaultRoute OBJECT-TYPE
	SYNTAX INTEGER {
		enable(1),
		disable(2)
		}
	ACCESS  read-write
	STATUS  mandatory
	DESCRIPTION
	" Whether to accept the default route from receive RIP message. "
	DEFVAL  { enable }
	::=   { ripInterfaceEntry 4 }

ripInterfaceSendDefaultRoute OBJECT-TYPE
	SYNTAX INTEGER {
		enable(1),
		disable(2)
		}
	ACCESS  read-write
	STATUS  mandatory
	DESCRIPTION
	" Whether to send the default route in RIP message. "
	DEFVAL  { disable }
	::=   { ripInterfaceEntry 5 }

ripInterfaceState OBJECT-TYPE
	SYNTAX INTEGER {
		active(1),
		inactive(2)
		}
	ACCESS  read-only
	STATUS  mandatory
	DESCRIPTION
	"The operational (current state) of the IP interface from RIP point of view.
	It depends on Global RIP status, IP interface status and rip interface STATUS.
	inactive - set by the device (status), the rip is not active on this interface. 
	active - 	set by the device (status), rip is active on this interface."
	::=   { ripInterfaceEntry 6 }

ripInterfaceSendMode OBJECT-TYPE
	SYNTAX INTEGER {
		all(1),
		defaultOnly(2),
		doNotSend(3)
		}
	ACCESS  read-write
	STATUS  mandatory
	DESCRIPTION
	" What the router sends on this interface.
	All - send the whole routing table according to the RIP version.
	DefaultOnly - send default route only. 
	DoNotDend - don't send any RIP information on this interface."
	::=   { ripInterfaceEntry 7 }

ripInterfaceVersion OBJECT-TYPE
	SYNTAX INTEGER {
		rip1(1),
		rip2(2)
		}
	ACCESS  read-write
	STATUS  mandatory
	DESCRIPTION
	" What RIP information the router sends on this interface."
	::=   { ripInterfaceEntry 8 }


-- OSPF Global Parameters Group.
ospfGlobals OBJECT IDENTIFIER  ::= { ipRoute 5 }

ospfGlobalsLeakRIPIntoOSPF OBJECT-TYPE
	SYNTAX INTEGER {
		enable(1),
		disable(2)
		}
	ACCESS  read-write
	STATUS  mandatory
	DESCRIPTION
	"Whenever to leak (redistribute) routes learned from RIP protocol into
	the domain of the OSPF protocol."
	DEFVAL  { disable }
	::=   { ospfGlobals 1 }

ospfGlobalsLeakStaticIntoOSPF OBJECT-TYPE
	SYNTAX INTEGER {
		enable(1),
		disable(2)
		}
	ACCESS  read-write
	STATUS  mandatory
	DESCRIPTION
	"Whenever to leak (redistribute) routes learned from Static Route into
	the domain of the OSPF protocol."
	DEFVAL  { enable }
	::=   { ospfGlobals 2 }

ospfGlobalsLeakDirectIntoOSPF OBJECT-TYPE
	SYNTAX INTEGER {
		enable(1),
		disable(2)
		}
	ACCESS  read-write
	STATUS  mandatory
	DESCRIPTION
	"Whenever to leak (redistribute) routes learned from Direct into
	the domain of the OSPF protocol."
	DEFVAL  { enable }
	::=   { ospfGlobals 3 }
 

-- virtualLan Servers Table
-- This table contains information for DHCP SERVERs located on each VLAN.

relayTable OBJECT-TYPE
	SYNTAX  SEQUENCE OF RelayEntry
	ACCESS  not-accessible
	STATUS  mandatory
	DESCRIPTION
	"This table is an extention of vlConfTable, and is used to add/delete
	DHCP Servers to/from that table."
	::= { ipRoute 6 }

relayEntry OBJECT-TYPE
	SYNTAX  RelayEntry
	ACCESS  not-accessible
	STATUS  mandatory
	DESCRIPTION
	"The information concerning one of this entity's VLAN interfaces.
	An VLAN interface is a virtual connection to a switch."
	INDEX   { relayVlIndex }
	::= { relayTable 1 }

RelayEntry ::=
	SEQUENCE {
		relayVlIndex			INTEGER,
		relayVlPrimaryServerAddr	IpAddress,
		relayVlSeconderyServerAddr	IpAddress,
		relayVlStatus			RowStatus,
		relayVlRelayAddr		IpAddress
		}

relayVlIndex OBJECT-TYPE
	SYNTAX  INTEGER
	ACCESS  read-only
	STATUS  mandatory
	DESCRIPTION
	"A unique value for each interface.  Its value ranges between 1
	and the value of ifNumber. The value for each interface must
	remain constant at least from one re-initialization of the entity's
	network management system to the next re-initialization."
              ::= { relayEntry 1 }

relayVlPrimaryServerAddr OBJECT-TYPE
	SYNTAX  IpAddress
	ACCESS  read-write
	STATUS  mandatory
	DESCRIPTION
	"The IP address of the primary server, to which the BOOTP/DHCP
	requests to be sent."
	::= { relayEntry 2 }

relayVlSeconderyServerAddr OBJECT-TYPE
	SYNTAX  IpAddress
	ACCESS  read-write
	STATUS  mandatory
	DESCRIPTION
	"The IP address of the secondary server, to which the BOOTP/DHCP
	requests to be sent."
	::= { relayEntry 3 }

relayVlStatus OBJECT-TYPE
	SYNTAX RowStatus
	ACCESS  read-write
	STATUS  mandatory
	DESCRIPTION
	" For deleting an DHCP/BOOTP servers entry. The entry will be deleted upon
	deleting the corresponding VLAN"
	::= { relayEntry 4 }

relayVlRelayAddr OBJECT-TYPE
	SYNTAX  IpAddress
	ACCESS  read-write
	STATUS  mandatory
	DESCRIPTION
	"The IP address of the Relay, i.e. the router's IP address to write in the relayed request
	(giaddr field in the Bootp packet). When there are multiple IP interfaces on the same
	VLAN such that the router has multiple IP addresses on the VLAN, the user can configure 
	which of these addresses to use when relaying requests arriving on this VLAN. 
	This relay address is used by the server to determines the subnet from which the address 
	shall be allocated. The special value 255.255.255.255 means DUPLICATE. 
	In this case the Relay will duplicate each request arriving on this VLAN and send to 
	the server multiple copies of the request, a copy for each of the router's IP addresses 
	on that VLAN. The relay address in each copy of the request shall be the router's 
	IP address (NOT 255.255.255.255). The special value 0.0.0.0 means that the router shall 
	use the Default value (lowest IP address on the VLAN) for the relay address"
	::= { relayEntry 5 }

-- IP ACCESS Global Parameters Group.
ipAccessGlobals OBJECT IDENTIFIER  ::= { ipRoute 7 }

ipAccessControlEnable OBJECT-TYPE
	SYNTAX INTEGER {
		enable(1),
		disable(2)
		}
	ACCESS  read-write
	STATUS  mandatory
	DESCRIPTION
	" Whenever to activate the IP ACCESS CONTROL statements on the device.
	disable means don't activate IP ACCESS CONTROL over all the IP statements
	enable means activate IP ACCESS CONTROL over all the IP statements "
	DEFVAL  { disable }
	::=   { ipAccessGlobals 1 }

-- The IP Access Control Table
-- This table contains parameters to define access control statements

ipAccessControlTable OBJECT-TYPE
	SYNTAX  SEQUENCE OF IpAccessControlEntry
	ACCESS  not-accessible
	STATUS  mandatory
	DESCRIPTION
	"This table is used to add/delete access control statement
	to/from that table."
	::= { ipRoute 8 }

ipAccessControlEntry OBJECT-TYPE
	SYNTAX  IpAccessControlEntry
	ACCESS  not-accessible
	STATUS  mandatory
	DESCRIPTION
	"The information concerning one of this entity's IP interfaces.
	An IP interface is a logical connection to a certain IP net/subnet."
	INDEX   { ipAccessControlIndex }
	::= { ipAccessControlTable 1 }

IpAccessControlEntry ::=
	SEQUENCE {
		ipAccessControlIndex		INTEGER,
		ipAccessControlSrcAddr		IpAddress,
		ipAccessControlSrcMask		IpAddress,
		ipAccessControlDstAddr		IpAddress,
		ipAccessControlDstMask		IpAddress,
		ipAccessControlOperation		INTEGER,
		ipAccessControlActivation	INTEGER,
		ipAccessControlProtocol		INTEGER,
		ipAccessControlApplication	INTEGER,
		ipAccessControlStatus		RowStatus
		}

ipAccessControlIndex OBJECT-TYPE
	SYNTAX  INTEGER
	ACCESS  read-only
	STATUS  mandatory
	DESCRIPTION
	"Entry index."
	::= { ipAccessControlEntry 1 }

ipAccessControlSrcAddr OBJECT-TYPE
	SYNTAX  IpAddress
	ACCESS  read-write
	STATUS  mandatory
	DESCRIPTION
	"The IP address of the source address."
	::= { ipAccessControlEntry 2 }

ipAccessControlSrcMask OBJECT-TYPE
	SYNTAX  IpAddress
	ACCESS  read-write
	STATUS  mandatory
	DESCRIPTION
	"The MASK address of the source address."
	::= { ipAccessControlEntry 3 }

ipAccessControlDstAddr OBJECT-TYPE
	SYNTAX  IpAddress
	ACCESS  read-write
	STATUS  mandatory
	DESCRIPTION
	"The IP address of the destination address."
	::= { ipAccessControlEntry 4 }

ipAccessControlDstMask OBJECT-TYPE
	SYNTAX  IpAddress
	ACCESS  read-write
	STATUS  mandatory
	DESCRIPTION
	"The MASK address of the destination address."
	::= { ipAccessControlEntry 5 }

ipAccessControlOperation OBJECT-TYPE
	SYNTAX INTEGER {
		forward(1),
		block(2),
		blockAndReport(3)
		}
	ACCESS  read-write
	STATUS  mandatory
	DESCRIPTION
	"How to operate the IP ACCESS CONTROL statement, on the receiving packet.
	Forwards the packet, Block (Discard) the packet or block (Discard) the packet
	and report to the user by sending trap."
	::=   { ipAccessControlEntry 6 }

ipAccessControlActivation OBJECT-TYPE
	SYNTAX INTEGER {
		wire-speed(1),
		regular(2)
		}
	ACCESS  read-write
	STATUS  mandatory
	DESCRIPTION
	"Does the IP ACCESS CONTROL statement done by HW or SW(CPU).
	HW - wire-speed, SW - regular."
	::=   { ipAccessControlEntry 7 }

ipAccessControlProtocol OBJECT-TYPE
	SYNTAX INTEGER {
		icmp(1),
		tcp(6),
		udp(17),
		none(256)
		}
	ACCESS  read-write
	STATUS  mandatory
	DESCRIPTION
	"Over which protocol does the IP ACCESS CONTROL statement activate.
	Icmp, Tcp, Udp. None - means IP addresses only"
	::=   { ipAccessControlEntry 8 }

ipAccessControlApplication OBJECT-TYPE
	SYNTAX INTEGER {
		ftp(21),
		telnet(23),
		smtp(25),
		http(80),
		pop3(110),
		snmp(161),
		snmpTrap(162),
		above1023(65536),
		none(65537)
		}
	ACCESS read-write
	STATUS mandatory
	DESCRIPTION
	"Over which application does the IP ACCESS CONTROL statement activate.
	The exception are: above1023 can work over TCP or UDP, none can't  work
	over TCP or UDP or ICMP only none is excepted"
	::=   { ipAccessControlEntry 9 }

ipAccessControlStatus OBJECT-TYPE
	SYNTAX RowStatus
	ACCESS read-write
	STATUS mandatory
	DESCRIPTION
	"For create/delete of a IP ACCESS CONTROL statement."
	::= { ipAccessControlEntry 10 }

-- IP Redundancy Global Parameters Group.
ipRedundancyGlobals OBJECT IDENTIFIER  ::= { ipRoute 9 }

ipRedundancyStatus OBJECT-TYPE
	SYNTAX INTEGER {
		enable(1),
		disable(2),
		inactive(3),
		active(4)
		}
	ACCESS  read-write
	STATUS  mandatory
	DESCRIPTION
	"Whenever to activate the IP REDUNDANCY mechanism on the device.
	enable  -	set by the user,
		means activate the IP REDUNDANCY mechanism over the defined IP interfaces.
	disable -	set by the user,
		means don't active the IP REDUNDANCY mechanism over the defined IP interfaces.
	inactive - set by the device (status),
		means the backup interface is in stand-by  (after enable operation).
	active - 	set by the device (status),
		means the backup interface is working (after time-out)."
	DEFVAL  { disable }
	::=   { ipRedundancyGlobals 1 }

ipRedundancyTimeout OBJECT-TYPE
	SYNTAX INTEGER
	ACCESS read-write
	STATUS mandatory
	DESCRIPTION
	"Time-out required to activate the backup process of IP REDUNDANCY. After Time-out
	the Redundant router assumes that the main (Backuped) router is not operational, and takes
	control over all defined IP interfaces of the main.
	The value is in seconds.
	The default value is 12"
	DEFVAL  { 12 }
	::=   { ipRedundancyGlobals 2 }

ipRedundancyPollingInterval OBJECT-TYPE
	SYNTAX INTEGER
	ACCESS read-write
	STATUS mandatory
	DESCRIPTION
	"The polling interval used to poll the Main (Backed up) router.
	The value is multiply of ipRedundancyTimeout.
	The value is in seconds.
	The default value is 3"
	DEFVAL  { 3 }
	::=   { ipRedundancyGlobals 3 }

-- Short-Cut Global Parameters Group.
ipShortcutGlobals OBJECT IDENTIFIER  ::= { ipRoute 10 }

ipShortcutARPServerStatus OBJECT-TYPE
	SYNTAX INTEGER {
		enable(1),
		disable(2)
		}
	ACCESS read-write
	STATUS mandatory
	DESCRIPTION
	"Whenever to activate the ARP Server mechanism on the device.
	enable  -	set by the user,
		means activate the ARP Server mechanism over the defined IP interfaces.
	disable -	set by the user,
		means don't active the ARP Server mechanism over the defined IP interfaces."
	DEFVAL  { disable }
	::=   { ipShortcutGlobals 1 }

-- The IP Multicast Table
-- This table contains parameters to define multicast parameters

ipMulticastInterfaceTable OBJECT-TYPE
	SYNTAX SEQUENCE OF IpMulticastInterfaceEntry
	ACCESS not-accessible
	STATUS mandatory
	DESCRIPTION
	"This table is used to update multicast parameters
	over interfaces already define"
	::= { ipRoute 11 }

ipMulticastInterfaceEntry OBJECT-TYPE
	SYNTAX IpMulticastInterfaceEntry
	ACCESS not-accessible
	STATUS mandatory
	DESCRIPTION
	"The information concerning one of this entity's interfaces."
	INDEX   { ipMulticastInterfaceIfIndex }
	::= { ipMulticastInterfaceTable 1 }

IpMulticastInterfaceEntry ::=
	SEQUENCE {
		ipMulticastInterfaceIfIndex	INTEGER,
		ipMulticastInterfaceSendAll	INTEGER,
		ipMulticastInterfaceState		INTEGER,
		ipMulticastInterfaceStatus		RowStatus
		}

ipMulticastInterfaceIfIndex OBJECT-TYPE
	SYNTAX INTEGER
	ACCESS read-only
	STATUS mandatory
	DESCRIPTION
	"A unique value for each interface.  Its value ranges between 1
	and the value of ifNumber. The value for each interface must
	remain constant at least from one re-initialization of the entity's
	network management system to the next re-initialization."
              ::= { ipMulticastInterfaceEntry 1 }

ipMulticastInterfaceSendAll OBJECT-TYPE
	SYNTAX INTEGER {
		enable(1),
		disable(2)
		}
	ACCESS read-write
	STATUS mandatory
	DESCRIPTION
	"The user will be able to configure whenever to send the all Multicast
	packets to this interface.
	Enable - Enable the user to define this interface, over all the existing groups
	Disable - Will acts according to the other parameters."
	DEFVAL  { disable }
	::=   { ipMulticastInterfaceEntry 2 }

ipMulticastInterfaceState OBJECT-TYPE
	SYNTAX INTEGER {
		active(1),
		inactive(2)
		}
	ACCESS  read-only
	STATUS  mandatory
	DESCRIPTION
	"The current state (operational) of the IP Multicast from IP Multicast point of view.
	It depends on global ipMRouteEnable status and Multicast interface status.
	Inactive - set by the device (status), 
                Global IP multicast is disabled or Multicast is disable on this interface. 
	Active - set by the device (status), 
              Global IP multicast is enable and Multicast is active on this interface."
	::=   { ipMulticastInterfaceEntry 3 }

ipMulticastInterfaceStatus OBJECT-TYPE
	SYNTAX RowStatus
	ACCESS  read-write
	STATUS  mandatory
	DESCRIPTION
	"For enable/disable of a IP multicast over an interface."
	DEFVAL  { active }
	::= { ipMulticastInterfaceEntry 4 }


--
-- EZ2R parameters
--
ipEZ2RouteMgmt OBJECT IDENTIFIER ::= { ipRoute 13 }
 
ipEZ2BoostRouterTable OBJECT-TYPE
	SYNTAX  SEQUENCE OF IpEZ2BoostRouterEntry
	ACCESS  not-accessible
	STATUS  mandatory
	DESCRIPTION
	""
	::= { ipEZ2RouteMgmt 1 }

ipEZ2BoostRouterEntry OBJECT-TYPE
	SYNTAX  IpEZ2BoostRouterEntry
	ACCESS  not-accessible
	STATUS  mandatory
	DESCRIPTION
	""
	INDEX   { ipEZ2BoostRouterSlot, ipEZ2BoostRouterBRAddress }
	::= { ipEZ2BoostRouterTable 1 }

IpEZ2BoostRouterEntry ::=
	SEQUENCE {
		ipEZ2BoostRouterSlot		INTEGER,
		ipEZ2BoostRouterBRAddress	IpAddress,
		ipEZ2BoostRouterType		INTEGER,
		ipEZ2BoostRouterStatus		RowStatus
		}

ipEZ2BoostRouterSlot OBJECT-TYPE
	SYNTAX  INTEGER
	ACCESS  read-only
	STATUS  mandatory
	DESCRIPTION
	""
	::= { ipEZ2BoostRouterEntry 1 }

ipEZ2BoostRouterBRAddress OBJECT-TYPE
	SYNTAX  IpAddress
	ACCESS  read-only
	STATUS  mandatory
	DESCRIPTION
	""
	::= { ipEZ2BoostRouterEntry 2 }

ipEZ2BoostRouterType OBJECT-TYPE
	SYNTAX  INTEGER {
		dynamic (1),
		static (2)
		}
	ACCESS  read-only
	STATUS  mandatory
	DESCRIPTION
	""
	::= { ipEZ2BoostRouterEntry 3 }

ipEZ2BoostRouterStatus OBJECT-TYPE
	SYNTAX RowStatus
	ACCESS  read-write
	STATUS  mandatory
	DESCRIPTION
	""
	::= { ipEZ2BoostRouterEntry 4 }

--
-- Control of EZ2route activities Table
--
ipEZ2RControlTable OBJECT-TYPE
	SYNTAX  SEQUENCE OF IpEZ2RControlEntry
	ACCESS  not-accessible
	STATUS  mandatory
	DESCRIPTION
	""
	::= { ipEZ2RouteMgmt 2 }

ipEZ2RControlEntry OBJECT-TYPE
	SYNTAX  IpEZ2RControlEntry
	ACCESS  not-accessible
	STATUS  mandatory
	DESCRIPTION
	""
	INDEX   { ipEZ2RControlSlot }
	::= { ipEZ2RControlTable 1 }

IpEZ2RControlEntry ::=
	SEQUENCE {
		ipEZ2RControlSlot			INTEGER,
		ipEZ2RControlBoostedRoutersTimeout	INTEGER,
		ipEZ2RControlHostsTimeout		INTEGER,
		ipEZ2RControlAutoLearnMode		INTEGER
		}

ipEZ2RControlSlot OBJECT-TYPE
	SYNTAX  INTEGER
	ACCESS read-only 
	STATUS  mandatory
	DESCRIPTION
	""
	::= { ipEZ2RControlEntry 1 }

ipEZ2RControlBoostedRoutersTimeout OBJECT-TYPE
	SYNTAX INTEGER (5..9999999)
	ACCESS read-write
	STATUS mandatory
	DESCRIPTION
	"Set the timeout of EZ2route routers"
	DEFVAL {900}
	::= { ipEZ2RControlEntry 2 }

ipEZ2RControlHostsTimeout OBJECT-TYPE
	SYNTAX INTEGER (300..9999999)
	ACCESS read-write
	STATUS mandatory
	DESCRIPTION
	"Set the timeout of EZ2route hosts"
	DEFVAL {14400}
	::= { ipEZ2RControlEntry 3 } 

ipEZ2RControlAutoLearnMode OBJECT-TYPE
	SYNTAX  INTEGER {
		enable (1),
		disable (2)
		}
	ACCESS  read-write
	STATUS  mandatory
	DESCRIPTION
	""
	DEFVAL {enable}
	::= { ipEZ2RControlEntry 5 }

--
-- VRRP parameters
--
ipVRRP OBJECT IDENTIFIER ::= { ipRoute 14 }
 
ipVRRPAdminStatus OBJECT-TYPE
	SYNTAX  INTEGER {
		enable (1),
		disable (2)
		}
	ACCESS  read-write
	STATUS  mandatory
	DESCRIPTION
	"Global switch to enable/disable VRRP"
	DEFVAL {disable}
	::= { ipVRRP 1 }
 

--
-- IPX Routing Group.
--
ipxRoute OBJECT IDENTIFIER  ::= { croute 2 }

--
-- The IPX Circuit Table
-- This table contains all the parameters to configure the IPX Circuits
--
ipxCircTable OBJECT-TYPE
	SYNTAX  SEQUENCE OF IpxCircEntry
	ACCESS  not-accessible
	STATUS  mandatory
	DESCRIPTION
	"This table is an extention of Novell mib IpxCircTable, and is used to
	add/delete entries to/from that table. In addition it contains private objects."
	::= { ipxRoute 1 }

ipxCircEntry OBJECT-TYPE
	SYNTAX  IpxCircEntry
	ACCESS  not-accessible
	STATUS  mandatory
	DESCRIPTION
	"The information concerning one of this entity's IPX circuits.
	An IPX circuit is a logical connection to a certain IPX netNumber."
	INDEX   { ipxCircIndex }
	::= { ipxCircTable 1 }

IpxCircEntry ::=
	SEQUENCE {
		ipxCircIndex			INTEGER,
		ipxCircNetNumber		NetNum,
		ipxCircLowerIfAlias		DisplayString,
		ipxCircEncapsulation		INTEGER,
		ipxCircNetbios			INTEGER,
		ipxCircStatus			RowStatus,
		ipxCircRipStatus			INTEGER,
		ipxCircRipUpdate		INTEGER,
		ipxCircRipAgeMultiplier		INTEGER,
		ipxCircSapUpdate		INTEGER,
		ipxCircSapAgeMultiplier		INTEGER,
		ipxCircGetNearestServerReply	INTEGER,
		ipxCircSapStatus			INTEGER,
		ipxCircRipState			INTEGER,
		ipxCircSapState			INTEGER
		}

ipxCircIndex OBJECT-TYPE
	SYNTAX INTEGER
	ACCESS read-only
	STATUS mandatory
	DESCRIPTION
	"The identifier of this circuit, unique within the instance of IPX.
	This value may be written only when creating a new entry in the table."
	::= { ipxCircEntry 1 }

ipxCircNetNumber OBJECT-TYPE
	SYNTAX NetNum
	ACCESS read-write
	STATUS mandatory
	DESCRIPTION
	"The IPX network number of this circuit."
	::= { ipxCircEntry 2 }

ipxCircLowerIfAlias OBJECT-TYPE
	SYNTAX DisplayString	(SIZE(0..16))
	ACCESS read-write
	STATUS mandatory
	DESCRIPTION
	"This object is an 'alias' name for the lower-layer interface on top
	of which this IP interface is defined. The alias is specified 
	by the network manager, and provides a non-volatile 'handle'
	for the lower-layer interface.
	The semantics of the object are similar to the semantics of
	the ifAlias object, defined by the Interfaces MIB. At the time 
	when this Madge MIB object was defined, the latest release
	of the Interfaces MIB was draft-ietf-ifmib-mib-05.txt. The
	purpose is to support all methods (static or dynamic) for creation 
	of interfaces and to allow creation of IPX table entries without the need 
	of the layer 2 interface to be present on the device at the time of the
	creation. It is assumed that some implementation dependent mechanisms
	allow the IPX application to be informed about the creation of new lower
	layer interfaces."
	::= { ipxCircEntry 3 }

ipxCircEncapsulation OBJECT-TYPE
	SYNTAX INTEGER {
		other(1),
		novell(2),
		ethernet(3),
		llc(4),
		snap(5)
		}
	ACCESS read-write
	STATUS mandatory
	DESCRIPTION
	"The media type (encapsulation of layer2) of this circuit."
	::= { ipxCircEntry 4 }

ipxCircNetbios OBJECT-TYPE
	SYNTAX INTEGER {
		enable(1),
		disable(2)
		}
	ACCESS read-write
	STATUS mandatory
	DESCRIPTION
	"The type of the circuit."
	DEFVAL  { enable }
	::= { ipxCircEntry 5 }

ipxCircStatus OBJECT-TYPE
	SYNTAX RowStatus
	ACCESS read-write
	STATUS mandatory
	DESCRIPTION
	" For adding and deleting Circuits. Deleting this row means deleting
	the corresponding entry in ipxCircTable. Deleting a Circuit also
	causes deletion of all static routes defined on this Circuit, 
	as well as protocol Circuit (e.g. RIP and SAP) defined on	this Circuit."
	::= { ipxCircEntry 6 }

ipxCircRipUpdate OBJECT-TYPE
	SYNTAX INTEGER
	ACCESS read-write
	STATUS mandatory
	DESCRIPTION
	"The RIP periodic update interval, in seconds."
	DEFVAL  { 60 }
	::= { ipxCircEntry 7 }

ipxCircRipAgeMultiplier OBJECT-TYPE
	SYNTAX INTEGER
	ACCESS read-write
	STATUS mandatory
	DESCRIPTION
	"The holding multiplier for information received in RIP periodic updates."
	DEFVAL {4}
	::= { ipxCircEntry 8}

ipxCircRipStatus OBJECT-TYPE
	SYNTAX INTEGER {
		enable(1),
		disable(2)
		}
	ACCESS read-write
	STATUS mandatory
	DESCRIPTION
	"Indicates whether RIP information may be sent/received over this circuit.
	Set by the user"
	DEFVAL {enable}
	::= { ipxCircEntry 9 }

ipxCircSapUpdate OBJECT-TYPE
	SYNTAX INTEGER
	ACCESS read-write
	STATUS mandatory
	DESCRIPTION
	"The SAP periodic update interval, in seconds."
	DEFVAL {60}
	::= { ipxCircEntry 10 }

ipxCircSapAgeMultiplier OBJECT-TYPE
	SYNTAX INTEGER
	ACCESS read-write
	STATUS mandatory
	DESCRIPTION
	"The holding multiplier for information received in SAP periodic updates."
	DEFVAL      {4}
	::= { ipxCircEntry 11}

ipxCircGetNearestServerReply OBJECT-TYPE
	SYNTAX INTEGER {
		enable(1),
		disable(2)
		}
	ACCESS read-write
	STATUS mandatory
	DESCRIPTION
	"Indicates whether to respond to SAP get nearest server requests
	 received on this circuit."
	DEFVAL      {enable}
	::= { ipxCircEntry 12 }

ipxCircSapStatus OBJECT-TYPE
	SYNTAX INTEGER {
		enable(1),
		disable(2)
		}
	ACCESS read-write
	STATUS mandatory
	DESCRIPTION
	"Indicates whether SAP information may be sent/received over this circuit."
	DEFVAL      {enable}
	::= { ipxCircEntry 13 }

ipxCircRipState OBJECT-TYPE
	SYNTAX INTEGER {
		active(1),
		inactive(2)
		}
	ACCESS read-only
	STATUS mandatory
	DESCRIPTION
	"Indicates whether RIP information may be sent/received over this circuit.
	Set by the device to reflect the RIP status and the interface status"
	DEFVAL { active }
	::= { ipxCircEntry 14 }

ipxCircSapState OBJECT-TYPE
	SYNTAX INTEGER {
		active(1),
		inactive(2)
		}
	ACCESS read-only
	STATUS mandatory
	DESCRIPTION
	"Indicates whether SAP information may be sent/received over this circuit.
	Set by the device to reflect the SAP status and the interface status"
	DEFVAL { active }
	::= { ipxCircEntry 15 }


-- The IPX RIP Table
-- This table contains all the parameters to configure the IPX Routes

ipxDestTable OBJECT-TYPE
	SYNTAX SEQUENCE OF IpxDestEntry
	ACCESS not-accessible
	STATUS mandatory
	DESCRIPTION
	"This table replace the Novell mib IpxDestTable, and is used to
	add/delete entries to/from that table."
	::= { ipxRoute 2 }

ipxDestEntry OBJECT-TYPE
	SYNTAX IpxDestEntry
	ACCESS not-accessible
	STATUS mandatory
	DESCRIPTION
	"The information concerning one of this entity's IPX Routes.
	An IPX service is a logical connection to a certain IPX Server."
	INDEX { ipxDestNetNum }
	::= { ipxDestTable 1 }

IpxDestEntry ::=
	SEQUENCE {
		ipxDestNetNum			NetNum,
		ipxDestProtocol			INTEGER,
		ipxDestTicks			INTEGER,
		ipxDestHopCount		INTEGER,
		ipxDestNextHopCircIndex		INTEGER,
		ipxDestNextHopNICAddress	PhysAddress,
		ipxDestNextHopNetNum		NetNum,
		ipxDestStatus			RowStatus,
		ipxDestAge			INTEGER
		}

ipxDestNetNum OBJECT-TYPE
	SYNTAX NetNum
	ACCESS read-only
	STATUS mandatory
	DESCRIPTION
	"The IPX network number portion of the IPX address of the destination."
	::= {ipxDestEntry 1}

ipxDestProtocol OBJECT-TYPE
	SYNTAX INTEGER {
		other(1),
		local(2),
		rip(3),
		nlsp(4),
		static(5)
		}
	ACCESS read-only
	STATUS mandatory
	DESCRIPTION
	"The routing protocol from which knowledge of this destination was obtained."
	::= {ipxDestEntry 2}

ipxDestTicks OBJECT-TYPE
	SYNTAX INTEGER
	ACCESS read-write
	STATUS mandatory
	DESCRIPTION
	"The delay in ticks to reach this destination."
	::= {ipxDestEntry 3}

ipxDestHopCount OBJECT-TYPE
	SYNTAX INTEGER
	ACCESS read-write
	STATUS mandatory
	DESCRIPTION
	"The number of hops necessary to reach the destination."
	::= {ipxDestEntry 4}

ipxDestNextHopCircIndex OBJECT-TYPE
	SYNTAX INTEGER
	ACCESS read-write
	STATUS mandatory
	DESCRIPTION
	"The unique identifier of the circuit, used to reach the next hop."
	::= {ipxDestEntry 5}

ipxDestNextHopNICAddress OBJECT-TYPE
	SYNTAX PhysAddress
	ACCESS read-write
	STATUS mandatory
	DESCRIPTION
	"The NIC address of the next hop."
	::= {ipxDestEntry 6}

ipxDestNextHopNetNum OBJECT-TYPE
	SYNTAX NetNum
	ACCESS read-write
	STATUS mandatory
	DESCRIPTION
	"The IPX network number of the next hop."
	::= {ipxDestEntry 7}

ipxDestStatus OBJECT-TYPE
	SYNTAX RowStatus
	ACCESS read-write
	STATUS mandatory
	DESCRIPTION
	""
	::= {ipxDestEntry 8}

ipxDestAge OBJECT-TYPE
	SYNTAX INTEGER
	ACCESS read-only
	STATUS mandatory
	DESCRIPTION
	"The age of the Routing table entry."
	::= { ipxDestEntry 9}


-- The IPX SAP Table
-- This table contains all the parameters to configure the IPX Services

ipxServTable OBJECT-TYPE
	SYNTAX SEQUENCE OF IpxServEntry
	ACCESS not-accessible
	STATUS mandatory
	DESCRIPTION
	"This table replace the Novell mib IpxServTable, and is used to
	add/delete entries to/from that table."
	::= { ipxRoute 3 }

ipxServEntry OBJECT-TYPE
	SYNTAX IpxServEntry
	ACCESS not-accessible
	STATUS mandatory
	DESCRIPTION
	"The information concerning one of this entity's IPX Services.
	An IPX service is a logical connection to a certain IPX Server."
	INDEX { ipxServType,
		 ipxServName }
	::= { ipxServTable 1 }

IpxServEntry ::=
	SEQUENCE {
		ipxServType			INTEGER,
		ipxServName			DisplayString,
		ipxServProtocol			INTEGER,
		ipxServNetNum			NetNum,
		ipxServNode			OCTET STRING,
		ipxServSocket			INTEGER,
		ipxServHopCount		INTEGER,
		ipxServStatus			RowStatus,
		ipxServAge			INTEGER
		}

ipxServType OBJECT-TYPE
	SYNTAX INTEGER
	ACCESS read-only
	STATUS mandatory
	DESCRIPTION
	"The service type."
	::= {ipxServEntry 1}

ipxServName OBJECT-TYPE
	SYNTAX DisplayString (SIZE(1..48))
	ACCESS read-only
	STATUS mandatory
	DESCRIPTION
	"The server name."
	::= {ipxServEntry 2}

ipxServProtocol OBJECT-TYPE
	SYNTAX INTEGER {
		other(1),
		local(2),
		nlsp(4),
		static(5),
		sap(6)
		}
	ACCESS read-only
	STATUS mandatory
	DESCRIPTION
	"The protocol from which knowledge of this service was obtained."
	::= {ipxServEntry 3}

ipxServNetNum OBJECT-TYPE
	SYNTAX NetNum
	ACCESS read-write
	STATUS mandatory
	DESCRIPTION
	"The IPX network number portion of the IPX address of the service."
	::= {ipxServEntry 4}

ipxServNode OBJECT-TYPE
	SYNTAX OCTET STRING (SIZE(6))
	ACCESS read-write
	STATUS mandatory
	DESCRIPTION
	"The node portion of the IPX address of the service."
	::= {ipxServEntry 5}

ipxServSocket OBJECT-TYPE
	SYNTAX INTEGER
	ACCESS read-write
	STATUS mandatory
	DESCRIPTION
	"The socket portion of the IPX address of the service."
	::= {ipxServEntry 6}

ipxServHopCount OBJECT-TYPE
	SYNTAX INTEGER
	ACCESS read-write
	STATUS mandatory
	DESCRIPTION
	"The number of hops to the service."
	::= {ipxServEntry 7}

ipxServStatus OBJECT-TYPE
	SYNTAX RowStatus
	ACCESS read-write
	STATUS mandatory
	DESCRIPTION
	""
	::= {ipxServEntry 8}

ipxServAge OBJECT-TYPE
	SYNTAX INTEGER
	ACCESS read-only
	STATUS mandatory
	DESCRIPTION
	"The age of the SAP entry."
	::= { ipxServEntry 9}


-- IPX ACCESS Global Parameters Group.
ipxAccessGlobals OBJECT IDENTIFIER  ::= { ipxRoute 4 }

ipxAccessControlEnable OBJECT-TYPE
	SYNTAX INTEGER {
		enable(1),
		disable(2)
		}
	ACCESS read-write
	STATUS mandatory
	DESCRIPTION
	"Whenever to activate the IPX ACCESS CONTROL statements on the device.
	disable means don't activate IPX ACCESS CONTROL over all the IPX statements
	enable means activate IPX ACCESS CONTROL over all the IPX statements "
	DEFVAL  { disable }
	::=   { ipxAccessGlobals 1 }

-- The IPX Access Control Table
-- This table contains parameters to define IPX access control statements

ipxAccessControlTable OBJECT-TYPE
	SYNTAX SEQUENCE OF IpxAccessControlEntry
	ACCESS not-accessible
	STATUS mandatory
	DESCRIPTION
	"This table is used to add/delete IPX access control statement
	to/from that table."
	::= { ipxRoute 5 }

ipxAccessControlEntry OBJECT-TYPE
	SYNTAX IpxAccessControlEntry
	ACCESS not-accessible
	STATUS mandatory
	DESCRIPTION
	"The information concerning one of this entity's IPX access control statements."
	INDEX   { ipxAccessControlIndex }
	::= { ipxAccessControlTable 1 }

IpxAccessControlEntry ::=
	SEQUENCE {
		ipxAccessControlIndex		INTEGER,
		ipxAccessControlSrcAddr		NetNum,
		ipxAccessControlDstAddr		NetNum,
		ipxAccessControlOperation	INTEGER,
		ipxAccessControlActivation	INTEGER,
		ipxAccessControlStatus		RowStatus
		}

ipxAccessControlIndex OBJECT-TYPE
	SYNTAX INTEGER
	ACCESS read-only
	STATUS mandatory
	DESCRIPTION
	"Entry index."
	::= { ipxAccessControlEntry 1 }

ipxAccessControlSrcAddr OBJECT-TYPE
	SYNTAX NetNum 
	ACCESS read-write
	STATUS mandatory
	DESCRIPTION
	"The IPX network of the source address."
	::= { ipxAccessControlEntry 2 }

ipxAccessControlDstAddr OBJECT-TYPE
	SYNTAX NetNum 
	ACCESS  read-write
	STATUS  mandatory
	DESCRIPTION
	"The IPX network of the destination address."
	::= { ipxAccessControlEntry 3 }

ipxAccessControlOperation OBJECT-TYPE
	SYNTAX INTEGER {
		forward(1),
		block(2),
		blockAndReport(3)
		}
	ACCESS read-write
	STATUS mandatory
	DESCRIPTION
	"How to operate the IPX ACCESS CONTROL statement, on the receiving packet.
	Forwards the packet, Block (Discard) the packet or block (Discard) the packet
	and report to the user by sending trap."
	::=   { ipxAccessControlEntry 4 }

ipxAccessControlActivation OBJECT-TYPE
	SYNTAX INTEGER {
		wire-speed(1),
		regular(2)
		}
	ACCESS  read-write
	STATUS  mandatory
	DESCRIPTION
	"Does the IPX ACCESS CONTROL statement done by HW or SW(CPU).
	HW - wire-speed, SW - regular."
	::=   { ipxAccessControlEntry 5 }

ipxAccessControlStatus OBJECT-TYPE
	SYNTAX RowStatus
	ACCESS  read-write
	STATUS  mandatory
	DESCRIPTION
	"For create/delete of an IPX ACCESS CONTROL statement."
	::= { ipxAccessControlEntry 6 }


-- IPX SAP Filter Global Parameters Group.
ipxSapFilterGlobals OBJECT IDENTIFIER  ::= { ipxRoute 6 }

ipxSapFilterEnable OBJECT-TYPE
	SYNTAX INTEGER {
		enable(1),
		disable(2)
		}
	ACCESS  read-write
	STATUS  mandatory
	DESCRIPTION
	"Whenever to activate the IPX SAP Filters statements on the device.
	disable means don't activate IPX SAP Filters over all the IPX SAP statements
	enable means activate IPX SAP Filter over all the IPX SAP statements "
	DEFVAL  { disable }
	::=   { ipxSapFilterGlobals 1 }

ipxSapFilterTable OBJECT-TYPE
	SYNTAX SEQUENCE OF IpxSapFilterEntry
	ACCESS not-accessible
	STATUS mandatory
	DESCRIPTION
	"Table of input/output SAP filter according to IPX circuit number."
	::= { ipxRoute 7 }

ipxSapFilterEntry OBJECT-TYPE
	SYNTAX IpxSapFilterEntry 
	ACCESS not-accessible
	STATUS mandatory
	DESCRIPTION
	"An entry in the SAP filter table"
	INDEX {ipxSapFilterID }
	::= {ipxSapFilterTable 1 }

IpxSapFilterEntry ::=
	SEQUENCE {
		ipxSapFilterID			INTEGER,
		ipxSapFilterCircIndex		INTEGER,
		ipxSapFilterServiceNetNumber	NetNum,
		ipxSapFilterServiceType		INTEGER,
		ipxSapFilterServerName		DisplayString (SIZE(1..48)),
		ipxSapFilterDirection		INTEGER,
		ipxSapFilterAction		INTEGER,
		ipxSapFilterStatus		RowStatus
		}

ipxSapFilterID OBJECT-TYPE
	SYNTAX INTEGER
	ACCESS read-only
	STATUS mandatory
	DESCRIPTION
	"ID of SAP filter. "
	::= {ipxSapFilterEntry  1}

ipxSapFilterCircIndex OBJECT-TYPE
	SYNTAX INTEGER
	ACCESS read-write
	STATUS mandatory
	DESCRIPTION
	".... 
	-- 0xffff means this is a global SAP filter "
	::= {ipxSapFilterEntry 2}

ipxSapFilterServiceNetNumber OBJECT-TYPE
	SYNTAX  NetNum
	ACCESS read-write
	STATUS mandatory
	DESCRIPTION
	"Number network of the filtered service. Value
	0xFFFFFFFF  applies for any network.
	DEFVAL {0xFFFFFFFF}"
	::= { ipxSapFilterEntry 3}

ipxSapFilterServiceType OBJECT-TYPE
	SYNTAX INTEGER
	ACCESS read-write
	STATUS mandatory
	DESCRIPTION
	"The type of the service which may be filtered; value 0xFFFF
	applies for all types of service and it's default
	DEFVAL {0xFFFF}"
	::= { ipxSapFilterEntry 4}

ipxSapFilterServerName OBJECT-TYPE
	SYNTAX DisplayString (SIZE(1..48))
	ACCESS read-write
	STATUS mandatory
	DESCRIPTION
	"The name of the service which may be filtered; wildcards (*)
	may be used in the end of the name.
	DEFVAL {*}"
	::= { ipxSapFilterEntry 5}

ipxSapFilterDirection OBJECT-TYPE
	SYNTAX INTEGER{
		input(1),
		output(2)
		}
	ACCESS read-write
	STATUS mandatory
	DESCRIPTION
	"Type of filter-input or output"
	::= { ipxSapFilterEntry 6}

ipxSapFilterAction OBJECT-TYPE
	SYNTAX INTEGER{
		 permit(1),
		deny(2) 
		}
	ACCESS read-write
	STATUS mandatory
	DESCRIPTION
	"Permit/deny receiving/transmitting of SAP entry"
	DEFVAL {permit}
	::= { ipxSapFilterEntry 7}

ipxSapFilterStatus OBJECT-TYPE
	SYNTAX RowStatus
	ACCESS read-write
	STATUS mandatory
	DESCRIPTION
	"...."
	::= {ipxSapFilterEntry  8}


-- Layer2 Group.
layer2 OBJECT IDENTIFIER  ::= { croute 3 } 

-- The VLAN interfaces Table
-- This table contains all the parameters to configure (set)  VLAN interfaces

vlConfTable OBJECT-TYPE
	SYNTAX  SEQUENCE OF VlConfEntry
	ACCESS  not-accessible
	STATUS  mandatory
	DESCRIPTION
	"This table is an extention of MIB II ifTable, and is used to
	add/delete entries to/from that table. In addition it contains private objects."
	::= { layer2 1 }

vlConfEntry OBJECT-TYPE
	SYNTAX  VlConfEntry
	ACCESS  not-accessible
	STATUS  mandatory
	DESCRIPTION
	"The information concerning one of this entity's VLAN interfaces.
	An VLAN interface is a virtual connection to a switch."
	INDEX   { vlConfIndex }
	::= { vlConfTable 1 }

VlConfEntry ::=
	SEQUENCE {
		vlConfIndex			INTEGER,
		vlConfAlias			DisplayString,
		vlConfStatus			RowStatus	
		}

vlConfIndex OBJECT-TYPE
	SYNTAX  INTEGER
	ACCESS  read-only
	STATUS  mandatory
	DESCRIPTION
	"A unique value for each interface.  Its value ranges between 1
	and the value of ifNumber. The value for each interface must
	remain constant at least from one re-initialization of the entity's
	network management system to the next re-initialization."
              ::= { vlConfEntry 1 }

vlConfAlias OBJECT-TYPE
	SYNTAX  DisplayString	(SIZE(0..16))
	ACCESS  read-write
	STATUS  mandatory
	DESCRIPTION
	"This object is an 'alias' name for the lower-layer interface on top
	of which this IP interface is defined. The alias is specified 
	by the network manager, and provides a non-volatile 'handle'
	for the lower-layer interface.
	The semantics of the object are similar to the semantics of
	the ifAlias object, defined by the Interfaces MIB. At the time 
	when this Madge MIB object was defined, the latest release
	of the Interfaces MIB was draft-ietf-ifmib-mib-05.txt. The
	purpose is to support all methods (static or dynamic) for creation 
	of interfaces and to allow creation of IP table entries without the need 
	of the layer 2 interface to be present on the device at the time of the
	creation. It is assumed that some implementation dependent mechanisms
	allow the IP application to be informed about the creation of new lower
	layer interfaces."
	::= { vlConfEntry 2 }

vlConfStatus OBJECT-TYPE
	SYNTAX RowStatus
	ACCESS  read-write
	STATUS  mandatory
	DESCRIPTION
	" For adding and deleting VLAN interfaces. Deleting this row means 
	deleting the corresponding entry in ifTable (MIB II). Deleting a VLAN
	interface is allowed only if IP interface is not defined on this VLAN."
	::= { vlConfEntry 3 }

-- virtualLan Bridge Table
-- This table contains information for group of VLANs, and VLANs belonging to it.

vlBridgeTable  OBJECT-TYPE
	SYNTAX SEQUENCE OF VlBridgeEntry
	ACCESS  not-accessible
	STATUS  mandatory
	DESCRIPTION
	"For each Bridge segment an entry of  this table specifies a set of VLANs,
	which it contains."
	::= { layer2 2 }

vlBridgeEntry   OBJECT-TYPE
	SYNTAX  VlBridgeEntry
	ACCESS  not-accessible
	STATUS  mandatory
	DESCRIPTION
	"A entry of this table specifies a Group of VLANs and VLANs belonging to it"
	INDEX  { vlBridgeProtocol, vlBridgeGroupIndex, vlBridgeIndex }
	::= { vlBridgeTable 1 }

VlBridgeEntry  ::=
	SEQUENCE {
		vlBridgeProtocol		INTEGER,
		vlBridgeGroupIndex	INTEGER,
		vlBridgeIndex		INTEGER,
		vlBridgeStatus		RowStatus
		}

vlBridgeProtocol  OBJECT-TYPE
	SYNTAX  INTEGER {
		other(1),  
		dec(2),
		netBios(3),
		appleTalk(4),
		sna(5),
		ipx(6)
		}
	ACCESS  read-only
	STATUS  mandatory
	DESCRIPTION
	"The protocol, supported by this VLAN. The meanings of the values are:
	other: none of the following. This VLAN includes any protocol except the 
                       following protocols. It is a bridging VLAN. L2 relies on a third-party
	          router to exchange traffic between nodes on different VLANs
	          of this type.
	dec       : This is a bridging VLAN, L2 relies on a third-party router to
	               exchange traffic between nodes on different DEC VALNs
	               of this type.
	netBios: This is a Bridging VLAN, L2 relies on a third-party router to
	              exchange traffic between nodes on different NetBIOS VLAN
	              of this type.
	appleTalk: This is a Bridging VLAN, L2 relies on a third-party router to
	              exchange traffic between nodes on different appleTalk VLAN
	              of this type.
	value of other(1) always exist"
	::= { vlBridgeEntry 1 }

vlBridgeGroupIndex  OBJECT-TYPE
	SYNTAX  INTEGER
	ACCESS  read-only
	STATUS  mandatory
	DESCRIPTION
	"A logical number, corresponded this group of VLANs"
	::= { vlBridgeEntry 2 }

vlBridgeIndex  OBJECT-TYPE
	SYNTAX  INTEGER
	ACCESS  read-only
	STATUS  mandatory
	DESCRIPTION
	"A logical number, corresponded this VLAN. Each VLAN
	is allowed to participate in ONE group only"
	::= { vlBridgeEntry 3 }

vlBridgeStatus  OBJECT-TYPE
	SYNTAX RowStatus
	ACCESS  read-write
	STATUS  mandatory
	DESCRIPTION
	"It is used to create or delete an entry"
	::= { vlBridgeEntry 4 }

-- Layer2 Global Parameters Group.
layer2Globals OBJECT IDENTIFIER  ::= { layer2 3 }

layer2GlobalsBridgeEnable OBJECT-TYPE
	SYNTAX INTEGER {
		enable(1),
		disable(2),
		backup(3),
		activeBackup(4)
		}
	ACCESS  read-write
	STATUS  mandatory
	DESCRIPTION
	" Whenever to activate the Bridge capability on the device.
	enable  -	set by the user,
		means activate the Bridge capability over the defined VLANs.
	disable -	set by the user,
		means don't active the Bridge capability.
	backup - set by the user,
		means the Bridge capability is in stand-by. It will enter to activeBackup mode
		after IP REDUNDANCY mechanism will enter to active mode.
	activeBackup -  set by the device (status),
		means the backup Bridge is working (after time-out of IP REDUNDANCY)."
	DEFVAL  { disable }
	::=   { layer2Globals 1 }

-- Device Management Group.
routeGroupMgmt OBJECT IDENTIFIER  ::= { croute 4 } 

--
-- Control of Device activities (at group level) Table
--
routeGroupTable OBJECT-TYPE
	SYNTAX SEQUENCE OF RouteGroupEntry
	ACCESS not-accessible
	STATUS mandatory
	DESCRIPTION
	""
	::= { routeGroupMgmt 1 }

routeGroupEntry OBJECT-TYPE
	SYNTAX RouteGroupEntry
	ACCESS not-accessible
	STATUS mandatory
	DESCRIPTION
	""
	INDEX   { routeGroupId }
	::= { routeGroupTable 1 }

RouteGroupEntry ::=
	SEQUENCE {
		routeGroupId		INTEGER,
		routeGroupRouteMode	INTEGER
		}

routeGroupId OBJECT-TYPE
	SYNTAX  INTEGER
	ACCESS read-only 
	STATUS  mandatory
	DESCRIPTION
	""
	::= { routeGroupEntry 1 }

routeGroupRouteMode  OBJECT-TYPE
	SYNTAX  INTEGER {
		secondLayer (1),
		ez2route (3),	
		router (5),
		routerAndWebSwitch (21),
		notSupported (255)
		}
	ACCESS read-write
	STATUS mandatory
	DESCRIPTION
	"A bit mask representing the routing mode of the module:
	bit 0 - L2 switching
	bit 1 - EZ2Route
	bit 2 - Router
	bit 3 - Rich L2
	bit 4 - WebSwitch (Load balance, application redirection).
	Currently, the following values for this bit mask are defined:
	secondLayer(1) - no routing. Behaves like P333T.
	ez2route (3) - no configuration is needed. Boosts external routers
	router (5) - Behaves like third layer switch.
	routerAndWebSwitch(21) - Perform routing and Load-Balancing or application redirection"
	::= { routeGroupEntry 2 }

-- Distributed Layer2 Group.
drLayer2 OBJECT IDENTIFIER  ::= { croute 5 } 

-- The DISTRIBUTED VLAN interfaces Table
-- This table is copy of the vlConfTable with an additional FIRST index 
--   of the module ID used for distribution purposes

drVlConfTable OBJECT-TYPE
	SYNTAX  SEQUENCE OF DrVlConfEntry
	ACCESS  not-accessible
	STATUS  mandatory
	DESCRIPTION
	"This table is an extention of MIB II ifTable, and is used to
	add/delete entries to/from that table. In addition it contains private objects."
	::= { drLayer2 1 }

drVlConfEntry OBJECT-TYPE
	SYNTAX  DrVlConfEntry
	ACCESS  not-accessible
	STATUS  mandatory
	DESCRIPTION
	"The information concerning one of this entity's VLAN interfaces.
	An VLAN interface is a virtual connection to a switch."
	INDEX   { drVlConfSlot, drVlConfIndex }
	::= { drVlConfTable 1 }

DrVlConfEntry ::=
	SEQUENCE {
	        drVlConfSlot                    INTEGER,
		drVlConfIndex			INTEGER,
		drVlConfAlias			DisplayString,
		drVlConfStatus			RowStatus	
		}

drVlConfSlot OBJECT-TYPE
	SYNTAX  INTEGER
	ACCESS  read-only
	STATUS  mandatory
	DESCRIPTION
	"The slot number of the module"
              ::= { drVlConfEntry 1 }

drVlConfIndex OBJECT-TYPE
	SYNTAX  INTEGER
	ACCESS  read-only
	STATUS  mandatory
	DESCRIPTION
	"A unique value for each interface.  Its value ranges between 1
	and the value of ifNumber. The value for each interface must
	remain constant at least from one re-initialization of the entity's
	network management system to the next re-initialization."
              ::= { drVlConfEntry 2 }

drVlConfAlias OBJECT-TYPE
	SYNTAX  DisplayString	(SIZE(0..16))
	ACCESS  read-write
	STATUS  mandatory
	DESCRIPTION
	"This object is an 'alias' name for the lower-layer interface on top
	of which this IP interface is defined. The alias is specified 
	by the network manager, and provides a non-volatile 'handle'
	for the lower-layer interface.
	The semantics of the object are similar to the semantics of
	the ifAlias object, defined by the Interfaces MIB. At the time 
	when this Madge MIB object was defined, the latest release
	of the Interfaces MIB was draft-ietf-ifmib-mib-05.txt. The
	purpose is to support all methods (static or dynamic) for creation 
	of interfaces and to allow creation of IP table entries without the need 
	of the layer 2 interface to be present on the device at the time of the
	creation. It is assumed that some implementation dependent mechanisms
	allow the IP application to be informed about the creation of new lower
	layer interfaces."
	::= { drVlConfEntry 3 }

drVlConfStatus OBJECT-TYPE
	SYNTAX RowStatus
	ACCESS  read-write
	STATUS  mandatory
	DESCRIPTION
	" For adding and deleting VLAN interfaces. Deleting this row means 
	deleting the corresponding entry in ifTable (MIB II). Deleting a VLAN
	interface is allowed only if IP interface is not defined on this VLAN."
	::= { drVlConfEntry 4 }









drIpRoute  OBJECT IDENTIFIER  ::= { croute 6 } 

-- The DISTRIBUTED IP interfaces Table
-- This table is copy of the ipInterfaceTable with an additional FIRST index 
--   of the module ID used for distribution purposes

drIpInterfaceTable OBJECT-TYPE
	SYNTAX  SEQUENCE OF DrIpInterfaceEntry
	ACCESS  not-accessible
	STATUS  mandatory
	DESCRIPTION
	"This table is an extention of MIB II IpAddrTable, and is used to
	add/delete entries to/from that table. In addition it contains private objects."
	::= { drIpRoute 1 }

drIpInterfaceEntry OBJECT-TYPE
	SYNTAX  DrIpInterfaceEntry
	ACCESS  not-accessible
	STATUS  mandatory
	DESCRIPTION
	"The information concerning one of this entity's IP interfaces.
	An IP interface is a logical connection to a certain IP net/subnet."
	INDEX   { drIpInterfaceSlot, drIpInterfaceAddr }
	::= { drIpInterfaceTable 1 }

DrIpInterfaceEntry ::=
	SEQUENCE {
		drIpInterfaceSlot			INTEGER,
		drIpInterfaceAddr		IpAddress,
		drIpInterfaceNetMask		IpAddress,
		drIpInterfaceLowerIfAlias		DisplayString,
		drIpInterfaceType		INTEGER,
		drIpInterfaceForwardIpBroadcast	INTEGER,
		drIpInterfaceBroadcastAddr	INTEGER,
		drIpInterfaceProxyArp		INTEGER,
		drIpInterfaceStatus		RowStatus,
		drIpInterfaceMainRouterAddr	IpAddress,
		drIpInterfaceARPServerStatus	INTEGER,
		drIpInterfaceName		DisplayString,
		drIpInterfaceNetbiosRebroadcast	INTEGER,
		drIpInterfaceIcmpRedirects	INTEGER
		}

drIpInterfaceSlot OBJECT-TYPE
	SYNTAX  INTEGER
	ACCESS  read-only
	STATUS  mandatory
	DESCRIPTION
	"The slot number of the module"
              ::= { drIpInterfaceEntry 1 }
	      
drIpInterfaceAddr OBJECT-TYPE
	SYNTAX  IpAddress
	ACCESS  read-only
	STATUS  mandatory
	DESCRIPTION
	"The IP address to which this entry's addressing information pertains."
	::= { drIpInterfaceEntry 2 }

drIpInterfaceNetMask OBJECT-TYPE
	SYNTAX  IpAddress
	ACCESS  read-write
	STATUS  mandatory
	DESCRIPTION
	"The subnet mask associated with the IP address of this entry.
	The value of the mask is an IP address with all the network bits
	set to 1 and all the hosts bits set to 0."
	::= { drIpInterfaceEntry 3 }

drIpInterfaceLowerIfAlias OBJECT-TYPE
	SYNTAX  DisplayString	(SIZE(0..16))
	ACCESS  read-write
	STATUS  mandatory
	DESCRIPTION
	"This object is an 'alias' name for the lower-layer interface on top
	of which this IP interface is defined. The alias is specified 
	by the network manager, and provides a non-volatile 'handle'
	for the lower-layer interface.
	The semantics of the object are similar to the semantics of
	the ifAlias object, defined by the Interfaces MIB. At the time 
	when this Madge MIB object was defined, the latest release
	of the Interfaces MIB was draft-ietf-ifmib-mib-05.txt. The
	purpose is to support all methods (static or dynamic) for creation 
	of interfaces and to allow creation of IP table entries without the need 
	of the layer 2 interface to be present on the device at the time of the
	creation. It is assumed that some implementation dependent mechanisms
	allow the IP application to be informed about the creation of new lower
	layer interfaces."
	::= { drIpInterfaceEntry 4 }

drIpInterfaceType OBJECT-TYPE
	SYNTAX  INTEGER {
		broadcast (1),
		nBMA (2),
		ptp (3)
		}
	ACCESS  read-write
	STATUS  mandatory
	DESCRIPTION
	"The logical type of the interface. The default depends on the physical type.
	For example Ethernet and Token-Ring LANs are of type broadcast"
	DEFVAL  { broadcast }
	::= { drIpInterfaceEntry 5 }

drIpInterfaceForwardIpBroadcast OBJECT-TYPE
	SYNTAX INTEGER {
		enable(1),
		disable(2)
		}
	ACCESS  read-write
	STATUS  mandatory
	DESCRIPTION
	" Whether the router forwards IP directed broadcasts that are to be
	transmitted as link-layer broadcast to an attached net or subnet. "
	DEFVAL  { enable }
	::=   { drIpInterfaceEntry 6 }

drIpInterfaceBroadcastAddr OBJECT-TYPE
	SYNTAX INTEGER
	ACCESS  read-write
	STATUS  mandatory
	DESCRIPTION
	"The value of the least-significant bit in the IP broadcast address used
	for sending datagrams on the (logical) interface associated with the IP
	address of this entry.
	For example, when the Internet standard all-ones broadcast address is
	used, the value will be 1. This value applies to both the subnet and
	network broadcasts addresses used by the entity on this (logical) interface."
	DEFVAL  { 1 }
	::=   { drIpInterfaceEntry 7 }

drIpInterfaceProxyArp OBJECT-TYPE
	SYNTAX INTEGER {
		enable(1),
		disable(2)
		}
	ACCESS  read-write
	STATUS  mandatory
	DESCRIPTION
	" When proxy ARP is enabled, the router responds to ARP 
	requests received on one link-layer interface for an IP-address 
	that is reachable via another link-layer interface. 
	The response provides the router's own MAC address. "
	DEFVAL  { disable }
	::=   { drIpInterfaceEntry 8 }

drIpInterfaceStatus OBJECT-TYPE
	SYNTAX RowStatus
	ACCESS  read-write
	STATUS  mandatory
	DESCRIPTION
	" For adding and deleting IP interfaces. Deleting this row means 
	deleting the corresponding entry in IpAddrTable (MIB II). Deleting an 
	IP interface also causes deletion of all static routes defined on this IP 
	interface, as well as protocol interfaces (e.g. RIP and OSPF) defined on 
	this IP interface."
	::= { drIpInterfaceEntry 9 }

drIpInterfaceMainRouterAddr OBJECT-TYPE
	SYNTAX  IpAddress
	ACCESS  read-write
	STATUS  mandatory
	DESCRIPTION
	"The IP address of the main router backed up on this interface."
	::= { drIpInterfaceEntry 10 }

drIpInterfaceARPServerStatus OBJECT-TYPE
	SYNTAX INTEGER {
		enable(1),
		disable(2)
		}
	ACCESS  read-write
	STATUS  mandatory
	DESCRIPTION
	"Whenever to activate the ARP Server mechanism on this interface.
	enable  -	set by the user,
		means activate the ARP Server mechanism over this IP interface.
	disable -	set by the user,
		means don't active the ARP Server mechanism over this IP interface."
	DEFVAL  { disable }
	::=   { drIpInterfaceEntry 11 }

drIpInterfaceName OBJECT-TYPE
	SYNTAX  DisplayString	(SIZE(0..32))
	ACCESS  read-write
	STATUS  mandatory
	DESCRIPTION
	"The name of this interface for compatibility with cli."
	::= { drIpInterfaceEntry 12 }


drIpInterfaceNetbiosRebroadcast OBJECT-TYPE
	SYNTAX INTEGER {
		inbound(1),
		outbound(2),
		both(3),
		disable(4)
		}
	ACCESS  read-write
	STATUS  mandatory        
	DESCRIPTION
	"inbound - netbios received from the interface are rebarodcasted,
	 outbound - netbios are rebraodcasted to this interface,
	 both - netbios are rebroadacsted both from and to this interface,
	disable - netbios is not rebraodcasted neither from nor to this interface.
	Currently only both and disable are supported"
	DEFVAL  { disable }
	::= { drIpInterfaceEntry 13 }

drIpInterfaceIcmpRedirects OBJECT-TYPE
	SYNTAX INTEGER {
		enable(1),
		disable(2)
		}
	ACCESS  read-write
	STATUS  mandatory        
	DESCRIPTION
	"enable - enable the sending of redirect messages if the router is forced to 
	                re-send a packet through the same interface on which it was received.
	disable - disable the sending of redirect messages on this interface."
	DEFVAL  { enable }
	::= { drIpInterfaceEntry 14 }


-- The DISTRIBUTED static Route Table, modeled after ipCidrRoute (RFC2096).
--  This table is copy of the ipCidrRouteTable with:
--  1. an additional FIRST index of the module ID used for 
--     distribution purposes. 
--  2. Internal Route type information (i.e. "Firewall Load Balancing group")
--  3. Operational status (active/inactive).
--  4. 'private' metric 5 method replaced by explicit precedence
-- 
-- NOTE: In P333RLB rev 3.2, the following implementation
-- restrictions will apply:
--  a. Table will be used only for FWLB routes
--  b. metric fields will not be implemented.

drStaticCidr  OBJECT IDENTIFIER  ::= { croute 7 }

drStaticCidrTable OBJECT-TYPE
    SYNTAX  SEQUENCE OF DrStaticCidrEntry
    ACCESS  not-accessible
    STATUS  mandatory
    DESCRIPTION
           "The static route table for this entity. The table
	   includes all static routes, both active and inactive.
	   Note that inactive static routes are deleted from RFC2096
	   ipCidrRouteTable; Hence the need for this private table to
	   maintain user configuration about disabled routes.
	   The table also includes the EntID index, to allow for
	   use in a distributed environment."
    REFERENCE
           "RFC 2096, ipCidrRouteTable"
    ::= { drStaticCidr 1 }

drStaticCidrEntry  OBJECT-TYPE
    SYNTAX  DrStaticCidrEntry
    ACCESS  not-accessible
    STATUS  mandatory
    DESCRIPTION
           "A particular route to  a  particular  destina-
       tion, under a particular policy."
    INDEX   {
                 drStaticCidrEntID,
                 drStaticCidrDest,
                 drStaticCidrMask,
                 drStaticCidrTos,
                 drStaticCidrNextHop
               }
    ::= { drStaticCidrTable  1 }

DrStaticCidrEntry ::=
    SEQUENCE {
        drStaticCidrEntID
	INTEGER,
        drStaticCidrDest
            IpAddress,

        drStaticCidrMask
            IpAddress,

        drStaticCidrTos
            INTEGER (-2147483648..2147483647),

        drStaticCidrNextHop
            IpAddress,

        drStaticCidrIfIndex
            INTEGER (-2147483648..2147483647),

        drStaticCidrType
            INTEGER,

        drStaticCidrMetric1
            INTEGER (-2147483648..2147483647),

        drStaticCidrPrecedence
            INTEGER,
	drStaticCidrCRPType
	INTEGER,
	drStaticCidrOperStatus
	INTEGER,
	drStaticCidrName
	DisplayString,
	drStaticOwner 
	OwnerString,
        drStaticCidrStatus
            RowStatus
    }
    
drStaticCidrEntID OBJECT-TYPE
    SYNTAX      INTEGER (1..65535)
    ACCESS  	read-only
    STATUS     mandatory
    DESCRIPTION
	"The Id of the entity for which a set of rows  applies. This index 
	is provided as a mean  of distributing non-related information on 
	different entities such as physical modules. 
	The value: The module ID (slot number). "
             ::= { drStaticCidrEntry 1 }

drStaticCidrDest OBJECT-TYPE
    SYNTAX  IpAddress
    ACCESS  read-only
    STATUS  mandatory
    DESCRIPTION
           "Equivalent  to ipCidrRouteDest.
       The destination IP address of this route.
       This object may not take a Multicast (Class  D)
       address value.
       Any assignment (implicit or  otherwise)  of  an
       instance  of  this  object to a value x must be
       rejected if the bitwise logical-AND of  x  with
       the  value of the corresponding instance of the
       drStaticCidrMask object is not equal to x."
    ::= { drStaticCidrEntry  2 }

drStaticCidrMask OBJECT-TYPE
    SYNTAX  IpAddress
    ACCESS  read-only
    STATUS  mandatory
    DESCRIPTION
           "Equivalent  to ipCidrRouteMask.
       Indicate the mask to be logical-ANDed with the
       destination  address  before  being compared to
       the value  in  the  drStaticCidrDest  field.   For
       those  systems  that  do  not support arbitrary
       subnet masks, an agent constructs the value  of
       the  drStaticCidrMask  by  reference to the IP Ad-
       dress Class.
       Any assignment (implicit or  otherwise)  of  an
       instance  of  this  object to a value x must be
       rejected if the bitwise logical-AND of  x  with
       the  value of the corresponding instance of the
       drStaticCidrDest object is not equal to drStaticCidr-
       Dest."
    ::= { drStaticCidrEntry  3 }

drStaticCidrTos OBJECT-TYPE
    SYNTAX  INTEGER (-2147483648..2147483647)
    ACCESS  read-only
    STATUS  mandatory
    DESCRIPTION
           "Equivalent  to ipCidrRouteTos.
       The policy specifier is the IP TOS Field.  The encoding
       of IP TOS is as specified  by  the  following convention.
       Zero indicates the default path if no more  specific
       policy applies.


       +-----+-----+-----+-----+-----+-----+-----+-----+
       |                 |                       |     |
       |   PRECEDENCE    |    TYPE OF SERVICE    |  0  |
       |                 |                       |     |
       +-----+-----+-----+-----+-----+-----+-----+-----+


                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30"
    ::= { drStaticCidrEntry  4 }

drStaticCidrNextHop OBJECT-TYPE
    SYNTAX  IpAddress
    ACCESS  read-only
    STATUS  mandatory
    DESCRIPTION
           "Equivalent  to ipCidrRouteNextHop.
	   On remote routes, the address of the next sys-
       tem en route; Otherwise, 0.0.0.0."
    ::= { drStaticCidrEntry  5 }

drStaticCidrIfIndex OBJECT-TYPE
    SYNTAX  INTEGER (-2147483648..2147483647)
    ACCESS  read-write
    STATUS  mandatory
    DESCRIPTION
           "Equivalent  to ipCidrRouteIfIndex.
	   The ifIndex value which identifies  the  local
       interface  through  which  the next hop of this
       route should be reached."
    DEFVAL  { 0 }
    ::= { drStaticCidrEntry  6 }

drStaticCidrType OBJECT-TYPE
    SYNTAX  INTEGER {
                 other(1),
                 reject(2),
                 local(3),
                 remote(4)
               }
    ACCESS  read-write
    STATUS  mandatory
    DESCRIPTION
           "Equivalent  to ipCidrRouteType.
       The type of route.  Note that local(3)  refers
       to  a route for which the next hop is the final
       destination; remote(4) refers to  a  route  for
       which  the  next  hop is not the final destina-
       tion.
       reject (2) refers to a route which, if matched, discards
       the message as unreachable. This is used in some
       protocols as a means of correctly aggregating routes."
    ::= { drStaticCidrEntry  7 }

drStaticCidrMetric1 OBJECT-TYPE
    SYNTAX  INTEGER (-2147483648..2147483647)
    ACCESS  read-write
    STATUS  mandatory
    DESCRIPTION
           "Equivalent  to ipCidrRouteMetric1.
       The primary routing  metric  for  this  route.
       The  semantics of this metric are determined by
       the routing-protocol specified in  the  route's
       drStaticCidrProto  value.   If  this metric is not
       used, its value should be set to -1."
    DEFVAL  { -1 }
    ::= { drStaticCidrEntry  8 }

drStaticCidrPrecedence OBJECT-TYPE
    SYNTAX  INTEGER (0..255)
    ACCESS  read-write
    STATUS  mandatory
    DESCRIPTION
           "Equivalent  to ipCidrRouteMetric5 (our use of it).
	   The precedence of this routing rule, compared to other
	   routes which may have been learned vie other methods.
	   Translates into ipCidrRouteMetric5 in ipCidrRouteTable (RFC2096).
	   
	   Higher values mean lower precedence.
	   The Agent initialize this value as follows:
	   0 -  drStaticCidrCRPType of bridgingFWLB or routingFWLB
	   250 - drStaticCidrCRPType of regularStatic
	   "
    ::= { drStaticCidrEntry  9 }

drStaticCidrCRPType OBJECT-TYPE
    SYNTAX  INTEGER {
       routingFWLB(1),
       bridgingFWLB(2),
       regularStatic(3)
       }
    ACCESS  read-write
    STATUS  mandatory
    DESCRIPTION
           "The internal type of this static routing entry.
	   routingFWLB - Route to a group of routing Firewallse 
	   bridgingFWLB - Route through a group of bridging Firewalls
	   regularStatic - Regular static routes
	   "
    ::= { drStaticCidrEntry  10 }

drStaticCidrOperStatus OBJECT-TYPE
    SYNTAX  INTEGER {
    up(1),
    down(2)
    }
    ACCESS  read-only
    STATUS  mandatory
    DESCRIPTION
           "The operational status of this route.
	   up - the route is active, and is present in ipCidrRouteTable.
	   down - the route is inactive; it is not present in 
	   ipCidrRouteTable.
	   "
    ::= { drStaticCidrEntry  11 }

drStaticCidrName OBJECT-TYPE
    SYNTAX  DisplayString (SIZE(0..32))
    ACCESS  read-write
    STATUS  mandatory
    DESCRIPTION
           "A label given to this route by the user.
	   Has no equivalent in ipCidrRouteTable.
	   "
    ::= { drStaticCidrEntry  12 }

drStaticOwner OBJECT-TYPE
    SYNTAX      OwnerString (SIZE (0..80))
    ACCESS  read-write
    STATUS      mandatory
    DESCRIPTION
  	"The user who is responsible for the entry. Management Apps should 
	write: 'user on host'
	CLI should write:CLI_User on local device"
   ::= { drStaticCidrEntry 13 }

drStaticCidrStatus OBJECT-TYPE
    SYNTAX  RowStatus
    ACCESS  read-write
    STATUS  mandatory
    DESCRIPTION
           "Creation, activation, de-activation and deletion of a 
	   static route, using the RowStatus convention:
	active(1), notInService(2) ,notReady(3), createAndGo(4), 
	createAndWait(5), destroy(6).
	
	when an entry is placed in the notInService state, the corresponding
	route is disabled (removed from ipCidrRouteTable)"
    ::= { drStaticCidrEntry  14 }




 
END
