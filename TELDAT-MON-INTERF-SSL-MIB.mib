-- Teldat, S.A.

                -- Parque Tecnolgico de Madrid

                -- 28760, Tres Cantos (Madrid)

                -- Tlf: +34 918076565

                -- Fax: +34 918076521

                -- e-mail: id@teldat.com


            -- MIB privada de Teldat


            -- Interfaces de lnea serie sincronos



    -- Historial:
    --      07/02/14    M.A. Pastor     XH 3523. Errors with HP Openview 9.20
    -- 1.2  19/01/12    J. Roman        Ignore CD, CTS, DSR. Open CD
    -- 1.1  23/12/05    M.A. Pastor     Modo loopback, modo echo y
    --                                  DTE-internal-clocks
    -- 1.0  01/07/04    J. Molina       Archivo procedente de SSL.MIB




    -- Historial de SSL.MIB:
    -- 1.0  14-06-01    J. L. Fuentes   MIB extrada de la PPP.MIB debido a la
    --                                  separacin de los interfaces PPP y lnea
    --                                  serie sncrona
    --------------------------------------------------------------------------

  TELDAT-MON-INTERF-SSL-MIB DEFINITIONS ::= BEGIN

    IMPORTS
            Counter
        FROM RFC1155-SMI
            OBJECT-TYPE
        FROM RFC-1212
            DisplayString
        FROM RFC1213-MIB
            telProdNpMonInterfRouter
        FROM TELDAT-SW-STRUCTURE-MIB;


    telProdNpMonInterfSSL   OBJECT IDENTIFIER ::= { telProdNpMonInterfRouter 15 }


-- Grupo telProdNpMonInterfSSL

-- Incluye los parmetros referentes a la monitorizacion de los interfaces de
-- lnea serie sncronos.

    -- Tabla de datos generales de los interfaces de lnea serie sincronos.
    -- Habr una entrada en la tabla por cada interfaz, y en cada entrada se
    -- muestran los datos que dan informacin sobre el tipo de driver
    -- (DCE o DTE), la velocidad de lnea, cundo se realiz el ultimo reset
    -- del puerto, si la SCC se encuentra en modo Loopback o en modo Echo y si
    -- el driver DTE da relojes (DTE-internal-clocks).

    telProdNpMonIfcSSLGlobalTable OBJECT-TYPE
        SYNTAX SEQUENCE OF TelProdNpMonIfcSSLGlobalEntry
        ACCESS not-accessible
        STATUS mandatory
        DESCRIPTION
        "This table contains general information about synchronous serial line
        interfaces. The interface number determines the entry number."
        ::= { telProdNpMonInterfSSL 1 }

    telProdNpMonIfcSSLGlobalEntry OBJECT-TYPE
        SYNTAX TelProdNpMonIfcSSLGlobalEntry
        ACCESS not-accessible
        STATUS mandatory
        DESCRIPTION
        "Each table entry contains the interface number of the related node,
        which is the index used to go over the table, the type of physical
        driver (DTE or DCE), the line speed, the time when the last port
        reset ocurred and variables to indicate if the SCC loopback mode or
        echo mode are active and if the DTE driver uses internal clocks."
        INDEX { telProdNpMonIfcSSLGloIndex }

        ::= { telProdNpMonIfcSSLGlobalTable 1 }

    TelProdNpMonIfcSSLGlobalEntry ::=
        SEQUENCE{
            telProdNpMonIfcSSLGloIndex
                INTEGER,
            telProdNpMonIfcSSLGloDriverType
                DisplayString,
            telProdNpMonIfcSSLGloLineSpeed
                INTEGER,
            telProdNpMonIfcSSLGloLastResetWeek
                INTEGER,
            telProdNpMonIfcSSLGloLastResetDay
                INTEGER,
            telProdNpMonIfcSSLGloLastResetHour
                INTEGER,
            telProdNpMonIfcSSLGloLastResetMin
                INTEGER,
            telProdNpMonIfcSSLGloLastResetSec
                INTEGER,
            telProdNpMonIfcSSLGloLoopback
                INTEGER,
            telProdNpMonIfcSSLGloEcho
                INTEGER,
            telProdNpMonIfcSSLGloDTEIntClocks
                INTEGER,
            telProdNpMonIfcSSLGloIgnoreCD
                INTEGER,
            telProdNpMonIfcSSLGloDisconnectCD
                INTEGER,
            telProdNpMonIfcSSLGloIgnoreCTS
                INTEGER,
            telProdNpMonIfcSSLGloIgnoreDSR
                INTEGER
            }

    telProdNpMonIfcSSLGloIndex OBJECT-TYPE
        SYNTAX INTEGER
        ACCESS read-only
        STATUS mandatory
        DESCRIPTION
        "The node interface number, which indicates the corresponding table
        entry (it is the table index)."
        ::= { telProdNpMonIfcSSLGlobalEntry 1 }

    telProdNpMonIfcSSLGloDriverType OBJECT-TYPE
        SYNTAX DisplayString
        ACCESS read-only
        STATUS mandatory
        DESCRIPTION
        "Type of physical driver: (1) DCE,  (2) DTE. This variable is a string
        that indicates the driver."
        ::= { telProdNpMonIfcSSLGlobalEntry 2 }

    telProdNpMonIfcSSLGloLineSpeed OBJECT-TYPE
        SYNTAX INTEGER
            ACCESS read-only
        STATUS mandatory
        DESCRIPTION
        "Line speed, in bits per second. The value 0 indicates speed unknown."
        ::= { telProdNpMonIfcSSLGlobalEntry 3 }

    telProdNpMonIfcSSLGloLastResetWeek OBJECT-TYPE
        SYNTAX INTEGER
        ACCESS read-only
        STATUS mandatory
        DESCRIPTION
        "Weeks passed since the last reset of the port."
        ::= { telProdNpMonIfcSSLGlobalEntry 4 }

    telProdNpMonIfcSSLGloLastResetDay OBJECT-TYPE
        SYNTAX INTEGER
        ACCESS read-only
        STATUS mandatory
        DESCRIPTION
        "Days passed since the last reset of the port: the remaining days that
        we get after counting the number of weeks that are not enough to form
        a week, this implies that the value of the variable must be under 7."
        ::= { telProdNpMonIfcSSLGlobalEntry 5 }

    telProdNpMonIfcSSLGloLastResetHour OBJECT-TYPE
        SYNTAX INTEGER
        ACCESS read-only
        STATUS mandatory
        DESCRIPTION
        "Hours passed since the last reset of the port. If it has passed more
        than a week, this variable indicates the number of hours to be added to
        the number of weeks and days, and its value should be under 24 so as not
        form a complete day."
        ::= { telProdNpMonIfcSSLGlobalEntry 6 }

    telProdNpMonIfcSSLGloLastResetMin OBJECT-TYPE
        SYNTAX INTEGER
        ACCESS read-only
        STATUS mandatory
        DESCRIPTION
        "Minutes passed since the last reset of the port. This variable
        indicates the number of minutes since the last hour added to the hour
        counter."
        ::= { telProdNpMonIfcSSLGlobalEntry 7 }

     telProdNpMonIfcSSLGloLastResetSec OBJECT-TYPE
        SYNTAX INTEGER
        ACCESS read-only
        STATUS mandatory
        DESCRIPTION
        "Seconds passed since the last reset of the port. The total time passed
        will be calculated by adding weeks, days, hours, minutes and seconds
        since the last reset."
        ::= { telProdNpMonIfcSSLGlobalEntry 8 }

    telProdNpMonIfcSSLGloLoopback OBJECT-TYPE
        SYNTAX INTEGER{
                active(1),
                inactive(2)
            }
        ACCESS read-only
        STATUS mandatory
        DESCRIPTION
        "This variable indicates if SCC loopback mode is active: transmitter is
        connected internally to the receiver."
        ::= { telProdNpMonIfcSSLGlobalEntry 9 }

    telProdNpMonIfcSSLGloEcho OBJECT-TYPE
        SYNTAX INTEGER{
                active(1),
                inactive(2)
            }
        ACCESS read-only
        STATUS mandatory
        DESCRIPTION
        "This variable indicates if SCC echo mode is active: transmitter
        resends received data."
        ::= { telProdNpMonIfcSSLGlobalEntry 10 }

    telProdNpMonIfcSSLGloDTEIntClocks OBJECT-TYPE
        SYNTAX INTEGER{
                yes(1),
                no(2)
            }
        ACCESS read-only
        STATUS mandatory
        DESCRIPTION
        "This variable indicates if DTE driver uses internal clocks."
        ::= { telProdNpMonIfcSSLGlobalEntry 11 }

    telProdNpMonIfcSSLGloIgnoreCD OBJECT-TYPE
        SYNTAX INTEGER{
                yes(1),
                no(2)
            }
        ACCESS read-only
        STATUS mandatory
        DESCRIPTION
        "This variable indicates if CD signal state is ignored."
        ::= { telProdNpMonIfcSSLGlobalEntry 12 }

    telProdNpMonIfcSSLGloDisconnectCD OBJECT-TYPE
        SYNTAX INTEGER{
                yes(1),
                no(2)
            }
        ACCESS read-only
        STATUS mandatory
        DESCRIPTION
        "This variable indicates if CD signal is disconnected from internal
        hardware."
        ::= { telProdNpMonIfcSSLGlobalEntry 13 }

    telProdNpMonIfcSSLGloIgnoreCTS OBJECT-TYPE
        SYNTAX INTEGER{
                yes(1),
                no(2)
            }
        ACCESS read-only
        STATUS mandatory
        DESCRIPTION
        "This variable indicates if CTS signal state is ignored."
        ::= { telProdNpMonIfcSSLGlobalEntry 14 }

    telProdNpMonIfcSSLGloIgnoreDSR OBJECT-TYPE
        SYNTAX INTEGER{
                yes(1),
                no(2)
            }
        ACCESS read-only
        STATUS mandatory
        DESCRIPTION
        "This variable indicates if DSR signal state is ignored."
        ::= { telProdNpMonIfcSSLGlobalEntry 15 }

    -- Tabla de los circuitos RS232. Esta tabla da informacin acerca de si las
    -- seales RTS, CTS, DSR, DTR, DCD, RI y LL estn activas o no.
    -- Habr una entrada por cada interfaz de lnea serie sncrono, siendo el
    -- numero de interfaz el ndice con que se recorre la tabla y con que se
    -- accede a la entrada correspondiente, y en cada una se proporciona el
    -- numero de orden del circuito RS232 (segundo ndice de la tabla), el
    -- numero de circuito, su nombre y si est o no activo.

    telProdNpMonIfcSSLRS232Table OBJECT-TYPE
        SYNTAX SEQUENCE OF TelProdNpMonIfcSSLRS232Entry
        ACCESS not-accessible
        STATUS mandatory
        DESCRIPTION
        "This table contains the signals or circuits RS232. It shows wether the
        signals are active or not. The entry number is determined by the
        interface number considered."
        ::= { telProdNpMonInterfSSL 2 }

    telProdNpMonIfcSSLRS232Entry OBJECT-TYPE
        SYNTAX TelProdNpMonIfcSSLRS232Entry
        ACCESS not-accessible
        STATUS mandatory
        DESCRIPTION
        "Each entry contains the interface number of the node considered, which
        will be the first index used to go over the table, the order number of
        the circuit inside that interface (second index), which must be between
        1 and a maximum value that depends on the conector type (the highest
        value will be 7), the circuit number (105, 106, 107, 108, 109, 125,
        141), its name (RTS, CTS, DSR, DTR, DCD, RI, LL) and wether it is active
        or not."
        INDEX { telProdNpMonIfcSSLRS232IfcIndex, telProdNpMonIfcSSLRS232CircIndex }

        ::= { telProdNpMonIfcSSLRS232Table 1 }

    TelProdNpMonIfcSSLRS232Entry ::=
        SEQUENCE{
            telProdNpMonIfcSSLRS232IfcIndex
                INTEGER,
            telProdNpMonIfcSSLRS232CircIndex
                INTEGER,
            telProdNpMonIfcSSLRS232Circuit
                INTEGER,
            telProdNpMonIfcSSLRS232Nickname
                DisplayString,
            telProdNpMonIfcSSLRS232State
                DisplayString
            }

    telProdNpMonIfcSSLRS232IfcIndex OBJECT-TYPE
        SYNTAX INTEGER
        ACCESS read-only
        STATUS mandatory
        DESCRIPTION
        "Synchronous serial line interface number of the node. It is the first
        table index."
        ::= { telProdNpMonIfcSSLRS232Entry 1 }

    telProdNpMonIfcSSLRS232CircIndex OBJECT-TYPE
        SYNTAX INTEGER(1..7)
        ACCESS read-only
        STATUS mandatory
        DESCRIPTION
        "Second table index. This number goes from 1 to the number of circuits
        of this type allowed, which varies with the conector type."
        ::= { telProdNpMonIfcSSLRS232Entry 2 }

    telProdNpMonIfcSSLRS232Circuit OBJECT-TYPE
        SYNTAX INTEGER(105..141)
        ACCESS read-only
        STATUS mandatory
        DESCRIPTION
        "RS232 circuit number. Values accepted are 105, 106, 107, 108, 109,
        125 y 141."
        ::= { telProdNpMonIfcSSLRS232Entry 3 }

    telProdNpMonIfcSSLRS232Nickname OBJECT-TYPE
        SYNTAX DisplayString
        ACCESS read-only
        STATUS mandatory
        DESCRIPTION
        "Circuit name."
        ::= { telProdNpMonIfcSSLRS232Entry 4 }

    telProdNpMonIfcSSLRS232State OBJECT-TYPE
        SYNTAX DisplayString
        ACCESS read-only
        STATUS mandatory
        DESCRIPTION
        "State of (circuit) signals: on, off or unknown."
        ::= { telProdNpMonIfcSSLRS232Entry 5 }

    -- Tabla de los contadores de las tramas de salida y de errores en las
    -- tramas de entrada.

    telProdNpMonIfcSSLFramesTable OBJECT-TYPE
        SYNTAX SEQUENCE OF TelProdNpMonIfcSSLFramesEntry
        ACCESS not-accessible
        STATUS mandatory
        DESCRIPTION
        "This table contains a counter of outgoing frames and a counter of bugs
        in ingoing frames. The entry number is determined by the interface
        number (table index)."
        ::= { telProdNpMonInterfSSL 3 }

    telProdNpMonIfcSSLFramesEntry OBJECT-TYPE
        SYNTAX TelProdNpMonIfcSSLFramesEntry
        ACCESS not-accessible
        STATUS mandatory
        DESCRIPTION
        "Each entry contains the node interface number, which is the index used
        to go over the table, a variable that shows the last output obtained
        when the user tried to delete the table (get operations) or performs
        the deletion (set operations), CRC errors in incoming frames, alignment
        errors, lost incoming frames due to overrun, too long frames, aborted
        frames, number of errors due to DMA/FIFO overrun, number of DMA/FIFO
        underrun in outgoing frames and aborted outputs sent."
        INDEX { telProdNpMonIfcSSLFramesIndex }

        ::= { telProdNpMonIfcSSLFramesTable 1 }

    TelProdNpMonIfcSSLFramesEntry ::=
        SEQUENCE{
            telProdNpMonIfcSSLFramesIndex
                INTEGER,
            telProdNpMonIfcSSLFramesClear
                INTEGER,
            telProdNpMonIfcSSLFramesCRCError
                Counter,
            telProdNpMonIfcSSLFramesAlignment
                Counter,
            telProdNpMonIfcSSLFramesMissed
                Counter,
            telProdNpMonIfcSSLFramesTooLong
                Counter,
            telProdNpMonIfcSSLFramesAborted
                Counter,
            telProdNpMonIfcSSLFramesOverrun
                Counter,
            telProdNpMonIfcSSLFramesUnderrun
                Counter,
            telProdNpMonIfcSSLFramesTxAbort
                Counter
            }

    telProdNpMonIfcSSLFramesIndex OBJECT-TYPE
        SYNTAX INTEGER
        ACCESS read-only
        STATUS mandatory
        DESCRIPTION
        "Interface number of the node, that shows the corresponding table entry
        (it is the index)."
        ::= { telProdNpMonIfcSSLFramesEntry 1 }

    telProdNpMonIfcSSLFramesClear OBJECT-TYPE
        SYNTAX INTEGER{
            delete(1),
            ok(2),
            error(3),
            undefined(4)
            }
        ACCESS read-write
        STATUS mandatory
        DESCRIPTION
        "This variable when is read shows the output from the last table delete
        attempt: the value is 2 if the deletion was performed succesfully, 3 if
        an error ocurred and 4 for an undefined result, that means that nobody
        has tried to delete the table yet. In set operations, the value 1 (it is
        the only value that can be assigned by a writing operation) causes a
        table deletion: frame counters are set to 0."
        ::= { telProdNpMonIfcSSLFramesEntry 2 }

    telProdNpMonIfcSSLFramesCRCError OBJECT-TYPE
        SYNTAX Counter
        ACCESS read-only
        STATUS mandatory
        DESCRIPTION
        "Number of frames with CRC errors."
        ::= { telProdNpMonIfcSSLFramesEntry 3 }

    telProdNpMonIfcSSLFramesAlignment OBJECT-TYPE
        SYNTAX Counter
        ACCESS read-only
        STATUS mandatory
        DESCRIPTION
        "Number of incoming frames with alignment errors."
        ::= { telProdNpMonIfcSSLFramesEntry 4 }

    telProdNpMonIfcSSLFramesMissed OBJECT-TYPE
        SYNTAX Counter
        ACCESS read-only
        STATUS mandatory
        DESCRIPTION
        "Number of incoming frames lost due to overrun."
        ::= { telProdNpMonIfcSSLFramesEntry 5 }

    telProdNpMonIfcSSLFramesTooLong OBJECT-TYPE
        SYNTAX Counter
        ACCESS read-only
        STATUS mandatory
        DESCRIPTION
        "Number of incoming frames too long."
        ::= { telProdNpMonIfcSSLFramesEntry 6 }

    telProdNpMonIfcSSLFramesAborted OBJECT-TYPE
        SYNTAX Counter
        ACCESS read-only
        STATUS mandatory
        DESCRIPTION
        "Number of incoming frames aborted."
        ::= { telProdNpMonIfcSSLFramesEntry 7 }

    telProdNpMonIfcSSLFramesOverrun OBJECT-TYPE
        SYNTAX Counter
        ACCESS read-only
        STATUS mandatory
        DESCRIPTION
        "Number of DMA/FIFO overrun."
        ::= { telProdNpMonIfcSSLFramesEntry 8 }

    telProdNpMonIfcSSLFramesUnderrun OBJECT-TYPE
        SYNTAX Counter
        ACCESS read-only
        STATUS mandatory
        DESCRIPTION
        "Number of DMA/FIFO underrun."
        ::= { telProdNpMonIfcSSLFramesEntry 9 }

    telProdNpMonIfcSSLFramesTxAbort OBJECT-TYPE
        SYNTAX Counter
        ACCESS read-only
        STATUS mandatory
        DESCRIPTION
        "Number of aborted outputs sent."
        ::= { telProdNpMonIfcSSLFramesEntry 10 }

END
