--
-- TELESTE-LUMINATO-MIB.mib
-- MIB generated by MG-SOFT Visual MIB Builder Version 4.0 Build 349
-- Wednesday, September 30, 2009 at 14:12:58
--
--  TELESTE-LUMINATO-MIB.mib
-- 
-- *****************************************************************************
-- Copyright (c) 2000-2010 by:
-- 
-- Teleste Corporation
-- Seponkatu 1
-- FIN-20660 Littoinen, Finland
-- tel. +358 2 2605 611
-- url: http://www.teleste.com
-- 
-- Description: Objects for Luminato
-- 
-- Revision History:
-- -----------------
-- 1.2 16.02.2010 Sami Salo and Sergey Egorov
-- - Changed OID 1.3.6.1.4.1.3715.17.2 from 'monitor' to 'statusCode' 
-- - Corrected types and ranges for PID, SID and TS IDs
-- - Minor cosmetic corrections
-- 1.1  30.09.2009 Rainer Salminen and Sami Salo
-- - Added monitor and alarm object tables
-- 1.0  19.02.2009 Sergey Egorov
-- - Initial release
-- ****************************************************************************
-- 

	TELESTE-LUMINATO-MIB DEFINITIONS ::= BEGIN
 
		IMPORTS
			OBJECT-TYPE			
				FROM RFC-1212			
			TimeTicks			
				FROM RFC1155-SMI			
			DisplayString			
				FROM RFC1213-MIB			
			Unsigned32, Counter32			
				FROM SNMPv2-SMI
			luminato			
				FROM TELESTE-ROOT-MIB
			Float
				FROM UCD-SNMP-MIB;			
	
	
	
--
-- Node definitions
--
-- General information of device
		-- 1.3.6.1.4.1.3715.17.1
		general OBJECT IDENTIFIER ::= { luminato 1 }

		-- 1.3.6.1.4.1.3715.17.1.1
		deviceName OBJECT-TYPE
			SYNTAX DisplayString
			MAX-ACCESS read-write
			STATUS current
			DESCRIPTION
				"The identification name ('aliasname') of the device"
			::= { general 1 }


		-- 1.3.6.1.4.1.3715.17.1.2
		generalStatus OBJECT-TYPE
			SYNTAX INTEGER
				{
				statusAlert(1),
				statusCritical(2),
				statusError(3),
				statusWarning(4),
				statusNotice(5),
				statusInformational(6),
				statusDebug(7)
				}
			MAX-ACCESS read-only
			STATUS current
			DESCRIPTION
				"General status of device"
			::= { general 2 }

		-- 1.3.6.1.4.1.3715.17.1.3
		redundancyStatus OBJECT-TYPE
			SYNTAX INTEGER
				{
				redundancyStandalone(1),
				redundancyMaster(16),
				redundancyMasterHandover(24),
				redundancyBackup(32),
				redundancyBackupHandover(40),
				redundancyError(64)
				}
			MAX-ACCESS read-only
			STATUS optional
			DESCRIPTION
				"Status of device in 1+1 backup operation mode"
			::= { general 3 }

		-- 1.3.6.1.4.1.3715.17.1.10
		hwSerialNumber OBJECT-TYPE
			SYNTAX DisplayString
			MAX-ACCESS read-only
			STATUS current
			DESCRIPTION
				"Device serial number"
			::= { general 10 }

		-- 1.3.6.1.4.1.3715.17.1.11
		hwType OBJECT-TYPE
			SYNTAX DisplayString
			MAX-ACCESS read-only
			STATUS current
			DESCRIPTION
				"The hardware type name of the device"
			::= { general 11 }

		-- 1.3.6.1.4.1.3715.17.1.12
		hwVersion OBJECT-TYPE
			SYNTAX DisplayString
			MAX-ACCESS read-only
			STATUS current
			DESCRIPTION
				"Device hardware version"
			::= { general 12 }

		-- 1.3.6.1.4.1.3715.17.1.13
		swVersion OBJECT-TYPE
			SYNTAX DisplayString
			MAX-ACCESS read-only
			STATUS current
			DESCRIPTION
				"Device running software version"
			::= { general 13 }

		-- 1.3.6.1.4.1.3715.17.1.14
		upTime OBJECT-TYPE
			SYNTAX TimeTicks
			MAX-ACCESS read-only
			STATUS current
			DESCRIPTION
				"Device uptime"
			::= { general 14 }


		-- 1.3.6.1.4.1.3715.17.1.15
		cumulativeUptime OBJECT-TYPE
			SYNTAX TimeTicks
			MAX-ACCESS read-only
			STATUS current
			DESCRIPTION
				"Device cummulative uptime"
			::= { general 15 }


		-- 1.3.6.1.4.1.3715.17.2
		statusCode OBJECT IDENTIFIER ::= { luminato 2 }

		-- 1.3.6.1.4.1.3715.17.2.1
		interfaceTypeTable OBJECT-TYPE
			SYNTAX SEQUENCE OF InterfaceTypeEntry
			MAX-ACCESS not-accessible
			STATUS current
			DESCRIPTION
				"InterfaceTypeTable lists possible interface types in the system."
			::= { statusCode 1 }

		-- 1.3.6.1.4.1.3715.17.2.1.1
		interfaceTypeEntry OBJECT-TYPE
			SYNTAX InterfaceTypeEntry
			MAX-ACCESS not-accessible
			STATUS current
			DESCRIPTION
				"Each InterfaceTypeEntry describes type of the interface."
			INDEX { interfaceTypeId }
			::= { interfaceTypeTable 1 }

		
		InterfaceTypeEntry ::=
			SEQUENCE { 
				interfaceTypeId
					INTEGER
			 }

		-- 1.3.6.1.4.1.3715.17.2.1.1.1
		interfaceTypeId OBJECT-TYPE
			SYNTAX INTEGER
				{
				input(1),
				output(2)
				}
			MAX-ACCESS not-accessible
			STATUS current
			DESCRIPTION
				"Interfacetype Id has two values input(1) and output(2). Values are used in other tables as index."
			::= { interfaceTypeEntry 1 }

		-- 1.3.6.1.4.1.3715.17.2.2
		statusCodeDeviceTable OBJECT-TYPE
			SYNTAX SEQUENCE OF StatusCodeDeviceEntry
			MAX-ACCESS not-accessible
			STATUS current
			DESCRIPTION
				"This table describes monitorable objects of the device.
				The objects may represents real objects or classes.
				The monitoring system or user shall not poll this table to detect device state.
				
				Instead - user shall wait for traps or poll currentAlarmTable(1.3.6.1.4.1.5591.1.1.2) from SCTE-HMS-PROPERTY-MIB.
				In this case statusCodeDeviceTable shall be used to obtains text definition of alarm."
			::= { statusCode 2 }

		-- 1.3.6.1.4.1.3715.17.2.2.1
		statusCodeDeviceEntry OBJECT-TYPE
			SYNTAX StatusCodeDeviceEntry
			MAX-ACCESS not-accessible
			STATUS current
			DESCRIPTION
				" "
			INDEX { scdObjectId }
			::= { statusCodeDeviceTable 1 }

		
		StatusCodeDeviceEntry ::=
			SEQUENCE { 
				scdObjectId
					Unsigned32,
				scdObjectValue
					INTEGER,
				scdObjectDescriptor
					DisplayString,
				scdObjectAlarmValue
					INTEGER
			 }

		-- 1.3.6.1.4.1.3715.17.2.2.1.1
		scdObjectId OBJECT-TYPE
			SYNTAX Unsigned32
			MAX-ACCESS read-only
			STATUS current
			DESCRIPTION
				"Unique identifier of the monitorable object.
				"
			::= { statusCodeDeviceEntry 1 }

		-- 1.3.6.1.4.1.3715.17.2.2.1.2
		scdObjectValue OBJECT-TYPE
			SYNTAX INTEGER
			MAX-ACCESS read-only
			STATUS current
			DESCRIPTION
				"Value of the monitorable object.
				The scdObjectDescriptor tells name, scale and unit of the object."
			::= { statusCodeDeviceEntry 2 }


		-- 1.3.6.1.4.1.3715.17.2.2.1.3
		scdObjectDescriptor OBJECT-TYPE
			SYNTAX DisplayString
			MAX-ACCESS read-only
			STATUS current
			DESCRIPTION
				"Description of the monitorable object.
				
				Free text if object has two states
				
				or
				
				Format:
				Name, Scale, Unit, [optional text]
				
				------------------------------------
				
				Example 1 (Analogue object):
				
				'MainVoltage, 0.01, V'
				
				Usage:
				scdObjectId:7 (example)
				scdObjectValue:2399
				scdObjectDescriptor:'MainVoltage, 0.01, V'
				
				means
				
				Main voltage is 23.99 V
				
				------------------------------------
				
				Example 2 (Discrete object):
				
				'TemperatureHigh, 1, high(2)/nominal(1), Alarm state of the temperature'
				
				Usage:
				scdObjectId:12 (example)
				scdObjectValue:2
				
				means
				
				Temperature is in high alarm state.
				
				------------------------------------
				"
			::= { statusCodeDeviceEntry 3 }

		
		-- 1.3.6.1.4.1.3715.17.2.2.1.4
		scdObjectAlarmValue OBJECT-TYPE
			SYNTAX INTEGER
			MAX-ACCESS read-only
			STATUS current
			DESCRIPTION
				"When the object has this value it is in the alarm state.
				One object id can have only one alarm state.
				If more alarm states exist then new associated object needs to be created.
				Note that alarm state value can have only discrete values.
				If the value is zero then there is no alarm for this object.
				
				Example:
				
				TemperatureHigh object can have values high(2) or nominal(1).
				Alarm monitoring for this object is triggered by setting dmObjectAlarmValue 
				to value 2 meaning high(2).
				 
				How the alarm processing is done is out of scope of this MIB.
				"
			::= { statusCodeDeviceEntry 4 }
		
		-- 1.3.6.1.4.1.3715.17.2.3
		statusCodeModuleTable OBJECT-TYPE
			SYNTAX SEQUENCE OF StatusCodeModuleEntry
			MAX-ACCESS not-accessible
			STATUS current
			DESCRIPTION
				"This table describes monitorable objects per module inside the device.
				The objects may represents real objects or classes.
				The monitoring system or user shall not poll this table to detect device state.
				
				Instead - user shall wait for traps or poll currentAlarmTable(1.3.6.1.4.1.5591.1.1.2) from SCTE-HMS-PROPERTY-MIB.
				In this case statusCodeModuleTable shall be used to obtains text definition of alarm."
			::= { statusCode 3 }

		-- 1.3.6.1.4.1.3715.17.2.3.1
		statusCodeModuleEntry OBJECT-TYPE
			SYNTAX StatusCodeModuleEntry
			MAX-ACCESS not-accessible
			STATUS current
			DESCRIPTION
				" "
			INDEX { scmModuleId, scmObjectId }
			::= { statusCodeModuleTable 1 }

		
		StatusCodeModuleEntry ::=
			SEQUENCE { 
				scmModuleId
					INTEGER,
				scmObjectId
					Unsigned32,
				scmObjectValue
					INTEGER,
				scmObjectDescriptor
					DisplayString,
				scmObjectAlarmValue
					INTEGER
			 }

		-- 1.3.6.1.4.1.3715.17.2.3.1.1
		scmModuleId OBJECT-TYPE
			SYNTAX INTEGER (1..7)
			MAX-ACCESS read-only
			STATUS current
			DESCRIPTION
				"Module Id within the device (usually slot number)."
			::= { statusCodeModuleEntry 1 }

		-- 1.3.6.1.4.1.3715.17.2.3.1.2
		scmObjectId OBJECT-TYPE
			SYNTAX Unsigned32
			MAX-ACCESS read-only
			STATUS current
			DESCRIPTION
				"Unique identifier of the monitorable object within the module."
			::= { statusCodeModuleEntry 2 }


		-- 1.3.6.1.4.1.3715.17.2.3.1.3
		scmObjectValue OBJECT-TYPE
			SYNTAX INTEGER
			MAX-ACCESS read-only
			STATUS current
			DESCRIPTION
				"Value of the monitorable object.
				The scmObjectDescriptor tells name, scale and unit of the object."
			::= { statusCodeModuleEntry 3 }


		-- 1.3.6.1.4.1.3715.17.2.3.1.4
		scmObjectDescriptor OBJECT-TYPE
			SYNTAX DisplayString
			MAX-ACCESS read-only
			STATUS current
			DESCRIPTION
				"Description of the monitorable object.
				See scdObjectDescriptor for format, example and usage.
				
				"
			::= { statusCodeModuleEntry 4 }

		
		-- 1.3.6.1.4.1.3715.17.2.3.1.5
		scmObjectAlarmValue OBJECT-TYPE
			SYNTAX INTEGER
			MAX-ACCESS read-only
			STATUS current
			DESCRIPTION
				"See scdObjectAlarmValue for format, example and usage.
				
				"
			::= { statusCodeModuleEntry 5 }

		
		-- 1.3.6.1.4.1.3715.17.2.4
		statusCodeInterfaceTable OBJECT-TYPE
			SYNTAX SEQUENCE OF StatusCodeInterfaceEntry
			MAX-ACCESS not-accessible
			STATUS current
			DESCRIPTION
				"This table describes monitorable objects per interface per module.
				The objects may represents real objects or classes.
				The monitoring system or user shall not poll this table to detect device state.
				
				Instead - user shall wait for traps or poll currentAlarmTable(1.3.6.1.4.1.5591.1.1.2) from SCTE-HMS-PROPERTY-MIB.
				In this case statusCodeInterfaceTable shall be used to obtains text definition of alarm."
				
			::= { statusCode 4 }

		-- 1.3.6.1.4.1.3715.17.2.4.1
		statusCodeInterfaceEntry OBJECT-TYPE
			SYNTAX StatusCodeInterfaceEntry
			MAX-ACCESS not-accessible
			STATUS current
			DESCRIPTION
				" "
			INDEX { interfaceTypeId, scmModuleId, sciInterfaceId, sciObjectId }
			::= { statusCodeInterfaceTable 1 }

		
		StatusCodeInterfaceEntry ::=
			SEQUENCE { 
				sciInterfaceId
					INTEGER,
				sciObjectId
					Unsigned32,
				sciObjectValue
					INTEGER,
				sciObjectDescriptor
					DisplayString,
				sciObjectAlarmValue
					INTEGER
			 }

		-- 1.3.6.1.4.1.3715.17.2.4.1.1
		sciInterfaceId OBJECT-TYPE
			SYNTAX INTEGER (1..4)
			MAX-ACCESS read-only
			STATUS current
			DESCRIPTION
				"Unique interface Id within the module (e.g. RF connector number)."
			::= { statusCodeInterfaceEntry 1 }


		-- 1.3.6.1.4.1.3715.17.2.4.1.2
		sciObjectId OBJECT-TYPE
			SYNTAX Unsigned32
			MAX-ACCESS read-only
			STATUS current
			DESCRIPTION
				"Unique identifier of the monitorable object within the interface."
			::= { statusCodeInterfaceEntry 2 }

		-- 1.3.6.1.4.1.3715.17.2.4.1.3
		sciObjectValue OBJECT-TYPE
			SYNTAX INTEGER
			MAX-ACCESS read-only
			STATUS current
			DESCRIPTION
				"Value of the monitorable object.
				The sciObjectDescriptor tells name, scale and unit of the object."
			::= { statusCodeInterfaceEntry 3 }


		-- 1.3.6.1.4.1.3715.17.2.4.1.4
		sciObjectDescriptor OBJECT-TYPE
			SYNTAX DisplayString
			MAX-ACCESS read-only
			STATUS current
			DESCRIPTION
				"Description of the monitorable object.
				See scdObjectDescriptor for format, example and usage.
				
				"
			::= { statusCodeInterfaceEntry 4 }

		
		-- 1.3.6.1.4.1.3715.17.2.4.1.5
		sciObjectAlarmValue OBJECT-TYPE
			SYNTAX INTEGER
			MAX-ACCESS read-only
			STATUS current
			DESCRIPTION
				"See dmObjectAlarmValue for format, example and usage.
				
				"
			::= { statusCodeInterfaceEntry 5 }

		
		-- 1.3.6.1.4.1.3715.17.2.5
		statusCodeTransportStreamTable OBJECT-TYPE
			SYNTAX SEQUENCE OF StatusCodeTransportStreamEntry
			MAX-ACCESS not-accessible
			STATUS current
			DESCRIPTION
				"This table describes monitorable objects of each transport stream.
				The objects may represents real objects or classes.
				The monitoring system or user shall not poll this table to detect device state.
				
				Instead - user shall wait for traps or poll currentAlarmTable(1.3.6.1.4.1.5591.1.1.2) from SCTE-HMS-PROPERTY-MIB.
				In this case statusCodeTransportStreamTable shall be used to obtains text definition of alarm."				
			::= { statusCode 5 }

		-- 1.3.6.1.4.1.3715.17.2.5.1
		statusCodeTransportStreamEntry OBJECT-TYPE
			SYNTAX StatusCodeTransportStreamEntry
			MAX-ACCESS not-accessible
			STATUS current
			DESCRIPTION
				" "
			INDEX { interfaceTypeId, scmModuleId, sciInterfaceId, sctsTransportStreamId, sctsObjectId
				 }
			::= { statusCodeTransportStreamTable 1 }

		
		StatusCodeTransportStreamEntry ::=
			SEQUENCE { 
				sctsTransportStreamId
					INTEGER,
				sctsObjectId
					Unsigned32,
				sctsObjectValue
					INTEGER,
				sctsObjectDescriptor
					DisplayString,
				sctsObjectAlarmValue
					INTEGER
			 }

		-- 1.3.6.1.4.1.3715.17.2.5.1.1
		sctsTransportStreamId OBJECT-TYPE
			SYNTAX INTEGER (1..8192)
			MAX-ACCESS read-only
			STATUS current
			DESCRIPTION
				"Unique transport stream id inside the interface."
			::= { statusCodeTransportStreamEntry 1 }

		
		-- 1.3.6.1.4.1.3715.17.2.5.1.2
		sctsObjectId OBJECT-TYPE
			SYNTAX Unsigned32
			MAX-ACCESS read-only
			STATUS current
			DESCRIPTION
				"Unique identifier of the monitorable object."
			::= { statusCodeTransportStreamEntry 2 }


		-- 1.3.6.1.4.1.3715.17.2.5.1.3
		sctsObjectValue OBJECT-TYPE
			SYNTAX INTEGER
			MAX-ACCESS read-only
			STATUS current
			DESCRIPTION
				"Value of the monitorable object.
				The sctsObjectDescriptor tells name, scale and unit of the object."
			::= { statusCodeTransportStreamEntry 3 }

		-- 1.3.6.1.4.1.3715.17.2.5.1.4
		sctsObjectDescriptor OBJECT-TYPE
			SYNTAX DisplayString
			MAX-ACCESS read-only
			STATUS current
			DESCRIPTION
				"Description of the monitorable object.
				See dmObjectDescriptor for format, example and usage.
				
				"
			::= { statusCodeTransportStreamEntry 4 }

		
		-- 1.3.6.1.4.1.3715.17.2.5.1.5
		sctsObjectAlarmValue OBJECT-TYPE
			SYNTAX INTEGER
			MAX-ACCESS read-only
			STATUS current
			DESCRIPTION
				"See scdObjectAlarmValue for format, example and usage.
				
				"
			::= { statusCodeTransportStreamEntry 5 }

		-- 1.3.6.1.4.1.3715.17.2.6
		statusCodeServiceTable OBJECT-TYPE
			SYNTAX SEQUENCE OF StatusCodeServiceEntry
			MAX-ACCESS not-accessible
			STATUS current
			DESCRIPTION
				"This table describes monitorable objects of each service.
				The objects may represents real objects or classes.
				The monitoring system or user shall not poll this table to detect device state.
				
				Instead - user shall wait for traps or poll currentAlarmTable(1.3.6.1.4.1.5591.1.1.2) from SCTE-HMS-PROPERTY-MIB.
				In this case statusCodeServiceTable shall be used to obtains text definition of alarm."				
			::= { statusCode 6 }

		-- 1.3.6.1.4.1.3715.17.2.6.1
		statusCodeServiceEntry OBJECT-TYPE
			SYNTAX StatusCodeServiceEntry
			MAX-ACCESS not-accessible
			STATUS current
			DESCRIPTION
				" "
			INDEX { interfaceTypeId, scmModuleId, sciInterfaceId, sctsTransportStreamId, scsSID, 
				scsObjectId }
			::= { statusCodeServiceTable 1 }

		
		StatusCodeServiceEntry ::=
			SEQUENCE { 
				scsSID
					INTEGER,
				scsObjectId
					Unsigned32,
				scsObjectValue
					INTEGER,
				scsObjectDescriptor
					DisplayString,
				scsServiceName
					DisplayString,
				scsObjectAlarmValue
					INTEGER
			 }

		-- 1.3.6.1.4.1.3715.17.2.6.1.1
		scsSID OBJECT-TYPE
			SYNTAX INTEGER (0..65535)
			MAX-ACCESS read-only
			STATUS current
			DESCRIPTION
				"Unique service id number inside the transport stream."
			::= { statusCodeServiceEntry 1 }

		-- 1.3.6.1.4.1.3715.17.2.6.1.2
		scsObjectId OBJECT-TYPE
			SYNTAX Unsigned32
			MAX-ACCESS read-only
			STATUS current
			DESCRIPTION
				"Unique identifier of the monitorable object."
			::= { statusCodeServiceEntry 2 }


		-- 1.3.6.1.4.1.3715.17.2.6.1.3
		scsObjectValue OBJECT-TYPE
			SYNTAX INTEGER
			MAX-ACCESS read-only
			STATUS current
			DESCRIPTION
				"Value of the monitorable object.
				The scsObjectDescriptor tells name, scale and unit of the object."
			::= { statusCodeServiceEntry 3 }

		-- 1.3.6.1.4.1.3715.17.2.6.1.4
		scsObjectDescriptor OBJECT-TYPE
			SYNTAX DisplayString
			MAX-ACCESS read-only
			STATUS current
			DESCRIPTION
				"Description of the monitorable object.
				See scdObjectDescriptor for format, example and usage.
				
				"
			::= { statusCodeServiceEntry 4 }


		-- 1.3.6.1.4.1.3715.17.2.6.1.5
		scsServiceName OBJECT-TYPE
			SYNTAX DisplayString
			MAX-ACCESS read-only
			STATUS current
			DESCRIPTION
				"The name of the service."
			::= { statusCodeServiceEntry 5 }

		
		-- 1.3.6.1.4.1.3715.17.2.6.1.6
		scsObjectAlarmValue OBJECT-TYPE
			SYNTAX INTEGER
			MAX-ACCESS read-only
			STATUS current
			DESCRIPTION
				"See scdObjectAlarmValue for format, example and usage.
				
				"
			::= { statusCodeServiceEntry 6 }


		-- 1.3.6.1.4.1.3715.17.2.7
		statusCodePidTable OBJECT-TYPE
			SYNTAX SEQUENCE OF StatusCodePidEntry
			MAX-ACCESS not-accessible
			STATUS current
			DESCRIPTION
				"This table lists monitorable objects of each PID.
				The objects may represents real objects or classes.
				The monitoring system or user shall not poll this table to detect device state.
				
				Instead - user shall wait for traps or poll currentAlarmTable(1.3.6.1.4.1.5591.1.1.2) from SCTE-HMS-PROPERTY-MIB.
				In this case statusCodePidTable shall be used to obtains text definition of alarm."				
			::= { statusCode 7 }

		-- 1.3.6.1.4.1.3715.17.2.7.1
		statusCodePidEntry OBJECT-TYPE
			SYNTAX StatusCodePidEntry
			MAX-ACCESS not-accessible
			STATUS current
			DESCRIPTION
				" "
			INDEX { interfaceTypeId, scmModuleId, sciInterfaceId, sctsTransportStreamId, scpPID, 
				scpObjectId }
			::= { statusCodePidTable 1 }

		
		StatusCodePidEntry ::=
			SEQUENCE { 
				scpPID
					INTEGER,
				scpObjectId
					Unsigned32,
				scpObjectValue
					INTEGER,
				scpObjectDescriptor
					DisplayString,
				scpObjectAlarmValue
					INTEGER
			 }


		-- 1.3.6.1.4.1.3715.17.2.7.1.1
		scpPID OBJECT-TYPE
			SYNTAX INTEGER (0..8191)
			MAX-ACCESS read-only
			STATUS current
			DESCRIPTION
				"Unique PID value inside the transport stream."
			::= { statusCodePidEntry 1 }

		
		-- 1.3.6.1.4.1.3715.17.2.7.1.2
		scpObjectId OBJECT-TYPE
			SYNTAX Unsigned32
			MAX-ACCESS read-only
			STATUS current
			DESCRIPTION
				"Unique identifier of the monitorable object."
			::= { statusCodePidEntry 2 }

		
		-- 1.3.6.1.4.1.3715.17.2.7.1.3
		scpObjectValue OBJECT-TYPE
			SYNTAX INTEGER
			MAX-ACCESS read-only
			STATUS current
			DESCRIPTION
				"Value of the monitorable object.
				The scpObjectDescriptor tells name, scale and unit of the object."
			::= { statusCodePidEntry 3 }

		-- 1.3.6.1.4.1.3715.17.2.7.1.4
		scpObjectDescriptor OBJECT-TYPE
			SYNTAX DisplayString
			MAX-ACCESS read-only
			STATUS current
			DESCRIPTION
				"Description of the monitorable object.
				See scdObjectDescriptor for format, example and usage.
				
				"
			::= { statusCodePidEntry 4 }

		
		-- 1.3.6.1.4.1.3715.17.2.7.1.5
		scpObjectAlarmValue OBJECT-TYPE
			SYNTAX INTEGER
			MAX-ACCESS read-only
			STATUS current
			DESCRIPTION
				"See scdObjectAlarmValue for format, example and usage.
				
				"
			::= { statusCodePidEntry 5 }
	
	
		-- 1.3.6.1.4.1.3715.17.3
		interface OBJECT IDENTIFIER ::= { luminato 3 }

		-- 1.3.6.1.4.1.3715.17.3.1
		ifExtTable OBJECT-TYPE
			SYNTAX SEQUENCE OF IfExtEntry
			MAX-ACCESS not-accessible
			STATUS current
			DESCRIPTION			
				""
			::= { interface 1 }

		
		-- 1.3.6.1.4.1.3715.17.3.1.1
		ifExtEntry OBJECT-TYPE
			SYNTAX IfExtEntry
			MAX-ACCESS not-accessible
			STATUS current
			DESCRIPTION			
				""
			--INDEX { INTEGER }
			::= { ifExtTable 1 }

		
		IfExtEntry ::=
			SEQUENCE { 
				ifExtIndex
					INTEGER,
				ifExtName
					DisplayString,
				ifExtModule
					INTEGER,
				ifExtPhysInterface
					INTEGER,
				ifExtLogiInterface
					INTEGER,
				ifExtDirection
					INTEGER
			 }

		-- 1.3.6.1.4.1.3715.17.3.1.1.1
		ifExtIndex OBJECT-TYPE
			SYNTAX INTEGER
			MAX-ACCESS not-accessible
			STATUS current
			DESCRIPTION
				"A unique index for an interface.
				The index is of following format: SDPPVVVV, where:
				 - S    = Slot number
				 - D    = input(1) / output(2)
				 - PP   = Physical interface number
				 - VVVV = Virtual interface number"
			::= { ifExtEntry 1 }

		
		-- 1.3.6.1.4.1.3715.17.3.1.1.2
		ifExtName OBJECT-TYPE
			SYNTAX DisplayString
			MAX-ACCESS read-only
			STATUS current
			DESCRIPTION
				"Description for the interface."
			::= { ifExtEntry 2 }

		
		-- 1.3.6.1.4.1.3715.17.3.1.1.3
		ifExtModule OBJECT-TYPE
			SYNTAX INTEGER
			MAX-ACCESS read-only
			STATUS current
			DESCRIPTION
				"Number of the physical module or slot housing the interface."
			::= { ifExtEntry 3 }

		
		-- 1.3.6.1.4.1.3715.17.3.1.1.4
		ifExtPhysInterface OBJECT-TYPE
			SYNTAX INTEGER
			MAX-ACCESS read-only
			STATUS current
			DESCRIPTION
				"Physical interface number."
			::= { ifExtEntry 4 }

		
		-- 1.3.6.1.4.1.3715.17.3.1.1.5
		ifExtLogiInterface OBJECT-TYPE
			SYNTAX INTEGER
			MAX-ACCESS read-only
			STATUS current
			DESCRIPTION
				"Logical interface number."
			::= { ifExtEntry 5 }

		
		-- 1.3.6.1.4.1.3715.17.3.1.1.6
		ifExtDirection OBJECT-TYPE
			SYNTAX INTEGER
				{
				input(1),
				output(2),
				both(3)
				}
			MAX-ACCESS read-only
			STATUS current
			DESCRIPTION
				"Direction for the data going through the interface."
			::= { ifExtEntry 6 }

		
-- Signal physical level

		-- 1.3.6.1.4.1.3715.17.3.2
		signalPhysTable OBJECT-TYPE
			SYNTAX SEQUENCE OF SignalPhysEntry
			MAX-ACCESS not-accessible
			STATUS current
			DESCRIPTION			
				""
			::= { interface 2 }

		
		-- 1.3.6.1.4.1.3715.17.3.2.1
		signalPhysEntry OBJECT-TYPE
			SYNTAX SignalPhysEntry
			MAX-ACCESS not-accessible
			STATUS current
			DESCRIPTION			
				""
			INDEX { ifExtIndex }
			::= { signalPhysTable 1 }

		
		SignalPhysEntry ::=
			SEQUENCE { 
				signalSnr
					INTEGER,
				signalSnrMin
					INTEGER,
				signalSnrMax
					INTEGER,
				signalCcErrors
					INTEGER,
				signalBer
					Float,
				signalVber
					Float
			 }

		-- 1.3.6.1.4.1.3715.17.3.2.1.2
		signalSnr OBJECT-TYPE
			SYNTAX INTEGER
			MAX-ACCESS read-only
			STATUS current
			DESCRIPTION
				"Recent signal to noise ratio in 1/10th of dB."
			::= { signalPhysEntry 2 }

		
		-- 1.3.6.1.4.1.3715.17.3.2.1.3
		signalSnrMin OBJECT-TYPE
			SYNTAX INTEGER
			MAX-ACCESS read-write
			STATUS current
			DESCRIPTION
				"Lowest measured SNR value since last device startup or last counter reset."
			::= { signalPhysEntry 3 }

		
		-- 1.3.6.1.4.1.3715.17.3.2.1.4
		signalSnrMax OBJECT-TYPE
			SYNTAX INTEGER
			MAX-ACCESS read-write
			STATUS current
			DESCRIPTION
				"Highest measured SNR value since last device startup or last counter reset."
			::= { signalPhysEntry 4 }

		
		-- 1.3.6.1.4.1.3715.17.3.2.1.5
		signalCcErrors OBJECT-TYPE
			SYNTAX INTEGER
			MAX-ACCESS read-write
			STATUS current
			DESCRIPTION
				"The number of continuity errors since last device startup or last counter reset."
			::= { signalPhysEntry 5 }

		
		-- 1.3.6.1.4.1.3715.17.3.2.1.6
		signalBer OBJECT-TYPE
			SYNTAX Float
			MAX-ACCESS read-only
			STATUS current
			DESCRIPTION
				"Calculated bit error ratio of the signal."
			::= { signalPhysEntry 6 }

		
		-- 1.3.6.1.4.1.3715.17.3.2.1.7
		signalVber OBJECT-TYPE
			SYNTAX Float
			MAX-ACCESS read-only
			STATUS current
			DESCRIPTION
				"Calculated Viterbi bit error ratio of the signal."
			::= { signalPhysEntry 7 }
		
		
		
-- transfer statistics

		-- 1.3.6.1.4.1.3715.17.3.3
		transferTable OBJECT-TYPE
			SYNTAX SEQUENCE OF TransferEntry
			MAX-ACCESS not-accessible
			STATUS current
			DESCRIPTION			
				""
			::= { interface 3 }

		
		-- 1.3.6.1.4.1.3715.17.3.3.1
		transferEntry OBJECT-TYPE
			SYNTAX TransferEntry
			MAX-ACCESS not-accessible
			STATUS current
			DESCRIPTION			
				""
			INDEX { ifExtIndex }
			::= { transferTable 1 }

		
		TransferEntry ::=
			SEQUENCE { 
				transBitrate
					INTEGER,
				transBitrateMin
					INTEGER,
				transBitrateMax
					INTEGER
			 }

		-- 1.3.6.1.4.1.3715.17.3.3.1.2
		transBitrate OBJECT-TYPE
			SYNTAX INTEGER
			MAX-ACCESS read-only
			STATUS current
			DESCRIPTION
				"Recent measured bitrate of the interface in kilobits per second."
			::= { transferEntry 2 }

		
		-- 1.3.6.1.4.1.3715.17.3.3.1.3
		transBitrateMin OBJECT-TYPE
			SYNTAX INTEGER
			MAX-ACCESS read-write
			STATUS current
			DESCRIPTION
				"Lowest measured bitrate since last device startup or last counter reset.
				Writing clears the counter."
			::= { transferEntry 3 }

		
		-- 1.3.6.1.4.1.3715.17.3.3.1.4
		transBitrateMax OBJECT-TYPE
			SYNTAX INTEGER
			MAX-ACCESS read-write
			STATUS current
			DESCRIPTION
				"Highest measured bitrate since last device startup or last counter reset.
				Writing clears the counter."
			::= { transferEntry 4 }
	
	
-- ProMpegFec interface related data

		-- 1.3.6.1.4.1.3715.17.3.20
		proMpegFecTable OBJECT-TYPE
			SYNTAX SEQUENCE OF ProMpegFecEntry
			MAX-ACCESS not-accessible
			STATUS current
			DESCRIPTION			
				""
			::= { interface 20 }

		
		-- 1.3.6.1.4.1.3715.17.3.20.1
		proMpegFecEntry OBJECT-TYPE
			SYNTAX ProMpegFecEntry
			MAX-ACCESS not-accessible
			STATUS current
			DESCRIPTION			
				""
			INDEX { ifExtIndex }
			::= { proMpegFecTable 1 }

		
		ProMpegFecEntry ::=
			SEQUENCE { 
				fecValidPkts
					Counter32,
				fecUncorrectedPkts
					Counter32,
				fecCorrectedPkts
					Counter32,
				fecDuplicatePkts
					Counter32,
				fecReorderedPkts
					Counter32,
				fecIncorrectSeqNumbers
					Counter32,
				fecDiscontinuities
					Counter32
			 }

		-- 1.3.6.1.4.1.3715.17.3.20.1.1
		fecValidPkts OBJECT-TYPE
			SYNTAX Counter32
			MAX-ACCESS read-write
			STATUS current
			DESCRIPTION
				"Number of media stream packets received.
				Writing any value in this oid will clear all ProMpegFec related counters on
				the current interface."
			::= { proMpegFecEntry 1 }

		
		-- 1.3.6.1.4.1.3715.17.3.20.1.2
		fecUncorrectedPkts OBJECT-TYPE
			SYNTAX Counter32
			MAX-ACCESS read-write
			STATUS current
			DESCRIPTION
				"Number of missing media stream packets after FEC decoding.
				Writing any value in this oid will clear all ProMpegFec related counters on
				the current interface."
			::= { proMpegFecEntry 2 }

		
		-- 1.3.6.1.4.1.3715.17.3.20.1.3
		fecCorrectedPkts OBJECT-TYPE
			SYNTAX Counter32
			MAX-ACCESS read-write
			STATUS current
			DESCRIPTION
				"Number of corrected packets after FEC decoding.
				Writing any value in this oid will clear all ProMpegFec related counters on
				the current interface."
			::= { proMpegFecEntry 3 }

			
		-- 1.3.6.1.4.1.3715.17.3.20.1.4
		fecDuplicatePkts OBJECT-TYPE
			SYNTAX Counter32
			MAX-ACCESS read-write
			STATUS current
			DESCRIPTION
				"Number of duplicate packets received. Defined as a received packet with 
				the same RTP sequence number as any of the packets already in the decoding 
				buffer. All duplicate packets are automatically discarded and do not cause 
				missing packets or duplicates to the output stream.
				Writing any value in this oid will clear all ProMpegFec related counters on
				the current interface."
			::= { proMpegFecEntry 4 }

		
		-- 1.3.6.1.4.1.3715.17.3.20.1.5
		fecReorderedPkts OBJECT-TYPE
			SYNTAX Counter32
			MAX-ACCESS read-write
			STATUS current
			DESCRIPTION
				"Number of reordered packets received. Defined as a received packet which 
				RTP sequence number is smaller than the highest RTP sequence number already 
				received, excluding duplicate packets and packets which are out of the 
				decoding buffer range. These packets will be re-ordered and do not cause 
				missing packets to the output stream. 
				Writing any value in this oid will clear all ProMpegFec related counters on
				the current interface."
			::= { proMpegFecEntry 5 }

		
		-- 1.3.6.1.4.1.3715.17.3.20.1.6
		fecIncorrectSeqNumbers OBJECT-TYPE
			SYNTAX Counter32
			MAX-ACCESS read-write
			STATUS current
			DESCRIPTION
				"Number of received media packets that have RTP sequence number out of 
				decoding buffer range. All these packet are discarded. If 10 consecutive 
				packets are out of range then decoding buffer is flushed and re-initialised 
				i.e. all packets in the buffer are discarded. Incorrect sequence numbers 
				counter will not be incremented if decoding buffer has been flushed.
				Writing any value in this oid will clear all ProMpegFec related counters on
				the current interface."
			::= { proMpegFecEntry 6 }

		
		-- 1.3.6.1.4.1.3715.17.3.20.1.7
		fecDiscontinuities OBJECT-TYPE
			SYNTAX Counter32
			MAX-ACCESS read-write
			STATUS current
			DESCRIPTION
				"Number of RTP sequence number discontinuities after FEC decoding. Discontinuity
				is detected when the sequence number of received RTP packet (after decoding) is 
				not equal to sequence number of previous packet. Discontinuities are typically 
				detected when there are uncorrected packets in the stream, or when there are 
				brief interruptions in the stream (in range of about 1-20 seconds). Also abrupt 
				change of stream source will be counted as discontinuity because of jump in RTP 
				sequence numbers.
				Writing any value in this oid will clear all ProMpegFec related counters on
				the current interface."
			::= { proMpegFecEntry 7 }
	
			
		-- 1.3.6.1.4.1.3715.17.4
		notifications OBJECT IDENTIFIER ::= { luminato 4 }	

		
		-- 1.3.6.1.4.1.3715.17.5
		statusFlags OBJECT IDENTIFIER ::= { luminato 5 }

			
		-- 1.3.6.1.4.1.3715.17.5.2
		moduleStatusTable OBJECT-TYPE
			SYNTAX SEQUENCE OF ModuleStatusEntry
			MAX-ACCESS not-accessible
			STATUS current
			DESCRIPTION			" "
			::= { statusFlags 2 }

		
		-- 1.3.6.1.4.1.3715.17.5.2.1
		moduleStatusEntry OBJECT-TYPE
			SYNTAX ModuleStatusEntry
			MAX-ACCESS not-accessible
			STATUS current
			DESCRIPTION			" "
			INDEX { moduleId }
			::= { moduleStatusTable 1 }

		
		ModuleStatusEntry ::=
			SEQUENCE { 
				moduleId
					INTEGER,
				modulePidConflictStatus
					INTEGER,
				moduleTemperatureHigh
					INTEGER,
				moduleTemperatureLow
					INTEGER,
				modulePidCapaStatus
					INTEGER,
				modulePsisiCaptureCapaStatus
					INTEGER,
				moduleSidAllocStatus
					INTEGER,
				moduleCaDetectStatus
					INTEGER,
				moduleDetectStatus
					INTEGER,
				moduleVoltageHigh
					INTEGER,
				moduleVoltageLow
					INTEGER,
				moduleCurrentHigh
					INTEGER,
				moduleCurrentLow
					INTEGER,
				moduleDaemonInitStatus
					INTEGER,
				moduleDriverStatus
					INTEGER,
				moduleHwStatus
					INTEGER,
				moduleFanStatus
					INTEGER,
				modulePowerSourceStatus
					INTEGER,
				modulePsuOverloadStatus
					INTEGER,
				moduleBootupProgressStatus
					INTEGER,
				moduleBootupRetryStatus
					INTEGER,
				moduleBootupStatus
					INTEGER,
				moduleShutdownProgressStatus
					INTEGER,
				moduleConnStatus
					INTEGER,
				moduleCompatStatus
					INTEGER,
				moduleUpcPowerLow
					INTEGER,
				moduleUpcPowerHigh
					INTEGER,
				moduleCalibrDataStatus
					INTEGER,
				moduleCalibrDataCheckStatus
					INTEGER,
				moduleDescrStatus
					INTEGER,
				moduleBackupStatus
					INTEGER,
				moduleNitOutputsStatus
					INTEGER,
				moduleNitSelectionStatus
					INTEGER,
				moduleNitConfChangeStatus
					INTEGER,
				moduleNitDataQueryStatus
					INTEGER,
				moduleNitWizardStatus
					INTEGER,
				moduleQamFreqStatus
					INTEGER,
				moduleOutputSidStatus
					INTEGER,
				moduleConfStatus
					INTEGER,
				moduleFreqStatus
					INTEGER,
				moduleOutputPowerStatus
					INTEGER,
				moduleSymrateStatus
					INTEGER,
				moduleChanDistStatus
					INTEGER,
				moduleLnbVoltStatus
					INTEGER,
				moduleFecRateStatus
					INTEGER,
				moduleLnbCurrStatus
					INTEGER,
				moduleFreqOffsetStatus
					INTEGER,
				moduleDescrRestartStatus
					INTEGER,
				moduleCamRestartStatus
					INTEGER,
				moduleEcmgStatus
					INTEGER,
				moduleEcmStreamStatus
					INTEGER,
				moduleEmmStatus
					INTEGER,
				moduleEmmStreamStatus
					INTEGER,
				moduleEcmgConnStatus
					INTEGER,
				moduleEmmConnStatus
					INTEGER,
				moduleEcmgSpareStatus
					INTEGER,
				moduleBootloaderAvailStatus
					INTEGER,
				moduleBl1UpdateProgStatus
					INTEGER,
				moduleBl2UpdateProgStatus
					INTEGER,
				moduleBl1UpdateStatus
					INTEGER,
				moduleBl2UpdateStatus
					INTEGER,
				moduleActiveBackupStatus
					INTEGER,
				moduleConfProgressStatus
					INTEGER,
				modulePresenceStatus
					INTEGER,
				moduleProcessRestartStatus
					INTEGER,
				moduleBackupLicenseStatus
					INTEGER,
				modulePsisiEditorLicenseStatus
					INTEGER,
				moduleMuxLicenseStatus
					INTEGER,
				moduleDemuxLicenseStatus
					INTEGER,
				moduleDvbLicenseStatus
					INTEGER,
				moduleMsdLicenseStatus
					INTEGER,
				moduleDvbs2LicenseStatus
					INTEGER,
				moduleDvbt2LicenseStatus
					INTEGER,
				moduleScsLicenseStatus
					INTEGER,
				moduleCliLoginStatus
					INTEGER,
				moduleRedunActivationStatus 
					INTEGER,
				moduleExtioPinSignalingStatus
					INTEGER,
				moduleBackupPsuStatus
					INTEGER,
				moduleIntrusionStatus
					INTEGER,
				moduleRedunStatus 
					INTEGER,
				moduleBackupHwStatus
					INTEGER,
				moduleSwUpdateProgress
					INTEGER,
				moduleSwUpdateStatus
					INTEGER,
				moduleEitLicenseStatus
					INTEGER,
				moduleDescramblingStatus
					INTEGER,
				moduleDvbTimeStatus
					INTEGER,
				moduleTunerDcFeedStatus
					INTEGER,
				moduleTunerPlpSelectionReqStatus
					INTEGER,
				moduleTunerPlpStatus
					INTEGER,
				moduleTunerHierarchyStatus
					INTEGER,
				moduleEcmStatus
					INTEGER,
				moduleScramConflictStatus
					INTEGER,
				moduleScramSharedStatus
					INTEGER,
				moduleBackupVoltageHigh
					INTEGER,
				moduleBackupVoltageLow
					INTEGER,
				moduleSdtTableStatus
					INTEGER,
				moduleDescramblingRestart
					INTEGER,
				moduleCaModuleRestart
					INTEGER,
				moduleCaMenuStatus
					INTEGER,
				moduleInvalidCamRouting
					INTEGER,
				moduleNitSidConflict
					INTEGER,
				moduleLicenseMissingFEC
					INTEGER,
				moduleFecCorrectionStatus
					INTEGER,
				moduleFecPacketDropStatus
					INTEGER,
				moduleFecMediaPktsStatus
					INTEGER,
				moduleSfpLinkStatus
					INTEGER,
				moduleBackupSyncModeOff
					INTEGER,
				moduleBackupSyncModeManual
					INTEGER,
				moduleBackupSyncModeAuto
					INTEGER,
				moduleBackupSyncConfStatus
					INTEGER,
				moduleBackupSyncStatus
					INTEGER,
				moduleBackupSyncSwCompatibility
					INTEGER,
				moduleBackupSyncHwCompatibility
					INTEGER,
				moduleBackupSyncConfFaultStatus
					INTEGER,
				moduleBackupSyncConnectionStatus
					INTEGER,
				moduleBackupSyncFromBackupStatus
					INTEGER,
				moduleBackupSyncRebootStatus
					INTEGER,
				moduleBackupSyncLicenseCompatStatus
					INTEGER,
				moduleBackupSyncLicenseCompareStatus
					INTEGER,
				moduleDeviceFirstBootStatus
					INTEGER,
				modulePartitionConfigurationBackup
					INTEGER,
				modulePartitionConfigurationRestore
					INTEGER,
				moduleSwRevertStatus
					INTEGER,
				moduleMaxOutputPidsStatus
					INTEGER,
				moduleUserRebootStatus
					INTEGER,
				moduleRemovalStatus
					INTEGER,
				moduleInsertionStatus
					INTEGER,
				moduleSptsInputConfStatus
					INTEGER
			 }


		-- 1.3.6.1.4.1.3715.17.5.2.1.1
		moduleId OBJECT-TYPE
			SYNTAX INTEGER
			MAX-ACCESS not-accessible
			STATUS current
			DESCRIPTION
				"Module identifier"
			::= { moduleStatusEntry 1 }

		
		-- 1.3.6.1.4.1.3715.17.5.2.1.4
		modulePidConflictStatus OBJECT-TYPE
			SYNTAX INTEGER
				{
				pidOk(1),
				pidConflict(2)
				}
			MAX-ACCESS read-only
			STATUS current
			DESCRIPTION
				"PID conflict status"
			::= { moduleStatusEntry 4 }

		
		-- 1.3.6.1.4.1.3715.17.5.2.1.6
		moduleTemperatureHigh OBJECT-TYPE
			SYNTAX INTEGER
				{
				temperatureNominal(1),
				temperatureHigh(2)
				}
			MAX-ACCESS read-only
			STATUS current
			DESCRIPTION
				"High temperature status"
			::= { moduleStatusEntry 6 }

		
		-- 1.3.6.1.4.1.3715.17.5.2.1.7
		moduleTemperatureLow OBJECT-TYPE
			SYNTAX INTEGER
				{
				temperatureNominal(1),
				temperatureLow(2)
				}
			MAX-ACCESS read-only
			STATUS current
			DESCRIPTION
				"Low temperature status"
			::= { moduleStatusEntry 7 }

		
		-- 1.3.6.1.4.1.3715.17.5.2.1.4104
		modulePidCapaStatus OBJECT-TYPE
			SYNTAX INTEGER
				{
				capacityNominal(1),
				capacityExceeded(2)
				}
			MAX-ACCESS read-only
			STATUS current
			DESCRIPTION
				"Module PID capacity status"
			::= { moduleStatusEntry 4104 }

		
		-- 1.3.6.1.4.1.3715.17.5.2.1.4105
		modulePsisiCaptureCapaStatus OBJECT-TYPE
			SYNTAX INTEGER
				{
				capacityNominal(1),
				capacityExceeded(2)
				}
			MAX-ACCESS read-only
			STATUS current
			DESCRIPTION
				"Module PSI/SI table capture capacity status"
			::= { moduleStatusEntry 4105 }

		
		-- 1.3.6.1.4.1.3715.17.5.2.1.4106
		moduleSidAllocStatus OBJECT-TYPE
			SYNTAX INTEGER
				{
				sidAllocOk(1),
				sidAllocCapaExceeded(2)
				}
			MAX-ACCESS read-only
			STATUS current
			DESCRIPTION
				"Module service ID allocation capacity status"
			::= { moduleStatusEntry 4106 }

		
		-- 1.3.6.1.4.1.3715.17.5.2.1.4108
		moduleCaDetectStatus OBJECT-TYPE
			SYNTAX INTEGER
				{
				moduleOk(1),
				moduleMissing(2)
				}
			MAX-ACCESS read-only
			STATUS current
			DESCRIPTION
				"CA module detection status"
			::= { moduleStatusEntry 4108 }

		
		-- 1.3.6.1.4.1.3715.17.5.2.1.4111
		moduleDetectStatus OBJECT-TYPE
			SYNTAX INTEGER
				{
				moduleOk(1),
				moduleUnknown(2)
				}
			MAX-ACCESS read-only
			STATUS current
			DESCRIPTION
				"Module detection status"
			::= { moduleStatusEntry 4111 }

		
		-- 1.3.6.1.4.1.3715.17.5.2.1.4112
		moduleVoltageHigh OBJECT-TYPE
			SYNTAX INTEGER
				{
				voltageNominal(1),
				voltageHigh(2)
				}
			MAX-ACCESS read-only
			STATUS current
			DESCRIPTION
				"High voltage status"
			::= { moduleStatusEntry 4112 }

		
		-- 1.3.6.1.4.1.3715.17.5.2.1.4113
		moduleVoltageLow OBJECT-TYPE
			SYNTAX INTEGER
				{
				voltageNominal(1),
				voltageLow(2)
				}
			MAX-ACCESS read-only
			STATUS current
			DESCRIPTION
				"Low voltage status"
			::= { moduleStatusEntry 4113 }

		
		-- 1.3.6.1.4.1.3715.17.5.2.1.4114
		moduleCurrentHigh OBJECT-TYPE
			SYNTAX INTEGER
				{
				currentNominal(1),
				currentHigh(2)
				}
			MAX-ACCESS read-only
			STATUS current
			DESCRIPTION
				"High current status"
			::= { moduleStatusEntry 4114 }

		
		-- 1.3.6.1.4.1.3715.17.5.2.1.4115
		moduleCurrentLow OBJECT-TYPE
			SYNTAX INTEGER
				{
				currentNominal(1),
				currentLow(2)
				}
			MAX-ACCESS read-only
			STATUS current
			DESCRIPTION
				"Low current status"
			::= { moduleStatusEntry 4115 }

		
		-- 1.3.6.1.4.1.3715.17.5.2.1.4127
		moduleDaemonInitStatus OBJECT-TYPE
			SYNTAX INTEGER
				{
				daemonNominal(1),
				daemonInitFailed(2)
				}
			MAX-ACCESS read-only
			STATUS current
			DESCRIPTION
				"Module daemon initialization status"
			::= { moduleStatusEntry 4127 }

		
		-- 1.3.6.1.4.1.3715.17.5.2.1.4129
		moduleDriverStatus OBJECT-TYPE
			SYNTAX INTEGER
				{
				driverNominal(1),
				driverFailure(2)
				}
			MAX-ACCESS read-only
			STATUS current
			DESCRIPTION
				"Module device driver status"
			::= { moduleStatusEntry 4129 }

		
		-- 1.3.6.1.4.1.3715.17.5.2.1.4130
		moduleHwStatus OBJECT-TYPE
			SYNTAX INTEGER
				{
				hwNominal(1),
				hwFailure(2)
				}
			MAX-ACCESS read-only
			STATUS current
			DESCRIPTION
				"Module hardware status"
			::= { moduleStatusEntry 4130 }

		
		-- 1.3.6.1.4.1.3715.17.5.2.1.4131
		moduleFanStatus OBJECT-TYPE
			SYNTAX INTEGER
				{
				fanNominal(1),
				fanFailure(2)
				}
			MAX-ACCESS read-only
			STATUS current
			DESCRIPTION
				"Fan status"
			::= { moduleStatusEntry 4131 }

		
		-- 1.3.6.1.4.1.3715.17.5.2.1.4132
		modulePowerSourceStatus OBJECT-TYPE
			SYNTAX INTEGER
				{
				runningOnMainPower(1),
				runningOnBackupPower(2)
				}
			MAX-ACCESS read-only
			STATUS current
			DESCRIPTION
				"Power source status"
			::= { moduleStatusEntry 4132 }

		
		-- 1.3.6.1.4.1.3715.17.5.2.1.4133
		modulePsuOverloadStatus OBJECT-TYPE
			SYNTAX INTEGER
				{
				psuNominal(1),
				psuOverloaded(2)
				}
			MAX-ACCESS read-only
			STATUS current
			DESCRIPTION
				"Power supply overload status"
			::= { moduleStatusEntry 4133 }

		
		-- 1.3.6.1.4.1.3715.17.5.2.1.4134
		moduleBootupProgressStatus OBJECT-TYPE
			SYNTAX INTEGER
				{
				moduleNominal(1),
				moduleBootingUp(2)
				}
			MAX-ACCESS read-only
			STATUS current
			DESCRIPTION
				"Module bootup progress"
			::= { moduleStatusEntry 4134 }

		
		-- 1.3.6.1.4.1.3715.17.5.2.1.4135
		moduleBootupRetryStatus OBJECT-TYPE
			SYNTAX INTEGER
				{
				moduleNominal(1),
				moduleBootingRetrying(2)
				}
			MAX-ACCESS read-only
			STATUS current
			DESCRIPTION
				"Module bootup retry status"
			::= { moduleStatusEntry 4135 }

		
		-- 1.3.6.1.4.1.3715.17.5.2.1.4136
		moduleBootupStatus OBJECT-TYPE
			SYNTAX INTEGER
				{
				moduleNominal(1),
				moduleBootFailure(2)
				}
			MAX-ACCESS read-only
			STATUS current
			DESCRIPTION
				"Module bootup status"
			::= { moduleStatusEntry 4136 }

		
		-- 1.3.6.1.4.1.3715.17.5.2.1.4137
		moduleShutdownProgressStatus OBJECT-TYPE
			SYNTAX INTEGER
				{
				moduleNominal(1),
				moduleShuttingDown(2)
				}
			MAX-ACCESS read-only
			STATUS current
			DESCRIPTION
				"Module shutdown progress"
			::= { moduleStatusEntry 4137 }

		
		-- 1.3.6.1.4.1.3715.17.5.2.1.4138
		moduleConnStatus OBJECT-TYPE
			SYNTAX INTEGER
				{
				connectionNominal(1),
				connectionLost(2)
				}
			MAX-ACCESS read-only
			STATUS current
			DESCRIPTION
				"Module connection status"
			::= { moduleStatusEntry 4138 }

		
		-- 1.3.6.1.4.1.3715.17.5.2.1.4139
		moduleCompatStatus OBJECT-TYPE
			SYNTAX INTEGER
				{
				moduleNominal(1),
				moduleIncompatible(2)
				}
			MAX-ACCESS read-only
			STATUS current
			DESCRIPTION
				"Module compatibility status"
			::= { moduleStatusEntry 4139 }

		
		-- 1.3.6.1.4.1.3715.17.5.2.1.4147
		moduleUpcPowerLow OBJECT-TYPE
			SYNTAX INTEGER
				{
				ucpPowerNominal(1),
				ucpPowerLow(2)
				}
			MAX-ACCESS read-only
			STATUS current
			DESCRIPTION
				"Module UPC input power low status"
			::= { moduleStatusEntry 4147 }

		
		-- 1.3.6.1.4.1.3715.17.5.2.1.4148
		moduleUpcPowerHigh OBJECT-TYPE
			SYNTAX INTEGER
				{
				ucpPowerNominal(1),
				ucpPowerHigh(2)
				}
			MAX-ACCESS read-only
			STATUS current
			DESCRIPTION
				"Module UPC input power high status"
			::= { moduleStatusEntry 4148 }

		
		-- 1.3.6.1.4.1.3715.17.5.2.1.4149
		moduleCalibrDataStatus OBJECT-TYPE
			SYNTAX INTEGER
				{
				calibrationDataNominal(1),
				calibrationDataMissing(2)
				}
			MAX-ACCESS read-only
			STATUS current
			DESCRIPTION
				"Module calibration data status"
			::= { moduleStatusEntry 4149 }

		
		-- 1.3.6.1.4.1.3715.17.5.2.1.4150
		moduleCalibrDataCheckStatus OBJECT-TYPE
			SYNTAX INTEGER
				{
				checkOk(1),
				checkSkipped(2)
				}
			MAX-ACCESS read-only
			STATUS current
			DESCRIPTION
				"Module calibration data check status"
			::= { moduleStatusEntry 4150 }

		
		-- 1.3.6.1.4.1.3715.17.5.2.1.4151
		moduleDescrStatus OBJECT-TYPE
			SYNTAX INTEGER
				{
				descramblingOk(1),
				descramblingFailure(2)
				}
			MAX-ACCESS read-only
			STATUS current
			DESCRIPTION
				"Module descrambling status"
			::= { moduleStatusEntry 4151 }

		
		-- 1.3.6.1.4.1.3715.17.5.2.1.4153
		moduleBackupStatus OBJECT-TYPE
			SYNTAX INTEGER
				{
				moduleNominal(1),
				moduleSwitchedToBackup(2)
				}
			MAX-ACCESS read-only
			STATUS current
			DESCRIPTION
				"Module backup status"
			::= { moduleStatusEntry 4153 }

		
		-- 1.3.6.1.4.1.3715.17.5.2.1.4154
		moduleNitOutputsStatus OBJECT-TYPE
			SYNTAX INTEGER
				{
				nitOutputsNominal(1),
				noSupportedNitOutputs(2)
				}
			MAX-ACCESS read-only
			STATUS current
			DESCRIPTION
				"Supported Nit output module status"
			::= { moduleStatusEntry 4154 }

		
		-- 1.3.6.1.4.1.3715.17.5.2.1.4155
		moduleNitSelectionStatus OBJECT-TYPE
			SYNTAX INTEGER
				{
				nitSelectionNominal(1),
				noSelectedNitOutputs(2)
				}
			MAX-ACCESS read-only
			STATUS current
			DESCRIPTION
				"Nit output selection status"
			::= { moduleStatusEntry 4155 }

		
		-- 1.3.6.1.4.1.3715.17.5.2.1.4156
		moduleNitConfChangeStatus OBJECT-TYPE
			SYNTAX INTEGER
				{
				nitConfNominal(1),
				nitConfChanged(2)
				}
			MAX-ACCESS read-only
			STATUS current
			DESCRIPTION
				"Nit configuration change status"
			::= { moduleStatusEntry 4156 }

		
		-- 1.3.6.1.4.1.3715.17.5.2.1.4157
		moduleNitDataQueryStatus OBJECT-TYPE
			SYNTAX INTEGER
				{
				nitDataQueryNominal(1),
				nitDataQueryFailure(2)
				}
			MAX-ACCESS read-only
			STATUS current
			DESCRIPTION
				"Nit data query status"
			::= { moduleStatusEntry 4157 }

		
		-- 1.3.6.1.4.1.3715.17.5.2.1.4158
		moduleNitWizardStatus OBJECT-TYPE
			SYNTAX INTEGER
				{
				nitWizardNominal(1),
				nitWizardFailure(2)
				}
			MAX-ACCESS read-only
			STATUS current
			DESCRIPTION
				"Nit wizard status"
			::= { moduleStatusEntry 4158 }

		
		-- 1.3.6.1.4.1.3715.17.5.2.1.4159
		moduleQamFreqStatus OBJECT-TYPE
			SYNTAX INTEGER
				{
				qamFreqUnique(1),
				qamFreqDuplicate(2)
				}
			MAX-ACCESS read-only
			STATUS current
			DESCRIPTION
				"QAM output unique frequency status"
			::= { moduleStatusEntry 4159 }

		
		-- 1.3.6.1.4.1.3715.17.5.2.1.4173
		moduleOutputSidStatus OBJECT-TYPE
			SYNTAX INTEGER
				{
				sidOk(1),
				sidConflict(2)
				}
			MAX-ACCESS read-only
			STATUS current
			DESCRIPTION
				"Module output SID status"
			::= { moduleStatusEntry 4173 }

		
		-- 1.3.6.1.4.1.3715.17.5.2.1.4175
		moduleConfStatus OBJECT-TYPE
			SYNTAX INTEGER
				{
				configurationOk(1),
				configurationUnsupported(2)
				}
			MAX-ACCESS read-only
			STATUS current
			DESCRIPTION
				"Module configuration status"
			::= { moduleStatusEntry 4175 }

		
		-- 1.3.6.1.4.1.3715.17.5.2.1.4176
		moduleFreqStatus OBJECT-TYPE
			SYNTAX INTEGER
				{
				freqOk(1),
				freqOutOfRange(2)
				}
			MAX-ACCESS read-only
			STATUS current
			DESCRIPTION
				"Module frequency configuration range status"
			::= { moduleStatusEntry 4176 }

		
		-- 1.3.6.1.4.1.3715.17.5.2.1.4177
		moduleOutputPowerStatus OBJECT-TYPE
			SYNTAX INTEGER
				{
				powerOk(1),
				powerOutOfRange(2)
				}
			MAX-ACCESS read-only
			STATUS current
			DESCRIPTION
				"Module output power status"
			::= { moduleStatusEntry 4177 }

		
		-- 1.3.6.1.4.1.3715.17.5.2.1.4178
		moduleSymrateStatus OBJECT-TYPE
			SYNTAX INTEGER
				{
				symbolRateOk(1),
				symbolRateOutOfRange(2)
				}
			MAX-ACCESS read-only
			STATUS current
			DESCRIPTION
				"Module symbol rate configuration status"
			::= { moduleStatusEntry 4178 }

		
		-- 1.3.6.1.4.1.3715.17.5.2.1.4179
		moduleChanDistStatus OBJECT-TYPE
			SYNTAX INTEGER
				{
				chanDistOk(1),
				chanDistTooNarrow(2)
				}
			MAX-ACCESS read-only
			STATUS current
			DESCRIPTION
				"Module channel distance configuration status"
			::= { moduleStatusEntry 4179 }

		
		-- 1.3.6.1.4.1.3715.17.5.2.1.4180
		moduleLnbVoltStatus OBJECT-TYPE
			SYNTAX INTEGER
				{
				lnbVoltageOk(1),
				lnbVoltageInvalid(2)
				}
			MAX-ACCESS read-only
			STATUS current
			DESCRIPTION
				"Module LNB voltage configuration status"
			::= { moduleStatusEntry 4180 }

		
		-- 1.3.6.1.4.1.3715.17.5.2.1.4181
		moduleFecRateStatus OBJECT-TYPE
			SYNTAX INTEGER
				{
				fecRateOk(1),
				fecRateInvalid(2)
				}
			MAX-ACCESS read-only
			STATUS current
			DESCRIPTION
				"Module FEC rate configuration vs modulation status"
			::= { moduleStatusEntry 4181 }

		
		-- 1.3.6.1.4.1.3715.17.5.2.1.4182
		moduleLnbCurrStatus OBJECT-TYPE
			SYNTAX INTEGER
				{
				lnbCurrentOk(1),
				lnbCurrentInvalid(2)
				}
			MAX-ACCESS read-only
			STATUS current
			DESCRIPTION
				"Module LNB current status"
			::= { moduleStatusEntry 4182 }

		
		-- 1.3.6.1.4.1.3715.17.5.2.1.4183
		moduleFreqOffsetStatus OBJECT-TYPE
			SYNTAX INTEGER
				{
				freqOffsetOk(1),
				freqOffsetInvalid(2)
				}
			MAX-ACCESS read-only
			STATUS current
			DESCRIPTION
				"Module frequency offset configuration status"
			::= { moduleStatusEntry 4183 }

		
		-- 1.3.6.1.4.1.3715.17.5.2.1.4185
		moduleDescrRestartStatus OBJECT-TYPE
			SYNTAX INTEGER
				{
				descramblingNominal(1),
				descramblingRestarting(2)
				}
			MAX-ACCESS read-only
			STATUS current
			DESCRIPTION
				"Module descrambling restart status"
			::= { moduleStatusEntry 4185 }

		
		-- 1.3.6.1.4.1.3715.17.5.2.1.4186
		moduleCamRestartStatus OBJECT-TYPE
			SYNTAX INTEGER
				{
				camNominal(1),
				camRestarting(2)
				}
			MAX-ACCESS read-only
			STATUS current
			DESCRIPTION
				"Module CAM restart status"
			::= { moduleStatusEntry 4186 }

		
		-- 1.3.6.1.4.1.3715.17.5.2.1.4187
		moduleEcmgStatus OBJECT-TYPE
			SYNTAX INTEGER
				{
				ecmgNominal(1),
				ecmgFailure(2)
				}
			MAX-ACCESS read-only
			STATUS current
			DESCRIPTION
				"Ecmg status"
			::= { moduleStatusEntry 4187 }

		
		-- 1.3.6.1.4.1.3715.17.5.2.1.4188
		moduleEcmStreamStatus OBJECT-TYPE
			SYNTAX INTEGER
				{
				ecmStreamNominal(1),
				ecmStreamFailure(2)
				}
			MAX-ACCESS read-only
			STATUS current
			DESCRIPTION
				"Ecm stream status"
			::= { moduleStatusEntry 4188 }

		
		-- 1.3.6.1.4.1.3715.17.5.2.1.4189
		moduleEmmStatus OBJECT-TYPE
			SYNTAX INTEGER
				{
				emmNominal(1),
				emmFailure(2)
				}
			MAX-ACCESS read-only
			STATUS current
			DESCRIPTION
				"Emm status"
			::= { moduleStatusEntry 4189 }

		
		-- 1.3.6.1.4.1.3715.17.5.2.1.4190
		moduleEmmStreamStatus OBJECT-TYPE
			SYNTAX INTEGER
				{
				emmStreamNominal(1),
				emmStreamFailure(2)
				}
			MAX-ACCESS read-only
			STATUS current
			DESCRIPTION
				"Emm stream status"
			::= { moduleStatusEntry 4190 }

		
		-- 1.3.6.1.4.1.3715.17.5.2.1.4191
		moduleEcmgConnStatus OBJECT-TYPE
			SYNTAX INTEGER
				{
				ecmgConnNominal(1),
				ecmgNotConnected(2)
				}
			MAX-ACCESS read-only
			STATUS current
			DESCRIPTION
				"Ecmg connection status"
			::= { moduleStatusEntry 4191 }

		
		-- 1.3.6.1.4.1.3715.17.5.2.1.4192
		moduleEmmConnStatus OBJECT-TYPE
			SYNTAX INTEGER
				{
				emmConnNominal(1),
				emmNotConnected(2)
				}
			MAX-ACCESS read-only
			STATUS current
			DESCRIPTION
				"Emm connection status"
			::= { moduleStatusEntry 4192 }

		
		-- 1.3.6.1.4.1.3715.17.5.2.1.4194
		moduleEcmgSpareStatus OBJECT-TYPE
			SYNTAX INTEGER
				{
				ecmgNominal(1),
				ecmgSwitchedToSpare(2)
				}
			MAX-ACCESS read-only
			STATUS current
			DESCRIPTION
				"Ecmg spare connection status"
			::= { moduleStatusEntry 4194 }

		
		-- 1.3.6.1.4.1.3715.17.5.2.1.4195
		moduleBootloaderAvailStatus OBJECT-TYPE
			SYNTAX INTEGER
				{
				bootloaderOk(1),
				bootloaderObsolete(2)
				}
			MAX-ACCESS read-only
			STATUS current
			DESCRIPTION
				"Module bootloader availability status"
			::= { moduleStatusEntry 4195 }

		
		-- 1.3.6.1.4.1.3715.17.5.2.1.4196
		moduleBl1UpdateProgStatus OBJECT-TYPE
			SYNTAX INTEGER
				{
				bootloaderNominal(1),
				bootloaderUpdating(2)
				}
			MAX-ACCESS read-only
			STATUS current
			DESCRIPTION
				"Module bootloader update progress"
			::= { moduleStatusEntry 4196 }

		
		-- 1.3.6.1.4.1.3715.17.5.2.1.4197
		moduleBl2UpdateProgStatus OBJECT-TYPE
			SYNTAX INTEGER
				{
				bootloaderNominal(1),
				bootloaderUpdating(2)
				}
			MAX-ACCESS read-only
			STATUS current
			DESCRIPTION
				"Module bootloader update progress"
			::= { moduleStatusEntry 4197 }

		
		-- 1.3.6.1.4.1.3715.17.5.2.1.4198
		moduleBl1UpdateStatus OBJECT-TYPE
			SYNTAX INTEGER
				{
				bootloaderNominal(1),
				bootloaderUpdateFailure(2)
				}
			MAX-ACCESS read-only
			STATUS current
			DESCRIPTION
				"Module bootloader update status"
			::= { moduleStatusEntry 4198 }

		
		-- 1.3.6.1.4.1.3715.17.5.2.1.4199
		moduleBl2UpdateStatus OBJECT-TYPE
			SYNTAX INTEGER
				{
				bootloaderNominal(1),
				bootloaderUpdateFailure(2)
				}
			MAX-ACCESS read-only
			STATUS current
			DESCRIPTION
				"Module bootloader update status"
			::= { moduleStatusEntry 4199 }

		
		-- 1.3.6.1.4.1.3715.17.5.2.1.4203
		moduleActiveBackupStatus OBJECT-TYPE
			SYNTAX INTEGER
				{
				backupPassive(1),
				backupActive(2)
				}
			MAX-ACCESS read-only
			STATUS current
			DESCRIPTION
				"Backup module status"
			::= { moduleStatusEntry 4203 }

		
		-- 1.3.6.1.4.1.3715.17.5.2.1.4205
		moduleConfProgressStatus OBJECT-TYPE
			SYNTAX INTEGER
				{
				moduleNominal(1),
				moduleConfiguring(2)
				}
			MAX-ACCESS read-only
			STATUS current
			DESCRIPTION
				"Module configuration progress"
			::= { moduleStatusEntry 4205 }

		
		-- 1.3.6.1.4.1.3715.17.5.2.1.4206
		modulePresenceStatus OBJECT-TYPE
			SYNTAX INTEGER
				{
				moduleNominal(1),
				noModule(2)
				}
			MAX-ACCESS read-only
			STATUS current
			DESCRIPTION
				"Module presence progress"
			::= { moduleStatusEntry 4206 }

		
		-- 1.3.6.1.4.1.3715.17.5.2.1.4208
		moduleProcessRestartStatus OBJECT-TYPE
			SYNTAX INTEGER
				{
				processesNominal(1),
				processRestarted(2)
				}
			MAX-ACCESS read-only
			STATUS current
			DESCRIPTION
				"Process restart status"
			::= { moduleStatusEntry 4208 }

		
		-- 1.3.6.1.4.1.3715.17.5.2.1.4209
		moduleBackupLicenseStatus OBJECT-TYPE
			SYNTAX INTEGER
				{
				licenseOk(1),
				notLicensed(2)
				}
			MAX-ACCESS read-only
			STATUS current
			DESCRIPTION
				"Backup license status"
			::= { moduleStatusEntry 4209 }

		
		-- 1.3.6.1.4.1.3715.17.5.2.1.4210
		modulePsisiEditorLicenseStatus OBJECT-TYPE
			SYNTAX INTEGER
				{
				licenseOk(1),
				notLicensed(2)
				}
			MAX-ACCESS read-only
			STATUS current
			DESCRIPTION
				"PSI/SI editor license status"
			::= { moduleStatusEntry 4210 }

		
		-- 1.3.6.1.4.1.3715.17.5.2.1.4211
		moduleMuxLicenseStatus OBJECT-TYPE
			SYNTAX INTEGER
				{
				licenseOk(1),
				notLicensed(2)
				}
			MAX-ACCESS read-only
			STATUS current
			DESCRIPTION
				"Multiplexing license status"
			::= { moduleStatusEntry 4211 }

		
		-- 1.3.6.1.4.1.3715.17.5.2.1.4212
		moduleDemuxLicenseStatus OBJECT-TYPE
			SYNTAX INTEGER
				{
				licenseOk(1),
				notLicensed(2)
				}
			MAX-ACCESS read-only
			STATUS current
			DESCRIPTION
				"Demultiplexing license status"
			::= { moduleStatusEntry 4212 }

		
		-- 1.3.6.1.4.1.3715.17.5.2.1.4213
		moduleDvbLicenseStatus OBJECT-TYPE
			SYNTAX INTEGER
				{
				licenseOk(1),
				notLicensed(2)
				}
			MAX-ACCESS read-only
			STATUS current
			DESCRIPTION
				"DVB processing license status"
			::= { moduleStatusEntry 4213 }

		
		-- 1.3.6.1.4.1.3715.17.5.2.1.4214
		moduleMsdLicenseStatus OBJECT-TYPE
			SYNTAX INTEGER
				{
				licenseOk(1),
				notLicensed(2)
				}
			MAX-ACCESS read-only
			STATUS current
			DESCRIPTION
				"MSD license status"
			::= { moduleStatusEntry 4214 }

		
		-- 1.3.6.1.4.1.3715.17.5.2.1.4215
		moduleDvbs2LicenseStatus OBJECT-TYPE
			SYNTAX INTEGER
				{
				licenseOk(1),
				notLicensed(2)
				}
			MAX-ACCESS read-only
			STATUS current
			DESCRIPTION
				"DVB-S2 processing license status"
			::= { moduleStatusEntry 4215 }

		
		-- 1.3.6.1.4.1.3715.17.5.2.1.4216
		moduleDvbt2LicenseStatus OBJECT-TYPE
			SYNTAX INTEGER
				{
				licenseOk(1),
				notLicensed(2)
				}
			MAX-ACCESS read-only
			STATUS current
			DESCRIPTION
				"DVB-T2 processing license status"
			::= { moduleStatusEntry 4216 }

		
		-- 1.3.6.1.4.1.3715.17.5.2.1.4217
		moduleScsLicenseStatus OBJECT-TYPE
			SYNTAX INTEGER
				{
				licenseValid(1),
				notLicensed(2)
				}
			MAX-ACCESS read-only
			STATUS current
			DESCRIPTION
				"Scs license status"
			::= { moduleStatusEntry 4217 }

		
		-- 1.3.6.1.4.1.3715.17.5.2.1.4218
		moduleCliLoginStatus OBJECT-TYPE
			SYNTAX INTEGER
				{
				cliNotLoggedIn(1),
				cliLoggedIn(2)
				}
			MAX-ACCESS read-only
			STATUS current
			DESCRIPTION
				"CLI login status"
			::= { moduleStatusEntry 4218 }

		
		-- 1.3.6.1.4.1.3715.17.5.2.1.4222
		moduleRedunActivationStatus OBJECT-TYPE
			SYNTAX INTEGER
				{
				redundancyPassive(1),
				redundancyActivated(2)
				}
			MAX-ACCESS read-only
			STATUS current
			DESCRIPTION
				"Redundancy activation status"
			::= { moduleStatusEntry 4222 }

		
		-- 1.3.6.1.4.1.3715.17.5.2.1.4223
		moduleExtioPinSignalingStatus OBJECT-TYPE
			SYNTAX INTEGER
				{
				extioPinNominal(1),
				extioPinSignaled(2)
				}
			MAX-ACCESS read-only
			STATUS current
			DESCRIPTION
				"EXT-IO pin status"
			::= { moduleStatusEntry 4223 }

		
		-- 1.3.6.1.4.1.3715.17.5.2.1.4224
		moduleBackupPsuStatus OBJECT-TYPE
			SYNTAX INTEGER
				{
				backupPsuNominal(1),
				backupPsuFailure(2)
				}
			MAX-ACCESS read-only
			STATUS current
			DESCRIPTION
				"Backup power supply status"
			::= { moduleStatusEntry 4224 }

		
		-- 1.3.6.1.4.1.3715.17.5.2.1.4225
		moduleIntrusionStatus OBJECT-TYPE
			SYNTAX INTEGER
				{
				intrusionNominal(1),
				intrusionDetected(2)
				}
			MAX-ACCESS read-only
			STATUS current
			DESCRIPTION
				"Intrusion detection status"
			::= { moduleStatusEntry 4225 }

		
		-- 1.3.6.1.4.1.3715.17.5.2.1.4227
		moduleRedunStatus OBJECT-TYPE
			SYNTAX INTEGER
				{
				redundancyOk(1),
				redundancyFailure(2)
				}
			MAX-ACCESS read-only
			STATUS current
			DESCRIPTION
				"Redundancy status"
			::= { moduleStatusEntry 4227 }

		
		-- 1.3.6.1.4.1.3715.17.5.2.1.4230
		moduleBackupHwStatus OBJECT-TYPE
			SYNTAX INTEGER
				{
				backupHwOk(1),
				backupHwNotSupported(2)
				}
			MAX-ACCESS read-only
			STATUS current
			DESCRIPTION
				"Hardware backup support status"
			::= { moduleStatusEntry 4230 }

		
		-- 1.3.6.1.4.1.3715.17.5.2.1.4231
		moduleSwUpdateProgress OBJECT-TYPE
			SYNTAX INTEGER
				{
				swUpdateInactive(1),
				swUpdateInProgress(2)
				}
			MAX-ACCESS read-only
			STATUS current
			DESCRIPTION
				"Software update progress"
			::= { moduleStatusEntry 4231 }

		
		-- 1.3.6.1.4.1.3715.17.5.2.1.4233
		moduleSwUpdateStatus OBJECT-TYPE
			SYNTAX INTEGER
				{
				swNominal(1),
				swUpdateFailure(2)
				}
			MAX-ACCESS read-only
			STATUS current
			DESCRIPTION
				"Software update status"
			::= { moduleStatusEntry 4233 }

		
		-- 1.3.6.1.4.1.3715.17.5.2.1.4235
		moduleEitLicenseStatus OBJECT-TYPE
			SYNTAX INTEGER
				{
				licenseValid(1),
				notLicensed(2)
				}
			MAX-ACCESS read-only
			STATUS current
			DESCRIPTION
				"EIT license status"
			::= { moduleStatusEntry 4235 }
		
		
		-- 1.3.6.1.4.1.3715.17.5.2.1.4237
		moduleDescramblingStatus OBJECT-TYPE
			SYNTAX INTEGER
				{
				descramblingNominal(1),
				descramblingFailure(2)
				}
			MAX-ACCESS read-only
			STATUS current
			DESCRIPTION
				"Descrambling status"
			::= { moduleStatusEntry 4237 }

		
		-- 1.3.6.1.4.1.3715.17.5.2.1.4243
		moduleDvbTimeStatus OBJECT-TYPE
			SYNTAX INTEGER
				{
				dvbTimeNominal(1),
				dvbTimeMissing(2)
				}
			MAX-ACCESS read-only
			STATUS current
			DESCRIPTION
				"DVB time detection status"
			::= { moduleStatusEntry 4243 }

		
		-- 1.3.6.1.4.1.3715.17.5.2.1.4245
		moduleTunerDcFeedStatus OBJECT-TYPE
			SYNTAX INTEGER
				{
				currentNominal(1),
				currentOutOfRange(2)
				}
			MAX-ACCESS read-only
			STATUS current
			DESCRIPTION
				"Tuner DC feed current status"
			::= { moduleStatusEntry 4245 }

		
		-- 1.3.6.1.4.1.3715.17.5.2.1.4247
		moduleTunerPlpSelectionReqStatus OBJECT-TYPE
			SYNTAX INTEGER
				{
				plpSelectionOk(1),
				plpSelectionRequired(2)
				}
			MAX-ACCESS read-only
			STATUS current
			DESCRIPTION
				"Tuner data PLP ID requirement status"
			::= { moduleStatusEntry 4247 }

		
		-- 1.3.6.1.4.1.3715.17.5.2.1.4248
		moduleTunerPlpStatus OBJECT-TYPE
			SYNTAX INTEGER
				{
				plpSelectionValid(1),
				plpSelectionNotValid(2)
				}
			MAX-ACCESS read-only
			STATUS current
			DESCRIPTION
				"Tuner data PLP ID validity status"
			::= { moduleStatusEntry 4248 }

		
		-- 1.3.6.1.4.1.3715.17.5.2.1.4249
		moduleTunerHierarchyStatus OBJECT-TYPE
			SYNTAX INTEGER
				{
				hierarchyOk(1),
				hierarchyInvalid(2)
				}
			MAX-ACCESS read-only
			STATUS current
			DESCRIPTION
				"Status of transmission hierarchy"
			::= { moduleStatusEntry 4249 }

		
		-- 1.3.6.1.4.1.3715.17.5.2.1.4250
		moduleEcmStatus OBJECT-TYPE
			SYNTAX INTEGER
				{
				ecmNominal(1),
				ecmMissing(2)
				}
			MAX-ACCESS read-only
			STATUS current
			DESCRIPTION
				"ECM stream connection status"
			::= { moduleStatusEntry 4250 }

		
		-- 1.3.6.1.4.1.3715.17.5.2.1.4251
		moduleScramConflictStatus OBJECT-TYPE
			SYNTAX INTEGER
				{
				scramblingNominal(1),
				scramblingConflict(2)
				}
			MAX-ACCESS read-only
			STATUS current
			DESCRIPTION
				"Module scrambling shared component conflict status"
			::= { moduleStatusEntry 4251 }

		
		-- 1.3.6.1.4.1.3715.17.5.2.1.4252
		moduleScramSharedStatus OBJECT-TYPE
			SYNTAX INTEGER
				{
				scramblingNominal(1),
				scramblingSharedComponent(2)
				}
			MAX-ACCESS read-only
			STATUS current
			DESCRIPTION
				"Module scrambling shared component status"
			::= { moduleStatusEntry 4252 }

		
		-- 1.3.6.1.4.1.3715.17.5.2.1.4253
		moduleBackupVoltageHigh OBJECT-TYPE
			SYNTAX INTEGER
				{
				voltageNominal(1),
				voltageHigh(2)
				}
			MAX-ACCESS read-only
			STATUS current
			DESCRIPTION
				"Backup high voltage status"
			::= { moduleStatusEntry 4253 }

		
		-- 1.3.6.1.4.1.3715.17.5.2.1.4254
		moduleBackupVoltageLow OBJECT-TYPE
			SYNTAX INTEGER
				{
				voltageNominal(1),
				voltageLow(2)
				}
			MAX-ACCESS read-only
			STATUS current
			DESCRIPTION
				"Backup low voltage status"
			::= { moduleStatusEntry 4254 }

		
		-- 1.3.6.1.4.1.3715.17.5.2.1.4255
		moduleSdtTableStatus OBJECT-TYPE
			SYNTAX INTEGER
				{
				sdtTableOk(1),
				invalidSdtTableTemplate(2)
				}
			MAX-ACCESS read-only
			STATUS current
			DESCRIPTION
				"Sdt table template status"
			::= { moduleStatusEntry 4255 }

		
		-- 1.3.6.1.4.1.3715.17.5.2.1.4256
		moduleDescramblingRestart OBJECT-TYPE
			SYNTAX INTEGER
				{
				descramblingNominal(1),
				descramblingRestarting(2)
				}
			MAX-ACCESS read-only
			STATUS current
			DESCRIPTION
				"Descrambling restart status"
			::= { moduleStatusEntry 4256 }

		
		-- 1.3.6.1.4.1.3715.17.5.2.1.4257
		moduleCaModuleRestart OBJECT-TYPE
			SYNTAX INTEGER
				{
				caModuleNominal(1),
				caModuleRestarting(2)
				}
			MAX-ACCESS read-only
			STATUS current
			DESCRIPTION
				"CA module restart status"
			::= { moduleStatusEntry 4257 }

		
		-- 1.3.6.1.4.1.3715.17.5.2.1.4258
		moduleCaMenuStatus OBJECT-TYPE
			SYNTAX INTEGER
				{
				caMenuNominal(1),
				caMenuOpen(2)
				}
			MAX-ACCESS read-only
			STATUS current
			DESCRIPTION
				"CA menu access status"
			::= { moduleStatusEntry 4258 }


		-- 1.3.6.1.4.1.3715.17.5.2.1.4259
		moduleInvalidCamRouting OBJECT-TYPE
			SYNTAX INTEGER
				{
					camRoutingNominal(1),
					camRoutingInvalid(2)
				}
			MAX-ACCESS read-only
			STATUS current
			DESCRIPTION
				"CAM routing status"
			::= { moduleStatusEntry 4259 }


		-- 1.3.6.1.4.1.3715.17.5.2.1.4260
		moduleNitSidConflict OBJECT-TYPE
			SYNTAX INTEGER
				{
					nitSidNominal(1),
					nitSidConflict(2)
				}
			MAX-ACCESS read-only
			STATUS current
			DESCRIPTION
				"Nit / Sid conflict status"
			::= { moduleStatusEntry 4260 }


		-- 1.3.6.1.4.1.3715.17.5.2.1.4262
		moduleLicenseMissingFEC OBJECT-TYPE
			SYNTAX INTEGER
				{
					licenseOk(1),
					licenseMissing(2)
				}
			MAX-ACCESS read-only
			STATUS current
			DESCRIPTION
				"FEC license status"
			::= { moduleStatusEntry 4262 }


		-- 1.3.6.1.4.1.3715.17.5.2.1.4263
		moduleFecCorrectionStatus OBJECT-TYPE
			SYNTAX INTEGER
				{
					correctionNominal(1),
					correctionOverload(2)
				}
			MAX-ACCESS read-only
			STATUS current
			DESCRIPTION
				"Fec packet correction status. Correction overload (2) is result of too many simultaneous missing packets."
			::= { moduleStatusEntry 4263 }


		-- 1.3.6.1.4.1.3715.17.5.2.1.4264
		moduleFecPacketDropStatus OBJECT-TYPE
			SYNTAX INTEGER
				{
					packetsNominal(1),
					packetsDropped(2)
				}
			MAX-ACCESS read-only
			STATUS current
			DESCRIPTION
				"FEC packet discarding status. Packet discarding (2) is resulted by too high bitrate."
			::= { moduleStatusEntry 4264 }


		-- 1.3.6.1.4.1.3715.17.5.2.1.4265
		moduleFecMediaPktsStatus OBJECT-TYPE
			SYNTAX INTEGER
				{
					packetsNominal(1),
					packetsDiscarded(2)
				}
			MAX-ACCESS read-only
			STATUS current
			DESCRIPTION
				"Fec media packet discarding status. Packet discarding (2) is resulted by too high bitrate."
			::= { moduleStatusEntry 4265 }


		-- 1.3.6.1.4.1.3715.17.5.2.1.4269
		moduleSfpLinkStatus OBJECT-TYPE
			SYNTAX INTEGER
				{
					sfpLinkNominal(1),
					sfpLinkDown(2)
				}
			MAX-ACCESS read-only
			STATUS current
			DESCRIPTION
				"SFP link status"
			::= { moduleStatusEntry 4269 }


		-- 1.3.6.1.4.1.3715.17.5.2.1.4272
		moduleBackupSyncModeOff OBJECT-TYPE
			SYNTAX INTEGER
				{
					modeNominal(1),
					modeOff(2)
				}
			MAX-ACCESS read-only
			STATUS current
			DESCRIPTION
				"Backup sync mode off status flag"
			::= { moduleStatusEntry 4272 }


		-- 1.3.6.1.4.1.3715.17.5.2.1.4273
		moduleBackupSyncModeManual OBJECT-TYPE
			SYNTAX INTEGER
				{
					modeNominal(1),
					modeManual(2)
				}
			MAX-ACCESS read-only
			STATUS current
			DESCRIPTION
				"Backup sync mode manual status flag"
			::= { moduleStatusEntry 4273 }


		-- 1.3.6.1.4.1.3715.17.5.2.1.4274
		moduleBackupSyncModeAuto OBJECT-TYPE
			SYNTAX INTEGER
				{
					modeNominal(1),
					modeAuto(2)
				}
			MAX-ACCESS read-only
			STATUS current
			DESCRIPTION
				"Backup sync mode automatic status flag"
			::= { moduleStatusEntry 4274 }


		-- 1.3.6.1.4.1.3715.17.5.2.1.4275
		moduleBackupSyncConfStatus OBJECT-TYPE
			SYNTAX INTEGER
				{
					configurationNominal(1),
					configurationChanged(2)
				}
			MAX-ACCESS read-only
			STATUS current
			DESCRIPTION
				"Backup sync configuration change status"
			::= { moduleStatusEntry 4275 }


		-- 1.3.6.1.4.1.3715.17.5.2.1.4276
		moduleBackupSyncStatus OBJECT-TYPE
			SYNTAX INTEGER
				{
					syncNominal(1),
					synchronizing(2)
				}
			MAX-ACCESS read-only
			STATUS current
			DESCRIPTION
				"Backup configuration synchronization status"
			::= { moduleStatusEntry 4276 }


		-- 1.3.6.1.4.1.3715.17.5.2.1.4278
		moduleBackupSyncSwCompatibility OBJECT-TYPE
			SYNTAX INTEGER
				{
					swCompatible(1),
					swIncompatible(2)
				}
			MAX-ACCESS read-only
			STATUS current
			DESCRIPTION
				"Software version compatibility for backup sync"
			::= { moduleStatusEntry 4278 }


		-- 1.3.6.1.4.1.3715.17.5.2.1.4279
		moduleBackupSyncHwCompatibility OBJECT-TYPE
			SYNTAX INTEGER
				{
					hwCompatible(1),
					hwIncompatible(2)
				}
			MAX-ACCESS read-only
			STATUS current
			DESCRIPTION
				"Hardware version compatibility for backup sync"
			::= { moduleStatusEntry 4279 }


		-- 1.3.6.1.4.1.3715.17.5.2.1.4280
		moduleBackupSyncConfFaultStatus OBJECT-TYPE
			SYNTAX INTEGER
				{
					configurationNominal(1),
					configurationFault(2)
				}
			MAX-ACCESS read-only
			STATUS current
			DESCRIPTION
				"Backup sync configuration fault status"
			::= { moduleStatusEntry 4280 }


		-- 1.3.6.1.4.1.3715.17.5.2.1.4281
		moduleBackupSyncConnectionStatus OBJECT-TYPE
			SYNTAX INTEGER
				{
					connectionNominal(1),
					connectionLost(2)
				}
			MAX-ACCESS read-only
			STATUS current
			DESCRIPTION
				"Backup sync connection status"
			::= { moduleStatusEntry 4281 }


		-- 1.3.6.1.4.1.3715.17.5.2.1.4283
		moduleBackupSyncFromBackupStatus OBJECT-TYPE
			SYNTAX INTEGER
				{
					syncNominal(1),
					syncNotPossible(2)
				}
			MAX-ACCESS read-only
			STATUS current
			DESCRIPTION
				"Status flag for backup autosync from backup to main"
			::= { moduleStatusEntry 4283 }


		-- 1.3.6.1.4.1.3715.17.5.2.1.4284
		moduleBackupSyncRebootStatus OBJECT-TYPE
			SYNTAX INTEGER
				{
					pairDevNominal(1),
					pairDevRebooting(2)
				}
			MAX-ACCESS read-only
			STATUS current
			DESCRIPTION
				"Status flag for rebooting pair device to new configuration"
			::= { moduleStatusEntry 4284 }


		-- 1.3.6.1.4.1.3715.17.5.2.1.4285
		moduleBackupSyncLicenseCompatStatus OBJECT-TYPE
			SYNTAX INTEGER
				{
					licensesCompatible(1),
					licensesIncompatible(2)
				}
			MAX-ACCESS read-only
			STATUS current
			DESCRIPTION
				"License compatibility status flag for backup sync"
			::= { moduleStatusEntry 4285 }


		-- 1.3.6.1.4.1.3715.17.5.2.1.4286
		moduleBackupSyncLicenseCompareStatus OBJECT-TYPE
			SYNTAX INTEGER
				{
					licenseNominal(1),
					licenseComparing(2)
				}
			MAX-ACCESS read-only
			STATUS current
			DESCRIPTION
				"Backup sync license comparing status"
			::= { moduleStatusEntry 4286 }


		-- 1.3.6.1.4.1.3715.17.5.2.1.4288
		moduleDeviceFirstBootStatus OBJECT-TYPE
			SYNTAX INTEGER
				{
					firstBootNominal(1),
					firstBootInProgress(2)
				}
			MAX-ACCESS read-only
			STATUS current
			DESCRIPTION
				"Status flag for device first boot operations"
			::= { moduleStatusEntry 4288 }


		-- 1.3.6.1.4.1.3715.17.5.2.1.4289
		modulePartitionConfigurationBackup OBJECT-TYPE
			SYNTAX INTEGER
				{
					configurationNominal(1),
					configurationBackupInProgress(2)
				}
			MAX-ACCESS read-only
			STATUS current
			DESCRIPTION
				"Status flag for partition configuration backup operation"
			::= { moduleStatusEntry 4289 }


		-- 1.3.6.1.4.1.3715.17.5.2.1.4290
		modulePartitionConfigurationRestore OBJECT-TYPE
			SYNTAX INTEGER
				{
					configurationNominal(1),
					configurationRestoreInProgress(2)
				}
			MAX-ACCESS read-only
			STATUS current
			DESCRIPTION
				"Status flag for partition configuration restore operation"
			::= { moduleStatusEntry 4290 }


		-- 1.3.6.1.4.1.3715.17.5.2.1.4291
		moduleSwRevertStatus OBJECT-TYPE
			SYNTAX INTEGER
				{
					swNominal(1),
					swRevertInProgress(2)
				}
			MAX-ACCESS read-only
			STATUS current
			DESCRIPTION
				"Software revertion status"
			::= { moduleStatusEntry 4291 }


		-- 1.3.6.1.4.1.3715.17.5.2.1.4292
		moduleMaxOutputPidsStatus OBJECT-TYPE
			SYNTAX INTEGER
				{
					pidsNominal(1),
					maxPidsUsed(2)
				}
			MAX-ACCESS read-only
			STATUS current
			DESCRIPTION
				"Status flag for maximum number of Pid allocations"
			::= { moduleStatusEntry 4292 }


		-- 1.3.6.1.4.1.3715.17.5.2.1.4293
		moduleUserRebootStatus OBJECT-TYPE
			SYNTAX INTEGER
				{
					moduleNominal(1),
					moduleRebootedByUser(2)
				}
			MAX-ACCESS read-only
			STATUS current
			DESCRIPTION
				"Status flag for user initiated reboot"
			::= { moduleStatusEntry 4293 }


		-- 1.3.6.1.4.1.3715.17.5.2.1.4294
		moduleRemovalStatus OBJECT-TYPE
			SYNTAX INTEGER
				{
					moduleNominal(1),
					moduleRemoved(2)
				}
			MAX-ACCESS read-only
			STATUS current
			DESCRIPTION
				"Status flag for module removal"
			::= { moduleStatusEntry 4294 }


		-- 1.3.6.1.4.1.3715.17.5.2.1.4295
		moduleInsertionStatus OBJECT-TYPE
			SYNTAX INTEGER
				{
					moduleNominal(1),
					moduleInserted(2)
				}
			MAX-ACCESS read-only
			STATUS current
			DESCRIPTION
				"Status flag for module insertion"
			::= { moduleStatusEntry 4295 }


		-- 1.3.6.1.4.1.3715.17.5.2.1.4296
		moduleSptsInputConfStatus OBJECT-TYPE
			SYNTAX INTEGER
				{
					sptsInputNominal(1),
					inputNotSpts(2)
				}
			MAX-ACCESS read-only
			STATUS current
			DESCRIPTION
				"Status flag for input spts misconfiguration"
			::= { moduleStatusEntry 4296 }



		-- 1.3.6.1.4.1.3715.17.5.3
		ifStatusTable OBJECT-TYPE
			SYNTAX SEQUENCE OF IfStatusEntry
			MAX-ACCESS not-accessible
			STATUS current
			DESCRIPTION			" "
			::= { statusFlags 3 }

		
		-- 1.3.6.1.4.1.3715.17.5.3.1
		ifStatusEntry OBJECT-TYPE
			SYNTAX IfStatusEntry
			MAX-ACCESS not-accessible
			STATUS current
			DESCRIPTION			" "
			INDEX { moduleId, ifDirection, ifId }
			::= { ifStatusTable 1 }

		
		IfStatusEntry ::=
			SEQUENCE { 
				ifId
					INTEGER,
				ifDirection
					INTEGER,
				ifSignalStatus
					INTEGER,
				ifAsiLinkStatus
					INTEGER,
				ifLinkStatus
					INTEGER
			 }

		-- 1.3.6.1.4.1.3715.17.5.3.1.1
		ifId OBJECT-TYPE
			SYNTAX INTEGER
			MAX-ACCESS not-accessible
			STATUS current
			DESCRIPTION
				"Interface identifier"
			::= { ifStatusEntry 1 }

		
		-- 1.3.6.1.4.1.3715.17.5.3.1.2
		ifDirection OBJECT-TYPE
			SYNTAX INTEGER
				{
				input(1),
				output(2),
				both(3)
				}
			MAX-ACCESS not-accessible
			STATUS current
			DESCRIPTION
				"Interface data direction"
			::= { ifStatusEntry 2 }

		
		-- 1.3.6.1.4.1.3715.17.5.3.1.4097
		ifSignalStatus OBJECT-TYPE
			SYNTAX INTEGER
				{
				signalOk(1),
				signalMissing(2)
				}
			MAX-ACCESS read-only
			STATUS current
			DESCRIPTION
				"Interface signal status"
			::= { ifStatusEntry 4097 }

		
		-- 1.3.6.1.4.1.3715.17.5.3.1.4102
		ifAsiLinkStatus OBJECT-TYPE
			SYNTAX INTEGER
				{
				linkOk(1),
				linkDown(2)
				}
			MAX-ACCESS read-only
			STATUS current
			DESCRIPTION
				"ASI link status"
			::= { ifStatusEntry 4102 }

		
		-- 1.3.6.1.4.1.3715.17.5.3.1.4226
		ifLinkStatus OBJECT-TYPE
			SYNTAX INTEGER
				{
				linkOk(1),
				linkDown(2)
				}
			MAX-ACCESS read-only
			STATUS current
			DESCRIPTION
				"Interface link status"
			::= { ifStatusEntry 4226 }

		
		
		
		-- 1.3.6.1.4.1.3715.17.5.4
		tsStatusTable OBJECT-TYPE
			SYNTAX SEQUENCE OF TsStatusEntry
			MAX-ACCESS not-accessible
			STATUS current
			DESCRIPTION			" "
			::= { statusFlags 4 }

		
		-- 1.3.6.1.4.1.3715.17.5.4.1
		tsStatusEntry OBJECT-TYPE
			SYNTAX TsStatusEntry
			MAX-ACCESS not-accessible
			STATUS current
			DESCRIPTION			" "
			INDEX { moduleId, ifDirection, ifId }
			::= { tsStatusTable 1 }

		
		TsStatusEntry ::=
			SEQUENCE { 
				tsPidRemappingStatus
					INTEGER,
				tsManualTableInsertStatus
					INTEGER,
				tsPassthruDupStatus
					INTEGER,
				tsSyncStatus
					INTEGER,
				tsRxStatus
					INTEGER,
				tsInputBufferStatus
					INTEGER,
				tsNetworkStatus
					INTEGER,
				tsPsisiCapaStatus
					INTEGER,
				tsMultiplexDiscardStatus
					INTEGER,
				tsMultiplexDelayStatus
					INTEGER,
				tsCbrOversubscriptionStatus
					INTEGER,
				tsCbrDiscardStatus
					INTEGER,
				tsIpInputCapaStatus
					INTEGER,
				tsEitReinsertCapaStatus
					INTEGER,
				tsSectionCapaStatus
					INTEGER,
				tsRtpInputStatus
					INTEGER,
				tsRtpSeqStatus
					INTEGER,
				tsTdtTotGenStatus
					INTEGER,
				tsSttGenStatus
					INTEGER,
				tsFecPacketCorrectionStatus
					INTEGER, 
				tsFecInputAnomalyStatus
					INTEGER,
				tsFecCorrectionCapacityStatus
					INTEGER,
				tsIpMirrorOutputPacketLossStatus
					INTEGER
			 }

		-- 1.3.6.1.4.1.3715.17.5.4.1.5
		tsPidRemappingStatus OBJECT-TYPE
			SYNTAX INTEGER
				{
				pidNominal(1),
				pidRemapped(2)
				}
			MAX-ACCESS read-only
			STATUS current
			DESCRIPTION
				"TS PID remapping status"
			::= { tsStatusEntry 5 }

		
		-- 1.3.6.1.4.1.3715.17.5.4.1.8
		tsManualTableInsertStatus OBJECT-TYPE
			SYNTAX INTEGER
				{
				insertOk(1),
				insertFailure(2)
				}
			MAX-ACCESS read-only
			STATUS current
			DESCRIPTION
				"TS manual table insertion status"
			::= { tsStatusEntry 8 }

		
		-- 1.3.6.1.4.1.3715.17.5.4.1.11
		tsPassthruDupStatus OBJECT-TYPE
			SYNTAX INTEGER
				{
				servicesNominal(1),
				servicesBlocked(2)
				}
			MAX-ACCESS read-only
			STATUS current
			DESCRIPTION
				"TS output service passthrough duplication status"
			::= { tsStatusEntry 11 }

		
		-- 1.3.6.1.4.1.3715.17.5.4.1.4098
		tsSyncStatus OBJECT-TYPE
			SYNTAX INTEGER
				{
				syncOk(1),
				noSync(2)
				}
			MAX-ACCESS read-only
			STATUS current
			DESCRIPTION
				"TS sync status"
			::= { tsStatusEntry 4098 }

		
		-- 1.3.6.1.4.1.3715.17.5.4.1.4099
		tsRxStatus OBJECT-TYPE
			SYNTAX INTEGER
				{
				rxNominal(1),
				rxErrors(2)
				}
			MAX-ACCESS read-only
			STATUS current
			DESCRIPTION
				"TS Rx error status"
			::= { tsStatusEntry 4099 }

		
		-- 1.3.6.1.4.1.3715.17.5.4.1.4100
		tsInputBufferStatus OBJECT-TYPE
			SYNTAX INTEGER
				{
				bufferNominal(1),
				bufferOverflow(2)
				}
			MAX-ACCESS read-only
			STATUS current
			DESCRIPTION
				"TS input buffer status"
			::= { tsStatusEntry 4100 }

		
		-- 1.3.6.1.4.1.3715.17.5.4.1.4103
		tsNetworkStatus OBJECT-TYPE
			SYNTAX INTEGER
				{
				netOk(1),
				netForbidden(2)
				}
			MAX-ACCESS read-only
			STATUS current
			DESCRIPTION
				"TS network ID status"
			::= { tsStatusEntry 4103 }

		
		-- 1.3.6.1.4.1.3715.17.5.4.1.4109
		tsPsisiCapaStatus OBJECT-TYPE
			SYNTAX INTEGER
				{
				capacityNominal(1),
				capacityExceeded(2)
				}
			MAX-ACCESS read-only
			STATUS current
			DESCRIPTION
				"TS PSI/SI insertion capacity status"
			::= { tsStatusEntry 4109 }

		
		-- 1.3.6.1.4.1.3715.17.5.4.1.4110
		tsMultiplexDiscardStatus OBJECT-TYPE
			SYNTAX INTEGER
				{
				muxNominal(1),
				muxPacketsDiscarded(2)
				}
			MAX-ACCESS read-only
			STATUS current
			DESCRIPTION
				"TS multiplex packet discard status"
			::= { tsStatusEntry 4110 }

		
		-- 1.3.6.1.4.1.3715.17.5.4.1.4228
		tsMultiplexDelayStatus OBJECT-TYPE
			SYNTAX INTEGER
				{
				muxNominal(1),
				muxPacketsDelayed(2)
				}
			MAX-ACCESS read-only
			STATUS current
			DESCRIPTION
				"TS multiplex packet delay status"
			::= { tsStatusEntry 4228 }

		
		-- 1.3.6.1.4.1.3715.17.5.4.1.4229
		tsCbrOversubscriptionStatus OBJECT-TYPE
			SYNTAX INTEGER
				{
				cbrNominal(1),
				cbrOversubscription(2)
				}
			MAX-ACCESS read-only
			STATUS current
			DESCRIPTION
				"TS CBR oversubscription status"
			::= { tsStatusEntry 4229 }

		
		-- 1.3.6.1.4.1.3715.17.5.4.1.4236
		tsCbrDiscardStatus OBJECT-TYPE
			SYNTAX INTEGER
				{
				cbrNominal(1),
				cbrPacketsDiscarded(2)
				}
			MAX-ACCESS read-only
			STATUS current
			DESCRIPTION
				"TS CBR packet discard due to oversubscription status"
			::= { tsStatusEntry 4236 }

		
		-- 1.3.6.1.4.1.3715.17.5.4.1.4238
		tsIpInputCapaStatus OBJECT-TYPE
			SYNTAX INTEGER
				{
				capacityNominal(1),
				capacityExceeded(2)
				}
			MAX-ACCESS read-only
			STATUS current
			DESCRIPTION
				"TS IP input capacity status"
			::= { tsStatusEntry 4238 }

		
		-- 1.3.6.1.4.1.3715.17.5.4.1.4239
		tsEitReinsertCapaStatus OBJECT-TYPE
			SYNTAX INTEGER
				{
				capacityNominal(1),
				capacityExceeded(2)
				}
			MAX-ACCESS read-only
			STATUS current
			DESCRIPTION
				"TS EIT reinsert capacity status"
			::= { tsStatusEntry 4239 }

		
		-- 1.3.6.1.4.1.3715.17.5.4.1.4240
		tsSectionCapaStatus OBJECT-TYPE
			SYNTAX INTEGER
				{
				capacityNominal(1),
				capacityExceeded(2)
				}
			MAX-ACCESS read-only
			STATUS current
			DESCRIPTION
				"TS section processing capacity status"
			::= { tsStatusEntry 4240 }

		
		-- 1.3.6.1.4.1.3715.17.5.4.1.4241
		tsRtpInputStatus OBJECT-TYPE
			SYNTAX INTEGER
				{
				inputOk(1),
				inputPacketsDropped(2)
				}
			MAX-ACCESS read-only
			STATUS current
			DESCRIPTION
				"TS RTP input packet droip status"
			::= { tsStatusEntry 4241 }

		
		-- 1.3.6.1.4.1.3715.17.5.4.1.4242
		tsRtpSeqStatus OBJECT-TYPE
			SYNTAX INTEGER
				{
				seqOk(1),
				seqAnomalies(2)
				}
			MAX-ACCESS read-only
			STATUS current
			DESCRIPTION
				"TS RTP input packet sequence anomaly status"
			::= { tsStatusEntry 4242 }

		
		-- 1.3.6.1.4.1.3715.17.5.4.1.4246
		tsTdtTotGenStatus OBJECT-TYPE
			SYNTAX INTEGER
				{
				tdtTotOk(1),
				tdtTotNotGenerated(2)
				}
			MAX-ACCESS read-only
			STATUS current
			DESCRIPTION
				"TS output TDT/TOT table generation status"
			::= { tsStatusEntry 4246 }

		
		-- 1.3.6.1.4.1.3715.17.5.4.1.4261
		tsSttGenStatus OBJECT-TYPE
			SYNTAX INTEGER
				{
				sttOk(1),
				sttNotGenerated(2)
				}
			MAX-ACCESS read-only
			STATUS current
			DESCRIPTION
				"TS output STT table generation status"
			::= { tsStatusEntry 4261 }


		-- 1.3.6.1.4.1.3715.17.5.4.1.4266
		tsFecPacketCorrectionStatus OBJECT-TYPE 
			SYNTAX INTEGER
				{
				packetsNominal(1),
				fecCorrectedPackets(2)
				}
			MAX-ACCESS read-only
			STATUS current
			DESCRIPTION
				"Status flag for FEC correcting packets"
			::= { tsStatusEntry 4266 }


		-- 1.3.6.1.4.1.3715.17.5.4.1.4267
		tsFecInputAnomalyStatus OBJECT-TYPE
			SYNTAX INTEGER
				{
				fecInputNominal(1),
				fecInputAnomalies(2)
				}
			MAX-ACCESS read-only
			STATUS current
			DESCRIPTION
				"Status flag for FEC input anomaly detection"
			::= { tsStatusEntry 4267 }


		-- 1.3.6.1.4.1.3715.17.5.4.1.4268
		tsFecCorrectionCapacityStatus OBJECT-TYPE
			SYNTAX INTEGER
				{
				correctionCapacityNominal(1),
				correctionCapacityExceeded(2)
				}
			MAX-ACCESS read-only
			STATUS current
			DESCRIPTION
				"Fec input packets correction capacity status"
			::= { tsStatusEntry 4268 }


		-- 1.3.6.1.4.1.3715.17.5.4.1.4297
		tsIpMirrorOutputPacketLossStatus OBJECT-TYPE
			SYNTAX INTEGER
				{
				ipOutputNominal(1),
				ipOutputPacketsDiscarded(2)
				}
			MAX-ACCESS read-only
			STATUS current
			DESCRIPTION
				"Status flag for IP mirror output packet discarding"
			::= { tsStatusEntry 4297 }


		
		-- 1.3.6.1.4.1.3715.17.5.5
		serviceStatusTable OBJECT-TYPE
			SYNTAX SEQUENCE OF ServiceStatusEntry
			MAX-ACCESS not-accessible
			STATUS current
			DESCRIPTION			" "
			::= { statusFlags 5 }

		
		-- 1.3.6.1.4.1.3715.17.5.5.1
		serviceStatusEntry OBJECT-TYPE
			SYNTAX ServiceStatusEntry
			MAX-ACCESS not-accessible
			STATUS current
			DESCRIPTION			" "
			INDEX { moduleId, ifDirection, ifId, serviceId }
			::= { serviceStatusTable 1 }

		
		ServiceStatusEntry ::=
			SEQUENCE {
				serviceId
					INTEGER,
				serviceStatus
					INTEGER
			 }

		-- 1.3.6.1.4.1.3715.17.5.5.1.1
		serviceId OBJECT-TYPE
			SYNTAX INTEGER
			MAX-ACCESS not-accessible
			STATUS current
			DESCRIPTION
				"Service identifier"
			::= { serviceStatusEntry 1 }

		
		-- 1.3.6.1.4.1.3715.17.5.5.1.3
		serviceStatus OBJECT-TYPE
			SYNTAX INTEGER
				{
				servicePresent(1),
				serviceMissing(2)
				}
			MAX-ACCESS read-only
			STATUS current
			DESCRIPTION
				"Service status"
			::= { serviceStatusEntry 3 }

		
		
		-- 1.3.6.1.4.1.3715.17.5.6
		pidStatusTable OBJECT-TYPE
			SYNTAX SEQUENCE OF PidStatusEntry
			MAX-ACCESS not-accessible
			STATUS current
			DESCRIPTION			" "
			::= { statusFlags 6 }

		
		-- 1.3.6.1.4.1.3715.17.5.6.1
		pidStatusEntry OBJECT-TYPE
			SYNTAX PidStatusEntry
			MAX-ACCESS not-accessible
			STATUS current
			DESCRIPTION			" "
			INDEX { moduleId, ifDirection, ifId, pId }
			::= { pidStatusTable 1 }

		
		PidStatusEntry ::=
			SEQUENCE { 
				pId
					INTEGER,
				pidStatus
					INTEGER
			 }

		-- 1.3.6.1.4.1.3715.17.5.6.1.1
		pId OBJECT-TYPE
			SYNTAX INTEGER (1..65535)
			MAX-ACCESS not-accessible
			STATUS current
			DESCRIPTION
				"Program Identifier"
			::= { pidStatusEntry 1 }

		
		-- 1.3.6.1.4.1.3715.17.5.6.1.2
		pidStatus OBJECT-TYPE
			SYNTAX INTEGER
				{
				pidPresent(1),
				pidMissing(2)
				}
			MAX-ACCESS read-only
			STATUS current
			DESCRIPTION
				"PID status"
			::= { pidStatusEntry 2 }

	END

--
-- TELESTE-LUMINATO-MIB.mib
--
