-- The AGENT-CAPABILITIES file for Velociraptor products

-- Our MIB compiler (smoc) is based on an earlier version of SMIC that
-- does not understand the NOTIFICATION-GROUP construct. Therefore, in
-- a few places below, names of notification groups are commented
-- out. The new SMICng compiler does parse them, so I haven't deleted
-- the references entirely.


XEDIA-VELOCIRAPTOR-PROF DEFINITIONS ::= BEGIN

IMPORTS
    MODULE-IDENTITY
        FROM SNMPv2-SMI
    DisplayString
        FROM SNMPv2-TC
    AGENT-CAPABILITIES
        FROM SNMPv2-CONF
    xediaProducts
        FROM XEDIA-REG
    snmpGroup, snmpCommunityGroup, snmpSetGroup, systemGroup
    --, snmpBasicNotificationsGroup
        FROM SNMPv2-MIB
    xsysAllGroup
        FROM XEDIA-SYSTEM-MIB
    ifGeneralInformationGroup, ifFixedLengthGroup,
    ifHCFixedLengthGroup, ifPacketGroup, ifHCPacketGroup,
    ifVHCPacketGroup, ifRcvAddressGroup, ifStackGroup2,
    ifCounterDiscontinuityGroup  
        FROM IF-MIB
    ds3NearEndConfigGroup, ds3NearEndStatisticsGroup,
    ds3FarEndGroup, ds3NearEndOptionalConfigGroup      
        FROM DS3-MIB
    etherStats100MbsGroup, etherCollisionTableGroup
        FROM EtherLike-MIB
    frPortGroup, frCircuitGroup, frErrGroup, frTrapGroup
        FROM FRAME-RELAY-DTE-MIB
    ipGroup, icmpGroup
        FROM IP-MIB
    tcpGroup
        FROM TCP-MIB
    udpGroup
        FROM UDP-MIB
    ipRouteTable
        FROM RFC1213-MIB
--    ospf 
--        FROM RFC1253-MIB
    ospfBasicGroup, ospfAreaGroup, ospfStubAreaGroup, ospfIfGroup,
    ospfIfMetricGroup, ospfVirtIfGroup, ospfNbrGroup, ospfVirtNbrGroup,
    ospfAreaAggregateGroup
        FROM OSPF-MIB
--    rip2
--        FROM RFC1389-MIB
    rip2GlobalGroup, rip2IfStatGroup, rip2IfConfGroup, rip2PeerGroup
        FROM RIPv2-MIB
    xtmClassGroup
        FROM XEDIA-TRAFFIC-MGMT-MIB
    usrHistoryGroup
        FROM RMON2-MIB
    agentConfigGeneralGroup
        FROM XEDIA-MIB
    xdot3Group
        FROM XEDIA-ETHERNET-MIB
    ;

xediaVelociraptor MODULE-IDENTITY
    LAST-UPDATED "9701142155Z" -- January 14, 1997
    ORGANIZATION "Xedia Corp."
    CONTACT-INFO
        "support@xedia.com"
    DESCRIPTION
        "This module defines the 'agent implementation profile' for
        the Velociraptor product. In other words, it describes exactly
        what parts of what MIBs are implemented for each product
        release."
    ::= { xediaProducts 1 }

xediaVelociraptorMaj1    OBJECT IDENTIFIER ::= { xediaVelociraptor 1 }
xediaVelociraptorMin0    OBJECT IDENTIFIER ::= { xediaVelociraptorMaj1 0 }

-- The source documents shown below in comments were the versions used
-- when the product was shipped. Newer versions of these MIBs should
-- be backwardly compatible with these. The filename is how it is
-- stored in our source control system under $CVSROOT/xedia/snmp/mibs
-- or $CVSROOT/xedia/snmp/mibs/standard.

-- The information below for the Velociraptor V1.0.0 can be summarized as:

-- Feature                    Source Document                      Filename
-- ==========================================================================
-- System, SNMP               RFC1907(*)                           rfc1907
-- Xedia System               n/a                                  xsys    
-- Interfaces (&stacking)     draft-ietf-ifmib-mib-05(*)           ifmib    
-- T3                         draft-ietf-trunkmib-ds3-mib-04       ds3    
-- Xedia t3/ds3               xds3                                 xds3   
-- Ethernet                   draft-ietf-hubmib-etherif-mib-01     etherif
-- Xedia Ethernet             n/a                                  xeth
-- Frame Relay                RFC1315                              frdte
-- IP                         RFC2011(*)                           ipmib
-- TCP                        RFC2012(*)                           tcpmib  
-- UDP                        RFC2013(*)                           udpmib 
-- Routing Table              RFC1213 (MIB-II*)                    rfc1213
-- OSPFv2                     RFC1253(***)                         ospfv2    
-- RIPv2                      RFC1389(***)                         ripv2    
-- Xedia Traffic Mgmt         n/a                                  xtm    
-- Xedia Community-based SNMP n/a                                  xsnmpc    
-- Xedia Security             n/a                                  xsecurity
-- PPP  Link Control Prot     RFC1471                              rfc1471
-- PPP  IP Net Control Prot   RFC1473                              rfc1473
-- BGP4 Mib (standard)        RFC1657                              rfc1657
-- Xedia BGP4 (extensions)    xbgp                                 xbgp
-- Xedia Route Policy         xpolicy                              xpolicy
-- Xedia Command Scheduler    xcron                                xcron
-- DNS Server Mib             rfc1611                              rfc1611 
-- DNS Resolver Mib           rfc1612                              rfc1612 
-- ATM Mib                    rfc1695                              rfc1695
-- Xedia ATM Mib              xatm                                 xatm
-- ATM Textual Conventions    atmtc                                atmtc
-- ATM IP-over-ATM Mib        ipoa                                 ipoa
-- Xedia Authentication Mib   xauth                                xauth
-- Xedia Radius Mib           xradius                              xradius
-- Radius Authentication(std) draft-ietf-radius-auth-clientmib-01  radiusc_auth
-- Radius Accounting(std)     draft-ietf-radius-acc-clientmib-01   radiusc_actg
-- L2TP                       draft-ietf-pppext-l2tp-mib-03        l2tp.mi2
-- T1                         rfc1406                              ds1
-- Xedia t1/ds1               xds1                                 xds1   

-- (*) Collectively, these make us compatible with RFC1213, MIB-II
-- (***) The OSPF and RIP MIBs supported by ISI/Phase2 are not the
--       most recent RFCs. 

xediaVelociraptorV010000 AGENT-CAPABILITIES
    PRODUCT-RELEASE
        "Xedia Velociraptor V1.0.0"
    STATUS      current
    DESCRIPTION
        "Information about the SNMP MIBs supported by the initial
        release of the Xedia Velociraptor product."

    SUPPORTS SNMPv2-MIB 
        INCLUDES { snmpGroup, snmpCommunityGroup, snmpSetGroup, 
                    systemGroup } -- , snmpBasicNotificationsGroup }

    SUPPORTS XEDIA-SYSTEM-MIB 
        INCLUDES { xsysAllGroup }

    SUPPORTS IF-MIB 
        INCLUDES { ifGeneralInformationGroup, ifFixedLengthGroup,
                    ifHCFixedLengthGroup, ifPacketGroup, ifHCPacketGroup,
                    ifVHCPacketGroup, ifRcvAddressGroup, ifStackGroup2,
                    ifCounterDiscontinuityGroup }

    SUPPORTS DS3-MIB
        INCLUDES { ds3NearEndConfigGroup, ds3NearEndStatisticsGroup,
                    ds3FarEndGroup, ds3NearEndOptionalConfigGroup }

    SUPPORTS EtherLike-MIB
        INCLUDES { etherStats100MbsGroup, etherCollisionTableGroup }

    SUPPORTS FRAME-RELAY-DTE-MIB
        INCLUDES { frPortGroup, frCircuitGroup, frErrGroup, frTrapGroup }

    SUPPORTS IP-MIB 
        INCLUDES { ipGroup, icmpGroup }

    SUPPORTS TCP-MIB 
        INCLUDES { tcpGroup }

    SUPPORTS UDP-MIB 
        INCLUDES { udpGroup }

    SUPPORTS RFC1213-MIB
        INCLUDES { ipRouteTable }

        VARIATION ipRouteDest
            ACCESS read-only
            DESCRIPTION
                "The route table is read-only (use the
                xipStaticRouteTable to add static routes.)"

        VARIATION ipRouteIfIndex
            ACCESS read-only
            DESCRIPTION
                "The route table is read-only (use the
                xipStaticRouteTable to add static routes.)"

        VARIATION ipRouteMetric1
            ACCESS read-only
            DESCRIPTION
                "The route table is read-only (use the
                xipStaticRouteTable to add static routes.)"

        VARIATION ipRouteMetric2
            ACCESS read-only
            DESCRIPTION
                "The route table is read-only (use the
                xipStaticRouteTable to add static routes.)"

        VARIATION ipRouteMetric3
            ACCESS read-only
            DESCRIPTION
                "The route table is read-only (use the
                xipStaticRouteTable to add static routes.)"

        VARIATION ipRouteMetric4
            ACCESS read-only
            DESCRIPTION
                "The route table is read-only (use the
                xipStaticRouteTable to add static routes.)"

        VARIATION ipRouteNextHop
            ACCESS read-only
            DESCRIPTION
                "The route table is read-only (use the
                xipStaticRouteTable to add static routes.)"

        VARIATION ipRouteType
            ACCESS read-only
            DESCRIPTION
                "The route table is read-only (use the
                xipStaticRouteTable to add static routes.)"

        VARIATION ipRouteAge
            ACCESS read-only
            DESCRIPTION
                "The route table is read-only (use the
                xipStaticRouteTable to add static routes.)"

        VARIATION ipRouteMask
            ACCESS read-only
            DESCRIPTION
                "The route table is read-only (use the
                xipStaticRouteTable to add static routes.)"

        VARIATION ipRouteMetric5
            ACCESS read-only
            DESCRIPTION
                "The route table is read-only (use the
                xipStaticRouteTable to add static routes.)"

--    SUPPORTS RFC1253-MIB
--        INCLUDES { ospf }
    SUPPORTS OSPF-MIB
        INCLUDES { ospfBasicGroup, ospfAreaGroup, ospfStubAreaGroup, 
                    ospfIfGroup, ospfIfMetricGroup, ospfVirtIfGroup, 
                    ospfNbrGroup, ospfVirtNbrGroup, ospfAreaAggregateGroup }

--    SUPPORTS RFC1389-MIB
--        INCLUDES { rip2 }
    SUPPORTS RIPv2-MIB
          INCLUDES { rip2GlobalGroup, rip2IfStatGroup, rip2IfConfGroup, 
                        rip2PeerGroup }

    SUPPORTS XEDIA-TRAFFIC-MGMT-MIB
        INCLUDES { xtmClassGroup }

    SUPPORTS XEDIA-MIB
        INCLUDES { agentConfigGeneralGroup }

        VARIATION configPassword
            SYNTAX  DisplayString (SIZE (0..32))
            DESCRIPTION
                "In the Velociraptor, we limit the size of a community
                string to 32 characters to save space in NVRAM."

        VARIATION communityName
            SYNTAX  DisplayString (SIZE (0..32))
            DESCRIPTION
                "In the Velociraptor, we limit the size of a community
                string to 32 characters to save space in NVRAM."

        VARIATION communityViewName
            SYNTAX  DisplayString (SIZE (0..32))
            DESCRIPTION
                "In the Velociraptor, we limit the size of a community
                string to 32 characters to save space in NVRAM."

        VARIATION trapCommunity
            SYNTAX  DisplayString (SIZE (0..32))
            DESCRIPTION
                "In the Velociraptor, we limit the size of a community
                string to 32 characters to save space in NVRAM."

    SUPPORTS XEDIA-ETHERNET-MIB
        INCLUDES { xdot3Group }

    ::= { xediaVelociraptorMin0 0 }
    -- this will give the sysObjectId 1.3.6.1.4.1.838.5.1.1.0.0 or
    -- ...xedia.xediaProducts.xediaVelociraptor.xediaVelociraptorMaj1.
    -- xediaVelociraptorMin0.xediaVelociraptorUpdate0

-- Additional releases of the Velociraptor would be defined here

END
