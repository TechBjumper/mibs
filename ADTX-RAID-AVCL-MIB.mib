-- ADTX's AVC (ADTX Virtual Console) for the RAID Subsystem L Series
-- Author: Jerrell Jay Arreza
-- Date: January, 2003

ADTX-RAID-AVCL-MIB DEFINITIONS ::= BEGIN

IMPORTS
	Counter			FROM RFC1155-SMI
	OBJECT-TYPE			FROM RFC-1212
	adtxProducts, adtx	FROM ADTX-SMI
	DisplayString		FROM RFC1213-MIB
	TRAP-TYPE			FROM RFC-1215
;

-- textual conventions
AvcString		::= DisplayString
	-- DisplayString is OCTET STRING (SIZE(0..255))
AvcLongString	::= OCTET STRING
	-- OCTET STRING has a range of 0 to 65535 octets or bytes
AvcCounter		::= Counter
AvcInteger		::= INTEGER


-- Node for the AVC Products' of ADTX
avc                  OBJECT IDENTIFIER ::= { adtxProducts 1 }

-- AVC node for ADTX RAID Subsystem L Series. This is used for AVC-L Daemon implementation.
avcl                 OBJECT IDENTIFIER ::= { avc 1 }


avclVersion  OBJECT-TYPE
	SYNTAX     AvcString
	ACCESS     read-only
	STATUS     mandatory
	DESCRIPTION
		"The software version of AVC-L basing on the Daemon as the data
		gathered is based on it.
		eg. '4.0'"
	::= { avcl 1 }

avclOS  OBJECT-TYPE
	SYNTAX     AvcString
	ACCESS     read-only
	STATUS     mandatory
	DESCRIPTION
		"The Operating System of where the AVC-L Daemon resides.
		eg. 'Windows 2000 (Service Pack 3)'"
	::= { avcl 2 }

avclHost  OBJECT-TYPE
	SYNTAX     AvcString
	ACCESS     read-only
	STATUS     mandatory
	DESCRIPTION
		"The IP address or hostname of the system where the AVC-L daemon resides.
		eg. '172.16.16.204'"
	::= { avcl 3 }

avclNumOfDevices  OBJECT-TYPE
	SYNTAX     AvcCounter
	ACCESS     read-only
	STATUS     mandatory
	DESCRIPTION
		"The number of L devices that the AVC-L Daemon is currently connected.
		eg. 2"
	::= { avcl 4 }

avclEventInfo  OBJECT-TYPE
	SYNTAX     AvcLongString
	ACCESS     read-only
	STATUS     mandatory
	DESCRIPTION
		"This object will show the most recently sent 'critical' event or trap.
		Events/Traps can be sent by the AVC-L Daemon if SNMP notification is enabled
		in the Daemon's configuration file. This file can be configured thru the
		AVC-L Client. Value can be one of the following phrases:
		'xxx  Serial Number: yyy ADTX ArrayMasStor IP zzz device not accessible.'
			- this means that the device is disconnected, accidental or otherwise,
			  and needs to be reconnected.
		'xxx  Serial Number: yyy IP zzz  Array nn: sss ==> Exposed.'
		'xxx  Serial Number: yyy IP zzz  Array nn: sss ==> Invalidated Protected Space.'
			- where:
				nn - array number
				sss - any status other than either 'Exposed' or 'Invalidated Protected Space'
			This means that the array's status changed to fail. Contact support.
		'xxx  Serial Number: yyy IP zzz  Array nn  Lun mm: sss ==> Data Lost.'
		'xxx  Serial Number: yyy IP zzz  Array nn  Lun mm: sss ==> Exposed.'
			- where:
				nn - array number
				mm - lun number
				sss - any status other than either 'Data Lost' or 'Exposed'
			This means that the lun's status changed to fail. Contact support.
		'xxx  Serial Number: yyy IP zzz  Spare ll: sss ==> Failed.'
		'xxx  Serial Number: yyy IP zzz  Spare ll: sss ==> Offline.'
		'xxx  Serial Number: yyy IP zzz  Spare ll: sss ==> Missing.'
		'xxx  Serial Number: yyy IP zzz  Spare ll: sss ==> Blank.'
			- where:
				ll - spare number
				sss - any status other than either 'Failed', 'Offline', 'Missing', or 'Blank'
			This means that the spare's status changed to fail. Contact support.
		'xxx  Serial Number: yyy IP zzz  Disk kk: sss ==> Failed.'
		'xxx  Serial Number: yyy IP zzz  Disk kk: sss ==> Offline.'
		'xxx  Serial Number: yyy IP zzz  Disk kk: sss ==> Missing.'
		'xxx  Serial Number: yyy IP zzz  Disk kk: sss ==> Blank.'
			- where:
				kk - disk/hdd number
				sss - any status other than either 'Failed', 'Offline', 'Missing', or 'Blank'
			This means that the disk's status changed to fail. Contact support.
		'xxx  Serial Number: yyy IP zzz  Component jj: sss ==> Broken.'
		'xxx  Serial Number: yyy IP zzz  Component jj: sss ==> Not Available.'
			- where:
				jj - disk/hdd number
				sss - any status other than either 'Broken' or 'Not Available'
			This means that the component's status changed to fail. Contact support.
		'xxx  Serial Number: yyy (ArrayMasStor) IP zzz Instant Copy LU ii to LU hh: abnormally ended.'
		'xxx  Serial Number: yyy (ArrayMasStor) IP zzz Instant Copy LU ii to LU hh: terminated due to power off.'
		'xxx  Serial Number: yyy (ArrayMasStor) IP zzz Instant Copy LU ii to LU hh: source size greater than destination.'
		'xxx  Serial Number: yyy (ArrayMasStor) IP zzz Instant Copy LU ii to LU hh: actual source size is lesser than specified size.'
			- where:
				ii - source lun
				hh - target lun
			This means that the instant copy failed and the data on target lun may be 
			corrupted. Contact support.

		where:
			xxx - 'avcdaemon' or 'AVC Monitor Daemon - WinNT'
			yyy - serial number of the device concerned, eg. 'S000023'
			zzz - the IP address of the device concerned, eg. '172.16.16.190'
		The above event values are only for the critical events. There are other events that
		are more for informational purposes only.
		"
	::= { avcl 5 }

avclDeviceInformationTable  OBJECT-TYPE
	SYNTAX SEQUENCE OF AvclDeviceInformationEntry
	ACCESS     not-accessible
	STATUS     mandatory
	DESCRIPTION
		"This group (table) provides information about the L devices that are
		currently connected to the AVC-L Daemon"
	::= { avcl 6 }

avclDeviceInformationEntry  OBJECT-TYPE
	SYNTAX 	AvclDeviceInformationEntry
	ACCESS     not-accessible
	STATUS     mandatory
	DESCRIPTION
		""
	INDEX { avclDeviceIndex }
	::= { avclDeviceInformationTable 1 }

AvclDeviceInformationEntry ::= SEQUENCE {
	avclDeviceIndex					AvcCounter,
	avclDeviceIP					AvcString,
	avclDeviceSystemVersion				AvcString,
	avclDeviceManufacturer				AvcString,
	avclDeviceProductName				AvcString,
	avclDeviceRevisionLevel				AvcString,
	avclDeviceSerialNumber				AvcString,
	avclDeviceDate					AvcString,
	avclDeviceTime					AvcString,
	avclDeviceAssignedSpare				AvcString,
	avclDeviceInitiatorMode				AvcString,
	avclDeviceInstantCopyLicense		AvcString,
	avclDeviceMirroringLicense			AvcString,
	avclDeviceWWNInfoCount				AvcCounter,
	avclDeviceWWNInfo					AvcString,
	avclDeviceSurfaceSchedMode			AvcLongString,
	avclDeviceSurfaceSchedTime			AvcString,
	avclDeviceSurfaceVerifyDuration		AvcCounter,
	avclDeviceICSourceLU				AvcInteger,
	avclDeviceICTargetLU				AvcInteger,
	avclDeviceICFlag					AvcString,
	avclDeviceICProgress				AvcCounter,
	avclDeviceICPairWWN				AvcString,
	avclDeviceRegHostCount				AvcCounter,
	avclDeviceRegHosts				AvcLongString,
	avclDeviceLuToMirrorCount			AvcCounter,
	avclDeviceLunsToMirror				AvcLongString,
	avclDeviceRaidGrpCount				AvcCounter,
	avclDeviceRaidGrpsState				AvcLongString,
	avclDeviceRaidGrpsDriveCount			AvcLongString,
	avclDeviceRaidGrpsSize				AvcLongString,
	avclDeviceRaidGrpsLuUnderSurfaceVerify	AvcLongString,
	avclDeviceRaidGrpsSurfaceVerifyProgress	AvcLongString,
	avclDeviceRaidGrpsInitReconProgress		AvcLongString,
	avclDeviceRaidGrpsFreeSpace			AvcLongString,
	avclDeviceSpareCount				AvcCounter,
	avclDeviceSparesState				AvcLongString,
	avclDeviceSparesRaidGrpNumber			AvcLongString,
	avclDeviceVolumeCount				AvcCounter,
	avclDeviceVolumesState				AvcLongString,
	avclDeviceVolumesRaidGrpNumber		AvcLongString,
	avclDeviceVolumesRaidLevel			AvcLongString,
	avclDeviceVolumesSize				AvcLongString,
	avclDeviceVolumesInitProgress			AvcLongString,
	avclDeviceVolumesNickname			AvcLongString,
	avclDeviceDriveCount				AvcCounter,
	avclDeviceDrivesState				AvcLongString,
	avclDeviceDrivesUsageType			AvcLongString,
	avclDeviceDrivesRaidGrpOrSpareNumber	AvcLongString,
	avclDeviceComponentCount			AvcCounter,
	avclDeviceComponentsType			AvcLongString,
	avclDeviceComponentsState			AvcLongString,
	avclDeviceComponentsInstanceNumber		AvcLongString
	}

avclDeviceIndex  OBJECT-TYPE
	SYNTAX     AvcCounter
	ACCESS     read-only
	STATUS     mandatory
	DESCRIPTION
		"The index number of the L Device pertaining to this table.
		eg. 1"
	::= { avclDeviceInformationEntry 1 }

avclDeviceIP  OBJECT-TYPE
	SYNTAX     AvcString
	ACCESS     read-only
	STATUS     mandatory
	DESCRIPTION
		"IP address of the specific L device queried
		eg. '172.16.16.190'"
	::= { avclDeviceInformationEntry 2 }

avclDeviceSystemVersion  OBJECT-TYPE
	SYNTAX     AvcString
	ACCESS     read-only
	STATUS     mandatory
	DESCRIPTION
		"The device's subsystem version.
		eg. '7.2'"
	::= { avclDeviceInformationEntry 3 }

avclDeviceManufacturer  OBJECT-TYPE
	SYNTAX     AvcString
	ACCESS     read-only
	STATUS     mandatory
	DESCRIPTION
		"The device's manufacturer name from the Inquiry command info
		eg. 'ADTX'"
	::= { avclDeviceInformationEntry 4 }

avclDeviceProductName  OBJECT-TYPE
	SYNTAX     AvcString
	ACCESS     read-only
	STATUS     mandatory
	DESCRIPTION
		"The device's product name from the Inquiry command info
		eg. 'AXRR-L'"
	::= { avclDeviceInformationEntry 5 }

avclDeviceRevisionLevel  OBJECT-TYPE
	SYNTAX     AvcString
	ACCESS     read-only
	STATUS     mandatory
	DESCRIPTION
		"The revision level of the device controller's microcode/firmware from
		the Inquiry command info.
		eg. 'L25X'"
	::= { avclDeviceInformationEntry 6 }

avclDeviceSerialNumber  OBJECT-TYPE
	SYNTAX     AvcString
	ACCESS     read-only
	STATUS     mandatory
	DESCRIPTION
		"The device's serial number from the Inquiry command info.
		eg. 'S000023'"
	::= { avclDeviceInformationEntry 7 }

avclDeviceDate  OBJECT-TYPE
	SYNTAX     AvcString
	ACCESS     read-only
	STATUS     mandatory
	DESCRIPTION
		"The controller's system date of the L device.
		eg. 'Mar 7, 2003'"
	::= { avclDeviceInformationEntry 8 }

avclDeviceTime  OBJECT-TYPE
	SYNTAX     AvcString
	ACCESS     read-only
	STATUS     mandatory
	DESCRIPTION
		"The controller's system time of the L device, in 24-hr format.
		eg. '14:35'"
	::= { avclDeviceInformationEntry 9 }

avclDeviceAssignedSpare  OBJECT-TYPE
	SYNTAX     AvcString
	ACCESS     read-only
	STATUS     mandatory
	DESCRIPTION
		"The device's global spare assignment. Can be any of the ff.:
			- No Assigned Spare
			- HDD #
		eg. 'No Assigned Spare' or 'HDD 1' or 'HDD 2, HDD 6'"
	::= { avclDeviceInformationEntry 10 }
	
avclDeviceInitiatorMode  OBJECT-TYPE
	SYNTAX     AvcString
	ACCESS     read-only
	STATUS     mandatory
	DESCRIPTION
		"Shows if the device is in Initiator mode or not. Can be any of the ff.:
			- Enabled
			- Disabled
		eg. 'Disabled'"
	::= { avclDeviceInformationEntry 11 }
	
avclDeviceInstantCopyLicense  OBJECT-TYPE
	SYNTAX     AvcString
	ACCESS     read-only
	STATUS     mandatory
	DESCRIPTION
		"Shows the license description for device Instant Copy. Can be any of the ff.:
			- Permanent Instant Copy
			- Temporary Instant Copy (# of days remaining)
			- No License
		eg. 'No License'"
	::= { avclDeviceInformationEntry 12 }
	
avclDeviceMirroringLicense  OBJECT-TYPE
	SYNTAX     AvcString
	ACCESS     read-only
	STATUS     mandatory
	DESCRIPTION
		"Shows the license description for device Mirroring. Can be any of the ff.:
			- Permanent Mirroring
			- Temporary Mirroring (# of days remaining)
			- No License
		eg. 'Permanent Mirroring'"
	::= { avclDeviceInformationEntry 13 }

-- information about WWN (worldwide node)
avclDeviceWWNInfoCount  OBJECT-TYPE
	SYNTAX     AvcCounter
	ACCESS     read-only
	STATUS     mandatory
	DESCRIPTION
		"The count/number of WWN Information present in the device.
		eg. 1"
	::= { avclDeviceInformationEntry 14 }

avclDeviceWWNInfo  OBJECT-TYPE
	SYNTAX     AvcString
	ACCESS     read-only
	STATUS     mandatory
	DESCRIPTION
		"All WWN Information present in the device.
		First Controller WWN Information to be returned is that of Primary Controller, followed
		by Secondary Controller, and so on. F/O (Fail Over) Mode can be either 'Independent WWN'
		or 'Fail Over On Primary WWN'
		e.g. '50:03:07:A8:0A:00:01:13, F/O Mode: Independent WWN; 50:03:07:A8:0A:00:00:23, ....; ......'
		"
	::= { avclDeviceInformationEntry 15 }

-- information about Scheduled Surface Check
avclDeviceSurfaceSchedMode  OBJECT-TYPE
	SYNTAX     AvcLongString
	ACCESS     read-only
	STATUS     mandatory
	DESCRIPTION
	"The mode for the scheduled surface check. Can be one of the ff:
		Type:
			- No Surface Verify
			- Sequential Verify
			- Parity Check
			- Parity Re-Generation
		Frequency:
			- null or the value is the zero-length string
			- Now
			- Once A Day
			- Once A Week
			- Once A Month
			- Always
		e.g. 'Type: No Surface Verify; Frequency: ' or 'Type: Sequential Verify; Frequency: Once A Day'
		"
	::= { avclDeviceInformationEntry 16 }

avclDeviceSurfaceSchedTime  OBJECT-TYPE
	SYNTAX     AvcString
	ACCESS     read-only
	STATUS     mandatory
	DESCRIPTION
		"The time for the scheduled surface check. Can be any of the ff. description:
		- null or the value is the zero-length string if there is no surface check or if always surface check.
		- the time of the day if 'Once A Day'
		- the day of the week and the time if 'Once A Week'
		- the day of the month and the time if 'Once A Month
		eg. '14:15' if Once A Day, 'Wednesday, 14:15' if Once A Week, or '24, 14:15' if Once A Month"
	::= { avclDeviceInformationEntry 17 }

avclDeviceSurfaceVerifyDuration  OBJECT-TYPE
	SYNTAX     AvcCounter
	ACCESS     read-only
	STATUS     mandatory
	DESCRIPTION
		"The duration of the scheduled surface check, in minutes.
		eg. 30"
	::= { avclDeviceInformationEntry 18 }

-- information about Instant Copy feature
avclDeviceICSourceLU  OBJECT-TYPE
	SYNTAX     AvcInteger
	ACCESS     read-only
	STATUS     mandatory
	DESCRIPTION
		"The number of the source LU of the IC (Instant Copy) operation.
		eg. 1"
	::= { avclDeviceInformationEntry 19 }

avclDeviceICTargetLU  OBJECT-TYPE
	SYNTAX     AvcInteger
	ACCESS     read-only
	STATUS     mandatory
	DESCRIPTION
		"The number of the target LU of the Instant Copy operation.
		eg. 2"
	::= { avclDeviceInformationEntry 20 }

avclDeviceICFlag  OBJECT-TYPE
	SYNTAX     AvcString
	ACCESS     read-only
	STATUS     mandatory
	DESCRIPTION
		"This Instant Copy flag/status can be one of the ff.:
		- Stopped
		- Started
		- Copy to External Device
		- Copy From External Device
		- Instant Copy In Progress
		- Failed Due to Error
		- Cancelling Instant Copy
		"
	::= { avclDeviceInformationEntry 21 }

avclDeviceICProgress  OBJECT-TYPE
	SYNTAX     AvcCounter
	ACCESS     read-only
	STATUS     mandatory
	DESCRIPTION
		"This will contain the progress of the instant copy operation, in percent.
		eg. 99"
	::= { avclDeviceInformationEntry 22 }

avclDeviceICPairWWN  OBJECT-TYPE
	SYNTAX     AvcString
	ACCESS     read-only
	STATUS     mandatory
	DESCRIPTION
		"The worldwide node of the instant copy pair.
		eg. '50:03:07:A8:0A:00:01:13'"
	::= { avclDeviceInformationEntry 23 }

-- information about Registered Hosts
avclDeviceRegHostCount  OBJECT-TYPE
	SYNTAX     AvcCounter
	ACCESS     read-only
	STATUS     mandatory
	DESCRIPTION
		"The count of all registered hosts present in the device.
		eg. 2"
	::= { avclDeviceInformationEntry 24 }

avclDeviceRegHosts  OBJECT-TYPE
	SYNTAX     AvcLongString
	ACCESS     read-only
	STATUS     mandatory
	DESCRIPTION
		"Information of all registered hosts present in the device.
		Information includes:
		- Host x WWN, i.e. 50:03:07:A8:0A:00:01:13
		- L Port Number: 0 (for Fibre Channel Port 0) and 1 (for Fibre Channel Port 1)
		- Host x LU Conversion, i.e. LU 1 can be seen as LU 5 by this host and
		  LU 3 as LU1. Show only valid LU conversions out of the possible 32 conversions..
		e.g. '50:03:07:A8:0A:00:01:13, 0, LU1->LU5, LU3->LU1; 50:03:07:A8:0A:00:00:23, 0, LU0->LU2, LU1->LU4, LU5->LU6, ; ......'
		"
	::= { avclDeviceInformationEntry 25 }

-- information about Luns to mirror
avclDeviceLuToMirrorCount  OBJECT-TYPE
	SYNTAX     AvcCounter
	ACCESS     read-only
	STATUS     mandatory
	DESCRIPTION
		"The count of all LU's to mirror.
		eg. 3"
	::= { avclDeviceInformationEntry 26 }

avclDeviceLunsToMirror  OBJECT-TYPE
	SYNTAX     AvcLongString
	ACCESS     read-only
	STATUS     mandatory
	DESCRIPTION
		"Information of all Luns to mirror. Includes:
		- Source Lun
		- Target Lun
		- L Port Number: 0 (for FC port 0) or 1 (for FC port 1)
		- Target WWN
		e.g. 'LU1, LU3, 0, 50:03:07:A8:0A:00:01:13; LU2, LU4, 1, 50:03:07:A8:0A:00:00:23; ......'
		"
	::= { avclDeviceInformationEntry 27 }

-- information about RAID groups or arrays present in any device
avclDeviceRaidGrpCount  OBJECT-TYPE
	SYNTAX     AvcCounter
	ACCESS     read-only
	STATUS     mandatory
	DESCRIPTION
		"The count of all RAID groups or arrays configured in any device.
		eg. 2"
	::= { avclDeviceInformationEntry 28 }

avclDeviceRaidGrpsState  OBJECT-TYPE
	SYNTAX     AvcLongString
	ACCESS     read-only
	STATUS     mandatory
	DESCRIPTION
		"Contains the state of each raid group present in the device.
		Can be one of the following:
		- Normal mode
		- Degraded mode
		- Reconstruction mode
		- Retry mode
		- System is starting up
		- System shutdown
		- System is not configured
		- System halt
		e.g. 'Array 1: Normal mode; Array 2: System halt; ......'
		"
	::= { avclDeviceInformationEntry 29 }

avclDeviceRaidGrpsDriveCount  OBJECT-TYPE
	SYNTAX     AvcLongString
	ACCESS     read-only
	STATUS     mandatory
	DESCRIPTION
		"The number of drives included in each raid group.
		e.g. 'Array 1: 5; Array 2: 3; ......'
		"
	::= { avclDeviceInformationEntry 30 }

avclDeviceRaidGrpsSize  OBJECT-TYPE
	SYNTAX     AvcLongString
	ACCESS     read-only
	STATUS     mandatory
	DESCRIPTION
		"Contains the size of each raid group. Size is in units of KB.
		e.g. 'Array 1: 645,620,224; Array 2: 300,000,000; ......'
		"
	::= { avclDeviceInformationEntry 31 }

avclDeviceRaidGrpsLuUnderSurfaceVerify  OBJECT-TYPE
	SYNTAX     AvcLongString
	ACCESS     read-only
	STATUS     mandatory
	DESCRIPTION
		"Contains the volume or LU number of all raid groups that is currently
		undergoing surface verify. Display only the raid groups
		that are undergoing this feature. If no raid group is undergoing
		surface verify, this value is the zero-length string.
		e.g. 'Array 1: LU3; Array 3: LU11; ......'
		"
	::= { avclDeviceInformationEntry 32 }

avclDeviceRaidGrpsSurfaceVerifyProgress  OBJECT-TYPE
	SYNTAX     AvcLongString
	ACCESS     read-only
	STATUS     mandatory
	DESCRIPTION
		"Contains the progress, in percentage, of all raid groups undergoing
		surface verify. Display only the raid groups that are undergoing
		this feature. If no raid group is undergoing surface verify,
		this value is the zero-length string.
		e.g. 'Array 1: 10; Array 3: 98; ......'
		"
	::= { avclDeviceInformationEntry 33 }

avclDeviceRaidGrpsInitReconProgress  OBJECT-TYPE
	SYNTAX     AvcLongString
	ACCESS     read-only
	STATUS     mandatory
	DESCRIPTION
		"Contains the progress, in percentage, of the initialization or
		reconstruction for all raid groups undergoing such process.
		e.g. 'Array 1: 17; Array 3: 85; ......'
		"
	::= { avclDeviceInformationEntry 34 }

avclDeviceRaidGrpsFreeSpace  OBJECT-TYPE
	SYNTAX     AvcLongString
	ACCESS     read-only
	STATUS     mandatory
	DESCRIPTION
		"Contains the total free space of all raid groups, in units of KB.
		e.g. 'Array 1: 5,000,000; Array 2: 0; ......'
		"
	::= { avclDeviceInformationEntry 35 }

-- information about spare drives present in any device
avclDeviceSpareCount  OBJECT-TYPE
	SYNTAX     AvcCounter
	ACCESS     read-only
	STATUS     mandatory
	DESCRIPTION
		"The count of all spare drives in any device.
		eg. 1"
	::= { avclDeviceInformationEntry 36 }

avclDeviceSparesState  OBJECT-TYPE
	SYNTAX     AvcLongString
	ACCESS     read-only
	STATUS     mandatory
	DESCRIPTION
		"Contains the state of each spare drive present in the device.
		Can be one of the following:
		- On Line
		- Off Line
		- Not Configured
		- Working Properly
		- Failed or Not Attached
		- Under Reconstruction
		- Under Retry
		- Installed
		- Not Installed
		- Starting Up
		- Standing By
		- Power Supplied to the Drive
		- No Power Supplied
		- Drive is Reserved
		- Drive is Not Reserved
		e.g. 'Spare 1: Under Reconstruction; Spare 2: On Line; ......'
		"
	::= { avclDeviceInformationEntry 37 }

avclDeviceSparesRaidGrpNumber  OBJECT-TYPE
	SYNTAX     AvcLongString
	ACCESS     read-only
	STATUS     mandatory
	DESCRIPTION
		"Shows the raid group number to which the spare belongs.
		value is 'Global' if the spare is global or does not belong to
		any raid group.
		e.g. 'Spare 1: 3; Spare 2: Global; ......'
		"
	::= { avclDeviceInformationEntry 38 }

-- information about volumes or LU's present in any device
avclDeviceVolumeCount  OBJECT-TYPE
	SYNTAX     AvcCounter
	ACCESS     read-only
	STATUS     mandatory
	DESCRIPTION
		"The count of all volumes present in any device. Maximum number of
		volumes configurable is 32. Volume/LU number starts at 0.
		eg. 4"
	::= { avclDeviceInformationEntry 39 }

avclDeviceVolumesState  OBJECT-TYPE
	SYNTAX     AvcLongString
	ACCESS     read-only
	STATUS     mandatory
	DESCRIPTION
		"Contains the state of volumes present in the device.
		Can be one of the following:
		- Initialization Completed
		- Required
		- Initialization In Progress
		- LUN Failed
		- LUN Not Configured
		- Format Required
		- Format In Progress
		e.g. 'LU 1: LUN Failed; LU 2: Format Required; ......'
		"
	::= { avclDeviceInformationEntry 40 }

avclDeviceVolumesRaidGrpNumber  OBJECT-TYPE
	SYNTAX     AvcLongString
	ACCESS     read-only
	STATUS     mandatory
	DESCRIPTION
		"Shows the raid group number to which the volume belongs.
		e.g. 'LU 1: 2; LU 2: 2; LU 3: 1;......'
		"
	::= { avclDeviceInformationEntry 41 }

avclDeviceVolumesRaidLevel  OBJECT-TYPE
	SYNTAX     AvcLongString
	ACCESS     read-only
	STATUS     mandatory
	DESCRIPTION
		"Shows the raid level the volume is configured.
		Can be any of the following:
		  0 - RAID 0
		  1 - RAID 1
		  5 - RAID 5
		e.g. 'LU 1: 0; LU 2: 0; LU 3: 5;......'
		"
	::= { avclDeviceInformationEntry 42 }

avclDeviceVolumesSize  OBJECT-TYPE
	SYNTAX     AvcLongString
	ACCESS     read-only
	STATUS     mandatory
	DESCRIPTION
		"Shows the size of all volumes in the device, in units of KB.
		e.g. 'LU 1: 1,500,000; LU 2: 7,000,000; LU 3: 15,000,000;......'
		"
	::= { avclDeviceInformationEntry 43 }

avclDeviceVolumesInitProgress  OBJECT-TYPE
	SYNTAX     AvcLongString
	ACCESS     read-only
	STATUS     mandatory
	DESCRIPTION
		"Contains the progress, in percentage, of the initialization or
		reconstruction for all volumes undergoing such process.
		e.g. 'LU 1: 1; LU 2: 89; LU 3: 64;......'
		"
	::= { avclDeviceInformationEntry 44 }

avclDeviceVolumesNickname  OBJECT-TYPE
	SYNTAX     AvcLongString
	ACCESS     read-only
	STATUS     mandatory
	DESCRIPTION
		"Contains the nickname or mount point of each volume in a device.
		If no nickname, the value is the zero-length string.
		e.g. 'LU 1: /mnt/device/sda; LU 2: ; LU 3: /mnt/device/sdc;......'
		"
	::= { avclDeviceInformationEntry 45 }

-- information about drives present in any device
avclDeviceDriveCount  OBJECT-TYPE
	SYNTAX     AvcCounter
	ACCESS     read-only
	STATUS     mandatory
	DESCRIPTION
		"The count of all drives present in any device. Maximum number of
		drives is 15, but can be 30 if there is an expansion.
		eg. 15"
	::= { avclDeviceInformationEntry 46 }

avclDeviceDrivesState  OBJECT-TYPE
	SYNTAX     AvcLongString
	ACCESS     read-only
	STATUS     mandatory
	DESCRIPTION
		"Contains the state of the drives present in the device.
		Can be one of the following:
		- On Line
		- Off Line
		- Spare
		- Not Configured
		- Working Properly
		- Failed or Not Attached
		- Under Reconstruction
		- Under Retry
		- Installed
		- Not Installed
		- Starting Up
		- Standing By
		- Power Supplied to the Drive
		- No Power Supplied
		- Drive is Reserved
		- Drive is Not Reserved
		e.g. 'Drive 1: Spare; LU 2: Starting UP; ......'
		"
	::= { avclDeviceInformationEntry 47 }

avclDeviceDrivesUsageType  OBJECT-TYPE
	SYNTAX     AvcLongString
	ACCESS     read-only
	STATUS     mandatory
	DESCRIPTION
		"The usage type of the drive in the device.
		Can be one of the ff.:
		- In Array
		- Not Assigned
		- As Spare
		- HDD does not exist
		e.g. 'Drive 1: As Spare; Drive 2: Not Assigned; ......'
		"
	::= { avclDeviceInformationEntry 48 }

avclDeviceDrivesRaidGrpOrSpareNumber  OBJECT-TYPE
	SYNTAX     AvcLongString
	ACCESS     read-only
	STATUS     mandatory
	DESCRIPTION
		"The raid group or spare number this drive belongs.
		If this is 'Not Assigned' or 'HDD does not exist',
        the value is the zero-length string.
		e.g. 'Drive 1: Spare 2; Drive 2: Array 1; ......'
		"
	::= { avclDeviceInformationEntry 49 }

-- information about components present in any device
avclDeviceComponentCount  OBJECT-TYPE
	SYNTAX     AvcCounter
	ACCESS     read-only
	STATUS     mandatory
	DESCRIPTION
		"The count of all components present in any device.
		eg. 3"
	::= { avclDeviceInformationEntry 50 }

avclDeviceComponentsType  OBJECT-TYPE
	SYNTAX     AvcLongString
	ACCESS     read-only
	STATUS     mandatory
	DESCRIPTION
		"The usage type of the component in the device.
		Can be one of the ff.:
		- Power Supply
		- Fan
		e.g. 'Component 1: Power Supply; Component 2: Fan; ......'
		"
	::= { avclDeviceInformationEntry 51 }

avclDeviceComponentsState  OBJECT-TYPE
	SYNTAX     AvcLongString
	ACCESS     read-only
	STATUS     mandatory
	DESCRIPTION
		"Contains the state of the components present in the device.
		Can be one of the following:
		- Normal
		- Fail
		- Not Available
		e.g. 'Component 1: Normal; Component 2: Fail; ......'
		"
	::= { avclDeviceInformationEntry 52 }

avclDeviceComponentsInstanceNumber  OBJECT-TYPE
	SYNTAX     AvcLongString
	ACCESS     read-only
	STATUS     mandatory
	DESCRIPTION
		"The index number of each unique component device type.
		Format of values are:
			PS1 - Power Supply 1
			F2 - Fan 2
		e.g. 'Component 1: PS1; Component 2: F2; ......'
		"
	::= { avclDeviceInformationEntry 53 }

-- Trap for AVC-L. Only one trap type but with many values in the form of string of
-- characters
daemonEvent	TRAP-TYPE
	ENTERPRISE	adtx
	VARIABLES	{ avclEventInfo }
	DESCRIPTION
		"This trap is sent if SNMP notification is enabled for any or all of the
		critical (needs troubleshooting) events described at 'avclEventInfo' above.
		There are other events but are categorized as status-changed events that
		don't need troubleshooting, just for informational purposes."
	::= 1

END
