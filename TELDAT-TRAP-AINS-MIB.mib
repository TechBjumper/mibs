-- file automatically created


TELDAT-TRAP-AINS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ainsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the AINS event subsystem."
    REVISION "201401200930Z"
    DESCRIPTION "Initial implementation"
        ::= { telEventTraps 167 }


ainsEventsGroup	OBJECT IDENTIFIER	::= { ainsTrapsMIB 1 }

ainsNotifications	OBJECT IDENTIFIER	::= { ainsTrapsMIB 2 }
ainsNotificationsPrefix	OBJECT IDENTIFIER	::= { ainsNotifications 0 }

ainsEventObjects1 OBJECT-IDENTITY
    STATUS current
    DESCRIPTION
        "Event AINS.1
        The AutoInstall process is starting/resuming."
    ::= { ainsEventsGroup 1 }

ains1-AutoInstall-Mode OBJECT-TYPE
    SYNTAX DisplayString
    MAX-ACCESS accessible-for-notify
    STATUS current
    DESCRIPTION
        "Parameter 'AutoInstall Mode' in event AINS.1"
    ::= { ainsEventObjects1 1 }

ainsEventObjects3 OBJECT-IDENTITY
    STATUS current
    DESCRIPTION
        "Event AINS.3
        BOOTREQUEST sent on the specified interface."
    ::= { ainsEventsGroup 3 }

ains3-Interface OBJECT-TYPE
    SYNTAX DisplayString
    MAX-ACCESS accessible-for-notify
    STATUS current
    DESCRIPTION
        "Parameter 'Interface' in event AINS.3"
    ::= { ainsEventObjects3 1 }

ainsEventObjects4 OBJECT-IDENTITY
    STATUS current
    DESCRIPTION
        "Event AINS.4
        Received data in a BOOTREPLY."
    ::= { ainsEventsGroup 4 }

ains4-BOOTP-Data OBJECT-TYPE
    SYNTAX DisplayString
    MAX-ACCESS accessible-for-notify
    STATUS current
    DESCRIPTION
        "Parameter 'BOOTP Data' in event AINS.4"
    ::= { ainsEventObjects4 1 }

ainsEventObjects5 OBJECT-IDENTITY
    STATUS current
    DESCRIPTION
        "Event AINS.5
        The device is trying to download a file from a TFTP server."
    ::= { ainsEventsGroup 5 }

ains5-File OBJECT-TYPE
    SYNTAX DisplayString
    MAX-ACCESS accessible-for-notify
    STATUS current
    DESCRIPTION
        "Parameter 'File' in event AINS.5"
    ::= { ainsEventObjects5 1 }

ains5-TFTP-server OBJECT-TYPE
    SYNTAX IpAddress
    MAX-ACCESS accessible-for-notify
    STATUS current
    DESCRIPTION
        "Parameter 'TFTP server' in event AINS.5"
    ::= { ainsEventObjects5 2 }

ainsEventObjects6 OBJECT-IDENTITY
    STATUS current
    DESCRIPTION
        "Event AINS.6
        Error trying to download a file from a TFTP server."
    ::= { ainsEventsGroup 6 }

ains6-File OBJECT-TYPE
    SYNTAX DisplayString
    MAX-ACCESS accessible-for-notify
    STATUS current
    DESCRIPTION
        "Parameter 'File' in event AINS.6"
    ::= { ainsEventObjects6 1 }

ainsEventObjects7 OBJECT-IDENTITY
    STATUS current
    DESCRIPTION
        "Event AINS.7
        A packet is received from/sent to the management station (Teldages)."
    ::= { ainsEventsGroup 7 }

ains7-Packet OBJECT-TYPE
    SYNTAX DisplayString
    MAX-ACCESS accessible-for-notify
    STATUS current
    DESCRIPTION
        "Parameter 'Packet' in event AINS.7"
    ::= { ainsEventObjects7 1 }

ainsEventObjects8 OBJECT-IDENTITY
    STATUS current
    DESCRIPTION
        "Event AINS.8
        Received AutoInstall packet (CONFIG) from the management station
        (Teldages)."
    ::= { ainsEventsGroup 8 }

ains8-dlci OBJECT-TYPE
    SYNTAX Integer32
    MAX-ACCESS accessible-for-notify
    STATUS current
    DESCRIPTION
        "Parameter 'dlci' in event AINS.8"
    ::= { ainsEventObjects8 1 }

ains8-Local-address OBJECT-TYPE
    SYNTAX IpAddress
    MAX-ACCESS accessible-for-notify
    STATUS current
    DESCRIPTION
        "Parameter 'Local address' in event AINS.8"
    ::= { ainsEventObjects8 2 }

ains8-Management-address OBJECT-TYPE
    SYNTAX IpAddress
    MAX-ACCESS accessible-for-notify
    STATUS current
    DESCRIPTION
        "Parameter 'Management address' in event AINS.8"
    ::= { ainsEventObjects8 3 }

ains8-type OBJECT-TYPE
    SYNTAX Integer32
    MAX-ACCESS accessible-for-notify
    STATUS current
    DESCRIPTION
        "Parameter 'type' in event AINS.8"
    ::= { ainsEventObjects8 4 }

ains8-dummy OBJECT-TYPE
    SYNTAX Integer32
    MAX-ACCESS accessible-for-notify
    STATUS current
    DESCRIPTION
        "Parameter 'dummy' in event AINS.8"
    ::= { ainsEventObjects8 5 }

ains8-length OBJECT-TYPE
    SYNTAX Integer32
    MAX-ACCESS accessible-for-notify
    STATUS current
    DESCRIPTION
        "Parameter 'length' in event AINS.8"
    ::= { ainsEventObjects8 6 }

ainsEventObjects10 OBJECT-IDENTITY
    STATUS current
    DESCRIPTION
        "Event AINS.10
        Error parsing the Network Configuration File (NCF)."
    ::= { ainsEventsGroup 10 }

ains10-Error OBJECT-TYPE
    SYNTAX DisplayString
    MAX-ACCESS accessible-for-notify
    STATUS current
    DESCRIPTION
        "Parameter 'Error' in event AINS.10"
    ::= { ainsEventObjects10 1 }

ainsEventObjects11 OBJECT-IDENTITY
    STATUS current
    DESCRIPTION
        "Event AINS.11
        The Hostname associated to the device local IP address was found
        (or not) in the Network Configuration File."
    ::= { ainsEventsGroup 11 }

ains11-Local-address OBJECT-TYPE
    SYNTAX IpAddress
    MAX-ACCESS accessible-for-notify
    STATUS current
    DESCRIPTION
        "Parameter 'Local address' in event AINS.11"
    ::= { ainsEventObjects11 1 }

ains11-found-or-not OBJECT-TYPE
    SYNTAX DisplayString
    MAX-ACCESS accessible-for-notify
    STATUS current
    DESCRIPTION
        "Parameter 'found or not' in event AINS.11"
    ::= { ainsEventObjects11 2 }

ains11-hostname-or-action OBJECT-TYPE
    SYNTAX DisplayString
    MAX-ACCESS accessible-for-notify
    STATUS current
    DESCRIPTION
        "Parameter 'hostname or action' in event AINS.11"
    ::= { ainsEventObjects11 3 }

ainsEventObjects12 OBJECT-IDENTITY
    STATUS current
    DESCRIPTION
        "Event AINS.12
        File download (TFTP) finished. The number of received bytes is shown."
    ::= { ainsEventsGroup 12 }

ains12-Bytes-Received OBJECT-TYPE
    SYNTAX Integer32
    MAX-ACCESS accessible-for-notify
    STATUS current
    DESCRIPTION
        "Parameter 'Bytes Received' in event AINS.12"
    ::= { ainsEventObjects12 1 }

ainsEventObjects13 OBJECT-IDENTITY
    STATUS current
    DESCRIPTION
        "Event AINS.13
        TFTP client message."
    ::= { ainsEventsGroup 13 }

ains13-TFTP-message OBJECT-TYPE
    SYNTAX DisplayString
    MAX-ACCESS accessible-for-notify
    STATUS current
    DESCRIPTION
        "Parameter 'TFTP message' in event AINS.13"
    ::= { ainsEventObjects13 1 }

ainsEventObjects14 OBJECT-IDENTITY
    STATUS current
    DESCRIPTION
        "Event AINS.14
        This message indicates the name used to save configuration file."
    ::= { ainsEventsGroup 14 }

ains14-Configuration-file OBJECT-TYPE
    SYNTAX DisplayString
    MAX-ACCESS accessible-for-notify
    STATUS current
    DESCRIPTION
        "Parameter 'Configuration file' in event AINS.14"
    ::= { ainsEventObjects14 1 }

ainsEventObjects16 OBJECT-IDENTITY
    STATUS current
    DESCRIPTION
        "Event AINS.16
        An error has taken place when copying configuration from the FLASH to
        the SmartCard."
    ::= { ainsEventsGroup 16 }

ains16-Error-message OBJECT-TYPE
    SYNTAX DisplayString
    MAX-ACCESS accessible-for-notify
    STATUS current
    DESCRIPTION
        "Parameter 'Error message' in event AINS.16"
    ::= { ainsEventObjects16 1 }

ainsEventObjects17 OBJECT-IDENTITY
    STATUS current
    DESCRIPTION
        "Event AINS.17
        This message shows the current AutoInstall state."
    ::= { ainsEventsGroup 17 }

ains17-State OBJECT-TYPE
    SYNTAX DisplayString
    MAX-ACCESS accessible-for-notify
    STATUS current
    DESCRIPTION
        "Parameter 'State' in event AINS.17"
    ::= { ainsEventObjects17 1 }

ainsEventObjects18 OBJECT-IDENTITY
    STATUS current
    DESCRIPTION
        "Event AINS.18
        This message shows events and information related to DNS. It is used
        when the AutoInstall process needs to resolve the management station
        fqdn or hostname."
    ::= { ainsEventsGroup 18 }

ains18-DNS-event OBJECT-TYPE
    SYNTAX DisplayString
    MAX-ACCESS accessible-for-notify
    STATUS current
    DESCRIPTION
        "Parameter 'DNS event' in event AINS.18"
    ::= { ainsEventObjects18 1 }

ains18-info OBJECT-TYPE
    SYNTAX DisplayString
    MAX-ACCESS accessible-for-notify
    STATUS current
    DESCRIPTION
        "Parameter 'info' in event AINS.18"
    ::= { ainsEventObjects18 2 }

ainsEventObjects19 OBJECT-IDENTITY
    STATUS current
    DESCRIPTION
        "Event AINS.19
        This message shows the frame sent when auto install net is detecting
        the line type."
    ::= { ainsEventsGroup 19 }

ains19-frame-type OBJECT-TYPE
    SYNTAX DisplayString
    MAX-ACCESS accessible-for-notify
    STATUS current
    DESCRIPTION
        "Parameter 'frame-type' in event AINS.19"
    ::= { ainsEventObjects19 1 }

ains19-interface OBJECT-TYPE
    SYNTAX DisplayString
    MAX-ACCESS accessible-for-notify
    STATUS current
    DESCRIPTION
        "Parameter 'interface' in event AINS.19"
    ::= { ainsEventObjects19 2 }

ainsEventObjects20 OBJECT-IDENTITY
    STATUS current
    DESCRIPTION
        "Event AINS.20
        This message shows the frame received when auto install net is detecting
        the line type."
    ::= { ainsEventsGroup 20 }

ains20-frame-type OBJECT-TYPE
    SYNTAX DisplayString
    MAX-ACCESS accessible-for-notify
    STATUS current
    DESCRIPTION
        "Parameter 'frame-type' in event AINS.20"
    ::= { ainsEventObjects20 1 }

ains20-interface OBJECT-TYPE
    SYNTAX DisplayString
    MAX-ACCESS accessible-for-notify
    STATUS current
    DESCRIPTION
        "Parameter 'interface' in event AINS.20"
    ::= { ainsEventObjects20 2 }

ainsEventObjects21 OBJECT-IDENTITY
    STATUS current
    DESCRIPTION
        "Event AINS.21
        Line detected, changing the configuration."
    ::= { ainsEventsGroup 21 }

ains21-line-type OBJECT-TYPE
    SYNTAX DisplayString
    MAX-ACCESS accessible-for-notify
    STATUS current
    DESCRIPTION
        "Parameter 'line-type' in event AINS.21"
    ::= { ainsEventObjects21 1 }

ains21-interface OBJECT-TYPE
    SYNTAX DisplayString
    MAX-ACCESS accessible-for-notify
    STATUS current
    DESCRIPTION
        "Parameter 'interface' in event AINS.21"
    ::= { ainsEventObjects21 2 }


ainsNotification1 NOTIFICATION-TYPE
    OBJECTS { 
              ains1-AutoInstall-Mode 
            }
    STATUS current
    DESCRIPTION
        "Notification of Event AINS.1

        Message: 'Starting $1 AutoInstall'

        Parameters list:
              $1: ains1-AutoInstall-Mode

        The AutoInstall process is starting/resuming."
    ::= { ainsNotificationsPrefix 1 }

ainsNotification2 NOTIFICATION-TYPE
    STATUS current
    DESCRIPTION
        "Notification of Event AINS.2

        Message: 'AutoInstall process completed successfully.'

        The AutoInstall process has completed successfully."
    ::= { ainsNotificationsPrefix 2 }

ainsNotification3 NOTIFICATION-TYPE
    OBJECTS { 
              ains3-Interface 
            }
    STATUS current
    DESCRIPTION
        "Notification of Event AINS.3

        Message: 'BOOTP Request sent [$1]'

        Parameters list:
              $1: ains3-Interface

        BOOTREQUEST sent on the specified interface."
    ::= { ainsNotificationsPrefix 3 }

ainsNotification4 NOTIFICATION-TYPE
    OBJECTS { 
              ains4-BOOTP-Data 
            }
    STATUS current
    DESCRIPTION
        "Notification of Event AINS.4

        Message: 'BOOTP: $1'

        Parameters list:
              $1: ains4-BOOTP-Data

        Received data in a BOOTREPLY."
    ::= { ainsNotificationsPrefix 4 }

ainsNotification5 NOTIFICATION-TYPE
    OBJECTS { 
              ains5-File, 
              ains5-TFTP-server 
            }
    STATUS current
    DESCRIPTION
        "Notification of Event AINS.5

        Message: 'Downloading $1 from $2'

        Parameters list:
              $1: ains5-File
              $2: ains5-TFTP-server

        The device is trying to download a file from a TFTP server."
    ::= { ainsNotificationsPrefix 5 }

ainsNotification6 NOTIFICATION-TYPE
    OBJECTS { 
              ains6-File 
            }
    STATUS current
    DESCRIPTION
        "Notification of Event AINS.6

        Message: 'Download failure [$1], retrying...'

        Parameters list:
              $1: ains6-File

        Error trying to download a file from a TFTP server."
    ::= { ainsNotificationsPrefix 6 }

ainsNotification7 NOTIFICATION-TYPE
    OBJECTS { 
              ains7-Packet 
            }
    STATUS current
    DESCRIPTION
        "Notification of Event AINS.7

        Message: 'Teldages: $1'

        Parameters list:
              $1: ains7-Packet

        A packet is received from/sent to the management station (Teldages)."
    ::= { ainsNotificationsPrefix 7 }

ainsNotification8 NOTIFICATION-TYPE
    OBJECTS { 
              ains8-dlci, 
              ains8-Local-address,
              ains8-Management-address,
              ains8-type,
              ains8-dummy,
              ains8-length 
            }
    STATUS current
    DESCRIPTION
        "Notification of Event AINS.8

        Message: 'Teldages: dlci $1, ifc $2 -> mng $3 [$4,$5,$6]'

        Parameters list:
              $1: ains8-dlci
              $2: ains8-Local-address
              $3: ains8-Management-address
              $4: ains8-type
              $5: ains8-dummy
              $6: ains8-length

        Received AutoInstall packet (CONFIG) from the management station
        (Teldages)."
    ::= { ainsNotificationsPrefix 8 }

ainsNotification9 NOTIFICATION-TYPE
    STATUS current
    DESCRIPTION
        "Notification of Event AINS.9

        Message: 'Unable to initiate download, retrying...'

        The downloading of a file from the TFTP server could not be initiated."
    ::= { ainsNotificationsPrefix 9 }

ainsNotification10 NOTIFICATION-TYPE
    OBJECTS { 
              ains10-Error 
            }
    STATUS current
    DESCRIPTION
        "Notification of Event AINS.10

        Message: 'NCF Parser: $1'

        Parameters list:
              $1: ains10-Error

        Error parsing the Network Configuration File (NCF)."
    ::= { ainsNotificationsPrefix 10 }

ainsNotification11 NOTIFICATION-TYPE
    OBJECTS { 
              ains11-Local-address, 
              ains11-found-or-not,
              ains11-hostname-or-action 
            }
    STATUS current
    DESCRIPTION
        "Notification of Event AINS.11

        Message: 'Hostname for $1 $2 $3'

        Parameters list:
              $1: ains11-Local-address
              $2: ains11-found-or-not
              $3: ains11-hostname-or-action

        The Hostname associated to the device local IP address was found
        (or not) in the Network Configuration File."
    ::= { ainsNotificationsPrefix 11 }

ainsNotification12 NOTIFICATION-TYPE
    OBJECTS { 
              ains12-Bytes-Received 
            }
    STATUS current
    DESCRIPTION
        "Notification of Event AINS.12

        Message: 'Download finished, $1 bytes received'

        Parameters list:
              $1: ains12-Bytes-Received

        File download (TFTP) finished. The number of received bytes is shown."
    ::= { ainsNotificationsPrefix 12 }

ainsNotification13 NOTIFICATION-TYPE
    OBJECTS { 
              ains13-TFTP-message 
            }
    STATUS current
    DESCRIPTION
        "Notification of Event AINS.13

        Message: 'TFTP: $1'

        Parameters list:
              $1: ains13-TFTP-message

        TFTP client message."
    ::= { ainsNotificationsPrefix 13 }

ainsNotification14 NOTIFICATION-TYPE
    OBJECTS { 
              ains14-Configuration-file 
            }
    STATUS current
    DESCRIPTION
        "Notification of Event AINS.14

        Message: 'Configuration saved as $1'

        Parameters list:
              $1: ains14-Configuration-file

        This message indicates the name used to save configuration file."
    ::= { ainsNotificationsPrefix 14 }

ainsNotification15 NOTIFICATION-TYPE
    STATUS current
    DESCRIPTION
        "Notification of Event AINS.15

        Message: 'Configuration saved in SmartCard'

        Configuration saved in SmartCard successfully. This message only will be
        shown in devices with SmartCard."
    ::= { ainsNotificationsPrefix 15 }

ainsNotification16 NOTIFICATION-TYPE
    OBJECTS { 
              ains16-Error-message 
            }
    STATUS current
    DESCRIPTION
        "Notification of Event AINS.16

        Message: 'Error saving in SmartCard: $1'

        Parameters list:
              $1: ains16-Error-message

        An error has taken place when copying configuration from the FLASH to
        the SmartCard."
    ::= { ainsNotificationsPrefix 16 }

ainsNotification17 NOTIFICATION-TYPE
    OBJECTS { 
              ains17-State 
            }
    STATUS current
    DESCRIPTION
        "Notification of Event AINS.17

        Message: 'AutoInstall state: $1'

        Parameters list:
              $1: ains17-State

        This message shows the current AutoInstall state."
    ::= { ainsNotificationsPrefix 17 }

ainsNotification18 NOTIFICATION-TYPE
    OBJECTS { 
              ains18-DNS-event, 
              ains18-info 
            }
    STATUS current
    DESCRIPTION
        "Notification of Event AINS.18

        Message: 'DNS: $1 - $2'

        Parameters list:
              $1: ains18-DNS-event
              $2: ains18-info

        This message shows events and information related to DNS. It is used
        when the AutoInstall process needs to resolve the management station
        fqdn or hostname."
    ::= { ainsNotificationsPrefix 18 }

ainsNotification19 NOTIFICATION-TYPE
    OBJECTS { 
              ains19-frame-type, 
              ains19-interface 
            }
    STATUS current
    DESCRIPTION
        "Notification of Event AINS.19

        Message: 'Auto Detect Line: sending $1 [$2]'

        Parameters list:
              $1: ains19-frame-type
              $2: ains19-interface

        This message shows the frame sent when auto install net is detecting
        the line type."
    ::= { ainsNotificationsPrefix 19 }

ainsNotification20 NOTIFICATION-TYPE
    OBJECTS { 
              ains20-frame-type, 
              ains20-interface 
            }
    STATUS current
    DESCRIPTION
        "Notification of Event AINS.20

        Message: 'Auto Detect Line: received $1 [$2]'

        Parameters list:
              $1: ains20-frame-type
              $2: ains20-interface

        This message shows the frame received when auto install net is detecting
        the line type."
    ::= { ainsNotificationsPrefix 20 }

ainsNotification21 NOTIFICATION-TYPE
    OBJECTS { 
              ains21-line-type, 
              ains21-interface 
            }
    STATUS current
    DESCRIPTION
        "Notification of Event AINS.21

        Message: 'Auto Detect Line: $1 detected [$2], proceeding...'

        Parameters list:
              $1: ains21-line-type
              $2: ains21-interface

        Line detected, changing the configuration."
    ::= { ainsNotificationsPrefix 21 }

ainsNotification22 NOTIFICATION-TYPE
    STATUS current
    DESCRIPTION
        "Notification of Event AINS.22

        Message: 'Auto Detect Line: configuration changed, resetting...'

        Configuration changed successfully, resetting equipment."
    ::= { ainsNotificationsPrefix 22 }

ainsNotification23 NOTIFICATION-TYPE
    STATUS current
    DESCRIPTION
        "Notification of Event AINS.23

        Message: 'Auto Detect Line: error, configuration not changed'

        Unable to change configuration, process aborted."
    ::= { ainsNotificationsPrefix 23 }


END
