-- =============================================================================
-- Copyright (C) 2012 by HUAWEI TECHNOLOGIES. All rights reserved.
--    
-- Description: The MIB is designed to get GLOBALIPCAR' statistic information. 
-- Reference: Huawei Enterprise MIB
-- Version: 1.0
-- History: 
--          V1.0 The initial version created by Juhailing 90003307. 
-- =============================================================================

HUAWEI-SECURITY-GLOBALIPCAR-MIB DEFINITIONS ::= BEGIN
 
	IMPORTS   
		RowStatus
			FROM SNMPv2-TC
		Gauge32, IpAddress, Counter64, OBJECT-TYPE, MODULE-IDENTITY
			FROM SNMPv2-SMI 
		MODULE-COMPLIANCE, OBJECT-GROUP, NOTIFICATION-GROUP          
		            FROM SNMPv2-CONF
    		enterprises			
		            FROM RFC1155-SMI; 

		            
		hwGlobalIPCar MODULE-IDENTITY 
		        LAST-UPDATED "201203210900Z"        -- March 21, 2012 at 09:00 GMT
		        ORGANIZATION 
		            "Huawei Symantec Technologies Co., Ltd."
		        CONTACT-INFO 
		            "3rd Floor,Section D, Keshi Building, No.28, Xinxi Rd., Shangdi,
		         	 Hai-Dian District Beijing P.R. China
			         Zip:100085
			         Http://www.huaweisymantec.com    
			         support@huawesymantec.com
                     "
		        DESCRIPTION 
		            "V1.00
			         The GlobalIPCar mib is for Eudemon and USG product series.
			         The GlobalIPCar feature is to limit traffic rate for global IP "
		        ::= { hwSecurity 54 }
		
-- ===============================================
-- Node definitions
-- ===============================================
	    
	    	-- 1.3.6.1.4.1.2011
		huawei OBJECT IDENTIFIER ::= { enterprises 2011 }
	        
		-- 1.3.6.1.4.1.2011.6
		huaweiUtility OBJECT IDENTIFIER ::= { huawei 6 }
	        
		-- 1.3.6.1.4.1.2011.6.122
		hwSecurity OBJECT IDENTIFIER ::= { huaweiUtility 122 }     
		
-- ===============================================
-- Begin the hwGlobalIPCarGlobalStats.
-- ===============================================
	    hwGlobalIPCarGlobalStats OBJECT IDENTIFIER ::= { hwGlobalIPCar 1 }
		
	    	hwGlobalIPCarIPTotal OBJECT-TYPE
			SYNTAX Gauge32 
			MAX-ACCESS read-only
			STATUS current
			DESCRIPTION
				"Total number of traffic limmited global IPs."
			::= { hwGlobalIPCarGlobalStats 1 }      
	    


-- ===============================================
-- Begin the table of hwGlobalIPCarConfigTable.
-- ===============================================
				    
	    	-- 1.3.6.1.4.1.2011.6.122.54.2
    		hwGlobalIPCarConfigTable OBJECT-TYPE
            		SYNTAX 		SEQUENCE OF HwGlobalIPCarConfigEntry
            		MAX-ACCESS 	not-accessible
            		STATUS 		current
            		DESCRIPTION
            			"This table specifies the configuration attributes for Huawei GlobalIPCar."   
            		::= { hwGlobalIPCar 2 }
    
    		-- 1.3.6.1.4.1.2011.6.122.54.2.1
    		hwGlobalIPCarConfigEntry OBJECT-TYPE
        		SYNTAX HwGlobalIPCarConfigEntry
        		MAX-ACCESS not-accessible
        		STATUS current
        		DESCRIPTION
            			"Each entry in the hwGlobalIPCarConfigTable holds a set of traffic monitoring configuration parameters associated with an instance of global IP."
        		INDEX { hwGlobalIPCarGlobalIP }
        		::= { hwGlobalIPCarConfigTable 1 }
    
    		HwGlobalIPCarConfigEntry ::=
        		SEQUENCE { 
            			hwGlobalIPCarGlobalIP
            			        IpAddress,
            			hwGlobalIPCarVrfIndex
                			Gauge32,            			 
                		hwGlobalIPCarInboundCarType
                			Gauge32,
		            	hwGlobalIPCarOutboundCarType
                			Gauge32,   
                		hwGlobalIPCarInboundCIR
                			Gauge32,     
			         hwGlobalIPCarOutboundCIR
                			Gauge32
         			}

        	-- 1.3.6.1.4.1.2011.6.122.54.2.1.1
        	
        	hwGlobalIPCarGlobalIP OBJECT-TYPE
	        	SYNTAX IpAddress 
	        	MAX-ACCESS not-accessible
	        	STATUS current
	        	DESCRIPTION
	            		"Address of the global IP."
	        	::= { hwGlobalIPCarConfigEntry 1 }
        	
        	
	    	hwGlobalIPCarVrfIndex OBJECT-TYPE
	        	SYNTAX Gauge32 
	        	MAX-ACCESS not-accessible
	        	STATUS current
	        	DESCRIPTION
	            		"Index for the virtual firewall(Vrf)."
	        	::= { hwGlobalIPCarConfigEntry 2 }
                                                    
               hwGlobalIPCarInboundCarType OBJECT-TYPE
	        	SYNTAX Gauge32 
	        	MAX-ACCESS read-only
	        	STATUS current
	        	DESCRIPTION
	            		"If the global IP inbound traffic is limited.If yes, the value is 1."
	        	::= { hwGlobalIPCarConfigEntry 3 }
                                        
	    	hwGlobalIPCarOutboundCarType OBJECT-TYPE
	        	SYNTAX Gauge32 
	        	MAX-ACCESS read-only
	        	STATUS current
	        	DESCRIPTION
	            		"If the global IP outbound traffic is limited.If yes, the value is 1."
	        	::= { hwGlobalIPCarConfigEntry 4 }
	   
	    	hwGlobalIPCarInboundCIR OBJECT-TYPE
	        	SYNTAX Gauge32 
	        	MAX-ACCESS read-only
	        	STATUS current
	        	DESCRIPTION
	            		"The global IP inbound committed information rate (CIR)."
	        	::= { hwGlobalIPCarConfigEntry 5 }
	    
	    	hwGlobalIPCarOutboundCIR OBJECT-TYPE
	        	SYNTAX Gauge32 
	        	MAX-ACCESS read-only
	        	STATUS current
	        	DESCRIPTION
	            		"The global IP outbound committed information rate (CIR)."
	        	::= { hwGlobalIPCarConfigEntry 6 }
	   
	     	        
-- ===============================================
-- Begin the table of hwGlobalIPCarStatsTable.
-- ===============================================
				    
	    	-- 1.3.6.1.4.1.2011.6.122.54.3
    		hwGlobalIPCarStatsTable OBJECT-TYPE
            		SYNTAX SEQUENCE OF HwGlobalIPCarStatsEntry
            		MAX-ACCESS not-accessible
            		STATUS current
            		DESCRIPTION
            			"This table specifies the status attributes for Huawei GlobalIPCar."   
            		::= { hwGlobalIPCar 3 }
    
    		-- 1.3.6.1.4.1.2011.6.122.54.3.1
    		hwGlobalIPCarStatsEntry OBJECT-TYPE
        		SYNTAX HwGlobalIPCarStatsEntry
        		MAX-ACCESS not-accessible
        		STATUS current
        		DESCRIPTION
            			"Each entry in the hwGlobalIPCarStatsTable holds a set of monitoring status parameters associated with an instance of Global IP."
        		INDEX { hwGlobalIPCarGlobalIP }
        		::= { hwGlobalIPCarStatsTable 1 }
    
    		HwGlobalIPCarStatsEntry ::=
        		SEQUENCE { 
                	hwGlobalIPCarGlobalIP
                		IpAddress,
            		hwGlobalIPCarVrfIndex
                		Gauge32, 
                	hwGlobalIPCarInboundPassBytes
                		Counter64,
                	hwGlobalIPCarOutboundPassBytes  
                		Counter64,
                	hwGlobalIPCarInboundDropBytes
                		Counter64,
                	hwGlobalIPCarOutboundDropBytes
                		Counter64
         		} 
	   
	    hwGlobalIPCarInboundPassBytes OBJECT-TYPE
	        SYNTAX Counter64 
	        MAX-ACCESS read-only
	        STATUS current
	        DESCRIPTION
	            "The global IP inbound traffic passed bytes."
	        ::= { hwGlobalIPCarStatsEntry 1 }   
	    
	    hwGlobalIPCarOutboundPassBytes OBJECT-TYPE
	        SYNTAX Counter64 
	        MAX-ACCESS read-only
	        STATUS current
	        DESCRIPTION
	            "The global IP outbound traffic passed bytes."
	        ::= { hwGlobalIPCarStatsEntry 2 }

	    hwGlobalIPCarInboundDropBytes  OBJECT-TYPE
	        SYNTAX Counter64 
	        MAX-ACCESS read-only
	        STATUS current
	        DESCRIPTION
	            "The global IP inbound traffic dropped bytes."
	        ::= { hwGlobalIPCarStatsEntry 3 }

	    hwGlobalIPCarOutboundDropBytes OBJECT-TYPE
	        SYNTAX Counter64 
	        MAX-ACCESS read-only
	        STATUS current
	        DESCRIPTION
	            "The global IP outbound traffic dropped bytes."
	        ::= { hwGlobalIPCarStatsEntry 4 }


   	        
-- ===============================================
-- hwGlobalIPCarTrapObject.
-- ===============================================
 
 		hwGlobalIPCarTrapObject OBJECT IDENTIFIER ::= { hwGlobalIPCar 4 }
	     	        
	    	hwGlobalIPCarTrapGlobalIP OBJECT-TYPE
	        	SYNTAX IpAddress 
	        	MAX-ACCESS accessible-for-notify
	        	STATUS current
	        	DESCRIPTION
	            		"Global IP Address for trap."
	        	::= { hwGlobalIPCarTrapObject 1 }
	    	
	    	hwGlobalIPCarTrapVrfIndex OBJECT-TYPE
	        	SYNTAX Gauge32 
	        	MAX-ACCESS accessible-for-notify
	        	STATUS current
	        	DESCRIPTION
	            		"Index of the virtual fire wall(Vrf) for trap."
	        	::= { hwGlobalIPCarTrapObject 2 }
	    
	    	hwGlobalIPCarTrapVrfName OBJECT-TYPE
	        	SYNTAX OCTET STRING (SIZE (1..31))
	        	MAX-ACCESS accessible-for-notify
	        	STATUS current
	        	DESCRIPTION
	            		"Name for the virtual fire wall(Vrf) for trap."
	        	::= { hwGlobalIPCarTrapObject 3 } 
	        
-- ===============================================
-- definition of traps.      
-- ===============================================

	    hwGlobalIPCarNotifications OBJECT IDENTIFIER ::= { hwGlobalIPCar 5 }
			                                
	        hwGlobalIPCarIPAdd NOTIFICATION-TYPE
			OBJECTS { 
				hwGlobalIPCarTrapGlobalIP,
				hwGlobalIPCarTrapVrfIndex,
				hwGlobalIPCarTrapVrfName    
			        }
			STATUS     current
			DESCRIPTION
			    "Send the message when a Global-IP-Car configuration is added."
			::= { hwGlobalIPCarNotifications 1 }
			
	        hwGlobalIPCarIPDel NOTIFICATION-TYPE
			OBJECTS { 
			 
				hwGlobalIPCarTrapGlobalIP,
				hwGlobalIPCarTrapVrfIndex,
				hwGlobalIPCarTrapVrfName  
			        }
			STATUS     current
			DESCRIPTION
			    "Send the message when a Global-IP-Car configuration is deleted."
			::= { hwGlobalIPCarNotifications 2 }   
-- ===============================================
-- Conformance Information             
-- ===============================================

		hwGlobalIPCarMibConformance OBJECT IDENTIFIER ::= { hwGlobalIPCar 6 }
		
		hwGlobalIPCarMibCompliances OBJECT IDENTIFIER ::= { hwGlobalIPCarMibConformance 1 }
		
		hwGlobalIPCarMibGroups OBJECT IDENTIFIER ::= { hwGlobalIPCarMibConformance 2 }
		
		
-- ===============================================
-- Compliance Statements             
-- ===============================================	
	
        hwGlobalIPCarMibCompliance MODULE-COMPLIANCE
			 STATUS current
			 DESCRIPTION 
				" "
			 MODULE -- this module
			 MANDATORY-GROUPS 
				{ 
				hwGlobalIPCarGlobalStatsGroup,
				hwGlobalIPCarConfigTableGroup,
				hwGlobalIPCarStatsTableGroup, 
				hwGlobalIPCarTrapObjectGroup,
				hwGlobalIPCarNotificationsGroup

				}
			::= { hwGlobalIPCarMibCompliances 1 }   
			
	       
	     
		hwGlobalIPCarGlobalStatsGroup OBJECT-GROUP
			OBJECTS { 
					hwGlobalIPCarIPTotal										
				}
			STATUS current
			DESCRIPTION 
				""
			::= { hwGlobalIPCarMibGroups 1 }			     
        
               hwGlobalIPCarConfigTableGroup OBJECT-GROUP
			OBJECTS { 
					hwGlobalIPCarInboundCarType,
                                        hwGlobalIPCarOutboundCarType,
                                        hwGlobalIPCarInboundCIR,
                                        hwGlobalIPCarOutboundCIR										
				}
			STATUS current
			DESCRIPTION 
				"This group holds a set of traffic monitoring configuration
				 parameters associated with an instance of global IP."
			::= { hwGlobalIPCarMibGroups 2 }                    
			
		hwGlobalIPCarStatsTableGroup OBJECT-GROUP
			OBJECTS {                       
					hwGlobalIPCarInboundPassBytes,
                                        hwGlobalIPCarOutboundPassBytes,
                                        hwGlobalIPCarInboundDropBytes,
                                        hwGlobalIPCarOutboundDropBytes										
				}
			STATUS current
			DESCRIPTION 
				"This group This group holds a set of traffic monitoring statis
				 parameters associated with an instance of global IP."
			::= { hwGlobalIPCarMibGroups 3 }	

			
		hwGlobalIPCarTrapObjectGroup OBJECT-GROUP
			OBJECTS {                               
                   	                hwGlobalIPCarTrapGlobalIP,
                                        hwGlobalIPCarTrapVrfIndex,
                                        hwGlobalIPCarTrapVrfName   						
				}
			STATUS current
			DESCRIPTION 
				"GlobalIPCar trap objects."
			::= { hwGlobalIPCarMibGroups 4 }	
			
	       hwGlobalIPCarNotificationsGroup NOTIFICATION-GROUP
			NOTIFICATIONS {                               
                   		hwGlobalIPCarIPAdd,
                                hwGlobalIPCarIPDel
               		}
			STATUS current
			DESCRIPTION 
				"GlobalIPCar traps."
			::= { hwGlobalIPCarMibGroups 5 }	
	END
