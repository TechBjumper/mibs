-- file automatically created


TELDAT-TRAP-TLPY-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tlpyTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TLPY event subsystem."
    REVISION "201401200930Z"
    DESCRIPTION "Initial implementation"
        ::= { telEventTraps 184 }


tlpyEventsGroup	OBJECT IDENTIFIER	::= { tlpyTrapsMIB 1 }

tlpyNotifications	OBJECT IDENTIFIER	::= { tlpyTrapsMIB 2 }
tlpyNotificationsPrefix	OBJECT IDENTIFIER	::= { tlpyNotifications 0 }

tlpyEventObjects1 OBJECT-IDENTITY
    STATUS current
    DESCRIPTION
        "Event TLPY.1
        Call events."
    ::= { tlpyEventsGroup 1 }

tlpy1-event OBJECT-TYPE
    SYNTAX DisplayString
    MAX-ACCESS accessible-for-notify
    STATUS current
    DESCRIPTION
        "Parameter 'event' in event TLPY.1"
    ::= { tlpyEventObjects1 1 }

tlpy1-caller OBJECT-TYPE
    SYNTAX DisplayString
    MAX-ACCESS accessible-for-notify
    STATUS current
    DESCRIPTION
        "Parameter 'caller' in event TLPY.1"
    ::= { tlpyEventObjects1 2 }

tlpy1-indp OBJECT-TYPE
    SYNTAX Integer32
    MAX-ACCESS accessible-for-notify
    STATUS current
    DESCRIPTION
        "Parameter 'indp' in event TLPY.1"
    ::= { tlpyEventObjects1 3 }

tlpy1-called OBJECT-TYPE
    SYNTAX DisplayString
    MAX-ACCESS accessible-for-notify
    STATUS current
    DESCRIPTION
        "Parameter 'called' in event TLPY.1"
    ::= { tlpyEventObjects1 4 }

tlpy1-outdp OBJECT-TYPE
    SYNTAX Integer32
    MAX-ACCESS accessible-for-notify
    STATUS current
    DESCRIPTION
        "Parameter 'outdp' in event TLPY.1"
    ::= { tlpyEventObjects1 5 }

tlpy1-cdr OBJECT-TYPE
    SYNTAX Integer32
    MAX-ACCESS accessible-for-notify
    STATUS current
    DESCRIPTION
        "Parameter 'cdr' in event TLPY.1"
    ::= { tlpyEventObjects1 6 }

tlpyEventObjects2 OBJECT-IDENTITY
    STATUS current
    DESCRIPTION
        "Event TLPY.2
        Call transfer event."
    ::= { tlpyEventsGroup 2 }

tlpy2-call1 OBJECT-TYPE
    SYNTAX DisplayString
    MAX-ACCESS accessible-for-notify
    STATUS current
    DESCRIPTION
        "Parameter 'call1' in event TLPY.2"
    ::= { tlpyEventObjects2 1 }

tlpy2-call2 OBJECT-TYPE
    SYNTAX DisplayString
    MAX-ACCESS accessible-for-notify
    STATUS current
    DESCRIPTION
        "Parameter 'call2' in event TLPY.2"
    ::= { tlpyEventObjects2 2 }

tlpyEventObjects3 OBJECT-IDENTITY
    STATUS current
    DESCRIPTION
        "Event TLPY.3
        NSLA changed."
    ::= { tlpyEventsGroup 3 }

tlpy3-dialpeer OBJECT-TYPE
    SYNTAX Integer32
    MAX-ACCESS accessible-for-notify
    STATUS current
    DESCRIPTION
        "Parameter 'dialpeer' in event TLPY.3"
    ::= { tlpyEventObjects3 1 }

tlpy3-status OBJECT-TYPE
    SYNTAX DisplayString
    MAX-ACCESS accessible-for-notify
    STATUS current
    DESCRIPTION
        "Parameter 'status' in event TLPY.3"
    ::= { tlpyEventObjects3 2 }

tlpyEventObjects4 OBJECT-IDENTITY
    STATUS current
    DESCRIPTION
        "Event TLPY.4
        Control status changed."
    ::= { tlpyEventsGroup 4 }

tlpy4-calltype OBJECT-TYPE
    SYNTAX DisplayString
    MAX-ACCESS accessible-for-notify
    STATUS current
    DESCRIPTION
        "Parameter 'calltype' in event TLPY.4"
    ::= { tlpyEventObjects4 1 }

tlpy4-status OBJECT-TYPE
    SYNTAX DisplayString
    MAX-ACCESS accessible-for-notify
    STATUS current
    DESCRIPTION
        "Parameter 'status' in event TLPY.4"
    ::= { tlpyEventObjects4 2 }

tlpyEventObjects5 OBJECT-IDENTITY
    STATUS current
    DESCRIPTION
        "Event TLPY.5
        Found dial-peer."
    ::= { tlpyEventsGroup 5 }

tlpy5-dialpeer OBJECT-TYPE
    SYNTAX Integer32
    MAX-ACCESS accessible-for-notify
    STATUS current
    DESCRIPTION
        "Parameter 'dialpeer' in event TLPY.5"
    ::= { tlpyEventObjects5 1 }

tlpy5-called-number OBJECT-TYPE
    SYNTAX DisplayString
    MAX-ACCESS accessible-for-notify
    STATUS current
    DESCRIPTION
        "Parameter 'called-number' in event TLPY.5"
    ::= { tlpyEventObjects5 2 }

tlpy5-calling-number OBJECT-TYPE
    SYNTAX DisplayString
    MAX-ACCESS accessible-for-notify
    STATUS current
    DESCRIPTION
        "Parameter 'calling-number' in event TLPY.5"
    ::= { tlpyEventObjects5 3 }

tlpyEventObjects6 OBJECT-IDENTITY
    STATUS current
    DESCRIPTION
        "Event TLPY.6
        Found dial-peer."
    ::= { tlpyEventsGroup 6 }

tlpy6-dialpeer OBJECT-TYPE
    SYNTAX Integer32
    MAX-ACCESS accessible-for-notify
    STATUS current
    DESCRIPTION
        "Parameter 'dialpeer' in event TLPY.6"
    ::= { tlpyEventObjects6 1 }

tlpy6-called-number OBJECT-TYPE
    SYNTAX DisplayString
    MAX-ACCESS accessible-for-notify
    STATUS current
    DESCRIPTION
        "Parameter 'called-number' in event TLPY.6"
    ::= { tlpyEventObjects6 2 }

tlpyEventObjects7 OBJECT-IDENTITY
    STATUS current
    DESCRIPTION
        "Event TLPY.7
        Dial-peer not found."
    ::= { tlpyEventsGroup 7 }

tlpy7-direction OBJECT-TYPE
    SYNTAX DisplayString
    MAX-ACCESS accessible-for-notify
    STATUS current
    DESCRIPTION
        "Parameter 'direction' in event TLPY.7"
    ::= { tlpyEventObjects7 1 }

tlpy7-called-number OBJECT-TYPE
    SYNTAX DisplayString
    MAX-ACCESS accessible-for-notify
    STATUS current
    DESCRIPTION
        "Parameter 'called-number' in event TLPY.7"
    ::= { tlpyEventObjects7 2 }

tlpy7-calling-number OBJECT-TYPE
    SYNTAX DisplayString
    MAX-ACCESS accessible-for-notify
    STATUS current
    DESCRIPTION
        "Parameter 'calling-number' in event TLPY.7"
    ::= { tlpyEventObjects7 3 }

tlpyEventObjects8 OBJECT-IDENTITY
    STATUS current
    DESCRIPTION
        "Event TLPY.8
        This message shows the percentage of lost frames in the last second."
    ::= { tlpyEventsGroup 8 }

tlpy8-num OBJECT-TYPE
    SYNTAX Integer32
    MAX-ACCESS accessible-for-notify
    STATUS current
    DESCRIPTION
        "Parameter 'num' in event TLPY.8"
    ::= { tlpyEventObjects8 1 }

tlpy8-per OBJECT-TYPE
    SYNTAX Integer32
    MAX-ACCESS accessible-for-notify
    STATUS current
    DESCRIPTION
        "Parameter 'per' in event TLPY.8"
    ::= { tlpyEventObjects8 2 }

tlpy8-id OBJECT-TYPE
    SYNTAX DisplayString
    MAX-ACCESS accessible-for-notify
    STATUS current
    DESCRIPTION
        "Parameter 'id' in event TLPY.8"
    ::= { tlpyEventObjects8 3 }

tlpy8-cdr OBJECT-TYPE
    SYNTAX Integer32
    MAX-ACCESS accessible-for-notify
    STATUS current
    DESCRIPTION
        "Parameter 'cdr' in event TLPY.8"
    ::= { tlpyEventObjects8 4 }

tlpyEventObjects9 OBJECT-IDENTITY
    STATUS current
    DESCRIPTION
        "Event TLPY.9
        Display several statistical values for current delay computation."
    ::= { tlpyEventsGroup 9 }

tlpy9-text OBJECT-TYPE
    SYNTAX DisplayString
    MAX-ACCESS accessible-for-notify
    STATUS current
    DESCRIPTION
        "Parameter 'text' in event TLPY.9"
    ::= { tlpyEventObjects9 1 }

tlpy9-id OBJECT-TYPE
    SYNTAX DisplayString
    MAX-ACCESS accessible-for-notify
    STATUS current
    DESCRIPTION
        "Parameter 'id' in event TLPY.9"
    ::= { tlpyEventObjects9 2 }

tlpy9-cdr OBJECT-TYPE
    SYNTAX Integer32
    MAX-ACCESS accessible-for-notify
    STATUS current
    DESCRIPTION
        "Parameter 'cdr' in event TLPY.9"
    ::= { tlpyEventObjects9 3 }

tlpyEventObjects10 OBJECT-IDENTITY
    STATUS current
    DESCRIPTION
        "Event TLPY.10
        This message gives information about the delay and variance measured in
        a communication."
    ::= { tlpyEventsGroup 10 }

tlpy10-delay OBJECT-TYPE
    SYNTAX Integer32
    MAX-ACCESS accessible-for-notify
    STATUS current
    DESCRIPTION
        "Parameter 'delay' in event TLPY.10"
    ::= { tlpyEventObjects10 1 }

tlpy10-jitter OBJECT-TYPE
    SYNTAX Integer32
    MAX-ACCESS accessible-for-notify
    STATUS current
    DESCRIPTION
        "Parameter 'jitter' in event TLPY.10"
    ::= { tlpyEventObjects10 2 }

tlpy10-id OBJECT-TYPE
    SYNTAX DisplayString
    MAX-ACCESS accessible-for-notify
    STATUS current
    DESCRIPTION
        "Parameter 'id' in event TLPY.10"
    ::= { tlpyEventObjects10 3 }

tlpy10-cdr OBJECT-TYPE
    SYNTAX Integer32
    MAX-ACCESS accessible-for-notify
    STATUS current
    DESCRIPTION
        "Parameter 'cdr' in event TLPY.10"
    ::= { tlpyEventObjects10 4 }

tlpyEventObjects11 OBJECT-IDENTITY
    STATUS current
    DESCRIPTION
        "Event TLPY.11
        RTP mean delay out."
    ::= { tlpyEventsGroup 11 }

tlpy11-delay OBJECT-TYPE
    SYNTAX Integer32
    MAX-ACCESS accessible-for-notify
    STATUS current
    DESCRIPTION
        "Parameter 'delay' in event TLPY.11"
    ::= { tlpyEventObjects11 1 }

tlpy11-id OBJECT-TYPE
    SYNTAX DisplayString
    MAX-ACCESS accessible-for-notify
    STATUS current
    DESCRIPTION
        "Parameter 'id' in event TLPY.11"
    ::= { tlpyEventObjects11 2 }

tlpy11-cdr OBJECT-TYPE
    SYNTAX Integer32
    MAX-ACCESS accessible-for-notify
    STATUS current
    DESCRIPTION
        "Parameter 'cdr' in event TLPY.11"
    ::= { tlpyEventObjects11 3 }

tlpyEventObjects12 OBJECT-IDENTITY
    STATUS current
    DESCRIPTION
        "Event TLPY.12
        RTP synchronize."
    ::= { tlpyEventsGroup 12 }

tlpy12-id OBJECT-TYPE
    SYNTAX DisplayString
    MAX-ACCESS accessible-for-notify
    STATUS current
    DESCRIPTION
        "Parameter 'id' in event TLPY.12"
    ::= { tlpyEventObjects12 1 }

tlpy12-cdr OBJECT-TYPE
    SYNTAX Integer32
    MAX-ACCESS accessible-for-notify
    STATUS current
    DESCRIPTION
        "Parameter 'cdr' in event TLPY.12"
    ::= { tlpyEventObjects12 2 }

tlpyEventObjects13 OBJECT-IDENTITY
    STATUS current
    DESCRIPTION
        "Event TLPY.13
        Lost a too delayed frame."
    ::= { tlpyEventsGroup 13 }

tlpy13-CurrDelay OBJECT-TYPE
    SYNTAX Integer32
    MAX-ACCESS accessible-for-notify
    STATUS current
    DESCRIPTION
        "Parameter 'CurrDelay' in event TLPY.13"
    ::= { tlpyEventObjects13 1 }

tlpy13-PlyDelay OBJECT-TYPE
    SYNTAX Integer32
    MAX-ACCESS accessible-for-notify
    STATUS current
    DESCRIPTION
        "Parameter 'PlyDelay' in event TLPY.13"
    ::= { tlpyEventObjects13 2 }

tlpy13-id OBJECT-TYPE
    SYNTAX DisplayString
    MAX-ACCESS accessible-for-notify
    STATUS current
    DESCRIPTION
        "Parameter 'id' in event TLPY.13"
    ::= { tlpyEventObjects13 3 }

tlpy13-cdr OBJECT-TYPE
    SYNTAX Integer32
    MAX-ACCESS accessible-for-notify
    STATUS current
    DESCRIPTION
        "Parameter 'cdr' in event TLPY.13"
    ::= { tlpyEventObjects13 4 }

tlpyEventObjects14 OBJECT-IDENTITY
    STATUS current
    DESCRIPTION
        "Event TLPY.14
        Codec added or removed from call."
    ::= { tlpyEventsGroup 14 }

tlpy14-action OBJECT-TYPE
    SYNTAX DisplayString
    MAX-ACCESS accessible-for-notify
    STATUS current
    DESCRIPTION
        "Parameter 'action' in event TLPY.14"
    ::= { tlpyEventObjects14 1 }

tlpy14-called-number OBJECT-TYPE
    SYNTAX DisplayString
    MAX-ACCESS accessible-for-notify
    STATUS current
    DESCRIPTION
        "Parameter 'called-number' in event TLPY.14"
    ::= { tlpyEventObjects14 2 }

tlpy14-calling-number OBJECT-TYPE
    SYNTAX DisplayString
    MAX-ACCESS accessible-for-notify
    STATUS current
    DESCRIPTION
        "Parameter 'calling-number' in event TLPY.14"
    ::= { tlpyEventObjects14 3 }

tlpy14-codec-str OBJECT-TYPE
    SYNTAX DisplayString
    MAX-ACCESS accessible-for-notify
    STATUS current
    DESCRIPTION
        "Parameter 'codec-str' in event TLPY.14"
    ::= { tlpyEventObjects14 4 }

tlpy14-nob OBJECT-TYPE
    SYNTAX Integer32
    MAX-ACCESS accessible-for-notify
    STATUS current
    DESCRIPTION
        "Parameter 'nob' in event TLPY.14"
    ::= { tlpyEventObjects14 5 }

tlpy14-vad OBJECT-TYPE
    SYNTAX DisplayString
    MAX-ACCESS accessible-for-notify
    STATUS current
    DESCRIPTION
        "Parameter 'vad' in event TLPY.14"
    ::= { tlpyEventObjects14 6 }

tlpy14-cdr OBJECT-TYPE
    SYNTAX Integer32
    MAX-ACCESS accessible-for-notify
    STATUS current
    DESCRIPTION
        "Parameter 'cdr' in event TLPY.14"
    ::= { tlpyEventObjects14 7 }

tlpyEventObjects15 OBJECT-IDENTITY
    STATUS current
    DESCRIPTION
        "Event TLPY.15
        Call jump event."
    ::= { tlpyEventsGroup 15 }

tlpy15-type OBJECT-TYPE
    SYNTAX DisplayString
    MAX-ACCESS accessible-for-notify
    STATUS current
    DESCRIPTION
        "Parameter 'type' in event TLPY.15"
    ::= { tlpyEventObjects15 1 }

tlpy15-peergroup OBJECT-TYPE
    SYNTAX Integer32
    MAX-ACCESS accessible-for-notify
    STATUS current
    DESCRIPTION
        "Parameter 'peergroup' in event TLPY.15"
    ::= { tlpyEventObjects15 2 }

tlpy15-dial-peer OBJECT-TYPE
    SYNTAX Integer32
    MAX-ACCESS accessible-for-notify
    STATUS current
    DESCRIPTION
        "Parameter 'dial-peer' in event TLPY.15"
    ::= { tlpyEventObjects15 3 }

tlpy15-telephone OBJECT-TYPE
    SYNTAX DisplayString
    MAX-ACCESS accessible-for-notify
    STATUS current
    DESCRIPTION
        "Parameter 'telephone' in event TLPY.15"
    ::= { tlpyEventObjects15 4 }

tlpy15-cdr OBJECT-TYPE
    SYNTAX Integer32
    MAX-ACCESS accessible-for-notify
    STATUS current
    DESCRIPTION
        "Parameter 'cdr' in event TLPY.15"
    ::= { tlpyEventObjects15 5 }

tlpyEventObjects16 OBJECT-IDENTITY
    STATUS current
    DESCRIPTION
        "Event TLPY.16
        CDR file information."
    ::= { tlpyEventsGroup 16 }

tlpy16-file OBJECT-TYPE
    SYNTAX DisplayString
    MAX-ACCESS accessible-for-notify
    STATUS current
    DESCRIPTION
        "Parameter 'file' in event TLPY.16"
    ::= { tlpyEventObjects16 1 }

tlpy16-state OBJECT-TYPE
    SYNTAX DisplayString
    MAX-ACCESS accessible-for-notify
    STATUS current
    DESCRIPTION
        "Parameter 'state' in event TLPY.16"
    ::= { tlpyEventObjects16 2 }

tlpy16-size OBJECT-TYPE
    SYNTAX Integer32
    MAX-ACCESS accessible-for-notify
    STATUS current
    DESCRIPTION
        "Parameter 'size' in event TLPY.16"
    ::= { tlpyEventObjects16 3 }

tlpyEventObjects17 OBJECT-IDENTITY
    STATUS current
    DESCRIPTION
        "Event TLPY.17
        Warning, too many consecutive errors."
    ::= { tlpyEventsGroup 17 }

tlpy17-errors OBJECT-TYPE
    SYNTAX Integer32
    MAX-ACCESS accessible-for-notify
    STATUS current
    DESCRIPTION
        "Parameter 'errors' in event TLPY.17"
    ::= { tlpyEventObjects17 1 }

tlpy17-dial-peer OBJECT-TYPE
    SYNTAX Integer32
    MAX-ACCESS accessible-for-notify
    STATUS current
    DESCRIPTION
        "Parameter 'dial-peer' in event TLPY.17"
    ::= { tlpyEventObjects17 2 }

tlpyEventObjects18 OBJECT-IDENTITY
    STATUS current
    DESCRIPTION
        "Event TLPY.18
        Fax detected in this call, switching to fax mode"
    ::= { tlpyEventsGroup 18 }

tlpy18-cdr OBJECT-TYPE
    SYNTAX Integer32
    MAX-ACCESS accessible-for-notify
    STATUS current
    DESCRIPTION
        "Parameter 'cdr' in event TLPY.18"
    ::= { tlpyEventObjects18 1 }

tlpy18-mode OBJECT-TYPE
    SYNTAX DisplayString
    MAX-ACCESS accessible-for-notify
    STATUS current
    DESCRIPTION
        "Parameter 'mode' in event TLPY.18"
    ::= { tlpyEventObjects18 2 }

tlpyEventObjects19 OBJECT-IDENTITY
    STATUS current
    DESCRIPTION
        "Event TLPY.19
        Hold or unhold event"
    ::= { tlpyEventsGroup 19 }

tlpy19-event OBJECT-TYPE
    SYNTAX DisplayString
    MAX-ACCESS accessible-for-notify
    STATUS current
    DESCRIPTION
        "Parameter 'event' in event TLPY.19"
    ::= { tlpyEventObjects19 1 }

tlpy19-peer-name OBJECT-TYPE
    SYNTAX DisplayString
    MAX-ACCESS accessible-for-notify
    STATUS current
    DESCRIPTION
        "Parameter 'peer-name' in event TLPY.19"
    ::= { tlpyEventObjects19 2 }

tlpy19-peer-line OBJECT-TYPE
    SYNTAX Integer32
    MAX-ACCESS accessible-for-notify
    STATUS current
    DESCRIPTION
        "Parameter 'peer-line' in event TLPY.19"
    ::= { tlpyEventObjects19 3 }

tlpy19-called OBJECT-TYPE
    SYNTAX DisplayString
    MAX-ACCESS accessible-for-notify
    STATUS current
    DESCRIPTION
        "Parameter 'called' in event TLPY.19"
    ::= { tlpyEventObjects19 4 }

tlpy19-calling OBJECT-TYPE
    SYNTAX DisplayString
    MAX-ACCESS accessible-for-notify
    STATUS current
    DESCRIPTION
        "Parameter 'calling' in event TLPY.19"
    ::= { tlpyEventObjects19 5 }

tlpy19-cdr OBJECT-TYPE
    SYNTAX Integer32
    MAX-ACCESS accessible-for-notify
    STATUS current
    DESCRIPTION
        "Parameter 'cdr' in event TLPY.19"
    ::= { tlpyEventObjects19 6 }

tlpyEventObjects20 OBJECT-IDENTITY
    STATUS current
    DESCRIPTION
        "Event TLPY.20
        Call error event."
    ::= { tlpyEventsGroup 20 }

tlpy20-description OBJECT-TYPE
    SYNTAX DisplayString
    MAX-ACCESS accessible-for-notify
    STATUS current
    DESCRIPTION
        "Parameter 'description' in event TLPY.20"
    ::= { tlpyEventObjects20 1 }

tlpy20-incoming-dialpeer OBJECT-TYPE
    SYNTAX Integer32
    MAX-ACCESS accessible-for-notify
    STATUS current
    DESCRIPTION
        "Parameter 'incoming-dialpeer' in event TLPY.20"
    ::= { tlpyEventObjects20 2 }

tlpy20-outging-dialpeer OBJECT-TYPE
    SYNTAX Integer32
    MAX-ACCESS accessible-for-notify
    STATUS current
    DESCRIPTION
        "Parameter 'outging-dialpeer' in event TLPY.20"
    ::= { tlpyEventObjects20 3 }

tlpy20-cdr OBJECT-TYPE
    SYNTAX Integer32
    MAX-ACCESS accessible-for-notify
    STATUS current
    DESCRIPTION
        "Parameter 'cdr' in event TLPY.20"
    ::= { tlpyEventObjects20 4 }

tlpyEventObjects21 OBJECT-IDENTITY
    STATUS current
    DESCRIPTION
        "Event TLPY.21
        RTP VAD detected/undetected"
    ::= { tlpyEventsGroup 21 }

tlpy21-vad OBJECT-TYPE
    SYNTAX DisplayString
    MAX-ACCESS accessible-for-notify
    STATUS current
    DESCRIPTION
        "Parameter 'vad' in event TLPY.21"
    ::= { tlpyEventObjects21 1 }

tlpy21-id OBJECT-TYPE
    SYNTAX DisplayString
    MAX-ACCESS accessible-for-notify
    STATUS current
    DESCRIPTION
        "Parameter 'id' in event TLPY.21"
    ::= { tlpyEventObjects21 2 }

tlpy21-cdr OBJECT-TYPE
    SYNTAX Integer32
    MAX-ACCESS accessible-for-notify
    STATUS current
    DESCRIPTION
        "Parameter 'cdr' in event TLPY.21"
    ::= { tlpyEventObjects21 3 }

tlpyEventObjects22 OBJECT-IDENTITY
    STATUS current
    DESCRIPTION
        "Event TLPY.22
        RTP collection session detected/undetected"
    ::= { tlpyEventsGroup 22 }

tlpy22-action OBJECT-TYPE
    SYNTAX DisplayString
    MAX-ACCESS accessible-for-notify
    STATUS current
    DESCRIPTION
        "Parameter 'action' in event TLPY.22"
    ::= { tlpyEventObjects22 1 }

tlpy22-remote-ip OBJECT-TYPE
    SYNTAX IpAddress
    MAX-ACCESS accessible-for-notify
    STATUS current
    DESCRIPTION
        "Parameter 'remote-ip' in event TLPY.22"
    ::= { tlpyEventObjects22 2 }

tlpy22-remote-port OBJECT-TYPE
    SYNTAX Integer32
    MAX-ACCESS accessible-for-notify
    STATUS current
    DESCRIPTION
        "Parameter 'remote-port' in event TLPY.22"
    ::= { tlpyEventObjects22 3 }

tlpy22-ssrc OBJECT-TYPE
    SYNTAX Integer32
    MAX-ACCESS accessible-for-notify
    STATUS current
    DESCRIPTION
        "Parameter 'ssrc' in event TLPY.22"
    ::= { tlpyEventObjects22 4 }

tlpy22-id OBJECT-TYPE
    SYNTAX DisplayString
    MAX-ACCESS accessible-for-notify
    STATUS current
    DESCRIPTION
        "Parameter 'id' in event TLPY.22"
    ::= { tlpyEventObjects22 5 }

tlpy22-cdr OBJECT-TYPE
    SYNTAX Integer32
    MAX-ACCESS accessible-for-notify
    STATUS current
    DESCRIPTION
        "Parameter 'cdr' in event TLPY.22"
    ::= { tlpyEventObjects22 6 }

tlpyEventObjects23 OBJECT-IDENTITY
    STATUS current
    DESCRIPTION
        "Event TLPY.23
        Call transfer event."
    ::= { tlpyEventsGroup 23 }

tlpy23-original-call OBJECT-TYPE
    SYNTAX Integer32
    MAX-ACCESS accessible-for-notify
    STATUS current
    DESCRIPTION
        "Parameter 'original-call' in event TLPY.23"
    ::= { tlpyEventObjects23 1 }

tlpy23-consult-call OBJECT-TYPE
    SYNTAX Integer32
    MAX-ACCESS accessible-for-notify
    STATUS current
    DESCRIPTION
        "Parameter 'consult-call' in event TLPY.23"
    ::= { tlpyEventObjects23 2 }

tlpy23-new-call OBJECT-TYPE
    SYNTAX Integer32
    MAX-ACCESS accessible-for-notify
    STATUS current
    DESCRIPTION
        "Parameter 'new-call' in event TLPY.23"
    ::= { tlpyEventObjects23 3 }

tlpyEventObjects24 OBJECT-IDENTITY
    STATUS current
    DESCRIPTION
        "Event TLPY.24
        Outgoing type of peers allowed for incoming call."
    ::= { tlpyEventsGroup 24 }

tlpy24-allowed-peers OBJECT-TYPE
    SYNTAX DisplayString
    MAX-ACCESS accessible-for-notify
    STATUS current
    DESCRIPTION
        "Parameter 'allowed-peers' in event TLPY.24"
    ::= { tlpyEventObjects24 1 }

tlpyEventObjects25 OBJECT-IDENTITY
    STATUS current
    DESCRIPTION
        "Event TLPY.25
        Keeping old incoming dial-peer in a call transfer."
    ::= { tlpyEventsGroup 25 }

tlpy25-dialpeer OBJECT-TYPE
    SYNTAX Integer32
    MAX-ACCESS accessible-for-notify
    STATUS current
    DESCRIPTION
        "Parameter 'dialpeer' in event TLPY.25"
    ::= { tlpyEventObjects25 1 }

tlpy25-called-number OBJECT-TYPE
    SYNTAX DisplayString
    MAX-ACCESS accessible-for-notify
    STATUS current
    DESCRIPTION
        "Parameter 'called-number' in event TLPY.25"
    ::= { tlpyEventObjects25 2 }

tlpy25-calling-number OBJECT-TYPE
    SYNTAX DisplayString
    MAX-ACCESS accessible-for-notify
    STATUS current
    DESCRIPTION
        "Parameter 'calling-number' in event TLPY.25"
    ::= { tlpyEventObjects25 3 }

tlpyEventObjects26 OBJECT-IDENTITY
    STATUS current
    DESCRIPTION
        "Event TLPY.26
        Change in max calls alowed for call limit control."
    ::= { tlpyEventsGroup 26 }

tlpy26-id1 OBJECT-TYPE
    SYNTAX DisplayString
    MAX-ACCESS accessible-for-notify
    STATUS current
    DESCRIPTION
        "Parameter 'id1' in event TLPY.26"
    ::= { tlpyEventObjects26 1 }

tlpy26-id2 OBJECT-TYPE
    SYNTAX DisplayString
    MAX-ACCESS accessible-for-notify
    STATUS current
    DESCRIPTION
        "Parameter 'id2' in event TLPY.26"
    ::= { tlpyEventObjects26 2 }

tlpy26-max-calls OBJECT-TYPE
    SYNTAX Integer32
    MAX-ACCESS accessible-for-notify
    STATUS current
    DESCRIPTION
        "Parameter 'max-calls' in event TLPY.26"
    ::= { tlpyEventObjects26 3 }

tlpyEventObjects27 OBJECT-IDENTITY
    STATUS current
    DESCRIPTION
        "Event TLPY.27
        Telephony facility event."
    ::= { tlpyEventsGroup 27 }

tlpy27-event OBJECT-TYPE
    SYNTAX DisplayString
    MAX-ACCESS accessible-for-notify
    STATUS current
    DESCRIPTION
        "Parameter 'event' in event TLPY.27"
    ::= { tlpyEventObjects27 1 }

tlpy27-number OBJECT-TYPE
    SYNTAX DisplayString
    MAX-ACCESS accessible-for-notify
    STATUS current
    DESCRIPTION
        "Parameter 'number' in event TLPY.27"
    ::= { tlpyEventObjects27 2 }

tlpy27-in-dialpeer OBJECT-TYPE
    SYNTAX Integer32
    MAX-ACCESS accessible-for-notify
    STATUS current
    DESCRIPTION
        "Parameter 'in-dialpeer' in event TLPY.27"
    ::= { tlpyEventObjects27 3 }

tlpy27-out-dialpeer OBJECT-TYPE
    SYNTAX Integer32
    MAX-ACCESS accessible-for-notify
    STATUS current
    DESCRIPTION
        "Parameter 'out-dialpeer' in event TLPY.27"
    ::= { tlpyEventObjects27 4 }

tlpy27-call-cdr OBJECT-TYPE
    SYNTAX Integer32
    MAX-ACCESS accessible-for-notify
    STATUS current
    DESCRIPTION
        "Parameter 'call-cdr' in event TLPY.27"
    ::= { tlpyEventObjects27 5 }

tlpyEventObjects28 OBJECT-IDENTITY
    STATUS current
    DESCRIPTION
        "Event TLPY.28
        SRTP engine event"
    ::= { tlpyEventsGroup 28 }

tlpy28-event OBJECT-TYPE
    SYNTAX DisplayString
    MAX-ACCESS accessible-for-notify
    STATUS current
    DESCRIPTION
        "Parameter 'event' in event TLPY.28"
    ::= { tlpyEventObjects28 1 }

tlpyEventObjects29 OBJECT-IDENTITY
    STATUS current
    DESCRIPTION
        "Event TLPY.29
        Report events related to voice messages"
    ::= { tlpyEventsGroup 29 }

tlpy29-loc-index OBJECT-TYPE
    SYNTAX Integer32
    MAX-ACCESS accessible-for-notify
    STATUS current
    DESCRIPTION
        "Parameter 'loc-index' in event TLPY.29"
    ::= { tlpyEventObjects29 1 }

tlpy29-event OBJECT-TYPE
    SYNTAX DisplayString
    MAX-ACCESS accessible-for-notify
    STATUS current
    DESCRIPTION
        "Parameter 'event' in event TLPY.29"
    ::= { tlpyEventObjects29 2 }

tlpyEventObjects30 OBJECT-IDENTITY
    STATUS current
    DESCRIPTION
        "Event TLPY.30
        Report events related to no-answer timer"
    ::= { tlpyEventsGroup 30 }

tlpy30-event OBJECT-TYPE
    SYNTAX DisplayString
    MAX-ACCESS accessible-for-notify
    STATUS current
    DESCRIPTION
        "Parameter 'event' in event TLPY.30"
    ::= { tlpyEventObjects30 1 }

tlpy30-out-dp OBJECT-TYPE
    SYNTAX Integer32
    MAX-ACCESS accessible-for-notify
    STATUS current
    DESCRIPTION
        "Parameter 'out-dp' in event TLPY.30"
    ::= { tlpyEventObjects30 2 }

tlpyEventObjects31 OBJECT-IDENTITY
    STATUS current
    DESCRIPTION
        "Event TLPY.31
        RTP timeout reached event"
    ::= { tlpyEventsGroup 31 }

tlpy31-local-ip OBJECT-TYPE
    SYNTAX DisplayString
    MAX-ACCESS accessible-for-notify
    STATUS current
    DESCRIPTION
        "Parameter 'local-ip' in event TLPY.31"
    ::= { tlpyEventObjects31 1 }

tlpy31-local-port OBJECT-TYPE
    SYNTAX Integer32
    MAX-ACCESS accessible-for-notify
    STATUS current
    DESCRIPTION
        "Parameter 'local-port' in event TLPY.31"
    ::= { tlpyEventObjects31 2 }

tlpy31-cdr OBJECT-TYPE
    SYNTAX Integer32
    MAX-ACCESS accessible-for-notify
    STATUS current
    DESCRIPTION
        "Parameter 'cdr' in event TLPY.31"
    ::= { tlpyEventObjects31 3 }

tlpyEventObjects32 OBJECT-IDENTITY
    STATUS current
    DESCRIPTION
        "Event TLPY.32
        RTP reception started event"
    ::= { tlpyEventsGroup 32 }

tlpy32-local-ip OBJECT-TYPE
    SYNTAX DisplayString
    MAX-ACCESS accessible-for-notify
    STATUS current
    DESCRIPTION
        "Parameter 'local-ip' in event TLPY.32"
    ::= { tlpyEventObjects32 1 }

tlpy32-local-port OBJECT-TYPE
    SYNTAX Integer32
    MAX-ACCESS accessible-for-notify
    STATUS current
    DESCRIPTION
        "Parameter 'local-port' in event TLPY.32"
    ::= { tlpyEventObjects32 2 }

tlpy32-cdr OBJECT-TYPE
    SYNTAX Integer32
    MAX-ACCESS accessible-for-notify
    STATUS current
    DESCRIPTION
        "Parameter 'cdr' in event TLPY.32"
    ::= { tlpyEventObjects32 3 }

tlpyEventObjects33 OBJECT-IDENTITY
    STATUS current
    DESCRIPTION
        "Event TLPY.33
        The OOD (Out of Dialog) OPTIONS keepalive process for the given
        dial-peer switched to the specified status."
    ::= { tlpyEventsGroup 33 }

tlpy33-dialpeer OBJECT-TYPE
    SYNTAX Integer32
    MAX-ACCESS accessible-for-notify
    STATUS current
    DESCRIPTION
        "Parameter 'dialpeer' in event TLPY.33"
    ::= { tlpyEventObjects33 1 }

tlpy33-status OBJECT-TYPE
    SYNTAX DisplayString
    MAX-ACCESS accessible-for-notify
    STATUS current
    DESCRIPTION
        "Parameter 'status' in event TLPY.33"
    ::= { tlpyEventObjects33 2 }


tlpyNotification1 NOTIFICATION-TYPE
    OBJECTS { 
              tlpy1-event, 
              tlpy1-caller,
              tlpy1-indp,
              tlpy1-called,
              tlpy1-outdp,
              tlpy1-cdr 
            }
    STATUS current
    DESCRIPTION
        "Notification of Event TLPY.1

        Message: 'Call $1 in $2(dp $3) out $4(dp $5) cdr $6'

        Parameters list:
              $1: tlpy1-event
              $2: tlpy1-caller
              $3: tlpy1-indp
              $4: tlpy1-called
              $5: tlpy1-outdp
              $6: tlpy1-cdr

        Call events."
    ::= { tlpyNotificationsPrefix 1 }

tlpyNotification2 NOTIFICATION-TYPE
    OBJECTS { 
              tlpy2-call1, 
              tlpy2-call2 
            }
    STATUS current
    DESCRIPTION
        "Notification of Event TLPY.2

        Message: 'Call transfer $1->$2'

        Parameters list:
              $1: tlpy2-call1
              $2: tlpy2-call2

        Call transfer event."
    ::= { tlpyNotificationsPrefix 2 }

tlpyNotification3 NOTIFICATION-TYPE
    OBJECTS { 
              tlpy3-dialpeer, 
              tlpy3-status 
            }
    STATUS current
    DESCRIPTION
        "Notification of Event TLPY.3

        Message: 'NSLA dial-peer $1 status changed to $2'

        Parameters list:
              $1: tlpy3-dialpeer
              $2: tlpy3-status

        NSLA changed."
    ::= { tlpyNotificationsPrefix 3 }

tlpyNotification4 NOTIFICATION-TYPE
    OBJECTS { 
              tlpy4-calltype, 
              tlpy4-status 
            }
    STATUS current
    DESCRIPTION
        "Notification of Event TLPY.4

        Message: '$1 calls control status changed to $2'

        Parameters list:
              $1: tlpy4-calltype
              $2: tlpy4-status

        Control status changed."
    ::= { tlpyNotificationsPrefix 4 }

tlpyNotification5 NOTIFICATION-TYPE
    OBJECTS { 
              tlpy5-dialpeer, 
              tlpy5-called-number,
              tlpy5-calling-number 
            }
    STATUS current
    DESCRIPTION
        "Notification of Event TLPY.5

        Message: 'Incoming dial-peer found $1 called $2 calling $3'

        Parameters list:
              $1: tlpy5-dialpeer
              $2: tlpy5-called-number
              $3: tlpy5-calling-number

        Found dial-peer."
    ::= { tlpyNotificationsPrefix 5 }

tlpyNotification6 NOTIFICATION-TYPE
    OBJECTS { 
              tlpy6-dialpeer, 
              tlpy6-called-number 
            }
    STATUS current
    DESCRIPTION
        "Notification of Event TLPY.6

        Message: 'Outgoing dial-peer found $1 called $2'

        Parameters list:
              $1: tlpy6-dialpeer
              $2: tlpy6-called-number

        Found dial-peer."
    ::= { tlpyNotificationsPrefix 6 }

tlpyNotification7 NOTIFICATION-TYPE
    OBJECTS { 
              tlpy7-direction, 
              tlpy7-called-number,
              tlpy7-calling-number 
            }
    STATUS current
    DESCRIPTION
        "Notification of Event TLPY.7

        Message: '$1 dial-peer not found called $2 calling $3'

        Parameters list:
              $1: tlpy7-direction
              $2: tlpy7-called-number
              $3: tlpy7-calling-number

        Dial-peer not found."
    ::= { tlpyNotificationsPrefix 7 }

tlpyNotification8 NOTIFICATION-TYPE
    OBJECTS { 
              tlpy8-num, 
              tlpy8-per,
              tlpy8-id,
              tlpy8-cdr 
            }
    STATUS current
    DESCRIPTION
        "Notification of Event TLPY.8

        Message: 'RTP lost frames $1 percentage $2$3 call cdr $4'

        Parameters list:
              $1: tlpy8-num
              $2: tlpy8-per
              $3: tlpy8-id
              $4: tlpy8-cdr

        This message shows the percentage of lost frames in the last second."
    ::= { tlpyNotificationsPrefix 8 }

tlpyNotification9 NOTIFICATION-TYPE
    OBJECTS { 
              tlpy9-text, 
              tlpy9-id,
              tlpy9-cdr 
            }
    STATUS current
    DESCRIPTION
        "Notification of Event TLPY.9

        Message: 'RTP:$1 $2 call cdr $3'

        Parameters list:
              $1: tlpy9-text
              $2: tlpy9-id
              $3: tlpy9-cdr

        Display several statistical values for current delay computation."
    ::= { tlpyNotificationsPrefix 9 }

tlpyNotification10 NOTIFICATION-TYPE
    OBJECTS { 
              tlpy10-delay, 
              tlpy10-jitter,
              tlpy10-id,
              tlpy10-cdr 
            }
    STATUS current
    DESCRIPTION
        "Notification of Event TLPY.10

        Message: 'Delay $1 ms Var $2 ms $3 call cdr $4'

        Parameters list:
              $1: tlpy10-delay
              $2: tlpy10-jitter
              $3: tlpy10-id
              $4: tlpy10-cdr

        This message gives information about the delay and variance measured in
        a communication."
    ::= { tlpyNotificationsPrefix 10 }

tlpyNotification11 NOTIFICATION-TYPE
    OBJECTS { 
              tlpy11-delay, 
              tlpy11-id,
              tlpy11-cdr 
            }
    STATUS current
    DESCRIPTION
        "Notification of Event TLPY.11

        Message: 'Mn-Dly Out: dly $1 $2 call cdr $3'

        Parameters list:
              $1: tlpy11-delay
              $2: tlpy11-id
              $3: tlpy11-cdr

        RTP mean delay out."
    ::= { tlpyNotificationsPrefix 11 }

tlpyNotification12 NOTIFICATION-TYPE
    OBJECTS { 
              tlpy12-id, 
              tlpy12-cdr 
            }
    STATUS current
    DESCRIPTION
        "Notification of Event TLPY.12

        Message: 'Sync Tmstamp $1 call cdr $2'

        Parameters list:
              $1: tlpy12-id
              $2: tlpy12-cdr

        RTP synchronize."
    ::= { tlpyNotificationsPrefix 12 }

tlpyNotification13 NOTIFICATION-TYPE
    OBJECTS { 
              tlpy13-CurrDelay, 
              tlpy13-PlyDelay,
              tlpy13-id,
              tlpy13-cdr 
            }
    STATUS current
    DESCRIPTION
        "Notification of Event TLPY.13

        Message: 'Lost Frame current delay $1 Playing delay $2 $3 call cdr $4'

        Parameters list:
              $1: tlpy13-CurrDelay
              $2: tlpy13-PlyDelay
              $3: tlpy13-id
              $4: tlpy13-cdr

        Lost a too delayed frame."
    ::= { tlpyNotificationsPrefix 13 }

tlpyNotification14 NOTIFICATION-TYPE
    OBJECTS { 
              tlpy14-action, 
              tlpy14-called-number,
              tlpy14-calling-number,
              tlpy14-codec-str,
              tlpy14-nob,
              tlpy14-vad,
              tlpy14-cdr 
            }
    STATUS current
    DESCRIPTION
        "Notification of Event TLPY.14

        Message: 'Codec $1 Call: $2/$3 (called/calling), codec $4, nob $5, vad $6, cdr $7'

        Parameters list:
              $1: tlpy14-action
              $2: tlpy14-called-number
              $3: tlpy14-calling-number
              $4: tlpy14-codec-str
              $5: tlpy14-nob
              $6: tlpy14-vad
              $7: tlpy14-cdr

        Codec added or removed from call."
    ::= { tlpyNotificationsPrefix 14 }

tlpyNotification15 NOTIFICATION-TYPE
    OBJECTS { 
              tlpy15-type, 
              tlpy15-peergroup,
              tlpy15-dial-peer,
              tlpy15-telephone,
              tlpy15-cdr 
            }
    STATUS current
    DESCRIPTION
        "Notification of Event TLPY.15

        Message: 'Call forward ($1): $2/$3 (group/dp), phone $4, cdr $5'

        Parameters list:
              $1: tlpy15-type
              $2: tlpy15-peergroup
              $3: tlpy15-dial-peer
              $4: tlpy15-telephone
              $5: tlpy15-cdr

        Call jump event."
    ::= { tlpyNotificationsPrefix 15 }

tlpyNotification16 NOTIFICATION-TYPE
    OBJECTS { 
              tlpy16-file, 
              tlpy16-state,
              tlpy16-size 
            }
    STATUS current
    DESCRIPTION
        "Notification of Event TLPY.16

        Message: 'CDR file $1 state $2 size $3'

        Parameters list:
              $1: tlpy16-file
              $2: tlpy16-state
              $3: tlpy16-size

        CDR file information."
    ::= { tlpyNotificationsPrefix 16 }

tlpyNotification17 NOTIFICATION-TYPE
    OBJECTS { 
              tlpy17-errors, 
              tlpy17-dial-peer 
            }
    STATUS current
    DESCRIPTION
        "Notification of Event TLPY.17

        Message: 'Warning: $1 consecutive errors in dial-peer $2'

        Parameters list:
              $1: tlpy17-errors
              $2: tlpy17-dial-peer

        Warning, too many consecutive errors."
    ::= { tlpyNotificationsPrefix 17 }

tlpyNotification18 NOTIFICATION-TYPE
    OBJECTS { 
              tlpy18-cdr, 
              tlpy18-mode 
            }
    STATUS current
    DESCRIPTION
        "Notification of Event TLPY.18

        Message: 'Fax detected in call $1, switching to $2'

        Parameters list:
              $1: tlpy18-cdr
              $2: tlpy18-mode

        Fax detected in this call, switching to fax mode"
    ::= { tlpyNotificationsPrefix 18 }

tlpyNotification19 NOTIFICATION-TYPE
    OBJECTS { 
              tlpy19-event, 
              tlpy19-peer-name,
              tlpy19-peer-line,
              tlpy19-called,
              tlpy19-calling,
              tlpy19-cdr 
            }
    STATUS current
    DESCRIPTION
        "Notification of Event TLPY.19

        Message: 'Event: $1 Peer: $2/$3 Call: $4/$5 (called/calling) cdr $6'

        Parameters list:
              $1: tlpy19-event
              $2: tlpy19-peer-name
              $3: tlpy19-peer-line
              $4: tlpy19-called
              $5: tlpy19-calling
              $6: tlpy19-cdr

        Hold or unhold event"
    ::= { tlpyNotificationsPrefix 19 }

tlpyNotification20 NOTIFICATION-TYPE
    OBJECTS { 
              tlpy20-description, 
              tlpy20-incoming-dialpeer,
              tlpy20-outging-dialpeer,
              tlpy20-cdr 
            }
    STATUS current
    DESCRIPTION
        "Notification of Event TLPY.20

        Message: 'Error $1. in dp $2 out dp $3 cdr $4'

        Parameters list:
              $1: tlpy20-description
              $2: tlpy20-incoming-dialpeer
              $3: tlpy20-outging-dialpeer
              $4: tlpy20-cdr

        Call error event."
    ::= { tlpyNotificationsPrefix 20 }

tlpyNotification21 NOTIFICATION-TYPE
    OBJECTS { 
              tlpy21-vad, 
              tlpy21-id,
              tlpy21-cdr 
            }
    STATUS current
    DESCRIPTION
        "Notification of Event TLPY.21

        Message: 'VAD $1 in $2 cdr $3'

        Parameters list:
              $1: tlpy21-vad
              $2: tlpy21-id
              $3: tlpy21-cdr

        RTP VAD detected/undetected"
    ::= { tlpyNotificationsPrefix 21 }

tlpyNotification22 NOTIFICATION-TYPE
    OBJECTS { 
              tlpy22-action, 
              tlpy22-remote-ip,
              tlpy22-remote-port,
              tlpy22-ssrc,
              tlpy22-id,
              tlpy22-cdr 
            }
    STATUS current
    DESCRIPTION
        "Notification of Event TLPY.22

        Message: 'Rtp source $1 from $2:$3 ssrc $4 in $5 cdr $6'

        Parameters list:
              $1: tlpy22-action
              $2: tlpy22-remote-ip
              $3: tlpy22-remote-port
              $4: tlpy22-ssrc
              $5: tlpy22-id
              $6: tlpy22-cdr

        RTP collection session detected/undetected"
    ::= { tlpyNotificationsPrefix 22 }

tlpyNotification23 NOTIFICATION-TYPE
    OBJECTS { 
              tlpy23-original-call, 
              tlpy23-consult-call,
              tlpy23-new-call 
            }
    STATUS current
    DESCRIPTION
        "Notification of Event TLPY.23

        Message: 'Call transfer: orig $1 cnsl $2 new $3'

        Parameters list:
              $1: tlpy23-original-call
              $2: tlpy23-consult-call
              $3: tlpy23-new-call

        Call transfer event."
    ::= { tlpyNotificationsPrefix 23 }

tlpyNotification24 NOTIFICATION-TYPE
    OBJECTS { 
              tlpy24-allowed-peers 
            }
    STATUS current
    DESCRIPTION
        "Notification of Event TLPY.24

        Message: 'Out peers allowed: $1'

        Parameters list:
              $1: tlpy24-allowed-peers

        Outgoing type of peers allowed for incoming call."
    ::= { tlpyNotificationsPrefix 24 }

tlpyNotification25 NOTIFICATION-TYPE
    OBJECTS { 
              tlpy25-dialpeer, 
              tlpy25-called-number,
              tlpy25-calling-number 
            }
    STATUS current
    DESCRIPTION
        "Notification of Event TLPY.25

        Message: 'Keeping old incoming dial-peer $1 called $2 calling $3'

        Parameters list:
              $1: tlpy25-dialpeer
              $2: tlpy25-called-number
              $3: tlpy25-calling-number

        Keeping old incoming dial-peer in a call transfer."
    ::= { tlpyNotificationsPrefix 25 }

tlpyNotification26 NOTIFICATION-TYPE
    OBJECTS { 
              tlpy26-id1, 
              tlpy26-id2,
              tlpy26-max-calls 
            }
    STATUS current
    DESCRIPTION
        "Notification of Event TLPY.26

        Message: 'CAC change Id1: $1, Id2: $2, Max Calls: $3'

        Parameters list:
              $1: tlpy26-id1
              $2: tlpy26-id2
              $3: tlpy26-max-calls

        Change in max calls alowed for call limit control."
    ::= { tlpyNotificationsPrefix 26 }

tlpyNotification27 NOTIFICATION-TYPE
    OBJECTS { 
              tlpy27-event, 
              tlpy27-number,
              tlpy27-in-dialpeer,
              tlpy27-out-dialpeer,
              tlpy27-call-cdr 
            }
    STATUS current
    DESCRIPTION
        "Notification of Event TLPY.27

        Message: 'Tlphy facility: $1, tlph $2, in $3, out $4, cdr $5'

        Parameters list:
              $1: tlpy27-event
              $2: tlpy27-number
              $3: tlpy27-in-dialpeer
              $4: tlpy27-out-dialpeer
              $5: tlpy27-call-cdr

        Telephony facility event."
    ::= { tlpyNotificationsPrefix 27 }

tlpyNotification28 NOTIFICATION-TYPE
    OBJECTS { 
              tlpy28-event 
            }
    STATUS current
    DESCRIPTION
        "Notification of Event TLPY.28

        Message: 'SRTP: $1'

        Parameters list:
              $1: tlpy28-event

        SRTP engine event"
    ::= { tlpyNotificationsPrefix 28 }

tlpyNotification29 NOTIFICATION-TYPE
    OBJECTS { 
              tlpy29-loc-index, 
              tlpy29-event 
            }
    STATUS current
    DESCRIPTION
        "Notification of Event TLPY.29

        Message: 'Voice message $1: $2'

        Parameters list:
              $1: tlpy29-loc-index
              $2: tlpy29-event

        Report events related to voice messages"
    ::= { tlpyNotificationsPrefix 29 }

tlpyNotification30 NOTIFICATION-TYPE
    OBJECTS { 
              tlpy30-event, 
              tlpy30-out-dp 
            }
    STATUS current
    DESCRIPTION
        "Notification of Event TLPY.30

        Message: 'No-answer timer $1 for dp $2'

        Parameters list:
              $1: tlpy30-event
              $2: tlpy30-out-dp

        Report events related to no-answer timer"
    ::= { tlpyNotificationsPrefix 30 }

tlpyNotification31 NOTIFICATION-TYPE
    OBJECTS { 
              tlpy31-local-ip, 
              tlpy31-local-port,
              tlpy31-cdr 
            }
    STATUS current
    DESCRIPTION
        "Notification of Event TLPY.31

        Message: 'RTP timeout reached, no RTP received at $1:$2, call cdr $3'

        Parameters list:
              $1: tlpy31-local-ip
              $2: tlpy31-local-port
              $3: tlpy31-cdr

        RTP timeout reached event"
    ::= { tlpyNotificationsPrefix 31 }

tlpyNotification32 NOTIFICATION-TYPE
    OBJECTS { 
              tlpy32-local-ip, 
              tlpy32-local-port,
              tlpy32-cdr 
            }
    STATUS current
    DESCRIPTION
        "Notification of Event TLPY.32

        Message: 'RTP reception started at $1:$2, call cdr $3'

        Parameters list:
              $1: tlpy32-local-ip
              $2: tlpy32-local-port
              $3: tlpy32-cdr

        RTP reception started event"
    ::= { tlpyNotificationsPrefix 32 }

tlpyNotification33 NOTIFICATION-TYPE
    OBJECTS { 
              tlpy33-dialpeer, 
              tlpy33-status 
            }
    STATUS current
    DESCRIPTION
        "Notification of Event TLPY.33

        Message: 'OPTIONS keepalive dial-peer $1 status changed to $2'

        Parameters list:
              $1: tlpy33-dialpeer
              $2: tlpy33-status

        The OOD (Out of Dialog) OPTIONS keepalive process for the given
        dial-peer switched to the specified status."
    ::= { tlpyNotificationsPrefix 33 }


END
